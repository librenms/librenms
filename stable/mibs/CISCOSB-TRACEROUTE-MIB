CISCOSB-TRACEROUTE-MIB DEFINITIONS ::= BEGIN

-- Title:                CISCOSB ROS
--                       Private Trace Route MIB
-- Version:              7.46
-- Date:                 15-Jan-2007

IMPORTS
    switch001                                                    FROM CISCOSB-MIB
    OBJECT-TYPE, MODULE-IDENTITY                            FROM SNMPv2-SMI;

rlTraceRoute MODULE-IDENTITY
                LAST-UPDATED "200701020000Z"
				ORGANIZATION "Cisco Small Business"

				CONTACT-INFO
				"Postal: 170 West Tasman Drive
				San Jose , CA 95134-1706
				USA

				Website: Cisco Small Business Home http://www.cisco.com/smb>;,
				Cisco Small Business Support Community <http://www.cisco.com/go/smallbizsupport>"

                DESCRIPTION
                      "This private MIB module defines TRACE ROUTE private MIBs."
                REVISION "200701020000Z"
                DESCRIPTION
                      "Initial revision."
        ::= { switch001 81 }

rlTraceRouteMibVersion OBJECT-TYPE
    SYNTAX  INTEGER
    MAX-ACCESS  read-only
    STATUS  current
    DESCRIPTION
        "MIB's version, the current version is 1."
    ::= { rlTraceRoute 1 }

END
