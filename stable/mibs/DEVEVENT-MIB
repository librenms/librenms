DEVEVENT-MIB DEFINITIONS ::= BEGIN

	IMPORTS
		OBJECT-TYPE, MODULE-IDENTITY
			FROM SNMPv2-SMI
		DisplayString
			FROM SNMPv2-TC
		device
			FROM ANIROOT-MIB;

-- the aniDevEventTable group

aniDevEvent  MODULE-IDENTITY
           LAST-UPDATED "0012111753Z"      -- Mon Dec 11 17:53:04 PDT 2000
           ORGANIZATION "Aperto Networks"
           CONTACT-INFO
          " 
          Postal: Aperto Networks Inc
                  1637 S Main Street 
                  Milpitas, California 95035
          Tel:    +1 408 719 9977
	  "
	DESCRIPTION
	"This group contains the Event Notification group.  

	 Event Notification can be sent through email by 
	 configuring the aniDevEvNotify group. Note that the
	 SMTP Server Address (aniDevSmtpServer from the
	 device_server.mib) should also be configured to send email.

	 Currently, viewing/clearing of Event Log Table through SNMP Agent
	 is not supported.
	"
     ::= { device 6 }


	-- The Event Notification Group

aniDevEvNotify  OBJECT IDENTIFIER
	--DEFAULT next-function-async     std_next_async
        ::= { aniDevEvent 2 }

aniDevEmailSending  OBJECT-TYPE 	  
	SYNTAX	INTEGER {
		enable(1),
		disable(2)
	}           
	MAX-ACCESS  read-write
	STATUS      current
	DESCRIPTION
	   "Enable or disable email sending.
	   "
	--DEFAULT next-function-async     std_next_async
	::= { aniDevEvNotify 1 }

aniDevEmailSender  OBJECT-TYPE
	SYNTAX      DisplayString (SIZE (0..80)) 
	MAX-ACCESS  read-write
	STATUS      current
	DESCRIPTION
	   "The email address for the sender.
	   "
	--DEFAULT next-function-async     std_next_async
	::= { aniDevEvNotify 2 }

aniDevDomainName  OBJECT-TYPE
	SYNTAX      DisplayString (SIZE (0..80)) 
	MAX-ACCESS  read-write
	STATUS      current
	DESCRIPTION
	   "The domain name.
	   "
	--DEFAULT next-function-async     std_next_async
	::= { aniDevEvNotify 3 }
        
aniDevEmailReceiver1  OBJECT-TYPE
	SYNTAX      DisplayString (SIZE (0..80)) 
	MAX-ACCESS  read-write
	STATUS      current
	DESCRIPTION
	   "The email address for the first receiver.
	   "
	--DEFAULT next-function-async     std_next_async
	::= { aniDevEvNotify 4 }
        
aniDevEmailReceiver2  OBJECT-TYPE
	SYNTAX      DisplayString (SIZE (0..80)) 
	MAX-ACCESS  read-write
	STATUS      current
	DESCRIPTION
	   "The email address for the second receiver.
	   "
	--DEFAULT next-function-async     std_next_async
	::= { aniDevEvNotify 5 }

          END
