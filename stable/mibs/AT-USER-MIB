-- ============================================================================
-- AT-USER.MIB, Allied Telesis enterprise MIB:USER
-- 
-- Copyright (c) 2008 by Allied Telesis, Inc.
-- All rights reserved.
-- 
-- ============================================================================

	AT-USER-MIB DEFINITIONS ::= BEGIN
 
		IMPORTS
			sysinfo			
				FROM AT-SMI-MIB			
			Unsigned32, OBJECT-TYPE, MODULE-IDENTITY			
				FROM SNMPv2-SMI			
			DisplayString			
				FROM SNMPv2-TC;
		-- 1.3.6.1.4.1.207.8.4.4.3.20
		user MODULE-IDENTITY 
			LAST-UPDATED "200811251200Z"		-- Nov 25, 2008 at 12:00 GMT
			ORGANIZATION 
				"Allied Telesis, Inc."
			CONTACT-INFO 
				"  http://www.alliedtelesis.com"
			DESCRIPTION 
				"The AT-USER MIB contains objects for displaying information of
				users currently logged into a device, or configured in the local
				user data base of the device."
			REVISION "200810161200Z"
			DESCRIPTION 
				"Add objects for local user data base information."
			REVISION "200808260000Z"		-- August 26, 2008 at 00:00 GMT
			DESCRIPTION 
				"Initial version."
			::= { sysinfo 20 }

		
	
	
--
-- Node definitions
--
	
		-- 1.3.6.1.4.1.207.8.4.4.3.12.1
		userInfoTable OBJECT-TYPE
			SYNTAX SEQUENCE OF UserInfoEntry
			MAX-ACCESS not-accessible
			STATUS current
			DESCRIPTION
				"A table of information about users. Each entry in the table
				represents a user currently logged into the device."
			::= { user 1 }

		
		-- 1.3.6.1.4.1.207.8.4.4.3.12.1.1
		userInfoEntry OBJECT-TYPE
			SYNTAX UserInfoEntry
			MAX-ACCESS not-accessible
			STATUS current
			DESCRIPTION
				"Information on a user currently logged into the device."
			INDEX { userInfoType, userInfoIndex }
			::= { userInfoTable 1 }

		
		UserInfoEntry ::=
			SEQUENCE { 
				userInfoType
					INTEGER,
				userInfoIndex
					Unsigned32,
				userInfoUserName
					DisplayString,
				userInfoPrivilegeLevel
					Unsigned32,
				userInfoIdleTime
					DisplayString,
				userInfoLocation
					DisplayString
			 }

		-- 1.3.6.1.4.1.207.8.4.4.3.12.1.1.1
		userInfoType OBJECT-TYPE
			SYNTAX INTEGER
				{
				console(1),
				aux(2),
				telnet(3),
				script(4),
				stack(5)
				}
			MAX-ACCESS not-accessible
			STATUS current
			DESCRIPTION
				"The type of connection through which the user logged into 
				the device."
			::= { userInfoEntry 1 }

		
		-- 1.3.6.1.4.1.207.8.4.4.3.12.1.1.2
		userInfoIndex OBJECT-TYPE
			SYNTAX Unsigned32 (1..16)
			MAX-ACCESS not-accessible
			STATUS current
			DESCRIPTION
				"The index of the line upon which the user logged into
				 the device."
			::= { userInfoEntry 2 }

		
		-- 1.3.6.1.4.1.207.8.4.4.3.12.1.1.3
		userInfoUserName OBJECT-TYPE
			SYNTAX DisplayString
			MAX-ACCESS read-only
			STATUS current
			DESCRIPTION
				"This object represents the user name of the user 
				 currently logged into the device."
			::= { userInfoEntry 3 }

		
		-- 1.3.6.1.4.1.207.8.4.4.3.12.1.1.4
		userInfoPrivilegeLevel OBJECT-TYPE
			SYNTAX Unsigned32 (1..15)
			MAX-ACCESS read-only
			STATUS current
			DESCRIPTION
				"This object indicates the privilege level the user is granted."
			::= { userInfoEntry 4 }

		
		-- 1.3.6.1.4.1.207.8.4.4.3.12.1.1.5
		userInfoIdleTime OBJECT-TYPE
			SYNTAX DisplayString
			MAX-ACCESS read-only
			STATUS current
			DESCRIPTION
				"This object indicates the amount of time since the user was last 
				active. It is in the form of hh:mm:ss."
			::= { userInfoEntry 5 }

		
		-- 1.3.6.1.4.1.207.8.4.4.3.12.1.1.6
		userInfoLocation OBJECT-TYPE
			SYNTAX DisplayString
			MAX-ACCESS read-only
			STATUS current
			DESCRIPTION
				"This object indicates the location or login method of the user.
				It can be an IP address used by the user to telnet into the device,
                                or an asyn port, etc."
			::= { userInfoEntry 6 }

		
		-- 1.3.6.1.4.1.207.8.4.4.3.12.2
		userConfigTable OBJECT-TYPE
			SYNTAX SEQUENCE OF UserConfigEntry
			MAX-ACCESS not-accessible
			STATUS current
			DESCRIPTION
				"A table of user configuration information. Each entry
				in the table represents a user configured in the local user 
				data base of the device."
			::= { user 2 }

		
		-- 1.3.6.1.4.1.207.8.4.4.3.12.2.1
		userConfigEntry OBJECT-TYPE
			SYNTAX UserConfigEntry
			MAX-ACCESS not-accessible
			STATUS current
			DESCRIPTION
				"A conceptual entry in the userConfigTable."
			INDEX { userConfigIndex }
			::= { userConfigTable 1 }

		
		UserConfigEntry ::=
			SEQUENCE { 
				userConfigIndex
					Unsigned32,
				userConfigUsername
					DisplayString,
				userConfigPrivilegeLevel
					Unsigned32
			 }

		
		-- 1.3.6.1.4.1.207.8.4.4.3.12.2.1.1
		userConfigIndex OBJECT-TYPE
			SYNTAX Unsigned32
			MAX-ACCESS not-accessible
			STATUS current
			DESCRIPTION
				"The index used to identify entries in the userConfigTable."
			::= { userConfigEntry 1 }
		
		-- 1.3.6.1.4.1.207.8.4.4.3.12.2.1.2
		userConfigUsername OBJECT-TYPE
			SYNTAX DisplayString
			MAX-ACCESS read-only
			STATUS current
			DESCRIPTION
				"This object represents the user's name in configuration."
			::= { userConfigEntry 2 }
		
		-- 1.3.6.1.4.1.207.8.4.4.3.12.2.1.3
		userConfigPrivilegeLevel OBJECT-TYPE
			SYNTAX Unsigned32 (1..15)
			MAX-ACCESS read-only
			STATUS current
			DESCRIPTION
				"This object represents the user's privilege level in configuration."
			::= { userConfigEntry 3 }
	
	END

--
-- AT-USER.MIB
--
