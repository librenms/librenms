WATCHGUARD-PRODUCTS-MIB DEFINITIONS ::= BEGIN

IMPORTS

    MODULE-IDENTITY     FROM    SNMPv2-SMI
    watchguard          FROM    WATCHGUARD-SMI;

wgProducts MODULE-IDENTITY
    LAST-UPDATED "200811100000Z"
    ORGANIZATION "WatchGuard Technologies, Inc."
    CONTACT-INFO
            "    Ella Yu
                 WatchGuard Technologies, Inc.
                 15901 Red Hill Avenue, Suite 202
                 Tustin, CA 92780
                 USA
                    
                 714-258-4598
                 ella.yu@watchguard.com
            "
    DESCRIPTION
            "This MIB module definesthe object identifiers  
            for WatchGuard Technologies Products."
    REVISION
            "200811100000Z"
    DESCRIPTION
            "Initial version."
    ::= { watchguard 1 }

fbXSeries OBJECT IDENTIFIER ::= { wgProducts 4 }
xtmSeries OBJECT IDENTIFIER ::= { wgProducts 5 }

-- fbX series
fbX500     OBJECT IDENTIFIER ::= { fbXSeries 1 }
fbX550e    OBJECT IDENTIFIER ::= { fbXSeries 2 }
fbX700     OBJECT IDENTIFIER ::= { fbXSeries 3 }
fbX750e    OBJECT IDENTIFIER ::= { fbXSeries 4 }
fbX750e-4  OBJECT IDENTIFIER ::= { fbXSeries 5 }
fbX1000    OBJECT IDENTIFIER ::= { fbXSeries 6 }
fbX1250e   OBJECT IDENTIFIER ::= { fbXSeries 7 }
fbX1250e-4 OBJECT IDENTIFIER ::= { fbXSeries 8 }
fbX2500    OBJECT IDENTIFIER ::= { fbXSeries 9 }
fbX5000    OBJECT IDENTIFIER ::= { fbXSeries 10 }
fbX5500e   OBJECT IDENTIFIER ::= { fbXSeries 11 }
fbX6000    OBJECT IDENTIFIER ::= { fbXSeries 12 }
fbX6500e   OBJECT IDENTIFIER ::= { fbXSeries 13 }
fbX8000    OBJECT IDENTIFIER ::= { fbXSeries 14 }
fbX8500e   OBJECT IDENTIFIER ::= { fbXSeries 15 }
fbX8500e-F OBJECT IDENTIFIER ::= { fbXSeries 16 }
fbX10e     OBJECT IDENTIFIER ::= { fbXSeries 17 }
fbX10e-W   OBJECT IDENTIFIER ::= { fbXSeries 18 }
fbX20e     OBJECT IDENTIFIER ::= { fbXSeries 19 }
fbX20e-W   OBJECT IDENTIFIER ::= { fbXSeries 20 }
fbX55e     OBJECT IDENTIFIER ::= { fbXSeries 21 }
fbX55e-W   OBJECT IDENTIFIER ::= { fbXSeries 22 }

-- xtm series
xtm1050    OBJECT IDENTIFIER ::= { xtmSeries 1 }
xtm1050-F  OBJECT IDENTIFIER ::= { XTMSeries 2 }
xtm830-F   OBJECT IDENTIFIER ::= { XTMSeries 3 }
xtm830     OBJECT IDENTIFIER ::= { XTMSeries 4 }
xtm820     OBJECT IDENTIFIER ::= { XTMSeries 5 }
xtm810     OBJECT IDENTIFIER ::= { XTMSeries 6 }
xtm530     OBJECT IDENTIFIER ::= { XTMSeries 7 }
xtm520     OBJECT IDENTIFIER ::= { XTMSeries 8 }
xtm510     OBJECT IDENTIFIER ::= { XTMSeries 9 }
xtm23      OBJECT IDENTIFIER ::= { XTMSeries 10 }
xtm22      OBJECT IDENTIFIER ::= { XTMSeries 11 }
xtm21      OBJECT IDENTIFIER ::= { XTMSeries 12 }
xtm23-W    OBJECT IDENTIFIER ::= { XTMSeries 13 }
xtm22-W    OBJECT IDENTIFIER ::= { XTMSeries 14 }
xtm21-W    OBJECT IDENTIFIER ::= { XTMSeries 15 }

END
