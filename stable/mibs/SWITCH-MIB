--
--
--	01/14/97 - moved DEFAULT keywords to switchProduct.ext file for
--             Epilogue compiler
--

SWITCH-MIB

DEFINITIONS ::= BEGIN

IMPORTS

    MODULE-IDENTITY, OBJECT-TYPE	FROM SNMPv2-SMI
    TEXTUAL-CONVENTION	FROM SNMPv2-TC
    switchProduct		FROM TELESYN-ATI-TC
    pPortNumber			FROM SWITCH-VLAN-MIB;

	switchProductMib MODULE-IDENTITY
		LAST-UPDATED "9701142000Z"
	ORGANIZATION ""
	CONTACT-INFO ""
	DESCRIPTION  
			"The MIB module for supporting HS150 product specific MIB
			objects."
		REVISION "9701140800Z"
		DESCRIPTION
			"Added additional enumerations to uplinkSwitchChassisType."
		REVISION "9608222200Z"
		DESCRIPTION
			"Initial creation."
		::= { switchProduct 1 }


	uplinkSwitchChassisType	OBJECT-TYPE
		SYNTAX	INTEGER {
			modelB(1),
			modelB2(2),
			modelCplus(3),
			modelCminus(4),
			modelBFx2(5),
			modelFx(6),
			modelFx2(7),
			modelFxB2(8),
			modelBminusFx2(9),
			modelCfx(10),
			modelCfxCminus(11)
		}
		MAX-ACCESS	read-only
		STATUS	current
		DESCRIPTION
			"The particular type of Hs150 chassis."
		::= { switchProductMib 1 }


-- switchModelType is added to support the HS140 & HS150 models
-- of the product. This is an add-on object after the original 
-- MIB was designed. The OID is out of sequence, but this is the
-- logical place.
	
	switchModelType		OBJECT-TYPE
		SYNTAX	INTEGER {
			uplinkSwitch(1),
			switch(2),
			unknown(3)
		}
		MAX-ACCESS	read-only
		STATUS		current
		DESCRIPTION
			"The model type of the switch. "
		::= { switchProductMib 3 }

	portMirrorGroup	OBJECT IDENTIFIER ::= { switchProductMib 2}

-- The portMirror Group
--
-- This group contains the general information regarding the
-- configuration of port sniffing feature, aka port mirroring.
-- The HS150 can mirror one or more physical ports to another
-- port in either direction with selective traffic.
-- This feature does not apply to uplink ports or virtual router
-- ports.

	PortMirrorStatus ::= TEXTUAL-CONVENTION
		STATUS	current
		DESCRIPTION
			"A flag to indicate whether a Mirroring feature is activated or 
			not.  In hardware, the 'on' condition corresponds to 1, while the
			'off' condition corresponds to 0. "
		SYNTAX INTEGER {
			on(1),
			off(2)
		}

	portMirrorProbePort  OBJECT-TYPE
		SYNTAX	INTEGER (1..32)
		MAX-ACCESS	read-write
		STATUS	current
		DESCRIPTION
			"The port to which the probe or sniffer is connected.
			Port Mirroring is enabled through the portMirrorSrcEnable
			and portMirrorDstEnable flag."
		::= { portMirrorGroup 1 }

	portMirrorSrcEnable  OBJECT-TYPE
		SYNTAX	PortMirrorStatus
		MAX-ACCESS	read-write
		STATUS	current
		DESCRIPTION
			"A flag to enable source sniffing at the probe port."
		::= { portMirrorGroup 2 }

	portMirrorDstEnable  OBJECT-TYPE
		SYNTAX	PortMirrorStatus
		MAX-ACCESS	read-write
		STATUS	current
		DESCRIPTION
			"A flag to enable destination sniffing at the probe port."
		::= { portMirrorGroup 3 }

	portMirrorTable OBJECT-TYPE
		SYNTAX	SEQUENCE OF PortMirrorEntry
		MAX-ACCESS	not-accessible
		STATUS	current
		DESCRIPTION
			"A table that contains the ports and type of frames
			to be sniffed. This table allows more than one port
			to be sniffed at a time."
		::= { portMirrorGroup 4 }

	portMirrorEntry OBJECT-TYPE
		SYNTAX	PortMirrorEntry
		MAX-ACCESS	not-accessible
		STATUS	current
		DESCRIPTION
			"A list of information sniffing characteristics
			for each physical port."
		INDEX  { pPortNumber }
		::= { portMirrorTable 1 }

	PortMirrorEntry ::= SEQUENCE {
		portMirrorSrcUcastFrames         PortMirrorStatus,
		portMirrorSrcBMCastFrames        PortMirrorStatus,
		portMirrorSrcDiscardedFrames     PortMirrorStatus,
		portMirrorSrcMarkedFrames        PortMirrorStatus,
		portMirrorDstAllFrames           PortMirrorStatus,
		portMirrorDstMarkedFrames        PortMirrorStatus
	}

	portMirrorSrcUcastFrames  OBJECT-TYPE
		SYNTAX	PortMirrorStatus
		MAX-ACCESS	read-write
		STATUS	current
		DESCRIPTION
			"A flag to activate sniffing source unicast frames,
			e.g., forwarded unicast frames only."
		::= { portMirrorEntry 1 }
 
	portMirrorSrcBMCastFrames  OBJECT-TYPE
		SYNTAX	PortMirrorStatus
		MAX-ACCESS	read-write 
		STATUS	current
		DESCRIPTION
			"A flag to activate sniffing source broadcast and
			multicast frames."
		::= { portMirrorEntry 2 }
 
	portMirrorSrcDiscardedFrames   OBJECT-TYPE
		SYNTAX	PortMirrorStatus
		MAX-ACCESS	read-write 
		STATUS	current
		DESCRIPTION
			"A flag to activate sniffing source frames which were
			discarded by the ARL."
		::= { portMirrorEntry 3 }

	portMirrorSrcMarkedFrames   OBJECT-TYPE
		SYNTAX	PortMirrorStatus
		MAX-ACCESS	read-write 
		STATUS	current
		DESCRIPTION
			"A flag to activate sniffing source frames which were
			marked by the ARL to be sniffed."
		::= { portMirrorEntry 4 }

	portMirrorDstAllFrames  OBJECT-TYPE
		SYNTAX	PortMirrorStatus
		MAX-ACCESS	read-write 
		STATUS	current
		DESCRIPTION
			"A flag to activate sniffing of all destination frames."
		::= { portMirrorEntry 5 }
 
	portMirrorDstMarkedFrames   OBJECT-TYPE
		SYNTAX	PortMirrorStatus
		MAX-ACCESS	read-write 
		STATUS	current
		DESCRIPTION
			"A flag to activate sniffing destination frames which were
			marked by the ARL to be sniffed."
		::= { portMirrorEntry 6 }

END
