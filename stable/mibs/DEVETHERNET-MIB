DEVETHERNET-MIB DEFINITIONS ::= BEGIN

	IMPORTS
		OBJECT-TYPE, MODULE-IDENTITY
			FROM SNMPv2-SMI
		device
			FROM ANIROOT-MIB;


aniDevEthernet  MODULE-IDENTITY
	LAST-UPDATED "0210251725Z"      -- Fri Oct 25 17:25:00 PDT 2002
	ORGANIZATION "Aperto Networks"
	CONTACT-INFO
	  "       
	  Postal:  Aperto Networks Inc
		   1637 S Main Street 
		   Milpitas, California 95035
	  Tel:	   +1 408 719 9977
	  "       
	DESCRIPTION
	   "This group provides Ethernet related information for BSU or SU.
	   "
	::= { device 11 }

	aniDevEthernetConfig	     OBJECT IDENTIFIER ::= { aniDevEthernet 1 }


	-- the BSU/SU Ethernet Configuration group

aniDevEthernetConfigMode OBJECT-TYPE	 
	SYNTAX	INTEGER {
			auto-negotiate(1),
			speed-100mbps-full(2),
			speed-100mbps-half(3),
			speed-10mbps-full(4),
			speed-10mbps-half(5)
	}
	MAX-ACCESS  read-write
	STATUS      current
	DESCRIPTION
	   "Specifies the Ethernet Speed (10 or 100 Mbps) and   
	    Duplex Setting (Half or Full) 
		or to set the device to auto-negotiate.
	   "
	DEFVAL { auto-negotiate }
	::= { aniDevEthernetConfig 1 }



aniDevEthernetCurrentLinkStatus OBJECT-TYPE 
	SYNTAX INTEGER {
			up(1),
			down(2)
	}
	MAX-ACCESS  read-only
	STATUS      current
	DESCRIPTION
	   "Displays the current ethernet link status of the device 
	   "
	::= { aniDevEthernetConfig 2 }

aniDevEthernetCurrentSpeed OBJECT-TYPE 
	SYNTAX INTEGER {
			speed-10-mbps(1),
			speed-100-mbps(2),
			not-applicable(3)
    }
	MAX-ACCESS  read-only
	STATUS      current
	DESCRIPTION
	   "Displays the current ethernet speed of the device 
	   "
	::= { aniDevEthernetConfig 3 }

aniDevEthernetCurrentDuplex OBJECT-TYPE 
	SYNTAX INTEGER {
			half-duplex(1),
			full-duplex(2),
			not-applicable(3)

    }

	MAX-ACCESS  read-only
	STATUS      current
	DESCRIPTION
	   "Displays the current ethernet duplex mode of the device 
	   "
	::= { aniDevEthernetConfig 4 }

END
