ENGENIUS-PRIVATE-MIB DEFINITIONS ::= BEGIN

IMPORTS
	MODULE-IDENTITY, OBJECT-TYPE, NOTIFICATION-TYPE, OBJECT-IDENTITY, 
	enterprises, IpAddress, Counter32, Gauge32, TimeTicks, Integer32,
	Counter64                                              
            	FROM SNMPv2-SMI
                                                   
	DisplayString, MacAddress, TruthValue, TimeStamp,
	TimeInterval, DateAndTime, RowStatus, TEXTUAL-CONVENTION
	FROM SNMPv2-TC

	MODULE-COMPLIANCE, OBJECT-GROUP
	FROM SNMPv2-CONF

	ifIndex
	    FROM RFC1213-MIB
        
      InetAddressType, InetAddress 
          FROM INET-ADDRESS-MIB;	    

engeniusprivate MODULE-IDENTITY
    LAST-UPDATED "200906111100Z"
    ORGANIZATION "Senao R&D Dept., S/W Division"
    CONTACT-INFO
       "
       Info
       SENAO INTERNATIONAL CO., LTD.
       No.500, Fusing 3 Rd., Hwa-Ya Technical Park,
       Kuei-Shan Hsiang, TAOYUAN County 333, TAIWAN, R.O.C.
       Tel: 886-3-328-9289
       Fax: 886-3-328-9666
       E-mail: info@senao.com.tw
       "
   DESCRIPTION
       "
       The MIB module defines Senao implementation-specific metrics useful in managing 
       IEEE 802.11 on Senao devices.
       This is used as a supplement to the standard 802.11 MIB proposed by IEEE.
       "
    REVISION        "200906111100Z"
    DESCRIPTION	    "Added new parameter: modelname,rf power, macadd, rssi"
    REVISION        "200906101600Z"
    DESCRIPTION	    "Simplified version, remove unsupported item, added ipaddress type, added reboot cmd"
    REVISION        "200905141000Z"
    DESCRIPTION	    "First version of Engenius-Private-MIB"

   ::= { engenius 2 }

engenius				OBJECT IDENTIFIER ::= { enterprises 14125 }


status			OBJECT IDENTIFIER ::= { engeniusprivate 1 }
configuration		OBJECT IDENTIFIER ::= { engeniusprivate 2 }
command			OBJECT IDENTIFIER ::= { engeniusprivate 3 }

system			        OBJECT IDENTIFIER ::= { status 1 }

wan				OBJECT IDENTIFIER ::= { configuration 1 }
pppoe				OBJECT IDENTIFIER ::= { configuration 2 }
dns				OBJECT IDENTIFIER ::= { configuration 3 }
mtu				OBJECT IDENTIFIER ::= { configuration 4 }
landhcp				OBJECT IDENTIFIER ::= { configuration 5 }
ntp				OBJECT IDENTIFIER ::= { configuration 6 }

admin				OBJECT IDENTIFIER ::= { configuration 8 }
wlan				OBJECT IDENTIFIER ::= { configuration 9 }
wlansta				OBJECT IDENTIFIER ::= { configuration 10 }
wlanmesh			OBJECT IDENTIFIER ::= { configuration 11 }

				wlanstawds			OBJECT IDENTIFIER ::= { configuration 14 }
stp				OBJECT IDENTIFIER ::= { configuration 15 }
snmp				OBJECT IDENTIFIER ::= { configuration 16 }
wmm				OBJECT IDENTIFIER ::= { configuration 17 }

logemail			OBJECT IDENTIFIER ::= { configuration 20 }
vpn				OBJECT IDENTIFIER ::= { configuration 21 }
traffic				OBJECT IDENTIFIER ::= { configuration 22 }

saveCmd				OBJECT IDENTIFIER ::= { command 1 }
resetCmd			OBJECT IDENTIFIER ::= { command 2 }
rebootCmd			OBJECT IDENTIFIER ::= { command 3 }


-- ==========================
-- Defination Begins
-- ==========================

-- =======| status > system | ===============

systemName OBJECT-TYPE
	SYNTAX DisplayString (SIZE (0..256))
   	MAX-ACCESS read-only
     	STATUS current
     	DESCRIPTION
	"The DUT's system name."
	DEFVAL { "Access Point" }
     ::= { system 1 }

sysPassword OBJECT-TYPE
	SYNTAX DisplayString (SIZE (0..256))
   	MAX-ACCESS read-only
     	STATUS current
     	DESCRIPTION
	"The password that system manager own."
	DEFVAL { "admin" }
     ::= { system 2 }

errMsg OBJECT-TYPE
	SYNTAX DisplayString (SIZE (0..256))
   	MAX-ACCESS read-only
     	STATUS current
     	DESCRIPTION
	"The error message record"
     ::= { system 3 }

statusWLANSTAAssoc OBJECT-TYPE
	SYNTAX INTEGER{
		false(0),
		true(1)
	}
   	MAX-ACCESS read-only
     	STATUS current
     	DESCRIPTION
	"The status of wireless interface connect to AP"
	DEFVAL { false }
     ::= { system 4 }

modelName OBJECT-TYPE
	  SYNTAX DisplayString (SIZE (0..256))
	  MAX-ACCESS read-only
	  STATUS current
	  DESCRIPTION
	  "Firmware model name"
     ::= { system 5  }	  

wirelessMacAddress OBJECT-TYPE
	   SYNTAX DisplayString (SIZE(0..17))
	   MAX-ACCESS read-only
	   STATUS current
	   DESCRIPTION
	   "The wireless MAC address"
      ::={ system 6 }

wanIPAddress OBJECT-TYPE
	   SYNTAX DisplayString
	   MAX-ACCESS read-only
	   STATUS current
	   DESCRIPTION
	   "The WAN IP address"
      ::={ system 7 }

wanSubnetMask OBJECT-TYPE
	   SYNTAX DisplayString
	   MAX-ACCESS read-only
	   STATUS current
	   DESCRIPTION
	   "The WAN subnet mask"
      ::={ system 8 }


-- ============== END =======================


-- =======| configuration > wan | ===============

wanConnectionType OBJECT-TYPE
	SYNTAX INTEGER
	{
		dhcp(1),
		static(2),
		pppoe(3)
	}
	MAX-ACCESS read-write
	STATUS current
	DESCRIPTION
	"The wan connection type which one of Static IP/DHCP/PPPoE/PPTP"
	DEFVAL { static }
	::= { wan 1 }

wanGeneralAccount OBJECT-TYPE
	SYNTAX DisplayString (SIZE (0..256))
	MAX-ACCESS read-write
	STATUS current
	DESCRIPTION
	"The DUT network Account ID"
	DEFVAL { "none" }
     ::= { wan 2 }

wanGeneralDomain OBJECT-TYPE
	SYNTAX DisplayString (SIZE (0..256))
	MAX-ACCESS read-write
	STATUS current
	DESCRIPTION
	"The DUT network Domain Name"
	DEFVAL { "none" }
     ::= { wan 3 }

wanGeneralIP OBJECT-TYPE
	SYNTAX IpAddress
	MAX-ACCESS read-write
	STATUS current
	DESCRIPTION
	"The DUT wan interface static IP address in static connection type"
	DEFVAL { "10.1.1.100" }
     ::= { wan 4 }

wanGeneralSubnetMask OBJECT-TYPE
	SYNTAX IpAddress
	MAX-ACCESS read-write
	STATUS current
	DESCRIPTION
	"The DUT wan interface subnet mask in static connection type"
	DEFVAL { "255.255.0.0" }
     ::= { wan 5 }

wanGeneralGateway OBJECT-TYPE
	SYNTAX IpAddress
	MAX-ACCESS read-write
	STATUS current
	DESCRIPTION
	"The DUT networks gateway IP address in static connection type"
	DEFVAL { "10.1.1.150" }
     ::= { wan 6 }


-- ============== END ===========================

-- =======| configuration > pppoe | ===============

wanPPPoELoginName OBJECT-TYPE
	SYNTAX DisplayString (SIZE (0..256))
	MAX-ACCESS read-write
	STATUS current
	DESCRIPTION
	"PPPoE user name"
     ::= { pppoe 1 }

wanPPPoEPassword OBJECT-TYPE
	SYNTAX DisplayString (SIZE (0..256))
	MAX-ACCESS read-write
	STATUS current
	DESCRIPTION
	"PPPoE password"
     ::= { pppoe 2 }

wanPPPoEServiceName OBJECT-TYPE
	SYNTAX DisplayString (SIZE (0..256))
	MAX-ACCESS read-write
	STATUS current
	DESCRIPTION
	"Specifies the desired PPPoE service name"
     ::= { pppoe 3 }

wanPPPoEConnectionType OBJECT-TYPE
	SYNTAX INTEGER
	{
		keepalive(0),
		connectondemand(1)
	}
	MAX-ACCESS read-write
	STATUS current
	DESCRIPTION
	"PPPoE connection type which keep alive or on demand."
	DEFVAL { keepalive }
	::= { pppoe 4 }

wanPPPoEMaxIdleTime OBJECT-TYPE
	SYNTAX Integer32 (1..99)
	MAX-ACCESS read-write
	STATUS current
	DESCRIPTION
	"The max idle time (minutes) in connect on demand connection type"
	DEFVAL { 1 }
     ::= { pppoe 5 }

wanPPPoERedialPeriod OBJECT-TYPE
	SYNTAX Integer32 (30..180)
	MAX-ACCESS read-write
	STATUS current
	DESCRIPTION
	"The redial period (seconds) in keep alive connection type"
	DEFVAL { 30 }
     ::= { pppoe 6 }

-- ============== END ===========================

-- =======| configuration > dns | ===============

wanDNSSourc OBJECT-TYPE
	SYNTAX INTEGER
	{
		isp(0),
		specified(1)
	}
	MAX-ACCESS read-write
	STATUS current
	DESCRIPTION
	"Automatically gets DNS IP address from ISP or user sepcisicify"
	DEFVAL { isp }
	::= { dns 1 }

wanPrimaryDNSIP OBJECT-TYPE
	SYNTAX IpAddress
	MAX-ACCESS read-write
	STATUS current
	DESCRIPTION
	"The primary DNS IP address"
	DEFVAL { "0.0.0.0" }
     ::= { dns 2 }

wanSecondaryDNSIP OBJECT-TYPE
	SYNTAX IpAddress
	MAX-ACCESS read-write
	STATUS current
	DESCRIPTION
	"The secondary DNS IP address"
	DEFVAL { "0.0.0.0" }
     ::= { dns 3 }

-- ============== END ===========================

-- =======| configuration > mtu | ===============

wanMTUMode OBJECT-TYPE
	SYNTAX INTEGER
	{
		auto(0),
		manual(1)
	}
	MAX-ACCESS read-write
	STATUS current
	DESCRIPTION
	"Automatically setting MTU value or user sepcisicify"
	DEFVAL { auto }
	::= { mtu 1 }

wanMTU OBJECT-TYPE
	SYNTAX Integer32 (576..1500)
	MAX-ACCESS read-write
	STATUS current
	DESCRIPTION
	"The Maximum Transmission Unit (MTU) in WAN interface"
	DEFVAL { 1500 }
     ::= { mtu 2 }

pppoeMTU OBJECT-TYPE
	SYNTAX Integer32 (576..1492)
	MAX-ACCESS read-write
	STATUS current
	DESCRIPTION
	"The Maximum Transmission Unit (MTU) in PPPoE protocol"
	DEFVAL { 1492 }
     ::= { mtu 3 }

-- ============== END ===========================

-- =======| configuration > landhcp | ===============

lanDHCPC OBJECT-TYPE
	SYNTAX INTEGER
	{
		disable(0),
		enable(1)
	}
	MAX-ACCESS read-write
	STATUS current
	DESCRIPTION
	"Automatically get LAN IP address form DHCP server or set static IP address"
	DEFVAL { disable }
	::= { landhcp 1 }

lanIP OBJECT-TYPE
	SYNTAX IpAddress
	MAX-ACCESS read-write
	STATUS current
	DESCRIPTION
	"To setting static LAN IP address in DUT"
	DEFVAL { "192.168.1.1" }
     ::= { landhcp 2 }

lanSubnetmask OBJECT-TYPE
	SYNTAX IpAddress
	MAX-ACCESS read-write
	STATUS current
	DESCRIPTION
	"To setting static Subnet Mask in DUT"
	DEFVAL { "255.255.255.0" }
     ::= { landhcp 3 }

lanGatewayIP OBJECT-TYPE
	SYNTAX IpAddress
	MAX-ACCESS read-write
	STATUS current
	DESCRIPTION
	"To setting getway IP address in DUT"
	DEFVAL { "0.0.0.0" }
     ::= { landhcp 4 }

lanWINSAddr OBJECT-TYPE
	SYNTAX IpAddress
	MAX-ACCESS read-write
	STATUS current
	DESCRIPTION
	"To setting WINS IP address in DUT"
	DEFVAL { "0.0.0.0" }
     ::= { landhcp 5 }

lanDHCPSrvEnable OBJECT-TYPE
	 SYNTAX INTEGER
        {
                disable(0),
                enable(1)
        }
        MAX-ACCESS read-write
        STATUS current
        DESCRIPTION
        "Enable / Disable DHCP server"
        DEFVAL { enable }
    ::= { landhcp 6 }
 	
lanDHCPSrvStartAddr OBJECT-TYPE
        SYNTAX IpAddress
        MAX-ACCESS read-write
        STATUS current
        DESCRIPTION
        "To setting DHCP server allocate IP address up bound"
        DEFVAL { "192.168.1.2" }
     ::= { landhcp 7 }
 	
lanDHCPSrvStopAddr OBJECT-TYPE
        SYNTAX IpAddress
        MAX-ACCESS read-write
        STATUS current
        DESCRIPTION
       "To setting DHCP server allocate IP address low bound"
        DEFVAL { "192.168.1.254" }
     ::= { landhcp 8 }

-- ============== END ================================

-- =======| configuration > ntp | ===============

timeSettingMode OBJECT-TYPE
	SYNTAX INTEGER
	{
		manual(0),
		auto(1)
	}
	MAX-ACCESS read-write
	STATUS current
	DESCRIPTION
	"Automatically get or manually set Date and Time"
	DEFVAL { auto }
	::= { ntp 1 }

userNTPSrvMode OBJECT-TYPE
	SYNTAX INTEGER
	{
		disable(0),
		enable(1)
	}
	MAX-ACCESS read-write
	STATUS current
	DESCRIPTION
	"Enable / Disable user sepcisicify NTP server"
	DEFVAL { disable }
	::= { ntp 2 }

userNTPSrvIP OBJECT-TYPE
	SYNTAX IpAddress
	MAX-ACCESS read-write
	STATUS current
	DESCRIPTION
	"User sepcisicify NTP server IP address"
	DEFVAL { "0.0.0.0" }
     ::= { ntp 3 }

timeZone OBJECT-TYPE
	SYNTAX DisplayString (SIZE (0..128))
	MAX-ACCESS read-only
	STATUS current
	DESCRIPTION
	"To setting time zone in DUT"
	DEFVAL { "GMT0" }
     ::= { ntp 4 }



-- ============== END ===========================



-- =======| configuration > admin | ===============

username OBJECT-TYPE
	SYNTAX DisplayString (SIZE (0..33))
	MAX-ACCESS read-write
	STATUS current
	DESCRIPTION
	"The User Name that system manager own"
	DEFVAL { "admin" }
     ::= { admin 1 }


remoteManagementEnable OBJECT-TYPE
	SYNTAX INTEGER
	{
		disable(0),
		enable(1)
	}
	MAX-ACCESS read-write
	STATUS current
	DESCRIPTION
	"Enable / Disable remote management DUT function"
	DEFVAL { disable }
	::= { admin 3 }

remoteUpgradeEnable OBJECT-TYPE
	SYNTAX INTEGER
	{
		disable(0),
		enable(1)
	}
	MAX-ACCESS read-write
	STATUS current
	DESCRIPTION
	"Enable / Disable remote upgrade firmware"
	DEFVAL { disable }
	::= { admin 4 }

remoteManagementPort OBJECT-TYPE
	SYNTAX Integer32 (1..65535)
	MAX-ACCESS read-write
	STATUS current
	DESCRIPTION
	"To setting remote management port"
	DEFVAL {  8080  }
     ::= { admin 5 }

remoteManagementVLANID OBJECT-TYPE
	SYNTAX Integer32 (1..4096)
	MAX-ACCESS read-write
	STATUS current
	DESCRIPTION
	"To setting management Tag on VLAN"
	DEFVAL { 4096 }
	::= { admin 6 }


-- ============== END ===========================

-- =======| configuration > wlan | ===============

wlanMode OBJECT-TYPE
	SYNTAX INTEGER
	{
		wlan11a(1),
		wlan11b(2),
		wlan11bg(3),
		wlan11astaticturbo(5),
		wlan11gdynamicturbo(6),
		wlan11gstaticturbo(7),
		wlan11gpure(9)
	}
	MAX-ACCESS read-write
	STATUS current
	DESCRIPTION
	"The wireless lan operation mode. (802.11a/b/g)"
	DEFVAL { wlan11bg }
	::= { wlan 1 }

chanBwMode OBJECT-TYPE
	SYNTAX INTEGER
	{
		wlan20MHz(0),
		wlan10MHz(1),
		wlan5MHz(2)

	}
	MAX-ACCESS read-write
	STATUS current
	DESCRIPTION
	"The WLAN narrow band"
	DEFVAL { wlan20MHz }
	::= { wlan 2 }

wlanaSSID OBJECT-TYPE
	SYNTAX DisplayString (SIZE (0..33))
	MAX-ACCESS read-write
	STATUS current
	DESCRIPTION
	"The SSID which station connect to"
	DEFVAL { "EnGenius" }
     ::= { wlan 3 }

wlanOpMode OBJECT-TYPE
	SYNTAX INTEGER
	{
		accesspoint(0),
		clientbridge(1),
		wdsbridge(2),
		repeater(3),
		aprouter(4),
		clientrouter(5),
		mesh(6)
	}
	MAX-ACCESS read-write
	STATUS current
	DESCRIPTION
	"The WLAN operation mode. (Access Point/ Client Bridge/ WDS Bridge/ Repeater/ AP Router / Client Router)"
	DEFVAL { accesspoint }
	::= { wlan 4 }

wlanCountryCode OBJECT-TYPE
	SYNTAX DisplayString (SIZE (0..5))
	MAX-ACCESS read-only
	STATUS current
	DESCRIPTION
	"The country code"
	DEFVAL { "0" }
     ::= { wlan 5 }

wlanCountry OBJECT-TYPE
	SYNTAX DisplayString (SIZE (0..20))
	MAX-ACCESS read-only
	STATUS current
	DESCRIPTION
	"The string of the country name"
	DEFVAL { "N/A" }
     ::= { wlan 6 }

wlanChannel OBJECT-TYPE
	SYNTAX Integer32 (0..255)
	MAX-ACCESS read-write
	STATUS current
	DESCRIPTION
	"The wireless channel frequency"
	DEFVAL { 1 }
     ::= { wlan 7 }

wlanACLMode OBJECT-TYPE
	SYNTAX INTEGER
	{
		disable(0),
		allow(1),
		deny(2)
	}
	MAX-ACCESS read-write
	STATUS current
	DESCRIPTION
	"The WLAN Mac filter mode. (Disable / Deny / Allow)"
	DEFVAL { disable }
	::= { wlan 8 }

wlanOutdoorDistance OBJECT-TYPE
	SYNTAX Integer32 (1000..30000)
	MAX-ACCESS read-write
	STATUS current
	DESCRIPTION
	"The distance between two DUTs"
	DEFVAL { 1000 }
     ::= { wlan 9 }

wlanDataRate OBJECT-TYPE
	SYNTAX DisplayString (SIZE (0..6))
	MAX-ACCESS read-write
	STATUS current
	DESCRIPTION
	"The wireless LAN Data rate. The available input option: 1M, 2M, 5.5M, 6M, 9M, 11M, 12M, 18M, 24M, 36M, 48M, 54M, auto"
	DEFVAL { "auto" }
     ::= { wlan 10 }

wlanTxPower OBJECT-TYPE
	SYNTAX Integer32 (0..30)
	MAX-ACCESS read-write
	STATUS current
	DESCRIPTION
	"The WLAN transmission power"
	DEFVAL { 20 }
     ::= { wlan 11 }

antennasel OBJECT-TYPE
	SYNTAX INTEGER	
	{
		diversity(0),
		vertical(1),
		horizontal(2)
	}
	MAX-ACCESS read-write
	STATUS current
	DESCRIPTION
	"The antenna which prefer to use"
	::= { wlan 12 }

wlanBeaconInterval OBJECT-TYPE
	SYNTAX Integer32 (25..500)
	MAX-ACCESS read-write
	STATUS current
	DESCRIPTION
	"The sent beacon interval time"
	DEFVAL { 100 }
     ::= { wlan 13 }



wlanRTSTh OBJECT-TYPE
	SYNTAX Integer32 (1..2346)
	MAX-ACCESS read-write
	STATUS current
	DESCRIPTION
	"The WLAN RTS/CTS threshold"
	DEFVAL { 2346 }
     ::= { wlan 15 }

wlanFragLen OBJECT-TYPE
	SYNTAX Integer32 (256..2346)
	MAX-ACCESS read-write
	STATUS current
	DESCRIPTION
	"The WLAN packages fragment length"
	DEFVAL { 2346 }
     ::= { wlan 16 }



wlanProtmode OBJECT-TYPE
	SYNTAX INTEGER
	{
		disable(0),
		ctsonly(1),
		rtscts(2)
	}
	MAX-ACCESS read-write
	STATUS current
	DESCRIPTION
	"Protection transmittion on G band. (CTS or RTS/CTS)"
	DEFVAL { disable }
	::= { wlan 18 }

wlanPreferBSSID OBJECT-TYPE
	SYNTAX DisplayString
	MAX-ACCESS read-write
	STATUS current
	DESCRIPTION
	"The MAC address of the prefer connection AP"
     ::= { wlan 19 }




wlanTable OBJECT-TYPE
    	SYNTAX SEQUENCE OF WLANTableEntry
    	MAX-ACCESS not-accessible
    	STATUS current
    	DESCRIPTION
	"This table display the wlan table." 
    ::= { wlan 21 }

wlanTableEntry OBJECT-TYPE
    	SYNTAX WLANTableEntry
   	MAX-ACCESS not-accessible
    	STATUS current
    	DESCRIPTION
	"Represent the entry in the wlan table."
    INDEX { wlanTableIndex }
    ::= { wlanTable 1 }

WLANTableEntry::=
    SEQUENCE
    {
	wlanTableIndex 			Integer32, 
	wlanEnable		 		INTEGER, 
	wlanSSID				DisplayString,
	wlanHideSSID			INTEGER,
	wlanStaSeparation		INTEGER,
	wlanVLANID			Integer32,
	wlanAuth				INTEGER,
	wlanEncryption			INTEGER,
	wlanWepDefaultKeyIdx		INTEGER,
	wlanWepKey				DisplayString,
	wlanWpapskPassphrase		DisplayString,
	wlanWpaRadiusSrvIP		IpAddress,
	wlanWpaRadiusSrvPort		Integer32,
	wlanWpaRadiusSrvSecret		DisplayString,
	wlanWpaGroupKeyUpdateInterval	Integer32
    }

wlanTableIndex OBJECT-TYPE
    SYNTAX Integer32 (0..4)
    MAX-ACCESS not-accessible
    STATUS current
    DESCRIPTION
	"Specify the index of the wlan table."
    ::= { wlanTableEntry 1 }

wlanEnable OBJECT-TYPE
    SYNTAX INTEGER{
	disable(0),
	enable(1)
    }
    MAX-ACCESS read-write
    STATUS current
    DESCRIPTION
	"Enable / Disable"
    ::= { wlanTableEntry 2 }

wlanSSID OBJECT-TYPE
	SYNTAX DisplayString (SIZE(1..32))
	MAX-ACCESS read-write
    	STATUS current
    	DESCRIPTION
	"The WLAN SSID"
    ::= { wlanTableEntry 3 }

wlanHideSSID OBJECT-TYPE
    SYNTAX INTEGER{
	disable(0),
	enable(1)
    }
    MAX-ACCESS read-write
    STATUS current
    DESCRIPTION
	"Enable / Disable broadcast SSID"
    ::= { wlanTableEntry 4 }

wlanStaSeparation OBJECT-TYPE
    SYNTAX INTEGER{
	disable(0),
	enable(1)
    }
    MAX-ACCESS read-write
    STATUS current
    DESCRIPTION
	"Enable / Disable STA separation"
    ::= { wlanTableEntry 5 }

wlanVLANID OBJECT-TYPE
    SYNTAX Integer32 (1..4095)
    MAX-ACCESS read-write
    STATUS current
    DESCRIPTION
	"The WLAN interface VLAN ID"
    ::= { wlanTableEntry 6 }

wlanAuth OBJECT-TYPE
    SYNTAX INTEGER{
	open(1),
	shared(2),
	auto(3),
	wlan8021x(4),
	wpa(5),
	wpapsk(6),
	wpa2(7),
	wpa2psk(8),
	wpamixed(9),
	wpapskmixed(10)
    }
    MAX-ACCESS read-write
    STATUS current
    DESCRIPTION
	"The WLAN authentication type"
    ::= { wlanTableEntry 7 }

wlanEncryption OBJECT-TYPE
    SYNTAX INTEGER{
	none(0),
	wep(1),
	tkip(2),
	aes(3),
	auto(4)
    }
    MAX-ACCESS read-write
    STATUS current
    DESCRIPTION
	"The WLAN encryption type"
    ::= { wlanTableEntry 8 }

wlanWepDefaultKeyIdx OBJECT-TYPE
    SYNTAX INTEGER{
	key1(1),
	key2(2),
	key3(3),
	key4(4)
    }
    MAX-ACCESS read-write
    STATUS current
    DESCRIPTION
	"The WLAN WEP Key index of combination"
    ::= { wlanTableEntry 9 }

wlanWepKey OBJECT-TYPE
    SYNTAX DisplayString (SIZE(5|10|13|16|26|32))
    MAX-ACCESS read-write
    STATUS current
    DESCRIPTION
	"The WLAN WEP Key combination. The input has to be 5,13,16 ascii keys, or 10,26,32 Hex keys "
    ::= { wlanTableEntry 10 }

wlanWpapskPassphrase OBJECT-TYPE
    SYNTAX DisplayString (SIZE (1..64))
    MAX-ACCESS read-write
    STATUS current
    DESCRIPTION
	"The WLAN WPA Key combination"
    ::= { wlanTableEntry 11 }

wlanWpaRadiusSrvIP OBJECT-TYPE
    SYNTAX IpAddress
    MAX-ACCESS read-write
    STATUS current
    DESCRIPTION
	"The WLAN WPA-Enterprise remote radius server IP"
    ::= { wlanTableEntry 12 }

wlanWpaRadiusSrvPort OBJECT-TYPE
    SYNTAX Integer32 (1..65535)
    MAX-ACCESS read-write
    STATUS current
    DESCRIPTION
	"The WLAN WPA-Enterprise remote radius server port"
    ::= { wlanTableEntry 13 }

wlanWpaRadiusSrvSecret OBJECT-TYPE
    SYNTAX DisplayString (SIZE(1..64))
    MAX-ACCESS read-write
    STATUS current
    DESCRIPTION
	"The WLAN WPA-Enterprise key combination"
    ::= { wlanTableEntry 14 }

wlanWpaGroupKeyUpdateInterval OBJECT-TYPE
    SYNTAX Integer32 (30..3600)
    MAX-ACCESS read-write
    STATUS current
    DESCRIPTION
	"The WLAN WPA-Enterprise group key update interval"
    ::= { wlanTableEntry 15 }



-- ============== END ===========================

-- =======| configuration > wlansta | ===============

wlanSTAAuth OBJECT-TYPE
	SYNTAX INTEGER
	{
		open(1),
		shared(2),		
		wpapsk(6),
		wpa2psk(8),
		wpapskmixed(10)
	}
	MAX-ACCESS read-write
	STATUS current
	DESCRIPTION
	"The WLAN STA authentication type"
	DEFVAL { open }
	::= { wlansta 1 }

wlanSTAEncryption OBJECT-TYPE
	SYNTAX INTEGER
	{
		none(0),
		wep(1),
		tkip(2),
		aes(3),
		auto(4)
	}
	MAX-ACCESS read-write
	STATUS current
	DESCRIPTION
	"The WLAN STA encryption type"
	DEFVAL { none }
	::= { wlansta 2 }

wlanSTAWepDefaultKeyIdx OBJECT-TYPE
	SYNTAX INTEGER
	{
		key1(1),
		key2(2),
		key3(3),
		key4(4)
	}
	MAX-ACCESS read-write
	STATUS current
	DESCRIPTION
	"The WLAN STA WEP Key index of combination"
	DEFVAL { key1 }
	::= { wlansta 3 }

wlanSTAWepKey OBJECT-TYPE
	SYNTAX DisplayString (SIZE(5|10|13|16|26|32))
	MAX-ACCESS read-write
        STATUS current
	DESCRIPTION
	"The WLAN STA WEP Key combination. The input has to be 5,13,16 ascii keys, or 10,26,32 Hex keys "

	::= { wlansta 4 }

wlanSTAWpapskPassphrase OBJECT-TYPE
	SYNTAX DisplayString (SIZE(1..64))
	MAX-ACCESS read-write
	STATUS current
	DESCRIPTION
	"The WLAN STA WPA Key combination"
	::= { wlansta 5 }



-- ============== END ===========================

-- =======| configuration > wlanmesh | ===============

wlanMESHSSID OBJECT-TYPE
	SYNTAX DisplayString (SIZE(0..33))
	MAX-ACCESS read-write
	STATUS current
	DESCRIPTION
	"The string of the WLAN SSID in MESH mode"
	DEFVAL { "EnGeniusMesh" }
	::= { wlanmesh 1 }

wlanMESHGateway OBJECT-TYPE
	SYNTAX INTEGER
	{	
		disable(0),
		enable(1)
	}
	MAX-ACCESS read-write
	STATUS current
	DESCRIPTION
	"The Gateway IP address in MESH mode"
	::= { wlanmesh 2 }


wlanMESHAuth OBJECT-TYPE
	SYNTAX INTEGER
	{
		open(1),
		shared(2)
	}
	MAX-ACCESS read-write
	STATUS current
	DESCRIPTION
	"The authentication type in MESH mode"
	DEFVAL { open }
	::= { wlanmesh 4 }

wlanMESHEncryption OBJECT-TYPE
	SYNTAX INTEGER
	{
		none(0),
		wep(1),
		aes(2)
	}
	MAX-ACCESS read-write
	STATUS current
	DESCRIPTION
	"The encryption type in MESH mode"
	DEFVAL { none }
	::= { wlanmesh 5 }

wlanMESHWepDefaultKeyIdx OBJECT-TYPE
	SYNTAX INTEGER
	{
		key1(1),
		key2(2),
		key3(3),
		key4(4)
	}
	MAX-ACCESS read-write
	STATUS current
	DESCRIPTION
	"The WLAN WEP Key index of combination in MESH mode"
	DEFVAL { key1 }
	::= { wlanmesh 6 }

wlanMESHWepKey OBJECT-TYPE
	SYNTAX DisplayString (SIZE(5|10|13|16|26|32))
	MAX-ACCESS read-write
        STATUS current
	DESCRIPTION
	"The WLAN MESH WEP Key combination. The input has to be 5,13,16 ascii keys, or 10,26,32 Hex keys "
	::= { wlanmesh 7 }

wlanMESHWpapskPassphrase OBJECT-TYPE
	SYNTAX DisplayString (SIZE(1..64))
	MAX-ACCESS read-write
	STATUS current
	DESCRIPTION
	"The WLAN WPA Key combination in MESH mode"
	::= { wlanmesh 8 }

-- ============== END ===========================



-- =======| configuration > wlanstawds | ===============

staWDS OBJECT-TYPE
	SYNTAX INTEGER
	{
		disable(0),
		enable(1)
	}
	MAX-ACCESS read-write
	STATUS current
	DESCRIPTION
	"Enable / Disable WDS link in Client Mode"
	DEFVAL { enable }
	::= { wlanstawds 1 }

-- ============== END ====================================

-- =======| configuration > stp | ===============

stpMode OBJECT-TYPE
	SYNTAX INTEGER
	{
		disable(0),
		enable(1)
	}
	MAX-ACCESS read-write
	STATUS current
	DESCRIPTION
	"Enable / Disable Spanning Tree"
	DEFVAL { disable }
	::= { stp 1 }

stpHelloTime OBJECT-TYPE
	SYNTAX Integer32 (1..10)
	MAX-ACCESS read-write
	STATUS current
	DESCRIPTION
	"The interval between periodic transmissions of Configuration Messages by Designated Ports. IEEE802.1D 17.13.6"
	DEFVAL { 1 }
	::= { stp 2 }

stpMaxAge OBJECT-TYPE
	SYNTAX Integer32 (6..40)
	MAX-ACCESS read-write
	STATUS current
	DESCRIPTION
	"The maximum age of the information transmitted by the Bridge when it is the Root Bridge. IEEE 802.1D 17.13.8"
	DEFVAL { 20 }
	::= { stp 3 }

stpForwardDelay OBJECT-TYPE
	SYNTAX Integer32 (4..30)
	MAX-ACCESS read-write
	STATUS current
	DESCRIPTION
	"The delay used by STP Bridges to transition Reoot and Designated Ports to Forwarding. IEEE 802.1D 17.13.5"
	DEFVAL { 4 }
	::= { stp 4 }

stpPriority OBJECT-TYPE
	SYNTAX Integer32 (0..65535)
	MAX-ACCESS read-write
	STATUS current
	DESCRIPTION
	"The manageable component of the Port Identifier. IEEE 802.1D 17.13.10"
	DEFVAL { 32768 }
	::= { stp 5 }

-- ============== END ===========================

-- =======| configuration > snmp | ===============

snmpEnable OBJECT-TYPE
	SYNTAX INTEGER
	{
		disable(0),
		enable(1)
	}
	MAX-ACCESS read-write
	STATUS current
	DESCRIPTION
	"Enable / Disable SNMP agent"
	DEFVAL { enable }
	::= { snmp 1 }

snmpCmntyRO OBJECT-TYPE
	SYNTAX DisplayString (SIZE(0..33))
	MAX-ACCESS read-write
	STATUS current
	DESCRIPTION
	"The communication string for Read Only"
	DEFVAL { "public" }
	::= { snmp 2 }

snmpCmntyRW OBJECT-TYPE
	SYNTAX DisplayString (SIZE(0..33))
	MAX-ACCESS read-write
	STATUS current
	DESCRIPTION
	"The communication string for Read Write"
	DEFVAL { "private" }
	::= { snmp 3 }

snmpTrapDstIP OBJECT-TYPE
	SYNTAX IpAddress
	MAX-ACCESS read-write
	STATUS current
	DESCRIPTION
	"The IP address which snmp trap sent to"
	DEFVAL { "0.0.0.0" }
	::= { snmp 4 }

snmpTrapCmnty OBJECT-TYPE
	SYNTAX DisplayString (SIZE(0..33))
	MAX-ACCESS read-write
	STATUS current
	DESCRIPTION
	"The communication string for trap message"
	DEFVAL { "public" }
	::= { snmp 5 }

snmpCont OBJECT-TYPE
	SYNTAX DisplayString (SIZE(0..256))
	MAX-ACCESS read-write
	STATUS current
	DESCRIPTION
	"The snmp contact information"
	::= { snmp 6 }

snmpLocation OBJECT-TYPE
	SYNTAX DisplayString (SIZE(0..256))
	MAX-ACCESS read-write
	STATUS current
	DESCRIPTION
	"The snmp location information"
	::= { snmp 7 }

sysObjectID OBJECT-TYPE
	SYNTAX DisplayString (SIZE(0..20))
	MAX-ACCESS read-only
	STATUS current
	DESCRIPTION
	"The SNMP company OID"
	DEFVAL { "1.3.6.1.4.1.14125" }
	::= { snmp 8 }


-- ============== END ===========================


-- =======| configuration > wmm | ===============

wmmEnable OBJECT-TYPE
	SYNTAX INTEGER
	{
		disable(0),
		enable(1)
	}
	MAX-ACCESS read-write
	STATUS current
	DESCRIPTION
	"Enable / Disable WMM setting"
	DEFVAL { disable }
	::= { wmm 1 }

-- ============== END ===========================


-- =======| configuration > logemail | ===============

logServerEnable OBJECT-TYPE
	SYNTAX INTEGER
	{
		disable(0),
		enable(1)
	}
	MAX-ACCESS read-write
	STATUS current
	DESCRIPTION
	"Enable / Disable remote log server which log sent to"
	DEFVAL { disable }
	::= { logemail 1 }

logServerIP OBJECT-TYPE
	SYNTAX IpAddress
	MAX-ACCESS read-write
	STATUS current
	DESCRIPTION
	"Remote log server IP address"
	DEFVAL { "0.0.0.0" }
	::= { logemail 2 }

logLocalEnable OBJECT-TYPE
	SYNTAX INTEGER
	{
		disable(0),
		enable(1)
	}
	MAX-ACCESS read-write
	STATUS current
	DESCRIPTION
	"Enable / Disable local log server"
	DEFVAL { disable }
	::= { logemail 3 }

logLevel OBJECT-TYPE
	SYNTAX INTEGER
	{
		emergency(0),
		alert(1),
		critical(2),
		error(3),
		warning(4),
		notice(5),
		information(6),
		debug(7),
		all(8)
	}
	MAX-ACCESS read-write
	STATUS current
	DESCRIPTION
	"The level (all/ Debug/ Information/ Notice/ Warning/ Error/ Critical/ Alert/ Emergency) of log message"
	DEFVAL { all }
	::= { logemail 4 }

-- ============== END ===========================

-- =======| configuration > vpn | ===============

vpnPassthroughPPTP OBJECT-TYPE
	SYNTAX INTEGER
	{
		disable(0),
		enable(1)
	}
	MAX-ACCESS read-write
	STATUS current
	DESCRIPTION
	"Enable / Disable PPTP packages pass through"
	DEFVAL { enable }
	::= { vpn 1 }

vpnPassthroughL2TP OBJECT-TYPE
	SYNTAX INTEGER
	{
		disable(0),
		enable(1)
	}
	MAX-ACCESS read-write
	STATUS current
	DESCRIPTION
	"Enable / Disable L2TP packages pass through"
	DEFVAL { enable }
	::= { vpn 2 }

vpnPassthroughIPSec OBJECT-TYPE
	SYNTAX INTEGER
	{
		disable(0),
		enable(1)
	}
	MAX-ACCESS read-write
	STATUS current
	DESCRIPTION
	"Enable / Disable IPSec packages pass through"
	DEFVAL { enable }
	::= { vpn 3 }

-- ============== END ===========================

-- =======| configuration > vpn | ===============

tcEnable OBJECT-TYPE
	SYNTAX INTEGER
	{
		disable(0),
		enable(1)
	}
	MAX-ACCESS read-write
	STATUS current
	DESCRIPTION
	"Enable Traffic Shapping"
	DEFVAL { disable }
	::= { traffic 1 }

tcInRate OBJECT-TYPE
	SYNTAX Integer32 (0..999999)
	MAX-ACCESS read-write
	STATUS current
	DESCRIPTION
	"Incoming Traffic Limit, in kbits/s"
	::= { traffic 2 }

tcInBurst OBJECT-TYPE
	SYNTAX Integer32 (0..999999)
	MAX-ACCESS read-write
	STATUS current
	DESCRIPTION
	"Incoming Traffic Burst, in kBytes"
	::= { traffic 3 }

tcOutRate OBJECT-TYPE
	SYNTAX Integer32 (0..999999)
	MAX-ACCESS read-write
	STATUS current
	DESCRIPTION
	"Outgoing Traffic Limit, in kbits/s"
	::= { traffic 4 }

tcOutBurst OBJECT-TYPE
	SYNTAX Integer32 (0..999999)
	MAX-ACCESS read-write
	STATUS current
	DESCRIPTION
	"Outgoing Traffic Burst, in kBytes"
	::= { traffic 5 }



-- ==============================================

-- =============== SAVE CMD ====================

executeSaveCmd OBJECT-TYPE
	SYNTAX Integer32 (0..1)
	MAX-ACCESS read-write
	STATUS current
	DESCRIPTION
	"SnmpSet with value 1 to execute the cfg_save() command."
	::= { saveCmd 1 }

-- =============================================


-- ============= RESET CMD ==================

executeResetCmd OBJECT-TYPE
	SYNTAX Integer32 (0..1)
	MAX-ACCESS read-write
	STATUS current
	DESCRIPTION
	"SnmpSet with value 1 to execute the cfg_factory_default() command."
	::= { resetCmd 1 }

-- ===========================================

-- ============= REBOOT CMD ==================

executeRebootCmd OBJECT-TYPE
	SYNTAX Integer32 (1..300)
	MAX-ACCESS read-write
	STATUS current
	DESCRIPTION
	"Define the timeout (1~300seconds) and execute the reboot command."
	::= { rebootCmd 1 }

-- ===========================================



END
