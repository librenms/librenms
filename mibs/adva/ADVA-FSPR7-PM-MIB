--  ***************************************************************************
--  ADVA-FSPR7-PM-MIB.txt
--
--               ADVA AG Optical Networking MIB File
--
--  Copyright 2011 ADVA AG Optical Networking.
--
--  All rights reserved.
--  ***************************************************************************


--  MIB Performance Monitoring definitions required for entity management.

ADVA-FSPR7-PM-MIB DEFINITIONS ::= BEGIN 

IMPORTS



    DateAndTime,
    TruthValue
                FROM SNMPv2-TC


    OBJECT-TYPE,
    MODULE-IDENTITY,
    Unsigned32,
    Integer32
                FROM SNMPv2-SMI


    fspR7,
    Counter64String
                FROM ADVA-MIB


    entityEqptShelfNo,
    entityEqptSlotNo,
    entityEqptPortNo,
    entityEqptExtNo,
    entityEqptClassName,
    entityDcnShelfNo,
    entityDcnSlotNo,
    entityDcnPortNo,
    entityDcnExtNo,
    entityDcnClassName,
    entityFacilityShelfNo,
    entityFacilitySlotNo,
    entityFacilityPortNo,
    entityFacilityExtNo,
    entityFacilityClassName,
    entityTerminPointIndexNo1,
    entityTerminPointIndexNo2,
    entityTerminPointIndexNo3,
    entityTerminPointIndexNo4,
    entityTerminPointClassName,
    entityOpticalMuxShelfNo,
    entityOpticalMuxSlotNo,
    entityOpticalMuxPortNo,
    entityOpticalMuxExtNo,
    entityOpticalMuxClassName,
    entityShelfConnShelfNo,
    entityShelfConnSlotNo,
    entityShelfConnPortNo,
    entityShelfConnExtNo,
    entityShelfConnClassName
                FROM ADVA-FSPR7-MIB;

advaFspR7Pm MODULE-IDENTITY

    LAST-UPDATED "201812140000Z"

    ORGANIZATION "ADVA Optical Networking"

    CONTACT-INFO "EMEA Support
                  Phone : +49 89 89 0665 848
                  Fax   : +49 89 89 0665 22848
                  Email : support@advaoptical.com

                  North American Support
                  Phone : 886 442 ADVA (2382) (toll-free within the US, Canada and Mexico)
                  Fax   : + 1 806 741 8529 (elsewhere)
                  Email : support-usa@advaoptical.com

                  Asia Pacific Support
                  Phone : + 1 866 442 2382 (other toll-free numbers available in some countries)
                  Email : support-asia@advaoptical.com"

    DESCRIPTION   "This is a MIB definition for ADVA AG Optical Networking entity management."

    REVISION        "201812140000Z"
    DESCRIPTION     "FSP3000 F7 Release 18.2.1 MIB."

    REVISION        "201810300000Z"
    DESCRIPTION     "FSP3000 F7 Release 18.1.2 MIB."

    REVISION        "201808090000Z"
    DESCRIPTION     "FSP3000 F7 Release 18.1.1 MIB."

    REVISION        "201805280000Z"
    DESCRIPTION     "FSP3000 F7 Release 17.2.2 MIB."

    REVISION        "201804170000Z"
    DESCRIPTION     "FSP3000 F7 Release 17.2.1 MIB."

    REVISION        "201709110000Z"
    DESCRIPTION     "FSP3000 F7 Release 16.3.1 MIB."

    REVISION        "201703230000Z"
    DESCRIPTION     "FSP3000 F7 Release 16.2.1 MIB."

    REVISION        "201609010000Z"
    DESCRIPTION     "FSP3000 F7 Release 16.1.3 MIB."

    REVISION        "201604010000Z"
    DESCRIPTION     "FSP3000 F7 Release 16.1.1 MIB."

    REVISION        "201512100000Z"
    DESCRIPTION     "FSP3000 F7 Release 15.2.1 MIB."

    REVISION        "201509030000Z"
    DESCRIPTION     "FSP3000 F7 Release 15.1.1 MIB."

    REVISION        "201503200000Z"
    DESCRIPTION     "FSP3000 F7 Release 13.3.1 MIB."

    REVISION        "201410150000Z"
    DESCRIPTION     "FSP3000 F7 Release 13.2.2 MIB."

    REVISION        "201409290000Z"
    DESCRIPTION     "FSP3000 F7 Release 13.2.1 MIB."

    REVISION        "201312040000Z"
    DESCRIPTION     "FSP3000 F7 Release 12.2.1 MIB."

    REVISION        "201308200000Z"
    DESCRIPTION     "FSP3000 F7 Release 12.1.1 MIB."
    ::= { fspR7 11 }

pmEqpt
    OBJECT IDENTIFIER ::= { advaFspR7Pm 1 }

pmEqptData
    OBJECT IDENTIFIER ::= { pmEqpt 1 }

pmEqptDataThreshold
    OBJECT IDENTIFIER ::= { pmEqptData 1 }

pmqpteDataRecord
    OBJECT IDENTIFIER ::= { pmEqptData 2 }

pmEqptPhysical
    OBJECT IDENTIFIER ::= { pmEqpt 2 }

pmEqptPhysValue
    OBJECT IDENTIFIER ::= { pmEqptPhysical 1 }

pmEqptPhysThreshold
    OBJECT IDENTIFIER ::= { pmEqptPhysical 2 }

pmEqptPhysRecord
    OBJECT IDENTIFIER ::= { pmEqptPhysical 3 }

pmDcn
    OBJECT IDENTIFIER ::= { advaFspR7Pm 2 }

pmDcnData
    OBJECT IDENTIFIER ::= { pmDcn 1 }

pmDcnDataThreshold
    OBJECT IDENTIFIER ::= { pmDcnData 1 }

pmDcnDataRecord
    OBJECT IDENTIFIER ::= { pmDcnData 2 }

pmDcnPhysical
    OBJECT IDENTIFIER ::= { pmDcn 2 }

pmDcnPhysValue
    OBJECT IDENTIFIER ::= { pmDcnPhysical 1 }

pmDcnPhysThreshold
    OBJECT IDENTIFIER ::= { pmDcnPhysical 2 }

pmDcnPhysRecord
    OBJECT IDENTIFIER ::= { pmDcnPhysical 3 }

pmFacility
    OBJECT IDENTIFIER ::= { advaFspR7Pm 7 }

pmFacilityData
    OBJECT IDENTIFIER ::= { pmFacility 1 }

pmFacilityDataThreshold
    OBJECT IDENTIFIER ::= { pmFacilityData 1 }

pmFacilityDataRecord
    OBJECT IDENTIFIER ::= { pmFacilityData 2 }

pmFacilityDataValue
    OBJECT IDENTIFIER ::= { pmFacilityData 3 }

pmFacilityPhysical
    OBJECT IDENTIFIER ::= { pmFacility 2 }

pmFacilityPhysValue
    OBJECT IDENTIFIER ::= { pmFacilityPhysical 1 }

pmFacilityPhysThreshold
    OBJECT IDENTIFIER ::= { pmFacilityPhysical 2 }

pmFacilityPhysRecord
    OBJECT IDENTIFIER ::= { pmFacilityPhysical 3 }

pmTerminPoint
    OBJECT IDENTIFIER ::= { advaFspR7Pm 10 }

pmTerminPointData
    OBJECT IDENTIFIER ::= { pmTerminPoint 1 }

pmTerminPointDataThreshold
    OBJECT IDENTIFIER ::= { pmTerminPointData 1 }

pmTerminPointDataRecord
    OBJECT IDENTIFIER ::= { pmTerminPointData 2 }

pmTerminPointPhysical
    OBJECT IDENTIFIER ::= { pmTerminPoint 2 }

pmTerminPointPhysValue
    OBJECT IDENTIFIER ::= { pmTerminPointPhysical 1 }

pmTerminPointPhysThreshold
    OBJECT IDENTIFIER ::= { pmTerminPointPhysical 2 }

pmTerminPointPhysRecord
    OBJECT IDENTIFIER ::= { pmTerminPointPhysical 3 }

pmOptMux
    OBJECT IDENTIFIER ::= { advaFspR7Pm 17 }

pmOptMuxData
    OBJECT IDENTIFIER ::= { pmOptMux 1 }

pmOptMuxDataThreshold
    OBJECT IDENTIFIER ::= { pmOptMuxData 1 }

pmOptMuxDataRecord
    OBJECT IDENTIFIER ::= { pmOptMuxData 2 }

pmOptMuxPhysical
    OBJECT IDENTIFIER ::= { pmOptMux 2 }

pmOptMuxPhysValue
    OBJECT IDENTIFIER ::= { pmOptMuxPhysical 1 }

pmOptMuxPhysThreshold
    OBJECT IDENTIFIER ::= { pmOptMuxPhysical 2 }

pmOptMuxPhysRecord
    OBJECT IDENTIFIER ::= { pmOptMuxPhysical 3 }

pmShelfConnection
    OBJECT IDENTIFIER ::= { advaFspR7Pm 18 }

pmShelfConnectionData
    OBJECT IDENTIFIER ::= { pmShelfConnection 1 }

pmShelfConnectionDataRecord
    OBJECT IDENTIFIER ::= { pmShelfConnectionData 2 }

eqptPhysInstValueTable OBJECT-TYPE
    SYNTAX        SEQUENCE OF EqptPhysInstValueEntry
    MAX-ACCESS    not-accessible
    STATUS        current
    DESCRIPTION   ""
    ::= { pmEqptPhysValue 1 }

eqptPhysInstValueEntry OBJECT-TYPE
    SYNTAX        EqptPhysInstValueEntry
    MAX-ACCESS    not-accessible
    STATUS        current
    DESCRIPTION   ""
    INDEX       {
                  entityEqptShelfNo,
                  entityEqptSlotNo,
                  entityEqptPortNo,
                  entityEqptExtNo,
                  entityEqptClassName
                }
    ::= { eqptPhysInstValueTable 1 }

EqptPhysInstValueEntry ::= SEQUENCE
  {    eqptPhysInstValueWattUp Unsigned32,
    eqptPhysInstValueWattOut Unsigned32,
    eqptPhysInstValueSubTemp Integer32,
    eqptPhysInstValueAmpere Unsigned32,
    eqptPhysInstValueTemp Integer32,
    eqptPhysInstValuePsuAmpere Unsigned32,
    eqptPhysInstValuePsuVoltInp Unsigned32,
    eqptPhysInstValueTempExt Integer32,
    eqptPhysInstValueMaxOutProt Unsigned32,
    eqptPhysInstValuePwrUse Unsigned32,
    eqptPhysInstValueMaxOutThres Unsigned32,
    eqptPhysInstValueLaserTemp Integer32,
    eqptPhysInstValuePwrConsumption Unsigned32,
    eqptPhysInstValueFanSpeed Unsigned32,
    eqptPhysInstValueOutputPwr Unsigned32 }

eqptPhysInstValueWattUp OBJECT-TYPE
    SYNTAX        Unsigned32
    UNITS         "W"
    MAX-ACCESS    read-only
    STATUS        current
    DESCRIPTION   "Sum maximum power conusmption for installed and/or provisioned equipment in the shelf excluding PSUs
        also includes power required for Fan startup in SH4 and SH12 shelves"
    ::= { eqptPhysInstValueEntry 1 }

eqptPhysInstValueWattOut OBJECT-TYPE
    SYNTAX        Unsigned32
    UNITS         "W"
    MAX-ACCESS    read-only
    STATUS        current
    DESCRIPTION   "Sum of the maximum output power for the power supplies (PSU or PSM) in the shelf with redundancy taken into account"
    ::= { eqptPhysInstValueEntry 2 }

eqptPhysInstValueSubTemp OBJECT-TYPE
    SYNTAX        Integer32
    UNITS         "0.1 degree Celsius"
    MAX-ACCESS    read-only
    STATUS        current
    DESCRIPTION   "Submodule Temperature"
    ::= { eqptPhysInstValueEntry 3 }

eqptPhysInstValueAmpere OBJECT-TYPE
    SYNTAX        Unsigned32
    UNITS         "0.001 A"
    MAX-ACCESS    read-only
    STATUS        current
    DESCRIPTION   "Instantaneous Current"
    ::= { eqptPhysInstValueEntry 4 }

eqptPhysInstValueTemp OBJECT-TYPE
    SYNTAX        Integer32
    UNITS         "0.1 degree Celsius"
    MAX-ACCESS    read-only
    STATUS        current
    DESCRIPTION   "Current (Instantaneous) Temperature"
    ::= { eqptPhysInstValueEntry 5 }

eqptPhysInstValuePsuAmpere OBJECT-TYPE
    SYNTAX        Unsigned32
    UNITS         "0.001 A"
    MAX-ACCESS    read-only
    STATUS        current
    DESCRIPTION   "PSU Input Instantaneous Current"
    ::= { eqptPhysInstValueEntry 6 }

eqptPhysInstValuePsuVoltInp OBJECT-TYPE
    SYNTAX        Unsigned32
    UNITS         "0.001 V"
    MAX-ACCESS    read-only
    STATUS        current
    DESCRIPTION   "PSU Input Voltage"
    ::= { eqptPhysInstValueEntry 7 }

eqptPhysInstValueTempExt OBJECT-TYPE
    SYNTAX        Integer32
    UNITS         "0.1 degree Celsius"
    MAX-ACCESS    read-only
    STATUS        current
    DESCRIPTION   "Shelf external ambient temperatur"
    ::= { eqptPhysInstValueEntry 8 }

eqptPhysInstValueMaxOutProt OBJECT-TYPE
    SYNTAX        Unsigned32
    UNITS         "W"
    MAX-ACCESS    read-only
    STATUS        current
    DESCRIPTION   "Sum of the equipment maximum power that can be protected for PSU failure"
    ::= { eqptPhysInstValueEntry 9 }

eqptPhysInstValuePwrUse OBJECT-TYPE
    SYNTAX        Unsigned32
    UNITS         "W"
    MAX-ACCESS    read-only
    STATUS        current
    DESCRIPTION   "Equipment power used"
    ::= { eqptPhysInstValueEntry 10 }

eqptPhysInstValueMaxOutThres OBJECT-TYPE
    SYNTAX        Unsigned32
    UNITS         "W"
    MAX-ACCESS    read-only
    STATUS        current
    DESCRIPTION   "Sum of the PSUs maximum output power in the shelf minus power of the strongest one (if more than one PSU equipped)."
    ::= { eqptPhysInstValueEntry 11 }

eqptPhysInstValueLaserTemp OBJECT-TYPE
    SYNTAX        Integer32
    UNITS         "0.1 degree Celsius"
    MAX-ACCESS    read-only
    STATUS        current
    DESCRIPTION   "Laser Temperature"
    ::= { eqptPhysInstValueEntry 12 }

eqptPhysInstValuePwrConsumption OBJECT-TYPE
    SYNTAX        Unsigned32
    UNITS         "W"
    MAX-ACCESS    read-only
    STATUS        current
    DESCRIPTION   "Instantaneous Power Consumption"
    ::= { eqptPhysInstValueEntry 13 }

eqptPhysInstValueFanSpeed OBJECT-TYPE
    SYNTAX        Unsigned32
    UNITS         "rpm"
    MAX-ACCESS    read-only
    STATUS        current
    DESCRIPTION   "Fan Speed"
    ::= { eqptPhysInstValueEntry 14 }

eqptPhysInstValueOutputPwr OBJECT-TYPE
    SYNTAX        Unsigned32
    UNITS         "W"
    MAX-ACCESS    read-only
    STATUS        current
    DESCRIPTION   "Instantaneous Output Power"
    ::= { eqptPhysInstValueEntry 15 }

endOfEqptPhysInstValueTable OBJECT-TYPE
    SYNTAX        Integer32
    MAX-ACCESS    read-only
    STATUS        current
    DESCRIPTION   ""
    ::= { pmEqptPhysValue 2 }

endOfPmEqptPhysValue OBJECT-TYPE
    SYNTAX        Integer32
    MAX-ACCESS    read-only
    STATUS        current
    DESCRIPTION   ""
    ::= { pmEqptPhysValue 10000 }

eqptPhysThresholdTable OBJECT-TYPE
    SYNTAX        SEQUENCE OF EqptPhysThresholdEntry
    MAX-ACCESS    not-accessible
    STATUS        current
    DESCRIPTION   ""
    ::= { pmEqptPhysThreshold 1 }

eqptPhysThresholdEntry OBJECT-TYPE
    SYNTAX        EqptPhysThresholdEntry
    MAX-ACCESS    not-accessible
    STATUS        current
    DESCRIPTION   ""
    INDEX       {
                  entityEqptShelfNo,
                  entityEqptSlotNo,
                  entityEqptPortNo,
                  entityEqptExtNo,
                  entityEqptClassName
                }
    ::= { eqptPhysThresholdTable 1 }

EqptPhysThresholdEntry ::= SEQUENCE
  {    eqptPhysThresholdTempHigh Integer32,
    eqptPhysThresholdTempLow Integer32,
    eqptPhysThresholdAmpHigh Unsigned32,
    eqptPhysThresholdSubTempHigh Integer32,
    eqptPhysThresholdLaserTempHighThres Integer32,
    eqptPhysThresholdLaserTempLowThres Integer32,
    eqptPhysThresholdPwrConsumptionHigh Unsigned32,
    eqptPhysThresholdOutputPwrHigh Unsigned32 }

eqptPhysThresholdTempHigh OBJECT-TYPE
    SYNTAX        Integer32
    UNITS         "0.1 degree Celsius"
    MAX-ACCESS    read-only
    STATUS        current
    DESCRIPTION   "Board Temperature"
    ::= { eqptPhysThresholdEntry 1 }

eqptPhysThresholdTempLow OBJECT-TYPE
    SYNTAX        Integer32
    UNITS         "0.1 degree Celsius"
    MAX-ACCESS    read-only
    STATUS        current
    DESCRIPTION   "Board Temperature"
    ::= { eqptPhysThresholdEntry 2 }

eqptPhysThresholdAmpHigh OBJECT-TYPE
    SYNTAX        Unsigned32
    UNITS         "0.001 A"
    MAX-ACCESS    read-only
    STATUS        current
    DESCRIPTION   "Fixed Threshold, read only"
    ::= { eqptPhysThresholdEntry 3 }

eqptPhysThresholdSubTempHigh OBJECT-TYPE
    SYNTAX        Integer32
    UNITS         "0.1 degree Celsius"
    MAX-ACCESS    read-only
    STATUS        current
    DESCRIPTION   "Submodule High Temperature Threshold"
    ::= { eqptPhysThresholdEntry 4 }

eqptPhysThresholdLaserTempHighThres OBJECT-TYPE
    SYNTAX        Integer32
    UNITS         "0.1 degree Celsius"
    MAX-ACCESS    read-only
    STATUS        current
    DESCRIPTION   "Laser temperature fixed high threshold."
    ::= { eqptPhysThresholdEntry 5 }

eqptPhysThresholdLaserTempLowThres OBJECT-TYPE
    SYNTAX        Integer32
    UNITS         "0.1 degree Celsius"
    MAX-ACCESS    read-only
    STATUS        current
    DESCRIPTION   "Laser temperature fixed low threshold."
    ::= { eqptPhysThresholdEntry 6 }

eqptPhysThresholdPwrConsumptionHigh OBJECT-TYPE
    SYNTAX        Unsigned32
    UNITS         "W"
    MAX-ACCESS    read-only
    STATUS        current
    DESCRIPTION   "Power Consumption (W) High, Fixed Threshold, read only"
    ::= { eqptPhysThresholdEntry 7 }

eqptPhysThresholdOutputPwrHigh OBJECT-TYPE
    SYNTAX        Unsigned32
    UNITS         "W"
    MAX-ACCESS    read-only
    STATUS        current
    DESCRIPTION   "Output Power High, Fixed Threshold, read only"
    ::= { eqptPhysThresholdEntry 8 }

endOfEqptPhysThresholdTable OBJECT-TYPE
    SYNTAX        Integer32
    MAX-ACCESS    read-only
    STATUS        current
    DESCRIPTION   ""
    ::= { pmEqptPhysThreshold 2 }

endOfPmEqptPhysThreshold OBJECT-TYPE
    SYNTAX        Integer32
    MAX-ACCESS    read-only
    STATUS        current
    DESCRIPTION   ""
    ::= { pmEqptPhysThreshold 10000 }

ampEqptHistorical15minTable OBJECT-TYPE
    SYNTAX        SEQUENCE OF AmpEqptHistorical15minEntry
    MAX-ACCESS    not-accessible
    STATUS        current
    DESCRIPTION   ""
    ::= { pmEqptPhysRecord 1 }

ampEqptHistorical15minEntry OBJECT-TYPE
    SYNTAX        AmpEqptHistorical15minEntry
    MAX-ACCESS    not-accessible
    STATUS        current
    DESCRIPTION   ""
    INDEX       {
                  entityEqptShelfNo,
                  entityEqptSlotNo,
                  entityEqptPortNo,
                  entityEqptExtNo,
                  entityEqptClassName,
                  ampEqptHistorical15minNumber
                }
    ::= { ampEqptHistorical15minTable 1 }

AmpEqptHistorical15minEntry ::= SEQUENCE
  {    ampEqptHistorical15minNumber Integer32,
    ampEqptHistorical15minLow Unsigned32,
    ampEqptHistorical15minMean Unsigned32,
    ampEqptHistorical15minHigh Unsigned32,
    ampEqptHistorical15minValidFlag TruthValue,
    ampEqptHistorical15minTimeStamp DateAndTime }

ampEqptHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { ampEqptHistorical15minEntry 1 }

ampEqptHistorical15minLow OBJECT-TYPE
    SYNTAX        Unsigned32
    UNITS         "0.001 A"
    MAX-ACCESS    read-only
    STATUS        current
    DESCRIPTION   "Board or Pluggable Submodule Low Current"
    ::= { ampEqptHistorical15minEntry 2 }

ampEqptHistorical15minMean OBJECT-TYPE
    SYNTAX        Unsigned32
    UNITS         "0.001 A"
    MAX-ACCESS    read-only
    STATUS        current
    DESCRIPTION   "Board or Pluggable Submodule Mean Current"
    ::= { ampEqptHistorical15minEntry 3 }

ampEqptHistorical15minHigh OBJECT-TYPE
    SYNTAX        Unsigned32
    UNITS         "0.001 A"
    MAX-ACCESS    read-only
    STATUS        current
    DESCRIPTION   "Board or Pluggable Submodule High Current"
    ::= { ampEqptHistorical15minEntry 4 }

ampEqptHistorical15minValidFlag OBJECT-TYPE
    SYNTAX        TruthValue
    MAX-ACCESS    read-only
    STATUS        current
    DESCRIPTION   "Valid Flag"
    ::= { ampEqptHistorical15minEntry 5 }

ampEqptHistorical15minTimeStamp OBJECT-TYPE
    SYNTAX        DateAndTime
    MAX-ACCESS    read-only
    STATUS        current
    DESCRIPTION   "Timestamp"
    ::= { ampEqptHistorical15minEntry 6 }

endOfAmpEqptHistorical15minTable OBJECT-TYPE
    SYNTAX        Integer32
    MAX-ACCESS    read-only
    STATUS        current
    DESCRIPTION   ""
    ::= { pmEqptPhysRecord 2 }

ampEqptHistorical1dayTable OBJECT-TYPE
    SYNTAX        SEQUENCE OF AmpEqptHistorical1dayEntry
    MAX-ACCESS    not-accessible
    STATUS        current
    DESCRIPTION   ""
    ::= { pmEqptPhysRecord 3 }

ampEqptHistorical1dayEntry OBJECT-TYPE
    SYNTAX        AmpEqptHistorical1dayEntry
    MAX-ACCESS    not-accessible
    STATUS        current
    DESCRIPTION   ""
    INDEX       {
                  entityEqptShelfNo,
                  entityEqptSlotNo,
                  entityEqptPortNo,
                  entityEqptExtNo,
                  entityEqptClassName,
                  ampEqptHistorical1dayNumber
                }
    ::= { ampEqptHistorical1dayTable 1 }

AmpEqptHistorical1dayEntry ::= SEQUENCE
  {    ampEqptHistorical1dayNumber Integer32,
    ampEqptHistorical1dayLow Unsigned32,
    ampEqptHistorical1dayMean Unsigned32,
    ampEqptHistorical1dayHigh Unsigned32,
    ampEqptHistorical1dayValidFlag TruthValue,
    ampEqptHistorical1dayTimeStamp DateAndTime }

ampEqptHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { ampEqptHistorical1dayEntry 1 }

ampEqptHistorical1dayLow OBJECT-TYPE
    SYNTAX        Unsigned32
    UNITS         "0.001 A"
    MAX-ACCESS    read-only
    STATUS        current
    DESCRIPTION   "Board or Pluggable Submodule Low Current"
    ::= { ampEqptHistorical1dayEntry 2 }

ampEqptHistorical1dayMean OBJECT-TYPE
    SYNTAX        Unsigned32
    UNITS         "0.001 A"
    MAX-ACCESS    read-only
    STATUS        current
    DESCRIPTION   "Board or Pluggable Submodule Mean Current"
    ::= { ampEqptHistorical1dayEntry 3 }

ampEqptHistorical1dayHigh OBJECT-TYPE
    SYNTAX        Unsigned32
    UNITS         "0.001 A"
    MAX-ACCESS    read-only
    STATUS        current
    DESCRIPTION   "Board or Pluggable Submodule High Current"
    ::= { ampEqptHistorical1dayEntry 4 }

ampEqptHistorical1dayValidFlag OBJECT-TYPE
    SYNTAX        TruthValue
    MAX-ACCESS    read-only
    STATUS        current
    DESCRIPTION   "Valid Flag"
    ::= { ampEqptHistorical1dayEntry 5 }

ampEqptHistorical1dayTimeStamp OBJECT-TYPE
    SYNTAX        DateAndTime
    MAX-ACCESS    read-only
    STATUS        current
    DESCRIPTION   "Timestamp"
    ::= { ampEqptHistorical1dayEntry 6 }

endOfAmpEqptHistorical1dayTable OBJECT-TYPE
    SYNTAX        Integer32
    MAX-ACCESS    read-only
    STATUS        current
    DESCRIPTION   ""
    ::= { pmEqptPhysRecord 4 }

ampEqptHistorical1weekTable OBJECT-TYPE
    SYNTAX        SEQUENCE OF AmpEqptHistorical1weekEntry
    MAX-ACCESS    not-accessible
    STATUS        current
    DESCRIPTION   ""
    ::= { pmEqptPhysRecord 5 }

ampEqptHistorical1weekEntry OBJECT-TYPE
    SYNTAX        AmpEqptHistorical1weekEntry
    MAX-ACCESS    not-accessible
    STATUS        current
    DESCRIPTION   ""
    INDEX       {
                  entityEqptShelfNo,
                  entityEqptSlotNo,
                  entityEqptPortNo,
                  entityEqptExtNo,
                  entityEqptClassName,
                  ampEqptHistorical1weekNumber
                }
    ::= { ampEqptHistorical1weekTable 1 }

AmpEqptHistorical1weekEntry ::= SEQUENCE
  {    ampEqptHistorical1weekNumber Integer32,
    ampEqptHistorical1weekLow Unsigned32,
    ampEqptHistorical1weekMean Unsigned32,
    ampEqptHistorical1weekHigh Unsigned32,
    ampEqptHistorical1weekValidFlag TruthValue,
    ampEqptHistorical1weekTimeStamp DateAndTime }

ampEqptHistorical1weekNumber OBJECT-TYPE
    SYNTAX        Integer32 (1..52)
    MAX-ACCESS    not-accessible
    STATUS        current
    DESCRIPTION   "Number 1week"
    ::= { ampEqptHistorical1weekEntry 1 }

ampEqptHistorical1weekLow OBJECT-TYPE
    SYNTAX        Unsigned32
    UNITS         "0.001 A"
    MAX-ACCESS    read-only
    STATUS        current
    DESCRIPTION   "Board or Pluggable Submodule Low Current"
    ::= { ampEqptHistorical1weekEntry 2 }

ampEqptHistorical1weekMean OBJECT-TYPE
    SYNTAX        Unsigned32
    UNITS         "0.001 A"
    MAX-ACCESS    read-only
    STATUS        current
    DESCRIPTION   "Board or Pluggable Submodule Mean Current"
    ::= { ampEqptHistorical1weekEntry 3 }

ampEqptHistorical1weekHigh OBJECT-TYPE
    SYNTAX        Unsigned32
    UNITS         "0.001 A"
    MAX-ACCESS    read-only
    STATUS        current
    DESCRIPTION   "Board or Pluggable Submodule High Current"
    ::= { ampEqptHistorical1weekEntry 4 }

ampEqptHistorical1weekValidFlag OBJECT-TYPE
    SYNTAX        TruthValue
    MAX-ACCESS    read-only
    STATUS        current
    DESCRIPTION   "Valid Flag"
    ::= { ampEqptHistorical1weekEntry 5 }

ampEqptHistorical1weekTimeStamp OBJECT-TYPE
    SYNTAX        DateAndTime
    MAX-ACCESS    read-only
    STATUS        current
    DESCRIPTION   "Timestamp"
    ::= { ampEqptHistorical1weekEntry 6 }

endOfAmpEqptHistorical1weekTable OBJECT-TYPE
    SYNTAX        Integer32
    MAX-ACCESS    read-only
    STATUS        current
    DESCRIPTION   ""
    ::= { pmEqptPhysRecord 6 }

ampInEqptHistorical15minTable OBJECT-TYPE
    SYNTAX        SEQUENCE OF AmpInEqptHistorical15minEntry
    MAX-ACCESS    not-accessible
    STATUS        current
    DESCRIPTION   ""
    ::= { pmEqptPhysRecord 7 }

ampInEqptHistorical15minEntry OBJECT-TYPE
    SYNTAX        AmpInEqptHistorical15minEntry
    MAX-ACCESS    not-accessible
    STATUS        current
    DESCRIPTION   ""
    INDEX       {
                  entityEqptShelfNo,
                  entityEqptSlotNo,
                  entityEqptPortNo,
                  entityEqptExtNo,
                  entityEqptClassName,
                  ampInEqptHistorical15minNumber
                }
    ::= { ampInEqptHistorical15minTable 1 }

AmpInEqptHistorical15minEntry ::= SEQUENCE
  {    ampInEqptHistorical15minNumber Integer32,
    ampInEqptHistorical15minLow Unsigned32,
    ampInEqptHistorical15minMean Unsigned32,
    ampInEqptHistorical15minHigh Unsigned32,
    ampInEqptHistorical15minValidFlag TruthValue,
    ampInEqptHistorical15minTimeStamp DateAndTime }

ampInEqptHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { ampInEqptHistorical15minEntry 1 }

ampInEqptHistorical15minLow OBJECT-TYPE
    SYNTAX        Unsigned32
    UNITS         "0.001 A"
    MAX-ACCESS    read-only
    STATUS        current
    DESCRIPTION   "PSU Input Low Current"
    ::= { ampInEqptHistorical15minEntry 2 }

ampInEqptHistorical15minMean OBJECT-TYPE
    SYNTAX        Unsigned32
    UNITS         "0.001 A"
    MAX-ACCESS    read-only
    STATUS        current
    DESCRIPTION   "PSU Input Mean Current"
    ::= { ampInEqptHistorical15minEntry 3 }

ampInEqptHistorical15minHigh OBJECT-TYPE
    SYNTAX        Unsigned32
    UNITS         "0.001 A"
    MAX-ACCESS    read-only
    STATUS        current
    DESCRIPTION   "PSU Input High Current"
    ::= { ampInEqptHistorical15minEntry 4 }

ampInEqptHistorical15minValidFlag OBJECT-TYPE
    SYNTAX        TruthValue
    MAX-ACCESS    read-only
    STATUS        current
    DESCRIPTION   "Valid Flag"
    ::= { ampInEqptHistorical15minEntry 5 }

ampInEqptHistorical15minTimeStamp OBJECT-TYPE
    SYNTAX        DateAndTime
    MAX-ACCESS    read-only
    STATUS        current
    DESCRIPTION   "Timestamp"
    ::= { ampInEqptHistorical15minEntry 6 }

endOfAmpInEqptHistorical15minTable OBJECT-TYPE
    SYNTAX        Integer32
    MAX-ACCESS    read-only
    STATUS        current
    DESCRIPTION   ""
    ::= { pmEqptPhysRecord 8 }

ampInEqptHistorical1dayTable OBJECT-TYPE
    SYNTAX        SEQUENCE OF AmpInEqptHistorical1dayEntry
    MAX-ACCESS    not-accessible
    STATUS        current
    DESCRIPTION   ""
    ::= { pmEqptPhysRecord 9 }

ampInEqptHistorical1dayEntry OBJECT-TYPE
    SYNTAX        AmpInEqptHistorical1dayEntry
    MAX-ACCESS    not-accessible
    STATUS        current
    DESCRIPTION   ""
    INDEX       {
                  entityEqptShelfNo,
                  entityEqptSlotNo,
                  entityEqptPortNo,
                  entityEqptExtNo,
                  entityEqptClassName,
                  ampInEqptHistorical1dayNumber
                }
    ::= { ampInEqptHistorical1dayTable 1 }

AmpInEqptHistorical1dayEntry ::= SEQUENCE
  {    ampInEqptHistorical1dayNumber Integer32,
    ampInEqptHistorical1dayLow Unsigned32,
    ampInEqptHistorical1dayMean Unsigned32,
    ampInEqptHistorical1dayHigh Unsigned32,
    ampInEqptHistorical1dayValidFlag TruthValue,
    ampInEqptHistorical1dayTimeStamp DateAndTime }

ampInEqptHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { ampInEqptHistorical1dayEntry 1 }

ampInEqptHistorical1dayLow OBJECT-TYPE
    SYNTAX        Unsigned32
    UNITS         "0.001 A"
    MAX-ACCESS    read-only
    STATUS        current
    DESCRIPTION   "PSU Input Low Current"
    ::= { ampInEqptHistorical1dayEntry 2 }

ampInEqptHistorical1dayMean OBJECT-TYPE
    SYNTAX        Unsigned32
    UNITS         "0.001 A"
    MAX-ACCESS    read-only
    STATUS        current
    DESCRIPTION   "PSU Input Mean Current"
    ::= { ampInEqptHistorical1dayEntry 3 }

ampInEqptHistorical1dayHigh OBJECT-TYPE
    SYNTAX        Unsigned32
    UNITS         "0.001 A"
    MAX-ACCESS    read-only
    STATUS        current
    DESCRIPTION   "PSU Input High Current"
    ::= { ampInEqptHistorical1dayEntry 4 }

ampInEqptHistorical1dayValidFlag OBJECT-TYPE
    SYNTAX        TruthValue
    MAX-ACCESS    read-only
    STATUS        current
    DESCRIPTION   "Valid Flag"
    ::= { ampInEqptHistorical1dayEntry 5 }

ampInEqptHistorical1dayTimeStamp OBJECT-TYPE
    SYNTAX        DateAndTime
    MAX-ACCESS    read-only
    STATUS        current
    DESCRIPTION   "Timestamp"
    ::= { ampInEqptHistorical1dayEntry 6 }

endOfAmpInEqptHistorical1dayTable OBJECT-TYPE
    SYNTAX        Integer32
    MAX-ACCESS    read-only
    STATUS        current
    DESCRIPTION   ""
    ::= { pmEqptPhysRecord 10 }

ampInEqptHistorical1weekTable OBJECT-TYPE
    SYNTAX        SEQUENCE OF AmpInEqptHistorical1weekEntry
    MAX-ACCESS    not-accessible
    STATUS        current
    DESCRIPTION   ""
    ::= { pmEqptPhysRecord 11 }

ampInEqptHistorical1weekEntry OBJECT-TYPE
    SYNTAX        AmpInEqptHistorical1weekEntry
    MAX-ACCESS    not-accessible
    STATUS        current
    DESCRIPTION   ""
    INDEX       {
                  entityEqptShelfNo,
                  entityEqptSlotNo,
                  entityEqptPortNo,
                  entityEqptExtNo,
                  entityEqptClassName,
                  ampInEqptHistorical1weekNumber
                }
    ::= { ampInEqptHistorical1weekTable 1 }

AmpInEqptHistorical1weekEntry ::= SEQUENCE
  {    ampInEqptHistorical1weekNumber Integer32,
    ampInEqptHistorical1weekLow Unsigned32,
    ampInEqptHistorical1weekMean Unsigned32,
    ampInEqptHistorical1weekHigh Unsigned32,
    ampInEqptHistorical1weekValidFlag TruthValue,
    ampInEqptHistorical1weekTimeStamp DateAndTime }

ampInEqptHistorical1weekNumber OBJECT-TYPE
    SYNTAX        Integer32 (1..52)
    MAX-ACCESS    not-accessible
    STATUS        current
    DESCRIPTION   "Number 1week"
    ::= { ampInEqptHistorical1weekEntry 1 }

ampInEqptHistorical1weekLow OBJECT-TYPE
    SYNTAX        Unsigned32
    UNITS         "0.001 A"
    MAX-ACCESS    read-only
    STATUS        current
    DESCRIPTION   "PSU Input Low Current"
    ::= { ampInEqptHistorical1weekEntry 2 }

ampInEqptHistorical1weekMean OBJECT-TYPE
    SYNTAX        Unsigned32
    UNITS         "0.001 A"
    MAX-ACCESS    read-only
    STATUS        current
    DESCRIPTION   "PSU Input Mean Current"
    ::= { ampInEqptHistorical1weekEntry 3 }

ampInEqptHistorical1weekHigh OBJECT-TYPE
    SYNTAX        Unsigned32
    UNITS         "0.001 A"
    MAX-ACCESS    read-only
    STATUS        current
    DESCRIPTION   "PSU Input High Current"
    ::= { ampInEqptHistorical1weekEntry 4 }

ampInEqptHistorical1weekValidFlag OBJECT-TYPE
    SYNTAX        TruthValue
    MAX-ACCESS    read-only
    STATUS        current
    DESCRIPTION   "Valid Flag"
    ::= { ampInEqptHistorical1weekEntry 5 }

ampInEqptHistorical1weekTimeStamp OBJECT-TYPE
    SYNTAX        DateAndTime
    MAX-ACCESS    read-only
    STATUS        current
    DESCRIPTION   "Timestamp"
    ::= { ampInEqptHistorical1weekEntry 6 }

endOfAmpInEqptHistorical1weekTable OBJECT-TYPE
    SYNTAX        Integer32
    MAX-ACCESS    read-only
    STATUS        current
    DESCRIPTION   ""
    ::= { pmEqptPhysRecord 12 }

voltInpEqptHistorical15minTable OBJECT-TYPE
    SYNTAX        SEQUENCE OF VoltInpEqptHistorical15minEntry
    MAX-ACCESS    not-accessible
    STATUS        current
    DESCRIPTION   ""
    ::= { pmEqptPhysRecord 13 }

voltInpEqptHistorical15minEntry OBJECT-TYPE
    SYNTAX        VoltInpEqptHistorical15minEntry
    MAX-ACCESS    not-accessible
    STATUS        current
    DESCRIPTION   ""
    INDEX       {
                  entityEqptShelfNo,
                  entityEqptSlotNo,
                  entityEqptPortNo,
                  entityEqptExtNo,
                  entityEqptClassName,
                  voltInpEqptHistorical15minNumber
                }
    ::= { voltInpEqptHistorical15minTable 1 }

VoltInpEqptHistorical15minEntry ::= SEQUENCE
  {    voltInpEqptHistorical15minNumber Integer32,
    voltInpEqptHistorical15minLow Unsigned32,
    voltInpEqptHistorical15minMean Unsigned32,
    voltInpEqptHistorical15minHigh Unsigned32,
    voltInpEqptHistorical15minValidFlag TruthValue,
    voltInpEqptHistorical15minTimeStamp DateAndTime }

voltInpEqptHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { voltInpEqptHistorical15minEntry 1 }

voltInpEqptHistorical15minLow OBJECT-TYPE
    SYNTAX        Unsigned32
    UNITS         "0.001 V"
    MAX-ACCESS    read-only
    STATUS        current
    DESCRIPTION   "PSU Input Low Voltage"
    ::= { voltInpEqptHistorical15minEntry 2 }

voltInpEqptHistorical15minMean OBJECT-TYPE
    SYNTAX        Unsigned32
    UNITS         "0.001 V"
    MAX-ACCESS    read-only
    STATUS        current
    DESCRIPTION   "PSU Input Mean Voltage"
    ::= { voltInpEqptHistorical15minEntry 3 }

voltInpEqptHistorical15minHigh OBJECT-TYPE
    SYNTAX        Unsigned32
    UNITS         "0.001 V"
    MAX-ACCESS    read-only
    STATUS        current
    DESCRIPTION   "PSU Input High Voltage"
    ::= { voltInpEqptHistorical15minEntry 4 }

voltInpEqptHistorical15minValidFlag OBJECT-TYPE
    SYNTAX        TruthValue
    MAX-ACCESS    read-only
    STATUS        current
    DESCRIPTION   "Valid Flag"
    ::= { voltInpEqptHistorical15minEntry 5 }

voltInpEqptHistorical15minTimeStamp OBJECT-TYPE
    SYNTAX        DateAndTime
    MAX-ACCESS    read-only
    STATUS        current
    DESCRIPTION   "Timestamp"
    ::= { voltInpEqptHistorical15minEntry 6 }

endOfVoltInpEqptHistorical15minTable OBJECT-TYPE
    SYNTAX        Integer32
    MAX-ACCESS    read-only
    STATUS        current
    DESCRIPTION   ""
    ::= { pmEqptPhysRecord 14 }

voltInpEqptHistorical1dayTable OBJECT-TYPE
    SYNTAX        SEQUENCE OF VoltInpEqptHistorical1dayEntry
    MAX-ACCESS    not-accessible
    STATUS        current
    DESCRIPTION   ""
    ::= { pmEqptPhysRecord 15 }

voltInpEqptHistorical1dayEntry OBJECT-TYPE
    SYNTAX        VoltInpEqptHistorical1dayEntry
    MAX-ACCESS    not-accessible
    STATUS        current
    DESCRIPTION   ""
    INDEX       {
                  entityEqptShelfNo,
                  entityEqptSlotNo,
                  entityEqptPortNo,
                  entityEqptExtNo,
                  entityEqptClassName,
                  voltInpEqptHistorical1dayNumber
                }
    ::= { voltInpEqptHistorical1dayTable 1 }

VoltInpEqptHistorical1dayEntry ::= SEQUENCE
  {    voltInpEqptHistorical1dayNumber Integer32,
    voltInpEqptHistorical1dayLow Unsigned32,
    voltInpEqptHistorical1dayMean Unsigned32,
    voltInpEqptHistorical1dayHigh Unsigned32,
    voltInpEqptHistorical1dayValidFlag TruthValue,
    voltInpEqptHistorical1dayTimeStamp DateAndTime }

voltInpEqptHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { voltInpEqptHistorical1dayEntry 1 }

voltInpEqptHistorical1dayLow OBJECT-TYPE
    SYNTAX        Unsigned32
    UNITS         "0.001 V"
    MAX-ACCESS    read-only
    STATUS        current
    DESCRIPTION   "PSU Input Low Voltage"
    ::= { voltInpEqptHistorical1dayEntry 2 }

voltInpEqptHistorical1dayMean OBJECT-TYPE
    SYNTAX        Unsigned32
    UNITS         "0.001 V"
    MAX-ACCESS    read-only
    STATUS        current
    DESCRIPTION   "PSU Input Mean Voltage"
    ::= { voltInpEqptHistorical1dayEntry 3 }

voltInpEqptHistorical1dayHigh OBJECT-TYPE
    SYNTAX        Unsigned32
    UNITS         "0.001 V"
    MAX-ACCESS    read-only
    STATUS        current
    DESCRIPTION   "PSU Input High Voltage"
    ::= { voltInpEqptHistorical1dayEntry 4 }

voltInpEqptHistorical1dayValidFlag OBJECT-TYPE
    SYNTAX        TruthValue
    MAX-ACCESS    read-only
    STATUS        current
    DESCRIPTION   "Valid Flag"
    ::= { voltInpEqptHistorical1dayEntry 5 }

voltInpEqptHistorical1dayTimeStamp OBJECT-TYPE
    SYNTAX        DateAndTime
    MAX-ACCESS    read-only
    STATUS        current
    DESCRIPTION   "Timestamp"
    ::= { voltInpEqptHistorical1dayEntry 6 }

endOfVoltInpEqptHistorical1dayTable OBJECT-TYPE
    SYNTAX        Integer32
    MAX-ACCESS    read-only
    STATUS        current
    DESCRIPTION   ""
    ::= { pmEqptPhysRecord 16 }

voltInpEqptHistorical1weekTable OBJECT-TYPE
    SYNTAX        SEQUENCE OF VoltInpEqptHistorical1weekEntry
    MAX-ACCESS    not-accessible
    STATUS        current
    DESCRIPTION   ""
    ::= { pmEqptPhysRecord 17 }

voltInpEqptHistorical1weekEntry OBJECT-TYPE
    SYNTAX        VoltInpEqptHistorical1weekEntry
    MAX-ACCESS    not-accessible
    STATUS        current
    DESCRIPTION   ""
    INDEX       {
                  entityEqptShelfNo,
                  entityEqptSlotNo,
                  entityEqptPortNo,
                  entityEqptExtNo,
                  entityEqptClassName,
                  voltInpEqptHistorical1weekNumber
                }
    ::= { voltInpEqptHistorical1weekTable 1 }

VoltInpEqptHistorical1weekEntry ::= SEQUENCE
  {    voltInpEqptHistorical1weekNumber Integer32,
    voltInpEqptHistorical1weekLow Unsigned32,
    voltInpEqptHistorical1weekMean Unsigned32,
    voltInpEqptHistorical1weekHigh Unsigned32,
    voltInpEqptHistorical1weekValidFlag TruthValue,
    voltInpEqptHistorical1weekTimeStamp DateAndTime }

voltInpEqptHistorical1weekNumber OBJECT-TYPE
    SYNTAX        Integer32 (1..52)
    MAX-ACCESS    not-accessible
    STATUS        current
    DESCRIPTION   "Number 1week"
    ::= { voltInpEqptHistorical1weekEntry 1 }

voltInpEqptHistorical1weekLow OBJECT-TYPE
    SYNTAX        Unsigned32
    UNITS         "0.001 V"
    MAX-ACCESS    read-only
    STATUS        current
    DESCRIPTION   "PSU Input Low Voltage"
    ::= { voltInpEqptHistorical1weekEntry 2 }

voltInpEqptHistorical1weekMean OBJECT-TYPE
    SYNTAX        Unsigned32
    UNITS         "0.001 V"
    MAX-ACCESS    read-only
    STATUS        current
    DESCRIPTION   "PSU Input Mean Voltage"
    ::= { voltInpEqptHistorical1weekEntry 3 }

voltInpEqptHistorical1weekHigh OBJECT-TYPE
    SYNTAX        Unsigned32
    UNITS         "0.001 V"
    MAX-ACCESS    read-only
    STATUS        current
    DESCRIPTION   "PSU Input High Voltage"
    ::= { voltInpEqptHistorical1weekEntry 4 }

voltInpEqptHistorical1weekValidFlag OBJECT-TYPE
    SYNTAX        TruthValue
    MAX-ACCESS    read-only
    STATUS        current
    DESCRIPTION   "Valid Flag"
    ::= { voltInpEqptHistorical1weekEntry 5 }

voltInpEqptHistorical1weekTimeStamp OBJECT-TYPE
    SYNTAX        DateAndTime
    MAX-ACCESS    read-only
    STATUS        current
    DESCRIPTION   "Timestamp"
    ::= { voltInpEqptHistorical1weekEntry 6 }

endOfVoltInpEqptHistorical1weekTable OBJECT-TYPE
    SYNTAX        Integer32
    MAX-ACCESS    read-only
    STATUS        current
    DESCRIPTION   ""
    ::= { pmEqptPhysRecord 18 }

endOfPmEqptPhysRecord OBJECT-TYPE
    SYNTAX        Integer32
    MAX-ACCESS    read-only
    STATUS        current
    DESCRIPTION   ""
    ::= { pmEqptPhysRecord 10000 }

frRcv2DcnCurrent15minTable OBJECT-TYPE
    SYNTAX        SEQUENCE OF FrRcv2DcnCurrent15minEntry
    MAX-ACCESS    not-accessible
    STATUS        current
    DESCRIPTION   ""
    ::= { pmDcnDataRecord 1 }

frRcv2DcnCurrent15minEntry OBJECT-TYPE
    SYNTAX        FrRcv2DcnCurrent15minEntry
    MAX-ACCESS    not-accessible
    STATUS        current
    DESCRIPTION   ""
    INDEX       {
                  entityDcnShelfNo,
                  entityDcnSlotNo,
                  entityDcnPortNo,
                  entityDcnExtNo,
                  entityDcnClassName
                }
    ::= { frRcv2DcnCurrent15minTable 1 }

FrRcv2DcnCurrent15minEntry ::= SEQUENCE
  {    frRcv2DcnCurrent15minGoodFrames Counter64String,
    frRcv2DcnCurrent15minPauseFrames Counter64String,
    frRcv2DcnCurrent15minCrcFrames Counter64String,
    frRcv2DcnCurrent15minBytes Counter64String,
    frRcv2DcnCurrent15minElapsedTime Integer32 }

frRcv2DcnCurrent15minGoodFrames OBJECT-TYPE
    SYNTAX        Counter64String
    MAX-ACCESS    read-only
    STATUS        current
    DESCRIPTION   "Frames Received"
    ::= { frRcv2DcnCurrent15minEntry 1 }

frRcv2DcnCurrent15minPauseFrames OBJECT-TYPE
    SYNTAX        Counter64String
    MAX-ACCESS    read-only
    STATUS        current
    DESCRIPTION   "Pause Frames Received"
    ::= { frRcv2DcnCurrent15minEntry 2 }

frRcv2DcnCurrent15minCrcFrames OBJECT-TYPE
    SYNTAX        Counter64String
    MAX-ACCESS    read-only
    STATUS        current
    DESCRIPTION   "Received CRC Errors"
    ::= { frRcv2DcnCurrent15minEntry 3 }

frRcv2DcnCurrent15minBytes OBJECT-TYPE
    SYNTAX        Counter64String
    MAX-ACCESS    read-only
    STATUS        current
    DESCRIPTION   "Bytes Received"
    ::= { frRcv2DcnCurrent15minEntry 4 }

frRcv2DcnCurrent15minElapsedTime OBJECT-TYPE
    SYNTAX        Integer32 (0..9000)
    MAX-ACCESS    read-only
    STATUS        current
    DESCRIPTION   "Elapsed 15Min"
    ::= { frRcv2DcnCurrent15minEntry 5 }

endOfFrRcv2DcnCurrent15minTable OBJECT-TYPE
    SYNTAX        Integer32
    MAX-ACCESS    read-only
    STATUS        current
    DESCRIPTION   ""
    ::= { pmDcnDataRecord 2 }

frRcv2DcnCurrent1dayTable OBJECT-TYPE
    SYNTAX        SEQUENCE OF FrRcv2DcnCurrent1dayEntry
    MAX-ACCESS    not-accessible
    STATUS        current
    DESCRIPTION   ""
    ::= { pmDcnDataRecord 3 }

frRcv2DcnCurrent1dayEntry OBJECT-TYPE
    SYNTAX        FrRcv2DcnCurrent1dayEntry
    MAX-ACCESS    not-accessible
    STATUS        current
    DESCRIPTION   ""
    INDEX       {
                  entityDcnShelfNo,
                  entityDcnSlotNo,
                  entityDcnPortNo,
                  entityDcnExtNo,
                  entityDcnClassName
                }
    ::= { frRcv2DcnCurrent1dayTable 1 }

FrRcv2DcnCurrent1dayEntry ::= SEQUENCE
  {    frRcv2DcnCurrent1dayGoodFrames Counter64String,
    frRcv2DcnCurrent1dayPauseFrames Counter64String,
    frRcv2DcnCurrent1dayCrcFrames Counter64String,
    frRcv2DcnCurrent1dayBytes Counter64String,
    frRcv2DcnCurrent1dayElapsedTime Integer32 }

frRcv2DcnCurrent1dayGoodFrames OBJECT-TYPE
    SYNTAX        Counter64String
    MAX-ACCESS    read-only
    STATUS        current
    DESCRIPTION   "Frames Received"
    ::= { frRcv2DcnCurrent1dayEntry 1 }

frRcv2DcnCurrent1dayPauseFrames OBJECT-TYPE
    SYNTAX        Counter64String
    MAX-ACCESS    read-only
    STATUS        current
    DESCRIPTION   "Pause Frames Received"
    ::= { frRcv2DcnCurrent1dayEntry 2 }

frRcv2DcnCurrent1dayCrcFrames OBJECT-TYPE
    SYNTAX        Counter64String
    MAX-ACCESS    read-only
    STATUS        current
    DESCRIPTION   "Received CRC Errors"
    ::= { frRcv2DcnCurrent1dayEntry 3 }

frRcv2DcnCurrent1dayBytes OBJECT-TYPE
    SYNTAX        Counter64String
    MAX-ACCESS    read-only
    STATUS        current
    DESCRIPTION   "Bytes Received"
    ::= { frRcv2DcnCurrent1dayEntry 4 }

frRcv2DcnCurrent1dayElapsedTime OBJECT-TYPE
    SYNTAX        Integer32 (0..86400)
    MAX-ACCESS    read-only
    STATUS        current
    DESCRIPTION   "Elapsed 1Day"
    ::= { frRcv2DcnCurrent1dayEntry 5 }

endOfFrRcv2DcnCurrent1dayTable OBJECT-TYPE
    SYNTAX        Integer32
    MAX-ACCESS    read-only
    STATUS        current
    DESCRIPTION   ""
    ::= { pmDcnDataRecord 4 }

frRcv2DcnHistorical15minTable OBJECT-TYPE
    SYNTAX        SEQUENCE OF FrRcv2DcnHistorical15minEntry
    MAX-ACCESS    not-accessible
    STATUS        current
    DESCRIPTION   ""
    ::= { pmDcnDataRecord 5 }

frRcv2DcnHistorical15minEntry OBJECT-TYPE
    SYNTAX        FrRcv2DcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  frRcv2DcnHistorical15minNumber
                }
    ::= { frRcv2DcnHistorical15minTable 1 }

FrRcv2DcnHistorical15minEntry ::= SEQUENCE
  {    frRcv2DcnHistorical15minNumber Integer32,
    frRcv2DcnHistorical15minGoodFrames Counter64String,
    frRcv2DcnHistorical15minPauseFrames Counter64String,
    frRcv2DcnHistorical15minCrcFrames Counter64String,
    frRcv2DcnHistorical15minBytes Counter64String,
    frRcv2DcnHistorical15minValidFlag TruthValue,
    frRcv2DcnHistorical15minTimeStamp DateAndTime }

frRcv2DcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frRcv2DcnHistorical15minEntry 1 }

frRcv2DcnHistorical15minGoodFrames OBJECT-TYPE
    SYNTAX        Counter64String
    MAX-ACCESS    read-only
    STATUS        current
    DESCRIPTION   "Frames Received"
    ::= { frRcv2DcnHistorical15minEntry 2 }

frRcv2DcnHistorical15minPauseFrames OBJECT-TYPE
    SYNTAX        Counter64String
    MAX-ACCESS    read-only
    STATUS        current
    DESCRIPTION   "Pause Frames Received"
    ::= { frRcv2DcnHistorical15minEntry 3 }

frRcv2DcnHistorical15minCrcFrames OBJECT-TYPE
    SYNTAX        Counter64String
    MAX-ACCESS    read-only
    STATUS        current
    DESCRIPTION   "Received CRC Errors"
    ::= { frRcv2DcnHistorical15minEntry 4 }

frRcv2DcnHistorical15minBytes OBJECT-TYPE
    SYNTAX        Counter64String
    MAX-ACCESS    read-only
    STATUS        current
    DESCRIPTION   "Bytes Received"
    ::= { frRcv2DcnHistorical15minEntry 5 }

frRcv2DcnHistorical15minValidFlag OBJECT-TYPE
    SYNTAX        TruthValue
    MAX-ACCESS    read-only
    STATUS        current
    DESCRIPTION   "Valid Flag"
    ::= { frRcv2DcnHistorical15minEntry 6 }

frRcv2DcnHistorical15minTimeStamp OBJECT-TYPE
    SYNTAX        DateAndTime
    MAX-ACCESS    read-only
    STATUS        current
    DESCRIPTION   "Timestamp"
    ::= { frRcv2DcnHistorical15minEntry 7 }

endOfFrRcv2DcnHistorical15minTable OBJECT-TYPE
    SYNTAX        Integer32
    MAX-ACCESS    read-only
    STATUS        current
    DESCRIPTION   ""
    ::= { pmDcnDataRecord 6 }

frRcv2DcnHistorical1dayTable OBJECT-TYPE
    SYNTAX        SEQUENCE OF FrRcv2DcnHistorical1dayEntry
    MAX-ACCESS    not-accessible
    STATUS        current
    DESCRIPTION   ""
    ::= { pmDcnDataRecord 7 }

frRcv2DcnHistorical1dayEntry OBJECT-TYPE
    SYNTAX        FrRcv2DcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  frRcv2DcnHistorical1dayNumber
                }
    ::= { frRcv2DcnHistorical1dayTable 1 }

FrRcv2DcnHistorical1dayEntry ::= SEQUENCE
  {    frRcv2DcnHistorical1dayNumber Integer32,
    frRcv2DcnHistorical1dayGoodFrames Counter64String,
    frRcv2DcnHistorical1dayPauseFrames Counter64String,
    frRcv2DcnHistorical1dayCrcFrames Counter64String,
    frRcv2DcnHistorical1dayBytes Counter64String,
    frRcv2DcnHistorical1dayValidFlag TruthValue,
    frRcv2DcnHistorical1dayTimeStamp DateAndTime }

frRcv2DcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frRcv2DcnHistorical1dayEntry 1 }

frRcv2DcnHistorical1dayGoodFrames OBJECT-TYPE
    SYNTAX        Counter64String
    MAX-ACCESS    read-only
    STATUS        current
    DESCRIPTION   "Frames Received"
    ::= { frRcv2DcnHistorical1dayEntry 2 }

frRcv2DcnHistorical1dayPauseFrames OBJECT-TYPE
    SYNTAX        Counter64String
    MAX-ACCESS    read-only
    STATUS        current
    DESCRIPTION   "Pause Frames Received"
    ::= { frRcv2DcnHistorical1dayEntry 3 }

frRcv2DcnHistorical1dayCrcFrames OBJECT-TYPE
    SYNTAX        Counter64String
    MAX-ACCESS    read-only
    STATUS        current
    DESCRIPTION   "Received CRC Errors"
    ::= { frRcv2DcnHistorical1dayEntry 4 }

frRcv2DcnHistorical1dayBytes OBJECT-TYPE
    SYNTAX        Counter64String
    MAX-ACCESS    read-only
    STATUS        current
    DESCRIPTION   "Bytes Received"
    ::= { frRcv2DcnHistorical1dayEntry 5 }

frRcv2DcnHistorical1dayValidFlag OBJECT-TYPE
    SYNTAX        TruthValue
    MAX-ACCESS    read-only
    STATUS        current
    DESCRIPTION   "Valid Flag"
    ::= { frRcv2DcnHistorical1dayEntry 6 }

frRcv2DcnHistorical1dayTimeStamp OBJECT-TYPE
    SYNTAX        DateAndTime
    MAX-ACCESS    read-only
    STATUS        current
    DESCRIPTION   "Timestamp"
    ::= { frRcv2DcnHistorical1dayEntry 7 }

endOfFrRcv2DcnHistorical1dayTable OBJECT-TYPE
    SYNTAX        Integer32
    MAX-ACCESS    read-only
    STATUS        current
    DESCRIPTION   ""
    ::= { pmDcnDataRecord 8 }

macRxDcnCurrent15minTable OBJECT-TYPE
    SYNTAX        SEQUENCE OF MacRxDcnCurrent15minEntry
    MAX-ACCESS    not-accessible
    STATUS        current
    DESCRIPTION   ""
    ::= { pmDcnDataRecord 9 }

macRxDcnCurrent15minEntry OBJECT-TYPE
    SYNTAX        MacRxDcnCurrent15minEntry
    MAX-ACCESS    not-accessible
    STATUS        current
    DESCRIPTION   ""
    INDEX       {
                  entityDcnShelfNo,
                  entityDcnSlotNo,
                  entityDcnPortNo,
                  entityDcnExtNo,
                  entityDcnClassName
                }
    ::= { macRxDcnCurrent15minTable 1 }

MacRxDcnCurrent15minEntry ::= SEQUENCE
  {    macRxDcnCurrent15minGoodFrames Counter64String,
    macRxDcnCurrent15minOctRcv Counter64String,
    macRxDcnCurrent15minBroadcastFramesRcv Counter64String,
    macRxDcnCurrent15minMulticastFramesRcv Counter64String,
    macRxDcnCurrent15minElapsedTime Integer32 }

macRxDcnCurrent15minGoodFrames OBJECT-TYPE
    SYNTAX        Counter64String
    MAX-ACCESS    read-only
    STATUS        current
    DESCRIPTION   "Frames Received"
    ::= { macRxDcnCurrent15minEntry 1 }

macRxDcnCurrent15minOctRcv OBJECT-TYPE
    SYNTAX        Counter64String
    MAX-ACCESS    read-only
    STATUS        current
    DESCRIPTION   "Bytes Received"
    ::= { macRxDcnCurrent15minEntry 2 }

macRxDcnCurrent15minBroadcastFramesRcv OBJECT-TYPE
    SYNTAX        Counter64String
    MAX-ACCESS    read-only
    STATUS        current
    DESCRIPTION   "Broadcast Frames Received"
    ::= { macRxDcnCurrent15minEntry 3 }

macRxDcnCurrent15minMulticastFramesRcv OBJECT-TYPE
    SYNTAX        Counter64String
    MAX-ACCESS    read-only
    STATUS        current
    DESCRIPTION   "Multicast Frames Received"
    ::= { macRxDcnCurrent15minEntry 4 }

macRxDcnCurrent15minElapsedTime OBJECT-TYPE
    SYNTAX        Integer32 (0..9000)
    MAX-ACCESS    read-only
    STATUS        current
    DESCRIPTION   "Elapsed 15Min"
    ::= { macRxDcnCurrent15minEntry 5 }

endOfMacRxDcnCurrent15minTable OBJECT-TYPE
    SYNTAX        Integer32
    MAX-ACCESS    read-only
    STATUS        current
    DESCRIPTION   ""
    ::= { pmDcnDataRecord 10 }

macRxDcnCurrent1dayTable OBJECT-TYPE
    SYNTAX        SEQUENCE OF MacRxDcnCurrent1dayEntry
    MAX-ACCESS    not-accessible
    STATUS        current
    DESCRIPTION   ""
    ::= { pmDcnDataRecord 11 }

macRxDcnCurrent1dayEntry OBJECT-TYPE
    SYNTAX        MacRxDcnCurrent1dayEntry
    MAX-ACCESS    not-accessible
    STATUS        current
    DESCRIPTION   ""
    INDEX       {
                  entityDcnShelfNo,
                  entityDcnSlotNo,
                  entityDcnPortNo,
                  entityDcnExtNo,
                  entityDcnClassName
                }
    ::= { macRxDcnCurrent1dayTable 1 }

MacRxDcnCurrent1dayEntry ::= SEQUENCE
  {    macRxDcnCurrent1dayGoodFrames Counter64String,
    macRxDcnCurrent1dayOctRcv Counter64String,
    macRxDcnCurrent1dayBroadcastFramesRcv Counter64String,
    macRxDcnCurrent1dayMulticastFramesRcv Counter64String,
    macRxDcnCurrent1dayElapsedTime Integer32 }

macRxDcnCurrent1dayGoodFrames OBJECT-TYPE
    SYNTAX        Counter64String
    MAX-ACCESS    read-only
    STATUS        current
    DESCRIPTION   "Frames Received"
    ::= { macRxDcnCurrent1dayEntry 1 }

macRxDcnCurrent1dayOctRcv OBJECT-TYPE
    SYNTAX        Counter64String
    MAX-ACCESS    read-only
    STATUS        current
    DESCRIPTION   "Bytes Received"
    ::= { macRxDcnCurrent1dayEntry 2 }

macRxDcnCurrent1dayBroadcastFramesRcv OBJECT-TYPE
    SYNTAX        Counter64String
    MAX-ACCESS    read-only
    STATUS        current
    DESCRIPTION   "Broadcast Frames Received"
    ::= { macRxDcnCurrent1dayEntry 3 }

macRxDcnCurrent1dayMulticastFramesRcv OBJECT-TYPE
    SYNTAX        Counter64String
    MAX-ACCESS    read-only
    STATUS        current
    DESCRIPTION   "Multicast Frames Received"
    ::= { macRxDcnCurrent1dayEntry 4 }

macRxDcnCurrent1dayElapsedTime OBJECT-TYPE
    SYNTAX        Integer32 (0..86400)
    MAX-ACCESS    read-only
    STATUS        current
    DESCRIPTION   "Elapsed 1Day"
    ::= { macRxDcnCurrent1dayEntry 5 }

endOfMacRxDcnCurrent1dayTable OBJECT-TYPE
    SYNTAX        Integer32
    MAX-ACCESS    read-only
    STATUS        current
    DESCRIPTION   ""
    ::= { pmDcnDataRecord 12 }

macRxDcnHistorical15minTable OBJECT-TYPE
    SYNTAX        SEQUENCE OF MacRxDcnHistorical15minEntry
    MAX-ACCESS    not-accessible
    STATUS        current
    DESCRIPTION   ""
    ::= { pmDcnDataRecord 13 }

macRxDcnHistorical15minEntry OBJECT-TYPE
    SYNTAX        MacRxDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  macRxDcnHistorical15minNumber
                }
    ::= { macRxDcnHistorical15minTable 1 }

MacRxDcnHistorical15minEntry ::= SEQUENCE
  {    macRxDcnHistorical15minNumber Integer32,
    macRxDcnHistorical15minGoodFrames Counter64String,
    macRxDcnHistorical15minOctRcv Counter64String,
    macRxDcnHistorical15minBroadcastFramesRcv Counter64String,
    macRxDcnHistorical15minMulticastFramesRcv Counter64String,
    macRxDcnHistorical15minValidFlag TruthValue,
    macRxDcnHistorical15minTimeStamp DateAndTime }

macRxDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macRxDcnHistorical15minEntry 1 }

macRxDcnHistorical15minGoodFrames OBJECT-TYPE
    SYNTAX        Counter64String
    MAX-ACCESS    read-only
    STATUS        current
    DESCRIPTION   "Frames Received"
    ::= { macRxDcnHistorical15minEntry 2 }

macRxDcnHistorical15minOctRcv OBJECT-TYPE
    SYNTAX        Counter64String
    MAX-ACCESS    read-only
    STATUS        current
    DESCRIPTION   "Bytes Received"
    ::= { macRxDcnHistorical15minEntry 3 }

macRxDcnHistorical15minBroadcastFramesRcv OBJECT-TYPE
    SYNTAX        Counter64String
    MAX-ACCESS    read-only
    STATUS        current
    DESCRIPTION   "Broadcast Frames Received"
    ::= { macRxDcnHistorical15minEntry 4 }

macRxDcnHistorical15minMulticastFramesRcv OBJECT-TYPE
    SYNTAX        Counter64String
    MAX-ACCESS    read-only
    STATUS        current
    DESCRIPTION   "Multicast Frames Received"
    ::= { macRxDcnHistorical15minEntry 5 }

macRxDcnHistorical15minValidFlag OBJECT-TYPE
    SYNTAX        TruthValue
    MAX-ACCESS    read-only
    STATUS        current
    DESCRIPTION   "Valid Flag"
    ::= { macRxDcnHistorical15minEntry 6 }

macRxDcnHistorical15minTimeStamp OBJECT-TYPE
    SYNTAX        DateAndTime
    MAX-ACCESS    read-only
    STATUS        current
    DESCRIPTION   "Timestamp"
    ::= { macRxDcnHistorical15minEntry 7 }

endOfMacRxDcnHistorical15minTable OBJECT-TYPE
    SYNTAX        Integer32
    MAX-ACCESS    read-only
    STATUS        current
    DESCRIPTION   ""
    ::= { pmDcnDataRecord 14 }

macRxDcnHistorical1dayTable OBJECT-TYPE
    SYNTAX        SEQUENCE OF MacRxDcnHistorical1dayEntry
    MAX-ACCESS    not-accessible
    STATUS        current
    DESCRIPTION   ""
    ::= { pmDcnDataRecord 15 }

macRxDcnHistorical1dayEntry OBJECT-TYPE
    SYNTAX        MacRxDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  macRxDcnHistorical1dayNumber
                }
    ::= { macRxDcnHistorical1dayTable 1 }

MacRxDcnHistorical1dayEntry ::= SEQUENCE
  {    macRxDcnHistorical1dayNumber Integer32,
    macRxDcnHistorical1dayGoodFrames Counter64String,
    macRxDcnHistorical1dayOctRcv Counter64String,
    macRxDcnHistorical1dayBroadcastFramesRcv Counter64String,
    macRxDcnHistorical1dayMulticastFramesRcv Counter64String,
    macRxDcnHistorical1dayValidFlag TruthValue,
    macRxDcnHistorical1dayTimeStamp DateAndTime }

macRxDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macRxDcnHistorical1dayEntry 1 }

macRxDcnHistorical1dayGoodFrames OBJECT-TYPE
    SYNTAX        Counter64String
    MAX-ACCESS    read-only
    STATUS        current
    DESCRIPTION   "Frames Received"
    ::= { macRxDcnHistorical1dayEntry 2 }

macRxDcnHistorical1dayOctRcv OBJECT-TYPE
    SYNTAX        Counter64String
    MAX-ACCESS    read-only
    STATUS        current
    DESCRIPTION   "Bytes Received"
    ::= { macRxDcnHistorical1dayEntry 3 }

macRxDcnHistorical1dayBroadcastFramesRcv OBJECT-TYPE
    SYNTAX        Counter64String
    MAX-ACCESS    read-only
    STATUS        current
    DESCRIPTION   "Broadcast Frames Received"
    ::= { macRxDcnHistorical1dayEntry 4 }

macRxDcnHistorical1dayMulticastFramesRcv OBJECT-TYPE
    SYNTAX        Counter64String
    MAX-ACCESS    read-only
    STATUS        current
    DESCRIPTION   "Multicast Frames Received"
    ::= { macRxDcnHistorical1dayEntry 5 }

macRxDcnHistorical1dayValidFlag OBJECT-TYPE
    SYNTAX        TruthValue
    MAX-ACCESS    read-only
    STATUS        current
    DESCRIPTION   "Valid Flag"
    ::= { macRxDcnHistorical1dayEntry 6 }

macRxDcnHistorical1dayTimeStamp OBJECT-TYPE
    SYNTAX        DateAndTime
    MAX-ACCESS    read-only
    STATUS        current
    DESCRIPTION   "Timestamp"
    ::= { macRxDcnHistorical1dayEntry 7 }

endOfMacRxDcnHistorical1dayTable OBJECT-TYPE
    SYNTAX        Integer32
    MAX-ACCESS    read-only
    STATUS        current
    DESCRIPTION   ""
    ::= { pmDcnDataRecord 16 }

macTxDcnCurrent15minTable OBJECT-TYPE
    SYNTAX        SEQUENCE OF MacTxDcnCurrent15minEntry
    MAX-ACCESS    not-accessible
    STATUS        current
    DESCRIPTION   ""
    ::= { pmDcnDataRecord 17 }

macTxDcnCurrent15minEntry OBJECT-TYPE
    SYNTAX        MacTxDcnCurrent15minEntry
    MAX-ACCESS    not-accessible
    STATUS        current
    DESCRIPTION   ""
    INDEX       {
                  entityDcnShelfNo,
                  entityDcnSlotNo,
                  entityDcnPortNo,
                  entityDcnExtNo,
                  entityDcnClassName
                }
    ::= { macTxDcnCurrent15minTable 1 }

MacTxDcnCurrent15minEntry ::= SEQUENCE
  {    macTxDcnCurrent15minFramesTrmt Counter64String,
    macTxDcnCurrent15minBytesTrmt Counter64String,
    macTxDcnCurrent15minBroadcastFramesTrmt Counter64String,
    macTxDcnCurrent15minMulticastFramesTrmt Counter64String,
    macTxDcnCurrent15minDiscardedFramesTrmt Counter64String,
    macTxDcnCurrent15minElapsedTime Integer32 }

macTxDcnCurrent15minFramesTrmt OBJECT-TYPE
    SYNTAX        Counter64String
    MAX-ACCESS    read-only
    STATUS        current
    DESCRIPTION   "Frames Transmitted"
    ::= { macTxDcnCurrent15minEntry 1 }

macTxDcnCurrent15minBytesTrmt OBJECT-TYPE
    SYNTAX        Counter64String
    MAX-ACCESS    read-only
    STATUS        current
    DESCRIPTION   "Bytes Transmitted"
    ::= { macTxDcnCurrent15minEntry 2 }

macTxDcnCurrent15minBroadcastFramesTrmt OBJECT-TYPE
    SYNTAX        Counter64String
    MAX-ACCESS    read-only
    STATUS        current
    DESCRIPTION   "Broadcast Frames Transmitted"
    ::= { macTxDcnCurrent15minEntry 3 }

macTxDcnCurrent15minMulticastFramesTrmt OBJECT-TYPE
    SYNTAX        Counter64String
    MAX-ACCESS    read-only
    STATUS        current
    DESCRIPTION   "Multicast / Broadcast Frames Transmitted"
    ::= { macTxDcnCurrent15minEntry 4 }

macTxDcnCurrent15minDiscardedFramesTrmt OBJECT-TYPE
    SYNTAX        Counter64String
    MAX-ACCESS    read-only
    STATUS        current
    DESCRIPTION   "Transmit Frames Discarded"
    ::= { macTxDcnCurrent15minEntry 5 }

macTxDcnCurrent15minElapsedTime OBJECT-TYPE
    SYNTAX        Integer32 (0..9000)
    MAX-ACCESS    read-only
    STATUS        current
    DESCRIPTION   "Elapsed 15Min"
    ::= { macTxDcnCurrent15minEntry 6 }

endOfMacTxDcnCurrent15minTable OBJECT-TYPE
    SYNTAX        Integer32
    MAX-ACCESS    read-only
    STATUS        current
    DESCRIPTION   ""
    ::= { pmDcnDataRecord 18 }

macTxDcnCurrent1dayTable OBJECT-TYPE
    SYNTAX        SEQUENCE OF MacTxDcnCurrent1dayEntry
    MAX-ACCESS    not-accessible
    STATUS        current
    DESCRIPTION   ""
    ::= { pmDcnDataRecord 19 }

macTxDcnCurrent1dayEntry OBJECT-TYPE
    SYNTAX        MacTxDcnCurrent1dayEntry
    MAX-ACCESS    not-accessible
    STATUS        current
    DESCRIPTION   ""
    INDEX       {
                  entityDcnShelfNo,
                  entityDcnSlotNo,
                  entityDcnPortNo,
                  entityDcnExtNo,
                  entityDcnClassName
                }
    ::= { macTxDcnCurrent1dayTable 1 }

MacTxDcnCurrent1dayEntry ::= SEQUENCE
  {    macTxDcnCurrent1dayFramesTrmt Counter64String,
    macTxDcnCurrent1dayBytesTrmt Counter64String,
    macTxDcnCurrent1dayBroadcastFramesTrmt Counter64String,
    macTxDcnCurrent1dayMulticastFramesTrmt Counter64String,
    macTxDcnCurrent1dayDiscardedFramesTrmt Counter64String,
    macTxDcnCurrent1dayElapsedTime Integer32 }

macTxDcnCurrent1dayFramesTrmt OBJECT-TYPE
    SYNTAX        Counter64String
    MAX-ACCESS    read-only
    STATUS        current
    DESCRIPTION   "Frames Transmitted"
    ::= { macTxDcnCurrent1dayEntry 1 }

macTxDcnCurrent1dayBytesTrmt OBJECT-TYPE
    SYNTAX        Counter64String
    MAX-ACCESS    read-only
    STATUS        current
    DESCRIPTION   "Bytes Transmitted"
    ::= { macTxDcnCurrent1dayEntry 2 }

macTxDcnCurrent1dayBroadcastFramesTrmt OBJECT-TYPE
    SYNTAX        Counter64String
    MAX-ACCESS    read-only
    STATUS        current
    DESCRIPTION   "Broadcast Frames Transmitted"
    ::= { macTxDcnCurrent1dayEntry 3 }

macTxDcnCurrent1dayMulticastFramesTrmt OBJECT-TYPE
    SYNTAX        Counter64String
    MAX-ACCESS    read-only
    STATUS        current
    DESCRIPTION   "Multicast / Broadcast Frames Transmitted"
    ::= { macTxDcnCurrent1dayEntry 4 }

macTxDcnCurrent1dayDiscardedFramesTrmt OBJECT-TYPE
    SYNTAX        Counter64String
    MAX-ACCESS    read-only
    STATUS        current
    DESCRIPTION   "Transmit Frames Discarded"
    ::= { macTxDcnCurrent1dayEntry 5 }

macTxDcnCurrent1dayElapsedTime OBJECT-TYPE
    SYNTAX        Integer32 (0..86400)
    MAX-ACCESS    read-only
    STATUS        current
    DESCRIPTION   "Elapsed 1Day"
    ::= { macTxDcnCurrent1dayEntry 6 }

endOfMacTxDcnCurrent1dayTable OBJECT-TYPE
    SYNTAX        Integer32
    MAX-ACCESS    read-only
    STATUS        current
    DESCRIPTION   ""
    ::= { pmDcnDataRecord 20 }

macTxDcnHistorical15minTable OBJECT-TYPE
    SYNTAX        SEQUENCE OF MacTxDcnHistorical15minEntry
    MAX-ACCESS    not-accessible
    STATUS        current
    DESCRIPTION   ""
    ::= { pmDcnDataRecord 21 }

macTxDcnHistorical15minEntry OBJECT-TYPE
    SYNTAX        MacTxDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  macTxDcnHistorical15minNumber
                }
    ::= { macTxDcnHistorical15minTable 1 }

MacTxDcnHistorical15minEntry ::= SEQUENCE
  {    macTxDcnHistorical15minNumber Integer32,
    macTxDcnHistorical15minFramesTrmt Counter64String,
    macTxDcnHistorical15minBytesTrmt Counter64String,
    macTxDcnHistorical15minBroadcastFramesTrmt Counter64String,
    macTxDcnHistorical15minMulticastFramesTrmt Counter64String,
    macTxDcnHistorical15minDiscardedFramesTrmt Counter64String,
    macTxDcnHistorical15minValidFlag TruthValue,
    macTxDcnHistorical15minTimeStamp DateAndTime }

macTxDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macTxDcnHistorical15minEntry 1 }

macTxDcnHistorical15minFramesTrmt OBJECT-TYPE
    SYNTAX        Counter64String
    MAX-ACCESS    read-only
    STATUS        current
    DESCRIPTION   "Frames Transmitted"
    ::= { macTxDcnHistorical15minEntry 2 }

macTxDcnHistorical15minBytesTrmt OBJECT-TYPE
    SYNTAX        Counter64String
    MAX-ACCESS    read-only
    STATUS        current
    DESCRIPTION   "Bytes Transmitted"
    ::= { macTxDcnHistorical15minEntry 3 }

macTxDcnHistorical15minBroadcastFramesTrmt OBJECT-TYPE
    SYNTAX        Counter64String
    MAX-ACCESS    read-only
    STATUS        current
    DESCRIPTION   "Broadcast Frames Transmitted"
    ::= { macTxDcnHistorical15minEntry 4 }

macTxDcnHistorical15minMulticastFramesTrmt OBJECT-TYPE
    SYNTAX        Counter64String
    MAX-ACCESS    read-only
    STATUS        current
    DESCRIPTION   "Multicast / Broadcast Frames Transmitted"
    ::= { macTxDcnHistorical15minEntry 5 }

macTxDcnHistorical15minDiscardedFramesTrmt OBJECT-TYPE
    SYNTAX        Counter64String
    MAX-ACCESS    read-only
    STATUS        current
    DESCRIPTION   "Transmit Frames Discarded"
    ::= { macTxDcnHistorical15minEntry 6 }

macTxDcnHistorical15minValidFlag OBJECT-TYPE
    SYNTAX        TruthValue
    MAX-ACCESS    read-only
    STATUS        current
    DESCRIPTION   "Valid Flag"
    ::= { macTxDcnHistorical15minEntry 7 }

macTxDcnHistorical15minTimeStamp OBJECT-TYPE
    SYNTAX        DateAndTime
    MAX-ACCESS    read-only
    STATUS        current
    DESCRIPTION   "Timestamp"
    ::= { macTxDcnHistorical15minEntry 8 }

endOfMacTxDcnHistorical15minTable OBJECT-TYPE
    SYNTAX        Integer32
    MAX-ACCESS    read-only
    STATUS        current
    DESCRIPTION   ""
    ::= { pmDcnDataRecord 22 }

macTxDcnHistorical1dayTable OBJECT-TYPE
    SYNTAX        SEQUENCE OF MacTxDcnHistorical1dayEntry
    MAX-ACCESS    not-accessible
    STATUS        current
    DESCRIPTION   ""
    ::= { pmDcnDataRecord 23 }

macTxDcnHistorical1dayEntry OBJECT-TYPE
    SYNTAX        MacTxDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  macTxDcnHistorical1dayNumber
                }
    ::= { macTxDcnHistorical1dayTable 1 }

MacTxDcnHistorical1dayEntry ::= SEQUENCE
  {    macTxDcnHistorical1dayNumber Integer32,
    macTxDcnHistorical1dayFramesTrmt Counter64String,
    macTxDcnHistorical1dayBytesTrmt Counter64String,
    macTxDcnHistorical1dayBroadcastFramesTrmt Counter64String,
    macTxDcnHistorical1dayMulticastFramesTrmt Counter64String,
    macTxDcnHistorical1dayDiscardedFramesTrmt Counter64String,
    macTxDcnHistorical1dayValidFlag TruthValue,
    macTxDcnHistorical1dayTimeStamp DateAndTime }

macTxDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macTxDcnHistorical1dayEntry 1 }

macTxDcnHistorical1dayFramesTrmt OBJECT-TYPE
    SYNTAX        Counter64String
    MAX-ACCESS    read-only
    STATUS        current
    DESCRIPTION   "Frames Transmitted"
    ::= { macTxDcnHistorical1dayEntry 2 }

macTxDcnHistorical1dayBytesTrmt OBJECT-TYPE
    SYNTAX        Counter64String
    MAX-ACCESS    read-only
    STATUS        current
    DESCRIPTION   "Bytes Transmitted"
    ::= { macTxDcnHistorical1dayEntry 3 }

macTxDcnHistorical1dayBroadcastFramesTrmt OBJECT-TYPE
    SYNTAX        Counter64String
    MAX-ACCESS    read-only
    STATUS        current
    DESCRIPTION   "Broadcast Frames Transmitted"
    ::= { macTxDcnHistorical1dayEntry 4 }

macTxDcnHistorical1dayMulticastFramesTrmt OBJECT-TYPE
    SYNTAX        Counter64String
    MAX-ACCESS    read-only
    STATUS        current
    DESCRIPTION   "Multicast / Broadcast Frames Transmitted"
    ::= { macTxDcnHistorical1dayEntry 5 }

macTxDcnHistorical1dayDiscardedFramesTrmt OBJECT-TYPE
    SYNTAX        Counter64String
    MAX-ACCESS    read-only
    STATUS        current
    DESCRIPTION   "Transmit Frames Discarded"
    ::= { macTxDcnHistorical1dayEntry 6 }

macTxDcnHistorical1dayValidFlag OBJECT-TYPE
    SYNTAX        TruthValue
    MAX-ACCESS    read-only
    STATUS        current
    DESCRIPTION   "Valid Flag"
    ::= { macTxDcnHistorical1dayEntry 7 }

macTxDcnHistorical1dayTimeStamp OBJECT-TYPE
    SYNTAX        DateAndTime
    MAX-ACCESS    read-only
    STATUS        current
    DESCRIPTION   "Timestamp"
    ::= { macTxDcnHistorical1dayEntry 8 }

endOfMacTxDcnHistorical1dayTable OBJECT-TYPE
    SYNTAX        Integer32
    MAX-ACCESS    read-only
    STATUS        current
    DESCRIPTION   ""
    ::= { pmDcnDataRecord 24 }

macSzRxDcnCurrent15minTable OBJECT-TYPE
    SYNTAX        SEQUENCE OF MacSzRxDcnCurrent15minEntry
    MAX-ACCESS    not-accessible
    STATUS        current
    DESCRIPTION   ""
    ::= { pmDcnDataRecord 25 }

macSzRxDcnCurrent15minEntry OBJECT-TYPE
    SYNTAX        MacSzRxDcnCurrent15minEntry
    MAX-ACCESS    not-accessible
    STATUS        current
    DESCRIPTION   ""
    INDEX       {
                  entityDcnShelfNo,
                  entityDcnSlotNo,
                  entityDcnPortNo,
                  entityDcnExtNo,
                  entityDcnClassName
                }
    ::= { macSzRxDcnCurrent15minTable 1 }

MacSzRxDcnCurrent15minEntry ::= SEQUENCE
  {    macSzRxDcnCurrent15minBytesFrames64Rcv Counter64String,
    macSzRxDcnCurrent15minBytesFrames65Rcv Counter64String,
    macSzRxDcnCurrent15minBytesFrames128Rcv Counter64String,
    macSzRxDcnCurrent15minBytesFrames256Rcv Counter64String,
    macSzRxDcnCurrent15minBytesFrames512Rcv Counter64String,
    macSzRxDcnCurrent15minBytesFrames1024Rcv Counter64String,
    macSzRxDcnCurrent15minBytesFrames1519Rcv Counter64String,
    macSzRxDcnCurrent15minElapsedTime Integer32 }

macSzRxDcnCurrent15minBytesFrames64Rcv OBJECT-TYPE
    SYNTAX        Counter64String
    MAX-ACCESS    read-only
    STATUS        current
    DESCRIPTION   "64 Byte Frames Received"
    ::= { macSzRxDcnCurrent15minEntry 1 }

macSzRxDcnCurrent15minBytesFrames65Rcv OBJECT-TYPE
    SYNTAX        Counter64String
    MAX-ACCESS    read-only
    STATUS        current
    DESCRIPTION   "65-127 Byte Frames Received"
    ::= { macSzRxDcnCurrent15minEntry 2 }

macSzRxDcnCurrent15minBytesFrames128Rcv OBJECT-TYPE
    SYNTAX        Counter64String
    MAX-ACCESS    read-only
    STATUS        current
    DESCRIPTION   "128-255 Byte Frames Received"
    ::= { macSzRxDcnCurrent15minEntry 3 }

macSzRxDcnCurrent15minBytesFrames256Rcv OBJECT-TYPE
    SYNTAX        Counter64String
    MAX-ACCESS    read-only
    STATUS        current
    DESCRIPTION   "256-511 Byte Frames Received"
    ::= { macSzRxDcnCurrent15minEntry 4 }

macSzRxDcnCurrent15minBytesFrames512Rcv OBJECT-TYPE
    SYNTAX        Counter64String
    MAX-ACCESS    read-only
    STATUS        current
    DESCRIPTION   "512-1023 Byte Frames Received"
    ::= { macSzRxDcnCurrent15minEntry 5 }

macSzRxDcnCurrent15minBytesFrames1024Rcv OBJECT-TYPE
    SYNTAX        Counter64String
    MAX-ACCESS    read-only
    STATUS        current
    DESCRIPTION   "1024-1518 Byte Frames Received"
    ::= { macSzRxDcnCurrent15minEntry 6 }

macSzRxDcnCurrent15minBytesFrames1519Rcv OBJECT-TYPE
    SYNTAX        Counter64String
    MAX-ACCESS    read-only
    STATUS        current
    DESCRIPTION   "1519-Max Byte Frames Received"
    ::= { macSzRxDcnCurrent15minEntry 7 }

macSzRxDcnCurrent15minElapsedTime OBJECT-TYPE
    SYNTAX        Integer32 (0..9000)
    MAX-ACCESS    read-only
    STATUS        current
    DESCRIPTION   "Elapsed 15Min"
    ::= { macSzRxDcnCurrent15minEntry 8 }

endOfMacSzRxDcnCurrent15minTable OBJECT-TYPE
    SYNTAX        Integer32
    MAX-ACCESS    read-only
    STATUS        current
    DESCRIPTION   ""
    ::= { pmDcnDataRecord 26 }

macSzRxDcnCurrent1dayTable OBJECT-TYPE
    SYNTAX        SEQUENCE OF MacSzRxDcnCurrent1dayEntry
    MAX-ACCESS    not-accessible
    STATUS        current
    DESCRIPTION   ""
    ::= { pmDcnDataRecord 27 }

macSzRxDcnCurrent1dayEntry OBJECT-TYPE
    SYNTAX        MacSzRxDcnCurrent1dayEntry
    MAX-ACCESS    not-accessible
    STATUS        current
    DESCRIPTION   ""
    INDEX       {
                  entityDcnShelfNo,
                  entityDcnSlotNo,
                  entityDcnPortNo,
                  entityDcnExtNo,
                  entityDcnClassName
                }
    ::= { macSzRxDcnCurrent1dayTable 1 }

MacSzRxDcnCurrent1dayEntry ::= SEQUENCE
  {    macSzRxDcnCurrent1dayBytesFrames64Rcv Counter64String,
    macSzRxDcnCurrent1dayBytesFrames65Rcv Counter64String,
    macSzRxDcnCurrent1dayBytesFrames128Rcv Counter64String,
    macSzRxDcnCurrent1dayBytesFrames256Rcv Counter64String,
    macSzRxDcnCurrent1dayBytesFrames512Rcv Counter64String,
    macSzRxDcnCurrent1dayBytesFrames1024Rcv Counter64String,
    macSzRxDcnCurrent1dayBytesFrames1519Rcv Counter64String,
    macSzRxDcnCurrent1dayElapsedTime Integer32 }

macSzRxDcnCurrent1dayBytesFrames64Rcv OBJECT-TYPE
    SYNTAX        Counter64String
    MAX-ACCESS    read-only
    STATUS        current
    DESCRIPTION   "64 Byte Frames Received"
    ::= { macSzRxDcnCurrent1dayEntry 1 }

macSzRxDcnCurrent1dayBytesFrames65Rcv OBJECT-TYPE
    SYNTAX        Counter64String
    MAX-ACCESS    read-only
    STATUS        current
    DESCRIPTION   "65-127 Byte Frames Received"
    ::= { macSzRxDcnCurrent1dayEntry 2 }

macSzRxDcnCurrent1dayBytesFrames128Rcv OBJECT-TYPE
    SYNTAX        Counter64String
    MAX-ACCESS    read-only
    STATUS        current
    DESCRIPTION   "128-255 Byte Frames Received"
    ::= { macSzRxDcnCurrent1dayEntry 3 }

macSzRxDcnCurrent1dayBytesFrames256Rcv OBJECT-TYPE
    SYNTAX        Counter64String
    MAX-ACCESS    read-only
    STATUS        current
    DESCRIPTION   "256-511 Byte Frames Received"
    ::= { macSzRxDcnCurrent1dayEntry 4 }

macSzRxDcnCurrent1dayBytesFrames512Rcv OBJECT-TYPE
    SYNTAX        Counter64String
    MAX-ACCESS    read-only
    STATUS        current
    DESCRIPTION   "512-1023 Byte Frames Received"
    ::= { macSzRxDcnCurrent1dayEntry 5 }

macSzRxDcnCurrent1dayBytesFrames1024Rcv OBJECT-TYPE
    SYNTAX        Counter64String
    MAX-ACCESS    read-only
    STATUS        current
    DESCRIPTION   "1024-1518 Byte Frames Received"
    ::= { macSzRxDcnCurrent1dayEntry 6 }

macSzRxDcnCurrent1dayBytesFrames1519Rcv OBJECT-TYPE
    SYNTAX        Counter64String
    MAX-ACCESS    read-only
    STATUS        current
    DESCRIPTION   "1519-Max Byte Frames Received"
    ::= { macSzRxDcnCurrent1dayEntry 7 }

macSzRxDcnCurrent1dayElapsedTime OBJECT-TYPE
    SYNTAX        Integer32 (0..86400)
    MAX-ACCESS    read-only
    STATUS        current
    DESCRIPTION   "Elapsed 1Day"
    ::= { macSzRxDcnCurrent1dayEntry 8 }

endOfMacSzRxDcnCurrent1dayTable OBJECT-TYPE
    SYNTAX        Integer32
    MAX-ACCESS    read-only
    STATUS        current
    DESCRIPTION   ""
    ::= { pmDcnDataRecord 28 }

macSzRxDcnHistorical15minTable OBJECT-TYPE
    SYNTAX        SEQUENCE OF MacSzRxDcnHistorical15minEntry
    MAX-ACCESS    not-accessible
    STATUS        current
    DESCRIPTION   ""
    ::= { pmDcnDataRecord 29 }

macSzRxDcnHistorical15minEntry OBJECT-TYPE
    SYNTAX        MacSzRxDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  macSzRxDcnHistorical15minNumber
                }
    ::= { macSzRxDcnHistorical15minTable 1 }

MacSzRxDcnHistorical15minEntry ::= SEQUENCE
  {    macSzRxDcnHistorical15minNumber Integer32,
    macSzRxDcnHistorical15minBytesFrames64Rcv Counter64String,
    macSzRxDcnHistorical15minBytesFrames65Rcv Counter64String,
    macSzRxDcnHistorical15minBytesFrames128Rcv Counter64String,
    macSzRxDcnHistorical15minBytesFrames256Rcv Counter64String,
    macSzRxDcnHistorical15minBytesFrames512Rcv Counter64String,
    macSzRxDcnHistorical15minBytesFrames1024Rcv Counter64String,
    macSzRxDcnHistorical15minBytesFrames1519Rcv Counter64String,
    macSzRxDcnHistorical15minValidFlag TruthValue,
    macSzRxDcnHistorical15minTimeStamp DateAndTime }

macSzRxDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macSzRxDcnHistorical15minEntry 1 }

macSzRxDcnHistorical15minBytesFrames64Rcv OBJECT-TYPE
    SYNTAX        Counter64String
    MAX-ACCESS    read-only
    STATUS        current
    DESCRIPTION   "64 Byte Frames Received"
    ::= { macSzRxDcnHistorical15minEntry 2 }

macSzRxDcnHistorical15minBytesFrames65Rcv OBJECT-TYPE
    SYNTAX        Counter64String
    MAX-ACCESS    read-only
    STATUS        current
    DESCRIPTION   "65-127 Byte Frames Received"
    ::= { macSzRxDcnHistorical15minEntry 3 }

macSzRxDcnHistorical15minBytesFrames128Rcv OBJECT-TYPE
    SYNTAX        Counter64String
    MAX-ACCESS    read-only
    STATUS        current
    DESCRIPTION   "128-255 Byte Frames Received"
    ::= { macSzRxDcnHistorical15minEntry 4 }

macSzRxDcnHistorical15minBytesFrames256Rcv OBJECT-TYPE
    SYNTAX        Counter64String
    MAX-ACCESS    read-only
    STATUS        current
    DESCRIPTION   "256-511 Byte Frames Received"
    ::= { macSzRxDcnHistorical15minEntry 5 }

macSzRxDcnHistorical15minBytesFrames512Rcv OBJECT-TYPE
    SYNTAX        Counter64String
    MAX-ACCESS    read-only
    STATUS        current
    DESCRIPTION   "512-1023 Byte Frames Received"
    ::= { macSzRxDcnHistorical15minEntry 6 }

macSzRxDcnHistorical15minBytesFrames1024Rcv OBJECT-TYPE
    SYNTAX        Counter64String
    MAX-ACCESS    read-only
    STATUS        current
    DESCRIPTION   "1024-1518 Byte Frames Received"
    ::= { macSzRxDcnHistorical15minEntry 7 }

macSzRxDcnHistorical15minBytesFrames1519Rcv OBJECT-TYPE
    SYNTAX        Counter64String
    MAX-ACCESS    read-only
    STATUS        current
    DESCRIPTION   "1519-Max Byte Frames Received"
    ::= { macSzRxDcnHistorical15minEntry 8 }

macSzRxDcnHistorical15minValidFlag OBJECT-TYPE
    SYNTAX        TruthValue
    MAX-ACCESS    read-only
    STATUS        current
    DESCRIPTION   "Valid Flag"
    ::= { macSzRxDcnHistorical15minEntry 9 }

macSzRxDcnHistorical15minTimeStamp OBJECT-TYPE
    SYNTAX        DateAndTime
    MAX-ACCESS    read-only
    STATUS        current
    DESCRIPTION   "Timestamp"
    ::= { macSzRxDcnHistorical15minEntry 10 }

endOfMacSzRxDcnHistorical15minTable OBJECT-TYPE
    SYNTAX        Integer32
    MAX-ACCESS    read-only
    STATUS        current
    DESCRIPTION   ""
    ::= { pmDcnDataRecord 30 }

macSzRxDcnHistorical1dayTable OBJECT-TYPE
    SYNTAX        SEQUENCE OF MacSzRxDcnHistorical1dayEntry
    MAX-ACCESS    not-accessible
    STATUS        current
    DESCRIPTION   ""
    ::= { pmDcnDataRecord 31 }

macSzRxDcnHistorical1dayEntry OBJECT-TYPE
    SYNTAX        MacSzRxDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  macSzRxDcnHistorical1dayNumber
                }
    ::= { macSzRxDcnHistorical1dayTable 1 }

MacSzRxDcnHistorical1dayEntry ::= SEQUENCE
  {    macSzRxDcnHistorical1dayNumber Integer32,
    macSzRxDcnHistorical1dayBytesFrames64Rcv Counter64String,
    macSzRxDcnHistorical1dayBytesFrames65Rcv Counter64String,
    macSzRxDcnHistorical1dayBytesFrames128Rcv Counter64String,
    macSzRxDcnHistorical1dayBytesFrames256Rcv Counter64String,
    macSzRxDcnHistorical1dayBytesFrames512Rcv Counter64String,
    macSzRxDcnHistorical1dayBytesFrames1024Rcv Counter64String,
    macSzRxDcnHistorical1dayBytesFrames1519Rcv Counter64String,
    macSzRxDcnHistorical1dayValidFlag TruthValue,
    macSzRxDcnHistorical1dayTimeStamp DateAndTime }

macSzRxDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macSzRxDcnHistorical1dayEntry 1 }

macSzRxDcnHistorical1dayBytesFrames64Rcv OBJECT-TYPE
    SYNTAX        Counter64String
    MAX-ACCESS    read-only
    STATUS        current
    DESCRIPTION   "64 Byte Frames Received"
    ::= { macSzRxDcnHistorical1dayEntry 2 }

macSzRxDcnHistorical1dayBytesFrames65Rcv OBJECT-TYPE
    SYNTAX        Counter64String
    MAX-ACCESS    read-only
    STATUS        current
    DESCRIPTION   "65-127 Byte Frames Received"
    ::= { macSzRxDcnHistorical1dayEntry 3 }

macSzRxDcnHistorical1dayBytesFrames128Rcv OBJECT-TYPE
    SYNTAX        Counter64String
    MAX-ACCESS    read-only
    STATUS        current
    DESCRIPTION   "128-255 Byte Frames Received"
    ::= { macSzRxDcnHistorical1dayEntry 4 }

macSzRxDcnHistorical1dayBytesFrames256Rcv OBJECT-TYPE
    SYNTAX        Counter64String
    MAX-ACCESS    read-only
    STATUS        current
    DESCRIPTION   "256-511 Byte Frames Received"
    ::= { macSzRxDcnHistorical1dayEntry 5 }

macSzRxDcnHistorical1dayBytesFrames512Rcv OBJECT-TYPE
    SYNTAX        Counter64String
    MAX-ACCESS    read-only
    STATUS        current
    DESCRIPTION   "512-1023 Byte Frames Received"
    ::= { macSzRxDcnHistorical1dayEntry 6 }

macSzRxDcnHistorical1dayBytesFrames1024Rcv OBJECT-TYPE
    SYNTAX        Counter64String
    MAX-ACCESS    read-only
    STATUS        current
    DESCRIPTION   "1024-1518 Byte Frames Received"
    ::= { macSzRxDcnHistorical1dayEntry 7 }

macSzRxDcnHistorical1dayBytesFrames1519Rcv OBJECT-TYPE
    SYNTAX        Counter64String
    MAX-ACCESS    read-only
    STATUS        current
    DESCRIPTION   "1519-Max Byte Frames Received"
    ::= { macSzRxDcnHistorical1dayEntry 8 }

macSzRxDcnHistorical1dayValidFlag OBJECT-TYPE
    SYNTAX        TruthValue
    MAX-ACCESS    read-only
    STATUS        current
    DESCRIPTION   "Valid Flag"
    ::= { macSzRxDcnHistorical1dayEntry 9 }

macSzRxDcnHistorical1dayTimeStamp OBJECT-TYPE
    SYNTAX        DateAndTime
    MAX-ACCESS    read-only
    STATUS        current
    DESCRIPTION   "Timestamp"
    ::= { macSzRxDcnHistorical1dayEntry 10 }

endOfMacSzRxDcnHistorical1dayTable OBJECT-TYPE
    SYNTAX        Integer32
    MAX-ACCESS    read-only
    STATUS        current
    DESCRIPTION   ""
    ::= { pmDcnDataRecord 32 }

macErrRxDcnCurrent15minTable OBJECT-TYPE
    SYNTAX        SEQUENCE OF MacErrRxDcnCurrent15minEntry
    MAX-ACCESS    not-accessible
    STATUS        current
    DESCRIPTION   ""
    ::= { pmDcnDataRecord 33 }

macErrRxDcnCurrent15minEntry OBJECT-TYPE
    SYNTAX        MacErrRxDcnCurrent15minEntry
    MAX-ACCESS    not-accessible
    STATUS        current
    DESCRIPTION   ""
    INDEX       {
                  entityDcnShelfNo,
                  entityDcnSlotNo,
                  entityDcnPortNo,
                  entityDcnExtNo,
                  entityDcnClassName
                }
    ::= { macErrRxDcnCurrent15minTable 1 }

MacErrRxDcnCurrent15minEntry ::= SEQUENCE
  {    macErrRxDcnCurrent15minCrcErrorsRcv Counter64String,
    macErrRxDcnCurrent15minOversizedFramesRcv Counter64String,
    macErrRxDcnCurrent15minUndersizedFramesRcv Counter64String,
    macErrRxDcnCurrent15minElapsedTime Integer32 }

macErrRxDcnCurrent15minCrcErrorsRcv OBJECT-TYPE
    SYNTAX        Counter64String
    MAX-ACCESS    read-only
    STATUS        current
    DESCRIPTION   "Received CRC Errors"
    ::= { macErrRxDcnCurrent15minEntry 1 }

macErrRxDcnCurrent15minOversizedFramesRcv OBJECT-TYPE
    SYNTAX        Counter64String
    MAX-ACCESS    read-only
    STATUS        current
    DESCRIPTION   "Oversized Frames Received"
    ::= { macErrRxDcnCurrent15minEntry 2 }

macErrRxDcnCurrent15minUndersizedFramesRcv OBJECT-TYPE
    SYNTAX        Counter64String
    MAX-ACCESS    read-only
    STATUS        current
    DESCRIPTION   "Undersized Frames Received"
    ::= { macErrRxDcnCurrent15minEntry 3 }

macErrRxDcnCurrent15minElapsedTime OBJECT-TYPE
    SYNTAX        Integer32 (0..9000)
    MAX-ACCESS    read-only
    STATUS        current
    DESCRIPTION   "Elapsed 15Min"
    ::= { macErrRxDcnCurrent15minEntry 4 }

endOfMacErrRxDcnCurrent15minTable OBJECT-TYPE
    SYNTAX        Integer32
    MAX-ACCESS    read-only
    STATUS        current
    DESCRIPTION   ""
    ::= { pmDcnDataRecord 34 }

macErrRxDcnCurrent1dayTable OBJECT-TYPE
    SYNTAX        SEQUENCE OF MacErrRxDcnCurrent1dayEntry
    MAX-ACCESS    not-accessible
    STATUS        current
    DESCRIPTION   ""
    ::= { pmDcnDataRecord 35 }

macErrRxDcnCurrent1dayEntry OBJECT-TYPE
    SYNTAX        MacErrRxDcnCurrent1dayEntry
    MAX-ACCESS    not-accessible
    STATUS        current
    DESCRIPTION   ""
    INDEX       {
                  entityDcnShelfNo,
                  entityDcnSlotNo,
                  entityDcnPortNo,
                  entityDcnExtNo,
                  entityDcnClassName
                }
    ::= { macErrRxDcnCurrent1dayTable 1 }

MacErrRxDcnCurrent1dayEntry ::= SEQUENCE
  {    macErrRxDcnCurrent1dayCrcErrorsRcv Counter64String,
    macErrRxDcnCurrent1dayOversizedFramesRcv Counter64String,
    macErrRxDcnCurrent1dayUndersizedFramesRcv Counter64String,
    macErrRxDcnCurrent1dayElapsedTime Integer32 }

macErrRxDcnCurrent1dayCrcErrorsRcv OBJECT-TYPE
    SYNTAX        Counter64String
    MAX-ACCESS    read-only
    STATUS        current
    DESCRIPTION   "Received CRC Errors"
    ::= { macErrRxDcnCurrent1dayEntry 1 }

macErrRxDcnCurrent1dayOversizedFramesRcv OBJECT-TYPE
    SYNTAX        Counter64String
    MAX-ACCESS    read-only
    STATUS        current
    DESCRIPTION   "Oversized Frames Received"
    ::= { macErrRxDcnCurrent1dayEntry 2 }

macErrRxDcnCurrent1dayUndersizedFramesRcv OBJECT-TYPE
    SYNTAX        Counter64String
    MAX-ACCESS    read-only
    STATUS        current
    DESCRIPTION   "Undersized Frames Received"
    ::= { macErrRxDcnCurrent1dayEntry 3 }

macErrRxDcnCurrent1dayElapsedTime OBJECT-TYPE
    SYNTAX        Integer32 (0..86400)
    MAX-ACCESS    read-only
    STATUS        current
    DESCRIPTION   "Elapsed 1Day"
    ::= { macErrRxDcnCurrent1dayEntry 4 }

endOfMacErrRxDcnCurrent1dayTable OBJECT-TYPE
    SYNTAX        Integer32
    MAX-ACCESS    read-only
    STATUS        current
    DESCRIPTION   ""
    ::= { pmDcnDataRecord 36 }

macErrRxDcnHistorical15minTable OBJECT-TYPE
    SYNTAX        SEQUENCE OF MacErrRxDcnHistorical15minEntry
    MAX-ACCESS    not-accessible
    STATUS        current
    DESCRIPTION   ""
    ::= { pmDcnDataRecord 37 }

macErrRxDcnHistorical15minEntry OBJECT-TYPE
    SYNTAX        MacErrRxDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  macErrRxDcnHistorical15minNumber
                }
    ::= { macErrRxDcnHistorical15minTable 1 }

MacErrRxDcnHistorical15minEntry ::= SEQUENCE
  {    macErrRxDcnHistorical15minNumber Integer32,
    macErrRxDcnHistorical15minCrcErrorsRcv Counter64String,
    macErrRxDcnHistorical15minOversizedFramesRcv Counter64String,
    macErrRxDcnHistorical15minUndersizedFramesRcv Counter64String,
    macErrRxDcnHistorical15minValidFlag TruthValue,
    macErrRxDcnHistorical15minTimeStamp DateAndTime }

macErrRxDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macErrRxDcnHistorical15minEntry 1 }

macErrRxDcnHistorical15minCrcErrorsRcv OBJECT-TYPE
    SYNTAX        Counter64String
    MAX-ACCESS    read-only
    STATUS        current
    DESCRIPTION   "Received CRC Errors"
    ::= { macErrRxDcnHistorical15minEntry 2 }

macErrRxDcnHistorical15minOversizedFramesRcv OBJECT-TYPE
    SYNTAX        Counter64String
    MAX-ACCESS    read-only
    STATUS        current
    DESCRIPTION   "Oversized Frames Received"
    ::= { macErrRxDcnHistorical15minEntry 3 }

macErrRxDcnHistorical15minUndersizedFramesRcv OBJECT-TYPE
    SYNTAX        Counter64String
    MAX-ACCESS    read-only
    STATUS        current
    DESCRIPTION   "Undersized Frames Received"
    ::= { macErrRxDcnHistorical15minEntry 4 }

macErrRxDcnHistorical15minValidFlag OBJECT-TYPE
    SYNTAX        TruthValue
    MAX-ACCESS    read-only
    STATUS        current
    DESCRIPTION   "Valid Flag"
    ::= { macErrRxDcnHistorical15minEntry 5 }

macErrRxDcnHistorical15minTimeStamp OBJECT-TYPE
    SYNTAX        DateAndTime
    MAX-ACCESS    read-only
    STATUS        current
    DESCRIPTION   "Timestamp"
    ::= { macErrRxDcnHistorical15minEntry 6 }

endOfMacErrRxDcnHistorical15minTable OBJECT-TYPE
    SYNTAX        Integer32
    MAX-ACCESS    read-only
    STATUS        current
    DESCRIPTION   ""
    ::= { pmDcnDataRecord 38 }

macErrRxDcnHistorical1dayTable OBJECT-TYPE
    SYNTAX        SEQUENCE OF MacErrRxDcnHistorical1dayEntry
    MAX-ACCESS    not-accessible
    STATUS        current
    DESCRIPTION   ""
    ::= { pmDcnDataRecord 39 }

macErrRxDcnHistorical1dayEntry OBJECT-TYPE
    SYNTAX        MacErrRxDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  macErrRxDcnHistorical1dayNumber
                }
    ::= { macErrRxDcnHistorical1dayTable 1 }

MacErrRxDcnHistorical1dayEntry ::= SEQUENCE
  {    macErrRxDcnHistorical1dayNumber Integer32,
    macErrRxDcnHistorical1dayCrcErrorsRcv Counter64String,
    macErrRxDcnHistorical1dayOversizedFramesRcv Counter64String,
    macErrRxDcnHistorical1dayUndersizedFramesRcv Counter64String,
    macErrRxDcnHistorical1dayValidFlag TruthValue,
    macErrRxDcnHistorical1dayTimeStamp DateAndTime }

macErrRxDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macErrRxDcnHistorical1dayEntry 1 }

macErrRxDcnHistorical1dayCrcErrorsRcv OBJECT-TYPE
    SYNTAX        Counter64String
    MAX-ACCESS    read-only
    STATUS        current
    DESCRIPTION   "Received CRC Errors"
    ::= { macErrRxDcnHistorical1dayEntry 2 }

macErrRxDcnHistorical1dayOversizedFramesRcv OBJECT-TYPE
    SYNTAX        Counter64String
    MAX-ACCESS    read-only
    STATUS        current
    DESCRIPTION   "Oversized Frames Received"
    ::= { macErrRxDcnHistorical1dayEntry 3 }

macErrRxDcnHistorical1dayUndersizedFramesRcv OBJECT-TYPE
    SYNTAX        Counter64String
    MAX-ACCESS    read-only
    STATUS        current
    DESCRIPTION   "Undersized Frames Received"
    ::= { macErrRxDcnHistorical1dayEntry 4 }

macErrRxDcnHistorical1dayValidFlag OBJECT-TYPE
    SYNTAX        TruthValue
    MAX-ACCESS    read-only
    STATUS        current
    DESCRIPTION   "Valid Flag"
    ::= { macErrRxDcnHistorical1dayEntry 5 }

macErrRxDcnHistorical1dayTimeStamp OBJECT-TYPE
    SYNTAX        DateAndTime
    MAX-ACCESS    read-only
    STATUS        current
    DESCRIPTION   "Timestamp"
    ::= { macErrRxDcnHistorical1dayEntry 6 }

endOfMacErrRxDcnHistorical1dayTable OBJECT-TYPE
    SYNTAX        Integer32
    MAX-ACCESS    read-only
    STATUS        current
    DESCRIPTION   ""
    ::= { pmDcnDataRecord 40 }

dcnPhysInstValueTable OBJECT-TYPE
    SYNTAX        SEQUENCE OF DcnPhysInstValueEntry
    MAX-ACCESS    not-accessible
    STATUS        current
    DESCRIPTION   ""
    ::= { pmDcnPhysValue 1 }

dcnPhysInstValueEntry OBJECT-TYPE
    SYNTAX        DcnPhysInstValueEntry
    MAX-ACCESS    not-accessible
    STATUS        current
    DESCRIPTION   ""
    INDEX       {
                  entityDcnShelfNo,
                  entityDcnSlotNo,
                  entityDcnPortNo,
                  entityDcnExtNo,
                  entityDcnClassName
                }
    ::= { dcnPhysInstValueTable 1 }

DcnPhysInstValueEntry ::= SEQUENCE
  {    dcnPhysInstValuelbcn Unsigned32,
    dcnPhysInstValueOpt Integer32,
    dcnPhysInstValueOpr Integer32,
    dcnPhysInstValueAtRcv Integer32,
    dcnPhysInstValueAttRmt Integer32,
    dcnPhysInstValuelbcl Unsigned32,
    dcnPhysInstValueFiberLength Unsigned32 }

dcnPhysInstValuelbcn OBJECT-TYPE
    SYNTAX        Unsigned32
    UNITS         "%"
    MAX-ACCESS    read-only
    STATUS        current
    DESCRIPTION   "Instantaneous Laser Bias Current Normalized"
    ::= { dcnPhysInstValueEntry 1 }

dcnPhysInstValueOpt OBJECT-TYPE
    SYNTAX        Integer32
    UNITS         "0.1 dBm"
    MAX-ACCESS    read-only
    STATUS        current
    DESCRIPTION   "Instantaneous Optical Power Transmitted (Output)"
    ::= { dcnPhysInstValueEntry 2 }

dcnPhysInstValueOpr OBJECT-TYPE
    SYNTAX        Integer32
    UNITS         "0.1 dBm"
    MAX-ACCESS    read-only
    STATUS        current
    DESCRIPTION   "Total Optical Input Power Received"
    ::= { dcnPhysInstValueEntry 3 }

dcnPhysInstValueAtRcv OBJECT-TYPE
    SYNTAX        Integer32
    UNITS         "0.1 dB"
    MAX-ACCESS    read-only
    STATUS        current
    DESCRIPTION   "Attenuation of Receive Fiber"
    ::= { dcnPhysInstValueEntry 4 }

dcnPhysInstValueAttRmt OBJECT-TYPE
    SYNTAX        Integer32
    UNITS         "0.1 dB"
    MAX-ACCESS    read-only
    STATUS        current
    DESCRIPTION   "Attenuation of Transmit Fiber"
    ::= { dcnPhysInstValueEntry 5 }

dcnPhysInstValuelbcl OBJECT-TYPE
    SYNTAX        Unsigned32
    UNITS         "0.001 A"
    MAX-ACCESS    read-only
    STATUS        current
    DESCRIPTION   "Laser Bias Current Level on demand"
    ::= { dcnPhysInstValueEntry 6 }

dcnPhysInstValueFiberLength OBJECT-TYPE
    SYNTAX        Unsigned32 (0..10000)
    UNITS         "km"
    MAX-ACCESS    read-only
    STATUS        current
    DESCRIPTION   "Fiber length between 2 remote NEs"
    ::= { dcnPhysInstValueEntry 7 }

endOfDcnPhysInstValueTable OBJECT-TYPE
    SYNTAX        Integer32
    MAX-ACCESS    read-only
    STATUS        current
    DESCRIPTION   ""
    ::= { pmDcnPhysValue 2 }

endOfPmDcnPhysValue OBJECT-TYPE
    SYNTAX        Integer32
    MAX-ACCESS    read-only
    STATUS        current
    DESCRIPTION   ""
    ::= { pmDcnPhysValue 10000 }

dcnPhysThresholdTable OBJECT-TYPE
    SYNTAX        SEQUENCE OF DcnPhysThresholdEntry
    MAX-ACCESS    not-accessible
    STATUS        current
    DESCRIPTION   ""
    ::= { pmDcnPhysThreshold 1 }

dcnPhysThresholdEntry OBJECT-TYPE
    SYNTAX        DcnPhysThresholdEntry
    MAX-ACCESS    not-accessible
    STATUS        current
    DESCRIPTION   ""
    INDEX       {
                  entityDcnShelfNo,
                  entityDcnSlotNo,
                  entityDcnPortNo,
                  entityDcnExtNo,
                  entityDcnClassName
                }
    ::= { dcnPhysThresholdTable 1 }

DcnPhysThresholdEntry ::= SEQUENCE
  {    dcnPhysThresholdOprLow Integer32,
    dcnPhysThresholdOprHigh Integer32,
    dcnPhysThresholdOptLow Integer32,
    dcnPhysThresholdOptHigh Integer32,
    dcnPhysThresholdAttRcvLow Integer32,
    dcnPhysThresholdAttRcvHigh Integer32 }

dcnPhysThresholdOprLow OBJECT-TYPE
    SYNTAX        Integer32 (-450..260)
    UNITS         "0.1 dBm"
    MAX-ACCESS    read-write
    STATUS        current
    DESCRIPTION   "Optical Input Power Received"
    ::= { dcnPhysThresholdEntry 1 }

dcnPhysThresholdOprHigh OBJECT-TYPE
    SYNTAX        Integer32 (-450..270)
    UNITS         "0.1 dBm"
    MAX-ACCESS    read-write
    STATUS        current
    DESCRIPTION   "Optical Input Power Received"
    ::= { dcnPhysThresholdEntry 2 }

dcnPhysThresholdOptLow OBJECT-TYPE
    SYNTAX        Integer32
    UNITS         "0.1 dBm"
    MAX-ACCESS    read-only
    STATUS        current
    DESCRIPTION   "Low fixed threshold of the Optical Power Transmitted (output)"
    ::= { dcnPhysThresholdEntry 3 }

dcnPhysThresholdOptHigh OBJECT-TYPE
    SYNTAX        Integer32
    UNITS         "0.1 dBm"
    MAX-ACCESS    read-only
    STATUS        current
    DESCRIPTION   "High fixed threshold of the Optical Power Transmitted (output)"
    ::= { dcnPhysThresholdEntry 4 }

dcnPhysThresholdAttRcvLow OBJECT-TYPE
    SYNTAX        Integer32
    UNITS         "0.1 dB"
    MAX-ACCESS    read-write
    STATUS        current
    DESCRIPTION   "Low Threshold for Attenuation on Receive Fiber."
    ::= { dcnPhysThresholdEntry 5 }

dcnPhysThresholdAttRcvHigh OBJECT-TYPE
    SYNTAX        Integer32
    UNITS         "0.1 dB"
    MAX-ACCESS    read-write
    STATUS        current
    DESCRIPTION   "High Threshold for Attenuation on Receive Fiber"
    ::= { dcnPhysThresholdEntry 6 }

endOfDcnPhysThresholdTable OBJECT-TYPE
    SYNTAX        Integer32
    MAX-ACCESS    read-only
    STATUS        current
    DESCRIPTION   ""
    ::= { pmDcnPhysThreshold 2 }

endOfPmDcnPhysThreshold OBJECT-TYPE
    SYNTAX        Integer32
    MAX-ACCESS    read-only
    STATUS        current
    DESCRIPTION   ""
    ::= { pmDcnPhysThreshold 10000 }

optDcnHistorical15minTable OBJECT-TYPE
    SYNTAX        SEQUENCE OF OptDcnHistorical15minEntry
    MAX-ACCESS    not-accessible
    STATUS        current
    DESCRIPTION   ""
    ::= { pmDcnPhysRecord 1 }

optDcnHistorical15minEntry OBJECT-TYPE
    SYNTAX        OptDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  optDcnHistorical15minNumber
                }
    ::= { optDcnHistorical15minTable 1 }

OptDcnHistorical15minEntry ::= SEQUENCE
  {    optDcnHistorical15minNumber Integer32,
    optDcnHistorical15minLow Integer32,
    optDcnHistorical15minMean Integer32,
    optDcnHistorical15minHigh Integer32,
    optDcnHistorical15minValidFlag TruthValue,
    optDcnHistorical15minTimeStamp DateAndTime }

optDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { optDcnHistorical15minEntry 1 }

optDcnHistorical15minLow OBJECT-TYPE
    SYNTAX        Integer32
    UNITS         "0.1 dBm"
    MAX-ACCESS    read-only
    STATUS        current
    DESCRIPTION   "Optical Output Power Transmitted"
    ::= { optDcnHistorical15minEntry 2 }

optDcnHistorical15minMean OBJECT-TYPE
    SYNTAX        Integer32
    UNITS         "0.1 dBm"
    MAX-ACCESS    read-only
    STATUS        current
    DESCRIPTION   "Optical Output Power Transmitted"
    ::= { optDcnHistorical15minEntry 3 }

optDcnHistorical15minHigh OBJECT-TYPE
    SYNTAX        Integer32
    UNITS         "0.1 dBm"
    MAX-ACCESS    read-only
    STATUS        current
    DESCRIPTION   "Optical Output Power Transmitted"
    ::= { optDcnHistorical15minEntry 4 }

optDcnHistorical15minValidFlag OBJECT-TYPE
    SYNTAX        TruthValue
    MAX-ACCESS    read-only
    STATUS        current
    DESCRIPTION   "Valid Flag"
    ::= { optDcnHistorical15minEntry 5 }

optDcnHistorical15minTimeStamp OBJECT-TYPE
    SYNTAX        DateAndTime
    MAX-ACCESS    read-only
    STATUS        current
    DESCRIPTION   "Timestamp"
    ::= { optDcnHistorical15minEntry 6 }

endOfOptDcnHistorical15minTable OBJECT-TYPE
    SYNTAX        Integer32
    MAX-ACCESS    read-only
    STATUS        current
    DESCRIPTION   ""
    ::= { pmDcnPhysRecord 2 }

optDcnHistorical1dayTable OBJECT-TYPE
    SYNTAX        SEQUENCE OF OptDcnHistorical1dayEntry
    MAX-ACCESS    not-accessible
    STATUS        current
    DESCRIPTION   ""
    ::= { pmDcnPhysRecord 3 }

optDcnHistorical1dayEntry OBJECT-TYPE
    SYNTAX        OptDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  optDcnHistorical1dayNumber
                }
    ::= { optDcnHistorical1dayTable 1 }

OptDcnHistorical1dayEntry ::= SEQUENCE
  {    optDcnHistorical1dayNumber Integer32,
    optDcnHistorical1dayLow Integer32,
    optDcnHistorical1dayMean Integer32,
    optDcnHistorical1dayHigh Integer32,
    optDcnHistorical1dayValidFlag TruthValue,
    optDcnHistorical1dayTimeStamp DateAndTime }

optDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { optDcnHistorical1dayEntry 1 }

optDcnHistorical1dayLow OBJECT-TYPE
    SYNTAX        Integer32
    UNITS         "0.1 dBm"
    MAX-ACCESS    read-only
    STATUS        current
    DESCRIPTION   "Optical Output Power Transmitted"
    ::= { optDcnHistorical1dayEntry 2 }

optDcnHistorical1dayMean OBJECT-TYPE
    SYNTAX        Integer32
    UNITS         "0.1 dBm"
    MAX-ACCESS    read-only
    STATUS        current
    DESCRIPTION   "Optical Output Power Transmitted"
    ::= { optDcnHistorical1dayEntry 3 }

optDcnHistorical1dayHigh OBJECT-TYPE
    SYNTAX        Integer32
    UNITS         "0.1 dBm"
    MAX-ACCESS    read-only
    STATUS        current
    DESCRIPTION   "Optical Output Power Transmitted"
    ::= { optDcnHistorical1dayEntry 4 }

optDcnHistorical1dayValidFlag OBJECT-TYPE
    SYNTAX        TruthValue
    MAX-ACCESS    read-only
    STATUS        current
    DESCRIPTION   "Valid Flag"
    ::= { optDcnHistorical1dayEntry 5 }

optDcnHistorical1dayTimeStamp OBJECT-TYPE
    SYNTAX        DateAndTime
    MAX-ACCESS    read-only
    STATUS        current
    DESCRIPTION   "Timestamp"
    ::= { optDcnHistorical1dayEntry 6 }

endOfOptDcnHistorical1dayTable OBJECT-TYPE
    SYNTAX        Integer32
    MAX-ACCESS    read-only
    STATUS        current
    DESCRIPTION   ""
    ::= { pmDcnPhysRecord 4 }

optDcnHistorical1weekTable OBJECT-TYPE
    SYNTAX        SEQUENCE OF OptDcnHistorical1weekEntry
    MAX-ACCESS    not-accessible
    STATUS        current
    DESCRIPTION   ""
    ::= { pmDcnPhysRecord 5 }

optDcnHistorical1weekEntry OBJECT-TYPE
    SYNTAX        OptDcnHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  optDcnHistorical1weekNumber
                }
    ::= { optDcnHistorical1weekTable 1 }

OptDcnHistorical1weekEntry ::= SEQUENCE
  {    optDcnHistorical1weekNumber Integer32,
    optDcnHistorical1weekLow Integer32,
    optDcnHistorical1weekMean Integer32,
    optDcnHistorical1weekHigh Integer32,
    optDcnHistorical1weekValidFlag TruthValue,
    optDcnHistorical1weekTimeStamp DateAndTime }

optDcnHistorical1weekNumber OBJECT-TYPE
    SYNTAX        Integer32 (1..52)
    MAX-ACCESS    not-accessible
    STATUS        current
    DESCRIPTION   "Number 1week"
    ::= { optDcnHistorical1weekEntry 1 }

optDcnHistorical1weekLow OBJECT-TYPE
    SYNTAX        Integer32
    UNITS         "0.1 dBm"
    MAX-ACCESS    read-only
    STATUS        current
    DESCRIPTION   "Optical Output Power Transmitted"
    ::= { optDcnHistorical1weekEntry 2 }

optDcnHistorical1weekMean OBJECT-TYPE
    SYNTAX        Integer32
    UNITS         "0.1 dBm"
    MAX-ACCESS    read-only
    STATUS        current
    DESCRIPTION   "Optical Output Power Transmitted"
    ::= { optDcnHistorical1weekEntry 3 }

optDcnHistorical1weekHigh OBJECT-TYPE
    SYNTAX        Integer32
    UNITS         "0.1 dBm"
    MAX-ACCESS    read-only
    STATUS        current
    DESCRIPTION   "Optical Output Power Transmitted"
    ::= { optDcnHistorical1weekEntry 4 }

optDcnHistorical1weekValidFlag OBJECT-TYPE
    SYNTAX        TruthValue
    MAX-ACCESS    read-only
    STATUS        current
    DESCRIPTION   "Valid Flag"
    ::= { optDcnHistorical1weekEntry 5 }

optDcnHistorical1weekTimeStamp OBJECT-TYPE
    SYNTAX        DateAndTime
    MAX-ACCESS    read-only
    STATUS        current
    DESCRIPTION   "Timestamp"
    ::= { optDcnHistorical1weekEntry 6 }

endOfOptDcnHistorical1weekTable OBJECT-TYPE
    SYNTAX        Integer32
    MAX-ACCESS    read-only
    STATUS        current
    DESCRIPTION   ""
    ::= { pmDcnPhysRecord 6 }

oprDcnHistorical15minTable OBJECT-TYPE
    SYNTAX        SEQUENCE OF OprDcnHistorical15minEntry
    MAX-ACCESS    not-accessible
    STATUS        current
    DESCRIPTION   ""
    ::= { pmDcnPhysRecord 7 }

oprDcnHistorical15minEntry OBJECT-TYPE
    SYNTAX        OprDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  oprDcnHistorical15minNumber
                }
    ::= { oprDcnHistorical15minTable 1 }

OprDcnHistorical15minEntry ::= SEQUENCE
  {    oprDcnHistorical15minNumber Integer32,
    oprDcnHistorical15minLow Integer32,
    oprDcnHistorical15minMean Integer32,
    oprDcnHistorical15minHigh Integer32,
    oprDcnHistorical15minValidFlag TruthValue,
    oprDcnHistorical15minTimeStamp DateAndTime }

oprDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oprDcnHistorical15minEntry 1 }

oprDcnHistorical15minLow OBJECT-TYPE
    SYNTAX        Integer32
    UNITS         "0.1 dBm"
    MAX-ACCESS    read-only
    STATUS        current
    DESCRIPTION   "Optical Input Power Received"
    ::= { oprDcnHistorical15minEntry 2 }

oprDcnHistorical15minMean OBJECT-TYPE
    SYNTAX        Integer32
    UNITS         "0.1 dBm"
    MAX-ACCESS    read-only
    STATUS        current
    DESCRIPTION   "Optical Input Power Received"
    ::= { oprDcnHistorical15minEntry 3 }

oprDcnHistorical15minHigh OBJECT-TYPE
    SYNTAX        Integer32
    UNITS         "0.1 dBm"
    MAX-ACCESS    read-only
    STATUS        current
    DESCRIPTION   "Optical Input Power Received"
    ::= { oprDcnHistorical15minEntry 4 }

oprDcnHistorical15minValidFlag OBJECT-TYPE
    SYNTAX        TruthValue
    MAX-ACCESS    read-only
    STATUS        current
    DESCRIPTION   "Valid Flag"
    ::= { oprDcnHistorical15minEntry 5 }

oprDcnHistorical15minTimeStamp OBJECT-TYPE
    SYNTAX        DateAndTime
    MAX-ACCESS    read-only
    STATUS        current
    DESCRIPTION   "Timestamp"
    ::= { oprDcnHistorical15minEntry 6 }

endOfOprDcnHistorical15minTable OBJECT-TYPE
    SYNTAX        Integer32
    MAX-ACCESS    read-only
    STATUS        current
    DESCRIPTION   ""
    ::= { pmDcnPhysRecord 8 }

oprDcnHistorical1dayTable OBJECT-TYPE
    SYNTAX        SEQUENCE OF OprDcnHistorical1dayEntry
    MAX-ACCESS    not-accessible
    STATUS        current
    DESCRIPTION   ""
    ::= { pmDcnPhysRecord 9 }

oprDcnHistorical1dayEntry OBJECT-TYPE
    SYNTAX        OprDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  oprDcnHistorical1dayNumber
                }
    ::= { oprDcnHistorical1dayTable 1 }

OprDcnHistorical1dayEntry ::= SEQUENCE
  {    oprDcnHistorical1dayNumber Integer32,
    oprDcnHistorical1dayLow Integer32,
    oprDcnHistorical1dayMean Integer32,
    oprDcnHistorical1dayHigh Integer32,
    oprDcnHistorical1dayValidFlag TruthValue,
    oprDcnHistorical1dayTimeStamp DateAndTime }

oprDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oprDcnHistorical1dayEntry 1 }

oprDcnHistorical1dayLow OBJECT-TYPE
    SYNTAX        Integer32
    UNITS         "0.1 dBm"
    MAX-ACCESS    read-only
    STATUS        current
    DESCRIPTION   "Optical Input Power Received"
    ::= { oprDcnHistorical1dayEntry 2 }

oprDcnHistorical1dayMean OBJECT-TYPE
    SYNTAX        Integer32
    UNITS         "0.1 dBm"
    MAX-ACCESS    read-only
    STATUS        current
    DESCRIPTION   "Optical Input Power Received"
    ::= { oprDcnHistorical1dayEntry 3 }

oprDcnHistorical1dayHigh OBJECT-TYPE
    SYNTAX        Integer32
    UNITS         "0.1 dBm"
    MAX-ACCESS    read-only
    STATUS        current
    DESCRIPTION   "Optical Input Power Received"
    ::= { oprDcnHistorical1dayEntry 4 }

oprDcnHistorical1dayValidFlag OBJECT-TYPE
    SYNTAX        TruthValue
    MAX-ACCESS    read-only
    STATUS        current
    DESCRIPTION   "Valid Flag"
    ::= { oprDcnHistorical1dayEntry 5 }

oprDcnHistorical1dayTimeStamp OBJECT-TYPE
    SYNTAX        DateAndTime
    MAX-ACCESS    read-only
    STATUS        current
    DESCRIPTION   "Timestamp"
    ::= { oprDcnHistorical1dayEntry 6 }

endOfOprDcnHistorical1dayTable OBJECT-TYPE
    SYNTAX        Integer32
    MAX-ACCESS    read-only
    STATUS        current
    DESCRIPTION   ""
    ::= { pmDcnPhysRecord 10 }

oprDcnHistorical1weekTable OBJECT-TYPE
    SYNTAX        SEQUENCE OF OprDcnHistorical1weekEntry
    MAX-ACCESS    not-accessible
    STATUS        current
    DESCRIPTION   ""
    ::= { pmDcnPhysRecord 11 }

oprDcnHistorical1weekEntry OBJECT-TYPE
    SYNTAX        OprDcnHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  oprDcnHistorical1weekNumber
                }
    ::= { oprDcnHistorical1weekTable 1 }

OprDcnHistorical1weekEntry ::= SEQUENCE
  {    oprDcnHistorical1weekNumber Integer32,
    oprDcnHistorical1weekLow Integer32,
    oprDcnHistorical1weekMean Integer32,
    oprDcnHistorical1weekHigh Integer32,
    oprDcnHistorical1weekValidFlag TruthValue,
    oprDcnHistorical1weekTimeStamp DateAndTime }

oprDcnHistorical1weekNumber OBJECT-TYPE
    SYNTAX        Integer32 (1..52)
    MAX-ACCESS    not-accessible
    STATUS        current
    DESCRIPTION   "Number 1week"
    ::= { oprDcnHistorical1weekEntry 1 }

oprDcnHistorical1weekLow OBJECT-TYPE
    SYNTAX        Integer32
    UNITS         "0.1 dBm"
    MAX-ACCESS    read-only
    STATUS        current
    DESCRIPTION   "Optical Input Power Received"
    ::= { oprDcnHistorical1weekEntry 2 }

oprDcnHistorical1weekMean OBJECT-TYPE
    SYNTAX        Integer32
    UNITS         "0.1 dBm"
    MAX-ACCESS    read-only
    STATUS        current
    DESCRIPTION   "Optical Input Power Received"
    ::= { oprDcnHistorical1weekEntry 3 }

oprDcnHistorical1weekHigh OBJECT-TYPE
    SYNTAX        Integer32
    UNITS         "0.1 dBm"
    MAX-ACCESS    read-only
    STATUS        current
    DESCRIPTION   "Optical Input Power Received"
    ::= { oprDcnHistorical1weekEntry 4 }

oprDcnHistorical1weekValidFlag OBJECT-TYPE
    SYNTAX        TruthValue
    MAX-ACCESS    read-only
    STATUS        current
    DESCRIPTION   "Valid Flag"
    ::= { oprDcnHistorical1weekEntry 5 }

oprDcnHistorical1weekTimeStamp OBJECT-TYPE
    SYNTAX        DateAndTime
    MAX-ACCESS    read-only
    STATUS        current
    DESCRIPTION   "Timestamp"
    ::= { oprDcnHistorical1weekEntry 6 }

endOfOprDcnHistorical1weekTable OBJECT-TYPE
    SYNTAX        Integer32
    MAX-ACCESS    read-only
    STATUS        current
    DESCRIPTION   ""
    ::= { pmDcnPhysRecord 12 }

lbcnDcnHistorical15minTable OBJECT-TYPE
    SYNTAX        SEQUENCE OF LbcnDcnHistorical15minEntry
    MAX-ACCESS    not-accessible
    STATUS        current
    DESCRIPTION   ""
    ::= { pmDcnPhysRecord 13 }

lbcnDcnHistorical15minEntry OBJECT-TYPE
    SYNTAX        LbcnDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  lbcnDcnHistorical15minNumber
                }
    ::= { lbcnDcnHistorical15minTable 1 }

LbcnDcnHistorical15minEntry ::= SEQUENCE
  {    lbcnDcnHistorical15minNumber Integer32,
    lbcnDcnHistorical15minLow Unsigned32,
    lbcnDcnHistorical15minMean Unsigned32,
    lbcnDcnHistorical15minHigh Unsigned32,
    lbcnDcnHistorical15minValidFlag TruthValue,
    lbcnDcnHistorical15minTimeStamp DateAndTime }

lbcnDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lbcnDcnHistorical15minEntry 1 }

lbcnDcnHistorical15minLow OBJECT-TYPE
    SYNTAX        Unsigned32
    UNITS         "%"
    MAX-ACCESS    read-only
    STATUS        current
    DESCRIPTION   "Laser Bias Current Normalized"
    ::= { lbcnDcnHistorical15minEntry 2 }

lbcnDcnHistorical15minMean OBJECT-TYPE
    SYNTAX        Unsigned32
    UNITS         "%"
    MAX-ACCESS    read-only
    STATUS        current
    DESCRIPTION   "Laser Bias Current Normalized"
    ::= { lbcnDcnHistorical15minEntry 3 }

lbcnDcnHistorical15minHigh OBJECT-TYPE
    SYNTAX        Unsigned32
    UNITS         "%"
    MAX-ACCESS    read-only
    STATUS        current
    DESCRIPTION   "Laser Bias Current Normalized"
    ::= { lbcnDcnHistorical15minEntry 4 }

lbcnDcnHistorical15minValidFlag OBJECT-TYPE
    SYNTAX        TruthValue
    MAX-ACCESS    read-only
    STATUS        current
    DESCRIPTION   "Valid Flag"
    ::= { lbcnDcnHistorical15minEntry 5 }

lbcnDcnHistorical15minTimeStamp OBJECT-TYPE
    SYNTAX        DateAndTime
    MAX-ACCESS    read-only
    STATUS        current
    DESCRIPTION   "Timestamp"
    ::= { lbcnDcnHistorical15minEntry 6 }

endOfLbcnDcnHistorical15minTable OBJECT-TYPE
    SYNTAX        Integer32
    MAX-ACCESS    read-only
    STATUS        current
    DESCRIPTION   ""
    ::= { pmDcnPhysRecord 14 }

lbcnDcnHistorical1dayTable OBJECT-TYPE
    SYNTAX        SEQUENCE OF LbcnDcnHistorical1dayEntry
    MAX-ACCESS    not-accessible
    STATUS        current
    DESCRIPTION   ""
    ::= { pmDcnPhysRecord 15 }

lbcnDcnHistorical1dayEntry OBJECT-TYPE
    SYNTAX        LbcnDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  lbcnDcnHistorical1dayNumber
                }
    ::= { lbcnDcnHistorical1dayTable 1 }

LbcnDcnHistorical1dayEntry ::= SEQUENCE
  {    lbcnDcnHistorical1dayNumber Integer32,
    lbcnDcnHistorical1dayLow Unsigned32,
    lbcnDcnHistorical1dayMean Unsigned32,
    lbcnDcnHistorical1dayHigh Unsigned32,
    lbcnDcnHistorical1dayValidFlag TruthValue,
    lbcnDcnHistorical1dayTimeStamp DateAndTime }

lbcnDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lbcnDcnHistorical1dayEntry 1 }

lbcnDcnHistorical1dayLow OBJECT-TYPE
    SYNTAX        Unsigned32
    UNITS         "%"
    MAX-ACCESS    read-only
    STATUS        current
    DESCRIPTION   "Laser Bias Current Normalized"
    ::= { lbcnDcnHistorical1dayEntry 2 }

lbcnDcnHistorical1dayMean OBJECT-TYPE
    SYNTAX        Unsigned32
    UNITS         "%"
    MAX-ACCESS    read-only
    STATUS        current
    DESCRIPTION   "Laser Bias Current Normalized"
    ::= { lbcnDcnHistorical1dayEntry 3 }

lbcnDcnHistorical1dayHigh OBJECT-TYPE
    SYNTAX        Unsigned32
    UNITS         "%"
    MAX-ACCESS    read-only
    STATUS        current
    DESCRIPTION   "Laser Bias Current Normalized"
    ::= { lbcnDcnHistorical1dayEntry 4 }

lbcnDcnHistorical1dayValidFlag OBJECT-TYPE
    SYNTAX        TruthValue
    MAX-ACCESS    read-only
    STATUS        current
    DESCRIPTION   "Valid Flag"
    ::= { lbcnDcnHistorical1dayEntry 5 }

lbcnDcnHistorical1dayTimeStamp OBJECT-TYPE
    SYNTAX        DateAndTime
    MAX-ACCESS    read-only
    STATUS        current
    DESCRIPTION   "Timestamp"
    ::= { lbcnDcnHistorical1dayEntry 6 }

endOfLbcnDcnHistorical1dayTable OBJECT-TYPE
    SYNTAX        Integer32
    MAX-ACCESS    read-only
    STATUS        current
    DESCRIPTION   ""
    ::= { pmDcnPhysRecord 16 }

lbcnDcnHistorical1weekTable OBJECT-TYPE
    SYNTAX        SEQUENCE OF LbcnDcnHistorical1weekEntry
    MAX-ACCESS    not-accessible
    STATUS        current
    DESCRIPTION   ""
    ::= { pmDcnPhysRecord 17 }

lbcnDcnHistorical1weekEntry OBJECT-TYPE
    SYNTAX        LbcnDcnHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  lbcnDcnHistorical1weekNumber
                }
    ::= { lbcnDcnHistorical1weekTable 1 }

LbcnDcnHistorical1weekEntry ::= SEQUENCE
  {    lbcnDcnHistorical1weekNumber Integer32,
    lbcnDcnHistorical1weekLow Unsigned32,
    lbcnDcnHistorical1weekMean Unsigned32,
    lbcnDcnHistorical1weekHigh Unsigned32,
    lbcnDcnHistorical1weekValidFlag TruthValue,
    lbcnDcnHistorical1weekTimeStamp DateAndTime }

lbcnDcnHistorical1weekNumber OBJECT-TYPE
    SYNTAX        Integer32 (1..52)
    MAX-ACCESS    not-accessible
    STATUS        current
    DESCRIPTION   "Number 1week"
    ::= { lbcnDcnHistorical1weekEntry 1 }

lbcnDcnHistorical1weekLow OBJECT-TYPE
    SYNTAX        Unsigned32
    UNITS         "%"
    MAX-ACCESS    read-only
    STATUS        current
    DESCRIPTION   "Laser Bias Current Normalized"
    ::= { lbcnDcnHistorical1weekEntry 2 }

lbcnDcnHistorical1weekMean OBJECT-TYPE
    SYNTAX        Unsigned32
    UNITS         "%"
    MAX-ACCESS    read-only
    STATUS        current
    DESCRIPTION   "Laser Bias Current Normalized"
    ::= { lbcnDcnHistorical1weekEntry 3 }

lbcnDcnHistorical1weekHigh OBJECT-TYPE
    SYNTAX        Unsigned32
    UNITS         "%"
    MAX-ACCESS    read-only
    STATUS        current
    DESCRIPTION   "Laser Bias Current Normalized"
    ::= { lbcnDcnHistorical1weekEntry 4 }

lbcnDcnHistorical1weekValidFlag OBJECT-TYPE
    SYNTAX        TruthValue
    MAX-ACCESS    read-only
    STATUS        current
    DESCRIPTION   "Valid Flag"
    ::= { lbcnDcnHistorical1weekEntry 5 }

lbcnDcnHistorical1weekTimeStamp OBJECT-TYPE
    SYNTAX        DateAndTime
    MAX-ACCESS    read-only
    STATUS        current
    DESCRIPTION   "Timestamp"
    ::= { lbcnDcnHistorical1weekEntry 6 }

endOfLbcnDcnHistorical1weekTable OBJECT-TYPE
    SYNTAX        Integer32
    MAX-ACCESS    read-only
    STATUS        current
    DESCRIPTION   ""
    ::= { pmDcnPhysRecord 18 }

atrcvDcnHistorical15minTable OBJECT-TYPE
    SYNTAX        SEQUENCE OF AtrcvDcnHistorical15minEntry
    MAX-ACCESS    not-accessible
    STATUS        current
    DESCRIPTION   ""
    ::= { pmDcnPhysRecord 19 }

atrcvDcnHistorical15minEntry OBJECT-TYPE
    SYNTAX        AtrcvDcnHistorical15minEntry
    MAX-ACCESS    not-accessible
    STATUS        current
    DESCRIPTION   ""
    INDEX       {
                  entityDcnShelfNo,
                  entityDcnSlotNo,
                  entityDcnPortNo,
                  entityDcnExtNo,
                  entityDcnClassName,
                  atrcvDcnHistorical15minNumber
                }
    ::= { atrcvDcnHistorical15minTable 1 }

AtrcvDcnHistorical15minEntry ::= SEQUENCE
  {    atrcvDcnHistorical15minNumber Integer32,
    atrcvDcnHistorical15minLow Integer32,
    atrcvDcnHistorical15minMean Integer32,
    atrcvDcnHistorical15minHigh Integer32,
    atrcvDcnHistorical15minValidFlag TruthValue,
    atrcvDcnHistorical15minTimeStamp DateAndTime }

atrcvDcnHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { atrcvDcnHistorical15minEntry 1 }

atrcvDcnHistorical15minLow OBJECT-TYPE
    SYNTAX        Integer32
    UNITS         "0.1 dB"
    MAX-ACCESS    read-only
    STATUS        current
    DESCRIPTION   "Low Attenuation on Receive Fiber"
    ::= { atrcvDcnHistorical15minEntry 2 }

atrcvDcnHistorical15minMean OBJECT-TYPE
    SYNTAX        Integer32
    UNITS         "0.1 dB"
    MAX-ACCESS    read-only
    STATUS        current
    DESCRIPTION   "Mean Attenuation on Receive Fiber"
    ::= { atrcvDcnHistorical15minEntry 3 }

atrcvDcnHistorical15minHigh OBJECT-TYPE
    SYNTAX        Integer32
    UNITS         "0.1 dB"
    MAX-ACCESS    read-only
    STATUS        current
    DESCRIPTION   "High Attenuation on Receive Fiber"
    ::= { atrcvDcnHistorical15minEntry 4 }

atrcvDcnHistorical15minValidFlag OBJECT-TYPE
    SYNTAX        TruthValue
    MAX-ACCESS    read-only
    STATUS        current
    DESCRIPTION   "Valid Flag"
    ::= { atrcvDcnHistorical15minEntry 5 }

atrcvDcnHistorical15minTimeStamp OBJECT-TYPE
    SYNTAX        DateAndTime
    MAX-ACCESS    read-only
    STATUS        current
    DESCRIPTION   "Timestamp"
    ::= { atrcvDcnHistorical15minEntry 6 }

endOfAtrcvDcnHistorical15minTable OBJECT-TYPE
    SYNTAX        Integer32
    MAX-ACCESS    read-only
    STATUS        current
    DESCRIPTION   ""
    ::= { pmDcnPhysRecord 20 }

atrcvDcnHistorical1dayTable OBJECT-TYPE
    SYNTAX        SEQUENCE OF AtrcvDcnHistorical1dayEntry
    MAX-ACCESS    not-accessible
    STATUS        current
    DESCRIPTION   ""
    ::= { pmDcnPhysRecord 21 }

atrcvDcnHistorical1dayEntry OBJECT-TYPE
    SYNTAX        AtrcvDcnHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  atrcvDcnHistorical1dayNumber
                }
    ::= { atrcvDcnHistorical1dayTable 1 }

AtrcvDcnHistorical1dayEntry ::= SEQUENCE
  {    atrcvDcnHistorical1dayNumber Integer32,
    atrcvDcnHistorical1dayLow Integer32,
    atrcvDcnHistorical1dayMean Integer32,
    atrcvDcnHistorical1dayHigh Integer32,
    atrcvDcnHistorical1dayValidFlag TruthValue,
    atrcvDcnHistorical1dayTimeStamp DateAndTime }

atrcvDcnHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { atrcvDcnHistorical1dayEntry 1 }

atrcvDcnHistorical1dayLow OBJECT-TYPE
    SYNTAX        Integer32
    UNITS         "0.1 dB"
    MAX-ACCESS    read-only
    STATUS        current
    DESCRIPTION   "Low Attenuation on Receive Fiber"
    ::= { atrcvDcnHistorical1dayEntry 2 }

atrcvDcnHistorical1dayMean OBJECT-TYPE
    SYNTAX        Integer32
    UNITS         "0.1 dB"
    MAX-ACCESS    read-only
    STATUS        current
    DESCRIPTION   "Mean Attenuation on Receive Fiber"
    ::= { atrcvDcnHistorical1dayEntry 3 }

atrcvDcnHistorical1dayHigh OBJECT-TYPE
    SYNTAX        Integer32
    UNITS         "0.1 dB"
    MAX-ACCESS    read-only
    STATUS        current
    DESCRIPTION   "High Attenuation on Receive Fiber"
    ::= { atrcvDcnHistorical1dayEntry 4 }

atrcvDcnHistorical1dayValidFlag OBJECT-TYPE
    SYNTAX        TruthValue
    MAX-ACCESS    read-only
    STATUS        current
    DESCRIPTION   "Valid Flag"
    ::= { atrcvDcnHistorical1dayEntry 5 }

atrcvDcnHistorical1dayTimeStamp OBJECT-TYPE
    SYNTAX        DateAndTime
    MAX-ACCESS    read-only
    STATUS        current
    DESCRIPTION   "Timestamp"
    ::= { atrcvDcnHistorical1dayEntry 6 }

endOfAtrcvDcnHistorical1dayTable OBJECT-TYPE
    SYNTAX        Integer32
    MAX-ACCESS    read-only
    STATUS        current
    DESCRIPTION   ""
    ::= { pmDcnPhysRecord 22 }

atrcvDcnHistorical1weekTable OBJECT-TYPE
    SYNTAX        SEQUENCE OF AtrcvDcnHistorical1weekEntry
    MAX-ACCESS    not-accessible
    STATUS        current
    DESCRIPTION   ""
    ::= { pmDcnPhysRecord 23 }

atrcvDcnHistorical1weekEntry OBJECT-TYPE
    SYNTAX        AtrcvDcnHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  atrcvDcnHistorical1weekNumber
                }
    ::= { atrcvDcnHistorical1weekTable 1 }

AtrcvDcnHistorical1weekEntry ::= SEQUENCE
  {    atrcvDcnHistorical1weekNumber Integer32,
    atrcvDcnHistorical1weekLow Integer32,
    atrcvDcnHistorical1weekMean Integer32,
    atrcvDcnHistorical1weekHigh Integer32,
    atrcvDcnHistorical1weekValidFlag TruthValue,
    atrcvDcnHistorical1weekTimeStamp DateAndTime }

atrcvDcnHistorical1weekNumber OBJECT-TYPE
    SYNTAX        Integer32 (1..52)
    MAX-ACCESS    not-accessible
    STATUS        current
    DESCRIPTION   "Number 1week"
    ::= { atrcvDcnHistorical1weekEntry 1 }

atrcvDcnHistorical1weekLow OBJECT-TYPE
    SYNTAX        Integer32
    UNITS         "0.1 dB"
    MAX-ACCESS    read-only
    STATUS        current
    DESCRIPTION   "Low Attenuation on Receive Fiber"
    ::= { atrcvDcnHistorical1weekEntry 2 }

atrcvDcnHistorical1weekMean OBJECT-TYPE
    SYNTAX        Integer32
    UNITS         "0.1 dB"
    MAX-ACCESS    read-only
    STATUS        current
    DESCRIPTION   "Mean Attenuation on Receive Fiber"
    ::= { atrcvDcnHistorical1weekEntry 3 }

atrcvDcnHistorical1weekHigh OBJECT-TYPE
    SYNTAX        Integer32
    UNITS         "0.1 dB"
    MAX-ACCESS    read-only
    STATUS        current
    DESCRIPTION   "High Attenuation on Receive Fiber"
    ::= { atrcvDcnHistorical1weekEntry 4 }

atrcvDcnHistorical1weekValidFlag OBJECT-TYPE
    SYNTAX        TruthValue
    MAX-ACCESS    read-only
    STATUS        current
    DESCRIPTION   "Valid Flag"
    ::= { atrcvDcnHistorical1weekEntry 5 }

atrcvDcnHistorical1weekTimeStamp OBJECT-TYPE
    SYNTAX        DateAndTime
    MAX-ACCESS    read-only
    STATUS        current
    DESCRIPTION   "Timestamp"
    ::= { atrcvDcnHistorical1weekEntry 6 }

endOfAtrcvDcnHistorical1weekTable OBJECT-TYPE
    SYNTAX        Integer32
    MAX-ACCESS    read-only
    STATUS        current
    DESCRIPTION   ""
    ::= { pmDcnPhysRecord 24 }

endOfPmDcnPhysRecord OBJECT-TYPE
    SYNTAX        Integer32
    MAX-ACCESS    read-only
    STATUS        current
    DESCRIPTION   ""
    ::= { pmDcnPhysRecord 10000 }

facilityDataThresholdTable OBJECT-TYPE
    SYNTAX        SEQUENCE OF FacilityDataThresholdEntry
    MAX-ACCESS    not-accessible
    STATUS        current
    DESCRIPTION   ""
    ::= { pmFacilityDataThreshold 1 }

facilityDataThresholdEntry OBJECT-TYPE
    SYNTAX        FacilityDataThresholdEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { facilityDataThresholdTable 1 }

FacilityDataThresholdEntry ::= SEQUENCE
  {    facilityDataThresholdESOduHT15min Unsigned32,
    facilityDataThresholdESOduHT1day Unsigned32,
    facilityDataThresholdSESOduHT15min Unsigned32,
    facilityDataThresholdSESOduHT1day Unsigned32,
    facilityDataThresholdBBEOduHT15min Counter64String,
    facilityDataThresholdBBEOduHT1day Counter64String,
    facilityDataThresholdUASOduHT15min Unsigned32,
    facilityDataThresholdUASOduHT1day Unsigned32,
    facilityDataThresholdESTcmaHT15min Unsigned32,
    facilityDataThresholdESTcmaHT1day Unsigned32,
    facilityDataThresholdSESTcmaHT15min Unsigned32,
    facilityDataThresholdSESTcmaHT1day Unsigned32,
    facilityDataThresholdBBETcmaHT15min Counter64String,
    facilityDataThresholdBBETcmaHT1day Counter64String,
    facilityDataThresholdUASTcmaHT15min Unsigned32,
    facilityDataThresholdUASTcmaHT1day Unsigned32,
    facilityDataThresholdESTcmbHT15min Unsigned32,
    facilityDataThresholdESTcmbHT1day Unsigned32,
    facilityDataThresholdSESTcmbHT15min Unsigned32,
    facilityDataThresholdSESTcmbHT1day Unsigned32,
    facilityDataThresholdBBETcmbHT15min Counter64String,
    facilityDataThresholdBBETcmbHT1day Counter64String,
    facilityDataThresholdUASTcmbHT15min Unsigned32,
    facilityDataThresholdUASTcmbHT1day Unsigned32,
    facilityDataThresholdESTcmcHT15min Unsigned32,
    facilityDataThresholdESTcmcHT1day Unsigned32,
    facilityDataThresholdSESTcmcHT15min Unsigned32,
    facilityDataThresholdSESTcmcHT1day Unsigned32,
    facilityDataThresholdBBETcmcHT15min Counter64String,
    facilityDataThresholdBBETcmcHT1day Counter64String,
    facilityDataThresholdUASTcmcHT15min Unsigned32,
    facilityDataThresholdUASTcmcHT1day Unsigned32,
    facilityDataThresholdESOtuHT15min Unsigned32,
    facilityDataThresholdESOtuHT1day Unsigned32,
    facilityDataThresholdSESOtuHT15min Unsigned32,
    facilityDataThresholdSESOtuHT1day Unsigned32,
    facilityDataThresholdBBEOtuHT15min Counter64String,
    facilityDataThresholdBBEOtuHT1day Counter64String,
    facilityDataThresholdUASOtuHT15min Unsigned32,
    facilityDataThresholdUASOtuHT1day Unsigned32,
    facilityDataThresholdESFecHT15min Unsigned32,
    facilityDataThresholdESFecHT1day Unsigned32,
    facilityDataThresholdSESFecHT15min Unsigned32,
    facilityDataThresholdSESFecHT1day Unsigned32,
    facilityDataThresholdUBEFecHT15min Counter64String,
    facilityDataThresholdUBEFecHT1day Counter64String,
    facilityDataThresholdCEFecHT15min Counter64String,
    facilityDataThresholdCEFecHT1day Counter64String,
    facilityDataThresholdBERCEFecHT15min Counter64String,
    facilityDataThresholdBERCEFecHT1day Counter64String,
    facilityDataThresholdESPcsHT15min Unsigned32,
    facilityDataThresholdESPcsHT1day Unsigned32,
    facilityDataThresholdDEPcsHT15min Unsigned32,
    facilityDataThresholdDEPcsHT1day Unsigned32,
    facilityDataThresholdCVPcsHT15min Counter64String,
    facilityDataThresholdCVPcsHT1day Counter64String,
    facilityDataThresholdESLHT15min Unsigned32,
    facilityDataThresholdESLHT1day Unsigned32,
    facilityDataThresholdSESLHT15min Unsigned32,
    facilityDataThresholdSESLHT1day Unsigned32,
    facilityDataThresholdUASLHT15min Unsigned32,
    facilityDataThresholdUASLHT1day Unsigned32,
    facilityDataThresholdCVLHT15min Counter64String,
    facilityDataThresholdCVLHT1day Counter64String,
    facilityDataThresholdESSHT15min Unsigned32,
    facilityDataThresholdESSHT1day Unsigned32,
    facilityDataThresholdSESSHT15min Unsigned32,
    facilityDataThresholdSESSHT1day Unsigned32,
    facilityDataThresholdSEFSSHT15min Unsigned32,
    facilityDataThresholdSEFSSHT1day Unsigned32,
    facilityDataThresholdCVSHT15min Counter64String,
    facilityDataThresholdCVSHT1day Counter64String,
    facilityDataThresholdBBEPcsHT15min Counter64String,
    facilityDataThresholdBBEPcsHT1day Counter64String,
    facilityDataThresholdCVDEPcsHT15min Counter64String,
    facilityDataThresholdCVDEPcsHT1day Counter64String,
    facilityDataThresholdSEPcsHT15min Unsigned32,
    facilityDataThresholdSEPcsHT1day Unsigned32,
    facilityDataThresholdCRCFrRcvHT15min Unsigned32,
    facilityDataThresholdCRCFrRcvHT1day Unsigned32,
    facilityDataThresholdCRCFrEgrsHT15min Unsigned32,
    facilityDataThresholdCRCFrEgrsHT1day Unsigned32,
    facilityDataThresholdBBESHT15min Counter64String,
    facilityDataThresholdBBESHT1day Counter64String,
    facilityDataThresholdBBELHT15min Counter64String,
    facilityDataThresholdBBELHT1day Counter64String,
    facilityDataThresholdOOFSSHT15min Unsigned32,
    facilityDataThresholdOOFSSHT1day Unsigned32 }

facilityDataThresholdESOduHT15min OBJECT-TYPE
    SYNTAX        Unsigned32 (0..900)
    MAX-ACCESS    read-write
    STATUS        current
    DESCRIPTION   "ODU Errored Seconds 15 Minute Threshold"
    ::= { facilityDataThresholdEntry 1 }

facilityDataThresholdESOduHT1day OBJECT-TYPE
    SYNTAX        Unsigned32 (0..86400)
    MAX-ACCESS    read-write
    STATUS        current
    DESCRIPTION   "ODU Errored Seconds 1 Day Threshold"
    ::= { facilityDataThresholdEntry 2 }

facilityDataThresholdSESOduHT15min OBJECT-TYPE
    SYNTAX        Unsigned32 (0..900)
    MAX-ACCESS    read-write
    STATUS        current
    DESCRIPTION   "ODU Severely Errored Seconds 15 Minute Threshold"
    ::= { facilityDataThresholdEntry 3 }

facilityDataThresholdSESOduHT1day OBJECT-TYPE
    SYNTAX        Unsigned32 (0..86400)
    MAX-ACCESS    read-write
    STATUS        current
    DESCRIPTION   "ODU Severely Errored Seconds 1 Day Threshold"
    ::= { facilityDataThresholdEntry 4 }

facilityDataThresholdBBEOduHT15min OBJECT-TYPE
    SYNTAX        Counter64String
    MAX-ACCESS    read-write
    STATUS        current
    DESCRIPTION   "ODU Background Block Errors 15 Minute Threshold"
    ::= { facilityDataThresholdEntry 5 }

facilityDataThresholdBBEOduHT1day OBJECT-TYPE
    SYNTAX        Counter64String
    MAX-ACCESS    read-write
    STATUS        current
    DESCRIPTION   "ODU Background Block Errors 1 Day Threshold"
    ::= { facilityDataThresholdEntry 6 }

facilityDataThresholdUASOduHT15min OBJECT-TYPE
    SYNTAX        Unsigned32 (0..900)
    MAX-ACCESS    read-write
    STATUS        current
    DESCRIPTION   "ODU Unavailable Seconds 15 Minute Threshold"
    ::= { facilityDataThresholdEntry 7 }

facilityDataThresholdUASOduHT1day OBJECT-TYPE
    SYNTAX        Unsigned32 (0..86400)
    MAX-ACCESS    read-write
    STATUS        current
    DESCRIPTION   "ODU Unavailable Seconds 1 Day Threshold"
    ::= { facilityDataThresholdEntry 8 }

facilityDataThresholdESTcmaHT15min OBJECT-TYPE
    SYNTAX        Unsigned32 (0..900)
    MAX-ACCESS    read-write
    STATUS        current
    DESCRIPTION   "ODU Tandem Connection Monitoring A Errored Seconds 15 Minute Threshold"
    ::= { facilityDataThresholdEntry 9 }

facilityDataThresholdESTcmaHT1day OBJECT-TYPE
    SYNTAX        Unsigned32 (0..86400)
    MAX-ACCESS    read-write
    STATUS        current
    DESCRIPTION   "ODU Tandem Connection Monitoring A Errored Seconds 1 Day Threshold"
    ::= { facilityDataThresholdEntry 10 }

facilityDataThresholdSESTcmaHT15min OBJECT-TYPE
    SYNTAX        Unsigned32 (0..900)
    MAX-ACCESS    read-write
    STATUS        current
    DESCRIPTION   "Tandem Connection Monitor A Section Severely Errored Seconds 15 Minute Threshold"
    ::= { facilityDataThresholdEntry 11 }

facilityDataThresholdSESTcmaHT1day OBJECT-TYPE
    SYNTAX        Unsigned32 (0..86400)
    MAX-ACCESS    read-write
    STATUS        current
    DESCRIPTION   "Tandem Connection Monitor A Section Severely Errored Seconds 1 Day Threshold"
    ::= { facilityDataThresholdEntry 12 }

facilityDataThresholdBBETcmaHT15min OBJECT-TYPE
    SYNTAX        Counter64String
    MAX-ACCESS    read-write
    STATUS        current
    DESCRIPTION   "ODU Tandem Connection A Background Block Errors 15 Minute Threshold"
    ::= { facilityDataThresholdEntry 13 }

facilityDataThresholdBBETcmaHT1day OBJECT-TYPE
    SYNTAX        Counter64String
    MAX-ACCESS    read-write
    STATUS        current
    DESCRIPTION   "ODU Tandem Connection A Background Block Errors 1 Day Minute Threshold"
    ::= { facilityDataThresholdEntry 14 }

facilityDataThresholdUASTcmaHT15min OBJECT-TYPE
    SYNTAX        Unsigned32 (0..900)
    MAX-ACCESS    read-write
    STATUS        current
    DESCRIPTION   "ODU Tandem Connection Monitoring A Unavailable Seconds 15 Minute Threshold"
    ::= { facilityDataThresholdEntry 15 }

facilityDataThresholdUASTcmaHT1day OBJECT-TYPE
    SYNTAX        Unsigned32 (0..86400)
    MAX-ACCESS    read-write
    STATUS        current
    DESCRIPTION   "ODU Tandem Connection Monitoring A Unavailable Seconds 1 Day Threshold"
    ::= { facilityDataThresholdEntry 16 }

facilityDataThresholdESTcmbHT15min OBJECT-TYPE
    SYNTAX        Unsigned32 (0..900)
    MAX-ACCESS    read-write
    STATUS        current
    DESCRIPTION   "ODU Tandem Connection Monitoring B Errored Seconds 15 Minute Threshold"
    ::= { facilityDataThresholdEntry 17 }

facilityDataThresholdESTcmbHT1day OBJECT-TYPE
    SYNTAX        Unsigned32 (0..86400)
    MAX-ACCESS    read-write
    STATUS        current
    DESCRIPTION   "ODU Tandem Connection Monitoring B Errored Seconds 1 Day Threshold"
    ::= { facilityDataThresholdEntry 18 }

facilityDataThresholdSESTcmbHT15min OBJECT-TYPE
    SYNTAX        Unsigned32 (0..900)
    MAX-ACCESS    read-write
    STATUS        current
    DESCRIPTION   "Tandem Connection Monitor B Section Severely Errored Seconds 15 Minute Threshold"
    ::= { facilityDataThresholdEntry 19 }

facilityDataThresholdSESTcmbHT1day OBJECT-TYPE
    SYNTAX        Unsigned32 (0..86400)
    MAX-ACCESS    read-write
    STATUS        current
    DESCRIPTION   "Tandem Connection Monitor B Section Severely Errored Seconds 1 Day Threshold"
    ::= { facilityDataThresholdEntry 20 }

facilityDataThresholdBBETcmbHT15min OBJECT-TYPE
    SYNTAX        Counter64String
    MAX-ACCESS    read-write
    STATUS        current
    DESCRIPTION   "ODU Tandem Connection B Background Block Errors 15 Minute Threshold"
    ::= { facilityDataThresholdEntry 21 }

facilityDataThresholdBBETcmbHT1day OBJECT-TYPE
    SYNTAX        Counter64String
    MAX-ACCESS    read-write
    STATUS        current
    DESCRIPTION   "ODU Tandem Connection B Background Block Errors 1 Day Threshold"
    ::= { facilityDataThresholdEntry 22 }

facilityDataThresholdUASTcmbHT15min OBJECT-TYPE
    SYNTAX        Unsigned32 (0..900)
    MAX-ACCESS    read-write
    STATUS        current
    DESCRIPTION   "ODU Tandem Connection Monitoring B Unavailable Seconds 15 Minute Threshold"
    ::= { facilityDataThresholdEntry 23 }

facilityDataThresholdUASTcmbHT1day OBJECT-TYPE
    SYNTAX        Unsigned32 (0..86400)
    MAX-ACCESS    read-write
    STATUS        current
    DESCRIPTION   "ODU Tandem Connection Monitoring B Unavailable Seconds 1 Day Threshold"
    ::= { facilityDataThresholdEntry 24 }

facilityDataThresholdESTcmcHT15min OBJECT-TYPE
    SYNTAX        Unsigned32 (0..900)
    MAX-ACCESS    read-write
    STATUS        current
    DESCRIPTION   "ODU Tandem Connection Monitoring C Errored Seconds 15 Minute Threshold"
    ::= { facilityDataThresholdEntry 25 }

facilityDataThresholdESTcmcHT1day OBJECT-TYPE
    SYNTAX        Unsigned32 (0..86400)
    MAX-ACCESS    read-write
    STATUS        current
    DESCRIPTION   "ODU Tandem Connection Monitoring C Errored Seconds 1 Day Threshold"
    ::= { facilityDataThresholdEntry 26 }

facilityDataThresholdSESTcmcHT15min OBJECT-TYPE
    SYNTAX        Unsigned32 (0..900)
    MAX-ACCESS    read-write
    STATUS        current
    DESCRIPTION   "Tandem Connection Monitor C Section Severely Errored Seconds 15 Minute Threshold"
    ::= { facilityDataThresholdEntry 27 }

facilityDataThresholdSESTcmcHT1day OBJECT-TYPE
    SYNTAX        Unsigned32 (0..86400)
    MAX-ACCESS    read-write
    STATUS        current
    DESCRIPTION   "Tandem Connection Monitor C Section Severely Errored Seconds 1 Day Threshold"
    ::= { facilityDataThresholdEntry 28 }

facilityDataThresholdBBETcmcHT15min OBJECT-TYPE
    SYNTAX        Counter64String
    MAX-ACCESS    read-write
    STATUS        current
    DESCRIPTION   "ODU Tandem Connection C Background Block Errors 15 Minute Threshold"
    ::= { facilityDataThresholdEntry 29 }

facilityDataThresholdBBETcmcHT1day OBJECT-TYPE
    SYNTAX        Counter64String
    MAX-ACCESS    read-write
    STATUS        current
    DESCRIPTION   "ODU Tandem Connection C Background Block Errors 1 Day Threshold"
    ::= { facilityDataThresholdEntry 30 }

facilityDataThresholdUASTcmcHT15min OBJECT-TYPE
    SYNTAX        Unsigned32 (0..900)
    MAX-ACCESS    read-write
    STATUS        current
    DESCRIPTION   "ODU Tandem Connection Monitoring C Unavailable Seconds 15 Minute Threshold"
    ::= { facilityDataThresholdEntry 31 }

facilityDataThresholdUASTcmcHT1day OBJECT-TYPE
    SYNTAX        Unsigned32 (0..86400)
    MAX-ACCESS    read-write
    STATUS        current
    DESCRIPTION   "ODU Tandem Connection Monitoring C Unavailable Seconds 1 Day Threshold"
    ::= { facilityDataThresholdEntry 32 }

facilityDataThresholdESOtuHT15min OBJECT-TYPE
    SYNTAX        Unsigned32 (0..900)
    MAX-ACCESS    read-write
    STATUS        current
    DESCRIPTION   "OTU Errored Seconds 15 Minute Threshold"
    ::= { facilityDataThresholdEntry 33 }

facilityDataThresholdESOtuHT1day OBJECT-TYPE
    SYNTAX        Unsigned32 (0..86400)
    MAX-ACCESS    read-write
    STATUS        current
    DESCRIPTION   "OTU Errored Seconds 1 Day Threshold"
    ::= { facilityDataThresholdEntry 34 }

facilityDataThresholdSESOtuHT15min OBJECT-TYPE
    SYNTAX        Unsigned32 (0..900)
    MAX-ACCESS    read-write
    STATUS        current
    DESCRIPTION   "OTU Severely Errored Seconds 15 Minute Threshold"
    ::= { facilityDataThresholdEntry 35 }

facilityDataThresholdSESOtuHT1day OBJECT-TYPE
    SYNTAX        Unsigned32 (0..86400)
    MAX-ACCESS    read-write
    STATUS        current
    DESCRIPTION   "OTU Severely Errored Seconds 1 Day Threshold"
    ::= { facilityDataThresholdEntry 36 }

facilityDataThresholdBBEOtuHT15min OBJECT-TYPE
    SYNTAX        Counter64String
    MAX-ACCESS    read-write
    STATUS        current
    DESCRIPTION   "OTU Background Block Errors 15 Minute Threshold"
    ::= { facilityDataThresholdEntry 37 }

facilityDataThresholdBBEOtuHT1day OBJECT-TYPE
    SYNTAX        Counter64String
    MAX-ACCESS    read-write
    STATUS        current
    DESCRIPTION   "OTU Background Block Errors 1 Day Threshold"
    ::= { facilityDataThresholdEntry 38 }

facilityDataThresholdUASOtuHT15min OBJECT-TYPE
    SYNTAX        Unsigned32 (0..900)
    MAX-ACCESS    read-write
    STATUS        current
    DESCRIPTION   "OTU Unavailable Seconds 15 Minute Threshold"
    ::= { facilityDataThresholdEntry 39 }

facilityDataThresholdUASOtuHT1day OBJECT-TYPE
    SYNTAX        Unsigned32 (0..86400)
    MAX-ACCESS    read-write
    STATUS        current
    DESCRIPTION   "OTU Unavailable Seconds 1 Day Threshold"
    ::= { facilityDataThresholdEntry 40 }

facilityDataThresholdESFecHT15min OBJECT-TYPE
    SYNTAX        Unsigned32 (0..900)
    MAX-ACCESS    read-write
    STATUS        current
    DESCRIPTION   "OTU FEC Errored Seconds 15 Minute Threshold"
    ::= { facilityDataThresholdEntry 41 }

facilityDataThresholdESFecHT1day OBJECT-TYPE
    SYNTAX        Unsigned32 (0..86400)
    MAX-ACCESS    read-write
    STATUS        current
    DESCRIPTION   "OTU FEC Errored Seconds Day Threshold"
    ::= { facilityDataThresholdEntry 42 }

facilityDataThresholdSESFecHT15min OBJECT-TYPE
    SYNTAX        Unsigned32 (0..900)
    MAX-ACCESS    read-write
    STATUS        current
    DESCRIPTION   "OTU FEC Severely Errored Seconds 15 Minute Threshold"
    ::= { facilityDataThresholdEntry 43 }

facilityDataThresholdSESFecHT1day OBJECT-TYPE
    SYNTAX        Unsigned32 (0..86400)
    MAX-ACCESS    read-write
    STATUS        current
    DESCRIPTION   "OTU FEC Severely Errored Seconds 1 Day Threshold"
    ::= { facilityDataThresholdEntry 44 }

facilityDataThresholdUBEFecHT15min OBJECT-TYPE
    SYNTAX        Counter64String
    MAX-ACCESS    read-write
    STATUS        current
    DESCRIPTION   "Uncorrected Block Errors 15 Minute Threshold"
    ::= { facilityDataThresholdEntry 45 }

facilityDataThresholdUBEFecHT1day OBJECT-TYPE
    SYNTAX        Counter64String
    MAX-ACCESS    read-write
    STATUS        current
    DESCRIPTION   "Uncorrected Block Errors 1 Day Threshold"
    ::= { facilityDataThresholdEntry 46 }

facilityDataThresholdCEFecHT15min OBJECT-TYPE
    SYNTAX        Counter64String
    MAX-ACCESS    read-write
    STATUS        current
    DESCRIPTION   "FEC Corrected Errors 15 Minute Threshold"
    ::= { facilityDataThresholdEntry 47 }

facilityDataThresholdCEFecHT1day OBJECT-TYPE
    SYNTAX        Counter64String
    MAX-ACCESS    read-write
    STATUS        current
    DESCRIPTION   "FEC Corrected Errors 1 Day Threshold"
    ::= { facilityDataThresholdEntry 48 }

facilityDataThresholdBERCEFecHT15min OBJECT-TYPE
    SYNTAX        Counter64String
    UNITS         "1.0E-18"
    MAX-ACCESS    read-write
    STATUS        current
    DESCRIPTION   "Bit Error Rate before FEC 15 Minute Threshold"
    ::= { facilityDataThresholdEntry 49 }

facilityDataThresholdBERCEFecHT1day OBJECT-TYPE
    SYNTAX        Counter64String
    UNITS         "1.0E-18"
    MAX-ACCESS    read-write
    STATUS        current
    DESCRIPTION   "Bit Error Rate before FEC 1 Day Threshold"
    ::= { facilityDataThresholdEntry 50 }

facilityDataThresholdESPcsHT15min OBJECT-TYPE
    SYNTAX        Unsigned32 (0..900)
    MAX-ACCESS    read-write
    STATUS        current
    DESCRIPTION   "Physical Coding Layer Errored Seconds 15 Minute Threshold"
    ::= { facilityDataThresholdEntry 51 }

facilityDataThresholdESPcsHT1day OBJECT-TYPE
    SYNTAX        Unsigned32 (0..89400)
    MAX-ACCESS    read-write
    STATUS        current
    DESCRIPTION   "Physical Coding Layer Errored Seconds 1 Day Threshold"
    ::= { facilityDataThresholdEntry 52 }

facilityDataThresholdDEPcsHT15min OBJECT-TYPE
    SYNTAX        Unsigned32
    MAX-ACCESS    read-write
    STATUS        current
    DESCRIPTION   "Physical Coding Layer Disparity Errors 15 Minute Threshold"
    ::= { facilityDataThresholdEntry 53 }

facilityDataThresholdDEPcsHT1day OBJECT-TYPE
    SYNTAX        Unsigned32
    MAX-ACCESS    read-write
    STATUS        current
    DESCRIPTION   "Physical Coding Layer Disparity Errors 1 Day Threshold"
    ::= { facilityDataThresholdEntry 54 }

facilityDataThresholdCVPcsHT15min OBJECT-TYPE
    SYNTAX        Counter64String
    MAX-ACCESS    read-write
    STATUS        current
    DESCRIPTION   "Physical Coding Layer 15 Minute Threshold"
    ::= { facilityDataThresholdEntry 55 }

facilityDataThresholdCVPcsHT1day OBJECT-TYPE
    SYNTAX        Counter64String
    MAX-ACCESS    read-write
    STATUS        current
    DESCRIPTION   "Physical Coding Layer Coding Violations 1 Day Threshold"
    ::= { facilityDataThresholdEntry 56 }

facilityDataThresholdESLHT15min OBJECT-TYPE
    SYNTAX        Unsigned32 (0..900)
    MAX-ACCESS    read-write
    STATUS        current
    DESCRIPTION   "Line / Multiplex Section Errored Seconds 15 Minute Threshold"
    ::= { facilityDataThresholdEntry 57 }

facilityDataThresholdESLHT1day OBJECT-TYPE
    SYNTAX        Unsigned32 (0..86400)
    MAX-ACCESS    read-write
    STATUS        current
    DESCRIPTION   "Line / Multiplex Section Errored Seconds 1 Day Threshold"
    ::= { facilityDataThresholdEntry 58 }

facilityDataThresholdSESLHT15min OBJECT-TYPE
    SYNTAX        Unsigned32 (0..900)
    MAX-ACCESS    read-write
    STATUS        current
    DESCRIPTION   "Line / Multiplex Section Severely Errored Seconds 15 Minute Threshold"
    ::= { facilityDataThresholdEntry 59 }

facilityDataThresholdSESLHT1day OBJECT-TYPE
    SYNTAX        Unsigned32 (0..86400)
    MAX-ACCESS    read-write
    STATUS        current
    DESCRIPTION   "Line / Multiplex Section Severely Errored Seconds 1 Day Threshold"
    ::= { facilityDataThresholdEntry 60 }

facilityDataThresholdUASLHT15min OBJECT-TYPE
    SYNTAX        Unsigned32 (0..900)
    MAX-ACCESS    read-write
    STATUS        current
    DESCRIPTION   "Line / Multiplex Section Unavailable Seconds 15 Minute Threshold"
    ::= { facilityDataThresholdEntry 61 }

facilityDataThresholdUASLHT1day OBJECT-TYPE
    SYNTAX        Unsigned32 (0..86400)
    MAX-ACCESS    read-write
    STATUS        current
    DESCRIPTION   "Line / Multiplex Section Unavailable Seconds 1 Day Threshold"
    ::= { facilityDataThresholdEntry 62 }

facilityDataThresholdCVLHT15min OBJECT-TYPE
    SYNTAX        Counter64String
    MAX-ACCESS    read-write
    STATUS        current
    DESCRIPTION   "Line / Multiplex Section Coding Violations 15 Minute Threshold"
    ::= { facilityDataThresholdEntry 63 }

facilityDataThresholdCVLHT1day OBJECT-TYPE
    SYNTAX        Counter64String
    MAX-ACCESS    read-write
    STATUS        current
    DESCRIPTION   "Line / Multiplex Section Coding Violations 1 Day Threshold"
    ::= { facilityDataThresholdEntry 64 }

facilityDataThresholdESSHT15min OBJECT-TYPE
    SYNTAX        Unsigned32 (0..900)
    MAX-ACCESS    read-write
    STATUS        current
    DESCRIPTION   "Section / Regeneration Section Errored Seconds 15 Minute Threshold"
    ::= { facilityDataThresholdEntry 65 }

facilityDataThresholdESSHT1day OBJECT-TYPE
    SYNTAX        Unsigned32 (0..86400)
    MAX-ACCESS    read-write
    STATUS        current
    DESCRIPTION   "Section / Regeneration Section Errored Seconds 1 Day Threshold"
    ::= { facilityDataThresholdEntry 66 }

facilityDataThresholdSESSHT15min OBJECT-TYPE
    SYNTAX        Unsigned32 (0..900)
    MAX-ACCESS    read-write
    STATUS        current
    DESCRIPTION   "Section / Regenerator Section Severely Errored Seconds 15 Minute Threshold"
    ::= { facilityDataThresholdEntry 67 }

facilityDataThresholdSESSHT1day OBJECT-TYPE
    SYNTAX        Unsigned32 (0..86400)
    MAX-ACCESS    read-write
    STATUS        current
    DESCRIPTION   "Section / Regenerator Section Severely Errored Seconds 1 Day Threshold"
    ::= { facilityDataThresholdEntry 68 }

facilityDataThresholdSEFSSHT15min OBJECT-TYPE
    SYNTAX        Unsigned32 (0..900)
    MAX-ACCESS    read-write
    STATUS        current
    DESCRIPTION   "Section Severely Errored Frame Seconds 15 Minute Threshold"
    ::= { facilityDataThresholdEntry 69 }

facilityDataThresholdSEFSSHT1day OBJECT-TYPE
    SYNTAX        Unsigned32 (0..86400)
    MAX-ACCESS    read-write
    STATUS        current
    DESCRIPTION   "Section Severely Errored Frame Seconds 1 Day Threshold"
    ::= { facilityDataThresholdEntry 70 }

facilityDataThresholdCVSHT15min OBJECT-TYPE
    SYNTAX        Counter64String
    MAX-ACCESS    read-write
    STATUS        current
    DESCRIPTION   "Section / Regenerator Section Coding Violations 15 Minute Threshold"
    ::= { facilityDataThresholdEntry 71 }

facilityDataThresholdCVSHT1day OBJECT-TYPE
    SYNTAX        Counter64String
    MAX-ACCESS    read-write
    STATUS        current
    DESCRIPTION   "Section / Regenerator Section Coding Violations 1 Day Threshold"
    ::= { facilityDataThresholdEntry 72 }

facilityDataThresholdBBEPcsHT15min OBJECT-TYPE
    SYNTAX        Counter64String
    MAX-ACCESS    read-write
    STATUS        current
    DESCRIPTION   "PCS Background Block Errors 15 Minute Threshold"
    ::= { facilityDataThresholdEntry 73 }

facilityDataThresholdBBEPcsHT1day OBJECT-TYPE
    SYNTAX        Counter64String
    MAX-ACCESS    read-write
    STATUS        current
    DESCRIPTION   "PCS Background Block Errors 1 Day Threshold"
    ::= { facilityDataThresholdEntry 74 }

facilityDataThresholdCVDEPcsHT15min OBJECT-TYPE
    SYNTAX        Counter64String
    MAX-ACCESS    read-write
    STATUS        current
    DESCRIPTION   "Physical Coding Layer Coding Violations + Disparity Errors 15 Minute Threshold"
    ::= { facilityDataThresholdEntry 75 }

facilityDataThresholdCVDEPcsHT1day OBJECT-TYPE
    SYNTAX        Counter64String
    MAX-ACCESS    read-write
    STATUS        current
    DESCRIPTION   "Physical Coding Layer Coding Violations + Disparity Errors 1 Day Threshold"
    ::= { facilityDataThresholdEntry 76 }

facilityDataThresholdSEPcsHT15min OBJECT-TYPE
    SYNTAX        Unsigned32 (0..900)
    MAX-ACCESS    read-write
    STATUS        current
    DESCRIPTION   "Physical Coding Layer Sync Header Errors 15 Minute Threshold"
    ::= { facilityDataThresholdEntry 77 }

facilityDataThresholdSEPcsHT1day OBJECT-TYPE
    SYNTAX        Unsigned32 (0..86400)
    MAX-ACCESS    read-write
    STATUS        current
    DESCRIPTION   "Physical Coding Layer Sync Header Errors 1 Day Threshold"
    ::= { facilityDataThresholdEntry 78 }

facilityDataThresholdCRCFrRcvHT15min OBJECT-TYPE
    SYNTAX        Unsigned32 (0..900)
    MAX-ACCESS    read-write
    STATUS        current
    DESCRIPTION   "Received CRC Errors 15 Minute Threshold"
    ::= { facilityDataThresholdEntry 79 }

facilityDataThresholdCRCFrRcvHT1day OBJECT-TYPE
    SYNTAX        Unsigned32 (0..86400)
    MAX-ACCESS    read-write
    STATUS        current
    DESCRIPTION   "Received CRC Errors 1 Day Threshold"
    ::= { facilityDataThresholdEntry 80 }

facilityDataThresholdCRCFrEgrsHT15min OBJECT-TYPE
    SYNTAX        Unsigned32 (0..900)
    MAX-ACCESS    read-write
    STATUS        current
    DESCRIPTION   "Egress CRC Errored Frames Received 15 Minute Threshold"
    ::= { facilityDataThresholdEntry 81 }

facilityDataThresholdCRCFrEgrsHT1day OBJECT-TYPE
    SYNTAX        Unsigned32 (0..86400)
    MAX-ACCESS    read-write
    STATUS        current
    DESCRIPTION   "Egress CRC Errored Frames Received 1 Day Threshold"
    ::= { facilityDataThresholdEntry 82 }

facilityDataThresholdBBESHT15min OBJECT-TYPE
    SYNTAX        Counter64String
    MAX-ACCESS    read-write
    STATUS        current
    DESCRIPTION   "Section/RS Background Block Errors 15 Minute Threshold"
    ::= { facilityDataThresholdEntry 83 }

facilityDataThresholdBBESHT1day OBJECT-TYPE
    SYNTAX        Counter64String
    MAX-ACCESS    read-write
    STATUS        current
    DESCRIPTION   "Section/RS Background Block Errors 1 Day Threshold"
    ::= { facilityDataThresholdEntry 84 }

facilityDataThresholdBBELHT15min OBJECT-TYPE
    SYNTAX        Counter64String
    MAX-ACCESS    read-write
    STATUS        current
    DESCRIPTION   "Line/MS Background Block Errors 15 Minute Threshold"
    ::= { facilityDataThresholdEntry 85 }

facilityDataThresholdBBELHT1day OBJECT-TYPE
    SYNTAX        Counter64String
    MAX-ACCESS    read-write
    STATUS        current
    DESCRIPTION   "Line/MS Background Block Errors 1 Day Threshold"
    ::= { facilityDataThresholdEntry 86 }

facilityDataThresholdOOFSSHT15min OBJECT-TYPE
    SYNTAX        Unsigned32 (0..900)
    MAX-ACCESS    read-write
    STATUS        current
    DESCRIPTION   "Section/RS Out-Of-Frame Seconds 15 Min Threshold"
    ::= { facilityDataThresholdEntry 87 }

facilityDataThresholdOOFSSHT1day OBJECT-TYPE
    SYNTAX        Unsigned32 (0..86400)
    MAX-ACCESS    read-write
    STATUS        current
    DESCRIPTION   "Section/RS Out-Of-Frame Seconds 1-Day Threshold"
    ::= { facilityDataThresholdEntry 88 }

endOfFacilityDataThresholdTable OBJECT-TYPE
    SYNTAX        Integer32
    MAX-ACCESS    read-only
    STATUS        current
    DESCRIPTION   ""
    ::= { pmFacilityDataThreshold 2 }

endOfPmFacilityDataThreshold OBJECT-TYPE
    SYNTAX        Integer32
    MAX-ACCESS    read-only
    STATUS        current
    DESCRIPTION   ""
    ::= { pmFacilityDataThreshold 10000 }

oduFacilityCurrent15minTable OBJECT-TYPE
    SYNTAX        SEQUENCE OF OduFacilityCurrent15minEntry
    MAX-ACCESS    not-accessible
    STATUS        current
    DESCRIPTION   ""
    ::= { pmFacilityDataRecord 1 }

oduFacilityCurrent15minEntry OBJECT-TYPE
    SYNTAX        OduFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { oduFacilityCurrent15minTable 1 }

OduFacilityCurrent15minEntry ::= SEQUENCE
  {    oduFacilityCurrent15minES Unsigned32,
    oduFacilityCurrent15minSES Unsigned32,
    oduFacilityCurrent15minBbe Counter64String,
    oduFacilityCurrent15minUAS Unsigned32,
    oduFacilityCurrent15minElapsedTime Integer32 }

oduFacilityCurrent15minES OBJECT-TYPE
    SYNTAX        Unsigned32
    MAX-ACCESS    read-only
    STATUS        current
    DESCRIPTION   "ODU Errored Seconds"
    ::= { oduFacilityCurrent15minEntry 1 }

oduFacilityCurrent15minSES OBJECT-TYPE
    SYNTAX        Unsigned32
    MAX-ACCESS    read-only
    STATUS        current
    DESCRIPTION   "ODU Severely Errored Seconds"
    ::= { oduFacilityCurrent15minEntry 2 }

oduFacilityCurrent15minBbe OBJECT-TYPE
    SYNTAX        Counter64String
    MAX-ACCESS    read-only
    STATUS        current
    DESCRIPTION   "ODU Background Block Errors"
    ::= { oduFacilityCurrent15minEntry 3 }

oduFacilityCurrent15minUAS OBJECT-TYPE
    SYNTAX        Unsigned32
    MAX-ACCESS    read-only
    STATUS        current
    DESCRIPTION   "ODU Unavailable Seconds"
    ::= { oduFacilityCurrent15minEntry 4 }

oduFacilityCurrent15minElapsedTime OBJECT-TYPE
    SYNTAX        Integer32 (0..9000)
    MAX-ACCESS    read-only
    STATUS        current
    DESCRIPTION   "Elapsed 15Min"
    ::= { oduFacilityCurrent15minEntry 5 }

endOfOduFacilityCurrent15minTable OBJECT-TYPE
    SYNTAX        Integer32
    MAX-ACCESS    read-only
    STATUS        current
    DESCRIPTION   ""
    ::= { pmFacilityDataRecord 2 }

oduFacilityCurrent1dayTable OBJECT-TYPE
    SYNTAX        SEQUENCE OF OduFacilityCurrent1dayEntry
    MAX-ACCESS    not-accessible
    STATUS        current
    DESCRIPTION   ""
    ::= { pmFacilityDataRecord 3 }

oduFacilityCurrent1dayEntry OBJECT-TYPE
    SYNTAX        OduFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { oduFacilityCurrent1dayTable 1 }

OduFacilityCurrent1dayEntry ::= SEQUENCE
  {    oduFacilityCurrent1dayES Unsigned32,
    oduFacilityCurrent1daySES Unsigned32,
    oduFacilityCurrent1dayBbe Counter64String,
    oduFacilityCurrent1dayUAS Unsigned32,
    oduFacilityCurrent1dayElapsedTime Integer32 }

oduFacilityCurrent1dayES OBJECT-TYPE
    SYNTAX        Unsigned32
    MAX-ACCESS    read-only
    STATUS        current
    DESCRIPTION   "ODU Errored Seconds"
    ::= { oduFacilityCurrent1dayEntry 1 }

oduFacilityCurrent1daySES OBJECT-TYPE
    SYNTAX        Unsigned32
    MAX-ACCESS    read-only
    STATUS        current
    DESCRIPTION   "ODU Severely Errored Seconds"
    ::= { oduFacilityCurrent1dayEntry 2 }

oduFacilityCurrent1dayBbe OBJECT-TYPE
    SYNTAX        Counter64String
    MAX-ACCESS    read-only
    STATUS        current
    DESCRIPTION   "ODU Background Block Errors"
    ::= { oduFacilityCurrent1dayEntry 3 }

oduFacilityCurrent1dayUAS OBJECT-TYPE
    SYNTAX        Unsigned32
    MAX-ACCESS    read-only
    STATUS        current
    DESCRIPTION   "ODU Unavailable Seconds"
    ::= { oduFacilityCurrent1dayEntry 4 }

oduFacilityCurrent1dayElapsedTime OBJECT-TYPE
    SYNTAX        Integer32 (0..86400)
    MAX-ACCESS    read-only
    STATUS        current
    DESCRIPTION   "Elapsed 1Day"
    ::= { oduFacilityCurrent1dayEntry 5 }

endOfOduFacilityCurrent1dayTable OBJECT-TYPE
    SYNTAX        Integer32
    MAX-ACCESS    read-only
    STATUS        current
    DESCRIPTION   ""
    ::= { pmFacilityDataRecord 4 }

oduFacilityHistorical15minTable OBJECT-TYPE
    SYNTAX        SEQUENCE OF OduFacilityHistorical15minEntry
    MAX-ACCESS    not-accessible
    STATUS        current
    DESCRIPTION   ""
    ::= { pmFacilityDataRecord 5 }

oduFacilityHistorical15minEntry OBJECT-TYPE
    SYNTAX        OduFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  oduFacilityHistorical15minNumber
                }
    ::= { oduFacilityHistorical15minTable 1 }

OduFacilityHistorical15minEntry ::= SEQUENCE
  {    oduFacilityHistorical15minNumber Integer32,
    oduFacilityHistorical15minES Unsigned32,
    oduFacilityHistorical15minSES Unsigned32,
    oduFacilityHistorical15minBbe Counter64String,
    oduFacilityHistorical15minUAS Unsigned32,
    oduFacilityHistorical15minValidFlag TruthValue,
    oduFacilityHistorical15minTimeStamp DateAndTime }

oduFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oduFacilityHistorical15minEntry 1 }

oduFacilityHistorical15minES OBJECT-TYPE
    SYNTAX        Unsigned32
    MAX-ACCESS    read-only
    STATUS        current
    DESCRIPTION   "ODU Errored Seconds"
    ::= { oduFacilityHistorical15minEntry 2 }

oduFacilityHistorical15minSES OBJECT-TYPE
    SYNTAX        Unsigned32
    MAX-ACCESS    read-only
    STATUS        current
    DESCRIPTION   "ODU Severely Errored Seconds"
    ::= { oduFacilityHistorical15minEntry 3 }

oduFacilityHistorical15minBbe OBJECT-TYPE
    SYNTAX        Counter64String
    MAX-ACCESS    read-only
    STATUS        current
    DESCRIPTION   "ODU Background Block Errors"
    ::= { oduFacilityHistorical15minEntry 4 }

oduFacilityHistorical15minUAS OBJECT-TYPE
    SYNTAX        Unsigned32
    MAX-ACCESS    read-only
    STATUS        current
    DESCRIPTION   "ODU Unavailable Seconds"
    ::= { oduFacilityHistorical15minEntry 5 }

oduFacilityHistorical15minValidFlag OBJECT-TYPE
    SYNTAX        TruthValue
    MAX-ACCESS    read-only
    STATUS        current
    DESCRIPTION   "Valid Flag"
    ::= { oduFacilityHistorical15minEntry 6 }

oduFacilityHistorical15minTimeStamp OBJECT-TYPE
    SYNTAX        DateAndTime
    MAX-ACCESS    read-only
    STATUS        current
    DESCRIPTION   "Timestamp"
    ::= { oduFacilityHistorical15minEntry 7 }

endOfOduFacilityHistorical15minTable OBJECT-TYPE
    SYNTAX        Integer32
    MAX-ACCESS    read-only
    STATUS        current
    DESCRIPTION   ""
    ::= { pmFacilityDataRecord 6 }

oduFacilityHistorical1dayTable OBJECT-TYPE
    SYNTAX        SEQUENCE OF OduFacilityHistorical1dayEntry
    MAX-ACCESS    not-accessible
    STATUS        current
    DESCRIPTION   ""
    ::= { pmFacilityDataRecord 7 }

oduFacilityHistorical1dayEntry OBJECT-TYPE
    SYNTAX        OduFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  oduFacilityHistorical1dayNumber
                }
    ::= { oduFacilityHistorical1dayTable 1 }

OduFacilityHistorical1dayEntry ::= SEQUENCE
  {    oduFacilityHistorical1dayNumber Integer32,
    oduFacilityHistorical1dayES Unsigned32,
    oduFacilityHistorical1daySES Unsigned32,
    oduFacilityHistorical1dayBbe Counter64String,
    oduFacilityHistorical1dayUAS Unsigned32,
    oduFacilityHistorical1dayValidFlag TruthValue,
    oduFacilityHistorical1dayTimeStamp DateAndTime }

oduFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oduFacilityHistorical1dayEntry 1 }

oduFacilityHistorical1dayES OBJECT-TYPE
    SYNTAX        Unsigned32
    MAX-ACCESS    read-only
    STATUS        current
    DESCRIPTION   "ODU Errored Seconds"
    ::= { oduFacilityHistorical1dayEntry 2 }

oduFacilityHistorical1daySES OBJECT-TYPE
    SYNTAX        Unsigned32
    MAX-ACCESS    read-only
    STATUS        current
    DESCRIPTION   "ODU Severely Errored Seconds"
    ::= { oduFacilityHistorical1dayEntry 3 }

oduFacilityHistorical1dayBbe OBJECT-TYPE
    SYNTAX        Counter64String
    MAX-ACCESS    read-only
    STATUS        current
    DESCRIPTION   "ODU Background Block Errors"
    ::= { oduFacilityHistorical1dayEntry 4 }

oduFacilityHistorical1dayUAS OBJECT-TYPE
    SYNTAX        Unsigned32
    MAX-ACCESS    read-only
    STATUS        current
    DESCRIPTION   "ODU Unavailable Seconds"
    ::= { oduFacilityHistorical1dayEntry 5 }

oduFacilityHistorical1dayValidFlag OBJECT-TYPE
    SYNTAX        TruthValue
    MAX-ACCESS    read-only
    STATUS        current
    DESCRIPTION   "Valid Flag"
    ::= { oduFacilityHistorical1dayEntry 6 }

oduFacilityHistorical1dayTimeStamp OBJECT-TYPE
    SYNTAX        DateAndTime
    MAX-ACCESS    read-only
    STATUS        current
    DESCRIPTION   "Timestamp"
    ::= { oduFacilityHistorical1dayEntry 7 }

endOfOduFacilityHistorical1dayTable OBJECT-TYPE
    SYNTAX        Integer32
    MAX-ACCESS    read-only
    STATUS        current
    DESCRIPTION   ""
    ::= { pmFacilityDataRecord 8 }

tcmAFacilityCurrent15minTable OBJECT-TYPE
    SYNTAX        SEQUENCE OF TcmAFacilityCurrent15minEntry
    MAX-ACCESS    not-accessible
    STATUS        current
    DESCRIPTION   ""
    ::= { pmFacilityDataRecord 9 }

tcmAFacilityCurrent15minEntry OBJECT-TYPE
    SYNTAX        TcmAFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmAFacilityCurrent15minTable 1 }

TcmAFacilityCurrent15minEntry ::= SEQUENCE
  {    tcmAFacilityCurrent15minES Unsigned32,
    tcmAFacilityCurrent15minSES Unsigned32,
    tcmAFacilityCurrent15minBbe Counter64String,
    tcmAFacilityCurrent15minUAS Unsigned32,
    tcmAFacilityCurrent15minElapsedTime Integer32 }

tcmAFacilityCurrent15minES OBJECT-TYPE
    SYNTAX        Unsigned32
    MAX-ACCESS    read-only
    STATUS        current
    DESCRIPTION   "ODU Tandem Connection Monitoring A Errored Seconds"
    ::= { tcmAFacilityCurrent15minEntry 1 }

tcmAFacilityCurrent15minSES OBJECT-TYPE
    SYNTAX        Unsigned32
    MAX-ACCESS    read-only
    STATUS        current
    DESCRIPTION   "ODU Tandem Connection Monitoring A Severely Errored Seconds"
    ::= { tcmAFacilityCurrent15minEntry 2 }

tcmAFacilityCurrent15minBbe OBJECT-TYPE
    SYNTAX        Counter64String
    MAX-ACCESS    read-only
    STATUS        current
    DESCRIPTION   "ODU Tandem Connection Monitoring A Background Block Errors"
    ::= { tcmAFacilityCurrent15minEntry 3 }

tcmAFacilityCurrent15minUAS OBJECT-TYPE
    SYNTAX        Unsigned32
    MAX-ACCESS    read-only
    STATUS        current
    DESCRIPTION   "ODU Tandem Connection Monitoring A Unavailable Seconds"
    ::= { tcmAFacilityCurrent15minEntry 4 }

tcmAFacilityCurrent15minElapsedTime OBJECT-TYPE
    SYNTAX        Integer32 (0..9000)
    MAX-ACCESS    read-only
    STATUS        current
    DESCRIPTION   "Elapsed 15Min"
    ::= { tcmAFacilityCurrent15minEntry 5 }

endOfTcmAFacilityCurrent15minTable OBJECT-TYPE
    SYNTAX        Integer32
    MAX-ACCESS    read-only
    STATUS        current
    DESCRIPTION   ""
    ::= { pmFacilityDataRecord 10 }

tcmAFacilityCurrent1dayTable OBJECT-TYPE
    SYNTAX        SEQUENCE OF TcmAFacilityCurrent1dayEntry
    MAX-ACCESS    not-accessible
    STATUS        current
    DESCRIPTION   ""
    ::= { pmFacilityDataRecord 11 }

tcmAFacilityCurrent1dayEntry OBJECT-TYPE
    SYNTAX        TcmAFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmAFacilityCurrent1dayTable 1 }

TcmAFacilityCurrent1dayEntry ::= SEQUENCE
  {    tcmAFacilityCurrent1dayES Unsigned32,
    tcmAFacilityCurrent1daySES Unsigned32,
    tcmAFacilityCurrent1dayBbe Counter64String,
    tcmAFacilityCurrent1dayUAS Unsigned32,
    tcmAFacilityCurrent1dayElapsedTime Integer32 }

tcmAFacilityCurrent1dayES OBJECT-TYPE
    SYNTAX        Unsigned32
    MAX-ACCESS    read-only
    STATUS        current
    DESCRIPTION   "ODU Tandem Connection Monitoring A Errored Seconds"
    ::= { tcmAFacilityCurrent1dayEntry 1 }

tcmAFacilityCurrent1daySES OBJECT-TYPE
    SYNTAX        Unsigned32
    MAX-ACCESS    read-only
    STATUS        current
    DESCRIPTION   "ODU Tandem Connection Monitoring A Severely Errored Seconds"
    ::= { tcmAFacilityCurrent1dayEntry 2 }

tcmAFacilityCurrent1dayBbe OBJECT-TYPE
    SYNTAX        Counter64String
    MAX-ACCESS    read-only
    STATUS        current
    DESCRIPTION   "ODU Tandem Connection Monitoring A Background Block Errors"
    ::= { tcmAFacilityCurrent1dayEntry 3 }

tcmAFacilityCurrent1dayUAS OBJECT-TYPE
    SYNTAX        Unsigned32
    MAX-ACCESS    read-only
    STATUS        current
    DESCRIPTION   "ODU Tandem Connection Monitoring A Unavailable Seconds"
    ::= { tcmAFacilityCurrent1dayEntry 4 }

tcmAFacilityCurrent1dayElapsedTime OBJECT-TYPE
    SYNTAX        Integer32 (0..86400)
    MAX-ACCESS    read-only
    STATUS        current
    DESCRIPTION   "Elapsed 1Day"
    ::= { tcmAFacilityCurrent1dayEntry 5 }

endOfTcmAFacilityCurrent1dayTable OBJECT-TYPE
    SYNTAX        Integer32
    MAX-ACCESS    read-only
    STATUS        current
    DESCRIPTION   ""
    ::= { pmFacilityDataRecord 12 }

tcmAFacilityHistorical15minTable OBJECT-TYPE
    SYNTAX        SEQUENCE OF TcmAFacilityHistorical15minEntry
    MAX-ACCESS    not-accessible
    STATUS        current
    DESCRIPTION   ""
    ::= { pmFacilityDataRecord 13 }

tcmAFacilityHistorical15minEntry OBJECT-TYPE
    SYNTAX        TcmAFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  tcmAFacilityHistorical15minNumber
                }
    ::= { tcmAFacilityHistorical15minTable 1 }

TcmAFacilityHistorical15minEntry ::= SEQUENCE
  {    tcmAFacilityHistorical15minNumber Integer32,
    tcmAFacilityHistorical15minES Unsigned32,
    tcmAFacilityHistorical15minSES Unsigned32,
    tcmAFacilityHistorical15minBbe Counter64String,
    tcmAFacilityHistorical15minUAS Unsigned32,
    tcmAFacilityHistorical15minValidFlag TruthValue,
    tcmAFacilityHistorical15minTimeStamp DateAndTime }

tcmAFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { tcmAFacilityHistorical15minEntry 1 }

tcmAFacilityHistorical15minES OBJECT-TYPE
    SYNTAX        Unsigned32
    MAX-ACCESS    read-only
    STATUS        current
    DESCRIPTION   "ODU Tandem Connection Monitoring A Errored Seconds"
    ::= { tcmAFacilityHistorical15minEntry 2 }

tcmAFacilityHistorical15minSES OBJECT-TYPE
    SYNTAX        Unsigned32
    MAX-ACCESS    read-only
    STATUS        current
    DESCRIPTION   "ODU Tandem Connection Monitoring A Severely Errored Seconds"
    ::= { tcmAFacilityHistorical15minEntry 3 }

tcmAFacilityHistorical15minBbe OBJECT-TYPE
    SYNTAX        Counter64String
    MAX-ACCESS    read-only
    STATUS        current
    DESCRIPTION   "ODU Tandem Connection Monitoring A Background Block Errors"
    ::= { tcmAFacilityHistorical15minEntry 4 }

tcmAFacilityHistorical15minUAS OBJECT-TYPE
    SYNTAX        Unsigned32
    MAX-ACCESS    read-only
    STATUS        current
    DESCRIPTION   "ODU Tandem Connection Monitoring A Unavailable Seconds"
    ::= { tcmAFacilityHistorical15minEntry 5 }

tcmAFacilityHistorical15minValidFlag OBJECT-TYPE
    SYNTAX        TruthValue
    MAX-ACCESS    read-only
    STATUS        current
    DESCRIPTION   "Valid Flag"
    ::= { tcmAFacilityHistorical15minEntry 6 }

tcmAFacilityHistorical15minTimeStamp OBJECT-TYPE
    SYNTAX        DateAndTime
    MAX-ACCESS    read-only
    STATUS        current
    DESCRIPTION   "Timestamp"
    ::= { tcmAFacilityHistorical15minEntry 7 }

endOfTcmAFacilityHistorical15minTable OBJECT-TYPE
    SYNTAX        Integer32
    MAX-ACCESS    read-only
    STATUS        current
    DESCRIPTION   ""
    ::= { pmFacilityDataRecord 14 }

tcmAFacilityHistorical1dayTable OBJECT-TYPE
    SYNTAX        SEQUENCE OF TcmAFacilityHistorical1dayEntry
    MAX-ACCESS    not-accessible
    STATUS        current
    DESCRIPTION   ""
    ::= { pmFacilityDataRecord 15 }

tcmAFacilityHistorical1dayEntry OBJECT-TYPE
    SYNTAX        TcmAFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  oduFacilityHistorical1dayNumber
                }
    ::= { tcmAFacilityHistorical1dayTable 1 }

TcmAFacilityHistorical1dayEntry ::= SEQUENCE
  {    tcmAFacilityHistorical1dayNumber Integer32,
    tcmAFacilityHistorical1dayES Unsigned32,
    tcmAFacilityHistorical1daySES Unsigned32,
    tcmAFacilityHistorical1dayBbe Counter64String,
    tcmAFacilityHistorical1dayUAS Unsigned32,
    tcmAFacilityHistorical1dayValidFlag TruthValue,
    tcmAFacilityHistorical1dayTimeStamp DateAndTime }

tcmAFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { tcmAFacilityHistorical1dayEntry 1 }

tcmAFacilityHistorical1dayES OBJECT-TYPE
    SYNTAX        Unsigned32
    MAX-ACCESS    read-only
    STATUS        current
    DESCRIPTION   "ODU Tandem Connection Monitoring A Errored Seconds"
    ::= { tcmAFacilityHistorical1dayEntry 2 }

tcmAFacilityHistorical1daySES OBJECT-TYPE
    SYNTAX        Unsigned32
    MAX-ACCESS    read-only
    STATUS        current
    DESCRIPTION   "ODU Tandem Connection Monitoring A Severely Errored Seconds"
    ::= { tcmAFacilityHistorical1dayEntry 3 }

tcmAFacilityHistorical1dayBbe OBJECT-TYPE
    SYNTAX        Counter64String
    MAX-ACCESS    read-only
    STATUS        current
    DESCRIPTION   "ODU Tandem Connection Monitoring A Background Block Errors"
    ::= { tcmAFacilityHistorical1dayEntry 4 }

tcmAFacilityHistorical1dayUAS OBJECT-TYPE
    SYNTAX        Unsigned32
    MAX-ACCESS    read-only
    STATUS        current
    DESCRIPTION   "ODU Tandem Connection Monitoring A Unavailable Seconds"
    ::= { tcmAFacilityHistorical1dayEntry 5 }

tcmAFacilityHistorical1dayValidFlag OBJECT-TYPE
    SYNTAX        TruthValue
    MAX-ACCESS    read-only
    STATUS        current
    DESCRIPTION   "Valid Flag"
    ::= { tcmAFacilityHistorical1dayEntry 6 }

tcmAFacilityHistorical1dayTimeStamp OBJECT-TYPE
    SYNTAX        DateAndTime
    MAX-ACCESS    read-only
    STATUS        current
    DESCRIPTION   "Timestamp"
    ::= { tcmAFacilityHistorical1dayEntry 7 }

endOfTcmAFacilityHistorical1dayTable OBJECT-TYPE
    SYNTAX        Integer32
    MAX-ACCESS    read-only
    STATUS        current
    DESCRIPTION   ""
    ::= { pmFacilityDataRecord 16 }

tcmBFacilityCurrent15minTable OBJECT-TYPE
    SYNTAX        SEQUENCE OF TcmBFacilityCurrent15minEntry
    MAX-ACCESS    not-accessible
    STATUS        current
    DESCRIPTION   ""
    ::= { pmFacilityDataRecord 17 }

tcmBFacilityCurrent15minEntry OBJECT-TYPE
    SYNTAX        TcmBFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmBFacilityCurrent15minTable 1 }

TcmBFacilityCurrent15minEntry ::= SEQUENCE
  {    tcmBFacilityCurrent15minES Unsigned32,
    tcmBFacilityCurrent15minSES Unsigned32,
    tcmBFacilityCurrent15minBbe Counter64String,
    tcmBFacilityCurrent15minUAS Unsigned32,
    tcmBFacilityCurrent15minElapsedTime Integer32 }

tcmBFacilityCurrent15minES OBJECT-TYPE
    SYNTAX        Unsigned32
    MAX-ACCESS    read-only
    STATUS        current
    DESCRIPTION   "ODU Tandem Connection Monitoring B Errored Seconds"
    ::= { tcmBFacilityCurrent15minEntry 1 }

tcmBFacilityCurrent15minSES OBJECT-TYPE
    SYNTAX        Unsigned32
    MAX-ACCESS    read-only
    STATUS        current
    DESCRIPTION   "ODU Tandem Connection Monitoring B Severely Errored Seconds"
    ::= { tcmBFacilityCurrent15minEntry 2 }

tcmBFacilityCurrent15minBbe OBJECT-TYPE
    SYNTAX        Counter64String
    MAX-ACCESS    read-only
    STATUS        current
    DESCRIPTION   "ODU Tandem Connection Monitoring B Background Block Errors"
    ::= { tcmBFacilityCurrent15minEntry 3 }

tcmBFacilityCurrent15minUAS OBJECT-TYPE
    SYNTAX        Unsigned32
    MAX-ACCESS    read-only
    STATUS        current
    DESCRIPTION   "ODU Tandem Connection Monitoring B Unavailable Seconds"
    ::= { tcmBFacilityCurrent15minEntry 4 }

tcmBFacilityCurrent15minElapsedTime OBJECT-TYPE
    SYNTAX        Integer32 (0..9000)
    MAX-ACCESS    read-only
    STATUS        current
    DESCRIPTION   "Elapsed 15Min"
    ::= { tcmBFacilityCurrent15minEntry 5 }

endOfTcmBFacilityCurrent15minTable OBJECT-TYPE
    SYNTAX        Integer32
    MAX-ACCESS    read-only
    STATUS        current
    DESCRIPTION   ""
    ::= { pmFacilityDataRecord 18 }

tcmBFacilityCurrent1dayTable OBJECT-TYPE
    SYNTAX        SEQUENCE OF TcmBFacilityCurrent1dayEntry
    MAX-ACCESS    not-accessible
    STATUS        current
    DESCRIPTION   ""
    ::= { pmFacilityDataRecord 19 }

tcmBFacilityCurrent1dayEntry OBJECT-TYPE
    SYNTAX        TcmBFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmBFacilityCurrent1dayTable 1 }

TcmBFacilityCurrent1dayEntry ::= SEQUENCE
  {    tcmBFacilityCurrent1dayES Unsigned32,
    tcmBFacilityCurrent1daySES Unsigned32,
    tcmBFacilityCurrent1dayBbe Counter64String,
    tcmBFacilityCurrent1dayUAS Unsigned32,
    tcmBFacilityCurrent1dayElapsedTime Integer32 }

tcmBFacilityCurrent1dayES OBJECT-TYPE
    SYNTAX        Unsigned32
    MAX-ACCESS    read-only
    STATUS        current
    DESCRIPTION   "ODU Tandem Connection Monitoring B Errored Seconds"
    ::= { tcmBFacilityCurrent1dayEntry 1 }

tcmBFacilityCurrent1daySES OBJECT-TYPE
    SYNTAX        Unsigned32
    MAX-ACCESS    read-only
    STATUS        current
    DESCRIPTION   "ODU Tandem Connection Monitoring B Severely Errored Seconds"
    ::= { tcmBFacilityCurrent1dayEntry 2 }

tcmBFacilityCurrent1dayBbe OBJECT-TYPE
    SYNTAX        Counter64String
    MAX-ACCESS    read-only
    STATUS        current
    DESCRIPTION   "ODU Tandem Connection Monitoring B Background Block Errors"
    ::= { tcmBFacilityCurrent1dayEntry 3 }

tcmBFacilityCurrent1dayUAS OBJECT-TYPE
    SYNTAX        Unsigned32
    MAX-ACCESS    read-only
    STATUS        current
    DESCRIPTION   "ODU Tandem Connection Monitoring B Unavailable Seconds"
    ::= { tcmBFacilityCurrent1dayEntry 4 }

tcmBFacilityCurrent1dayElapsedTime OBJECT-TYPE
    SYNTAX        Integer32 (0..86400)
    MAX-ACCESS    read-only
    STATUS        current
    DESCRIPTION   "Elapsed 1Day"
    ::= { tcmBFacilityCurrent1dayEntry 5 }

endOfTcmBFacilityCurrent1dayTable OBJECT-TYPE
    SYNTAX        Integer32
    MAX-ACCESS    read-only
    STATUS        current
    DESCRIPTION   ""
    ::= { pmFacilityDataRecord 20 }

tcmBFacilityHistorical15minTable OBJECT-TYPE
    SYNTAX        SEQUENCE OF TcmBFacilityHistorical15minEntry
    MAX-ACCESS    not-accessible
    STATUS        current
    DESCRIPTION   ""
    ::= { pmFacilityDataRecord 21 }

tcmBFacilityHistorical15minEntry OBJECT-TYPE
    SYNTAX        TcmBFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  tcmBFacilityHistorical15minNumber
                }
    ::= { tcmBFacilityHistorical15minTable 1 }

TcmBFacilityHistorical15minEntry ::= SEQUENCE
  {    tcmBFacilityHistorical15minNumber Integer32,
    tcmBFacilityHistorical15minES Unsigned32,
    tcmBFacilityHistorical15minSES Unsigned32,
    tcmBFacilityHistorical15minBbe Counter64String,
    tcmBFacilityHistorical15minUAS Unsigned32,
    tcmBFacilityHistorical15minValidFlag TruthValue,
    tcmBFacilityHistorical15minTimeStamp DateAndTime }

tcmBFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { tcmBFacilityHistorical15minEntry 1 }

tcmBFacilityHistorical15minES OBJECT-TYPE
    SYNTAX        Unsigned32
    MAX-ACCESS    read-only
    STATUS        current
    DESCRIPTION   "ODU Tandem Connection Monitoring B Errored Seconds"
    ::= { tcmBFacilityHistorical15minEntry 2 }

tcmBFacilityHistorical15minSES OBJECT-TYPE
    SYNTAX        Unsigned32
    MAX-ACCESS    read-only
    STATUS        current
    DESCRIPTION   "ODU Tandem Connection Monitoring B Severely Errored Seconds"
    ::= { tcmBFacilityHistorical15minEntry 3 }

tcmBFacilityHistorical15minBbe OBJECT-TYPE
    SYNTAX        Counter64String
    MAX-ACCESS    read-only
    STATUS        current
    DESCRIPTION   "ODU Tandem Connection Monitoring B Background Block Errors"
    ::= { tcmBFacilityHistorical15minEntry 4 }

tcmBFacilityHistorical15minUAS OBJECT-TYPE
    SYNTAX        Unsigned32
    MAX-ACCESS    read-only
    STATUS        current
    DESCRIPTION   "ODU Tandem Connection Monitoring B Unavailable Seconds"
    ::= { tcmBFacilityHistorical15minEntry 5 }

tcmBFacilityHistorical15minValidFlag OBJECT-TYPE
    SYNTAX        TruthValue
    MAX-ACCESS    read-only
    STATUS        current
    DESCRIPTION   "Valid Flag"
    ::= { tcmBFacilityHistorical15minEntry 6 }

tcmBFacilityHistorical15minTimeStamp OBJECT-TYPE
    SYNTAX        DateAndTime
    MAX-ACCESS    read-only
    STATUS        current
    DESCRIPTION   "Timestamp"
    ::= { tcmBFacilityHistorical15minEntry 7 }

endOfTcmBFacilityHistorical15minTable OBJECT-TYPE
    SYNTAX        Integer32
    MAX-ACCESS    read-only
    STATUS        current
    DESCRIPTION   ""
    ::= { pmFacilityDataRecord 22 }

tcmBFacilityHistorical1dayTable OBJECT-TYPE
    SYNTAX        SEQUENCE OF TcmBFacilityHistorical1dayEntry
    MAX-ACCESS    not-accessible
    STATUS        current
    DESCRIPTION   ""
    ::= { pmFacilityDataRecord 23 }

tcmBFacilityHistorical1dayEntry OBJECT-TYPE
    SYNTAX        TcmBFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  tcmBFacilityHistorical1dayNumber
                }
    ::= { tcmBFacilityHistorical1dayTable 1 }

TcmBFacilityHistorical1dayEntry ::= SEQUENCE
  {    tcmBFacilityHistorical1dayNumber Integer32,
    tcmBFacilityHistorical1dayES Unsigned32,
    tcmBFacilityHistorical1daySES Unsigned32,
    tcmBFacilityHistorical1dayBbe Counter64String,
    tcmBFacilityHistorical1dayUAS Unsigned32,
    tcmBFacilityHistorical1dayValidFlag TruthValue,
    tcmBFacilityHistorical1dayTimeStamp DateAndTime }

tcmBFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { tcmBFacilityHistorical1dayEntry 1 }

tcmBFacilityHistorical1dayES OBJECT-TYPE
    SYNTAX        Unsigned32
    MAX-ACCESS    read-only
    STATUS        current
    DESCRIPTION   "ODU Tandem Connection Monitoring B Errored Seconds"
    ::= { tcmBFacilityHistorical1dayEntry 2 }

tcmBFacilityHistorical1daySES OBJECT-TYPE
    SYNTAX        Unsigned32
    MAX-ACCESS    read-only
    STATUS        current
    DESCRIPTION   "ODU Tandem Connection Monitoring B Severely Errored Seconds"
    ::= { tcmBFacilityHistorical1dayEntry 3 }

tcmBFacilityHistorical1dayBbe OBJECT-TYPE
    SYNTAX        Counter64String
    MAX-ACCESS    read-only
    STATUS        current
    DESCRIPTION   "ODU Tandem Connection Monitoring B Background Block Errors"
    ::= { tcmBFacilityHistorical1dayEntry 4 }

tcmBFacilityHistorical1dayUAS OBJECT-TYPE
    SYNTAX        Unsigned32
    MAX-ACCESS    read-only
    STATUS        current
    DESCRIPTION   "ODU Tandem Connection Monitoring B Unavailable Seconds"
    ::= { tcmBFacilityHistorical1dayEntry 5 }

tcmBFacilityHistorical1dayValidFlag OBJECT-TYPE
    SYNTAX        TruthValue
    MAX-ACCESS    read-only
    STATUS        current
    DESCRIPTION   "Valid Flag"
    ::= { tcmBFacilityHistorical1dayEntry 6 }

tcmBFacilityHistorical1dayTimeStamp OBJECT-TYPE
    SYNTAX        DateAndTime
    MAX-ACCESS    read-only
    STATUS        current
    DESCRIPTION   "Timestamp"
    ::= { tcmBFacilityHistorical1dayEntry 7 }

endOfTcmBFacilityHistorical1dayTable OBJECT-TYPE
    SYNTAX        Integer32
    MAX-ACCESS    read-only
    STATUS        current
    DESCRIPTION   ""
    ::= { pmFacilityDataRecord 24 }

tcmCFacilityCurrent15minTable OBJECT-TYPE
    SYNTAX        SEQUENCE OF TcmCFacilityCurrent15minEntry
    MAX-ACCESS    not-accessible
    STATUS        current
    DESCRIPTION   ""
    ::= { pmFacilityDataRecord 25 }

tcmCFacilityCurrent15minEntry OBJECT-TYPE
    SYNTAX        TcmCFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmCFacilityCurrent15minTable 1 }

TcmCFacilityCurrent15minEntry ::= SEQUENCE
  {    tcmCFacilityCurrent15minES Unsigned32,
    tcmCFacilityCurrent15minSES Unsigned32,
    tcmCFacilityCurrent15minBbe Counter64String,
    tcmCFacilityCurrent15minUAS Unsigned32,
    tcmCFacilityCurrent15minElapsedTime Integer32 }

tcmCFacilityCurrent15minES OBJECT-TYPE
    SYNTAX        Unsigned32
    MAX-ACCESS    read-only
    STATUS        current
    DESCRIPTION   "ODU Tandem Connection Monitoring C Errored Seconds"
    ::= { tcmCFacilityCurrent15minEntry 1 }

tcmCFacilityCurrent15minSES OBJECT-TYPE
    SYNTAX        Unsigned32
    MAX-ACCESS    read-only
    STATUS        current
    DESCRIPTION   "ODU Tandem Connection Monitoring C Severely Errored Seconds"
    ::= { tcmCFacilityCurrent15minEntry 2 }

tcmCFacilityCurrent15minBbe OBJECT-TYPE
    SYNTAX        Counter64String
    MAX-ACCESS    read-only
    STATUS        current
    DESCRIPTION   "ODU Tandem Connection Monitoring C Background Block Errors"
    ::= { tcmCFacilityCurrent15minEntry 3 }

tcmCFacilityCurrent15minUAS OBJECT-TYPE
    SYNTAX        Unsigned32
    MAX-ACCESS    read-only
    STATUS        current
    DESCRIPTION   "ODU Tandem Connection Monitoring C Unavailable Seconds"
    ::= { tcmCFacilityCurrent15minEntry 4 }

tcmCFacilityCurrent15minElapsedTime OBJECT-TYPE
    SYNTAX        Integer32 (0..9000)
    MAX-ACCESS    read-only
    STATUS        current
    DESCRIPTION   "Elapsed 15Min"
    ::= { tcmCFacilityCurrent15minEntry 5 }

endOfTcmCFacilityCurrent15minTable OBJECT-TYPE
    SYNTAX        Integer32
    MAX-ACCESS    read-only
    STATUS        current
    DESCRIPTION   ""
    ::= { pmFacilityDataRecord 26 }

tcmCFacilityCurrent1dayTable OBJECT-TYPE
    SYNTAX        SEQUENCE OF TcmCFacilityCurrent1dayEntry
    MAX-ACCESS    not-accessible
    STATUS        current
    DESCRIPTION   ""
    ::= { pmFacilityDataRecord 27 }

tcmCFacilityCurrent1dayEntry OBJECT-TYPE
    SYNTAX        TcmCFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmCFacilityCurrent1dayTable 1 }

TcmCFacilityCurrent1dayEntry ::= SEQUENCE
  {    tcmCFacilityCurrent1dayES Unsigned32,
    tcmCFacilityCurrent1daySES Unsigned32,
    tcmCFacilityCurrent1dayBbe Counter64String,
    tcmCFacilityCurrent1dayUAS Unsigned32,
    tcmCFacilityCurrent1dayElapsedTime Integer32 }

tcmCFacilityCurrent1dayES OBJECT-TYPE
    SYNTAX        Unsigned32
    MAX-ACCESS    read-only
    STATUS        current
    DESCRIPTION   "ODU Tandem Connection Monitoring C Errored Seconds"
    ::= { tcmCFacilityCurrent1dayEntry 1 }

tcmCFacilityCurrent1daySES OBJECT-TYPE
    SYNTAX        Unsigned32
    MAX-ACCESS    read-only
    STATUS        current
    DESCRIPTION   "ODU Tandem Connection Monitoring C Severely Errored Seconds"
    ::= { tcmCFacilityCurrent1dayEntry 2 }

tcmCFacilityCurrent1dayBbe OBJECT-TYPE
    SYNTAX        Counter64String
    MAX-ACCESS    read-only
    STATUS        current
    DESCRIPTION   "ODU Tandem Connection Monitoring C Background Block Errors"
    ::= { tcmCFacilityCurrent1dayEntry 3 }

tcmCFacilityCurrent1dayUAS OBJECT-TYPE
    SYNTAX        Unsigned32
    MAX-ACCESS    read-only
    STATUS        current
    DESCRIPTION   "ODU Tandem Connection Monitoring C Unavailable Seconds"
    ::= { tcmCFacilityCurrent1dayEntry 4 }

tcmCFacilityCurrent1dayElapsedTime OBJECT-TYPE
    SYNTAX        Integer32 (0..86400)
    MAX-ACCESS    read-only
    STATUS        current
    DESCRIPTION   "Elapsed 1Day"
    ::= { tcmCFacilityCurrent1dayEntry 5 }

endOfTcmCFacilityCurrent1dayTable OBJECT-TYPE
    SYNTAX        Integer32
    MAX-ACCESS    read-only
    STATUS        current
    DESCRIPTION   ""
    ::= { pmFacilityDataRecord 28 }

tcmCFacilityHistorical15minTable OBJECT-TYPE
    SYNTAX        SEQUENCE OF TcmCFacilityHistorical15minEntry
    MAX-ACCESS    not-accessible
    STATUS        current
    DESCRIPTION   ""
    ::= { pmFacilityDataRecord 29 }

tcmCFacilityHistorical15minEntry OBJECT-TYPE
    SYNTAX        TcmCFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  tcmCFacilityHistorical15minNumber
                }
    ::= { tcmCFacilityHistorical15minTable 1 }

TcmCFacilityHistorical15minEntry ::= SEQUENCE
  {    tcmCFacilityHistorical15minNumber Integer32,
    tcmCFacilityHistorical15minES Unsigned32,
    tcmCFacilityHistorical15minSES Unsigned32,
    tcmCFacilityHistorical15minBbe Counter64String,
    tcmCFacilityHistorical15minUAS Unsigned32,
    tcmCFacilityHistorical15minValidFlag TruthValue,
    tcmCFacilityHistorical15minTimeStamp DateAndTime }

tcmCFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { tcmCFacilityHistorical15minEntry 1 }

tcmCFacilityHistorical15minES OBJECT-TYPE
    SYNTAX        Unsigned32
    MAX-ACCESS    read-only
    STATUS        current
    DESCRIPTION   "ODU Tandem Connection Monitoring C Errored Seconds"
    ::= { tcmCFacilityHistorical15minEntry 2 }

tcmCFacilityHistorical15minSES OBJECT-TYPE
    SYNTAX        Unsigned32
    MAX-ACCESS    read-only
    STATUS        current
    DESCRIPTION   "ODU Tandem Connection Monitoring C Severely Errored Seconds"
    ::= { tcmCFacilityHistorical15minEntry 3 }

tcmCFacilityHistorical15minBbe OBJECT-TYPE
    SYNTAX        Counter64String
    MAX-ACCESS    read-only
    STATUS        current
    DESCRIPTION   "ODU Tandem Connection Monitoring C Background Block Errors"
    ::= { tcmCFacilityHistorical15minEntry 4 }

tcmCFacilityHistorical15minUAS OBJECT-TYPE
    SYNTAX        Unsigned32
    MAX-ACCESS    read-only
    STATUS        current
    DESCRIPTION   "ODU Tandem Connection Monitoring C Unavailable Seconds"
    ::= { tcmCFacilityHistorical15minEntry 5 }

tcmCFacilityHistorical15minValidFlag OBJECT-TYPE
    SYNTAX        TruthValue
    MAX-ACCESS    read-only
    STATUS        current
    DESCRIPTION   "Valid Flag"
    ::= { tcmCFacilityHistorical15minEntry 6 }

tcmCFacilityHistorical15minTimeStamp OBJECT-TYPE
    SYNTAX        DateAndTime
    MAX-ACCESS    read-only
    STATUS        current
    DESCRIPTION   "Timestamp"
    ::= { tcmCFacilityHistorical15minEntry 7 }

endOfTcmCFacilityHistorical15minTable OBJECT-TYPE
    SYNTAX        Integer32
    MAX-ACCESS    read-only
    STATUS        current
    DESCRIPTION   ""
    ::= { pmFacilityDataRecord 30 }

tcmCFacilityHistorical1dayTable OBJECT-TYPE
    SYNTAX        SEQUENCE OF TcmCFacilityHistorical1dayEntry
    MAX-ACCESS    not-accessible
    STATUS        current
    DESCRIPTION   ""
    ::= { pmFacilityDataRecord 31 }

tcmCFacilityHistorical1dayEntry OBJECT-TYPE
    SYNTAX        TcmCFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  tcmCFacilityHistorical1dayNumber
                }
    ::= { tcmCFacilityHistorical1dayTable 1 }

TcmCFacilityHistorical1dayEntry ::= SEQUENCE
  {    tcmCFacilityHistorical1dayNumber Integer32,
    tcmCFacilityHistorical1dayES Unsigned32,
    tcmCFacilityHistorical1daySES Unsigned32,
    tcmCFacilityHistorical1dayBbe Counter64String,
    tcmCFacilityHistorical1dayUAS Unsigned32,
    tcmCFacilityHistorical1dayValidFlag TruthValue,
    tcmCFacilityHistorical1dayTimeStamp DateAndTime }

tcmCFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { tcmCFacilityHistorical1dayEntry 1 }

tcmCFacilityHistorical1dayES OBJECT-TYPE
    SYNTAX        Unsigned32
    MAX-ACCESS    read-only
    STATUS        current
    DESCRIPTION   "ODU Tandem Connection Monitoring C Errored Seconds"
    ::= { tcmCFacilityHistorical1dayEntry 2 }

tcmCFacilityHistorical1daySES OBJECT-TYPE
    SYNTAX        Unsigned32
    MAX-ACCESS    read-only
    STATUS        current
    DESCRIPTION   "ODU Tandem Connection Monitoring C Severely Errored Seconds"
    ::= { tcmCFacilityHistorical1dayEntry 3 }

tcmCFacilityHistorical1dayBbe OBJECT-TYPE
    SYNTAX        Counter64String
    MAX-ACCESS    read-only
    STATUS        current
    DESCRIPTION   "ODU Tandem Connection Monitoring C Background Block Errors"
    ::= { tcmCFacilityHistorical1dayEntry 4 }

tcmCFacilityHistorical1dayUAS OBJECT-TYPE
    SYNTAX        Unsigned32
    MAX-ACCESS    read-only
    STATUS        current
    DESCRIPTION   "ODU Tandem Connection Monitoring C Unavailable Seconds"
    ::= { tcmCFacilityHistorical1dayEntry 5 }

tcmCFacilityHistorical1dayValidFlag OBJECT-TYPE
    SYNTAX        TruthValue
    MAX-ACCESS    read-only
    STATUS        current
    DESCRIPTION   "Valid Flag"
    ::= { tcmCFacilityHistorical1dayEntry 6 }

tcmCFacilityHistorical1dayTimeStamp OBJECT-TYPE
    SYNTAX        DateAndTime
    MAX-ACCESS    read-only
    STATUS        current
    DESCRIPTION   "Timestamp"
    ::= { tcmCFacilityHistorical1dayEntry 7 }

endOfTcmCFacilityHistorical1dayTable OBJECT-TYPE
    SYNTAX        Integer32
    MAX-ACCESS    read-only
    STATUS        current
    DESCRIPTION   ""
    ::= { pmFacilityDataRecord 32 }

otuFacilityCurrent15minTable OBJECT-TYPE
    SYNTAX        SEQUENCE OF OtuFacilityCurrent15minEntry
    MAX-ACCESS    not-accessible
    STATUS        current
    DESCRIPTION   ""
    ::= { pmFacilityDataRecord 33 }

otuFacilityCurrent15minEntry OBJECT-TYPE
    SYNTAX        OtuFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { otuFacilityCurrent15minTable 1 }

OtuFacilityCurrent15minEntry ::= SEQUENCE
  {    otuFacilityCurrent15minES Unsigned32,
    otuFacilityCurrent15minSES Unsigned32,
    otuFacilityCurrent15minBbe Counter64String,
    otuFacilityCurrent15minUAS Unsigned32,
    otuFacilityCurrent15minElapsedTime Integer32 }

otuFacilityCurrent15minES OBJECT-TYPE
    SYNTAX        Unsigned32
    MAX-ACCESS    read-only
    STATUS        current
    DESCRIPTION   "OTU Errored Seconds"
    ::= { otuFacilityCurrent15minEntry 1 }

otuFacilityCurrent15minSES OBJECT-TYPE
    SYNTAX        Unsigned32
    MAX-ACCESS    read-only
    STATUS        current
    DESCRIPTION   "OTU Severely Errored Seconds"
    ::= { otuFacilityCurrent15minEntry 2 }

otuFacilityCurrent15minBbe OBJECT-TYPE
    SYNTAX        Counter64String
    MAX-ACCESS    read-only
    STATUS        current
    DESCRIPTION   "OTU Background Block Errors"
    ::= { otuFacilityCurrent15minEntry 3 }

otuFacilityCurrent15minUAS OBJECT-TYPE
    SYNTAX        Unsigned32
    MAX-ACCESS    read-only
    STATUS        current
    DESCRIPTION   "OTU Unavailable Seconds"
    ::= { otuFacilityCurrent15minEntry 4 }

otuFacilityCurrent15minElapsedTime OBJECT-TYPE
    SYNTAX        Integer32 (0..9000)
    MAX-ACCESS    read-only
    STATUS        current
    DESCRIPTION   "Elapsed 15Min"
    ::= { otuFacilityCurrent15minEntry 5 }

endOfOtuFacilityCurrent15minTable OBJECT-TYPE
    SYNTAX        Integer32
    MAX-ACCESS    read-only
    STATUS        current
    DESCRIPTION   ""
    ::= { pmFacilityDataRecord 34 }

otuFacilityCurrent1dayTable OBJECT-TYPE
    SYNTAX        SEQUENCE OF OtuFacilityCurrent1dayEntry
    MAX-ACCESS    not-accessible
    STATUS        current
    DESCRIPTION   ""
    ::= { pmFacilityDataRecord 35 }

otuFacilityCurrent1dayEntry OBJECT-TYPE
    SYNTAX        OtuFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { otuFacilityCurrent1dayTable 1 }

OtuFacilityCurrent1dayEntry ::= SEQUENCE
  {    otuFacilityCurrent1dayES Unsigned32,
    otuFacilityCurrent1daySES Unsigned32,
    otuFacilityCurrent1dayBbe Counter64String,
    otuFacilityCurrent1dayUAS Unsigned32,
    otuFacilityCurrent1dayElapsedTime Integer32 }

otuFacilityCurrent1dayES OBJECT-TYPE
    SYNTAX        Unsigned32
    MAX-ACCESS    read-only
    STATUS        current
    DESCRIPTION   "OTU Errored Seconds"
    ::= { otuFacilityCurrent1dayEntry 1 }

otuFacilityCurrent1daySES OBJECT-TYPE
    SYNTAX        Unsigned32
    MAX-ACCESS    read-only
    STATUS        current
    DESCRIPTION   "OTU Severely Errored Seconds"
    ::= { otuFacilityCurrent1dayEntry 2 }

otuFacilityCurrent1dayBbe OBJECT-TYPE
    SYNTAX        Counter64String
    MAX-ACCESS    read-only
    STATUS        current
    DESCRIPTION   "OTU Background Block Errors"
    ::= { otuFacilityCurrent1dayEntry 3 }

otuFacilityCurrent1dayUAS OBJECT-TYPE
    SYNTAX        Unsigned32
    MAX-ACCESS    read-only
    STATUS        current
    DESCRIPTION   "OTU Unavailable Seconds"
    ::= { otuFacilityCurrent1dayEntry 4 }

otuFacilityCurrent1dayElapsedTime OBJECT-TYPE
    SYNTAX        Integer32 (0..86400)
    MAX-ACCESS    read-only
    STATUS        current
    DESCRIPTION   "Elapsed 1Day"
    ::= { otuFacilityCurrent1dayEntry 5 }

endOfOtuFacilityCurrent1dayTable OBJECT-TYPE
    SYNTAX        Integer32
    MAX-ACCESS    read-only
    STATUS        current
    DESCRIPTION   ""
    ::= { pmFacilityDataRecord 36 }

otuFacilityHistorical15minTable OBJECT-TYPE
    SYNTAX        SEQUENCE OF OtuFacilityHistorical15minEntry
    MAX-ACCESS    not-accessible
    STATUS        current
    DESCRIPTION   ""
    ::= { pmFacilityDataRecord 37 }

otuFacilityHistorical15minEntry OBJECT-TYPE
    SYNTAX        OtuFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  otuFacilityHistorical15minNumber
                }
    ::= { otuFacilityHistorical15minTable 1 }

OtuFacilityHistorical15minEntry ::= SEQUENCE
  {    otuFacilityHistorical15minNumber Integer32,
    otuFacilityHistorical15minES Unsigned32,
    otuFacilityHistorical15minSES Unsigned32,
    otuFacilityHistorical15minBbe Counter64String,
    otuFacilityHistorical15minUAS Unsigned32,
    otuFacilityHistorical15minValidFlag TruthValue,
    otuFacilityHistorical15minTimeStamp DateAndTime }

otuFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { otuFacilityHistorical15minEntry 1 }

otuFacilityHistorical15minES OBJECT-TYPE
    SYNTAX        Unsigned32
    MAX-ACCESS    read-only
    STATUS        current
    DESCRIPTION   "OTU Errored Seconds"
    ::= { otuFacilityHistorical15minEntry 2 }

otuFacilityHistorical15minSES OBJECT-TYPE
    SYNTAX        Unsigned32
    MAX-ACCESS    read-only
    STATUS        current
    DESCRIPTION   "OTU Severely Errored Seconds"
    ::= { otuFacilityHistorical15minEntry 3 }

otuFacilityHistorical15minBbe OBJECT-TYPE
    SYNTAX        Counter64String
    MAX-ACCESS    read-only
    STATUS        current
    DESCRIPTION   "OTU Background Block Errors"
    ::= { otuFacilityHistorical15minEntry 4 }

otuFacilityHistorical15minUAS OBJECT-TYPE
    SYNTAX        Unsigned32
    MAX-ACCESS    read-only
    STATUS        current
    DESCRIPTION   "OTU Unavailable Seconds"
    ::= { otuFacilityHistorical15minEntry 5 }

otuFacilityHistorical15minValidFlag OBJECT-TYPE
    SYNTAX        TruthValue
    MAX-ACCESS    read-only
    STATUS        current
    DESCRIPTION   "Valid Flag"
    ::= { otuFacilityHistorical15minEntry 6 }

otuFacilityHistorical15minTimeStamp OBJECT-TYPE
    SYNTAX        DateAndTime
    MAX-ACCESS    read-only
    STATUS        current
    DESCRIPTION   "Timestamp"
    ::= { otuFacilityHistorical15minEntry 7 }

endOfOtuFacilityHistorical15minTable OBJECT-TYPE
    SYNTAX        Integer32
    MAX-ACCESS    read-only
    STATUS        current
    DESCRIPTION   ""
    ::= { pmFacilityDataRecord 38 }

otuFacilityHistorical1dayTable OBJECT-TYPE
    SYNTAX        SEQUENCE OF OtuFacilityHistorical1dayEntry
    MAX-ACCESS    not-accessible
    STATUS        current
    DESCRIPTION   ""
    ::= { pmFacilityDataRecord 39 }

otuFacilityHistorical1dayEntry OBJECT-TYPE
    SYNTAX        OtuFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  otuFacilityHistorical1dayNumber
                }
    ::= { otuFacilityHistorical1dayTable 1 }

OtuFacilityHistorical1dayEntry ::= SEQUENCE
  {    otuFacilityHistorical1dayNumber Integer32,
    otuFacilityHistorical1dayES Unsigned32,
    otuFacilityHistorical1daySES Unsigned32,
    otuFacilityHistorical1dayBbe Counter64String,
    otuFacilityHistorical1dayUAS Unsigned32,
    otuFacilityHistorical1dayValidFlag TruthValue,
    otuFacilityHistorical1dayTimeStamp DateAndTime }

otuFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { otuFacilityHistorical1dayEntry 1 }

otuFacilityHistorical1dayES OBJECT-TYPE
    SYNTAX        Unsigned32
    MAX-ACCESS    read-only
    STATUS        current
    DESCRIPTION   "OTU Errored Seconds"
    ::= { otuFacilityHistorical1dayEntry 2 }

otuFacilityHistorical1daySES OBJECT-TYPE
    SYNTAX        Unsigned32
    MAX-ACCESS    read-only
    STATUS        current
    DESCRIPTION   "OTU Severely Errored Seconds"
    ::= { otuFacilityHistorical1dayEntry 3 }

otuFacilityHistorical1dayBbe OBJECT-TYPE
    SYNTAX        Counter64String
    MAX-ACCESS    read-only
    STATUS        current
    DESCRIPTION   "OTU Background Block Errors"
    ::= { otuFacilityHistorical1dayEntry 4 }

otuFacilityHistorical1dayUAS OBJECT-TYPE
    SYNTAX        Unsigned32
    MAX-ACCESS    read-only
    STATUS        current
    DESCRIPTION   "OTU Unavailable Seconds"
    ::= { otuFacilityHistorical1dayEntry 5 }

otuFacilityHistorical1dayValidFlag OBJECT-TYPE
    SYNTAX        TruthValue
    MAX-ACCESS    read-only
    STATUS        current
    DESCRIPTION   "Valid Flag"
    ::= { otuFacilityHistorical1dayEntry 6 }

otuFacilityHistorical1dayTimeStamp OBJECT-TYPE
    SYNTAX        DateAndTime
    MAX-ACCESS    read-only
    STATUS        current
    DESCRIPTION   "Timestamp"
    ::= { otuFacilityHistorical1dayEntry 7 }

endOfOtuFacilityHistorical1dayTable OBJECT-TYPE
    SYNTAX        Integer32
    MAX-ACCESS    read-only
    STATUS        current
    DESCRIPTION   ""
    ::= { pmFacilityDataRecord 40 }

otuFecFacilityCurrent15minTable OBJECT-TYPE
    SYNTAX        SEQUENCE OF OtuFecFacilityCurrent15minEntry
    MAX-ACCESS    not-accessible
    STATUS        current
    DESCRIPTION   ""
    ::= { pmFacilityDataRecord 41 }

otuFecFacilityCurrent15minEntry OBJECT-TYPE
    SYNTAX        OtuFecFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { otuFecFacilityCurrent15minTable 1 }

OtuFecFacilityCurrent15minEntry ::= SEQUENCE
  {    otuFecFacilityCurrent15minES Unsigned32,
    otuFecFacilityCurrent15minSES Unsigned32,
    otuFecFacilityCurrent15minCE Counter64String,
    otuFecFacilityCurrent15minUBE Counter64String,
    otuFecFacilityCurrent15minBERCE Counter64String,
    otuFecFacilityCurrent15minElapsedTime Integer32 }

otuFecFacilityCurrent15minES OBJECT-TYPE
    SYNTAX        Unsigned32
    MAX-ACCESS    read-only
    STATUS        current
    DESCRIPTION   "OTU FEC Errored Seconds"
    ::= { otuFecFacilityCurrent15minEntry 1 }

otuFecFacilityCurrent15minSES OBJECT-TYPE
    SYNTAX        Unsigned32
    MAX-ACCESS    read-only
    STATUS        current
    DESCRIPTION   "OTU FEC Severely Errored Seconds"
    ::= { otuFecFacilityCurrent15minEntry 2 }

otuFecFacilityCurrent15minCE OBJECT-TYPE
    SYNTAX        Counter64String
    MAX-ACCESS    read-only
    STATUS        current
    DESCRIPTION   "OTU FEC Corrected Errors"
    ::= { otuFecFacilityCurrent15minEntry 3 }

otuFecFacilityCurrent15minUBE OBJECT-TYPE
    SYNTAX        Counter64String
    MAX-ACCESS    read-only
    STATUS        current
    DESCRIPTION   "OTU FEC Uncorrected Block Errors"
    ::= { otuFecFacilityCurrent15minEntry 4 }

otuFecFacilityCurrent15minBERCE OBJECT-TYPE
    SYNTAX        Counter64String
    UNITS         "1.0E-18"
    MAX-ACCESS    read-only
    STATUS        current
    DESCRIPTION   "Bit Error Rate before Foward Error Correction (FEC) calculated from corrected errors"
    ::= { otuFecFacilityCurrent15minEntry 5 }

otuFecFacilityCurrent15minElapsedTime OBJECT-TYPE
    SYNTAX        Integer32 (0..9000)
    MAX-ACCESS    read-only
    STATUS        current
    DESCRIPTION   "Elapsed 15Min"
    ::= { otuFecFacilityCurrent15minEntry 6 }

endOfOtuFecFacilityCurrent15minTable OBJECT-TYPE
    SYNTAX        Integer32
    MAX-ACCESS    read-only
    STATUS        current
    DESCRIPTION   ""
    ::= { pmFacilityDataRecord 42 }

otuFecFacilityCurrent1dayTable OBJECT-TYPE
    SYNTAX        SEQUENCE OF OtuFecFacilityCurrent1dayEntry
    MAX-ACCESS    not-accessible
    STATUS        current
    DESCRIPTION   ""
    ::= { pmFacilityDataRecord 43 }

otuFecFacilityCurrent1dayEntry OBJECT-TYPE
    SYNTAX        OtuFecFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { otuFecFacilityCurrent1dayTable 1 }

OtuFecFacilityCurrent1dayEntry ::= SEQUENCE
  {    otuFecFacilityCurrent1dayES Unsigned32,
    otuFecFacilityCurrent1daySES Unsigned32,
    otuFecFacilityCurrent1dayCE Counter64String,
    otuFecFacilityCurrent1dayUBE Counter64String,
    otuFecFacilityCurrent1dayBERCE Counter64String,
    otuFecFacilityCurrent1dayElapsedTime Integer32 }

otuFecFacilityCurrent1dayES OBJECT-TYPE
    SYNTAX        Unsigned32
    MAX-ACCESS    read-only
    STATUS        current
    DESCRIPTION   "OTU FEC Errored Seconds"
    ::= { otuFecFacilityCurrent1dayEntry 1 }

otuFecFacilityCurrent1daySES OBJECT-TYPE
    SYNTAX        Unsigned32
    MAX-ACCESS    read-only
    STATUS        current
    DESCRIPTION   "OTU FEC Severely Errored Seconds"
    ::= { otuFecFacilityCurrent1dayEntry 2 }

otuFecFacilityCurrent1dayCE OBJECT-TYPE
    SYNTAX        Counter64String
    MAX-ACCESS    read-only
    STATUS        current
    DESCRIPTION   "OTU FEC Corrected Errors"
    ::= { otuFecFacilityCurrent1dayEntry 3 }

otuFecFacilityCurrent1dayUBE OBJECT-TYPE
    SYNTAX        Counter64String
    MAX-ACCESS    read-only
    STATUS        current
    DESCRIPTION   "OTU FEC Uncorrected Block Errors"
    ::= { otuFecFacilityCurrent1dayEntry 4 }

otuFecFacilityCurrent1dayBERCE OBJECT-TYPE
    SYNTAX        Counter64String
    UNITS         "1.0E-18"
    MAX-ACCESS    read-only
    STATUS        current
    DESCRIPTION   "Bit Error Rate before Foward Error Correction (FEC) calculated from corrected errors"
    ::= { otuFecFacilityCurrent1dayEntry 5 }

otuFecFacilityCurrent1dayElapsedTime OBJECT-TYPE
    SYNTAX        Integer32 (0..86400)
    MAX-ACCESS    read-only
    STATUS        current
    DESCRIPTION   "Elapsed 1Day"
    ::= { otuFecFacilityCurrent1dayEntry 6 }

endOfOtuFecFacilityCurrent1dayTable OBJECT-TYPE
    SYNTAX        Integer32
    MAX-ACCESS    read-only
    STATUS        current
    DESCRIPTION   ""
    ::= { pmFacilityDataRecord 44 }

otuFecFacilityHistorical15minTable OBJECT-TYPE
    SYNTAX        SEQUENCE OF OtuFecFacilityHistorical15minEntry
    MAX-ACCESS    not-accessible
    STATUS        current
    DESCRIPTION   ""
    ::= { pmFacilityDataRecord 45 }

otuFecFacilityHistorical15minEntry OBJECT-TYPE
    SYNTAX        OtuFecFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  otuFecFacilityHistorical15minNumber
                }
    ::= { otuFecFacilityHistorical15minTable 1 }

OtuFecFacilityHistorical15minEntry ::= SEQUENCE
  {    otuFecFacilityHistorical15minNumber Integer32,
    otuFecFacilityHistorical15minES Unsigned32,
    otuFecFacilityHistorical15minSES Unsigned32,
    otuFecFacilityHistorical15minCE Counter64String,
    otuFecFacilityHistorical15minUBE Counter64String,
    otuFecFacilityHistorical15minBERCE Counter64String,
    otuFecFacilityHistorical15minValidFlag TruthValue,
    otuFecFacilityHistorical15minTimeStamp DateAndTime }

otuFecFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { otuFecFacilityHistorical15minEntry 1 }

otuFecFacilityHistorical15minES OBJECT-TYPE
    SYNTAX        Unsigned32
    MAX-ACCESS    read-only
    STATUS        current
    DESCRIPTION   "OTU FEC Errored Seconds"
    ::= { otuFecFacilityHistorical15minEntry 2 }

otuFecFacilityHistorical15minSES OBJECT-TYPE
    SYNTAX        Unsigned32
    MAX-ACCESS    read-only
    STATUS        current
    DESCRIPTION   "OTU FEC Severely Errored Seconds"
    ::= { otuFecFacilityHistorical15minEntry 3 }

otuFecFacilityHistorical15minCE OBJECT-TYPE
    SYNTAX        Counter64String
    MAX-ACCESS    read-only
    STATUS        current
    DESCRIPTION   "OTU FEC Corrected Errors"
    ::= { otuFecFacilityHistorical15minEntry 4 }

otuFecFacilityHistorical15minUBE OBJECT-TYPE
    SYNTAX        Counter64String
    MAX-ACCESS    read-only
    STATUS        current
    DESCRIPTION   "OTU FEC Uncorrected Block Errors"
    ::= { otuFecFacilityHistorical15minEntry 5 }

otuFecFacilityHistorical15minBERCE OBJECT-TYPE
    SYNTAX        Counter64String
    UNITS         "1.0E-18"
    MAX-ACCESS    read-only
    STATUS        current
    DESCRIPTION   "Bit Error Rate before Foward Error Correction (FEC) calculated from corrected errors"
    ::= { otuFecFacilityHistorical15minEntry 6 }

otuFecFacilityHistorical15minValidFlag OBJECT-TYPE
    SYNTAX        TruthValue
    MAX-ACCESS    read-only
    STATUS        current
    DESCRIPTION   "Valid Flag"
    ::= { otuFecFacilityHistorical15minEntry 7 }

otuFecFacilityHistorical15minTimeStamp OBJECT-TYPE
    SYNTAX        DateAndTime
    MAX-ACCESS    read-only
    STATUS        current
    DESCRIPTION   "Timestamp"
    ::= { otuFecFacilityHistorical15minEntry 8 }

endOfOtuFecFacilityHistorical15minTable OBJECT-TYPE
    SYNTAX        Integer32
    MAX-ACCESS    read-only
    STATUS        current
    DESCRIPTION   ""
    ::= { pmFacilityDataRecord 46 }

otuFecFacilityHistorical1dayTable OBJECT-TYPE
    SYNTAX        SEQUENCE OF OtuFecFacilityHistorical1dayEntry
    MAX-ACCESS    not-accessible
    STATUS        current
    DESCRIPTION   ""
    ::= { pmFacilityDataRecord 47 }

otuFecFacilityHistorical1dayEntry OBJECT-TYPE
    SYNTAX        OtuFecFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  otuFecFacilityHistorical1dayNumber
                }
    ::= { otuFecFacilityHistorical1dayTable 1 }

OtuFecFacilityHistorical1dayEntry ::= SEQUENCE
  {    otuFecFacilityHistorical1dayNumber Integer32,
    otuFecFacilityHistorical1dayES Unsigned32,
    otuFecFacilityHistorical1daySES Unsigned32,
    otuFecFacilityHistorical1dayCE Counter64String,
    otuFecFacilityHistorical1dayUBE Counter64String,
    otuFecFacilityHistorical1dayBERCE Counter64String,
    otuFecFacilityHistorical1dayValidFlag TruthValue,
    otuFecFacilityHistorical1dayTimeStamp DateAndTime }

otuFecFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { otuFecFacilityHistorical1dayEntry 1 }

otuFecFacilityHistorical1dayES OBJECT-TYPE
    SYNTAX        Unsigned32
    MAX-ACCESS    read-only
    STATUS        current
    DESCRIPTION   "OTU FEC Errored Seconds"
    ::= { otuFecFacilityHistorical1dayEntry 2 }

otuFecFacilityHistorical1daySES OBJECT-TYPE
    SYNTAX        Unsigned32
    MAX-ACCESS    read-only
    STATUS        current
    DESCRIPTION   "OTU FEC Severely Errored Seconds"
    ::= { otuFecFacilityHistorical1dayEntry 3 }

otuFecFacilityHistorical1dayCE OBJECT-TYPE
    SYNTAX        Counter64String
    MAX-ACCESS    read-only
    STATUS        current
    DESCRIPTION   "OTU FEC Corrected Errors"
    ::= { otuFecFacilityHistorical1dayEntry 4 }

otuFecFacilityHistorical1dayUBE OBJECT-TYPE
    SYNTAX        Counter64String
    MAX-ACCESS    read-only
    STATUS        current
    DESCRIPTION   "OTU FEC Uncorrected Block Errors"
    ::= { otuFecFacilityHistorical1dayEntry 5 }

otuFecFacilityHistorical1dayBERCE OBJECT-TYPE
    SYNTAX        Counter64String
    UNITS         "1.0E-18"
    MAX-ACCESS    read-only
    STATUS        current
    DESCRIPTION   "Bit Error Rate before Foward Error Correction (FEC) calculated from corrected errors"
    ::= { otuFecFacilityHistorical1dayEntry 6 }

otuFecFacilityHistorical1dayValidFlag OBJECT-TYPE
    SYNTAX        TruthValue
    MAX-ACCESS    read-only
    STATUS        current
    DESCRIPTION   "Valid Flag"
    ::= { otuFecFacilityHistorical1dayEntry 7 }

otuFecFacilityHistorical1dayTimeStamp OBJECT-TYPE
    SYNTAX        DateAndTime
    MAX-ACCESS    read-only
    STATUS        current
    DESCRIPTION   "Timestamp"
    ::= { otuFecFacilityHistorical1dayEntry 8 }

endOfOtuFecFacilityHistorical1dayTable OBJECT-TYPE
    SYNTAX        Integer32
    MAX-ACCESS    read-only
    STATUS        current
    DESCRIPTION   ""
    ::= { pmFacilityDataRecord 48 }

fecFacilityCurrent15minTable OBJECT-TYPE
    SYNTAX        SEQUENCE OF FecFacilityCurrent15minEntry
    MAX-ACCESS    not-accessible
    STATUS        current
    DESCRIPTION   ""
    ::= { pmFacilityDataRecord 49 }

fecFacilityCurrent15minEntry OBJECT-TYPE
    SYNTAX        FecFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { fecFacilityCurrent15minTable 1 }

FecFacilityCurrent15minEntry ::= SEQUENCE
  {    fecFacilityCurrent15minSES Unsigned32,
    fecFacilityCurrent15minCE Counter64String,
    fecFacilityCurrent15minUBE Counter64String,
    fecFacilityCurrent15minBERCE Counter64String,
    fecFacilityCurrent15minElapsedTime Integer32 }

fecFacilityCurrent15minSES OBJECT-TYPE
    SYNTAX        Unsigned32
    MAX-ACCESS    read-only
    STATUS        current
    DESCRIPTION   "Severely Errored Seconds FEC Monitoring for internal use"
    ::= { fecFacilityCurrent15minEntry 1 }

fecFacilityCurrent15minCE OBJECT-TYPE
    SYNTAX        Counter64String
    MAX-ACCESS    read-only
    STATUS        current
    DESCRIPTION   "OTU FEC Corrected Errors"
    ::= { fecFacilityCurrent15minEntry 2 }

fecFacilityCurrent15minUBE OBJECT-TYPE
    SYNTAX        Counter64String
    MAX-ACCESS    read-only
    STATUS        current
    DESCRIPTION   "OTU FEC Uncorrected Block Errors"
    ::= { fecFacilityCurrent15minEntry 3 }

fecFacilityCurrent15minBERCE OBJECT-TYPE
    SYNTAX        Counter64String
    UNITS         "1.0E-18"
    MAX-ACCESS    read-only
    STATUS        current
    DESCRIPTION   "Bit Error Rate before Foward Error Correction (FEC) calculated from corrected errors"
    ::= { fecFacilityCurrent15minEntry 4 }

fecFacilityCurrent15minElapsedTime OBJECT-TYPE
    SYNTAX        Integer32 (0..9000)
    MAX-ACCESS    read-only
    STATUS        current
    DESCRIPTION   "Elapsed 15Min"
    ::= { fecFacilityCurrent15minEntry 5 }

endOfFecFacilityCurrent15minTable OBJECT-TYPE
    SYNTAX        Integer32
    MAX-ACCESS    read-only
    STATUS        current
    DESCRIPTION   ""
    ::= { pmFacilityDataRecord 50 }

fecFacilityCurrent1dayTable OBJECT-TYPE
    SYNTAX        SEQUENCE OF FecFacilityCurrent1dayEntry
    MAX-ACCESS    not-accessible
    STATUS        current
    DESCRIPTION   ""
    ::= { pmFacilityDataRecord 51 }

fecFacilityCurrent1dayEntry OBJECT-TYPE
    SYNTAX        FecFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { fecFacilityCurrent1dayTable 1 }

FecFacilityCurrent1dayEntry ::= SEQUENCE
  {    fecFacilityCurrent1daySES Unsigned32,
    fecFacilityCurrent1dayCE Counter64String,
    fecFacilityCurrent1dayUBE Counter64String,
    fecFacilityCurrent1dayBERCE Counter64String,
    fecFacilityCurrent1dayElapsedTime Integer32 }

fecFacilityCurrent1daySES OBJECT-TYPE
    SYNTAX        Unsigned32
    MAX-ACCESS    read-only
    STATUS        current
    DESCRIPTION   "Severely Errored Seconds FEC Monitoring for internal use"
    ::= { fecFacilityCurrent1dayEntry 1 }

fecFacilityCurrent1dayCE OBJECT-TYPE
    SYNTAX        Counter64String
    MAX-ACCESS    read-only
    STATUS        current
    DESCRIPTION   "OTU FEC Corrected Errors"
    ::= { fecFacilityCurrent1dayEntry 2 }

fecFacilityCurrent1dayUBE OBJECT-TYPE
    SYNTAX        Counter64String
    MAX-ACCESS    read-only
    STATUS        current
    DESCRIPTION   "OTU FEC Uncorrected Block Errors"
    ::= { fecFacilityCurrent1dayEntry 3 }

fecFacilityCurrent1dayBERCE OBJECT-TYPE
    SYNTAX        Counter64String
    UNITS         "1.0E-18"
    MAX-ACCESS    read-only
    STATUS        current
    DESCRIPTION   "Bit Error Rate before Foward Error Correction (FEC) calculated from corrected errors"
    ::= { fecFacilityCurrent1dayEntry 4 }

fecFacilityCurrent1dayElapsedTime OBJECT-TYPE
    SYNTAX        Integer32 (0..86400)
    MAX-ACCESS    read-only
    STATUS        current
    DESCRIPTION   "Elapsed 1Day"
    ::= { fecFacilityCurrent1dayEntry 5 }

endOfFecFacilityCurrent1dayTable OBJECT-TYPE
    SYNTAX        Integer32
    MAX-ACCESS    read-only
    STATUS        current
    DESCRIPTION   ""
    ::= { pmFacilityDataRecord 52 }

fecFacilityHistorical15minTable OBJECT-TYPE
    SYNTAX        SEQUENCE OF FecFacilityHistorical15minEntry
    MAX-ACCESS    not-accessible
    STATUS        current
    DESCRIPTION   ""
    ::= { pmFacilityDataRecord 53 }

fecFacilityHistorical15minEntry OBJECT-TYPE
    SYNTAX        FecFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  fecFacilityHistorical15minNumber
                }
    ::= { fecFacilityHistorical15minTable 1 }

FecFacilityHistorical15minEntry ::= SEQUENCE
  {    fecFacilityHistorical15minNumber Integer32,
    fecFacilityHistorical15minSES Unsigned32,
    fecFacilityHistorical15minCE Counter64String,
    fecFacilityHistorical15minUBE Counter64String,
    fecFacilityHistorical15minBERCE Counter64String,
    fecFacilityHistorical15minValidFlag TruthValue,
    fecFacilityHistorical15minTimeStamp DateAndTime }

fecFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { fecFacilityHistorical15minEntry 1 }

fecFacilityHistorical15minSES OBJECT-TYPE
    SYNTAX        Unsigned32
    MAX-ACCESS    read-only
    STATUS        current
    DESCRIPTION   "Severely Errored Seconds FEC Monitoring for internal use"
    ::= { fecFacilityHistorical15minEntry 2 }

fecFacilityHistorical15minCE OBJECT-TYPE
    SYNTAX        Counter64String
    MAX-ACCESS    read-only
    STATUS        current
    DESCRIPTION   "OTU FEC Corrected Errors"
    ::= { fecFacilityHistorical15minEntry 3 }

fecFacilityHistorical15minUBE OBJECT-TYPE
    SYNTAX        Counter64String
    MAX-ACCESS    read-only
    STATUS        current
    DESCRIPTION   "OTU FEC Uncorrected Block Errors"
    ::= { fecFacilityHistorical15minEntry 4 }

fecFacilityHistorical15minBERCE OBJECT-TYPE
    SYNTAX        Counter64String
    UNITS         "1.0E-18"
    MAX-ACCESS    read-only
    STATUS        current
    DESCRIPTION   "Bit Error Rate before Foward Error Correction (FEC) calculated from corrected errors"
    ::= { fecFacilityHistorical15minEntry 5 }

fecFacilityHistorical15minValidFlag OBJECT-TYPE
    SYNTAX        TruthValue
    MAX-ACCESS    read-only
    STATUS        current
    DESCRIPTION   "Valid Flag"
    ::= { fecFacilityHistorical15minEntry 6 }

fecFacilityHistorical15minTimeStamp OBJECT-TYPE
    SYNTAX        DateAndTime
    MAX-ACCESS    read-only
    STATUS        current
    DESCRIPTION   "Timestamp"
    ::= { fecFacilityHistorical15minEntry 7 }

endOfFecFacilityHistorical15minTable OBJECT-TYPE
    SYNTAX        Integer32
    MAX-ACCESS    read-only
    STATUS        current
    DESCRIPTION   ""
    ::= { pmFacilityDataRecord 54 }

fecFacilityHistorical1dayTable OBJECT-TYPE
    SYNTAX        SEQUENCE OF FecFacilityHistorical1dayEntry
    MAX-ACCESS    not-accessible
    STATUS        current
    DESCRIPTION   ""
    ::= { pmFacilityDataRecord 55 }

fecFacilityHistorical1dayEntry OBJECT-TYPE
    SYNTAX        FecFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  fecFacilityHistorical1dayNumber
                }
    ::= { fecFacilityHistorical1dayTable 1 }

FecFacilityHistorical1dayEntry ::= SEQUENCE
  {    fecFacilityHistorical1dayNumber Integer32,
    fecFacilityHistorical1daySES Unsigned32,
    fecFacilityHistorical1dayCE Counter64String,
    fecFacilityHistorical1dayUBE Counter64String,
    fecFacilityHistorical1dayBERCE Counter64String,
    fecFacilityHistorical1dayValidFlag TruthValue,
    fecFacilityHistorical1dayTimeStamp DateAndTime }

fecFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { fecFacilityHistorical1dayEntry 1 }

fecFacilityHistorical1daySES OBJECT-TYPE
    SYNTAX        Unsigned32
    MAX-ACCESS    read-only
    STATUS        current
    DESCRIPTION   "Severely Errored Seconds FEC Monitoring for internal use"
    ::= { fecFacilityHistorical1dayEntry 2 }

fecFacilityHistorical1dayCE OBJECT-TYPE
    SYNTAX        Counter64String
    MAX-ACCESS    read-only
    STATUS        current
    DESCRIPTION   "OTU FEC Corrected Errors"
    ::= { fecFacilityHistorical1dayEntry 3 }

fecFacilityHistorical1dayUBE OBJECT-TYPE
    SYNTAX        Counter64String
    MAX-ACCESS    read-only
    STATUS        current
    DESCRIPTION   "OTU FEC Uncorrected Block Errors"
    ::= { fecFacilityHistorical1dayEntry 4 }

fecFacilityHistorical1dayBERCE OBJECT-TYPE
    SYNTAX        Counter64String
    UNITS         "1.0E-18"
    MAX-ACCESS    read-only
    STATUS        current
    DESCRIPTION   "Bit Error Rate before Foward Error Correction (FEC) calculated from corrected errors"
    ::= { fecFacilityHistorical1dayEntry 5 }

fecFacilityHistorical1dayValidFlag OBJECT-TYPE
    SYNTAX        TruthValue
    MAX-ACCESS    read-only
    STATUS        current
    DESCRIPTION   "Valid Flag"
    ::= { fecFacilityHistorical1dayEntry 6 }

fecFacilityHistorical1dayTimeStamp OBJECT-TYPE
    SYNTAX        DateAndTime
    MAX-ACCESS    read-only
    STATUS        current
    DESCRIPTION   "Timestamp"
    ::= { fecFacilityHistorical1dayEntry 7 }

endOfFecFacilityHistorical1dayTable OBJECT-TYPE
    SYNTAX        Integer32
    MAX-ACCESS    read-only
    STATUS        current
    DESCRIPTION   ""
    ::= { pmFacilityDataRecord 56 }

pcs1FacilityCurrent15minTable OBJECT-TYPE
    SYNTAX        SEQUENCE OF Pcs1FacilityCurrent15minEntry
    MAX-ACCESS    not-accessible
    STATUS        current
    DESCRIPTION   ""
    ::= { pmFacilityDataRecord 57 }

pcs1FacilityCurrent15minEntry OBJECT-TYPE
    SYNTAX        Pcs1FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs1FacilityCurrent15minTable 1 }

Pcs1FacilityCurrent15minEntry ::= SEQUENCE
  {    pcs1FacilityCurrent15minES Unsigned32,
    pcs1FacilityCurrent15minCV Counter64String,
    pcs1FacilityCurrent15minSE Unsigned32,
    pcs1FacilityCurrent15minElapsedTime Integer32 }

pcs1FacilityCurrent15minES OBJECT-TYPE
    SYNTAX        Unsigned32
    MAX-ACCESS    read-only
    STATUS        current
    DESCRIPTION   "Physical Coding Layer Errored Seconds"
    ::= { pcs1FacilityCurrent15minEntry 1 }

pcs1FacilityCurrent15minCV OBJECT-TYPE
    SYNTAX        Counter64String
    MAX-ACCESS    read-only
    STATUS        current
    DESCRIPTION   "Physical Coding Layer Coding Violations"
    ::= { pcs1FacilityCurrent15minEntry 2 }

pcs1FacilityCurrent15minSE OBJECT-TYPE
    SYNTAX        Unsigned32
    MAX-ACCESS    read-only
    STATUS        current
    DESCRIPTION   "Sync Header Errors Physical Coding Layer"
    ::= { pcs1FacilityCurrent15minEntry 3 }

pcs1FacilityCurrent15minElapsedTime OBJECT-TYPE
    SYNTAX        Integer32 (0..9000)
    MAX-ACCESS    read-only
    STATUS        current
    DESCRIPTION   "Elapsed 15Min"
    ::= { pcs1FacilityCurrent15minEntry 4 }

endOfPcs1FacilityCurrent15minTable OBJECT-TYPE
    SYNTAX        Integer32
    MAX-ACCESS    read-only
    STATUS        current
    DESCRIPTION   ""
    ::= { pmFacilityDataRecord 58 }

pcs1FacilityCurrent1dayTable OBJECT-TYPE
    SYNTAX        SEQUENCE OF Pcs1FacilityCurrent1dayEntry
    MAX-ACCESS    not-accessible
    STATUS        current
    DESCRIPTION   ""
    ::= { pmFacilityDataRecord 59 }

pcs1FacilityCurrent1dayEntry OBJECT-TYPE
    SYNTAX        Pcs1FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs1FacilityCurrent1dayTable 1 }

Pcs1FacilityCurrent1dayEntry ::= SEQUENCE
  {    pcs1FacilityCurrent1dayES Unsigned32,
    pcs1FacilityCurrent1dayCV Counter64String,
    pcs1FacilityCurrent1daySE Unsigned32,
    pcs1FacilityCurrent1dayElapsedTime Integer32 }

pcs1FacilityCurrent1dayES OBJECT-TYPE
    SYNTAX        Unsigned32
    MAX-ACCESS    read-only
    STATUS        current
    DESCRIPTION   "Physical Coding Layer Errored Seconds"
    ::= { pcs1FacilityCurrent1dayEntry 1 }

pcs1FacilityCurrent1dayCV OBJECT-TYPE
    SYNTAX        Counter64String
    MAX-ACCESS    read-only
    STATUS        current
    DESCRIPTION   "Physical Coding Layer Coding Violations"
    ::= { pcs1FacilityCurrent1dayEntry 2 }

pcs1FacilityCurrent1daySE OBJECT-TYPE
    SYNTAX        Unsigned32
    MAX-ACCESS    read-only
    STATUS        current
    DESCRIPTION   "Sync Header Errors Physical Coding Layer"
    ::= { pcs1FacilityCurrent1dayEntry 3 }

pcs1FacilityCurrent1dayElapsedTime OBJECT-TYPE
    SYNTAX        Integer32 (0..86400)
    MAX-ACCESS    read-only
    STATUS        current
    DESCRIPTION   "Elapsed 1Day"
    ::= { pcs1FacilityCurrent1dayEntry 4 }

endOfPcs1FacilityCurrent1dayTable OBJECT-TYPE
    SYNTAX        Integer32
    MAX-ACCESS    read-only
    STATUS        current
    DESCRIPTION   ""
    ::= { pmFacilityDataRecord 60 }

pcs1FacilityHistorical15minTable OBJECT-TYPE
    SYNTAX        SEQUENCE OF Pcs1FacilityHistorical15minEntry
    MAX-ACCESS    not-accessible
    STATUS        current
    DESCRIPTION   ""
    ::= { pmFacilityDataRecord 61 }

pcs1FacilityHistorical15minEntry OBJECT-TYPE
    SYNTAX        Pcs1FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs1FacilityHistorical15minNumber
                }
    ::= { pcs1FacilityHistorical15minTable 1 }

Pcs1FacilityHistorical15minEntry ::= SEQUENCE
  {    pcs1FacilityHistorical15minNumber Integer32,
    pcs1FacilityHistorical15minES Unsigned32,
    pcs1FacilityHistorical15minCV Counter64String,
    pcs1FacilityHistorical15minSE Unsigned32,
    pcs1FacilityHistorical15minValidFlag TruthValue,
    pcs1FacilityHistorical15minTimeStamp DateAndTime }

pcs1FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pcs1FacilityHistorical15minEntry 1 }

pcs1FacilityHistorical15minES OBJECT-TYPE
    SYNTAX        Unsigned32
    MAX-ACCESS    read-only
    STATUS        current
    DESCRIPTION   "Physical Coding Layer Errored Seconds"
    ::= { pcs1FacilityHistorical15minEntry 2 }

pcs1FacilityHistorical15minCV OBJECT-TYPE
    SYNTAX        Counter64String
    MAX-ACCESS    read-only
    STATUS        current
    DESCRIPTION   "Physical Coding Layer Coding Violations"
    ::= { pcs1FacilityHistorical15minEntry 3 }

pcs1FacilityHistorical15minSE OBJECT-TYPE
    SYNTAX        Unsigned32
    MAX-ACCESS    read-only
    STATUS        current
    DESCRIPTION   "Sync Header Errors Physical Coding Layer"
    ::= { pcs1FacilityHistorical15minEntry 4 }

pcs1FacilityHistorical15minValidFlag OBJECT-TYPE
    SYNTAX        TruthValue
    MAX-ACCESS    read-only
    STATUS        current
    DESCRIPTION   "Valid Flag"
    ::= { pcs1FacilityHistorical15minEntry 5 }

pcs1FacilityHistorical15minTimeStamp OBJECT-TYPE
    SYNTAX        DateAndTime
    MAX-ACCESS    read-only
    STATUS        current
    DESCRIPTION   "Timestamp"
    ::= { pcs1FacilityHistorical15minEntry 6 }

endOfPcs1FacilityHistorical15minTable OBJECT-TYPE
    SYNTAX        Integer32
    MAX-ACCESS    read-only
    STATUS        current
    DESCRIPTION   ""
    ::= { pmFacilityDataRecord 62 }

pcs1FacilityHistorical1dayTable OBJECT-TYPE
    SYNTAX        SEQUENCE OF Pcs1FacilityHistorical1dayEntry
    MAX-ACCESS    not-accessible
    STATUS        current
    DESCRIPTION   ""
    ::= { pmFacilityDataRecord 63 }

pcs1FacilityHistorical1dayEntry OBJECT-TYPE
    SYNTAX        Pcs1FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs1FacilityHistorical1dayNumber
                }
    ::= { pcs1FacilityHistorical1dayTable 1 }

Pcs1FacilityHistorical1dayEntry ::= SEQUENCE
  {    pcs1FacilityHistorical1dayNumber Integer32,
    pcs1FacilityHistorical1dayES Unsigned32,
    pcs1FacilityHistorical1dayCV Counter64String,
    pcs1FacilityHistorical1daySE Unsigned32,
    pcs1FacilityHistorical1dayValidFlag TruthValue,
    pcs1FacilityHistorical1dayTimeStamp DateAndTime }

pcs1FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pcs1FacilityHistorical1dayEntry 1 }

pcs1FacilityHistorical1dayES OBJECT-TYPE
    SYNTAX        Unsigned32
    MAX-ACCESS    read-only
    STATUS        current
    DESCRIPTION   "Physical Coding Layer Errored Seconds"
    ::= { pcs1FacilityHistorical1dayEntry 2 }

pcs1FacilityHistorical1dayCV OBJECT-TYPE
    SYNTAX        Counter64String
    MAX-ACCESS    read-only
    STATUS        current
    DESCRIPTION   "Physical Coding Layer Coding Violations"
    ::= { pcs1FacilityHistorical1dayEntry 3 }

pcs1FacilityHistorical1daySE OBJECT-TYPE
    SYNTAX        Unsigned32
    MAX-ACCESS    read-only
    STATUS        current
    DESCRIPTION   "Sync Header Errors Physical Coding Layer"
    ::= { pcs1FacilityHistorical1dayEntry 4 }

pcs1FacilityHistorical1dayValidFlag OBJECT-TYPE
    SYNTAX        TruthValue
    MAX-ACCESS    read-only
    STATUS        current
    DESCRIPTION   "Valid Flag"
    ::= { pcs1FacilityHistorical1dayEntry 5 }

pcs1FacilityHistorical1dayTimeStamp OBJECT-TYPE
    SYNTAX        DateAndTime
    MAX-ACCESS    read-only
    STATUS        current
    DESCRIPTION   "Timestamp"
    ::= { pcs1FacilityHistorical1dayEntry 6 }

endOfPcs1FacilityHistorical1dayTable OBJECT-TYPE
    SYNTAX        Integer32
    MAX-ACCESS    read-only
    STATUS        current
    DESCRIPTION   ""
    ::= { pmFacilityDataRecord 64 }

pcs2FacilityCurrent15minTable OBJECT-TYPE
    SYNTAX        SEQUENCE OF Pcs2FacilityCurrent15minEntry
    MAX-ACCESS    not-accessible
    STATUS        current
    DESCRIPTION   ""
    ::= { pmFacilityDataRecord 65 }

pcs2FacilityCurrent15minEntry OBJECT-TYPE
    SYNTAX        Pcs2FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs2FacilityCurrent15minTable 1 }

Pcs2FacilityCurrent15minEntry ::= SEQUENCE
  {    pcs2FacilityCurrent15minES Unsigned32,
    pcs2FacilityCurrent15minDE Unsigned32,
    pcs2FacilityCurrent15minCV Counter64String,
    pcs2FacilityCurrent15minElapsedTime Integer32 }

pcs2FacilityCurrent15minES OBJECT-TYPE
    SYNTAX        Unsigned32
    MAX-ACCESS    read-only
    STATUS        current
    DESCRIPTION   "Physical Coding Layer Errored Seconds"
    ::= { pcs2FacilityCurrent15minEntry 1 }

pcs2FacilityCurrent15minDE OBJECT-TYPE
    SYNTAX        Unsigned32
    MAX-ACCESS    read-only
    STATUS        current
    DESCRIPTION   "Physical Coding Layer Disparity Errors"
    ::= { pcs2FacilityCurrent15minEntry 2 }

pcs2FacilityCurrent15minCV OBJECT-TYPE
    SYNTAX        Counter64String
    MAX-ACCESS    read-only
    STATUS        current
    DESCRIPTION   "Physical Coding Layer Coding Violations"
    ::= { pcs2FacilityCurrent15minEntry 3 }

pcs2FacilityCurrent15minElapsedTime OBJECT-TYPE
    SYNTAX        Integer32 (0..9000)
    MAX-ACCESS    read-only
    STATUS        current
    DESCRIPTION   "Elapsed 15Min"
    ::= { pcs2FacilityCurrent15minEntry 4 }

endOfPcs2FacilityCurrent15minTable OBJECT-TYPE
    SYNTAX        Integer32
    MAX-ACCESS    read-only
    STATUS        current
    DESCRIPTION   ""
    ::= { pmFacilityDataRecord 66 }

pcs2FacilityCurrent1dayTable OBJECT-TYPE
    SYNTAX        SEQUENCE OF Pcs2FacilityCurrent1dayEntry
    MAX-ACCESS    not-accessible
    STATUS        current
    DESCRIPTION   ""
    ::= { pmFacilityDataRecord 67 }

pcs2FacilityCurrent1dayEntry OBJECT-TYPE
    SYNTAX        Pcs2FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs2FacilityCurrent1dayTable 1 }

Pcs2FacilityCurrent1dayEntry ::= SEQUENCE
  {    pcs2FacilityCurrent1dayES Unsigned32,
    pcs2FacilityCurrent1dayDE Unsigned32,
    pcs2FacilityCurrent1dayCV Counter64String,
    pcs2FacilityCurrent1dayElapsedTime Integer32 }

pcs2FacilityCurrent1dayES OBJECT-TYPE
    SYNTAX        Unsigned32
    MAX-ACCESS    read-only
    STATUS        current
    DESCRIPTION   "Physical Coding Layer Errored Seconds"
    ::= { pcs2FacilityCurrent1dayEntry 1 }

pcs2FacilityCurrent1dayDE OBJECT-TYPE
    SYNTAX        Unsigned32
    MAX-ACCESS    read-only
    STATUS        current
    DESCRIPTION   "Physical Coding Layer Disparity Errors"
    ::= { pcs2FacilityCurrent1dayEntry 2 }

pcs2FacilityCurrent1dayCV OBJECT-TYPE
    SYNTAX        Counter64String
    MAX-ACCESS    read-only
    STATUS        current
    DESCRIPTION   "Physical Coding Layer Coding Violations"
    ::= { pcs2FacilityCurrent1dayEntry 3 }

pcs2FacilityCurrent1dayElapsedTime OBJECT-TYPE
    SYNTAX        Integer32 (0..86400)
    MAX-ACCESS    read-only
    STATUS        current
    DESCRIPTION   "Elapsed 1Day"
    ::= { pcs2FacilityCurrent1dayEntry 4 }

endOfPcs2FacilityCurrent1dayTable OBJECT-TYPE
    SYNTAX        Integer32
    MAX-ACCESS    read-only
    STATUS        current
    DESCRIPTION   ""
    ::= { pmFacilityDataRecord 68 }

pcs2FacilityHistorical15minTable OBJECT-TYPE
    SYNTAX        SEQUENCE OF Pcs2FacilityHistorical15minEntry
    MAX-ACCESS    not-accessible
    STATUS        current
    DESCRIPTION   ""
    ::= { pmFacilityDataRecord 69 }

pcs2FacilityHistorical15minEntry OBJECT-TYPE
    SYNTAX        Pcs2FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs2FacilityHistorical15minNumber
                }
    ::= { pcs2FacilityHistorical15minTable 1 }

Pcs2FacilityHistorical15minEntry ::= SEQUENCE
  {    pcs2FacilityHistorical15minNumber Integer32,
    pcs2FacilityHistorical15minES Unsigned32,
    pcs2FacilityHistorical15minDE Unsigned32,
    pcs2FacilityHistorical15minCV Counter64String,
    pcs2FacilityHistorical15minValidFlag TruthValue,
    pcs2FacilityHistorical15minTimeStamp DateAndTime }

pcs2FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pcs2FacilityHistorical15minEntry 1 }

pcs2FacilityHistorical15minES OBJECT-TYPE
    SYNTAX        Unsigned32
    MAX-ACCESS    read-only
    STATUS        current
    DESCRIPTION   "Physical Coding Layer Errored Seconds"
    ::= { pcs2FacilityHistorical15minEntry 2 }

pcs2FacilityHistorical15minDE OBJECT-TYPE
    SYNTAX        Unsigned32
    MAX-ACCESS    read-only
    STATUS        current
    DESCRIPTION   "Physical Coding Layer Disparity Errors"
    ::= { pcs2FacilityHistorical15minEntry 3 }

pcs2FacilityHistorical15minCV OBJECT-TYPE
    SYNTAX        Counter64String
    MAX-ACCESS    read-only
    STATUS        current
    DESCRIPTION   "Physical Coding Layer Coding Violations"
    ::= { pcs2FacilityHistorical15minEntry 4 }

pcs2FacilityHistorical15minValidFlag OBJECT-TYPE
    SYNTAX        TruthValue
    MAX-ACCESS    read-only
    STATUS        current
    DESCRIPTION   "Valid Flag"
    ::= { pcs2FacilityHistorical15minEntry 5 }

pcs2FacilityHistorical15minTimeStamp OBJECT-TYPE
    SYNTAX        DateAndTime
    MAX-ACCESS    read-only
    STATUS        current
    DESCRIPTION   "Timestamp"
    ::= { pcs2FacilityHistorical15minEntry 6 }

endOfPcs2FacilityHistorical15minTable OBJECT-TYPE
    SYNTAX        Integer32
    MAX-ACCESS    read-only
    STATUS        current
    DESCRIPTION   ""
    ::= { pmFacilityDataRecord 70 }

pcs2FacilityHistorical1dayTable OBJECT-TYPE
    SYNTAX        SEQUENCE OF Pcs2FacilityHistorical1dayEntry
    MAX-ACCESS    not-accessible
    STATUS        current
    DESCRIPTION   ""
    ::= { pmFacilityDataRecord 71 }

pcs2FacilityHistorical1dayEntry OBJECT-TYPE
    SYNTAX        Pcs2FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs2FacilityHistorical1dayNumber
                }
    ::= { pcs2FacilityHistorical1dayTable 1 }

Pcs2FacilityHistorical1dayEntry ::= SEQUENCE
  {    pcs2FacilityHistorical1dayNumber Integer32,
    pcs2FacilityHistorical1dayES Unsigned32,
    pcs2FacilityHistorical1dayDE Unsigned32,
    pcs2FacilityHistorical1dayCV Counter64String,
    pcs2FacilityHistorical1dayValidFlag TruthValue,
    pcs2FacilityHistorical1dayTimeStamp DateAndTime }

pcs2FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pcs2FacilityHistorical1dayEntry 1 }

pcs2FacilityHistorical1dayES OBJECT-TYPE
    SYNTAX        Unsigned32
    MAX-ACCESS    read-only
    STATUS        current
    DESCRIPTION   "Physical Coding Layer Errored Seconds"
    ::= { pcs2FacilityHistorical1dayEntry 2 }

pcs2FacilityHistorical1dayDE OBJECT-TYPE
    SYNTAX        Unsigned32
    MAX-ACCESS    read-only
    STATUS        current
    DESCRIPTION   "Physical Coding Layer Disparity Errors"
    ::= { pcs2FacilityHistorical1dayEntry 3 }

pcs2FacilityHistorical1dayCV OBJECT-TYPE
    SYNTAX        Counter64String
    MAX-ACCESS    read-only
    STATUS        current
    DESCRIPTION   "Physical Coding Layer Coding Violations"
    ::= { pcs2FacilityHistorical1dayEntry 4 }

pcs2FacilityHistorical1dayValidFlag OBJECT-TYPE
    SYNTAX        TruthValue
    MAX-ACCESS    read-only
    STATUS        current
    DESCRIPTION   "Valid Flag"
    ::= { pcs2FacilityHistorical1dayEntry 5 }

pcs2FacilityHistorical1dayTimeStamp OBJECT-TYPE
    SYNTAX        DateAndTime
    MAX-ACCESS    read-only
    STATUS        current
    DESCRIPTION   "Timestamp"
    ::= { pcs2FacilityHistorical1dayEntry 6 }

endOfPcs2FacilityHistorical1dayTable OBJECT-TYPE
    SYNTAX        Integer32
    MAX-ACCESS    read-only
    STATUS        current
    DESCRIPTION   ""
    ::= { pmFacilityDataRecord 72 }

pcs3FacilityCurrent15minTable OBJECT-TYPE
    SYNTAX        SEQUENCE OF Pcs3FacilityCurrent15minEntry
    MAX-ACCESS    not-accessible
    STATUS        current
    DESCRIPTION   ""
    ::= { pmFacilityDataRecord 73 }

pcs3FacilityCurrent15minEntry OBJECT-TYPE
    SYNTAX        Pcs3FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs3FacilityCurrent15minTable 1 }

Pcs3FacilityCurrent15minEntry ::= SEQUENCE
  {    pcs3FacilityCurrent15minES Unsigned32,
    pcs3FacilityCurrent15minCVDE Counter64String,
    pcs3FacilityCurrent15minElapsedTime Integer32 }

pcs3FacilityCurrent15minES OBJECT-TYPE
    SYNTAX        Unsigned32
    MAX-ACCESS    read-only
    STATUS        current
    DESCRIPTION   "Physical Coding Layer Errored Seconds"
    ::= { pcs3FacilityCurrent15minEntry 1 }

pcs3FacilityCurrent15minCVDE OBJECT-TYPE
    SYNTAX        Counter64String
    MAX-ACCESS    read-only
    STATUS        current
    DESCRIPTION   "Physical Coding Layer Coding Violations + Disparity Errors"
    ::= { pcs3FacilityCurrent15minEntry 2 }

pcs3FacilityCurrent15minElapsedTime OBJECT-TYPE
    SYNTAX        Integer32 (0..9000)
    MAX-ACCESS    read-only
    STATUS        current
    DESCRIPTION   "Elapsed 15Min"
    ::= { pcs3FacilityCurrent15minEntry 3 }

endOfPcs3FacilityCurrent15minTable OBJECT-TYPE
    SYNTAX        Integer32
    MAX-ACCESS    read-only
    STATUS        current
    DESCRIPTION   ""
    ::= { pmFacilityDataRecord 74 }

pcs3FacilityCurrent1dayTable OBJECT-TYPE
    SYNTAX        SEQUENCE OF Pcs3FacilityCurrent1dayEntry
    MAX-ACCESS    not-accessible
    STATUS        current
    DESCRIPTION   ""
    ::= { pmFacilityDataRecord 75 }

pcs3FacilityCurrent1dayEntry OBJECT-TYPE
    SYNTAX        Pcs3FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs3FacilityCurrent1dayTable 1 }

Pcs3FacilityCurrent1dayEntry ::= SEQUENCE
  {    pcs3FacilityCurrent1dayES Unsigned32,
    pcs3FacilityCurrent1dayCVDE Counter64String,
    pcs3FacilityCurrent1dayElapsedTime Integer32 }

pcs3FacilityCurrent1dayES OBJECT-TYPE
    SYNTAX        Unsigned32
    MAX-ACCESS    read-only
    STATUS        current
    DESCRIPTION   "Physical Coding Layer Errored Seconds"
    ::= { pcs3FacilityCurrent1dayEntry 1 }

pcs3FacilityCurrent1dayCVDE OBJECT-TYPE
    SYNTAX        Counter64String
    MAX-ACCESS    read-only
    STATUS        current
    DESCRIPTION   "Physical Coding Layer Coding Violations + Disparity Errors"
    ::= { pcs3FacilityCurrent1dayEntry 2 }

pcs3FacilityCurrent1dayElapsedTime OBJECT-TYPE
    SYNTAX        Integer32 (0..86400)
    MAX-ACCESS    read-only
    STATUS        current
    DESCRIPTION   "Elapsed 1Day"
    ::= { pcs3FacilityCurrent1dayEntry 3 }

endOfPcs3FacilityCurrent1dayTable OBJECT-TYPE
    SYNTAX        Integer32
    MAX-ACCESS    read-only
    STATUS        current
    DESCRIPTION   ""
    ::= { pmFacilityDataRecord 76 }

pcs3FacilityHistorical15minTable OBJECT-TYPE
    SYNTAX        SEQUENCE OF Pcs3FacilityHistorical15minEntry
    MAX-ACCESS    not-accessible
    STATUS        current
    DESCRIPTION   ""
    ::= { pmFacilityDataRecord 77 }

pcs3FacilityHistorical15minEntry OBJECT-TYPE
    SYNTAX        Pcs3FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs3FacilityHistorical15minNumber
                }
    ::= { pcs3FacilityHistorical15minTable 1 }

Pcs3FacilityHistorical15minEntry ::= SEQUENCE
  {    pcs3FacilityHistorical15minNumber Integer32,
    pcs3FacilityHistorical15minES Unsigned32,
    pcs3FacilityHistorical15minCVDE Counter64String,
    pcs3FacilityHistorical15minValidFlag TruthValue,
    pcs3FacilityHistorical15minTimeStamp DateAndTime }

pcs3FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pcs3FacilityHistorical15minEntry 1 }

pcs3FacilityHistorical15minES OBJECT-TYPE
    SYNTAX        Unsigned32
    MAX-ACCESS    read-only
    STATUS        current
    DESCRIPTION   "Physical Coding Layer Errored Seconds"
    ::= { pcs3FacilityHistorical15minEntry 2 }

pcs3FacilityHistorical15minCVDE OBJECT-TYPE
    SYNTAX        Counter64String
    MAX-ACCESS    read-only
    STATUS        current
    DESCRIPTION   "Physical Coding Layer Coding Violations + Disparity Errors"
    ::= { pcs3FacilityHistorical15minEntry 3 }

pcs3FacilityHistorical15minValidFlag OBJECT-TYPE
    SYNTAX        TruthValue
    MAX-ACCESS    read-only
    STATUS        current
    DESCRIPTION   "Valid Flag"
    ::= { pcs3FacilityHistorical15minEntry 4 }

pcs3FacilityHistorical15minTimeStamp OBJECT-TYPE
    SYNTAX        DateAndTime
    MAX-ACCESS    read-only
    STATUS        current
    DESCRIPTION   "Timestamp"
    ::= { pcs3FacilityHistorical15minEntry 5 }

endOfPcs3FacilityHistorical15minTable OBJECT-TYPE
    SYNTAX        Integer32
    MAX-ACCESS    read-only
    STATUS        current
    DESCRIPTION   ""
    ::= { pmFacilityDataRecord 78 }

pcs3FacilityHistorical1dayTable OBJECT-TYPE
    SYNTAX        SEQUENCE OF Pcs3FacilityHistorical1dayEntry
    MAX-ACCESS    not-accessible
    STATUS        current
    DESCRIPTION   ""
    ::= { pmFacilityDataRecord 79 }

pcs3FacilityHistorical1dayEntry OBJECT-TYPE
    SYNTAX        Pcs3FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs3FacilityHistorical1dayNumber
                }
    ::= { pcs3FacilityHistorical1dayTable 1 }

Pcs3FacilityHistorical1dayEntry ::= SEQUENCE
  {    pcs3FacilityHistorical1dayNumber Integer32,
    pcs3FacilityHistorical1dayES Unsigned32,
    pcs3FacilityHistorical1dayCVDE Counter64String,
    pcs3FacilityHistorical1dayValidFlag TruthValue,
    pcs3FacilityHistorical1dayTimeStamp DateAndTime }

pcs3FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pcs3FacilityHistorical1dayEntry 1 }

pcs3FacilityHistorical1dayES OBJECT-TYPE
    SYNTAX        Unsigned32
    MAX-ACCESS    read-only
    STATUS        current
    DESCRIPTION   "Physical Coding Layer Errored Seconds"
    ::= { pcs3FacilityHistorical1dayEntry 2 }

pcs3FacilityHistorical1dayCVDE OBJECT-TYPE
    SYNTAX        Counter64String
    MAX-ACCESS    read-only
    STATUS        current
    DESCRIPTION   "Physical Coding Layer Coding Violations + Disparity Errors"
    ::= { pcs3FacilityHistorical1dayEntry 3 }

pcs3FacilityHistorical1dayValidFlag OBJECT-TYPE
    SYNTAX        TruthValue
    MAX-ACCESS    read-only
    STATUS        current
    DESCRIPTION   "Valid Flag"
    ::= { pcs3FacilityHistorical1dayEntry 4 }

pcs3FacilityHistorical1dayTimeStamp OBJECT-TYPE
    SYNTAX        DateAndTime
    MAX-ACCESS    read-only
    STATUS        current
    DESCRIPTION   "Timestamp"
    ::= { pcs3FacilityHistorical1dayEntry 5 }

endOfPcs3FacilityHistorical1dayTable OBJECT-TYPE
    SYNTAX        Integer32
    MAX-ACCESS    read-only
    STATUS        current
    DESCRIPTION   ""
    ::= { pmFacilityDataRecord 80 }

pcs4FacilityCurrent15minTable OBJECT-TYPE
    SYNTAX        SEQUENCE OF Pcs4FacilityCurrent15minEntry
    MAX-ACCESS    not-accessible
    STATUS        current
    DESCRIPTION   ""
    ::= { pmFacilityDataRecord 81 }

pcs4FacilityCurrent15minEntry OBJECT-TYPE
    SYNTAX        Pcs4FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs4FacilityCurrent15minTable 1 }

Pcs4FacilityCurrent15minEntry ::= SEQUENCE
  {    pcs4FacilityCurrent15minES Unsigned32,
    pcs4FacilityCurrent15minCV Counter64String,
    pcs4FacilityCurrent15minBBE Counter64String,
    pcs4FacilityCurrent15minElapsedTime Integer32 }

pcs4FacilityCurrent15minES OBJECT-TYPE
    SYNTAX        Unsigned32
    MAX-ACCESS    read-only
    STATUS        current
    DESCRIPTION   "Physical Coding Layer Errored Seconds"
    ::= { pcs4FacilityCurrent15minEntry 1 }

pcs4FacilityCurrent15minCV OBJECT-TYPE
    SYNTAX        Counter64String
    MAX-ACCESS    read-only
    STATUS        current
    DESCRIPTION   "Physical Coding Layer Coding Violations"
    ::= { pcs4FacilityCurrent15minEntry 2 }

pcs4FacilityCurrent15minBBE OBJECT-TYPE
    SYNTAX        Counter64String
    MAX-ACCESS    read-only
    STATUS        current
    DESCRIPTION   "PCS Background Block Errors"
    ::= { pcs4FacilityCurrent15minEntry 3 }

pcs4FacilityCurrent15minElapsedTime OBJECT-TYPE
    SYNTAX        Integer32 (0..9000)
    MAX-ACCESS    read-only
    STATUS        current
    DESCRIPTION   "Elapsed 15Min"
    ::= { pcs4FacilityCurrent15minEntry 4 }

endOfPcs4FacilityCurrent15minTable OBJECT-TYPE
    SYNTAX        Integer32
    MAX-ACCESS    read-only
    STATUS        current
    DESCRIPTION   ""
    ::= { pmFacilityDataRecord 82 }

pcs4FacilityCurrent1dayTable OBJECT-TYPE
    SYNTAX        SEQUENCE OF Pcs4FacilityCurrent1dayEntry
    MAX-ACCESS    not-accessible
    STATUS        current
    DESCRIPTION   ""
    ::= { pmFacilityDataRecord 83 }

pcs4FacilityCurrent1dayEntry OBJECT-TYPE
    SYNTAX        Pcs4FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs4FacilityCurrent1dayTable 1 }

Pcs4FacilityCurrent1dayEntry ::= SEQUENCE
  {    pcs4FacilityCurrent1dayES Unsigned32,
    pcs4FacilityCurrent1dayCV Counter64String,
    pcs4FacilityCurrent1dayBBE Counter64String,
    pcs4FacilityCurrent1dayElapsedTime Integer32 }

pcs4FacilityCurrent1dayES OBJECT-TYPE
    SYNTAX        Unsigned32
    MAX-ACCESS    read-only
    STATUS        current
    DESCRIPTION   "Physical Coding Layer Errored Seconds"
    ::= { pcs4FacilityCurrent1dayEntry 1 }

pcs4FacilityCurrent1dayCV OBJECT-TYPE
    SYNTAX        Counter64String
    MAX-ACCESS    read-only
    STATUS        current
    DESCRIPTION   "Physical Coding Layer Coding Violations"
    ::= { pcs4FacilityCurrent1dayEntry 2 }

pcs4FacilityCurrent1dayBBE OBJECT-TYPE
    SYNTAX        Counter64String
    MAX-ACCESS    read-only
    STATUS        current
    DESCRIPTION   "PCS Background Block Errors"
    ::= { pcs4FacilityCurrent1dayEntry 3 }

pcs4FacilityCurrent1dayElapsedTime OBJECT-TYPE
    SYNTAX        Integer32 (0..86400)
    MAX-ACCESS    read-only
    STATUS        current
    DESCRIPTION   "Elapsed 1Day"
    ::= { pcs4FacilityCurrent1dayEntry 4 }

endOfPcs4FacilityCurrent1dayTable OBJECT-TYPE
    SYNTAX        Integer32
    MAX-ACCESS    read-only
    STATUS        current
    DESCRIPTION   ""
    ::= { pmFacilityDataRecord 84 }

pcs4FacilityHistorical15minTable OBJECT-TYPE
    SYNTAX        SEQUENCE OF Pcs4FacilityHistorical15minEntry
    MAX-ACCESS    not-accessible
    STATUS        current
    DESCRIPTION   ""
    ::= { pmFacilityDataRecord 85 }

pcs4FacilityHistorical15minEntry OBJECT-TYPE
    SYNTAX        Pcs4FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs4FacilityHistorical15minNumber
                }
    ::= { pcs4FacilityHistorical15minTable 1 }

Pcs4FacilityHistorical15minEntry ::= SEQUENCE
  {    pcs4FacilityHistorical15minNumber Integer32,
    pcs4FacilityHistorical15minES Unsigned32,
    pcs4FacilityHistorical15minCV Counter64String,
    pcs4FacilityHistorical15minBBE Counter64String,
    pcs4FacilityHistorical15minValidFlag TruthValue,
    pcs4FacilityHistorical15minTimeStamp DateAndTime }

pcs4FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pcs4FacilityHistorical15minEntry 1 }

pcs4FacilityHistorical15minES OBJECT-TYPE
    SYNTAX        Unsigned32
    MAX-ACCESS    read-only
    STATUS        current
    DESCRIPTION   "Physical Coding Layer Errored Seconds"
    ::= { pcs4FacilityHistorical15minEntry 2 }

pcs4FacilityHistorical15minCV OBJECT-TYPE
    SYNTAX        Counter64String
    MAX-ACCESS    read-only
    STATUS        current
    DESCRIPTION   "Physical Coding Layer Coding Violations"
    ::= { pcs4FacilityHistorical15minEntry 3 }

pcs4FacilityHistorical15minBBE OBJECT-TYPE
    SYNTAX        Counter64String
    MAX-ACCESS    read-only
    STATUS        current
    DESCRIPTION   "PCS Background Block Errors"
    ::= { pcs4FacilityHistorical15minEntry 4 }

pcs4FacilityHistorical15minValidFlag OBJECT-TYPE
    SYNTAX        TruthValue
    MAX-ACCESS    read-only
    STATUS        current
    DESCRIPTION   "Valid Flag"
    ::= { pcs4FacilityHistorical15minEntry 5 }

pcs4FacilityHistorical15minTimeStamp OBJECT-TYPE
    SYNTAX        DateAndTime
    MAX-ACCESS    read-only
    STATUS        current
    DESCRIPTION   "Timestamp"
    ::= { pcs4FacilityHistorical15minEntry 6 }

endOfPcs4FacilityHistorical15minTable OBJECT-TYPE
    SYNTAX        Integer32
    MAX-ACCESS    read-only
    STATUS        current
    DESCRIPTION   ""
    ::= { pmFacilityDataRecord 86 }

pcs4FacilityHistorical1dayTable OBJECT-TYPE
    SYNTAX        SEQUENCE OF Pcs4FacilityHistorical1dayEntry
    MAX-ACCESS    not-accessible
    STATUS        current
    DESCRIPTION   ""
    ::= { pmFacilityDataRecord 87 }

pcs4FacilityHistorical1dayEntry OBJECT-TYPE
    SYNTAX        Pcs4FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcs4FacilityHistorical1dayNumber
                }
    ::= { pcs4FacilityHistorical1dayTable 1 }

Pcs4FacilityHistorical1dayEntry ::= SEQUENCE
  {    pcs4FacilityHistorical1dayNumber Integer32,
    pcs4FacilityHistorical1dayES Unsigned32,
    pcs4FacilityHistorical1dayCV Counter64String,
    pcs4FacilityHistorical1dayBBE Counter64String,
    pcs4FacilityHistorical1dayValidFlag TruthValue,
    pcs4FacilityHistorical1dayTimeStamp DateAndTime }

pcs4FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pcs4FacilityHistorical1dayEntry 1 }

pcs4FacilityHistorical1dayES OBJECT-TYPE
    SYNTAX        Unsigned32
    MAX-ACCESS    read-only
    STATUS        current
    DESCRIPTION   "Physical Coding Layer Errored Seconds"
    ::= { pcs4FacilityHistorical1dayEntry 2 }

pcs4FacilityHistorical1dayCV OBJECT-TYPE
    SYNTAX        Counter64String
    MAX-ACCESS    read-only
    STATUS        current
    DESCRIPTION   "Physical Coding Layer Coding Violations"
    ::= { pcs4FacilityHistorical1dayEntry 3 }

pcs4FacilityHistorical1dayBBE OBJECT-TYPE
    SYNTAX        Counter64String
    MAX-ACCESS    read-only
    STATUS        current
    DESCRIPTION   "PCS Background Block Errors"
    ::= { pcs4FacilityHistorical1dayEntry 4 }

pcs4FacilityHistorical1dayValidFlag OBJECT-TYPE
    SYNTAX        TruthValue
    MAX-ACCESS    read-only
    STATUS        current
    DESCRIPTION   "Valid Flag"
    ::= { pcs4FacilityHistorical1dayEntry 5 }

pcs4FacilityHistorical1dayTimeStamp OBJECT-TYPE
    SYNTAX        DateAndTime
    MAX-ACCESS    read-only
    STATUS        current
    DESCRIPTION   "Timestamp"
    ::= { pcs4FacilityHistorical1dayEntry 6 }

endOfPcs4FacilityHistorical1dayTable OBJECT-TYPE
    SYNTAX        Integer32
    MAX-ACCESS    read-only
    STATUS        current
    DESCRIPTION   ""
    ::= { pmFacilityDataRecord 88 }

lFacilityCurrent15minTable OBJECT-TYPE
    SYNTAX        SEQUENCE OF LFacilityCurrent15minEntry
    MAX-ACCESS    not-accessible
    STATUS        current
    DESCRIPTION   ""
    ::= { pmFacilityDataRecord 89 }

lFacilityCurrent15minEntry OBJECT-TYPE
    SYNTAX        LFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lFacilityCurrent15minTable 1 }

LFacilityCurrent15minEntry ::= SEQUENCE
  {    lFacilityCurrent15minES Unsigned32,
    lFacilityCurrent15minSES Unsigned32,
    lFacilityCurrent15minUAS Unsigned32,
    lFacilityCurrent15minCV Counter64String,
    lFacilityCurrent15minElapsedTime Integer32 }

lFacilityCurrent15minES OBJECT-TYPE
    SYNTAX        Unsigned32
    MAX-ACCESS    read-only
    STATUS        current
    DESCRIPTION   "Line / Multiplex Section Errored Second"
    ::= { lFacilityCurrent15minEntry 1 }

lFacilityCurrent15minSES OBJECT-TYPE
    SYNTAX        Unsigned32
    MAX-ACCESS    read-only
    STATUS        current
    DESCRIPTION   "Line / Multiplex Section Severely Errored Seconds"
    ::= { lFacilityCurrent15minEntry 2 }

lFacilityCurrent15minUAS OBJECT-TYPE
    SYNTAX        Unsigned32
    MAX-ACCESS    read-only
    STATUS        current
    DESCRIPTION   "Line / Multiplex Section Unavailable Seconds"
    ::= { lFacilityCurrent15minEntry 3 }

lFacilityCurrent15minCV OBJECT-TYPE
    SYNTAX        Counter64String
    MAX-ACCESS    read-only
    STATUS        current
    DESCRIPTION   "Line / Multiplex Section Coding Violations"
    ::= { lFacilityCurrent15minEntry 4 }

lFacilityCurrent15minElapsedTime OBJECT-TYPE
    SYNTAX        Integer32 (0..9000)
    MAX-ACCESS    read-only
    STATUS        current
    DESCRIPTION   "Elapsed 15Min"
    ::= { lFacilityCurrent15minEntry 5 }

endOfLFacilityCurrent15minTable OBJECT-TYPE
    SYNTAX        Integer32
    MAX-ACCESS    read-only
    STATUS        current
    DESCRIPTION   ""
    ::= { pmFacilityDataRecord 90 }

lFacilityCurrent1dayTable OBJECT-TYPE
    SYNTAX        SEQUENCE OF LFacilityCurrent1dayEntry
    MAX-ACCESS    not-accessible
    STATUS        current
    DESCRIPTION   ""
    ::= { pmFacilityDataRecord 91 }

lFacilityCurrent1dayEntry OBJECT-TYPE
    SYNTAX        LFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lFacilityCurrent1dayTable 1 }

LFacilityCurrent1dayEntry ::= SEQUENCE
  {    lFacilityCurrent1dayES Unsigned32,
    lFacilityCurrent1daySES Unsigned32,
    lFacilityCurrent1dayUAS Unsigned32,
    lFacilityCurrent1dayCV Counter64String,
    lFacilityCurrent1dayElapsedTime Integer32 }

lFacilityCurrent1dayES OBJECT-TYPE
    SYNTAX        Unsigned32
    MAX-ACCESS    read-only
    STATUS        current
    DESCRIPTION   "Line / Multiplex Section Errored Second"
    ::= { lFacilityCurrent1dayEntry 1 }

lFacilityCurrent1daySES OBJECT-TYPE
    SYNTAX        Unsigned32
    MAX-ACCESS    read-only
    STATUS        current
    DESCRIPTION   "Line / Multiplex Section Severely Errored Seconds"
    ::= { lFacilityCurrent1dayEntry 2 }

lFacilityCurrent1dayUAS OBJECT-TYPE
    SYNTAX        Unsigned32
    MAX-ACCESS    read-only
    STATUS        current
    DESCRIPTION   "Line / Multiplex Section Unavailable Seconds"
    ::= { lFacilityCurrent1dayEntry 3 }

lFacilityCurrent1dayCV OBJECT-TYPE
    SYNTAX        Counter64String
    MAX-ACCESS    read-only
    STATUS        current
    DESCRIPTION   "Line / Multiplex Section Coding Violations"
    ::= { lFacilityCurrent1dayEntry 4 }

lFacilityCurrent1dayElapsedTime OBJECT-TYPE
    SYNTAX        Integer32 (0..86400)
    MAX-ACCESS    read-only
    STATUS        current
    DESCRIPTION   "Elapsed 1Day"
    ::= { lFacilityCurrent1dayEntry 5 }

endOfLFacilityCurrent1dayTable OBJECT-TYPE
    SYNTAX        Integer32
    MAX-ACCESS    read-only
    STATUS        current
    DESCRIPTION   ""
    ::= { pmFacilityDataRecord 92 }

lFacilityHistorical15minTable OBJECT-TYPE
    SYNTAX        SEQUENCE OF LFacilityHistorical15minEntry
    MAX-ACCESS    not-accessible
    STATUS        current
    DESCRIPTION   ""
    ::= { pmFacilityDataRecord 93 }

lFacilityHistorical15minEntry OBJECT-TYPE
    SYNTAX        LFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lFacilityHistorical15minNumber
                }
    ::= { lFacilityHistorical15minTable 1 }

LFacilityHistorical15minEntry ::= SEQUENCE
  {    lFacilityHistorical15minNumber Integer32,
    lFacilityHistorical15minES Unsigned32,
    lFacilityHistorical15minSES Unsigned32,
    lFacilityHistorical15minUAS Unsigned32,
    lFacilityHistorical15minCV Counter64String,
    lFacilityHistorical15minValidFlag TruthValue,
    lFacilityHistorical15minTimeStamp DateAndTime }

lFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lFacilityHistorical15minEntry 1 }

lFacilityHistorical15minES OBJECT-TYPE
    SYNTAX        Unsigned32
    MAX-ACCESS    read-only
    STATUS        current
    DESCRIPTION   "Line / Multiplex Section Errored Second"
    ::= { lFacilityHistorical15minEntry 2 }

lFacilityHistorical15minSES OBJECT-TYPE
    SYNTAX        Unsigned32
    MAX-ACCESS    read-only
    STATUS        current
    DESCRIPTION   "Line / Multiplex Section Severely Errored Seconds"
    ::= { lFacilityHistorical15minEntry 3 }

lFacilityHistorical15minUAS OBJECT-TYPE
    SYNTAX        Unsigned32
    MAX-ACCESS    read-only
    STATUS        current
    DESCRIPTION   "Line / Multiplex Section Unavailable Seconds"
    ::= { lFacilityHistorical15minEntry 4 }

lFacilityHistorical15minCV OBJECT-TYPE
    SYNTAX        Counter64String
    MAX-ACCESS    read-only
    STATUS        current
    DESCRIPTION   "Line / Multiplex Section Coding Violations"
    ::= { lFacilityHistorical15minEntry 5 }

lFacilityHistorical15minValidFlag OBJECT-TYPE
    SYNTAX        TruthValue
    MAX-ACCESS    read-only
    STATUS        current
    DESCRIPTION   "Valid Flag"
    ::= { lFacilityHistorical15minEntry 6 }

lFacilityHistorical15minTimeStamp OBJECT-TYPE
    SYNTAX        DateAndTime
    MAX-ACCESS    read-only
    STATUS        current
    DESCRIPTION   "Timestamp"
    ::= { lFacilityHistorical15minEntry 7 }

endOfLFacilityHistorical15minTable OBJECT-TYPE
    SYNTAX        Integer32
    MAX-ACCESS    read-only
    STATUS        current
    DESCRIPTION   ""
    ::= { pmFacilityDataRecord 94 }

lFacilityHistorical1dayTable OBJECT-TYPE
    SYNTAX        SEQUENCE OF LFacilityHistorical1dayEntry
    MAX-ACCESS    not-accessible
    STATUS        current
    DESCRIPTION   ""
    ::= { pmFacilityDataRecord 95 }

lFacilityHistorical1dayEntry OBJECT-TYPE
    SYNTAX        LFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lFacilityHistorical1dayNumber
                }
    ::= { lFacilityHistorical1dayTable 1 }

LFacilityHistorical1dayEntry ::= SEQUENCE
  {    lFacilityHistorical1dayNumber Integer32,
    lFacilityHistorical1dayES Unsigned32,
    lFacilityHistorical1daySES Unsigned32,
    lFacilityHistorical1dayUAS Unsigned32,
    lFacilityHistorical1dayCV Counter64String,
    lFacilityHistorical1dayValidFlag TruthValue,
    lFacilityHistorical1dayTimeStamp DateAndTime }

lFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lFacilityHistorical1dayEntry 1 }

lFacilityHistorical1dayES OBJECT-TYPE
    SYNTAX        Unsigned32
    MAX-ACCESS    read-only
    STATUS        current
    DESCRIPTION   "Line / Multiplex Section Errored Second"
    ::= { lFacilityHistorical1dayEntry 2 }

lFacilityHistorical1daySES OBJECT-TYPE
    SYNTAX        Unsigned32
    MAX-ACCESS    read-only
    STATUS        current
    DESCRIPTION   "Line / Multiplex Section Severely Errored Seconds"
    ::= { lFacilityHistorical1dayEntry 3 }

lFacilityHistorical1dayUAS OBJECT-TYPE
    SYNTAX        Unsigned32
    MAX-ACCESS    read-only
    STATUS        current
    DESCRIPTION   "Line / Multiplex Section Unavailable Seconds"
    ::= { lFacilityHistorical1dayEntry 4 }

lFacilityHistorical1dayCV OBJECT-TYPE
    SYNTAX        Counter64String
    MAX-ACCESS    read-only
    STATUS        current
    DESCRIPTION   "Line / Multiplex Section Coding Violations"
    ::= { lFacilityHistorical1dayEntry 5 }

lFacilityHistorical1dayValidFlag OBJECT-TYPE
    SYNTAX        TruthValue
    MAX-ACCESS    read-only
    STATUS        current
    DESCRIPTION   "Valid Flag"
    ::= { lFacilityHistorical1dayEntry 6 }

lFacilityHistorical1dayTimeStamp OBJECT-TYPE
    SYNTAX        DateAndTime
    MAX-ACCESS    read-only
    STATUS        current
    DESCRIPTION   "Timestamp"
    ::= { lFacilityHistorical1dayEntry 7 }

endOfLFacilityHistorical1dayTable OBJECT-TYPE
    SYNTAX        Integer32
    MAX-ACCESS    read-only
    STATUS        current
    DESCRIPTION   ""
    ::= { pmFacilityDataRecord 96 }

sFacilityCurrent15minTable OBJECT-TYPE
    SYNTAX        SEQUENCE OF SFacilityCurrent15minEntry
    MAX-ACCESS    not-accessible
    STATUS        current
    DESCRIPTION   ""
    ::= { pmFacilityDataRecord 97 }

sFacilityCurrent15minEntry OBJECT-TYPE
    SYNTAX        SFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sFacilityCurrent15minTable 1 }

SFacilityCurrent15minEntry ::= SEQUENCE
  {    sFacilityCurrent15minES Unsigned32,
    sFacilityCurrent15minSES Unsigned32,
    sFacilityCurrent15minSEFS Unsigned32,
    sFacilityCurrent15minCV Counter64String,
    sFacilityCurrent15minElapsedTime Integer32 }

sFacilityCurrent15minES OBJECT-TYPE
    SYNTAX        Unsigned32
    MAX-ACCESS    read-only
    STATUS        current
    DESCRIPTION   "Section / Regenerator Section Errored Seconds"
    ::= { sFacilityCurrent15minEntry 1 }

sFacilityCurrent15minSES OBJECT-TYPE
    SYNTAX        Unsigned32
    MAX-ACCESS    read-only
    STATUS        current
    DESCRIPTION   "Section Severely Errored Seconds"
    ::= { sFacilityCurrent15minEntry 2 }

sFacilityCurrent15minSEFS OBJECT-TYPE
    SYNTAX        Unsigned32
    MAX-ACCESS    read-only
    STATUS        current
    DESCRIPTION   "Section Severely Errored Frame Seconds"
    ::= { sFacilityCurrent15minEntry 3 }

sFacilityCurrent15minCV OBJECT-TYPE
    SYNTAX        Counter64String
    MAX-ACCESS    read-only
    STATUS        current
    DESCRIPTION   "Section / Regenator Section Coding Violations"
    ::= { sFacilityCurrent15minEntry 4 }

sFacilityCurrent15minElapsedTime OBJECT-TYPE
    SYNTAX        Integer32 (0..9000)
    MAX-ACCESS    read-only
    STATUS        current
    DESCRIPTION   "Elapsed 15Min"
    ::= { sFacilityCurrent15minEntry 5 }

endOfSFacilityCurrent15minTable OBJECT-TYPE
    SYNTAX        Integer32
    MAX-ACCESS    read-only
    STATUS        current
    DESCRIPTION   ""
    ::= { pmFacilityDataRecord 98 }

sFacilityCurrent1dayTable OBJECT-TYPE
    SYNTAX        SEQUENCE OF SFacilityCurrent1dayEntry
    MAX-ACCESS    not-accessible
    STATUS        current
    DESCRIPTION   ""
    ::= { pmFacilityDataRecord 99 }

sFacilityCurrent1dayEntry OBJECT-TYPE
    SYNTAX        SFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sFacilityCurrent1dayTable 1 }

SFacilityCurrent1dayEntry ::= SEQUENCE
  {    sFacilityCurrent1dayES Unsigned32,
    sFacilityCurrent1daySES Unsigned32,
    sFacilityCurrent1daySEFS Unsigned32,
    sFacilityCurrent1dayCV Counter64String,
    sFacilityCurrent1dayElapsedTime Integer32 }

sFacilityCurrent1dayES OBJECT-TYPE
    SYNTAX        Unsigned32
    MAX-ACCESS    read-only
    STATUS        current
    DESCRIPTION   "Section / Regenerator Section Errored Seconds"
    ::= { sFacilityCurrent1dayEntry 1 }

sFacilityCurrent1daySES OBJECT-TYPE
    SYNTAX        Unsigned32
    MAX-ACCESS    read-only
    STATUS        current
    DESCRIPTION   "Section Severely Errored Seconds"
    ::= { sFacilityCurrent1dayEntry 2 }

sFacilityCurrent1daySEFS OBJECT-TYPE
    SYNTAX        Unsigned32
    MAX-ACCESS    read-only
    STATUS        current
    DESCRIPTION   "Section Severely Errored Frame Seconds"
    ::= { sFacilityCurrent1dayEntry 3 }

sFacilityCurrent1dayCV OBJECT-TYPE
    SYNTAX        Counter64String
    MAX-ACCESS    read-only
    STATUS        current
    DESCRIPTION   "Section / Regenator Section Coding Violations"
    ::= { sFacilityCurrent1dayEntry 4 }

sFacilityCurrent1dayElapsedTime OBJECT-TYPE
    SYNTAX        Integer32 (0..86400)
    MAX-ACCESS    read-only
    STATUS        current
    DESCRIPTION   "Elapsed 1Day"
    ::= { sFacilityCurrent1dayEntry 5 }

endOfSFacilityCurrent1dayTable OBJECT-TYPE
    SYNTAX        Integer32
    MAX-ACCESS    read-only
    STATUS        current
    DESCRIPTION   ""
    ::= { pmFacilityDataRecord 100 }

sFacilityHistorical15minTable OBJECT-TYPE
    SYNTAX        SEQUENCE OF SFacilityHistorical15minEntry
    MAX-ACCESS    not-accessible
    STATUS        current
    DESCRIPTION   ""
    ::= { pmFacilityDataRecord 101 }

sFacilityHistorical15minEntry OBJECT-TYPE
    SYNTAX        SFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  sFacilityHistorical15minNumber
                }
    ::= { sFacilityHistorical15minTable 1 }

SFacilityHistorical15minEntry ::= SEQUENCE
  {    sFacilityHistorical15minNumber Integer32,
    sFacilityHistorical15minES Unsigned32,
    sFacilityHistorical15minSES Unsigned32,
    sFacilityHistorical15minSEFS Unsigned32,
    sFacilityHistorical15minCV Counter64String,
    sFacilityHistorical15minValidFlag TruthValue,
    sFacilityHistorical15minTimeStamp DateAndTime }

sFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { sFacilityHistorical15minEntry 1 }

sFacilityHistorical15minES OBJECT-TYPE
    SYNTAX        Unsigned32
    MAX-ACCESS    read-only
    STATUS        current
    DESCRIPTION   "Section / Regenerator Section Errored Seconds"
    ::= { sFacilityHistorical15minEntry 2 }

sFacilityHistorical15minSES OBJECT-TYPE
    SYNTAX        Unsigned32
    MAX-ACCESS    read-only
    STATUS        current
    DESCRIPTION   "Section Severely Errored Seconds"
    ::= { sFacilityHistorical15minEntry 3 }

sFacilityHistorical15minSEFS OBJECT-TYPE
    SYNTAX        Unsigned32
    MAX-ACCESS    read-only
    STATUS        current
    DESCRIPTION   "Section Severely Errored Frame Seconds"
    ::= { sFacilityHistorical15minEntry 4 }

sFacilityHistorical15minCV OBJECT-TYPE
    SYNTAX        Counter64String
    MAX-ACCESS    read-only
    STATUS        current
    DESCRIPTION   "Section / Regenator Section Coding Violations"
    ::= { sFacilityHistorical15minEntry 5 }

sFacilityHistorical15minValidFlag OBJECT-TYPE
    SYNTAX        TruthValue
    MAX-ACCESS    read-only
    STATUS        current
    DESCRIPTION   "Valid Flag"
    ::= { sFacilityHistorical15minEntry 6 }

sFacilityHistorical15minTimeStamp OBJECT-TYPE
    SYNTAX        DateAndTime
    MAX-ACCESS    read-only
    STATUS        current
    DESCRIPTION   "Timestamp"
    ::= { sFacilityHistorical15minEntry 7 }

endOfSFacilityHistorical15minTable OBJECT-TYPE
    SYNTAX        Integer32
    MAX-ACCESS    read-only
    STATUS        current
    DESCRIPTION   ""
    ::= { pmFacilityDataRecord 102 }

sFacilityHistorical1dayTable OBJECT-TYPE
    SYNTAX        SEQUENCE OF SFacilityHistorical1dayEntry
    MAX-ACCESS    not-accessible
    STATUS        current
    DESCRIPTION   ""
    ::= { pmFacilityDataRecord 103 }

sFacilityHistorical1dayEntry OBJECT-TYPE
    SYNTAX        SFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  sFacilityHistorical1dayNumber
                }
    ::= { sFacilityHistorical1dayTable 1 }

SFacilityHistorical1dayEntry ::= SEQUENCE
  {    sFacilityHistorical1dayNumber Integer32,
    sFacilityHistorical1dayES Unsigned32,
    sFacilityHistorical1daySES Unsigned32,
    sFacilityHistorical1daySEFS Unsigned32,
    sFacilityHistorical1dayCV Counter64String,
    sFacilityHistorical1dayValidFlag TruthValue,
    sFacilityHistorical1dayTimeStamp DateAndTime }

sFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { sFacilityHistorical1dayEntry 1 }

sFacilityHistorical1dayES OBJECT-TYPE
    SYNTAX        Unsigned32
    MAX-ACCESS    read-only
    STATUS        current
    DESCRIPTION   "Section / Regenerator Section Errored Seconds"
    ::= { sFacilityHistorical1dayEntry 2 }

sFacilityHistorical1daySES OBJECT-TYPE
    SYNTAX        Unsigned32
    MAX-ACCESS    read-only
    STATUS        current
    DESCRIPTION   "Section Severely Errored Seconds"
    ::= { sFacilityHistorical1dayEntry 3 }

sFacilityHistorical1daySEFS OBJECT-TYPE
    SYNTAX        Unsigned32
    MAX-ACCESS    read-only
    STATUS        current
    DESCRIPTION   "Section Severely Errored Frame Seconds"
    ::= { sFacilityHistorical1dayEntry 4 }

sFacilityHistorical1dayCV OBJECT-TYPE
    SYNTAX        Counter64String
    MAX-ACCESS    read-only
    STATUS        current
    DESCRIPTION   "Section / Regenator Section Coding Violations"
    ::= { sFacilityHistorical1dayEntry 5 }

sFacilityHistorical1dayValidFlag OBJECT-TYPE
    SYNTAX        TruthValue
    MAX-ACCESS    read-only
    STATUS        current
    DESCRIPTION   "Valid Flag"
    ::= { sFacilityHistorical1dayEntry 6 }

sFacilityHistorical1dayTimeStamp OBJECT-TYPE
    SYNTAX        DateAndTime
    MAX-ACCESS    read-only
    STATUS        current
    DESCRIPTION   "Timestamp"
    ::= { sFacilityHistorical1dayEntry 7 }

endOfSFacilityHistorical1dayTable OBJECT-TYPE
    SYNTAX        Integer32
    MAX-ACCESS    read-only
    STATUS        current
    DESCRIPTION   ""
    ::= { pmFacilityDataRecord 104 }

gfpfrFacilityCurrent15minTable OBJECT-TYPE
    SYNTAX        SEQUENCE OF GfpfrFacilityCurrent15minEntry
    MAX-ACCESS    not-accessible
    STATUS        current
    DESCRIPTION   ""
    ::= { pmFacilityDataRecord 105 }

gfpfrFacilityCurrent15minEntry OBJECT-TYPE
    SYNTAX        GfpfrFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { gfpfrFacilityCurrent15minTable 1 }

GfpfrFacilityCurrent15minEntry ::= SEQUENCE
  {    gfpfrFacilityCurrent15minGoodFrames Counter64String,
    gfpfrFacilityCurrent15minCHecDiscardedFrames Counter64String,
    gfpfrFacilityCurrent15minTHecDiscardedFrames Counter64String,
    gfpfrFacilityCurrent15minElapsedTime Integer32 }

gfpfrFacilityCurrent15minGoodFrames OBJECT-TYPE
    SYNTAX        Counter64String
    MAX-ACCESS    read-only
    STATUS        current
    DESCRIPTION   "GFP Valid Frames"
    ::= { gfpfrFacilityCurrent15minEntry 1 }

gfpfrFacilityCurrent15minCHecDiscardedFrames OBJECT-TYPE
    SYNTAX        Counter64String
    MAX-ACCESS    read-only
    STATUS        current
    DESCRIPTION   "Core HEC Discarded Frames"
    ::= { gfpfrFacilityCurrent15minEntry 2 }

gfpfrFacilityCurrent15minTHecDiscardedFrames OBJECT-TYPE
    SYNTAX        Counter64String
    MAX-ACCESS    read-only
    STATUS        current
    DESCRIPTION   "Type Field HEC Discarded Frames"
    ::= { gfpfrFacilityCurrent15minEntry 3 }

gfpfrFacilityCurrent15minElapsedTime OBJECT-TYPE
    SYNTAX        Integer32 (0..9000)
    MAX-ACCESS    read-only
    STATUS        current
    DESCRIPTION   "Elapsed 15Min"
    ::= { gfpfrFacilityCurrent15minEntry 4 }

endOfGfpfrFacilityCurrent15minTable OBJECT-TYPE
    SYNTAX        Integer32
    MAX-ACCESS    read-only
    STATUS        current
    DESCRIPTION   ""
    ::= { pmFacilityDataRecord 106 }

gfpfrFacilityCurrent1dayTable OBJECT-TYPE
    SYNTAX        SEQUENCE OF GfpfrFacilityCurrent1dayEntry
    MAX-ACCESS    not-accessible
    STATUS        current
    DESCRIPTION   ""
    ::= { pmFacilityDataRecord 107 }

gfpfrFacilityCurrent1dayEntry OBJECT-TYPE
    SYNTAX        GfpfrFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { gfpfrFacilityCurrent1dayTable 1 }

GfpfrFacilityCurrent1dayEntry ::= SEQUENCE
  {    gfpfrFacilityCurrent1dayGoodFrames Counter64String,
    gfpfrFacilityCurrent1dayCHecDiscardedFrames Counter64String,
    gfpfrFacilityCurrent1dayTHecDiscardedFrames Counter64String,
    gfpfrFacilityCurrent1dayElapsedTime Integer32 }

gfpfrFacilityCurrent1dayGoodFrames OBJECT-TYPE
    SYNTAX        Counter64String
    MAX-ACCESS    read-only
    STATUS        current
    DESCRIPTION   "GFP Valid Frames"
    ::= { gfpfrFacilityCurrent1dayEntry 1 }

gfpfrFacilityCurrent1dayCHecDiscardedFrames OBJECT-TYPE
    SYNTAX        Counter64String
    MAX-ACCESS    read-only
    STATUS        current
    DESCRIPTION   "Core HEC Discarded Frames"
    ::= { gfpfrFacilityCurrent1dayEntry 2 }

gfpfrFacilityCurrent1dayTHecDiscardedFrames OBJECT-TYPE
    SYNTAX        Counter64String
    MAX-ACCESS    read-only
    STATUS        current
    DESCRIPTION   "Type Field HEC Discarded Frames"
    ::= { gfpfrFacilityCurrent1dayEntry 3 }

gfpfrFacilityCurrent1dayElapsedTime OBJECT-TYPE
    SYNTAX        Integer32 (0..86400)
    MAX-ACCESS    read-only
    STATUS        current
    DESCRIPTION   "Elapsed 1Day"
    ::= { gfpfrFacilityCurrent1dayEntry 4 }

endOfGfpfrFacilityCurrent1dayTable OBJECT-TYPE
    SYNTAX        Integer32
    MAX-ACCESS    read-only
    STATUS        current
    DESCRIPTION   ""
    ::= { pmFacilityDataRecord 108 }

gfpfrFacilityHistorical15minTable OBJECT-TYPE
    SYNTAX        SEQUENCE OF GfpfrFacilityHistorical15minEntry
    MAX-ACCESS    not-accessible
    STATUS        current
    DESCRIPTION   ""
    ::= { pmFacilityDataRecord 109 }

gfpfrFacilityHistorical15minEntry OBJECT-TYPE
    SYNTAX        GfpfrFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  gfpfrFacilityHistorical15minNumber
                }
    ::= { gfpfrFacilityHistorical15minTable 1 }

GfpfrFacilityHistorical15minEntry ::= SEQUENCE
  {    gfpfrFacilityHistorical15minNumber Integer32,
    gfpfrFacilityHistorical15minGoodFrames Counter64String,
    gfpfrFacilityHistorical15minCHecDiscardedFrames Counter64String,
    gfpfrFacilityHistorical15minTHecDiscardedFrames Counter64String,
    gfpfrFacilityHistorical15minValidFlag TruthValue,
    gfpfrFacilityHistorical15minTimeStamp DateAndTime }

gfpfrFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { gfpfrFacilityHistorical15minEntry 1 }

gfpfrFacilityHistorical15minGoodFrames OBJECT-TYPE
    SYNTAX        Counter64String
    MAX-ACCESS    read-only
    STATUS        current
    DESCRIPTION   "GFP Valid Frames"
    ::= { gfpfrFacilityHistorical15minEntry 2 }

gfpfrFacilityHistorical15minCHecDiscardedFrames OBJECT-TYPE
    SYNTAX        Counter64String
    MAX-ACCESS    read-only
    STATUS        current
    DESCRIPTION   "Core HEC Discarded Frames"
    ::= { gfpfrFacilityHistorical15minEntry 3 }

gfpfrFacilityHistorical15minTHecDiscardedFrames OBJECT-TYPE
    SYNTAX        Counter64String
    MAX-ACCESS    read-only
    STATUS        current
    DESCRIPTION   "Type Field HEC Discarded Frames"
    ::= { gfpfrFacilityHistorical15minEntry 4 }

gfpfrFacilityHistorical15minValidFlag OBJECT-TYPE
    SYNTAX        TruthValue
    MAX-ACCESS    read-only
    STATUS        current
    DESCRIPTION   "Valid Flag"
    ::= { gfpfrFacilityHistorical15minEntry 5 }

gfpfrFacilityHistorical15minTimeStamp OBJECT-TYPE
    SYNTAX        DateAndTime
    MAX-ACCESS    read-only
    STATUS        current
    DESCRIPTION   "Timestamp"
    ::= { gfpfrFacilityHistorical15minEntry 6 }

endOfGfpfrFacilityHistorical15minTable OBJECT-TYPE
    SYNTAX        Integer32
    MAX-ACCESS    read-only
    STATUS        current
    DESCRIPTION   ""
    ::= { pmFacilityDataRecord 110 }

gfpfrFacilityHistorical1dayTable OBJECT-TYPE
    SYNTAX        SEQUENCE OF GfpfrFacilityHistorical1dayEntry
    MAX-ACCESS    not-accessible
    STATUS        current
    DESCRIPTION   ""
    ::= { pmFacilityDataRecord 111 }

gfpfrFacilityHistorical1dayEntry OBJECT-TYPE
    SYNTAX        GfpfrFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  gfpfrFacilityHistorical1dayNumber
                }
    ::= { gfpfrFacilityHistorical1dayTable 1 }

GfpfrFacilityHistorical1dayEntry ::= SEQUENCE
  {    gfpfrFacilityHistorical1dayNumber Integer32,
    gfpfrFacilityHistorical1dayGoodFrames Counter64String,
    gfpfrFacilityHistorical1dayCHecDiscardedFrames Counter64String,
    gfpfrFacilityHistorical1dayTHecDiscardedFrames Counter64String,
    gfpfrFacilityHistorical1dayValidFlag TruthValue,
    gfpfrFacilityHistorical1dayTimeStamp DateAndTime }

gfpfrFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { gfpfrFacilityHistorical1dayEntry 1 }

gfpfrFacilityHistorical1dayGoodFrames OBJECT-TYPE
    SYNTAX        Counter64String
    MAX-ACCESS    read-only
    STATUS        current
    DESCRIPTION   "GFP Valid Frames"
    ::= { gfpfrFacilityHistorical1dayEntry 2 }

gfpfrFacilityHistorical1dayCHecDiscardedFrames OBJECT-TYPE
    SYNTAX        Counter64String
    MAX-ACCESS    read-only
    STATUS        current
    DESCRIPTION   "Core HEC Discarded Frames"
    ::= { gfpfrFacilityHistorical1dayEntry 3 }

gfpfrFacilityHistorical1dayTHecDiscardedFrames OBJECT-TYPE
    SYNTAX        Counter64String
    MAX-ACCESS    read-only
    STATUS        current
    DESCRIPTION   "Type Field HEC Discarded Frames"
    ::= { gfpfrFacilityHistorical1dayEntry 4 }

gfpfrFacilityHistorical1dayValidFlag OBJECT-TYPE
    SYNTAX        TruthValue
    MAX-ACCESS    read-only
    STATUS        current
    DESCRIPTION   "Valid Flag"
    ::= { gfpfrFacilityHistorical1dayEntry 5 }

gfpfrFacilityHistorical1dayTimeStamp OBJECT-TYPE
    SYNTAX        DateAndTime
    MAX-ACCESS    read-only
    STATUS        current
    DESCRIPTION   "Timestamp"
    ::= { gfpfrFacilityHistorical1dayEntry 6 }

endOfGfpfrFacilityHistorical1dayTable OBJECT-TYPE
    SYNTAX        Integer32
    MAX-ACCESS    read-only
    STATUS        current
    DESCRIPTION   ""
    ::= { pmFacilityDataRecord 112 }

checfrFacilityCurrent15minTable OBJECT-TYPE
    SYNTAX        SEQUENCE OF ChecfrFacilityCurrent15minEntry
    MAX-ACCESS    not-accessible
    STATUS        current
    DESCRIPTION   ""
    ::= { pmFacilityDataRecord 113 }

checfrFacilityCurrent15minEntry OBJECT-TYPE
    SYNTAX        ChecfrFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { checfrFacilityCurrent15minTable 1 }

ChecfrFacilityCurrent15minEntry ::= SEQUENCE
  {    checfrFacilityCurrent15minCoreHecCorrectedFrames Unsigned32,
    checfrFacilityCurrent15minTypeHecCorrectedFrames Unsigned32,
    checfrFacilityCurrent15minTypeHecDiscardedFrames Counter64String,
    checfrFacilityCurrent15minElapsedTime Integer32 }

checfrFacilityCurrent15minCoreHecCorrectedFrames OBJECT-TYPE
    SYNTAX        Unsigned32
    MAX-ACCESS    read-only
    STATUS        current
    DESCRIPTION   "Core HEC Corrected Frames"
    ::= { checfrFacilityCurrent15minEntry 1 }

checfrFacilityCurrent15minTypeHecCorrectedFrames OBJECT-TYPE
    SYNTAX        Unsigned32
    MAX-ACCESS    read-only
    STATUS        current
    DESCRIPTION   "Type Field HEC Corrected Frames"
    ::= { checfrFacilityCurrent15minEntry 2 }

checfrFacilityCurrent15minTypeHecDiscardedFrames OBJECT-TYPE
    SYNTAX        Counter64String
    MAX-ACCESS    read-only
    STATUS        current
    DESCRIPTION   "Type Field HEC Discarded Frames"
    ::= { checfrFacilityCurrent15minEntry 3 }

checfrFacilityCurrent15minElapsedTime OBJECT-TYPE
    SYNTAX        Integer32 (0..9000)
    MAX-ACCESS    read-only
    STATUS        current
    DESCRIPTION   "Elapsed 15Min"
    ::= { checfrFacilityCurrent15minEntry 4 }

endOfChecfrFacilityCurrent15minTable OBJECT-TYPE
    SYNTAX        Integer32
    MAX-ACCESS    read-only
    STATUS        current
    DESCRIPTION   ""
    ::= { pmFacilityDataRecord 114 }

checfrFacilityCurrent1dayTable OBJECT-TYPE
    SYNTAX        SEQUENCE OF ChecfrFacilityCurrent1dayEntry
    MAX-ACCESS    not-accessible
    STATUS        current
    DESCRIPTION   ""
    ::= { pmFacilityDataRecord 115 }

checfrFacilityCurrent1dayEntry OBJECT-TYPE
    SYNTAX        ChecfrFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { checfrFacilityCurrent1dayTable 1 }

ChecfrFacilityCurrent1dayEntry ::= SEQUENCE
  {    checfrFacilityCurrent1dayCoreHecCorrectedFrames Unsigned32,
    checfrFacilityCurrent1dayTypeHecCorrectedFrames Unsigned32,
    checfrFacilityCurrent1dayTypeHecDiscardedFrames Counter64String,
    checfrFacilityCurrent1dayElapsedTime Integer32 }

checfrFacilityCurrent1dayCoreHecCorrectedFrames OBJECT-TYPE
    SYNTAX        Unsigned32
    MAX-ACCESS    read-only
    STATUS        current
    DESCRIPTION   "Core HEC Corrected Frames"
    ::= { checfrFacilityCurrent1dayEntry 1 }

checfrFacilityCurrent1dayTypeHecCorrectedFrames OBJECT-TYPE
    SYNTAX        Unsigned32
    MAX-ACCESS    read-only
    STATUS        current
    DESCRIPTION   "Type Field HEC Corrected Frames"
    ::= { checfrFacilityCurrent1dayEntry 2 }

checfrFacilityCurrent1dayTypeHecDiscardedFrames OBJECT-TYPE
    SYNTAX        Counter64String
    MAX-ACCESS    read-only
    STATUS        current
    DESCRIPTION   "Type Field HEC Discarded Frames"
    ::= { checfrFacilityCurrent1dayEntry 3 }

checfrFacilityCurrent1dayElapsedTime OBJECT-TYPE
    SYNTAX        Integer32 (0..86400)
    MAX-ACCESS    read-only
    STATUS        current
    DESCRIPTION   "Elapsed 1Day"
    ::= { checfrFacilityCurrent1dayEntry 4 }

endOfChecfrFacilityCurrent1dayTable OBJECT-TYPE
    SYNTAX        Integer32
    MAX-ACCESS    read-only
    STATUS        current
    DESCRIPTION   ""
    ::= { pmFacilityDataRecord 116 }

checfrFacilityHistorical15minTable OBJECT-TYPE
    SYNTAX        SEQUENCE OF ChecfrFacilityHistorical15minEntry
    MAX-ACCESS    not-accessible
    STATUS        current
    DESCRIPTION   ""
    ::= { pmFacilityDataRecord 117 }

checfrFacilityHistorical15minEntry OBJECT-TYPE
    SYNTAX        ChecfrFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  checfrFacilityHistorical15minNumber
                }
    ::= { checfrFacilityHistorical15minTable 1 }

ChecfrFacilityHistorical15minEntry ::= SEQUENCE
  {    checfrFacilityHistorical15minNumber Integer32,
    checfrFacilityHistorical15minCoreHecCorrectedFrames Unsigned32,
    checfrFacilityHistorical15minTypeHecCorrectedFrames Unsigned32,
    checfrFacilityHistorical15minTypeHecDiscardedFrames Counter64String,
    checfrFacilityHistorical15minValidFlag TruthValue,
    checfrFacilityHistorical15minTimeStamp DateAndTime }

checfrFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { checfrFacilityHistorical15minEntry 1 }

checfrFacilityHistorical15minCoreHecCorrectedFrames OBJECT-TYPE
    SYNTAX        Unsigned32
    MAX-ACCESS    read-only
    STATUS        current
    DESCRIPTION   "Core HEC Corrected Frames"
    ::= { checfrFacilityHistorical15minEntry 2 }

checfrFacilityHistorical15minTypeHecCorrectedFrames OBJECT-TYPE
    SYNTAX        Unsigned32
    MAX-ACCESS    read-only
    STATUS        current
    DESCRIPTION   "Type Field HEC Corrected Frames"
    ::= { checfrFacilityHistorical15minEntry 3 }

checfrFacilityHistorical15minTypeHecDiscardedFrames OBJECT-TYPE
    SYNTAX        Counter64String
    MAX-ACCESS    read-only
    STATUS        current
    DESCRIPTION   "Type Field HEC Discarded Frames"
    ::= { checfrFacilityHistorical15minEntry 4 }

checfrFacilityHistorical15minValidFlag OBJECT-TYPE
    SYNTAX        TruthValue
    MAX-ACCESS    read-only
    STATUS        current
    DESCRIPTION   "Valid Flag"
    ::= { checfrFacilityHistorical15minEntry 5 }

checfrFacilityHistorical15minTimeStamp OBJECT-TYPE
    SYNTAX        DateAndTime
    MAX-ACCESS    read-only
    STATUS        current
    DESCRIPTION   "Timestamp"
    ::= { checfrFacilityHistorical15minEntry 6 }

endOfChecfrFacilityHistorical15minTable OBJECT-TYPE
    SYNTAX        Integer32
    MAX-ACCESS    read-only
    STATUS        current
    DESCRIPTION   ""
    ::= { pmFacilityDataRecord 118 }

checfrFacilityHistorical1dayTable OBJECT-TYPE
    SYNTAX        SEQUENCE OF ChecfrFacilityHistorical1dayEntry
    MAX-ACCESS    not-accessible
    STATUS        current
    DESCRIPTION   ""
    ::= { pmFacilityDataRecord 119 }

checfrFacilityHistorical1dayEntry OBJECT-TYPE
    SYNTAX        ChecfrFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  checfrFacilityHistorical1dayNumber
                }
    ::= { checfrFacilityHistorical1dayTable 1 }

ChecfrFacilityHistorical1dayEntry ::= SEQUENCE
  {    checfrFacilityHistorical1dayNumber Integer32,
    checfrFacilityHistorical1dayCoreHecCorrectedFrames Unsigned32,
    checfrFacilityHistorical1dayTypeHecCorrectedFrames Unsigned32,
    checfrFacilityHistorical1dayTypeHecDiscardedFrames Counter64String,
    checfrFacilityHistorical1dayValidFlag TruthValue,
    checfrFacilityHistorical1dayTimeStamp DateAndTime }

checfrFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { checfrFacilityHistorical1dayEntry 1 }

checfrFacilityHistorical1dayCoreHecCorrectedFrames OBJECT-TYPE
    SYNTAX        Unsigned32
    MAX-ACCESS    read-only
    STATUS        current
    DESCRIPTION   "Core HEC Corrected Frames"
    ::= { checfrFacilityHistorical1dayEntry 2 }

checfrFacilityHistorical1dayTypeHecCorrectedFrames OBJECT-TYPE
    SYNTAX        Unsigned32
    MAX-ACCESS    read-only
    STATUS        current
    DESCRIPTION   "Type Field HEC Corrected Frames"
    ::= { checfrFacilityHistorical1dayEntry 3 }

checfrFacilityHistorical1dayTypeHecDiscardedFrames OBJECT-TYPE
    SYNTAX        Counter64String
    MAX-ACCESS    read-only
    STATUS        current
    DESCRIPTION   "Type Field HEC Discarded Frames"
    ::= { checfrFacilityHistorical1dayEntry 4 }

checfrFacilityHistorical1dayValidFlag OBJECT-TYPE
    SYNTAX        TruthValue
    MAX-ACCESS    read-only
    STATUS        current
    DESCRIPTION   "Valid Flag"
    ::= { checfrFacilityHistorical1dayEntry 5 }

checfrFacilityHistorical1dayTimeStamp OBJECT-TYPE
    SYNTAX        DateAndTime
    MAX-ACCESS    read-only
    STATUS        current
    DESCRIPTION   "Timestamp"
    ::= { checfrFacilityHistorical1dayEntry 6 }

endOfChecfrFacilityHistorical1dayTable OBJECT-TYPE
    SYNTAX        Integer32
    MAX-ACCESS    read-only
    STATUS        current
    DESCRIPTION   ""
    ::= { pmFacilityDataRecord 120 }

discsBlockFacilityCurrent15minTable OBJECT-TYPE
    SYNTAX        SEQUENCE OF DiscsBlockFacilityCurrent15minEntry
    MAX-ACCESS    not-accessible
    STATUS        current
    DESCRIPTION   ""
    ::= { pmFacilityDataRecord 121 }

discsBlockFacilityCurrent15minEntry OBJECT-TYPE
    SYNTAX        DiscsBlockFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { discsBlockFacilityCurrent15minTable 1 }

DiscsBlockFacilityCurrent15minEntry ::= SEQUENCE
  {    discsBlockFacilityCurrent15minDiscardedSuperblocks Unsigned32,
    discsBlockFacilityCurrent15minElapsedTime Integer32 }

discsBlockFacilityCurrent15minDiscardedSuperblocks OBJECT-TYPE
    SYNTAX        Unsigned32
    MAX-ACCESS    read-only
    STATUS        current
    DESCRIPTION   "Discarded Super Blocks"
    ::= { discsBlockFacilityCurrent15minEntry 1 }

discsBlockFacilityCurrent15minElapsedTime OBJECT-TYPE
    SYNTAX        Integer32 (0..9000)
    MAX-ACCESS    read-only
    STATUS        current
    DESCRIPTION   "Elapsed 15Min"
    ::= { discsBlockFacilityCurrent15minEntry 2 }

endOfDiscsBlockFacilityCurrent15minTable OBJECT-TYPE
    SYNTAX        Integer32
    MAX-ACCESS    read-only
    STATUS        current
    DESCRIPTION   ""
    ::= { pmFacilityDataRecord 122 }

discsBlockFacilityCurrent1dayTable OBJECT-TYPE
    SYNTAX        SEQUENCE OF DiscsBlockFacilityCurrent1dayEntry
    MAX-ACCESS    not-accessible
    STATUS        current
    DESCRIPTION   ""
    ::= { pmFacilityDataRecord 123 }

discsBlockFacilityCurrent1dayEntry OBJECT-TYPE
    SYNTAX        DiscsBlockFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { discsBlockFacilityCurrent1dayTable 1 }

DiscsBlockFacilityCurrent1dayEntry ::= SEQUENCE
  {    discsBlockFacilityCurrent1dayDiscardedSuperblocks Unsigned32,
    discsBlockFacilityCurrent1dayElapsedTime Integer32 }

discsBlockFacilityCurrent1dayDiscardedSuperblocks OBJECT-TYPE
    SYNTAX        Unsigned32
    MAX-ACCESS    read-only
    STATUS        current
    DESCRIPTION   "Discarded Super Blocks"
    ::= { discsBlockFacilityCurrent1dayEntry 1 }

discsBlockFacilityCurrent1dayElapsedTime OBJECT-TYPE
    SYNTAX        Integer32 (0..86400)
    MAX-ACCESS    read-only
    STATUS        current
    DESCRIPTION   "Elapsed 1Day"
    ::= { discsBlockFacilityCurrent1dayEntry 2 }

endOfDiscsBlockFacilityCurrent1dayTable OBJECT-TYPE
    SYNTAX        Integer32
    MAX-ACCESS    read-only
    STATUS        current
    DESCRIPTION   ""
    ::= { pmFacilityDataRecord 124 }

discsBlockFacilityHistorical15minTable OBJECT-TYPE
    SYNTAX        SEQUENCE OF DiscsBlockFacilityHistorical15minEntry
    MAX-ACCESS    not-accessible
    STATUS        current
    DESCRIPTION   ""
    ::= { pmFacilityDataRecord 125 }

discsBlockFacilityHistorical15minEntry OBJECT-TYPE
    SYNTAX        DiscsBlockFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  discsBlockFacilityHistorical15minNumber
                }
    ::= { discsBlockFacilityHistorical15minTable 1 }

DiscsBlockFacilityHistorical15minEntry ::= SEQUENCE
  {    discsBlockFacilityHistorical15minNumber Integer32,
    discsBlockFacilityHistorical15minDiscardedSuperblocks Unsigned32,
    discsBlockFacilityHistorical15minValidFlag TruthValue,
    discsBlockFacilityHistorical15minTimeStamp DateAndTime }

discsBlockFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { discsBlockFacilityHistorical15minEntry 1 }

discsBlockFacilityHistorical15minDiscardedSuperblocks OBJECT-TYPE
    SYNTAX        Unsigned32
    MAX-ACCESS    read-only
    STATUS        current
    DESCRIPTION   "Discarded Super Blocks"
    ::= { discsBlockFacilityHistorical15minEntry 2 }

discsBlockFacilityHistorical15minValidFlag OBJECT-TYPE
    SYNTAX        TruthValue
    MAX-ACCESS    read-only
    STATUS        current
    DESCRIPTION   "Valid Flag"
    ::= { discsBlockFacilityHistorical15minEntry 3 }

discsBlockFacilityHistorical15minTimeStamp OBJECT-TYPE
    SYNTAX        DateAndTime
    MAX-ACCESS    read-only
    STATUS        current
    DESCRIPTION   "Timestamp"
    ::= { discsBlockFacilityHistorical15minEntry 4 }

endOfDiscsBlockFacilityHistorical15minTable OBJECT-TYPE
    SYNTAX        Integer32
    MAX-ACCESS    read-only
    STATUS        current
    DESCRIPTION   ""
    ::= { pmFacilityDataRecord 126 }

discsBlockFacilityHistorical1dayTable OBJECT-TYPE
    SYNTAX        SEQUENCE OF DiscsBlockFacilityHistorical1dayEntry
    MAX-ACCESS    not-accessible
    STATUS        current
    DESCRIPTION   ""
    ::= { pmFacilityDataRecord 127 }

discsBlockFacilityHistorical1dayEntry OBJECT-TYPE
    SYNTAX        DiscsBlockFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  discsBlockFacilityHistorical1dayNumber
                }
    ::= { discsBlockFacilityHistorical1dayTable 1 }

DiscsBlockFacilityHistorical1dayEntry ::= SEQUENCE
  {    discsBlockFacilityHistorical1dayNumber Integer32,
    discsBlockFacilityHistorical1dayDiscardedSuperblocks Unsigned32,
    discsBlockFacilityHistorical1dayValidFlag TruthValue,
    discsBlockFacilityHistorical1dayTimeStamp DateAndTime }

discsBlockFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { discsBlockFacilityHistorical1dayEntry 1 }

discsBlockFacilityHistorical1dayDiscardedSuperblocks OBJECT-TYPE
    SYNTAX        Unsigned32
    MAX-ACCESS    read-only
    STATUS        current
    DESCRIPTION   "Discarded Super Blocks"
    ::= { discsBlockFacilityHistorical1dayEntry 2 }

discsBlockFacilityHistorical1dayValidFlag OBJECT-TYPE
    SYNTAX        TruthValue
    MAX-ACCESS    read-only
    STATUS        current
    DESCRIPTION   "Valid Flag"
    ::= { discsBlockFacilityHistorical1dayEntry 3 }

discsBlockFacilityHistorical1dayTimeStamp OBJECT-TYPE
    SYNTAX        DateAndTime
    MAX-ACCESS    read-only
    STATUS        current
    DESCRIPTION   "Timestamp"
    ::= { discsBlockFacilityHistorical1dayEntry 4 }

endOfDiscsBlockFacilityHistorical1dayTable OBJECT-TYPE
    SYNTAX        Integer32
    MAX-ACCESS    read-only
    STATUS        current
    DESCRIPTION   ""
    ::= { pmFacilityDataRecord 128 }

l2PortTxFacilityCurrent15minTable OBJECT-TYPE
    SYNTAX        SEQUENCE OF L2PortTxFacilityCurrent15minEntry
    MAX-ACCESS    not-accessible
    STATUS        current
    DESCRIPTION   ""
    ::= { pmFacilityDataRecord 129 }

l2PortTxFacilityCurrent15minEntry OBJECT-TYPE
    SYNTAX        L2PortTxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { l2PortTxFacilityCurrent15minTable 1 }

L2PortTxFacilityCurrent15minEntry ::= SEQUENCE
  {    l2PortTxFacilityCurrent15minFramesTrmt Counter64String,
    l2PortTxFacilityCurrent15minBytesTrmt Counter64String,
    l2PortTxFacilityCurrent15minBroadcastFramesTrmt Counter64String,
    l2PortTxFacilityCurrent15minMulticastFramesTrmt Counter64String,
    l2PortTxFacilityCurrent15minPauseFramesTrmt Counter64String,
    l2PortTxFacilityCurrent15minBytesFrames64Trmt Counter64String,
    l2PortTxFacilityCurrent15minBytesFrames65Trmt Counter64String,
    l2PortTxFacilityCurrent15minBytesFrames128Trmt Counter64String,
    l2PortTxFacilityCurrent15minBytesFrames256Trmt Counter64String,
    l2PortTxFacilityCurrent15minBytesFrames512Trmt Counter64String,
    l2PortTxFacilityCurrent15minBytesFrames1024Trmt Counter64String,
    l2PortTxFacilityCurrent15minBytesFrames1519Trmt Counter64String,
    l2PortTxFacilityCurrent15minElapsedTime Integer32 }

l2PortTxFacilityCurrent15minFramesTrmt OBJECT-TYPE
    SYNTAX        Counter64String
    MAX-ACCESS    read-only
    STATUS        current
    DESCRIPTION   "Frames Transmitted"
    ::= { l2PortTxFacilityCurrent15minEntry 1 }

l2PortTxFacilityCurrent15minBytesTrmt OBJECT-TYPE
    SYNTAX        Counter64String
    MAX-ACCESS    read-only
    STATUS        current
    DESCRIPTION   "Bytes Transmitted"
    ::= { l2PortTxFacilityCurrent15minEntry 2 }

l2PortTxFacilityCurrent15minBroadcastFramesTrmt OBJECT-TYPE
    SYNTAX        Counter64String
    MAX-ACCESS    read-only
    STATUS        current
    DESCRIPTION   "Broadcast Frames Transmitted"
    ::= { l2PortTxFacilityCurrent15minEntry 3 }

l2PortTxFacilityCurrent15minMulticastFramesTrmt OBJECT-TYPE
    SYNTAX        Counter64String
    MAX-ACCESS    read-only
    STATUS        current
    DESCRIPTION   "Multicast Frames Received"
    ::= { l2PortTxFacilityCurrent15minEntry 4 }

l2PortTxFacilityCurrent15minPauseFramesTrmt OBJECT-TYPE
    SYNTAX        Counter64String
    MAX-ACCESS    read-only
    STATUS        current
    DESCRIPTION   "Pause Frames Transmitted"
    ::= { l2PortTxFacilityCurrent15minEntry 5 }

l2PortTxFacilityCurrent15minBytesFrames64Trmt OBJECT-TYPE
    SYNTAX        Counter64String
    MAX-ACCESS    read-only
    STATUS        current
    DESCRIPTION   "64 Byte Frames Transmitted"
    ::= { l2PortTxFacilityCurrent15minEntry 6 }

l2PortTxFacilityCurrent15minBytesFrames65Trmt OBJECT-TYPE
    SYNTAX        Counter64String
    MAX-ACCESS    read-only
    STATUS        current
    DESCRIPTION   "65-127 Byte Frames Transmitted"
    ::= { l2PortTxFacilityCurrent15minEntry 7 }

l2PortTxFacilityCurrent15minBytesFrames128Trmt OBJECT-TYPE
    SYNTAX        Counter64String
    MAX-ACCESS    read-only
    STATUS        current
    DESCRIPTION   "128-255 Byte Frames Transmitted"
    ::= { l2PortTxFacilityCurrent15minEntry 8 }

l2PortTxFacilityCurrent15minBytesFrames256Trmt OBJECT-TYPE
    SYNTAX        Counter64String
    MAX-ACCESS    read-only
    STATUS        current
    DESCRIPTION   "256-511 Byte Frames Transmitted"
    ::= { l2PortTxFacilityCurrent15minEntry 9 }

l2PortTxFacilityCurrent15minBytesFrames512Trmt OBJECT-TYPE
    SYNTAX        Counter64String
    MAX-ACCESS    read-only
    STATUS        current
    DESCRIPTION   "512-1023 Byte Frames Transmitted"
    ::= { l2PortTxFacilityCurrent15minEntry 10 }

l2PortTxFacilityCurrent15minBytesFrames1024Trmt OBJECT-TYPE
    SYNTAX        Counter64String
    MAX-ACCESS    read-only
    STATUS        current
    DESCRIPTION   "1024-1518 Byte Frames Transmitted"
    ::= { l2PortTxFacilityCurrent15minEntry 11 }

l2PortTxFacilityCurrent15minBytesFrames1519Trmt OBJECT-TYPE
    SYNTAX        Counter64String
    MAX-ACCESS    read-only
    STATUS        current
    DESCRIPTION   "1519-Max Byte Frames Transmitted"
    ::= { l2PortTxFacilityCurrent15minEntry 12 }

l2PortTxFacilityCurrent15minElapsedTime OBJECT-TYPE
    SYNTAX        Integer32 (0..9000)
    MAX-ACCESS    read-only
    STATUS        current
    DESCRIPTION   "Elapsed 15Min"
    ::= { l2PortTxFacilityCurrent15minEntry 13 }

endOfL2ProtTxFacilityCurrent15minTable OBJECT-TYPE
    SYNTAX        Integer32
    MAX-ACCESS    read-only
    STATUS        current
    DESCRIPTION   ""
    ::= { pmFacilityDataRecord 130 }

l2PortTxFacilityCurrent1dayTable OBJECT-TYPE
    SYNTAX        SEQUENCE OF L2PortTxFacilityCurrent1dayEntry
    MAX-ACCESS    not-accessible
    STATUS        current
    DESCRIPTION   ""
    ::= { pmFacilityDataRecord 131 }

l2PortTxFacilityCurrent1dayEntry OBJECT-TYPE
    SYNTAX        L2PortTxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { l2PortTxFacilityCurrent1dayTable 1 }

L2PortTxFacilityCurrent1dayEntry ::= SEQUENCE
  {    l2PortTxFacilityCurrent1dayFramesTrmt Counter64String,
    l2PortTxFacilityCurrent1dayBytesTrmt Counter64String,
    l2PortTxFacilityCurrent1dayBroadcastFramesTrmt Counter64String,
    l2PortTxFacilityCurrent1dayMulticastFramesTrmt Counter64String,
    l2PortTxFacilityCurrent1dayPauseFramesTrmt Counter64String,
    l2PortTxFacilityCurrent1dayBytesFrames64Trmt Counter64String,
    l2PortTxFacilityCurrent1dayBytesFrames65Trmt Counter64String,
    l2PortTxFacilityCurrent1dayBytesFrames128Trmt Counter64String,
    l2PortTxFacilityCurrent1dayBytesFrames256Trmt Counter64String,
    l2PortTxFacilityCurrent1dayBytesFrames512Trmt Counter64String,
    l2PortTxFacilityCurrent1dayBytesFrames1024Trmt Counter64String,
    l2PortTxFacilityCurrent1dayBytesFrames1519Trmt Counter64String,
    l2PortTxFacilityCurrent1dayElapsedTime Integer32 }

l2PortTxFacilityCurrent1dayFramesTrmt OBJECT-TYPE
    SYNTAX        Counter64String
    MAX-ACCESS    read-only
    STATUS        current
    DESCRIPTION   "Frames Transmitted"
    ::= { l2PortTxFacilityCurrent1dayEntry 1 }

l2PortTxFacilityCurrent1dayBytesTrmt OBJECT-TYPE
    SYNTAX        Counter64String
    MAX-ACCESS    read-only
    STATUS        current
    DESCRIPTION   "Bytes Transmitted"
    ::= { l2PortTxFacilityCurrent1dayEntry 2 }

l2PortTxFacilityCurrent1dayBroadcastFramesTrmt OBJECT-TYPE
    SYNTAX        Counter64String
    MAX-ACCESS    read-only
    STATUS        current
    DESCRIPTION   "Broadcast Frames Transmitted"
    ::= { l2PortTxFacilityCurrent1dayEntry 3 }

l2PortTxFacilityCurrent1dayMulticastFramesTrmt OBJECT-TYPE
    SYNTAX        Counter64String
    MAX-ACCESS    read-only
    STATUS        current
    DESCRIPTION   "Multicast Frames Received"
    ::= { l2PortTxFacilityCurrent1dayEntry 4 }

l2PortTxFacilityCurrent1dayPauseFramesTrmt OBJECT-TYPE
    SYNTAX        Counter64String
    MAX-ACCESS    read-only
    STATUS        current
    DESCRIPTION   "Pause Frames Transmitted"
    ::= { l2PortTxFacilityCurrent1dayEntry 5 }

l2PortTxFacilityCurrent1dayBytesFrames64Trmt OBJECT-TYPE
    SYNTAX        Counter64String
    MAX-ACCESS    read-only
    STATUS        current
    DESCRIPTION   "64 Byte Frames Transmitted"
    ::= { l2PortTxFacilityCurrent1dayEntry 6 }

l2PortTxFacilityCurrent1dayBytesFrames65Trmt OBJECT-TYPE
    SYNTAX        Counter64String
    MAX-ACCESS    read-only
    STATUS        current
    DESCRIPTION   "65-127 Byte Frames Transmitted"
    ::= { l2PortTxFacilityCurrent1dayEntry 7 }

l2PortTxFacilityCurrent1dayBytesFrames128Trmt OBJECT-TYPE
    SYNTAX        Counter64String
    MAX-ACCESS    read-only
    STATUS        current
    DESCRIPTION   "128-255 Byte Frames Transmitted"
    ::= { l2PortTxFacilityCurrent1dayEntry 8 }

l2PortTxFacilityCurrent1dayBytesFrames256Trmt OBJECT-TYPE
    SYNTAX        Counter64String
    MAX-ACCESS    read-only
    STATUS        current
    DESCRIPTION   "256-511 Byte Frames Transmitted"
    ::= { l2PortTxFacilityCurrent1dayEntry 9 }

l2PortTxFacilityCurrent1dayBytesFrames512Trmt OBJECT-TYPE
    SYNTAX        Counter64String
    MAX-ACCESS    read-only
    STATUS        current
    DESCRIPTION   "512-1023 Byte Frames Transmitted"
    ::= { l2PortTxFacilityCurrent1dayEntry 10 }

l2PortTxFacilityCurrent1dayBytesFrames1024Trmt OBJECT-TYPE
    SYNTAX        Counter64String
    MAX-ACCESS    read-only
    STATUS        current
    DESCRIPTION   "1024-1518 Byte Frames Transmitted"
    ::= { l2PortTxFacilityCurrent1dayEntry 11 }

l2PortTxFacilityCurrent1dayBytesFrames1519Trmt OBJECT-TYPE
    SYNTAX        Counter64String
    MAX-ACCESS    read-only
    STATUS        current
    DESCRIPTION   "1519-Max Byte Frames Transmitted"
    ::= { l2PortTxFacilityCurrent1dayEntry 12 }

l2PortTxFacilityCurrent1dayElapsedTime OBJECT-TYPE
    SYNTAX        Integer32 (0..86400)
    MAX-ACCESS    read-only
    STATUS        current
    DESCRIPTION   "Elapsed 1Day"
    ::= { l2PortTxFacilityCurrent1dayEntry 13 }

endOfL2PortTxFacilityCurrent1dayTable OBJECT-TYPE
    SYNTAX        Integer32
    MAX-ACCESS    read-only
    STATUS        current
    DESCRIPTION   ""
    ::= { pmFacilityDataRecord 132 }

l2PortTxFacilityHistorical15minTable OBJECT-TYPE
    SYNTAX        SEQUENCE OF L2PortTxFacilityHistorical15minEntry
    MAX-ACCESS    not-accessible
    STATUS        current
    DESCRIPTION   ""
    ::= { pmFacilityDataRecord 133 }

l2PortTxFacilityHistorical15minEntry OBJECT-TYPE
    SYNTAX        L2PortTxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  l2PortTxFacilityHistorical15minNumber
                }
    ::= { l2PortTxFacilityHistorical15minTable 1 }

L2PortTxFacilityHistorical15minEntry ::= SEQUENCE
  {    l2PortTxFacilityHistorical15minNumber Integer32,
    l2PortTxFacilityHistorical15minFramesTrmt Counter64String,
    l2PortTxFacilityHistorical15minBytesTrmt Counter64String,
    l2PortTxFacilityHistorical15minBroadcastFramesTrmt Counter64String,
    l2PortTxFacilityHistorical15minMulticastFramesTrmt Counter64String,
    l2PortTxFacilityHistorical15minPauseFramesTrmt Counter64String,
    l2PortTxFacilityHistorical15minBytesFrames64Trmt Counter64String,
    l2PortTxFacilityHistorical15minBytesFrames65Trmt Counter64String,
    l2PortTxFacilityHistorical15minBytesFrames128Trmt Counter64String,
    l2PortTxFacilityHistorical15minBytesFrames256Trmt Counter64String,
    l2PortTxFacilityHistorical15minBytesFrames512Trmt Counter64String,
    l2PortTxFacilityHistorical15minBytesFrames1024Trmt Counter64String,
    l2PortTxFacilityHistorical15minBytesFrames1519Trmt Counter64String,
    l2PortTxFacilityHistorical15minValidFlag TruthValue,
    l2PortTxFacilityHistorical15minTimeStamp DateAndTime }

l2PortTxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { l2PortTxFacilityHistorical15minEntry 1 }

l2PortTxFacilityHistorical15minFramesTrmt OBJECT-TYPE
    SYNTAX        Counter64String
    MAX-ACCESS    read-only
    STATUS        current
    DESCRIPTION   "Frames Transmitted"
    ::= { l2PortTxFacilityHistorical15minEntry 2 }

l2PortTxFacilityHistorical15minBytesTrmt OBJECT-TYPE
    SYNTAX        Counter64String
    MAX-ACCESS    read-only
    STATUS        current
    DESCRIPTION   "Bytes Transmitted"
    ::= { l2PortTxFacilityHistorical15minEntry 3 }

l2PortTxFacilityHistorical15minBroadcastFramesTrmt OBJECT-TYPE
    SYNTAX        Counter64String
    MAX-ACCESS    read-only
    STATUS        current
    DESCRIPTION   "Broadcast Frames Transmitted"
    ::= { l2PortTxFacilityHistorical15minEntry 4 }

l2PortTxFacilityHistorical15minMulticastFramesTrmt OBJECT-TYPE
    SYNTAX        Counter64String
    MAX-ACCESS    read-only
    STATUS        current
    DESCRIPTION   "Multicast Frames Received"
    ::= { l2PortTxFacilityHistorical15minEntry 5 }

l2PortTxFacilityHistorical15minPauseFramesTrmt OBJECT-TYPE
    SYNTAX        Counter64String
    MAX-ACCESS    read-only
    STATUS        current
    DESCRIPTION   "Pause Frames Transmitted"
    ::= { l2PortTxFacilityHistorical15minEntry 6 }

l2PortTxFacilityHistorical15minBytesFrames64Trmt OBJECT-TYPE
    SYNTAX        Counter64String
    MAX-ACCESS    read-only
    STATUS        current
    DESCRIPTION   "64 Byte Frames Transmitted"
    ::= { l2PortTxFacilityHistorical15minEntry 7 }

l2PortTxFacilityHistorical15minBytesFrames65Trmt OBJECT-TYPE
    SYNTAX        Counter64String
    MAX-ACCESS    read-only
    STATUS        current
    DESCRIPTION   "65-127 Byte Frames Transmitted"
    ::= { l2PortTxFacilityHistorical15minEntry 8 }

l2PortTxFacilityHistorical15minBytesFrames128Trmt OBJECT-TYPE
    SYNTAX        Counter64String
    MAX-ACCESS    read-only
    STATUS        current
    DESCRIPTION   "128-255 Byte Frames Transmitted"
    ::= { l2PortTxFacilityHistorical15minEntry 9 }

l2PortTxFacilityHistorical15minBytesFrames256Trmt OBJECT-TYPE
    SYNTAX        Counter64String
    MAX-ACCESS    read-only
    STATUS        current
    DESCRIPTION   "256-511 Byte Frames Transmitted"
    ::= { l2PortTxFacilityHistorical15minEntry 10 }

l2PortTxFacilityHistorical15minBytesFrames512Trmt OBJECT-TYPE
    SYNTAX        Counter64String
    MAX-ACCESS    read-only
    STATUS        current
    DESCRIPTION   "512-1023 Byte Frames Transmitted"
    ::= { l2PortTxFacilityHistorical15minEntry 11 }

l2PortTxFacilityHistorical15minBytesFrames1024Trmt OBJECT-TYPE
    SYNTAX        Counter64String
    MAX-ACCESS    read-only
    STATUS        current
    DESCRIPTION   "1024-1518 Byte Frames Transmitted"
    ::= { l2PortTxFacilityHistorical15minEntry 12 }

l2PortTxFacilityHistorical15minBytesFrames1519Trmt OBJECT-TYPE
    SYNTAX        Counter64String
    MAX-ACCESS    read-only
    STATUS        current
    DESCRIPTION   "1519-Max Byte Frames Transmitted"
    ::= { l2PortTxFacilityHistorical15minEntry 13 }

l2PortTxFacilityHistorical15minValidFlag OBJECT-TYPE
    SYNTAX        TruthValue
    MAX-ACCESS    read-only
    STATUS        current
    DESCRIPTION   "Valid Flag"
    ::= { l2PortTxFacilityHistorical15minEntry 14 }

l2PortTxFacilityHistorical15minTimeStamp OBJECT-TYPE
    SYNTAX        DateAndTime
    MAX-ACCESS    read-only
    STATUS        current
    DESCRIPTION   "Timestamp"
    ::= { l2PortTxFacilityHistorical15minEntry 15 }

endOfL2PortTxFacilityHistorical15minTable OBJECT-TYPE
    SYNTAX        Integer32
    MAX-ACCESS    read-only
    STATUS        current
    DESCRIPTION   ""
    ::= { pmFacilityDataRecord 134 }

l2PortTxFacilityHistorical1dayTable OBJECT-TYPE
    SYNTAX        SEQUENCE OF L2PortTxFacilityHistorical1dayEntry
    MAX-ACCESS    not-accessible
    STATUS        current
    DESCRIPTION   ""
    ::= { pmFacilityDataRecord 135 }

l2PortTxFacilityHistorical1dayEntry OBJECT-TYPE
    SYNTAX        L2PortTxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  l2PortTxFacilityHistorical1dayNumber
                }
    ::= { l2PortTxFacilityHistorical1dayTable 1 }

L2PortTxFacilityHistorical1dayEntry ::= SEQUENCE
  {    l2PortTxFacilityHistorical1dayNumber Integer32,
    l2PortTxFacilityHistorical1dayFramesTrmt Counter64String,
    l2PortTxFacilityHistorical1dayBytesTrmt Counter64String,
    l2PortTxFacilityHistorical1dayBroadcastFramesTrmt Counter64String,
    l2PortTxFacilityHistorical1dayMulticastFramesTrmt Counter64String,
    l2PortTxFacilityHistorical1dayPauseFramesTrmt Counter64String,
    l2PortTxFacilityHistorical1dayBytesFrames64Trmt Counter64String,
    l2PortTxFacilityHistorical1dayBytesFrames65Trmt Counter64String,
    l2PortTxFacilityHistorical1dayBytesFrames128Trmt Counter64String,
    l2PortTxFacilityHistorical1dayBytesFrames256Trmt Counter64String,
    l2PortTxFacilityHistorical1dayBytesFrames512Trmt Counter64String,
    l2PortTxFacilityHistorical1dayBytesFrames1024Trmt Counter64String,
    l2PortTxFacilityHistorical1dayBytesFrames1519Trmt Counter64String,
    l2PortTxFacilityHistorical1dayValidFlag TruthValue,
    l2PortTxFacilityHistorical1dayTimeStamp DateAndTime }

l2PortTxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { l2PortTxFacilityHistorical1dayEntry 1 }

l2PortTxFacilityHistorical1dayFramesTrmt OBJECT-TYPE
    SYNTAX        Counter64String
    MAX-ACCESS    read-only
    STATUS        current
    DESCRIPTION   "Frames Transmitted"
    ::= { l2PortTxFacilityHistorical1dayEntry 2 }

l2PortTxFacilityHistorical1dayBytesTrmt OBJECT-TYPE
    SYNTAX        Counter64String
    MAX-ACCESS    read-only
    STATUS        current
    DESCRIPTION   "Bytes Transmitted"
    ::= { l2PortTxFacilityHistorical1dayEntry 3 }

l2PortTxFacilityHistorical1dayBroadcastFramesTrmt OBJECT-TYPE
    SYNTAX        Counter64String
    MAX-ACCESS    read-only
    STATUS        current
    DESCRIPTION   "Broadcast Frames Transmitted"
    ::= { l2PortTxFacilityHistorical1dayEntry 4 }

l2PortTxFacilityHistorical1dayMulticastFramesTrmt OBJECT-TYPE
    SYNTAX        Counter64String
    MAX-ACCESS    read-only
    STATUS        current
    DESCRIPTION   "Multicast Frames Received"
    ::= { l2PortTxFacilityHistorical1dayEntry 5 }

l2PortTxFacilityHistorical1dayPauseFramesTrmt OBJECT-TYPE
    SYNTAX        Counter64String
    MAX-ACCESS    read-only
    STATUS        current
    DESCRIPTION   "Pause Frames Transmitted"
    ::= { l2PortTxFacilityHistorical1dayEntry 6 }

l2PortTxFacilityHistorical1dayBytesFrames64Trmt OBJECT-TYPE
    SYNTAX        Counter64String
    MAX-ACCESS    read-only
    STATUS        current
    DESCRIPTION   "64 Byte Frames Transmitted"
    ::= { l2PortTxFacilityHistorical1dayEntry 7 }

l2PortTxFacilityHistorical1dayBytesFrames65Trmt OBJECT-TYPE
    SYNTAX        Counter64String
    MAX-ACCESS    read-only
    STATUS        current
    DESCRIPTION   "65-127 Byte Frames Transmitted"
    ::= { l2PortTxFacilityHistorical1dayEntry 8 }

l2PortTxFacilityHistorical1dayBytesFrames128Trmt OBJECT-TYPE
    SYNTAX        Counter64String
    MAX-ACCESS    read-only
    STATUS        current
    DESCRIPTION   "128-255 Byte Frames Transmitted"
    ::= { l2PortTxFacilityHistorical1dayEntry 9 }

l2PortTxFacilityHistorical1dayBytesFrames256Trmt OBJECT-TYPE
    SYNTAX        Counter64String
    MAX-ACCESS    read-only
    STATUS        current
    DESCRIPTION   "256-511 Byte Frames Transmitted"
    ::= { l2PortTxFacilityHistorical1dayEntry 10 }

l2PortTxFacilityHistorical1dayBytesFrames512Trmt OBJECT-TYPE
    SYNTAX        Counter64String
    MAX-ACCESS    read-only
    STATUS        current
    DESCRIPTION   "512-1023 Byte Frames Transmitted"
    ::= { l2PortTxFacilityHistorical1dayEntry 11 }

l2PortTxFacilityHistorical1dayBytesFrames1024Trmt OBJECT-TYPE
    SYNTAX        Counter64String
    MAX-ACCESS    read-only
    STATUS        current
    DESCRIPTION   "1024-1518 Byte Frames Transmitted"
    ::= { l2PortTxFacilityHistorical1dayEntry 12 }

l2PortTxFacilityHistorical1dayBytesFrames1519Trmt OBJECT-TYPE
    SYNTAX        Counter64String
    MAX-ACCESS    read-only
    STATUS        current
    DESCRIPTION   "1519-Max Byte Frames Transmitted"
    ::= { l2PortTxFacilityHistorical1dayEntry 13 }

l2PortTxFacilityHistorical1dayValidFlag OBJECT-TYPE
    SYNTAX        TruthValue
    MAX-ACCESS    read-only
    STATUS        current
    DESCRIPTION   "Valid Flag"
    ::= { l2PortTxFacilityHistorical1dayEntry 14 }

l2PortTxFacilityHistorical1dayTimeStamp OBJECT-TYPE
    SYNTAX        DateAndTime
    MAX-ACCESS    read-only
    STATUS        current
    DESCRIPTION   "Timestamp"
    ::= { l2PortTxFacilityHistorical1dayEntry 15 }

endOfL2PortTxFacilityHistorical1dayTable OBJECT-TYPE
    SYNTAX        Integer32
    MAX-ACCESS    read-only
    STATUS        current
    DESCRIPTION   ""
    ::= { pmFacilityDataRecord 136 }

l2PortRxFacilityCurrent15minTable OBJECT-TYPE
    SYNTAX        SEQUENCE OF L2PortRxFacilityCurrent15minEntry
    MAX-ACCESS    not-accessible
    STATUS        current
    DESCRIPTION   ""
    ::= { pmFacilityDataRecord 137 }

l2PortRxFacilityCurrent15minEntry OBJECT-TYPE
    SYNTAX        L2PortRxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { l2PortRxFacilityCurrent15minTable 1 }

L2PortRxFacilityCurrent15minEntry ::= SEQUENCE
  {    l2PortRxFacilityCurrent15minFramesRcv Counter64String,
    l2PortRxFacilityCurrent15minBytesRcv Counter64String,
    l2PortRxFacilityCurrent15minBroadcastFramesRcv Counter64String,
    l2PortRxFacilityCurrent15minMulticastFramesRcv Counter64String,
    l2PortRxFacilityCurrent15minCrcErrorsRcv Counter64String,
    l2PortRxFacilityCurrent15minUndersizedFramesRcv Counter64String,
    l2PortRxFacilityCurrent15minOversizedFramesRcv Counter64String,
    l2PortRxFacilityCurrent15minPauseFramesRcv Counter64String,
    l2PortRxFacilityCurrent15minBytesFrames64Rcv Counter64String,
    l2PortRxFacilityCurrent15minBytesFrames65Rcv Counter64String,
    l2PortRxFacilityCurrent15minBytesFrames128Rcv Counter64String,
    l2PortRxFacilityCurrent15minBytesFrames256Rcv Counter64String,
    l2PortRxFacilityCurrent15minBytesFrames512Rcv Counter64String,
    l2PortRxFacilityCurrent15minBytesFrames1024Rcv Counter64String,
    l2PortRxFacilityCurrent15minBytesFrames1519Rcv Counter64String,
    l2PortRxFacilityCurrent15minInterPackJunkBytesFramesRcv Counter64String,
    l2PortRxFacilityCurrent15minElapsedTime Integer32 }

l2PortRxFacilityCurrent15minFramesRcv OBJECT-TYPE
    SYNTAX        Counter64String
    MAX-ACCESS    read-only
    STATUS        current
    DESCRIPTION   "Frames Received"
    ::= { l2PortRxFacilityCurrent15minEntry 1 }

l2PortRxFacilityCurrent15minBytesRcv OBJECT-TYPE
    SYNTAX        Counter64String
    MAX-ACCESS    read-only
    STATUS        current
    DESCRIPTION   "Bytes Received"
    ::= { l2PortRxFacilityCurrent15minEntry 2 }

l2PortRxFacilityCurrent15minBroadcastFramesRcv OBJECT-TYPE
    SYNTAX        Counter64String
    MAX-ACCESS    read-only
    STATUS        current
    DESCRIPTION   "Broadcast Frames Received"
    ::= { l2PortRxFacilityCurrent15minEntry 3 }

l2PortRxFacilityCurrent15minMulticastFramesRcv OBJECT-TYPE
    SYNTAX        Counter64String
    MAX-ACCESS    read-only
    STATUS        current
    DESCRIPTION   "Multicast Frames Received"
    ::= { l2PortRxFacilityCurrent15minEntry 4 }

l2PortRxFacilityCurrent15minCrcErrorsRcv OBJECT-TYPE
    SYNTAX        Counter64String
    MAX-ACCESS    read-only
    STATUS        current
    DESCRIPTION   "Received CRC Errors"
    ::= { l2PortRxFacilityCurrent15minEntry 5 }

l2PortRxFacilityCurrent15minUndersizedFramesRcv OBJECT-TYPE
    SYNTAX        Counter64String
    MAX-ACCESS    read-only
    STATUS        current
    DESCRIPTION   "Undersized Frames Received"
    ::= { l2PortRxFacilityCurrent15minEntry 6 }

l2PortRxFacilityCurrent15minOversizedFramesRcv OBJECT-TYPE
    SYNTAX        Counter64String
    MAX-ACCESS    read-only
    STATUS        current
    DESCRIPTION   "Oversized Frames Received"
    ::= { l2PortRxFacilityCurrent15minEntry 7 }

l2PortRxFacilityCurrent15minPauseFramesRcv OBJECT-TYPE
    SYNTAX        Counter64String
    MAX-ACCESS    read-only
    STATUS        current
    DESCRIPTION   "Pause Frames Received"
    ::= { l2PortRxFacilityCurrent15minEntry 8 }

l2PortRxFacilityCurrent15minBytesFrames64Rcv OBJECT-TYPE
    SYNTAX        Counter64String
    MAX-ACCESS    read-only
    STATUS        current
    DESCRIPTION   "64 Byte Frames Received"
    ::= { l2PortRxFacilityCurrent15minEntry 9 }

l2PortRxFacilityCurrent15minBytesFrames65Rcv OBJECT-TYPE
    SYNTAX        Counter64String
    MAX-ACCESS    read-only
    STATUS        current
    DESCRIPTION   "65-127 Byte Frames Received"
    ::= { l2PortRxFacilityCurrent15minEntry 10 }

l2PortRxFacilityCurrent15minBytesFrames128Rcv OBJECT-TYPE
    SYNTAX        Counter64String
    MAX-ACCESS    read-only
    STATUS        current
    DESCRIPTION   "128-255 Byte Frames Received"
    ::= { l2PortRxFacilityCurrent15minEntry 11 }

l2PortRxFacilityCurrent15minBytesFrames256Rcv OBJECT-TYPE
    SYNTAX        Counter64String
    MAX-ACCESS    read-only
    STATUS        current
    DESCRIPTION   "256-511 Byte Frames Received"
    ::= { l2PortRxFacilityCurrent15minEntry 12 }

l2PortRxFacilityCurrent15minBytesFrames512Rcv OBJECT-TYPE
    SYNTAX        Counter64String
    MAX-ACCESS    read-only
    STATUS        current
    DESCRIPTION   "512-1023 Byte Frames Received"
    ::= { l2PortRxFacilityCurrent15minEntry 13 }

l2PortRxFacilityCurrent15minBytesFrames1024Rcv OBJECT-TYPE
    SYNTAX        Counter64String
    MAX-ACCESS    read-only
    STATUS        current
    DESCRIPTION   "1024-1518 Byte Frames Received"
    ::= { l2PortRxFacilityCurrent15minEntry 14 }

l2PortRxFacilityCurrent15minBytesFrames1519Rcv OBJECT-TYPE
    SYNTAX        Counter64String
    MAX-ACCESS    read-only
    STATUS        current
    DESCRIPTION   "1519-Max Byte Frames Received"
    ::= { l2PortRxFacilityCurrent15minEntry 15 }

l2PortRxFacilityCurrent15minInterPackJunkBytesFramesRcv OBJECT-TYPE
    SYNTAX        Counter64String
    MAX-ACCESS    read-only
    STATUS        current
    DESCRIPTION   "InterPackJunk Bytes Frames Received (10Gbit/s only)"
    ::= { l2PortRxFacilityCurrent15minEntry 16 }

l2PortRxFacilityCurrent15minElapsedTime OBJECT-TYPE
    SYNTAX        Integer32 (0..9000)
    MAX-ACCESS    read-only
    STATUS        current
    DESCRIPTION   "Elapsed 15Min"
    ::= { l2PortRxFacilityCurrent15minEntry 17 }

endOfL2PortRxFacilityCurrent15minTable OBJECT-TYPE
    SYNTAX        Integer32
    MAX-ACCESS    read-only
    STATUS        current
    DESCRIPTION   ""
    ::= { pmFacilityDataRecord 138 }

l2PortRxFacilityCurrent1dayTable OBJECT-TYPE
    SYNTAX        SEQUENCE OF L2PortRxFacilityCurrent1dayEntry
    MAX-ACCESS    not-accessible
    STATUS        current
    DESCRIPTION   ""
    ::= { pmFacilityDataRecord 139 }

l2PortRxFacilityCurrent1dayEntry OBJECT-TYPE
    SYNTAX        L2PortRxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { l2PortRxFacilityCurrent1dayTable 1 }

L2PortRxFacilityCurrent1dayEntry ::= SEQUENCE
  {    l2PortRxFacilityCurrent1dayFramesRcv Counter64String,
    l2PortRxFacilityCurrent1dayBytesRcv Counter64String,
    l2PortRxFacilityCurrent1dayBroadcastFramesRcv Counter64String,
    l2PortRxFacilityCurrent1dayMulticastFramesRcv Counter64String,
    l2PortRxFacilityCurrent1dayCrcErrorsRcv Counter64String,
    l2PortRxFacilityCurrent1dayUndersizedFramesRcv Counter64String,
    l2PortRxFacilityCurrent1dayOversizedFramesRcv Counter64String,
    l2PortRxFacilityCurrent1dayPauseFramesRcv Counter64String,
    l2PortRxFacilityCurrent1dayBytesFrames64Rcv Counter64String,
    l2PortRxFacilityCurrent1dayBytesFrames65Rcv Counter64String,
    l2PortRxFacilityCurrent1dayBytesFrames128Rcv Counter64String,
    l2PortRxFacilityCurrent1dayBytesFrames256Rcv Counter64String,
    l2PortRxFacilityCurrent1dayBytesFrames512Rcv Counter64String,
    l2PortRxFacilityCurrent1dayBytesFrames1024Rcv Counter64String,
    l2PortRxFacilityCurrent1dayBytesFrames1519Rcv Counter64String,
    l2PortRxFacilityCurrent1dayInterPackJunkBytesFramesRcv Counter64String,
    l2PortRxFacilityCurrent1dayElapsedTime Integer32 }

l2PortRxFacilityCurrent1dayFramesRcv OBJECT-TYPE
    SYNTAX        Counter64String
    MAX-ACCESS    read-only
    STATUS        current
    DESCRIPTION   "Frames Received"
    ::= { l2PortRxFacilityCurrent1dayEntry 1 }

l2PortRxFacilityCurrent1dayBytesRcv OBJECT-TYPE
    SYNTAX        Counter64String
    MAX-ACCESS    read-only
    STATUS        current
    DESCRIPTION   "Bytes Received"
    ::= { l2PortRxFacilityCurrent1dayEntry 2 }

l2PortRxFacilityCurrent1dayBroadcastFramesRcv OBJECT-TYPE
    SYNTAX        Counter64String
    MAX-ACCESS    read-only
    STATUS        current
    DESCRIPTION   "Broadcast Frames Received"
    ::= { l2PortRxFacilityCurrent1dayEntry 3 }

l2PortRxFacilityCurrent1dayMulticastFramesRcv OBJECT-TYPE
    SYNTAX        Counter64String
    MAX-ACCESS    read-only
    STATUS        current
    DESCRIPTION   "Multicast Frames Received"
    ::= { l2PortRxFacilityCurrent1dayEntry 4 }

l2PortRxFacilityCurrent1dayCrcErrorsRcv OBJECT-TYPE
    SYNTAX        Counter64String
    MAX-ACCESS    read-only
    STATUS        current
    DESCRIPTION   "Received CRC Errors"
    ::= { l2PortRxFacilityCurrent1dayEntry 5 }

l2PortRxFacilityCurrent1dayUndersizedFramesRcv OBJECT-TYPE
    SYNTAX        Counter64String
    MAX-ACCESS    read-only
    STATUS        current
    DESCRIPTION   "Undersized Frames Received"
    ::= { l2PortRxFacilityCurrent1dayEntry 6 }

l2PortRxFacilityCurrent1dayOversizedFramesRcv OBJECT-TYPE
    SYNTAX        Counter64String
    MAX-ACCESS    read-only
    STATUS        current
    DESCRIPTION   "Oversized Frames Received"
    ::= { l2PortRxFacilityCurrent1dayEntry 7 }

l2PortRxFacilityCurrent1dayPauseFramesRcv OBJECT-TYPE
    SYNTAX        Counter64String
    MAX-ACCESS    read-only
    STATUS        current
    DESCRIPTION   "Pause Frames Received"
    ::= { l2PortRxFacilityCurrent1dayEntry 8 }

l2PortRxFacilityCurrent1dayBytesFrames64Rcv OBJECT-TYPE
    SYNTAX        Counter64String
    MAX-ACCESS    read-only
    STATUS        current
    DESCRIPTION   "64 Byte Frames Received"
    ::= { l2PortRxFacilityCurrent1dayEntry 9 }

l2PortRxFacilityCurrent1dayBytesFrames65Rcv OBJECT-TYPE
    SYNTAX        Counter64String
    MAX-ACCESS    read-only
    STATUS        current
    DESCRIPTION   "65-127 Byte Frames Received"
    ::= { l2PortRxFacilityCurrent1dayEntry 10 }

l2PortRxFacilityCurrent1dayBytesFrames128Rcv OBJECT-TYPE
    SYNTAX        Counter64String
    MAX-ACCESS    read-only
    STATUS        current
    DESCRIPTION   "128-255 Byte Frames Received"
    ::= { l2PortRxFacilityCurrent1dayEntry 11 }

l2PortRxFacilityCurrent1dayBytesFrames256Rcv OBJECT-TYPE
    SYNTAX        Counter64String
    MAX-ACCESS    read-only
    STATUS        current
    DESCRIPTION   "256-511 Byte Frames Received"
    ::= { l2PortRxFacilityCurrent1dayEntry 12 }

l2PortRxFacilityCurrent1dayBytesFrames512Rcv OBJECT-TYPE
    SYNTAX        Counter64String
    MAX-ACCESS    read-only
    STATUS        current
    DESCRIPTION   "512-1023 Byte Frames Received"
    ::= { l2PortRxFacilityCurrent1dayEntry 13 }

l2PortRxFacilityCurrent1dayBytesFrames1024Rcv OBJECT-TYPE
    SYNTAX        Counter64String
    MAX-ACCESS    read-only
    STATUS        current
    DESCRIPTION   "1024-1518 Byte Frames Received"
    ::= { l2PortRxFacilityCurrent1dayEntry 14 }

l2PortRxFacilityCurrent1dayBytesFrames1519Rcv OBJECT-TYPE
    SYNTAX        Counter64String
    MAX-ACCESS    read-only
    STATUS        current
    DESCRIPTION   "1519-Max Byte Frames Received"
    ::= { l2PortRxFacilityCurrent1dayEntry 15 }

l2PortRxFacilityCurrent1dayInterPackJunkBytesFramesRcv OBJECT-TYPE
    SYNTAX        Counter64String
    MAX-ACCESS    read-only
    STATUS        current
    DESCRIPTION   "InterPackJunk Bytes Frames Received (10Gbit/s only)"
    ::= { l2PortRxFacilityCurrent1dayEntry 16 }

l2PortRxFacilityCurrent1dayElapsedTime OBJECT-TYPE
    SYNTAX        Integer32 (0..86400)
    MAX-ACCESS    read-only
    STATUS        current
    DESCRIPTION   "Elapsed 1Day"
    ::= { l2PortRxFacilityCurrent1dayEntry 17 }

endOfL2PortRxFacilityCurrent1dayTable OBJECT-TYPE
    SYNTAX        Integer32
    MAX-ACCESS    read-only
    STATUS        current
    DESCRIPTION   ""
    ::= { pmFacilityDataRecord 140 }

l2PortRxFacilityHistorical15minTable OBJECT-TYPE
    SYNTAX        SEQUENCE OF L2PortRxFacilityHistorical15minEntry
    MAX-ACCESS    not-accessible
    STATUS        current
    DESCRIPTION   ""
    ::= { pmFacilityDataRecord 141 }

l2PortRxFacilityHistorical15minEntry OBJECT-TYPE
    SYNTAX        L2PortRxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  l2PortRxFacilityHistorical15minNumber
                }
    ::= { l2PortRxFacilityHistorical15minTable 1 }

L2PortRxFacilityHistorical15minEntry ::= SEQUENCE
  {    l2PortRxFacilityHistorical15minNumber Integer32,
    l2PortRxFacilityHistorical15minFramesRcv Counter64String,
    l2PortRxFacilityHistorical15minBytesRcv Counter64String,
    l2PortRxFacilityHistorical15minBroadcastFramesRcv Counter64String,
    l2PortRxFacilityHistorical15minMulticastFramesRcv Counter64String,
    l2PortRxFacilityHistorical15minCrcErrorsRcv Counter64String,
    l2PortRxFacilityHistorical15minUndersizedFramesRcv Counter64String,
    l2PortRxFacilityHistorical15minOversizedFramesRcv Counter64String,
    l2PortRxFacilityHistorical15minPauseFramesRcv Counter64String,
    l2PortRxFacilityHistorical15minBytesFrames64Rcv Counter64String,
    l2PortRxFacilityHistorical15minBytesFrames65Rcv Counter64String,
    l2PortRxFacilityHistorical15minBytesFrames128Rcv Counter64String,
    l2PortRxFacilityHistorical15minBytesFrames256Rcv Counter64String,
    l2PortRxFacilityHistorical15minBytesFrames512Rcv Counter64String,
    l2PortRxFacilityHistorical15minBytesFrames1024Rcv Counter64String,
    l2PortRxFacilityHistorical15minBytesFrames1519Rcv Counter64String,
    l2PortRxFacilityHistorical15minInterPackJunkBytesFramesRcv Counter64String,
    l2PortRxFacilityHistorical15minValidFlag TruthValue,
    l2PortRxFacilityHistorical15minTimeStamp DateAndTime }

l2PortRxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { l2PortRxFacilityHistorical15minEntry 1 }

l2PortRxFacilityHistorical15minFramesRcv OBJECT-TYPE
    SYNTAX        Counter64String
    MAX-ACCESS    read-only
    STATUS        current
    DESCRIPTION   "Frames Received"
    ::= { l2PortRxFacilityHistorical15minEntry 2 }

l2PortRxFacilityHistorical15minBytesRcv OBJECT-TYPE
    SYNTAX        Counter64String
    MAX-ACCESS    read-only
    STATUS        current
    DESCRIPTION   "Bytes Received"
    ::= { l2PortRxFacilityHistorical15minEntry 3 }

l2PortRxFacilityHistorical15minBroadcastFramesRcv OBJECT-TYPE
    SYNTAX        Counter64String
    MAX-ACCESS    read-only
    STATUS        current
    DESCRIPTION   "Broadcast Frames Received"
    ::= { l2PortRxFacilityHistorical15minEntry 4 }

l2PortRxFacilityHistorical15minMulticastFramesRcv OBJECT-TYPE
    SYNTAX        Counter64String
    MAX-ACCESS    read-only
    STATUS        current
    DESCRIPTION   "Multicast Frames Received"
    ::= { l2PortRxFacilityHistorical15minEntry 5 }

l2PortRxFacilityHistorical15minCrcErrorsRcv OBJECT-TYPE
    SYNTAX        Counter64String
    MAX-ACCESS    read-only
    STATUS        current
    DESCRIPTION   "Received CRC Errors"
    ::= { l2PortRxFacilityHistorical15minEntry 6 }

l2PortRxFacilityHistorical15minUndersizedFramesRcv OBJECT-TYPE
    SYNTAX        Counter64String
    MAX-ACCESS    read-only
    STATUS        current
    DESCRIPTION   "Undersized Frames Received"
    ::= { l2PortRxFacilityHistorical15minEntry 7 }

l2PortRxFacilityHistorical15minOversizedFramesRcv OBJECT-TYPE
    SYNTAX        Counter64String
    MAX-ACCESS    read-only
    STATUS        current
    DESCRIPTION   "Oversized Frames Received"
    ::= { l2PortRxFacilityHistorical15minEntry 8 }

l2PortRxFacilityHistorical15minPauseFramesRcv OBJECT-TYPE
    SYNTAX        Counter64String
    MAX-ACCESS    read-only
    STATUS        current
    DESCRIPTION   "Pause Frames Received"
    ::= { l2PortRxFacilityHistorical15minEntry 9 }

l2PortRxFacilityHistorical15minBytesFrames64Rcv OBJECT-TYPE
    SYNTAX        Counter64String
    MAX-ACCESS    read-only
    STATUS        current
    DESCRIPTION   "64 Byte Frames Received"
    ::= { l2PortRxFacilityHistorical15minEntry 10 }

l2PortRxFacilityHistorical15minBytesFrames65Rcv OBJECT-TYPE
    SYNTAX        Counter64String
    MAX-ACCESS    read-only
    STATUS        current
    DESCRIPTION   "65-127 Byte Frames Received"
    ::= { l2PortRxFacilityHistorical15minEntry 11 }

l2PortRxFacilityHistorical15minBytesFrames128Rcv OBJECT-TYPE
    SYNTAX        Counter64String
    MAX-ACCESS    read-only
    STATUS        current
    DESCRIPTION   "128-255 Byte Frames Received"
    ::= { l2PortRxFacilityHistorical15minEntry 12 }

l2PortRxFacilityHistorical15minBytesFrames256Rcv OBJECT-TYPE
    SYNTAX        Counter64String
    MAX-ACCESS    read-only
    STATUS        current
    DESCRIPTION   "256-511 Byte Frames Received"
    ::= { l2PortRxFacilityHistorical15minEntry 13 }

l2PortRxFacilityHistorical15minBytesFrames512Rcv OBJECT-TYPE
    SYNTAX        Counter64String
    MAX-ACCESS    read-only
    STATUS        current
    DESCRIPTION   "512-1023 Byte Frames Received"
    ::= { l2PortRxFacilityHistorical15minEntry 14 }

l2PortRxFacilityHistorical15minBytesFrames1024Rcv OBJECT-TYPE
    SYNTAX        Counter64String
    MAX-ACCESS    read-only
    STATUS        current
    DESCRIPTION   "1024-1518 Byte Frames Received"
    ::= { l2PortRxFacilityHistorical15minEntry 15 }

l2PortRxFacilityHistorical15minBytesFrames1519Rcv OBJECT-TYPE
    SYNTAX        Counter64String
    MAX-ACCESS    read-only
    STATUS        current
    DESCRIPTION   "1519-Max Byte Frames Received"
    ::= { l2PortRxFacilityHistorical15minEntry 16 }

l2PortRxFacilityHistorical15minInterPackJunkBytesFramesRcv OBJECT-TYPE
    SYNTAX        Counter64String
    MAX-ACCESS    read-only
    STATUS        current
    DESCRIPTION   "InterPackJunk Bytes Frames Received (10Gbit/s only)"
    ::= { l2PortRxFacilityHistorical15minEntry 17 }

l2PortRxFacilityHistorical15minValidFlag OBJECT-TYPE
    SYNTAX        TruthValue
    MAX-ACCESS    read-only
    STATUS        current
    DESCRIPTION   "Valid Flag"
    ::= { l2PortRxFacilityHistorical15minEntry 18 }

l2PortRxFacilityHistorical15minTimeStamp OBJECT-TYPE
    SYNTAX        DateAndTime
    MAX-ACCESS    read-only
    STATUS        current
    DESCRIPTION   "Timestamp"
    ::= { l2PortRxFacilityHistorical15minEntry 19 }

endOfL2PortRxFacilityHistorical15minTable OBJECT-TYPE
    SYNTAX        Integer32
    MAX-ACCESS    read-only
    STATUS        current
    DESCRIPTION   ""
    ::= { pmFacilityDataRecord 142 }

l2PortRxFacilityHistorical1dayTable OBJECT-TYPE
    SYNTAX        SEQUENCE OF L2PortRxFacilityHistorical1dayEntry
    MAX-ACCESS    not-accessible
    STATUS        current
    DESCRIPTION   ""
    ::= { pmFacilityDataRecord 143 }

l2PortRxFacilityHistorical1dayEntry OBJECT-TYPE
    SYNTAX        L2PortRxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  l2PortRxFacilityHistorical1dayNumber
                }
    ::= { l2PortRxFacilityHistorical1dayTable 1 }

L2PortRxFacilityHistorical1dayEntry ::= SEQUENCE
  {    l2PortRxFacilityHistorical1dayNumber Integer32,
    l2PortRxFacilityHistorical1dayFramesRcv Counter64String,
    l2PortRxFacilityHistorical1dayBytesRcv Counter64String,
    l2PortRxFacilityHistorical1dayBroadcastFramesRcv Counter64String,
    l2PortRxFacilityHistorical1dayMulticastFramesRcv Counter64String,
    l2PortRxFacilityHistorical1dayCrcErrorsRcv Counter64String,
    l2PortRxFacilityHistorical1dayUndersizedFramesRcv Counter64String,
    l2PortRxFacilityHistorical1dayOversizedFramesRcv Counter64String,
    l2PortRxFacilityHistorical1dayPauseFramesRcv Counter64String,
    l2PortRxFacilityHistorical1dayBytesFrames64Rcv Counter64String,
    l2PortRxFacilityHistorical1dayBytesFrames65Rcv Counter64String,
    l2PortRxFacilityHistorical1dayBytesFrames128Rcv Counter64String,
    l2PortRxFacilityHistorical1dayBytesFrames256Rcv Counter64String,
    l2PortRxFacilityHistorical1dayBytesFrames512Rcv Counter64String,
    l2PortRxFacilityHistorical1dayBytesFrames1024Rcv Counter64String,
    l2PortRxFacilityHistorical1dayBytesFrames1519Rcv Counter64String,
    l2PortRxFacilityHistorical1dayInterPackJunkBytesFramesRcv Counter64String,
    l2PortRxFacilityHistorical1dayValidFlag TruthValue,
    l2PortRxFacilityHistorical1dayTimeStamp DateAndTime }

l2PortRxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { l2PortRxFacilityHistorical1dayEntry 1 }

l2PortRxFacilityHistorical1dayFramesRcv OBJECT-TYPE
    SYNTAX        Counter64String
    MAX-ACCESS    read-only
    STATUS        current
    DESCRIPTION   "Frames Received"
    ::= { l2PortRxFacilityHistorical1dayEntry 2 }

l2PortRxFacilityHistorical1dayBytesRcv OBJECT-TYPE
    SYNTAX        Counter64String
    MAX-ACCESS    read-only
    STATUS        current
    DESCRIPTION   "Bytes Received"
    ::= { l2PortRxFacilityHistorical1dayEntry 3 }

l2PortRxFacilityHistorical1dayBroadcastFramesRcv OBJECT-TYPE
    SYNTAX        Counter64String
    MAX-ACCESS    read-only
    STATUS        current
    DESCRIPTION   "Broadcast Frames Received"
    ::= { l2PortRxFacilityHistorical1dayEntry 4 }

l2PortRxFacilityHistorical1dayMulticastFramesRcv OBJECT-TYPE
    SYNTAX        Counter64String
    MAX-ACCESS    read-only
    STATUS        current
    DESCRIPTION   "Multicast Frames Received"
    ::= { l2PortRxFacilityHistorical1dayEntry 5 }

l2PortRxFacilityHistorical1dayCrcErrorsRcv OBJECT-TYPE
    SYNTAX        Counter64String
    MAX-ACCESS    read-only
    STATUS        current
    DESCRIPTION   "Received CRC Errors"
    ::= { l2PortRxFacilityHistorical1dayEntry 6 }

l2PortRxFacilityHistorical1dayUndersizedFramesRcv OBJECT-TYPE
    SYNTAX        Counter64String
    MAX-ACCESS    read-only
    STATUS        current
    DESCRIPTION   "Undersized Frames Received"
    ::= { l2PortRxFacilityHistorical1dayEntry 7 }

l2PortRxFacilityHistorical1dayOversizedFramesRcv OBJECT-TYPE
    SYNTAX        Counter64String
    MAX-ACCESS    read-only
    STATUS        current
    DESCRIPTION   "Oversized Frames Received"
    ::= { l2PortRxFacilityHistorical1dayEntry 8 }

l2PortRxFacilityHistorical1dayPauseFramesRcv OBJECT-TYPE
    SYNTAX        Counter64String
    MAX-ACCESS    read-only
    STATUS        current
    DESCRIPTION   "Pause Frames Received"
    ::= { l2PortRxFacilityHistorical1dayEntry 9 }

l2PortRxFacilityHistorical1dayBytesFrames64Rcv OBJECT-TYPE
    SYNTAX        Counter64String
    MAX-ACCESS    read-only
    STATUS        current
    DESCRIPTION   "64 Byte Frames Received"
    ::= { l2PortRxFacilityHistorical1dayEntry 10 }

l2PortRxFacilityHistorical1dayBytesFrames65Rcv OBJECT-TYPE
    SYNTAX        Counter64String
    MAX-ACCESS    read-only
    STATUS        current
    DESCRIPTION   "65-127 Byte Frames Received"
    ::= { l2PortRxFacilityHistorical1dayEntry 11 }

l2PortRxFacilityHistorical1dayBytesFrames128Rcv OBJECT-TYPE
    SYNTAX        Counter64String
    MAX-ACCESS    read-only
    STATUS        current
    DESCRIPTION   "128-255 Byte Frames Received"
    ::= { l2PortRxFacilityHistorical1dayEntry 12 }

l2PortRxFacilityHistorical1dayBytesFrames256Rcv OBJECT-TYPE
    SYNTAX        Counter64String
    MAX-ACCESS    read-only
    STATUS        current
    DESCRIPTION   "256-511 Byte Frames Received"
    ::= { l2PortRxFacilityHistorical1dayEntry 13 }

l2PortRxFacilityHistorical1dayBytesFrames512Rcv OBJECT-TYPE
    SYNTAX        Counter64String
    MAX-ACCESS    read-only
    STATUS        current
    DESCRIPTION   "512-1023 Byte Frames Received"
    ::= { l2PortRxFacilityHistorical1dayEntry 14 }

l2PortRxFacilityHistorical1dayBytesFrames1024Rcv OBJECT-TYPE
    SYNTAX        Counter64String
    MAX-ACCESS    read-only
    STATUS        current
    DESCRIPTION   "1024-1518 Byte Frames Received"
    ::= { l2PortRxFacilityHistorical1dayEntry 15 }

l2PortRxFacilityHistorical1dayBytesFrames1519Rcv OBJECT-TYPE
    SYNTAX        Counter64String
    MAX-ACCESS    read-only
    STATUS        current
    DESCRIPTION   "1519-Max Byte Frames Received"
    ::= { l2PortRxFacilityHistorical1dayEntry 16 }

l2PortRxFacilityHistorical1dayInterPackJunkBytesFramesRcv OBJECT-TYPE
    SYNTAX        Counter64String
    MAX-ACCESS    read-only
    STATUS        current
    DESCRIPTION   "InterPackJunk Bytes Frames Received (10Gbit/s only)"
    ::= { l2PortRxFacilityHistorical1dayEntry 17 }

l2PortRxFacilityHistorical1dayValidFlag OBJECT-TYPE
    SYNTAX        TruthValue
    MAX-ACCESS    read-only
    STATUS        current
    DESCRIPTION   "Valid Flag"
    ::= { l2PortRxFacilityHistorical1dayEntry 18 }

l2PortRxFacilityHistorical1dayTimeStamp OBJECT-TYPE
    SYNTAX        DateAndTime
    MAX-ACCESS    read-only
    STATUS        current
    DESCRIPTION   "Timestamp"
    ::= { l2PortRxFacilityHistorical1dayEntry 19 }

endOfL2PortRxFacilityHistorical1dayTable OBJECT-TYPE
    SYNTAX        Integer32
    MAX-ACCESS    read-only
    STATUS        current
    DESCRIPTION   ""
    ::= { pmFacilityDataRecord 144 }

frRcv1FacilityCurrent15minTable OBJECT-TYPE
    SYNTAX        SEQUENCE OF FrRcv1FacilityCurrent15minEntry
    MAX-ACCESS    not-accessible
    STATUS        current
    DESCRIPTION   ""
    ::= { pmFacilityDataRecord 145 }

frRcv1FacilityCurrent15minEntry OBJECT-TYPE
    SYNTAX        FrRcv1FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv1FacilityCurrent15minTable 1 }

FrRcv1FacilityCurrent15minEntry ::= SEQUENCE
  {    frRcv1FacilityCurrent15minGoodFrames Counter64String,
    frRcv1FacilityCurrent15minPauseFrames Counter64String,
    frRcv1FacilityCurrent15minCrcFrames Counter64String,
    frRcv1FacilityCurrent15minDiscardedFrames Counter64String,
    frRcv1FacilityCurrent15minBytes Counter64String,
    frRcv1FacilityCurrent15minElapsedTime Integer32 }

frRcv1FacilityCurrent15minGoodFrames OBJECT-TYPE
    SYNTAX        Counter64String
    MAX-ACCESS    read-only
    STATUS        current
    DESCRIPTION   "Frames Received"
    ::= { frRcv1FacilityCurrent15minEntry 1 }

frRcv1FacilityCurrent15minPauseFrames OBJECT-TYPE
    SYNTAX        Counter64String
    MAX-ACCESS    read-only
    STATUS        current
    DESCRIPTION   "Pause Frames Received"
    ::= { frRcv1FacilityCurrent15minEntry 2 }

frRcv1FacilityCurrent15minCrcFrames OBJECT-TYPE
    SYNTAX        Counter64String
    MAX-ACCESS    read-only
    STATUS        current
    DESCRIPTION   "Received CRC Errors"
    ::= { frRcv1FacilityCurrent15minEntry 3 }

frRcv1FacilityCurrent15minDiscardedFrames OBJECT-TYPE
    SYNTAX        Counter64String
    MAX-ACCESS    read-only
    STATUS        current
    DESCRIPTION   "Received Frames Discarded"
    ::= { frRcv1FacilityCurrent15minEntry 4 }

frRcv1FacilityCurrent15minBytes OBJECT-TYPE
    SYNTAX        Counter64String
    MAX-ACCESS    read-only
    STATUS        current
    DESCRIPTION   "Bytes Received"
    ::= { frRcv1FacilityCurrent15minEntry 5 }

frRcv1FacilityCurrent15minElapsedTime OBJECT-TYPE
    SYNTAX        Integer32 (0..9000)
    MAX-ACCESS    read-only
    STATUS        current
    DESCRIPTION   "Elapsed 15Min"
    ::= { frRcv1FacilityCurrent15minEntry 6 }

endOfFrRcv1FacilityCurrent15minTable OBJECT-TYPE
    SYNTAX        Integer32
    MAX-ACCESS    read-only
    STATUS        current
    DESCRIPTION   ""
    ::= { pmFacilityDataRecord 146 }

frRcv1FacilityCurrent1dayTable OBJECT-TYPE
    SYNTAX        SEQUENCE OF FrRcv1FacilityCurrent1dayEntry
    MAX-ACCESS    not-accessible
    STATUS        current
    DESCRIPTION   ""
    ::= { pmFacilityDataRecord 147 }

frRcv1FacilityCurrent1dayEntry OBJECT-TYPE
    SYNTAX        FrRcv1FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv1FacilityCurrent1dayTable 1 }

FrRcv1FacilityCurrent1dayEntry ::= SEQUENCE
  {    frRcv1FacilityCurrent1dayGoodFrames Counter64String,
    frRcv1FacilityCurrent1dayPauseFrames Counter64String,
    frRcv1FacilityCurrent1dayCrcFrames Counter64String,
    frRcv1FacilityCurrent1dayDiscardedFrames Counter64String,
    frRcv1FacilityCurrent1dayBytes Counter64String,
    frRcv1FacilityCurrent1dayElapsedTime Integer32 }

frRcv1FacilityCurrent1dayGoodFrames OBJECT-TYPE
    SYNTAX        Counter64String
    MAX-ACCESS    read-only
    STATUS        current
    DESCRIPTION   "Frames Received"
    ::= { frRcv1FacilityCurrent1dayEntry 1 }

frRcv1FacilityCurrent1dayPauseFrames OBJECT-TYPE
    SYNTAX        Counter64String
    MAX-ACCESS    read-only
    STATUS        current
    DESCRIPTION   "Pause Frames Received"
    ::= { frRcv1FacilityCurrent1dayEntry 2 }

frRcv1FacilityCurrent1dayCrcFrames OBJECT-TYPE
    SYNTAX        Counter64String
    MAX-ACCESS    read-only
    STATUS        current
    DESCRIPTION   "Received CRC Errors"
    ::= { frRcv1FacilityCurrent1dayEntry 3 }

frRcv1FacilityCurrent1dayDiscardedFrames OBJECT-TYPE
    SYNTAX        Counter64String
    MAX-ACCESS    read-only
    STATUS        current
    DESCRIPTION   "Received Frames Discarded"
    ::= { frRcv1FacilityCurrent1dayEntry 4 }

frRcv1FacilityCurrent1dayBytes OBJECT-TYPE
    SYNTAX        Counter64String
    MAX-ACCESS    read-only
    STATUS        current
    DESCRIPTION   "Bytes Received"
    ::= { frRcv1FacilityCurrent1dayEntry 5 }

frRcv1FacilityCurrent1dayElapsedTime OBJECT-TYPE
    SYNTAX        Integer32 (0..86400)
    MAX-ACCESS    read-only
    STATUS        current
    DESCRIPTION   "Elapsed 1Day"
    ::= { frRcv1FacilityCurrent1dayEntry 6 }

endOfFrRcv1FacilityCurrent1dayTable OBJECT-TYPE
    SYNTAX        Integer32
    MAX-ACCESS    read-only
    STATUS        current
    DESCRIPTION   ""
    ::= { pmFacilityDataRecord 148 }

frRcv1FacilityHistorical15minTable OBJECT-TYPE
    SYNTAX        SEQUENCE OF FrRcv1FacilityHistorical15minEntry
    MAX-ACCESS    not-accessible
    STATUS        current
    DESCRIPTION   ""
    ::= { pmFacilityDataRecord 149 }

frRcv1FacilityHistorical15minEntry OBJECT-TYPE
    SYNTAX        FrRcv1FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv1FacilityHistorical15minNumber
                }
    ::= { frRcv1FacilityHistorical15minTable 1 }

FrRcv1FacilityHistorical15minEntry ::= SEQUENCE
  {    frRcv1FacilityHistorical15minNumber Integer32,
    frRcv1FacilityHistorical15minGoodFrames Counter64String,
    frRcv1FacilityHistorical15minPauseFrames Counter64String,
    frRcv1FacilityHistorical15minCrcFrames Counter64String,
    frRcv1FacilityHistorical15minDiscardedFrames Counter64String,
    frRcv1FacilityHistorical15minBytes Counter64String,
    frRcv1FacilityHistorical15minValidFlag TruthValue,
    frRcv1FacilityHistorical15minTimeStamp DateAndTime }

frRcv1FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frRcv1FacilityHistorical15minEntry 1 }

frRcv1FacilityHistorical15minGoodFrames OBJECT-TYPE
    SYNTAX        Counter64String
    MAX-ACCESS    read-only
    STATUS        current
    DESCRIPTION   "Frames Received"
    ::= { frRcv1FacilityHistorical15minEntry 2 }

frRcv1FacilityHistorical15minPauseFrames OBJECT-TYPE
    SYNTAX        Counter64String
    MAX-ACCESS    read-only
    STATUS        current
    DESCRIPTION   "Pause Frames Received"
    ::= { frRcv1FacilityHistorical15minEntry 3 }

frRcv1FacilityHistorical15minCrcFrames OBJECT-TYPE
    SYNTAX        Counter64String
    MAX-ACCESS    read-only
    STATUS        current
    DESCRIPTION   "Received CRC Errors"
    ::= { frRcv1FacilityHistorical15minEntry 4 }

frRcv1FacilityHistorical15minDiscardedFrames OBJECT-TYPE
    SYNTAX        Counter64String
    MAX-ACCESS    read-only
    STATUS        current
    DESCRIPTION   "Received Frames Discarded"
    ::= { frRcv1FacilityHistorical15minEntry 5 }

frRcv1FacilityHistorical15minBytes OBJECT-TYPE
    SYNTAX        Counter64String
    MAX-ACCESS    read-only
    STATUS        current
    DESCRIPTION   "Bytes Received"
    ::= { frRcv1FacilityHistorical15minEntry 6 }

frRcv1FacilityHistorical15minValidFlag OBJECT-TYPE
    SYNTAX        TruthValue
    MAX-ACCESS    read-only
    STATUS        current
    DESCRIPTION   "Valid Flag"
    ::= { frRcv1FacilityHistorical15minEntry 7 }

frRcv1FacilityHistorical15minTimeStamp OBJECT-TYPE
    SYNTAX        DateAndTime
    MAX-ACCESS    read-only
    STATUS        current
    DESCRIPTION   "Timestamp"
    ::= { frRcv1FacilityHistorical15minEntry 8 }

endOfFrRcv1FacilityHistorical15minTable OBJECT-TYPE
    SYNTAX        Integer32
    MAX-ACCESS    read-only
    STATUS        current
    DESCRIPTION   ""
    ::= { pmFacilityDataRecord 150 }

frRcv1FacilityHistorical1dayTable OBJECT-TYPE
    SYNTAX        SEQUENCE OF FrRcv1FacilityHistorical1dayEntry
    MAX-ACCESS    not-accessible
    STATUS        current
    DESCRIPTION   ""
    ::= { pmFacilityDataRecord 151 }

frRcv1FacilityHistorical1dayEntry OBJECT-TYPE
    SYNTAX        FrRcv1FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv1FacilityHistorical1dayNumber
                }
    ::= { frRcv1FacilityHistorical1dayTable 1 }

FrRcv1FacilityHistorical1dayEntry ::= SEQUENCE
  {    frRcv1FacilityHistorical1dayNumber Integer32,
    frRcv1FacilityHistorical1dayGoodFrames Counter64String,
    frRcv1FacilityHistorical1dayPauseFrames Counter64String,
    frRcv1FacilityHistorical1dayCrcFrames Counter64String,
    frRcv1FacilityHistorical1dayDiscardedFrames Counter64String,
    frRcv1FacilityHistorical1dayBytes Counter64String,
    frRcv1FacilityHistorical1dayValidFlag TruthValue,
    frRcv1FacilityHistorical1dayTimeStamp DateAndTime }

frRcv1FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frRcv1FacilityHistorical1dayEntry 1 }

frRcv1FacilityHistorical1dayGoodFrames OBJECT-TYPE
    SYNTAX        Counter64String
    MAX-ACCESS    read-only
    STATUS        current
    DESCRIPTION   "Frames Received"
    ::= { frRcv1FacilityHistorical1dayEntry 2 }

frRcv1FacilityHistorical1dayPauseFrames OBJECT-TYPE
    SYNTAX        Counter64String
    MAX-ACCESS    read-only
    STATUS        current
    DESCRIPTION   "Pause Frames Received"
    ::= { frRcv1FacilityHistorical1dayEntry 3 }

frRcv1FacilityHistorical1dayCrcFrames OBJECT-TYPE
    SYNTAX        Counter64String
    MAX-ACCESS    read-only
    STATUS        current
    DESCRIPTION   "Received CRC Errors"
    ::= { frRcv1FacilityHistorical1dayEntry 4 }

frRcv1FacilityHistorical1dayDiscardedFrames OBJECT-TYPE
    SYNTAX        Counter64String
    MAX-ACCESS    read-only
    STATUS        current
    DESCRIPTION   "Received Frames Discarded"
    ::= { frRcv1FacilityHistorical1dayEntry 5 }

frRcv1FacilityHistorical1dayBytes OBJECT-TYPE
    SYNTAX        Counter64String
    MAX-ACCESS    read-only
    STATUS        current
    DESCRIPTION   "Bytes Received"
    ::= { frRcv1FacilityHistorical1dayEntry 6 }

frRcv1FacilityHistorical1dayValidFlag OBJECT-TYPE
    SYNTAX        TruthValue
    MAX-ACCESS    read-only
    STATUS        current
    DESCRIPTION   "Valid Flag"
    ::= { frRcv1FacilityHistorical1dayEntry 7 }

frRcv1FacilityHistorical1dayTimeStamp OBJECT-TYPE
    SYNTAX        DateAndTime
    MAX-ACCESS    read-only
    STATUS        current
    DESCRIPTION   "Timestamp"
    ::= { frRcv1FacilityHistorical1dayEntry 8 }

endOfFrRcv1FacilityHistorical1dayTable OBJECT-TYPE
    SYNTAX        Integer32
    MAX-ACCESS    read-only
    STATUS        current
    DESCRIPTION   ""
    ::= { pmFacilityDataRecord 152 }

frRcv2FacilityCurrent15minTable OBJECT-TYPE
    SYNTAX        SEQUENCE OF FrRcv2FacilityCurrent15minEntry
    MAX-ACCESS    not-accessible
    STATUS        current
    DESCRIPTION   ""
    ::= { pmFacilityDataRecord 153 }

frRcv2FacilityCurrent15minEntry OBJECT-TYPE
    SYNTAX        FrRcv2FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv2FacilityCurrent15minTable 1 }

FrRcv2FacilityCurrent15minEntry ::= SEQUENCE
  {    frRcv2FacilityCurrent15minGoodFrames Counter64String,
    frRcv2FacilityCurrent15minPauseFrames Counter64String,
    frRcv2FacilityCurrent15minCrcFrames Counter64String,
    frRcv2FacilityCurrent15minBytes Counter64String,
    frRcv2FacilityCurrent15minElapsedTime Integer32 }

frRcv2FacilityCurrent15minGoodFrames OBJECT-TYPE
    SYNTAX        Counter64String
    MAX-ACCESS    read-only
    STATUS        current
    DESCRIPTION   "Frames Received"
    ::= { frRcv2FacilityCurrent15minEntry 1 }

frRcv2FacilityCurrent15minPauseFrames OBJECT-TYPE
    SYNTAX        Counter64String
    MAX-ACCESS    read-only
    STATUS        current
    DESCRIPTION   "Pause Frames Received"
    ::= { frRcv2FacilityCurrent15minEntry 2 }

frRcv2FacilityCurrent15minCrcFrames OBJECT-TYPE
    SYNTAX        Counter64String
    MAX-ACCESS    read-only
    STATUS        current
    DESCRIPTION   "Received CRC Errors"
    ::= { frRcv2FacilityCurrent15minEntry 3 }

frRcv2FacilityCurrent15minBytes OBJECT-TYPE
    SYNTAX        Counter64String
    MAX-ACCESS    read-only
    STATUS        current
    DESCRIPTION   "Bytes Received"
    ::= { frRcv2FacilityCurrent15minEntry 4 }

frRcv2FacilityCurrent15minElapsedTime OBJECT-TYPE
    SYNTAX        Integer32 (0..9000)
    MAX-ACCESS    read-only
    STATUS        current
    DESCRIPTION   "Elapsed 15Min"
    ::= { frRcv2FacilityCurrent15minEntry 5 }

endOfFrRcv2FacilityCurrent15minTable OBJECT-TYPE
    SYNTAX        Integer32
    MAX-ACCESS    read-only
    STATUS        current
    DESCRIPTION   ""
    ::= { pmFacilityDataRecord 154 }

frRcv2FacilityCurrent1dayTable OBJECT-TYPE
    SYNTAX        SEQUENCE OF FrRcv2FacilityCurrent1dayEntry
    MAX-ACCESS    not-accessible
    STATUS        current
    DESCRIPTION   ""
    ::= { pmFacilityDataRecord 155 }

frRcv2FacilityCurrent1dayEntry OBJECT-TYPE
    SYNTAX        FrRcv2FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv2FacilityCurrent1dayTable 1 }

FrRcv2FacilityCurrent1dayEntry ::= SEQUENCE
  {    frRcv2FacilityCurrent1dayGoodFrames Counter64String,
    frRcv2FacilityCurrent1dayPauseFrames Counter64String,
    frRcv2FacilityCurrent1dayCrcFrames Counter64String,
    frRcv2FacilityCurrent1dayBytes Counter64String,
    frRcv2FacilityCurrent1dayElapsedTime Integer32 }

frRcv2FacilityCurrent1dayGoodFrames OBJECT-TYPE
    SYNTAX        Counter64String
    MAX-ACCESS    read-only
    STATUS        current
    DESCRIPTION   "Frames Received"
    ::= { frRcv2FacilityCurrent1dayEntry 1 }

frRcv2FacilityCurrent1dayPauseFrames OBJECT-TYPE
    SYNTAX        Counter64String
    MAX-ACCESS    read-only
    STATUS        current
    DESCRIPTION   "Pause Frames Received"
    ::= { frRcv2FacilityCurrent1dayEntry 2 }

frRcv2FacilityCurrent1dayCrcFrames OBJECT-TYPE
    SYNTAX        Counter64String
    MAX-ACCESS    read-only
    STATUS        current
    DESCRIPTION   "Received CRC Errors"
    ::= { frRcv2FacilityCurrent1dayEntry 3 }

frRcv2FacilityCurrent1dayBytes OBJECT-TYPE
    SYNTAX        Counter64String
    MAX-ACCESS    read-only
    STATUS        current
    DESCRIPTION   "Bytes Received"
    ::= { frRcv2FacilityCurrent1dayEntry 4 }

frRcv2FacilityCurrent1dayElapsedTime OBJECT-TYPE
    SYNTAX        Integer32 (0..86400)
    MAX-ACCESS    read-only
    STATUS        current
    DESCRIPTION   "Elapsed 1Day"
    ::= { frRcv2FacilityCurrent1dayEntry 5 }

endOfFrRcv2FacilityCurrent1dayTable OBJECT-TYPE
    SYNTAX        Integer32
    MAX-ACCESS    read-only
    STATUS        current
    DESCRIPTION   ""
    ::= { pmFacilityDataRecord 156 }

frRcv2FacilityHistorical15minTable OBJECT-TYPE
    SYNTAX        SEQUENCE OF FrRcv2FacilityHistorical15minEntry
    MAX-ACCESS    not-accessible
    STATUS        current
    DESCRIPTION   ""
    ::= { pmFacilityDataRecord 157 }

frRcv2FacilityHistorical15minEntry OBJECT-TYPE
    SYNTAX        FrRcv2FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv2FacilityHistorical15minNumber
                }
    ::= { frRcv2FacilityHistorical15minTable 1 }

FrRcv2FacilityHistorical15minEntry ::= SEQUENCE
  {    frRcv2FacilityHistorical15minNumber Integer32,
    frRcv2FacilityHistorical15minGoodFrames Counter64String,
    frRcv2FacilityHistorical15minPauseFrames Counter64String,
    frRcv2FacilityHistorical15minCrcFrames Counter64String,
    frRcv2FacilityHistorical15minBytes Counter64String,
    frRcv2FacilityHistorical15minValidFlag TruthValue,
    frRcv2FacilityHistorical15minTimeStamp DateAndTime }

frRcv2FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frRcv2FacilityHistorical15minEntry 1 }

frRcv2FacilityHistorical15minGoodFrames OBJECT-TYPE
    SYNTAX        Counter64String
    MAX-ACCESS    read-only
    STATUS        current
    DESCRIPTION   "Frames Received"
    ::= { frRcv2FacilityHistorical15minEntry 2 }

frRcv2FacilityHistorical15minPauseFrames OBJECT-TYPE
    SYNTAX        Counter64String
    MAX-ACCESS    read-only
    STATUS        current
    DESCRIPTION   "Pause Frames Received"
    ::= { frRcv2FacilityHistorical15minEntry 3 }

frRcv2FacilityHistorical15minCrcFrames OBJECT-TYPE
    SYNTAX        Counter64String
    MAX-ACCESS    read-only
    STATUS        current
    DESCRIPTION   "Received CRC Errors"
    ::= { frRcv2FacilityHistorical15minEntry 4 }

frRcv2FacilityHistorical15minBytes OBJECT-TYPE
    SYNTAX        Counter64String
    MAX-ACCESS    read-only
    STATUS        current
    DESCRIPTION   "Bytes Received"
    ::= { frRcv2FacilityHistorical15minEntry 5 }

frRcv2FacilityHistorical15minValidFlag OBJECT-TYPE
    SYNTAX        TruthValue
    MAX-ACCESS    read-only
    STATUS        current
    DESCRIPTION   "Valid Flag"
    ::= { frRcv2FacilityHistorical15minEntry 6 }

frRcv2FacilityHistorical15minTimeStamp OBJECT-TYPE
    SYNTAX        DateAndTime
    MAX-ACCESS    read-only
    STATUS        current
    DESCRIPTION   "Timestamp"
    ::= { frRcv2FacilityHistorical15minEntry 7 }

endOfFrRcv2FacilityHistorical15minTable OBJECT-TYPE
    SYNTAX        Integer32
    MAX-ACCESS    read-only
    STATUS        current
    DESCRIPTION   ""
    ::= { pmFacilityDataRecord 158 }

frRcv2FacilityHistorical1dayTable OBJECT-TYPE
    SYNTAX        SEQUENCE OF FrRcv2FacilityHistorical1dayEntry
    MAX-ACCESS    not-accessible
    STATUS        current
    DESCRIPTION   ""
    ::= { pmFacilityDataRecord 159 }

frRcv2FacilityHistorical1dayEntry OBJECT-TYPE
    SYNTAX        FrRcv2FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv2FacilityHistorical1dayNumber
                }
    ::= { frRcv2FacilityHistorical1dayTable 1 }

FrRcv2FacilityHistorical1dayEntry ::= SEQUENCE
  {    frRcv2FacilityHistorical1dayNumber Integer32,
    frRcv2FacilityHistorical1dayGoodFrames Counter64String,
    frRcv2FacilityHistorical1dayPauseFrames Counter64String,
    frRcv2FacilityHistorical1dayCrcFrames Counter64String,
    frRcv2FacilityHistorical1dayBytes Counter64String,
    frRcv2FacilityHistorical1dayValidFlag TruthValue,
    frRcv2FacilityHistorical1dayTimeStamp DateAndTime }

frRcv2FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frRcv2FacilityHistorical1dayEntry 1 }

frRcv2FacilityHistorical1dayGoodFrames OBJECT-TYPE
    SYNTAX        Counter64String
    MAX-ACCESS    read-only
    STATUS        current
    DESCRIPTION   "Frames Received"
    ::= { frRcv2FacilityHistorical1dayEntry 2 }

frRcv2FacilityHistorical1dayPauseFrames OBJECT-TYPE
    SYNTAX        Counter64String
    MAX-ACCESS    read-only
    STATUS        current
    DESCRIPTION   "Pause Frames Received"
    ::= { frRcv2FacilityHistorical1dayEntry 3 }

frRcv2FacilityHistorical1dayCrcFrames OBJECT-TYPE
    SYNTAX        Counter64String
    MAX-ACCESS    read-only
    STATUS        current
    DESCRIPTION   "Received CRC Errors"
    ::= { frRcv2FacilityHistorical1dayEntry 4 }

frRcv2FacilityHistorical1dayBytes OBJECT-TYPE
    SYNTAX        Counter64String
    MAX-ACCESS    read-only
    STATUS        current
    DESCRIPTION   "Bytes Received"
    ::= { frRcv2FacilityHistorical1dayEntry 5 }

frRcv2FacilityHistorical1dayValidFlag OBJECT-TYPE
    SYNTAX        TruthValue
    MAX-ACCESS    read-only
    STATUS        current
    DESCRIPTION   "Valid Flag"
    ::= { frRcv2FacilityHistorical1dayEntry 6 }

frRcv2FacilityHistorical1dayTimeStamp OBJECT-TYPE
    SYNTAX        DateAndTime
    MAX-ACCESS    read-only
    STATUS        current
    DESCRIPTION   "Timestamp"
    ::= { frRcv2FacilityHistorical1dayEntry 7 }

endOfFrRcv2FacilityHistorical1dayTable OBJECT-TYPE
    SYNTAX        Integer32
    MAX-ACCESS    read-only
    STATUS        current
    DESCRIPTION   ""
    ::= { pmFacilityDataRecord 160 }

frRcv3FacilityCurrent15minTable OBJECT-TYPE
    SYNTAX        SEQUENCE OF FrRcv3FacilityCurrent15minEntry
    MAX-ACCESS    not-accessible
    STATUS        current
    DESCRIPTION   ""
    ::= { pmFacilityDataRecord 161 }

frRcv3FacilityCurrent15minEntry OBJECT-TYPE
    SYNTAX        FrRcv3FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv3FacilityCurrent15minTable 1 }

FrRcv3FacilityCurrent15minEntry ::= SEQUENCE
  {    frRcv3FacilityCurrent15minGoodFrames Counter64String,
    frRcv3FacilityCurrent15minPauseFrames Counter64String,
    frRcv3FacilityCurrent15minCrcFrames Counter64String,
    frRcv3FacilityCurrent15minBytes Counter64String,
    frRcv3FacilityCurrent15minBroadcastFramesRcv Counter64String,
    frRcv3FacilityCurrent15minMulticastFramesRcv Counter64String,
    frRcv3FacilityCurrent15minUndersizedFramesRcv Counter64String,
    frRcv3FacilityCurrent15minOversizedFramesRcv Counter64String,
    frRcv3FacilityCurrent15minFragmentFramesRcv Counter64String,
    frRcv3FacilityCurrent15minJabberFrameRcv Counter64String,
    frRcv3FacilityCurrent15minControlFrameRcv Counter64String,
    frRcv3FacilityCurrent15minBytesFrames64Rcv Counter64String,
    frRcv3FacilityCurrent15minBytesFrames65Rcv Counter64String,
    frRcv3FacilityCurrent15minBytesFrames128Rcv Counter64String,
    frRcv3FacilityCurrent15minBytesFrames256Rcv Counter64String,
    frRcv3FacilityCurrent15minBytesFrames512Rcv Counter64String,
    frRcv3FacilityCurrent15minBytesFrames1024Rcv Counter64String,
    frRcv3FacilityCurrent15minBytesFrames1519Rcv Counter64String,
    frRcv3FacilityCurrent15minElapsedTime Integer32 }

frRcv3FacilityCurrent15minGoodFrames OBJECT-TYPE
    SYNTAX        Counter64String
    MAX-ACCESS    read-only
    STATUS        current
    DESCRIPTION   "Frames Received"
    ::= { frRcv3FacilityCurrent15minEntry 1 }

frRcv3FacilityCurrent15minPauseFrames OBJECT-TYPE
    SYNTAX        Counter64String
    MAX-ACCESS    read-only
    STATUS        current
    DESCRIPTION   "Pause Frames Received"
    ::= { frRcv3FacilityCurrent15minEntry 2 }

frRcv3FacilityCurrent15minCrcFrames OBJECT-TYPE
    SYNTAX        Counter64String
    MAX-ACCESS    read-only
    STATUS        current
    DESCRIPTION   "Received CRC Errors"
    ::= { frRcv3FacilityCurrent15minEntry 3 }

frRcv3FacilityCurrent15minBytes OBJECT-TYPE
    SYNTAX        Counter64String
    MAX-ACCESS    read-only
    STATUS        current
    DESCRIPTION   "Bytes Received"
    ::= { frRcv3FacilityCurrent15minEntry 4 }

frRcv3FacilityCurrent15minBroadcastFramesRcv OBJECT-TYPE
    SYNTAX        Counter64String
    MAX-ACCESS    read-only
    STATUS        current
    DESCRIPTION   "Broadcast Frames Received"
    ::= { frRcv3FacilityCurrent15minEntry 5 }

frRcv3FacilityCurrent15minMulticastFramesRcv OBJECT-TYPE
    SYNTAX        Counter64String
    MAX-ACCESS    read-only
    STATUS        current
    DESCRIPTION   "Multicast Frames Received"
    ::= { frRcv3FacilityCurrent15minEntry 6 }

frRcv3FacilityCurrent15minUndersizedFramesRcv OBJECT-TYPE
    SYNTAX        Counter64String
    MAX-ACCESS    read-only
    STATUS        current
    DESCRIPTION   "Undersized Frames Received"
    ::= { frRcv3FacilityCurrent15minEntry 7 }

frRcv3FacilityCurrent15minOversizedFramesRcv OBJECT-TYPE
    SYNTAX        Counter64String
    MAX-ACCESS    read-only
    STATUS        current
    DESCRIPTION   "Oversized Frames Received"
    ::= { frRcv3FacilityCurrent15minEntry 8 }

frRcv3FacilityCurrent15minFragmentFramesRcv OBJECT-TYPE
    SYNTAX        Counter64String
    MAX-ACCESS    read-only
    STATUS        current
    DESCRIPTION   "Fragment Frames Received"
    ::= { frRcv3FacilityCurrent15minEntry 9 }

frRcv3FacilityCurrent15minJabberFrameRcv OBJECT-TYPE
    SYNTAX        Counter64String
    MAX-ACCESS    read-only
    STATUS        current
    DESCRIPTION   "Rx Jabber Frame"
    ::= { frRcv3FacilityCurrent15minEntry 10 }

frRcv3FacilityCurrent15minControlFrameRcv OBJECT-TYPE
    SYNTAX        Counter64String
    MAX-ACCESS    read-only
    STATUS        current
    DESCRIPTION   "Control Frames Received"
    ::= { frRcv3FacilityCurrent15minEntry 11 }

frRcv3FacilityCurrent15minBytesFrames64Rcv OBJECT-TYPE
    SYNTAX        Counter64String
    MAX-ACCESS    read-only
    STATUS        current
    DESCRIPTION   "64 Byte Frames Received"
    ::= { frRcv3FacilityCurrent15minEntry 12 }

frRcv3FacilityCurrent15minBytesFrames65Rcv OBJECT-TYPE
    SYNTAX        Counter64String
    MAX-ACCESS    read-only
    STATUS        current
    DESCRIPTION   "65-127 Byte Frames Received"
    ::= { frRcv3FacilityCurrent15minEntry 13 }

frRcv3FacilityCurrent15minBytesFrames128Rcv OBJECT-TYPE
    SYNTAX        Counter64String
    MAX-ACCESS    read-only
    STATUS        current
    DESCRIPTION   "128-255 Byte Frames Received"
    ::= { frRcv3FacilityCurrent15minEntry 14 }

frRcv3FacilityCurrent15minBytesFrames256Rcv OBJECT-TYPE
    SYNTAX        Counter64String
    MAX-ACCESS    read-only
    STATUS        current
    DESCRIPTION   "256-511 Byte Frames Received"
    ::= { frRcv3FacilityCurrent15minEntry 15 }

frRcv3FacilityCurrent15minBytesFrames512Rcv OBJECT-TYPE
    SYNTAX        Counter64String
    MAX-ACCESS    read-only
    STATUS        current
    DESCRIPTION   "512-1023 Byte Frames Received"
    ::= { frRcv3FacilityCurrent15minEntry 16 }

frRcv3FacilityCurrent15minBytesFrames1024Rcv OBJECT-TYPE
    SYNTAX        Counter64String
    MAX-ACCESS    read-only
    STATUS        current
    DESCRIPTION   "1024-1518 Byte Frames Received"
    ::= { frRcv3FacilityCurrent15minEntry 17 }

frRcv3FacilityCurrent15minBytesFrames1519Rcv OBJECT-TYPE
    SYNTAX        Counter64String
    MAX-ACCESS    read-only
    STATUS        current
    DESCRIPTION   "1519-Max Byte Frames Received"
    ::= { frRcv3FacilityCurrent15minEntry 18 }

frRcv3FacilityCurrent15minElapsedTime OBJECT-TYPE
    SYNTAX        Integer32 (0..9000)
    MAX-ACCESS    read-only
    STATUS        current
    DESCRIPTION   "Elapsed 15Min"
    ::= { frRcv3FacilityCurrent15minEntry 19 }

endOfFrRcv3FacilityCurrent15minTable OBJECT-TYPE
    SYNTAX        Integer32
    MAX-ACCESS    read-only
    STATUS        current
    DESCRIPTION   ""
    ::= { pmFacilityDataRecord 162 }

frRcv3FacilityCurrent1dayTable OBJECT-TYPE
    SYNTAX        SEQUENCE OF FrRcv3FacilityCurrent1dayEntry
    MAX-ACCESS    not-accessible
    STATUS        current
    DESCRIPTION   ""
    ::= { pmFacilityDataRecord 163 }

frRcv3FacilityCurrent1dayEntry OBJECT-TYPE
    SYNTAX        FrRcv3FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv3FacilityCurrent1dayTable 1 }

FrRcv3FacilityCurrent1dayEntry ::= SEQUENCE
  {    frRcv3FacilityCurrent1dayGoodFrames Counter64String,
    frRcv3FacilityCurrent1dayPauseFrames Counter64String,
    frRcv3FacilityCurrent1dayCrcFrames Counter64String,
    frRcv3FacilityCurrent1dayBytes Counter64String,
    frRcv3FacilityCurrent1dayBroadcastFramesRcv Counter64String,
    frRcv3FacilityCurrent1dayMulticastFramesRcv Counter64String,
    frRcv3FacilityCurrent1dayUndersizedFramesRcv Counter64String,
    frRcv3FacilityCurrent1dayOversizedFramesRcv Counter64String,
    frRcv3FacilityCurrent1dayFragmentFramesRcv Counter64String,
    frRcv3FacilityCurrent1dayJabberFrameRcv Counter64String,
    frRcv3FacilityCurrent1dayControlFrameRcv Counter64String,
    frRcv3FacilityCurrent1dayBytesFrames64Rcv Counter64String,
    frRcv3FacilityCurrent1dayBytesFrames65Rcv Counter64String,
    frRcv3FacilityCurrent1dayBytesFrames128Rcv Counter64String,
    frRcv3FacilityCurrent1dayBytesFrames256Rcv Counter64String,
    frRcv3FacilityCurrent1dayBytesFrames512Rcv Counter64String,
    frRcv3FacilityCurrent1dayBytesFrames1024Rcv Counter64String,
    frRcv3FacilityCurrent1dayBytesFrames1519Rcv Counter64String,
    frRcv3FacilityCurrent1dayElapsedTime Integer32 }

frRcv3FacilityCurrent1dayGoodFrames OBJECT-TYPE
    SYNTAX        Counter64String
    MAX-ACCESS    read-only
    STATUS        current
    DESCRIPTION   "Frames Received"
    ::= { frRcv3FacilityCurrent1dayEntry 1 }

frRcv3FacilityCurrent1dayPauseFrames OBJECT-TYPE
    SYNTAX        Counter64String
    MAX-ACCESS    read-only
    STATUS        current
    DESCRIPTION   "Pause Frames Received"
    ::= { frRcv3FacilityCurrent1dayEntry 2 }

frRcv3FacilityCurrent1dayCrcFrames OBJECT-TYPE
    SYNTAX        Counter64String
    MAX-ACCESS    read-only
    STATUS        current
    DESCRIPTION   "Received CRC Errors"
    ::= { frRcv3FacilityCurrent1dayEntry 3 }

frRcv3FacilityCurrent1dayBytes OBJECT-TYPE
    SYNTAX        Counter64String
    MAX-ACCESS    read-only
    STATUS        current
    DESCRIPTION   "Bytes Received"
    ::= { frRcv3FacilityCurrent1dayEntry 4 }

frRcv3FacilityCurrent1dayBroadcastFramesRcv OBJECT-TYPE
    SYNTAX        Counter64String
    MAX-ACCESS    read-only
    STATUS        current
    DESCRIPTION   "Broadcast Frames Received"
    ::= { frRcv3FacilityCurrent1dayEntry 5 }

frRcv3FacilityCurrent1dayMulticastFramesRcv OBJECT-TYPE
    SYNTAX        Counter64String
    MAX-ACCESS    read-only
    STATUS        current
    DESCRIPTION   "Multicast Frames Received"
    ::= { frRcv3FacilityCurrent1dayEntry 6 }

frRcv3FacilityCurrent1dayUndersizedFramesRcv OBJECT-TYPE
    SYNTAX        Counter64String
    MAX-ACCESS    read-only
    STATUS        current
    DESCRIPTION   "Undersized Frames Received"
    ::= { frRcv3FacilityCurrent1dayEntry 7 }

frRcv3FacilityCurrent1dayOversizedFramesRcv OBJECT-TYPE
    SYNTAX        Counter64String
    MAX-ACCESS    read-only
    STATUS        current
    DESCRIPTION   "Oversized Frames Received"
    ::= { frRcv3FacilityCurrent1dayEntry 8 }

frRcv3FacilityCurrent1dayFragmentFramesRcv OBJECT-TYPE
    SYNTAX        Counter64String
    MAX-ACCESS    read-only
    STATUS        current
    DESCRIPTION   "Fragment Frames Received"
    ::= { frRcv3FacilityCurrent1dayEntry 9 }

frRcv3FacilityCurrent1dayJabberFrameRcv OBJECT-TYPE
    SYNTAX        Counter64String
    MAX-ACCESS    read-only
    STATUS        current
    DESCRIPTION   "Rx Jabber Frame"
    ::= { frRcv3FacilityCurrent1dayEntry 10 }

frRcv3FacilityCurrent1dayControlFrameRcv OBJECT-TYPE
    SYNTAX        Counter64String
    MAX-ACCESS    read-only
    STATUS        current
    DESCRIPTION   "Control Frames Received"
    ::= { frRcv3FacilityCurrent1dayEntry 11 }

frRcv3FacilityCurrent1dayBytesFrames64Rcv OBJECT-TYPE
    SYNTAX        Counter64String
    MAX-ACCESS    read-only
    STATUS        current
    DESCRIPTION   "64 Byte Frames Received"
    ::= { frRcv3FacilityCurrent1dayEntry 12 }

frRcv3FacilityCurrent1dayBytesFrames65Rcv OBJECT-TYPE
    SYNTAX        Counter64String
    MAX-ACCESS    read-only
    STATUS        current
    DESCRIPTION   "65-127 Byte Frames Received"
    ::= { frRcv3FacilityCurrent1dayEntry 13 }

frRcv3FacilityCurrent1dayBytesFrames128Rcv OBJECT-TYPE
    SYNTAX        Counter64String
    MAX-ACCESS    read-only
    STATUS        current
    DESCRIPTION   "128-255 Byte Frames Received"
    ::= { frRcv3FacilityCurrent1dayEntry 14 }

frRcv3FacilityCurrent1dayBytesFrames256Rcv OBJECT-TYPE
    SYNTAX        Counter64String
    MAX-ACCESS    read-only
    STATUS        current
    DESCRIPTION   "256-511 Byte Frames Received"
    ::= { frRcv3FacilityCurrent1dayEntry 15 }

frRcv3FacilityCurrent1dayBytesFrames512Rcv OBJECT-TYPE
    SYNTAX        Counter64String
    MAX-ACCESS    read-only
    STATUS        current
    DESCRIPTION   "512-1023 Byte Frames Received"
    ::= { frRcv3FacilityCurrent1dayEntry 16 }

frRcv3FacilityCurrent1dayBytesFrames1024Rcv OBJECT-TYPE
    SYNTAX        Counter64String
    MAX-ACCESS    read-only
    STATUS        current
    DESCRIPTION   "1024-1518 Byte Frames Received"
    ::= { frRcv3FacilityCurrent1dayEntry 17 }

frRcv3FacilityCurrent1dayBytesFrames1519Rcv OBJECT-TYPE
    SYNTAX        Counter64String
    MAX-ACCESS    read-only
    STATUS        current
    DESCRIPTION   "1519-Max Byte Frames Received"
    ::= { frRcv3FacilityCurrent1dayEntry 18 }

frRcv3FacilityCurrent1dayElapsedTime OBJECT-TYPE
    SYNTAX        Integer32 (0..86400)
    MAX-ACCESS    read-only
    STATUS        current
    DESCRIPTION   "Elapsed 1Day"
    ::= { frRcv3FacilityCurrent1dayEntry 19 }

endOfFrRcv3FacilityCurrent1dayTable OBJECT-TYPE
    SYNTAX        Integer32
    MAX-ACCESS    read-only
    STATUS        current
    DESCRIPTION   ""
    ::= { pmFacilityDataRecord 164 }

frRcv3FacilityHistorical15minTable OBJECT-TYPE
    SYNTAX        SEQUENCE OF FrRcv3FacilityHistorical15minEntry
    MAX-ACCESS    not-accessible
    STATUS        current
    DESCRIPTION   ""
    ::= { pmFacilityDataRecord 165 }

frRcv3FacilityHistorical15minEntry OBJECT-TYPE
    SYNTAX        FrRcv3FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv3FacilityHistorical15minNumber
                }
    ::= { frRcv3FacilityHistorical15minTable 1 }

FrRcv3FacilityHistorical15minEntry ::= SEQUENCE
  {    frRcv3FacilityHistorical15minNumber Integer32,
    frRcv3FacilityHistorical15minGoodFrames Counter64String,
    frRcv3FacilityHistorical15minPauseFrames Counter64String,
    frRcv3FacilityHistorical15minCrcFrames Counter64String,
    frRcv3FacilityHistorical15minBytes Counter64String,
    frRcv3FacilityHistorical15minBroadcastFramesRcv Counter64String,
    frRcv3FacilityHistorical15minMulticastFramesRcv Counter64String,
    frRcv3FacilityHistorical15minUndersizedFramesRcv Counter64String,
    frRcv3FacilityHistorical15minOversizedFramesRcv Counter64String,
    frRcv3FacilityHistorical15minFragmentFramesRcv Counter64String,
    frRcv3FacilityHistorical15minJabberFrameRcv Counter64String,
    frRcv3FacilityHistorical15minControlFrameRcv Counter64String,
    frRcv3FacilityHistorical15minBytesFrames64Rcv Counter64String,
    frRcv3FacilityHistorical15minBytesFrames65Rcv Counter64String,
    frRcv3FacilityHistorical15minBytesFrames128Rcv Counter64String,
    frRcv3FacilityHistorical15minBytesFrames256Rcv Counter64String,
    frRcv3FacilityHistorical15minBytesFrames512Rcv Counter64String,
    frRcv3FacilityHistorical15minBytesFrames1024Rcv Counter64String,
    frRcv3FacilityHistorical15minBytesFrames1519Rcv Counter64String,
    frRcv3FacilityHistorical15minValidFlag TruthValue,
    frRcv3FacilityHistorical15minTimeStamp DateAndTime }

frRcv3FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frRcv3FacilityHistorical15minEntry 1 }

frRcv3FacilityHistorical15minGoodFrames OBJECT-TYPE
    SYNTAX        Counter64String
    MAX-ACCESS    read-only
    STATUS        current
    DESCRIPTION   "Frames Received"
    ::= { frRcv3FacilityHistorical15minEntry 2 }

frRcv3FacilityHistorical15minPauseFrames OBJECT-TYPE
    SYNTAX        Counter64String
    MAX-ACCESS    read-only
    STATUS        current
    DESCRIPTION   "Pause Frames Received"
    ::= { frRcv3FacilityHistorical15minEntry 3 }

frRcv3FacilityHistorical15minCrcFrames OBJECT-TYPE
    SYNTAX        Counter64String
    MAX-ACCESS    read-only
    STATUS        current
    DESCRIPTION   "Received CRC Errors"
    ::= { frRcv3FacilityHistorical15minEntry 4 }

frRcv3FacilityHistorical15minBytes OBJECT-TYPE
    SYNTAX        Counter64String
    MAX-ACCESS    read-only
    STATUS        current
    DESCRIPTION   "Bytes Received"
    ::= { frRcv3FacilityHistorical15minEntry 5 }

frRcv3FacilityHistorical15minBroadcastFramesRcv OBJECT-TYPE
    SYNTAX        Counter64String
    MAX-ACCESS    read-only
    STATUS        current
    DESCRIPTION   "Broadcast Frames Received"
    ::= { frRcv3FacilityHistorical15minEntry 6 }

frRcv3FacilityHistorical15minMulticastFramesRcv OBJECT-TYPE
    SYNTAX        Counter64String
    MAX-ACCESS    read-only
    STATUS        current
    DESCRIPTION   "Multicast Frames Received"
    ::= { frRcv3FacilityHistorical15minEntry 7 }

frRcv3FacilityHistorical15minUndersizedFramesRcv OBJECT-TYPE
    SYNTAX        Counter64String
    MAX-ACCESS    read-only
    STATUS        current
    DESCRIPTION   "Undersized Frames Received"
    ::= { frRcv3FacilityHistorical15minEntry 8 }

frRcv3FacilityHistorical15minOversizedFramesRcv OBJECT-TYPE
    SYNTAX        Counter64String
    MAX-ACCESS    read-only
    STATUS        current
    DESCRIPTION   "Oversized Frames Received"
    ::= { frRcv3FacilityHistorical15minEntry 9 }

frRcv3FacilityHistorical15minFragmentFramesRcv OBJECT-TYPE
    SYNTAX        Counter64String
    MAX-ACCESS    read-only
    STATUS        current
    DESCRIPTION   "Fragment Frames Received"
    ::= { frRcv3FacilityHistorical15minEntry 10 }

frRcv3FacilityHistorical15minJabberFrameRcv OBJECT-TYPE
    SYNTAX        Counter64String
    MAX-ACCESS    read-only
    STATUS        current
    DESCRIPTION   "Rx Jabber Frame"
    ::= { frRcv3FacilityHistorical15minEntry 11 }

frRcv3FacilityHistorical15minControlFrameRcv OBJECT-TYPE
    SYNTAX        Counter64String
    MAX-ACCESS    read-only
    STATUS        current
    DESCRIPTION   "Control Frames Received"
    ::= { frRcv3FacilityHistorical15minEntry 12 }

frRcv3FacilityHistorical15minBytesFrames64Rcv OBJECT-TYPE
    SYNTAX        Counter64String
    MAX-ACCESS    read-only
    STATUS        current
    DESCRIPTION   "64 Byte Frames Received"
    ::= { frRcv3FacilityHistorical15minEntry 13 }

frRcv3FacilityHistorical15minBytesFrames65Rcv OBJECT-TYPE
    SYNTAX        Counter64String
    MAX-ACCESS    read-only
    STATUS        current
    DESCRIPTION   "65-127 Byte Frames Received"
    ::= { frRcv3FacilityHistorical15minEntry 14 }

frRcv3FacilityHistorical15minBytesFrames128Rcv OBJECT-TYPE
    SYNTAX        Counter64String
    MAX-ACCESS    read-only
    STATUS        current
    DESCRIPTION   "128-255 Byte Frames Received"
    ::= { frRcv3FacilityHistorical15minEntry 15 }

frRcv3FacilityHistorical15minBytesFrames256Rcv OBJECT-TYPE
    SYNTAX        Counter64String
    MAX-ACCESS    read-only
    STATUS        current
    DESCRIPTION   "256-511 Byte Frames Received"
    ::= { frRcv3FacilityHistorical15minEntry 16 }

frRcv3FacilityHistorical15minBytesFrames512Rcv OBJECT-TYPE
    SYNTAX        Counter64String
    MAX-ACCESS    read-only
    STATUS        current
    DESCRIPTION   "512-1023 Byte Frames Received"
    ::= { frRcv3FacilityHistorical15minEntry 17 }

frRcv3FacilityHistorical15minBytesFrames1024Rcv OBJECT-TYPE
    SYNTAX        Counter64String
    MAX-ACCESS    read-only
    STATUS        current
    DESCRIPTION   "1024-1518 Byte Frames Received"
    ::= { frRcv3FacilityHistorical15minEntry 18 }

frRcv3FacilityHistorical15minBytesFrames1519Rcv OBJECT-TYPE
    SYNTAX        Counter64String
    MAX-ACCESS    read-only
    STATUS        current
    DESCRIPTION   "1519-Max Byte Frames Received"
    ::= { frRcv3FacilityHistorical15minEntry 19 }

frRcv3FacilityHistorical15minValidFlag OBJECT-TYPE
    SYNTAX        TruthValue
    MAX-ACCESS    read-only
    STATUS        current
    DESCRIPTION   "Valid Flag"
    ::= { frRcv3FacilityHistorical15minEntry 20 }

frRcv3FacilityHistorical15minTimeStamp OBJECT-TYPE
    SYNTAX        DateAndTime
    MAX-ACCESS    read-only
    STATUS        current
    DESCRIPTION   "Timestamp"
    ::= { frRcv3FacilityHistorical15minEntry 21 }

endOfFrRcv3FacilityHistorical15minTable OBJECT-TYPE
    SYNTAX        Integer32
    MAX-ACCESS    read-only
    STATUS        current
    DESCRIPTION   ""
    ::= { pmFacilityDataRecord 166 }

frRcv3FacilityHistorical1dayTable OBJECT-TYPE
    SYNTAX        SEQUENCE OF FrRcv3FacilityHistorical1dayEntry
    MAX-ACCESS    not-accessible
    STATUS        current
    DESCRIPTION   ""
    ::= { pmFacilityDataRecord 167 }

frRcv3FacilityHistorical1dayEntry OBJECT-TYPE
    SYNTAX        FrRcv3FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv3FacilityHistorical1dayNumber
                }
    ::= { frRcv3FacilityHistorical1dayTable 1 }

FrRcv3FacilityHistorical1dayEntry ::= SEQUENCE
  {    frRcv3FacilityHistorical1dayNumber Integer32,
    frRcv3FacilityHistorical1dayGoodFrames Counter64String,
    frRcv3FacilityHistorical1dayPauseFrames Counter64String,
    frRcv3FacilityHistorical1dayCrcFrames Counter64String,
    frRcv3FacilityHistorical1dayBytes Counter64String,
    frRcv3FacilityHistorical1dayBroadcastFramesRcv Counter64String,
    frRcv3FacilityHistorical1dayMulticastFramesRcv Counter64String,
    frRcv3FacilityHistorical1dayUndersizedFramesRcv Counter64String,
    frRcv3FacilityHistorical1dayOversizedFramesRcv Counter64String,
    frRcv3FacilityHistorical1dayFragmentFramesRcv Counter64String,
    frRcv3FacilityHistorical1dayJabberFrameRcv Counter64String,
    frRcv3FacilityHistorical1dayControlFrameRcv Counter64String,
    frRcv3FacilityHistorical1dayBytesFrames64Rcv Counter64String,
    frRcv3FacilityHistorical1dayBytesFrames65Rcv Counter64String,
    frRcv3FacilityHistorical1dayBytesFrames128Rcv Counter64String,
    frRcv3FacilityHistorical1dayBytesFrames256Rcv Counter64String,
    frRcv3FacilityHistorical1dayBytesFrames512Rcv Counter64String,
    frRcv3FacilityHistorical1dayBytesFrames1024Rcv Counter64String,
    frRcv3FacilityHistorical1dayBytesFrames1519Rcv Counter64String,
    frRcv3FacilityHistorical1dayValidFlag TruthValue,
    frRcv3FacilityHistorical1dayTimeStamp DateAndTime }

frRcv3FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frRcv3FacilityHistorical1dayEntry 1 }

frRcv3FacilityHistorical1dayGoodFrames OBJECT-TYPE
    SYNTAX        Counter64String
    MAX-ACCESS    read-only
    STATUS        current
    DESCRIPTION   "Frames Received"
    ::= { frRcv3FacilityHistorical1dayEntry 2 }

frRcv3FacilityHistorical1dayPauseFrames OBJECT-TYPE
    SYNTAX        Counter64String
    MAX-ACCESS    read-only
    STATUS        current
    DESCRIPTION   "Pause Frames Received"
    ::= { frRcv3FacilityHistorical1dayEntry 3 }

frRcv3FacilityHistorical1dayCrcFrames OBJECT-TYPE
    SYNTAX        Counter64String
    MAX-ACCESS    read-only
    STATUS        current
    DESCRIPTION   "Received CRC Errors"
    ::= { frRcv3FacilityHistorical1dayEntry 4 }

frRcv3FacilityHistorical1dayBytes OBJECT-TYPE
    SYNTAX        Counter64String
    MAX-ACCESS    read-only
    STATUS        current
    DESCRIPTION   "Bytes Received"
    ::= { frRcv3FacilityHistorical1dayEntry 5 }

frRcv3FacilityHistorical1dayBroadcastFramesRcv OBJECT-TYPE
    SYNTAX        Counter64String
    MAX-ACCESS    read-only
    STATUS        current
    DESCRIPTION   "Broadcast Frames Received"
    ::= { frRcv3FacilityHistorical1dayEntry 6 }

frRcv3FacilityHistorical1dayMulticastFramesRcv OBJECT-TYPE
    SYNTAX        Counter64String
    MAX-ACCESS    read-only
    STATUS        current
    DESCRIPTION   "Multicast Frames Received"
    ::= { frRcv3FacilityHistorical1dayEntry 7 }

frRcv3FacilityHistorical1dayUndersizedFramesRcv OBJECT-TYPE
    SYNTAX        Counter64String
    MAX-ACCESS    read-only
    STATUS        current
    DESCRIPTION   "Undersized Frames Received"
    ::= { frRcv3FacilityHistorical1dayEntry 8 }

frRcv3FacilityHistorical1dayOversizedFramesRcv OBJECT-TYPE
    SYNTAX        Counter64String
    MAX-ACCESS    read-only
    STATUS        current
    DESCRIPTION   "Oversized Frames Received"
    ::= { frRcv3FacilityHistorical1dayEntry 9 }

frRcv3FacilityHistorical1dayFragmentFramesRcv OBJECT-TYPE
    SYNTAX        Counter64String
    MAX-ACCESS    read-only
    STATUS        current
    DESCRIPTION   "Fragment Frames Received"
    ::= { frRcv3FacilityHistorical1dayEntry 10 }

frRcv3FacilityHistorical1dayJabberFrameRcv OBJECT-TYPE
    SYNTAX        Counter64String
    MAX-ACCESS    read-only
    STATUS        current
    DESCRIPTION   "Rx Jabber Frame"
    ::= { frRcv3FacilityHistorical1dayEntry 11 }

frRcv3FacilityHistorical1dayControlFrameRcv OBJECT-TYPE
    SYNTAX        Counter64String
    MAX-ACCESS    read-only
    STATUS        current
    DESCRIPTION   "Control Frames Received"
    ::= { frRcv3FacilityHistorical1dayEntry 12 }

frRcv3FacilityHistorical1dayBytesFrames64Rcv OBJECT-TYPE
    SYNTAX        Counter64String
    MAX-ACCESS    read-only
    STATUS        current
    DESCRIPTION   "64 Byte Frames Received"
    ::= { frRcv3FacilityHistorical1dayEntry 13 }

frRcv3FacilityHistorical1dayBytesFrames65Rcv OBJECT-TYPE
    SYNTAX        Counter64String
    MAX-ACCESS    read-only
    STATUS        current
    DESCRIPTION   "65-127 Byte Frames Received"
    ::= { frRcv3FacilityHistorical1dayEntry 14 }

frRcv3FacilityHistorical1dayBytesFrames128Rcv OBJECT-TYPE
    SYNTAX        Counter64String
    MAX-ACCESS    read-only
    STATUS        current
    DESCRIPTION   "128-255 Byte Frames Received"
    ::= { frRcv3FacilityHistorical1dayEntry 15 }

frRcv3FacilityHistorical1dayBytesFrames256Rcv OBJECT-TYPE
    SYNTAX        Counter64String
    MAX-ACCESS    read-only
    STATUS        current
    DESCRIPTION   "256-511 Byte Frames Received"
    ::= { frRcv3FacilityHistorical1dayEntry 16 }

frRcv3FacilityHistorical1dayBytesFrames512Rcv OBJECT-TYPE
    SYNTAX        Counter64String
    MAX-ACCESS    read-only
    STATUS        current
    DESCRIPTION   "512-1023 Byte Frames Received"
    ::= { frRcv3FacilityHistorical1dayEntry 17 }

frRcv3FacilityHistorical1dayBytesFrames1024Rcv OBJECT-TYPE
    SYNTAX        Counter64String
    MAX-ACCESS    read-only
    STATUS        current
    DESCRIPTION   "1024-1518 Byte Frames Received"
    ::= { frRcv3FacilityHistorical1dayEntry 18 }

frRcv3FacilityHistorical1dayBytesFrames1519Rcv OBJECT-TYPE
    SYNTAX        Counter64String
    MAX-ACCESS    read-only
    STATUS        current
    DESCRIPTION   "1519-Max Byte Frames Received"
    ::= { frRcv3FacilityHistorical1dayEntry 19 }

frRcv3FacilityHistorical1dayValidFlag OBJECT-TYPE
    SYNTAX        TruthValue
    MAX-ACCESS    read-only
    STATUS        current
    DESCRIPTION   "Valid Flag"
    ::= { frRcv3FacilityHistorical1dayEntry 20 }

frRcv3FacilityHistorical1dayTimeStamp OBJECT-TYPE
    SYNTAX        DateAndTime
    MAX-ACCESS    read-only
    STATUS        current
    DESCRIPTION   "Timestamp"
    ::= { frRcv3FacilityHistorical1dayEntry 21 }

endOfFrRcv3FacilityHistorical1dayTable OBJECT-TYPE
    SYNTAX        Integer32
    MAX-ACCESS    read-only
    STATUS        current
    DESCRIPTION   ""
    ::= { pmFacilityDataRecord 168 }

dsFacilityCurrent15minTable OBJECT-TYPE
    SYNTAX        SEQUENCE OF DsFacilityCurrent15minEntry
    MAX-ACCESS    not-accessible
    STATUS        current
    DESCRIPTION   ""
    ::= { pmFacilityDataRecord 169 }

dsFacilityCurrent15minEntry OBJECT-TYPE
    SYNTAX        DsFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { dsFacilityCurrent15minTable 1 }

DsFacilityCurrent15minEntry ::= SEQUENCE
  {    dsFacilityCurrent15minDS Unsigned32,
    dsFacilityCurrent15minElapsedTime Integer32 }

dsFacilityCurrent15minDS OBJECT-TYPE
    SYNTAX        Unsigned32
    MAX-ACCESS    read-only
    STATUS        current
    DESCRIPTION   "Defect Seconds"
    ::= { dsFacilityCurrent15minEntry 1 }

dsFacilityCurrent15minElapsedTime OBJECT-TYPE
    SYNTAX        Integer32 (0..9000)
    MAX-ACCESS    read-only
    STATUS        current
    DESCRIPTION   "Elapsed 15Min"
    ::= { dsFacilityCurrent15minEntry 2 }

endOfDsFacilityCurrent15minTable OBJECT-TYPE
    SYNTAX        Integer32
    MAX-ACCESS    read-only
    STATUS        current
    DESCRIPTION   ""
    ::= { pmFacilityDataRecord 170 }

dsFacilityCurrent1dayTable OBJECT-TYPE
    SYNTAX        SEQUENCE OF DsFacilityCurrent1dayEntry
    MAX-ACCESS    not-accessible
    STATUS        current
    DESCRIPTION   ""
    ::= { pmFacilityDataRecord 171 }

dsFacilityCurrent1dayEntry OBJECT-TYPE
    SYNTAX        DsFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { dsFacilityCurrent1dayTable 1 }

DsFacilityCurrent1dayEntry ::= SEQUENCE
  {    dsFacilityCurrent1dayDS Unsigned32,
    dsFacilityCurrent1dayElapsedTime Integer32 }

dsFacilityCurrent1dayDS OBJECT-TYPE
    SYNTAX        Unsigned32
    MAX-ACCESS    read-only
    STATUS        current
    DESCRIPTION   "Defect Seconds"
    ::= { dsFacilityCurrent1dayEntry 1 }

dsFacilityCurrent1dayElapsedTime OBJECT-TYPE
    SYNTAX        Integer32 (0..86400)
    MAX-ACCESS    read-only
    STATUS        current
    DESCRIPTION   "Elapsed 1Day"
    ::= { dsFacilityCurrent1dayEntry 2 }

endOfDsFacilityCurrent1dayTable OBJECT-TYPE
    SYNTAX        Integer32
    MAX-ACCESS    read-only
    STATUS        current
    DESCRIPTION   ""
    ::= { pmFacilityDataRecord 172 }

dsFacilityHistorical15minTable OBJECT-TYPE
    SYNTAX        SEQUENCE OF DsFacilityHistorical15minEntry
    MAX-ACCESS    not-accessible
    STATUS        current
    DESCRIPTION   ""
    ::= { pmFacilityDataRecord 173 }

dsFacilityHistorical15minEntry OBJECT-TYPE
    SYNTAX        DsFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  dsFacilityHistorical15minNumber
                }
    ::= { dsFacilityHistorical15minTable 1 }

DsFacilityHistorical15minEntry ::= SEQUENCE
  {    dsFacilityHistorical15minNumber Integer32,
    dsFacilityHistorical15minDS Unsigned32,
    dsFacilityHistorical15minValidFlag TruthValue,
    dsFacilityHistorical15minTimeStamp DateAndTime }

dsFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { dsFacilityHistorical15minEntry 1 }

dsFacilityHistorical15minDS OBJECT-TYPE
    SYNTAX        Unsigned32
    MAX-ACCESS    read-only
    STATUS        current
    DESCRIPTION   "Defect Seconds"
    ::= { dsFacilityHistorical15minEntry 2 }

dsFacilityHistorical15minValidFlag OBJECT-TYPE
    SYNTAX        TruthValue
    MAX-ACCESS    read-only
    STATUS        current
    DESCRIPTION   "Valid Flag"
    ::= { dsFacilityHistorical15minEntry 3 }

dsFacilityHistorical15minTimeStamp OBJECT-TYPE
    SYNTAX        DateAndTime
    MAX-ACCESS    read-only
    STATUS        current
    DESCRIPTION   "Timestamp"
    ::= { dsFacilityHistorical15minEntry 4 }

endOfDsFacilityHistorical15minTable OBJECT-TYPE
    SYNTAX        Integer32
    MAX-ACCESS    read-only
    STATUS        current
    DESCRIPTION   ""
    ::= { pmFacilityDataRecord 174 }

dsFacilityHistorical1dayTable OBJECT-TYPE
    SYNTAX        SEQUENCE OF DsFacilityHistorical1dayEntry
    MAX-ACCESS    not-accessible
    STATUS        current
    DESCRIPTION   ""
    ::= { pmFacilityDataRecord 175 }

dsFacilityHistorical1dayEntry OBJECT-TYPE
    SYNTAX        DsFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  dsFacilityHistorical1dayNumber
                }
    ::= { dsFacilityHistorical1dayTable 1 }

DsFacilityHistorical1dayEntry ::= SEQUENCE
  {    dsFacilityHistorical1dayNumber Integer32,
    dsFacilityHistorical1dayDS Unsigned32,
    dsFacilityHistorical1dayValidFlag TruthValue,
    dsFacilityHistorical1dayTimeStamp DateAndTime }

dsFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { dsFacilityHistorical1dayEntry 1 }

dsFacilityHistorical1dayDS OBJECT-TYPE
    SYNTAX        Unsigned32
    MAX-ACCESS    read-only
    STATUS        current
    DESCRIPTION   "Defect Seconds"
    ::= { dsFacilityHistorical1dayEntry 2 }

dsFacilityHistorical1dayValidFlag OBJECT-TYPE
    SYNTAX        TruthValue
    MAX-ACCESS    read-only
    STATUS        current
    DESCRIPTION   "Valid Flag"
    ::= { dsFacilityHistorical1dayEntry 3 }

dsFacilityHistorical1dayTimeStamp OBJECT-TYPE
    SYNTAX        DateAndTime
    MAX-ACCESS    read-only
    STATUS        current
    DESCRIPTION   "Timestamp"
    ::= { dsFacilityHistorical1dayEntry 4 }

endOfDsFacilityHistorical1dayTable OBJECT-TYPE
    SYNTAX        Integer32
    MAX-ACCESS    read-only
    STATUS        current
    DESCRIPTION   ""
    ::= { pmFacilityDataRecord 176 }

muxFacilityCurrent15minTable OBJECT-TYPE
    SYNTAX        SEQUENCE OF MuxFacilityCurrent15minEntry
    MAX-ACCESS    not-accessible
    STATUS        current
    DESCRIPTION   ""
    ::= { pmFacilityDataRecord 177 }

muxFacilityCurrent15minEntry OBJECT-TYPE
    SYNTAX        MuxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { muxFacilityCurrent15minTable 1 }

MuxFacilityCurrent15minEntry ::= SEQUENCE
  {    muxFacilityCurrent15minES Unsigned32,
    muxFacilityCurrent15minSES Unsigned32,
    muxFacilityCurrent15minCrc Unsigned32,
    muxFacilityCurrent15minElapsedTime Integer32 }

muxFacilityCurrent15minES OBJECT-TYPE
    SYNTAX        Unsigned32
    MAX-ACCESS    read-only
    STATUS        current
    DESCRIPTION   "Multiplexer Errored Seconds"
    ::= { muxFacilityCurrent15minEntry 1 }

muxFacilityCurrent15minSES OBJECT-TYPE
    SYNTAX        Unsigned32
    MAX-ACCESS    read-only
    STATUS        current
    DESCRIPTION   "Multiplexer Severely Errored Seconds"
    ::= { muxFacilityCurrent15minEntry 2 }

muxFacilityCurrent15minCrc OBJECT-TYPE
    SYNTAX        Unsigned32
    MAX-ACCESS    read-only
    STATUS        current
    DESCRIPTION   "Multiplexer Cyclic Redundancy Check Errors"
    ::= { muxFacilityCurrent15minEntry 3 }

muxFacilityCurrent15minElapsedTime OBJECT-TYPE
    SYNTAX        Integer32 (0..9000)
    MAX-ACCESS    read-only
    STATUS        current
    DESCRIPTION   "Elapsed 15Min"
    ::= { muxFacilityCurrent15minEntry 4 }

endOfMuxFacilityCurrent15minTable OBJECT-TYPE
    SYNTAX        Integer32
    MAX-ACCESS    read-only
    STATUS        current
    DESCRIPTION   ""
    ::= { pmFacilityDataRecord 178 }

muxFacilityCurrent1dayTable OBJECT-TYPE
    SYNTAX        SEQUENCE OF MuxFacilityCurrent1dayEntry
    MAX-ACCESS    not-accessible
    STATUS        current
    DESCRIPTION   ""
    ::= { pmFacilityDataRecord 179 }

muxFacilityCurrent1dayEntry OBJECT-TYPE
    SYNTAX        MuxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { muxFacilityCurrent1dayTable 1 }

MuxFacilityCurrent1dayEntry ::= SEQUENCE
  {    muxFacilityCurrent1dayES Unsigned32,
    muxFacilityCurrent1daySES Unsigned32,
    muxFacilityCurrent1dayCrc Unsigned32,
    muxFacilityCurrent1dayElapsedTime Integer32 }

muxFacilityCurrent1dayES OBJECT-TYPE
    SYNTAX        Unsigned32
    MAX-ACCESS    read-only
    STATUS        current
    DESCRIPTION   "Multiplexer Errored Seconds"
    ::= { muxFacilityCurrent1dayEntry 1 }

muxFacilityCurrent1daySES OBJECT-TYPE
    SYNTAX        Unsigned32
    MAX-ACCESS    read-only
    STATUS        current
    DESCRIPTION   "Multiplexer Severely Errored Seconds"
    ::= { muxFacilityCurrent1dayEntry 2 }

muxFacilityCurrent1dayCrc OBJECT-TYPE
    SYNTAX        Unsigned32
    MAX-ACCESS    read-only
    STATUS        current
    DESCRIPTION   "Multiplexer Cyclic Redundancy Check Errors"
    ::= { muxFacilityCurrent1dayEntry 3 }

muxFacilityCurrent1dayElapsedTime OBJECT-TYPE
    SYNTAX        Integer32 (0..86400)
    MAX-ACCESS    read-only
    STATUS        current
    DESCRIPTION   "Elapsed 1Day"
    ::= { muxFacilityCurrent1dayEntry 4 }

endOfMuxFacilityCurrent1dayTable OBJECT-TYPE
    SYNTAX        Integer32
    MAX-ACCESS    read-only
    STATUS        current
    DESCRIPTION   ""
    ::= { pmFacilityDataRecord 180 }

muxFacilityHistorical15minTable OBJECT-TYPE
    SYNTAX        SEQUENCE OF MuxFacilityHistorical15minEntry
    MAX-ACCESS    not-accessible
    STATUS        current
    DESCRIPTION   ""
    ::= { pmFacilityDataRecord 181 }

muxFacilityHistorical15minEntry OBJECT-TYPE
    SYNTAX        MuxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  muxFacilityHistorical15minNumber
                }
    ::= { muxFacilityHistorical15minTable 1 }

MuxFacilityHistorical15minEntry ::= SEQUENCE
  {    muxFacilityHistorical15minNumber Integer32,
    muxFacilityHistorical15minES Unsigned32,
    muxFacilityHistorical15minSES Unsigned32,
    muxFacilityHistorical15minCrc Unsigned32,
    muxFacilityHistorical15minValidFlag TruthValue,
    muxFacilityHistorical15minTimeStamp DateAndTime }

muxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { muxFacilityHistorical15minEntry 1 }

muxFacilityHistorical15minES OBJECT-TYPE
    SYNTAX        Unsigned32
    MAX-ACCESS    read-only
    STATUS        current
    DESCRIPTION   "Multiplexer Errored Seconds"
    ::= { muxFacilityHistorical15minEntry 2 }

muxFacilityHistorical15minSES OBJECT-TYPE
    SYNTAX        Unsigned32
    MAX-ACCESS    read-only
    STATUS        current
    DESCRIPTION   "Multiplexer Severely Errored Seconds"
    ::= { muxFacilityHistorical15minEntry 3 }

muxFacilityHistorical15minCrc OBJECT-TYPE
    SYNTAX        Unsigned32
    MAX-ACCESS    read-only
    STATUS        current
    DESCRIPTION   "Multiplexer Cyclic Redundancy Check Errors"
    ::= { muxFacilityHistorical15minEntry 4 }

muxFacilityHistorical15minValidFlag OBJECT-TYPE
    SYNTAX        TruthValue
    MAX-ACCESS    read-only
    STATUS        current
    DESCRIPTION   "Valid Flag"
    ::= { muxFacilityHistorical15minEntry 5 }

muxFacilityHistorical15minTimeStamp OBJECT-TYPE
    SYNTAX        DateAndTime
    MAX-ACCESS    read-only
    STATUS        current
    DESCRIPTION   "Timestamp"
    ::= { muxFacilityHistorical15minEntry 6 }

endOfMuxFacilityHistorical15minTable OBJECT-TYPE
    SYNTAX        Integer32
    MAX-ACCESS    read-only
    STATUS        current
    DESCRIPTION   ""
    ::= { pmFacilityDataRecord 182 }

muxFacilityHistorical1dayTable OBJECT-TYPE
    SYNTAX        SEQUENCE OF MuxFacilityHistorical1dayEntry
    MAX-ACCESS    not-accessible
    STATUS        current
    DESCRIPTION   ""
    ::= { pmFacilityDataRecord 183 }

muxFacilityHistorical1dayEntry OBJECT-TYPE
    SYNTAX        MuxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  muxFacilityHistorical1dayNumber
                }
    ::= { muxFacilityHistorical1dayTable 1 }

MuxFacilityHistorical1dayEntry ::= SEQUENCE
  {    muxFacilityHistorical1dayNumber Integer32,
    muxFacilityHistorical1dayES Unsigned32,
    muxFacilityHistorical1daySES Unsigned32,
    muxFacilityHistorical1dayCrc Unsigned32,
    muxFacilityHistorical1dayValidFlag TruthValue,
    muxFacilityHistorical1dayTimeStamp DateAndTime }

muxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { muxFacilityHistorical1dayEntry 1 }

muxFacilityHistorical1dayES OBJECT-TYPE
    SYNTAX        Unsigned32
    MAX-ACCESS    read-only
    STATUS        current
    DESCRIPTION   "Multiplexer Errored Seconds"
    ::= { muxFacilityHistorical1dayEntry 2 }

muxFacilityHistorical1daySES OBJECT-TYPE
    SYNTAX        Unsigned32
    MAX-ACCESS    read-only
    STATUS        current
    DESCRIPTION   "Multiplexer Severely Errored Seconds"
    ::= { muxFacilityHistorical1dayEntry 3 }

muxFacilityHistorical1dayCrc OBJECT-TYPE
    SYNTAX        Unsigned32
    MAX-ACCESS    read-only
    STATUS        current
    DESCRIPTION   "Multiplexer Cyclic Redundancy Check Errors"
    ::= { muxFacilityHistorical1dayEntry 4 }

muxFacilityHistorical1dayValidFlag OBJECT-TYPE
    SYNTAX        TruthValue
    MAX-ACCESS    read-only
    STATUS        current
    DESCRIPTION   "Valid Flag"
    ::= { muxFacilityHistorical1dayEntry 5 }

muxFacilityHistorical1dayTimeStamp OBJECT-TYPE
    SYNTAX        DateAndTime
    MAX-ACCESS    read-only
    STATUS        current
    DESCRIPTION   "Timestamp"
    ::= { muxFacilityHistorical1dayEntry 6 }

endOfMuxFacilityHistorical1dayTable OBJECT-TYPE
    SYNTAX        Integer32
    MAX-ACCESS    read-only
    STATUS        current
    DESCRIPTION   ""
    ::= { pmFacilityDataRecord 184 }

frTrmt1FacilityCurrent15minTable OBJECT-TYPE
    SYNTAX        SEQUENCE OF FrTrmt1FacilityCurrent15minEntry
    MAX-ACCESS    not-accessible
    STATUS        current
    DESCRIPTION   ""
    ::= { pmFacilityDataRecord 185 }

frTrmt1FacilityCurrent15minEntry OBJECT-TYPE
    SYNTAX        FrTrmt1FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frTrmt1FacilityCurrent15minTable 1 }

FrTrmt1FacilityCurrent15minEntry ::= SEQUENCE
  {    frTrmt1FacilityCurrent15minGoodFramesx Counter64String,
    frTrmt1FacilityCurrent15minPauseFrames Counter64String,
    frTrmt1FacilityCurrent15minBytes Counter64String,
    frTrmt1FacilityCurrent15minCrcFramesEgress Counter64String,
    frTrmt1FacilityCurrent15minElapsedTime Integer32 }

frTrmt1FacilityCurrent15minGoodFramesx OBJECT-TYPE
    SYNTAX        Counter64String
    MAX-ACCESS    read-only
    STATUS        current
    DESCRIPTION   "Frames Transmitted"
    ::= { frTrmt1FacilityCurrent15minEntry 1 }

frTrmt1FacilityCurrent15minPauseFrames OBJECT-TYPE
    SYNTAX        Counter64String
    MAX-ACCESS    read-only
    STATUS        current
    DESCRIPTION   "Pause Frames Transmitted"
    ::= { frTrmt1FacilityCurrent15minEntry 2 }

frTrmt1FacilityCurrent15minBytes OBJECT-TYPE
    SYNTAX        Counter64String
    MAX-ACCESS    read-only
    STATUS        current
    DESCRIPTION   "Bytes Transmitted"
    ::= { frTrmt1FacilityCurrent15minEntry 3 }

frTrmt1FacilityCurrent15minCrcFramesEgress OBJECT-TYPE
    SYNTAX        Counter64String
    MAX-ACCESS    read-only
    STATUS        current
    DESCRIPTION   "Egress CRC Errored Frames"
    ::= { frTrmt1FacilityCurrent15minEntry 4 }

frTrmt1FacilityCurrent15minElapsedTime OBJECT-TYPE
    SYNTAX        Integer32 (0..9000)
    MAX-ACCESS    read-only
    STATUS        current
    DESCRIPTION   "Elapsed 15Min"
    ::= { frTrmt1FacilityCurrent15minEntry 5 }

endOfFrTrmt1FacilityCurrent15minTable OBJECT-TYPE
    SYNTAX        Integer32
    MAX-ACCESS    read-only
    STATUS        current
    DESCRIPTION   ""
    ::= { pmFacilityDataRecord 186 }

frTrmt1FacilityCurrent1dayTable OBJECT-TYPE
    SYNTAX        SEQUENCE OF FrTrmt1FacilityCurrent1dayEntry
    MAX-ACCESS    not-accessible
    STATUS        current
    DESCRIPTION   ""
    ::= { pmFacilityDataRecord 187 }

frTrmt1FacilityCurrent1dayEntry OBJECT-TYPE
    SYNTAX        FrTrmt1FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frTrmt1FacilityCurrent1dayTable 1 }

FrTrmt1FacilityCurrent1dayEntry ::= SEQUENCE
  {    frTrmt1FacilityCurrent1dayGoodFramesx Counter64String,
    frTrmt1FacilityCurrent1dayPauseFrames Counter64String,
    frTrmt1FacilityCurrent1dayBytes Counter64String,
    frTrmt1FacilityCurrent1dayCrcFramesEgress Counter64String,
    frTrmt1FacilityCurrent1dayElapsedTime Integer32 }

frTrmt1FacilityCurrent1dayGoodFramesx OBJECT-TYPE
    SYNTAX        Counter64String
    MAX-ACCESS    read-only
    STATUS        current
    DESCRIPTION   "Frames Transmitted"
    ::= { frTrmt1FacilityCurrent1dayEntry 1 }

frTrmt1FacilityCurrent1dayPauseFrames OBJECT-TYPE
    SYNTAX        Counter64String
    MAX-ACCESS    read-only
    STATUS        current
    DESCRIPTION   "Pause Frames Transmitted"
    ::= { frTrmt1FacilityCurrent1dayEntry 2 }

frTrmt1FacilityCurrent1dayBytes OBJECT-TYPE
    SYNTAX        Counter64String
    MAX-ACCESS    read-only
    STATUS        current
    DESCRIPTION   "Bytes Transmitted"
    ::= { frTrmt1FacilityCurrent1dayEntry 3 }

frTrmt1FacilityCurrent1dayCrcFramesEgress OBJECT-TYPE
    SYNTAX        Counter64String
    MAX-ACCESS    read-only
    STATUS        current
    DESCRIPTION   "Egress CRC Errored Frames"
    ::= { frTrmt1FacilityCurrent1dayEntry 4 }

frTrmt1FacilityCurrent1dayElapsedTime OBJECT-TYPE
    SYNTAX        Integer32 (0..86400)
    MAX-ACCESS    read-only
    STATUS        current
    DESCRIPTION   "Elapsed 1Day"
    ::= { frTrmt1FacilityCurrent1dayEntry 5 }

endOfFrTrmt1FacilityCurrent1dayTable OBJECT-TYPE
    SYNTAX        Integer32
    MAX-ACCESS    read-only
    STATUS        current
    DESCRIPTION   ""
    ::= { pmFacilityDataRecord 188 }

frTrmt1FacilityHistorical15minTable OBJECT-TYPE
    SYNTAX        SEQUENCE OF FrTrmt1FacilityHistorical15minEntry
    MAX-ACCESS    not-accessible
    STATUS        current
    DESCRIPTION   ""
    ::= { pmFacilityDataRecord 189 }

frTrmt1FacilityHistorical15minEntry OBJECT-TYPE
    SYNTAX        FrTrmt1FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  frTrmt1FacilityHistorical15minNumber
                }
    ::= { frTrmt1FacilityHistorical15minTable 1 }

FrTrmt1FacilityHistorical15minEntry ::= SEQUENCE
  {    frTrmt1FacilityHistorical15minNumber Integer32,
    frTrmt1FacilityHistorical15minGoodFramesx Counter64String,
    frTrmt1FacilityHistorical15minPauseFrames Counter64String,
    frTrmt1FacilityHistorical15minBytes Counter64String,
    frTrmt1FacilityHistorical15minCrcFramesEgress Counter64String,
    frTrmt1FacilityHistorical15minValidFlag TruthValue,
    frTrmt1FacilityHistorical15minTimeStamp DateAndTime }

frTrmt1FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frTrmt1FacilityHistorical15minEntry 1 }

frTrmt1FacilityHistorical15minGoodFramesx OBJECT-TYPE
    SYNTAX        Counter64String
    MAX-ACCESS    read-only
    STATUS        current
    DESCRIPTION   "Frames Transmitted"
    ::= { frTrmt1FacilityHistorical15minEntry 2 }

frTrmt1FacilityHistorical15minPauseFrames OBJECT-TYPE
    SYNTAX        Counter64String
    MAX-ACCESS    read-only
    STATUS        current
    DESCRIPTION   "Pause Frames Transmitted"
    ::= { frTrmt1FacilityHistorical15minEntry 3 }

frTrmt1FacilityHistorical15minBytes OBJECT-TYPE
    SYNTAX        Counter64String
    MAX-ACCESS    read-only
    STATUS        current
    DESCRIPTION   "Bytes Transmitted"
    ::= { frTrmt1FacilityHistorical15minEntry 4 }

frTrmt1FacilityHistorical15minCrcFramesEgress OBJECT-TYPE
    SYNTAX        Counter64String
    MAX-ACCESS    read-only
    STATUS        current
    DESCRIPTION   "Egress CRC Errored Frames"
    ::= { frTrmt1FacilityHistorical15minEntry 5 }

frTrmt1FacilityHistorical15minValidFlag OBJECT-TYPE
    SYNTAX        TruthValue
    MAX-ACCESS    read-only
    STATUS        current
    DESCRIPTION   "Valid Flag"
    ::= { frTrmt1FacilityHistorical15minEntry 6 }

frTrmt1FacilityHistorical15minTimeStamp OBJECT-TYPE
    SYNTAX        DateAndTime
    MAX-ACCESS    read-only
    STATUS        current
    DESCRIPTION   "Timestamp"
    ::= { frTrmt1FacilityHistorical15minEntry 7 }

endOfFrTrmt1FacilityHistorical15minTable OBJECT-TYPE
    SYNTAX        Integer32
    MAX-ACCESS    read-only
    STATUS        current
    DESCRIPTION   ""
    ::= { pmFacilityDataRecord 190 }

frTrmt1FacilityHistorical1dayTable OBJECT-TYPE
    SYNTAX        SEQUENCE OF FrTrmt1FacilityHistorical1dayEntry
    MAX-ACCESS    not-accessible
    STATUS        current
    DESCRIPTION   ""
    ::= { pmFacilityDataRecord 191 }

frTrmt1FacilityHistorical1dayEntry OBJECT-TYPE
    SYNTAX        FrTrmt1FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  frTrmt1FacilityHistorical1dayNumber
                }
    ::= { frTrmt1FacilityHistorical1dayTable 1 }

FrTrmt1FacilityHistorical1dayEntry ::= SEQUENCE
  {    frTrmt1FacilityHistorical1dayNumber Integer32,
    frTrmt1FacilityHistorical1dayGoodFramesx Counter64String,
    frTrmt1FacilityHistorical1dayPauseFrames Counter64String,
    frTrmt1FacilityHistorical1dayBytes Counter64String,
    frTrmt1FacilityHistorical1dayCrcFramesEgress Counter64String,
    frTrmt1FacilityHistorical1dayValidFlag TruthValue,
    frTrmt1FacilityHistorical1dayTimeStamp DateAndTime }

frTrmt1FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frTrmt1FacilityHistorical1dayEntry 1 }

frTrmt1FacilityHistorical1dayGoodFramesx OBJECT-TYPE
    SYNTAX        Counter64String
    MAX-ACCESS    read-only
    STATUS        current
    DESCRIPTION   "Frames Transmitted"
    ::= { frTrmt1FacilityHistorical1dayEntry 2 }

frTrmt1FacilityHistorical1dayPauseFrames OBJECT-TYPE
    SYNTAX        Counter64String
    MAX-ACCESS    read-only
    STATUS        current
    DESCRIPTION   "Pause Frames Transmitted"
    ::= { frTrmt1FacilityHistorical1dayEntry 3 }

frTrmt1FacilityHistorical1dayBytes OBJECT-TYPE
    SYNTAX        Counter64String
    MAX-ACCESS    read-only
    STATUS        current
    DESCRIPTION   "Bytes Transmitted"
    ::= { frTrmt1FacilityHistorical1dayEntry 4 }

frTrmt1FacilityHistorical1dayCrcFramesEgress OBJECT-TYPE
    SYNTAX        Counter64String
    MAX-ACCESS    read-only
    STATUS        current
    DESCRIPTION   "Egress CRC Errored Frames"
    ::= { frTrmt1FacilityHistorical1dayEntry 5 }

frTrmt1FacilityHistorical1dayValidFlag OBJECT-TYPE
    SYNTAX        TruthValue
    MAX-ACCESS    read-only
    STATUS        current
    DESCRIPTION   "Valid Flag"
    ::= { frTrmt1FacilityHistorical1dayEntry 6 }

frTrmt1FacilityHistorical1dayTimeStamp OBJECT-TYPE
    SYNTAX        DateAndTime
    MAX-ACCESS    read-only
    STATUS        current
    DESCRIPTION   "Timestamp"
    ::= { frTrmt1FacilityHistorical1dayEntry 7 }

endOfFrTrmt1FacilityHistorical1dayTable OBJECT-TYPE
    SYNTAX        Integer32
    MAX-ACCESS    read-only
    STATUS        current
    DESCRIPTION   ""
    ::= { pmFacilityDataRecord 192 }

sarLinkTrmtFacilityCurrent15minTable OBJECT-TYPE
    SYNTAX        SEQUENCE OF SarLinkTrmtFacilityCurrent15minEntry
    MAX-ACCESS    not-accessible
    STATUS        current
    DESCRIPTION   ""
    ::= { pmFacilityDataRecord 193 }

sarLinkTrmtFacilityCurrent15minEntry OBJECT-TYPE
    SYNTAX        SarLinkTrmtFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sarLinkTrmtFacilityCurrent15minTable 1 }

SarLinkTrmtFacilityCurrent15minEntry ::= SEQUENCE
  {    sarLinkTrmtFacilityCurrent15minES Unsigned32,
    sarLinkTrmtFacilityCurrent15minSES Counter64String,
    sarLinkTrmtFacilityCurrent15minElapsedTime Integer32 }

sarLinkTrmtFacilityCurrent15minES OBJECT-TYPE
    SYNTAX        Unsigned32
    MAX-ACCESS    read-only
    STATUS        current
    DESCRIPTION   "SAR Link Transmit ES"
    ::= { sarLinkTrmtFacilityCurrent15minEntry 1 }

sarLinkTrmtFacilityCurrent15minSES OBJECT-TYPE
    SYNTAX        Counter64String
    MAX-ACCESS    read-only
    STATUS        current
    DESCRIPTION   "SAR Link Transmit SES"
    ::= { sarLinkTrmtFacilityCurrent15minEntry 2 }

sarLinkTrmtFacilityCurrent15minElapsedTime OBJECT-TYPE
    SYNTAX        Integer32 (0..9000)
    MAX-ACCESS    read-only
    STATUS        current
    DESCRIPTION   "Elapsed 15Min"
    ::= { sarLinkTrmtFacilityCurrent15minEntry 3 }

endOfSarLinkTrmt1FacilityCurrent15minTable OBJECT-TYPE
    SYNTAX        Integer32
    MAX-ACCESS    read-only
    STATUS        current
    DESCRIPTION   ""
    ::= { pmFacilityDataRecord 194 }

sarLinkTrmtFacilityCurrent1dayTable OBJECT-TYPE
    SYNTAX        SEQUENCE OF SarLinkTrmtFacilityCurrent1dayEntry
    MAX-ACCESS    not-accessible
    STATUS        current
    DESCRIPTION   ""
    ::= { pmFacilityDataRecord 195 }

sarLinkTrmtFacilityCurrent1dayEntry OBJECT-TYPE
    SYNTAX        SarLinkTrmtFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sarLinkTrmtFacilityCurrent1dayTable 1 }

SarLinkTrmtFacilityCurrent1dayEntry ::= SEQUENCE
  {    sarLinkTrmtFacilityCurrent1dayES Unsigned32,
    sarLinkTrmtFacilityCurrent1daySES Counter64String,
    sarLinkTrmtFacilityCurrent1dayElapsedTime Integer32 }

sarLinkTrmtFacilityCurrent1dayES OBJECT-TYPE
    SYNTAX        Unsigned32
    MAX-ACCESS    read-only
    STATUS        current
    DESCRIPTION   "SAR Link Transmit ES"
    ::= { sarLinkTrmtFacilityCurrent1dayEntry 1 }

sarLinkTrmtFacilityCurrent1daySES OBJECT-TYPE
    SYNTAX        Counter64String
    MAX-ACCESS    read-only
    STATUS        current
    DESCRIPTION   "SAR Link Transmit SES"
    ::= { sarLinkTrmtFacilityCurrent1dayEntry 2 }

sarLinkTrmtFacilityCurrent1dayElapsedTime OBJECT-TYPE
    SYNTAX        Integer32 (0..86400)
    MAX-ACCESS    read-only
    STATUS        current
    DESCRIPTION   "Elapsed 1Day"
    ::= { sarLinkTrmtFacilityCurrent1dayEntry 3 }

endOfSarLinkTrmt1FacilityCurrent1dayTable OBJECT-TYPE
    SYNTAX        Integer32
    MAX-ACCESS    read-only
    STATUS        current
    DESCRIPTION   ""
    ::= { pmFacilityDataRecord 196 }

sarLinkTrmtFacilityHistorical15minTable OBJECT-TYPE
    SYNTAX        SEQUENCE OF SarLinkTrmtFacilityHistorical15minEntry
    MAX-ACCESS    not-accessible
    STATUS        current
    DESCRIPTION   ""
    ::= { pmFacilityDataRecord 197 }

sarLinkTrmtFacilityHistorical15minEntry OBJECT-TYPE
    SYNTAX        SarLinkTrmtFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  sarLinkTrmtFacilityHistorical15minNumber
                }
    ::= { sarLinkTrmtFacilityHistorical15minTable 1 }

SarLinkTrmtFacilityHistorical15minEntry ::= SEQUENCE
  {    sarLinkTrmtFacilityHistorical15minNumber Integer32,
    sarLinkTrmtFacilityHistorical15minES Unsigned32,
    sarLinkTrmtFacilityHistorical15minSES Counter64String,
    sarLinkTrmtFacilityHistorical15minValidFlag TruthValue,
    sarLinkTrmtFacilityHistorical15minTimeStamp DateAndTime }

sarLinkTrmtFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { sarLinkTrmtFacilityHistorical15minEntry 1 }

sarLinkTrmtFacilityHistorical15minES OBJECT-TYPE
    SYNTAX        Unsigned32
    MAX-ACCESS    read-only
    STATUS        current
    DESCRIPTION   "SAR Link Transmit ES"
    ::= { sarLinkTrmtFacilityHistorical15minEntry 2 }

sarLinkTrmtFacilityHistorical15minSES OBJECT-TYPE
    SYNTAX        Counter64String
    MAX-ACCESS    read-only
    STATUS        current
    DESCRIPTION   "SAR Link Transmit SES"
    ::= { sarLinkTrmtFacilityHistorical15minEntry 3 }

sarLinkTrmtFacilityHistorical15minValidFlag OBJECT-TYPE
    SYNTAX        TruthValue
    MAX-ACCESS    read-only
    STATUS        current
    DESCRIPTION   "Valid Flag"
    ::= { sarLinkTrmtFacilityHistorical15minEntry 4 }

sarLinkTrmtFacilityHistorical15minTimeStamp OBJECT-TYPE
    SYNTAX        DateAndTime
    MAX-ACCESS    read-only
    STATUS        current
    DESCRIPTION   "Timestamp"
    ::= { sarLinkTrmtFacilityHistorical15minEntry 5 }

endOfSarLinkTrmt1FacilityHistorical15minTable OBJECT-TYPE
    SYNTAX        Integer32
    MAX-ACCESS    read-only
    STATUS        current
    DESCRIPTION   ""
    ::= { pmFacilityDataRecord 198 }

sarLinkTrmtFacilityHistorical1dayTable OBJECT-TYPE
    SYNTAX        SEQUENCE OF SarLinkTrmtFacilityHistorical1dayEntry
    MAX-ACCESS    not-accessible
    STATUS        current
    DESCRIPTION   ""
    ::= { pmFacilityDataRecord 199 }

sarLinkTrmtFacilityHistorical1dayEntry OBJECT-TYPE
    SYNTAX        SarLinkTrmtFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  sarLinkTrmtFacilityHistorical1dayNumber
                }
    ::= { sarLinkTrmtFacilityHistorical1dayTable 1 }

SarLinkTrmtFacilityHistorical1dayEntry ::= SEQUENCE
  {    sarLinkTrmtFacilityHistorical1dayNumber Integer32,
    sarLinkTrmtFacilityHistorical1dayES Unsigned32,
    sarLinkTrmtFacilityHistorical1daySES Counter64String,
    sarLinkTrmtFacilityHistorical1dayValidFlag TruthValue,
    sarLinkTrmtFacilityHistorical1dayTimeStamp DateAndTime }

sarLinkTrmtFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { sarLinkTrmtFacilityHistorical1dayEntry 1 }

sarLinkTrmtFacilityHistorical1dayES OBJECT-TYPE
    SYNTAX        Unsigned32
    MAX-ACCESS    read-only
    STATUS        current
    DESCRIPTION   "SAR Link Transmit ES"
    ::= { sarLinkTrmtFacilityHistorical1dayEntry 2 }

sarLinkTrmtFacilityHistorical1daySES OBJECT-TYPE
    SYNTAX        Counter64String
    MAX-ACCESS    read-only
    STATUS        current
    DESCRIPTION   "SAR Link Transmit SES"
    ::= { sarLinkTrmtFacilityHistorical1dayEntry 3 }

sarLinkTrmtFacilityHistorical1dayValidFlag OBJECT-TYPE
    SYNTAX        TruthValue
    MAX-ACCESS    read-only
    STATUS        current
    DESCRIPTION   "Valid Flag"
    ::= { sarLinkTrmtFacilityHistorical1dayEntry 4 }

sarLinkTrmtFacilityHistorical1dayTimeStamp OBJECT-TYPE
    SYNTAX        DateAndTime
    MAX-ACCESS    read-only
    STATUS        current
    DESCRIPTION   "Timestamp"
    ::= { sarLinkTrmtFacilityHistorical1dayEntry 5 }

endOfSarLinkTrmt1FacilityHistorical1dayTable OBJECT-TYPE
    SYNTAX        Integer32
    MAX-ACCESS    read-only
    STATUS        current
    DESCRIPTION   ""
    ::= { pmFacilityDataRecord 200 }

sarLinkRcvFacilityCurrent15minTable OBJECT-TYPE
    SYNTAX        SEQUENCE OF SarLinkRcvFacilityCurrent15minEntry
    MAX-ACCESS    not-accessible
    STATUS        current
    DESCRIPTION   ""
    ::= { pmFacilityDataRecord 201 }

sarLinkRcvFacilityCurrent15minEntry OBJECT-TYPE
    SYNTAX        SarLinkRcvFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sarLinkRcvFacilityCurrent15minTable 1 }

SarLinkRcvFacilityCurrent15minEntry ::= SEQUENCE
  {    sarLinkRcvFacilityCurrent15minES Unsigned32,
    sarLinkRcvFacilityCurrent15minSES Unsigned32,
    sarLinkRcvFacilityCurrent15minElapsedTime Integer32 }

sarLinkRcvFacilityCurrent15minES OBJECT-TYPE
    SYNTAX        Unsigned32
    MAX-ACCESS    read-only
    STATUS        current
    DESCRIPTION   "SAR Link Receive ES"
    ::= { sarLinkRcvFacilityCurrent15minEntry 1 }

sarLinkRcvFacilityCurrent15minSES OBJECT-TYPE
    SYNTAX        Unsigned32
    MAX-ACCESS    read-only
    STATUS        current
    DESCRIPTION   "SAR Link Recive SES"
    ::= { sarLinkRcvFacilityCurrent15minEntry 2 }

sarLinkRcvFacilityCurrent15minElapsedTime OBJECT-TYPE
    SYNTAX        Integer32 (0..9000)
    MAX-ACCESS    read-only
    STATUS        current
    DESCRIPTION   "Elapsed 15Min"
    ::= { sarLinkRcvFacilityCurrent15minEntry 3 }

endOfSarLinkRcvFacilityCurrent15minTable OBJECT-TYPE
    SYNTAX        Integer32
    MAX-ACCESS    read-only
    STATUS        current
    DESCRIPTION   ""
    ::= { pmFacilityDataRecord 202 }

sarLinkRcvFacilityCurrent1dayTable OBJECT-TYPE
    SYNTAX        SEQUENCE OF SarLinkRcvFacilityCurrent1dayEntry
    MAX-ACCESS    not-accessible
    STATUS        current
    DESCRIPTION   ""
    ::= { pmFacilityDataRecord 203 }

sarLinkRcvFacilityCurrent1dayEntry OBJECT-TYPE
    SYNTAX        SarLinkRcvFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sarLinkRcvFacilityCurrent1dayTable 1 }

SarLinkRcvFacilityCurrent1dayEntry ::= SEQUENCE
  {    sarLinkRcvFacilityCurrent1dayES Unsigned32,
    sarLinkRcvFacilityCurrent1daySES Unsigned32,
    sarLinkRcvFacilityCurrent1dayElapsedTime Integer32 }

sarLinkRcvFacilityCurrent1dayES OBJECT-TYPE
    SYNTAX        Unsigned32
    MAX-ACCESS    read-only
    STATUS        current
    DESCRIPTION   "SAR Link Receive ES"
    ::= { sarLinkRcvFacilityCurrent1dayEntry 1 }

sarLinkRcvFacilityCurrent1daySES OBJECT-TYPE
    SYNTAX        Unsigned32
    MAX-ACCESS    read-only
    STATUS        current
    DESCRIPTION   "SAR Link Recive SES"
    ::= { sarLinkRcvFacilityCurrent1dayEntry 2 }

sarLinkRcvFacilityCurrent1dayElapsedTime OBJECT-TYPE
    SYNTAX        Integer32 (0..86400)
    MAX-ACCESS    read-only
    STATUS        current
    DESCRIPTION   "Elapsed 1Day"
    ::= { sarLinkRcvFacilityCurrent1dayEntry 3 }

endOfSarLinkRcvFacilityCurrent1dayTable OBJECT-TYPE
    SYNTAX        Integer32
    MAX-ACCESS    read-only
    STATUS        current
    DESCRIPTION   ""
    ::= { pmFacilityDataRecord 204 }

sarLinkRcvFacilityHistorical15minTable OBJECT-TYPE
    SYNTAX        SEQUENCE OF SarLinkRcvFacilityHistorical15minEntry
    MAX-ACCESS    not-accessible
    STATUS        current
    DESCRIPTION   ""
    ::= { pmFacilityDataRecord 205 }

sarLinkRcvFacilityHistorical15minEntry OBJECT-TYPE
    SYNTAX        SarLinkRcvFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  sarLinkRcvFacilityHistorical15minNumber
                }
    ::= { sarLinkRcvFacilityHistorical15minTable 1 }

SarLinkRcvFacilityHistorical15minEntry ::= SEQUENCE
  {    sarLinkRcvFacilityHistorical15minNumber Integer32,
    sarLinkRcvFacilityHistorical15minES Unsigned32,
    sarLinkRcvFacilityHistorical15minSES Unsigned32,
    sarLinkRcvFacilityHistorical15minValidFlag TruthValue,
    sarLinkRcvFacilityHistorical15minTimeStamp DateAndTime }

sarLinkRcvFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { sarLinkRcvFacilityHistorical15minEntry 1 }

sarLinkRcvFacilityHistorical15minES OBJECT-TYPE
    SYNTAX        Unsigned32
    MAX-ACCESS    read-only
    STATUS        current
    DESCRIPTION   "SAR Link Receive ES"
    ::= { sarLinkRcvFacilityHistorical15minEntry 2 }

sarLinkRcvFacilityHistorical15minSES OBJECT-TYPE
    SYNTAX        Unsigned32
    MAX-ACCESS    read-only
    STATUS        current
    DESCRIPTION   "SAR Link Recive SES"
    ::= { sarLinkRcvFacilityHistorical15minEntry 3 }

sarLinkRcvFacilityHistorical15minValidFlag OBJECT-TYPE
    SYNTAX        TruthValue
    MAX-ACCESS    read-only
    STATUS        current
    DESCRIPTION   "Valid Flag"
    ::= { sarLinkRcvFacilityHistorical15minEntry 4 }

sarLinkRcvFacilityHistorical15minTimeStamp OBJECT-TYPE
    SYNTAX        DateAndTime
    MAX-ACCESS    read-only
    STATUS        current
    DESCRIPTION   "Timestamp"
    ::= { sarLinkRcvFacilityHistorical15minEntry 5 }

endOfSarLinkRcvFacilityHistorical15minTable OBJECT-TYPE
    SYNTAX        Integer32
    MAX-ACCESS    read-only
    STATUS        current
    DESCRIPTION   ""
    ::= { pmFacilityDataRecord 206 }

sarLinkRcvFacilityHistorical1dayTable OBJECT-TYPE
    SYNTAX        SEQUENCE OF SarLinkRcvFacilityHistorical1dayEntry
    MAX-ACCESS    not-accessible
    STATUS        current
    DESCRIPTION   ""
    ::= { pmFacilityDataRecord 207 }

sarLinkRcvFacilityHistorical1dayEntry OBJECT-TYPE
    SYNTAX        SarLinkRcvFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  sarLinkRcvFacilityHistorical1dayNumber
                }
    ::= { sarLinkRcvFacilityHistorical1dayTable 1 }

SarLinkRcvFacilityHistorical1dayEntry ::= SEQUENCE
  {    sarLinkRcvFacilityHistorical1dayNumber Integer32,
    sarLinkRcvFacilityHistorical1dayES Unsigned32,
    sarLinkRcvFacilityHistorical1daySES Unsigned32,
    sarLinkRcvFacilityHistorical1dayValidFlag TruthValue,
    sarLinkRcvFacilityHistorical1dayTimeStamp DateAndTime }

sarLinkRcvFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { sarLinkRcvFacilityHistorical1dayEntry 1 }

sarLinkRcvFacilityHistorical1dayES OBJECT-TYPE
    SYNTAX        Unsigned32
    MAX-ACCESS    read-only
    STATUS        current
    DESCRIPTION   "SAR Link Receive ES"
    ::= { sarLinkRcvFacilityHistorical1dayEntry 2 }

sarLinkRcvFacilityHistorical1daySES OBJECT-TYPE
    SYNTAX        Unsigned32
    MAX-ACCESS    read-only
    STATUS        current
    DESCRIPTION   "SAR Link Recive SES"
    ::= { sarLinkRcvFacilityHistorical1dayEntry 3 }

sarLinkRcvFacilityHistorical1dayValidFlag OBJECT-TYPE
    SYNTAX        TruthValue
    MAX-ACCESS    read-only
    STATUS        current
    DESCRIPTION   "Valid Flag"
    ::= { sarLinkRcvFacilityHistorical1dayEntry 4 }

sarLinkRcvFacilityHistorical1dayTimeStamp OBJECT-TYPE
    SYNTAX        DateAndTime
    MAX-ACCESS    read-only
    STATUS        current
    DESCRIPTION   "Timestamp"
    ::= { sarLinkRcvFacilityHistorical1dayEntry 5 }

endOfSarLinkRcvFacilityHistorical1dayTable OBJECT-TYPE
    SYNTAX        Integer32
    MAX-ACCESS    read-only
    STATUS        current
    DESCRIPTION   ""
    ::= { pmFacilityDataRecord 208 }

frTrmt2FacilityCurrent15minTable OBJECT-TYPE
    SYNTAX        SEQUENCE OF FrTrmt2FacilityCurrent15minEntry
    MAX-ACCESS    not-accessible
    STATUS        current
    DESCRIPTION   ""
    ::= { pmFacilityDataRecord 209 }

frTrmt2FacilityCurrent15minEntry OBJECT-TYPE
    SYNTAX        FrTrmt2FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frTrmt2FacilityCurrent15minTable 1 }

FrTrmt2FacilityCurrent15minEntry ::= SEQUENCE
  {    frTrmt2FacilityCurrent15minGoodFramesx Counter64String,
    frTrmt2FacilityCurrent15minPauseFrames Counter64String,
    frTrmt2FacilityCurrent15minBytes Counter64String,
    frTrmt2FacilityCurrent15minCrcFramesEgress Counter64String,
    frTrmt2FacilityCurrent15minDiscardedFrames Counter64String,
    frTrmt2FacilityCurrent15minElapsedTime Integer32 }

frTrmt2FacilityCurrent15minGoodFramesx OBJECT-TYPE
    SYNTAX        Counter64String
    MAX-ACCESS    read-only
    STATUS        current
    DESCRIPTION   "Frames Transmitted"
    ::= { frTrmt2FacilityCurrent15minEntry 1 }

frTrmt2FacilityCurrent15minPauseFrames OBJECT-TYPE
    SYNTAX        Counter64String
    MAX-ACCESS    read-only
    STATUS        current
    DESCRIPTION   "Pause Frames Transmitted"
    ::= { frTrmt2FacilityCurrent15minEntry 2 }

frTrmt2FacilityCurrent15minBytes OBJECT-TYPE
    SYNTAX        Counter64String
    MAX-ACCESS    read-only
    STATUS        current
    DESCRIPTION   "Bytes Transmitted"
    ::= { frTrmt2FacilityCurrent15minEntry 3 }

frTrmt2FacilityCurrent15minCrcFramesEgress OBJECT-TYPE
    SYNTAX        Counter64String
    MAX-ACCESS    read-only
    STATUS        current
    DESCRIPTION   "Egress CRC Errored Frames"
    ::= { frTrmt2FacilityCurrent15minEntry 4 }

frTrmt2FacilityCurrent15minDiscardedFrames OBJECT-TYPE
    SYNTAX        Counter64String
    MAX-ACCESS    read-only
    STATUS        current
    DESCRIPTION   "Transmit Frames Discarded"
    ::= { frTrmt2FacilityCurrent15minEntry 5 }

frTrmt2FacilityCurrent15minElapsedTime OBJECT-TYPE
    SYNTAX        Integer32 (0..9000)
    MAX-ACCESS    read-only
    STATUS        current
    DESCRIPTION   "Elapsed 15Min"
    ::= { frTrmt2FacilityCurrent15minEntry 6 }

endOfFrTrmt2FacilityCurrent15minTable OBJECT-TYPE
    SYNTAX        Integer32
    MAX-ACCESS    read-only
    STATUS        current
    DESCRIPTION   ""
    ::= { pmFacilityDataRecord 210 }

frTrmt2FacilityCurrent1dayTable OBJECT-TYPE
    SYNTAX        SEQUENCE OF FrTrmt2FacilityCurrent1dayEntry
    MAX-ACCESS    not-accessible
    STATUS        current
    DESCRIPTION   ""
    ::= { pmFacilityDataRecord 211 }

frTrmt2FacilityCurrent1dayEntry OBJECT-TYPE
    SYNTAX        FrTrmt2FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frTrmt2FacilityCurrent1dayTable 1 }

FrTrmt2FacilityCurrent1dayEntry ::= SEQUENCE
  {    frTrmt2FacilityCurrent1dayGoodFramesx Counter64String,
    frTrmt2FacilityCurrent1dayPauseFrames Counter64String,
    frTrmt2FacilityCurrent1dayBytes Counter64String,
    frTrmt2FacilityCurrent1dayCrcFramesEgress Counter64String,
    frTrmt2FacilityCurrent1dayDiscardedFrames Counter64String,
    frTrmt2FacilityCurrent1dayElapsedTime Integer32 }

frTrmt2FacilityCurrent1dayGoodFramesx OBJECT-TYPE
    SYNTAX        Counter64String
    MAX-ACCESS    read-only
    STATUS        current
    DESCRIPTION   "Frames Transmitted"
    ::= { frTrmt2FacilityCurrent1dayEntry 1 }

frTrmt2FacilityCurrent1dayPauseFrames OBJECT-TYPE
    SYNTAX        Counter64String
    MAX-ACCESS    read-only
    STATUS        current
    DESCRIPTION   "Pause Frames Transmitted"
    ::= { frTrmt2FacilityCurrent1dayEntry 2 }

frTrmt2FacilityCurrent1dayBytes OBJECT-TYPE
    SYNTAX        Counter64String
    MAX-ACCESS    read-only
    STATUS        current
    DESCRIPTION   "Bytes Transmitted"
    ::= { frTrmt2FacilityCurrent1dayEntry 3 }

frTrmt2FacilityCurrent1dayCrcFramesEgress OBJECT-TYPE
    SYNTAX        Counter64String
    MAX-ACCESS    read-only
    STATUS        current
    DESCRIPTION   "Egress CRC Errored Frames"
    ::= { frTrmt2FacilityCurrent1dayEntry 4 }

frTrmt2FacilityCurrent1dayDiscardedFrames OBJECT-TYPE
    SYNTAX        Counter64String
    MAX-ACCESS    read-only
    STATUS        current
    DESCRIPTION   "Transmit Frames Discarded"
    ::= { frTrmt2FacilityCurrent1dayEntry 5 }

frTrmt2FacilityCurrent1dayElapsedTime OBJECT-TYPE
    SYNTAX        Integer32 (0..86400)
    MAX-ACCESS    read-only
    STATUS        current
    DESCRIPTION   "Elapsed 1Day"
    ::= { frTrmt2FacilityCurrent1dayEntry 6 }

endOfFrTrmt2FacilityCurrent1dayTable OBJECT-TYPE
    SYNTAX        Integer32
    MAX-ACCESS    read-only
    STATUS        current
    DESCRIPTION   ""
    ::= { pmFacilityDataRecord 212 }

frTrmt2FacilityHistorical15minTable OBJECT-TYPE
    SYNTAX        SEQUENCE OF FrTrmt2FacilityHistorical15minEntry
    MAX-ACCESS    not-accessible
    STATUS        current
    DESCRIPTION   ""
    ::= { pmFacilityDataRecord 213 }

frTrmt2FacilityHistorical15minEntry OBJECT-TYPE
    SYNTAX        FrTrmt2FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  frTrmt2FacilityHistorical15minNumber
                }
    ::= { frTrmt2FacilityHistorical15minTable 1 }

FrTrmt2FacilityHistorical15minEntry ::= SEQUENCE
  {    frTrmt2FacilityHistorical15minNumber Integer32,
    frTrmt2FacilityHistorical15minGoodFramesx Counter64String,
    frTrmt2FacilityHistorical15minPauseFrames Counter64String,
    frTrmt2FacilityHistorical15minBytes Counter64String,
    frTrmt2FacilityHistorical15minCrcFramesEgress Counter64String,
    frTrmt2FacilityHistorical15minDiscardedFrames Counter64String,
    frTrmt2FacilityHistorical15minValidFlag TruthValue,
    frTrmt2FacilityHistorical15minTimeStamp DateAndTime }

frTrmt2FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frTrmt2FacilityHistorical15minEntry 1 }

frTrmt2FacilityHistorical15minGoodFramesx OBJECT-TYPE
    SYNTAX        Counter64String
    MAX-ACCESS    read-only
    STATUS        current
    DESCRIPTION   "Frames Transmitted"
    ::= { frTrmt2FacilityHistorical15minEntry 2 }

frTrmt2FacilityHistorical15minPauseFrames OBJECT-TYPE
    SYNTAX        Counter64String
    MAX-ACCESS    read-only
    STATUS        current
    DESCRIPTION   "Pause Frames Transmitted"
    ::= { frTrmt2FacilityHistorical15minEntry 3 }

frTrmt2FacilityHistorical15minBytes OBJECT-TYPE
    SYNTAX        Counter64String
    MAX-ACCESS    read-only
    STATUS        current
    DESCRIPTION   "Bytes Transmitted"
    ::= { frTrmt2FacilityHistorical15minEntry 4 }

frTrmt2FacilityHistorical15minCrcFramesEgress OBJECT-TYPE
    SYNTAX        Counter64String
    MAX-ACCESS    read-only
    STATUS        current
    DESCRIPTION   "Egress CRC Errored Frames"
    ::= { frTrmt2FacilityHistorical15minEntry 5 }

frTrmt2FacilityHistorical15minDiscardedFrames OBJECT-TYPE
    SYNTAX        Counter64String
    MAX-ACCESS    read-only
    STATUS        current
    DESCRIPTION   "Transmit Frames Discarded"
    ::= { frTrmt2FacilityHistorical15minEntry 6 }

frTrmt2FacilityHistorical15minValidFlag OBJECT-TYPE
    SYNTAX        TruthValue
    MAX-ACCESS    read-only
    STATUS        current
    DESCRIPTION   "Valid Flag"
    ::= { frTrmt2FacilityHistorical15minEntry 7 }

frTrmt2FacilityHistorical15minTimeStamp OBJECT-TYPE
    SYNTAX        DateAndTime
    MAX-ACCESS    read-only
    STATUS        current
    DESCRIPTION   "Timestamp"
    ::= { frTrmt2FacilityHistorical15minEntry 8 }

endOfFrTrmt2FacilityHistorical15minTable OBJECT-TYPE
    SYNTAX        Integer32
    MAX-ACCESS    read-only
    STATUS        current
    DESCRIPTION   ""
    ::= { pmFacilityDataRecord 214 }

frTrmt2FacilityHistorical1dayTable OBJECT-TYPE
    SYNTAX        SEQUENCE OF FrTrmt2FacilityHistorical1dayEntry
    MAX-ACCESS    not-accessible
    STATUS        current
    DESCRIPTION   ""
    ::= { pmFacilityDataRecord 215 }

frTrmt2FacilityHistorical1dayEntry OBJECT-TYPE
    SYNTAX        FrTrmt2FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  frTrmt2FacilityHistorical1dayNumber
                }
    ::= { frTrmt2FacilityHistorical1dayTable 1 }

FrTrmt2FacilityHistorical1dayEntry ::= SEQUENCE
  {    frTrmt2FacilityHistorical1dayNumber Integer32,
    frTrmt2FacilityHistorical1dayGoodFramesx Counter64String,
    frTrmt2FacilityHistorical1dayPauseFrames Counter64String,
    frTrmt2FacilityHistorical1dayBytes Counter64String,
    frTrmt2FacilityHistorical1dayCrcFramesEgress Counter64String,
    frTrmt2FacilityHistorical1dayDiscardedFrames Counter64String,
    frTrmt2FacilityHistorical1dayValidFlag TruthValue,
    frTrmt2FacilityHistorical1dayTimeStamp DateAndTime }

frTrmt2FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frTrmt2FacilityHistorical1dayEntry 1 }

frTrmt2FacilityHistorical1dayGoodFramesx OBJECT-TYPE
    SYNTAX        Counter64String
    MAX-ACCESS    read-only
    STATUS        current
    DESCRIPTION   "Frames Transmitted"
    ::= { frTrmt2FacilityHistorical1dayEntry 2 }

frTrmt2FacilityHistorical1dayPauseFrames OBJECT-TYPE
    SYNTAX        Counter64String
    MAX-ACCESS    read-only
    STATUS        current
    DESCRIPTION   "Pause Frames Transmitted"
    ::= { frTrmt2FacilityHistorical1dayEntry 3 }

frTrmt2FacilityHistorical1dayBytes OBJECT-TYPE
    SYNTAX        Counter64String
    MAX-ACCESS    read-only
    STATUS        current
    DESCRIPTION   "Bytes Transmitted"
    ::= { frTrmt2FacilityHistorical1dayEntry 4 }

frTrmt2FacilityHistorical1dayCrcFramesEgress OBJECT-TYPE
    SYNTAX        Counter64String
    MAX-ACCESS    read-only
    STATUS        current
    DESCRIPTION   "Egress CRC Errored Frames"
    ::= { frTrmt2FacilityHistorical1dayEntry 5 }

frTrmt2FacilityHistorical1dayDiscardedFrames OBJECT-TYPE
    SYNTAX        Counter64String
    MAX-ACCESS    read-only
    STATUS        current
    DESCRIPTION   "Transmit Frames Discarded"
    ::= { frTrmt2FacilityHistorical1dayEntry 6 }

frTrmt2FacilityHistorical1dayValidFlag OBJECT-TYPE
    SYNTAX        TruthValue
    MAX-ACCESS    read-only
    STATUS        current
    DESCRIPTION   "Valid Flag"
    ::= { frTrmt2FacilityHistorical1dayEntry 7 }

frTrmt2FacilityHistorical1dayTimeStamp OBJECT-TYPE
    SYNTAX        DateAndTime
    MAX-ACCESS    read-only
    STATUS        current
    DESCRIPTION   "Timestamp"
    ::= { frTrmt2FacilityHistorical1dayEntry 8 }

endOfFrTrmt2FacilityHistorical1dayTable OBJECT-TYPE
    SYNTAX        Integer32
    MAX-ACCESS    read-only
    STATUS        current
    DESCRIPTION   ""
    ::= { pmFacilityDataRecord 216 }

frRcv4FacilityCurrent15minTable OBJECT-TYPE
    SYNTAX        SEQUENCE OF FrRcv4FacilityCurrent15minEntry
    MAX-ACCESS    not-accessible
    STATUS        current
    DESCRIPTION   ""
    ::= { pmFacilityDataRecord 217 }

frRcv4FacilityCurrent15minEntry OBJECT-TYPE
    SYNTAX        FrRcv4FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv4FacilityCurrent15minTable 1 }

FrRcv4FacilityCurrent15minEntry ::= SEQUENCE
  {    frRcv4FacilityCurrent15minGoodFrames Counter64String,
    frRcv4FacilityCurrent15minCrcFrames Counter64String,
    frRcv4FacilityCurrent15minBytes Counter64String,
    frRcv4FacilityCurrent15minElapsedTime Integer32 }

frRcv4FacilityCurrent15minGoodFrames OBJECT-TYPE
    SYNTAX        Counter64String
    MAX-ACCESS    read-only
    STATUS        current
    DESCRIPTION   "Frames Received"
    ::= { frRcv4FacilityCurrent15minEntry 1 }

frRcv4FacilityCurrent15minCrcFrames OBJECT-TYPE
    SYNTAX        Counter64String
    MAX-ACCESS    read-only
    STATUS        current
    DESCRIPTION   "Received CRC Errors"
    ::= { frRcv4FacilityCurrent15minEntry 2 }

frRcv4FacilityCurrent15minBytes OBJECT-TYPE
    SYNTAX        Counter64String
    MAX-ACCESS    read-only
    STATUS        current
    DESCRIPTION   "Bytes Received"
    ::= { frRcv4FacilityCurrent15minEntry 3 }

frRcv4FacilityCurrent15minElapsedTime OBJECT-TYPE
    SYNTAX        Integer32 (0..9000)
    MAX-ACCESS    read-only
    STATUS        current
    DESCRIPTION   "Elapsed 15Min"
    ::= { frRcv4FacilityCurrent15minEntry 4 }

endOfFrRcv4FacilityCurrent15minTable OBJECT-TYPE
    SYNTAX        Integer32
    MAX-ACCESS    read-only
    STATUS        current
    DESCRIPTION   ""
    ::= { pmFacilityDataRecord 218 }

frRcv4FacilityCurrent1dayTable OBJECT-TYPE
    SYNTAX        SEQUENCE OF FrRcv4FacilityCurrent1dayEntry
    MAX-ACCESS    not-accessible
    STATUS        current
    DESCRIPTION   ""
    ::= { pmFacilityDataRecord 219 }

frRcv4FacilityCurrent1dayEntry OBJECT-TYPE
    SYNTAX        FrRcv4FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { frRcv4FacilityCurrent1dayTable 1 }

FrRcv4FacilityCurrent1dayEntry ::= SEQUENCE
  {    frRcv4FacilityCurrent1dayGoodFrames Counter64String,
    frRcv4FacilityCurrent1dayCrcFrames Counter64String,
    frRcv4FacilityCurrent1dayBytes Counter64String,
    frRcv4FacilityCurrent1dayElapsedTime Integer32 }

frRcv4FacilityCurrent1dayGoodFrames OBJECT-TYPE
    SYNTAX        Counter64String
    MAX-ACCESS    read-only
    STATUS        current
    DESCRIPTION   "Frames Received"
    ::= { frRcv4FacilityCurrent1dayEntry 1 }

frRcv4FacilityCurrent1dayCrcFrames OBJECT-TYPE
    SYNTAX        Counter64String
    MAX-ACCESS    read-only
    STATUS        current
    DESCRIPTION   "Received CRC Errors"
    ::= { frRcv4FacilityCurrent1dayEntry 2 }

frRcv4FacilityCurrent1dayBytes OBJECT-TYPE
    SYNTAX        Counter64String
    MAX-ACCESS    read-only
    STATUS        current
    DESCRIPTION   "Bytes Received"
    ::= { frRcv4FacilityCurrent1dayEntry 3 }

frRcv4FacilityCurrent1dayElapsedTime OBJECT-TYPE
    SYNTAX        Integer32 (0..86400)
    MAX-ACCESS    read-only
    STATUS        current
    DESCRIPTION   "Elapsed 1Day"
    ::= { frRcv4FacilityCurrent1dayEntry 4 }

endOfFrRcv4FacilityCurrent1dayTable OBJECT-TYPE
    SYNTAX        Integer32
    MAX-ACCESS    read-only
    STATUS        current
    DESCRIPTION   ""
    ::= { pmFacilityDataRecord 220 }

frRcv4FacilityHistorical15minTable OBJECT-TYPE
    SYNTAX        SEQUENCE OF FrRcv4FacilityHistorical15minEntry
    MAX-ACCESS    not-accessible
    STATUS        current
    DESCRIPTION   ""
    ::= { pmFacilityDataRecord 221 }

frRcv4FacilityHistorical15minEntry OBJECT-TYPE
    SYNTAX        FrRcv4FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv4FacilityHistorical15minNumber
                }
    ::= { frRcv4FacilityHistorical15minTable 1 }

FrRcv4FacilityHistorical15minEntry ::= SEQUENCE
  {    frRcv4FacilityHistorical15minNumber Integer32,
    frRcv4FacilityHistorical15minGoodFrames Counter64String,
    frRcv4FacilityHistorical15minCrcFrames Counter64String,
    frRcv4FacilityHistorical15minBytes Counter64String,
    frRcv4FacilityHistorical15minValidFlag TruthValue,
    frRcv4FacilityHistorical15minTimeStamp DateAndTime }

frRcv4FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frRcv4FacilityHistorical15minEntry 1 }

frRcv4FacilityHistorical15minGoodFrames OBJECT-TYPE
    SYNTAX        Counter64String
    MAX-ACCESS    read-only
    STATUS        current
    DESCRIPTION   "Frames Received"
    ::= { frRcv4FacilityHistorical15minEntry 2 }

frRcv4FacilityHistorical15minCrcFrames OBJECT-TYPE
    SYNTAX        Counter64String
    MAX-ACCESS    read-only
    STATUS        current
    DESCRIPTION   "Received CRC Errors"
    ::= { frRcv4FacilityHistorical15minEntry 3 }

frRcv4FacilityHistorical15minBytes OBJECT-TYPE
    SYNTAX        Counter64String
    MAX-ACCESS    read-only
    STATUS        current
    DESCRIPTION   "Bytes Received"
    ::= { frRcv4FacilityHistorical15minEntry 4 }

frRcv4FacilityHistorical15minValidFlag OBJECT-TYPE
    SYNTAX        TruthValue
    MAX-ACCESS    read-only
    STATUS        current
    DESCRIPTION   "Valid Flag"
    ::= { frRcv4FacilityHistorical15minEntry 5 }

frRcv4FacilityHistorical15minTimeStamp OBJECT-TYPE
    SYNTAX        DateAndTime
    MAX-ACCESS    read-only
    STATUS        current
    DESCRIPTION   "Timestamp"
    ::= { frRcv4FacilityHistorical15minEntry 6 }

endOfFrRcv4FacilityHistorical15minTable OBJECT-TYPE
    SYNTAX        Integer32
    MAX-ACCESS    read-only
    STATUS        current
    DESCRIPTION   ""
    ::= { pmFacilityDataRecord 222 }

frRcv4FacilityHistorical1dayTable OBJECT-TYPE
    SYNTAX        SEQUENCE OF FrRcv4FacilityHistorical1dayEntry
    MAX-ACCESS    not-accessible
    STATUS        current
    DESCRIPTION   ""
    ::= { pmFacilityDataRecord 223 }

frRcv4FacilityHistorical1dayEntry OBJECT-TYPE
    SYNTAX        FrRcv4FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  frRcv4FacilityHistorical1dayNumber
                }
    ::= { frRcv4FacilityHistorical1dayTable 1 }

FrRcv4FacilityHistorical1dayEntry ::= SEQUENCE
  {    frRcv4FacilityHistorical1dayNumber Integer32,
    frRcv4FacilityHistorical1dayGoodFrames Counter64String,
    frRcv4FacilityHistorical1dayCrcFrames Counter64String,
    frRcv4FacilityHistorical1dayBytes Counter64String,
    frRcv4FacilityHistorical1dayValidFlag TruthValue,
    frRcv4FacilityHistorical1dayTimeStamp DateAndTime }

frRcv4FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frRcv4FacilityHistorical1dayEntry 1 }

frRcv4FacilityHistorical1dayGoodFrames OBJECT-TYPE
    SYNTAX        Counter64String
    MAX-ACCESS    read-only
    STATUS        current
    DESCRIPTION   "Frames Received"
    ::= { frRcv4FacilityHistorical1dayEntry 2 }

frRcv4FacilityHistorical1dayCrcFrames OBJECT-TYPE
    SYNTAX        Counter64String
    MAX-ACCESS    read-only
    STATUS        current
    DESCRIPTION   "Received CRC Errors"
    ::= { frRcv4FacilityHistorical1dayEntry 3 }

frRcv4FacilityHistorical1dayBytes OBJECT-TYPE
    SYNTAX        Counter64String
    MAX-ACCESS    read-only
    STATUS        current
    DESCRIPTION   "Bytes Received"
    ::= { frRcv4FacilityHistorical1dayEntry 4 }

frRcv4FacilityHistorical1dayValidFlag OBJECT-TYPE
    SYNTAX        TruthValue
    MAX-ACCESS    read-only
    STATUS        current
    DESCRIPTION   "Valid Flag"
    ::= { frRcv4FacilityHistorical1dayEntry 5 }

frRcv4FacilityHistorical1dayTimeStamp OBJECT-TYPE
    SYNTAX        DateAndTime
    MAX-ACCESS    read-only
    STATUS        current
    DESCRIPTION   "Timestamp"
    ::= { frRcv4FacilityHistorical1dayEntry 6 }

endOfFrRcv4FacilityHistorical1dayTable OBJECT-TYPE
    SYNTAX        Integer32
    MAX-ACCESS    read-only
    STATUS        current
    DESCRIPTION   ""
    ::= { pmFacilityDataRecord 224 }

byteTrmtFacilityCurrent15minTable OBJECT-TYPE
    SYNTAX        SEQUENCE OF ByteTrmtFacilityCurrent15minEntry
    MAX-ACCESS    not-accessible
    STATUS        current
    DESCRIPTION   ""
    ::= { pmFacilityDataRecord 225 }

byteTrmtFacilityCurrent15minEntry OBJECT-TYPE
    SYNTAX        ByteTrmtFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { byteTrmtFacilityCurrent15minTable 1 }

ByteTrmtFacilityCurrent15minEntry ::= SEQUENCE
  {    byteTrmtFacilityCurrent15minFramesTrmt Counter64String,
    byteTrmtFacilityCurrent15minBytesTrmt Counter64String,
    byteTrmtFacilityCurrent15minCrcFramesEgress Counter64String,
    byteTrmtFacilityCurrent15minElapsedTime Integer32 }

byteTrmtFacilityCurrent15minFramesTrmt OBJECT-TYPE
    SYNTAX        Counter64String
    MAX-ACCESS    read-only
    STATUS        current
    DESCRIPTION   "Frames Transmitted"
    ::= { byteTrmtFacilityCurrent15minEntry 1 }

byteTrmtFacilityCurrent15minBytesTrmt OBJECT-TYPE
    SYNTAX        Counter64String
    MAX-ACCESS    read-only
    STATUS        current
    DESCRIPTION   "Bytes Transmitted"
    ::= { byteTrmtFacilityCurrent15minEntry 2 }

byteTrmtFacilityCurrent15minCrcFramesEgress OBJECT-TYPE
    SYNTAX        Counter64String
    MAX-ACCESS    read-only
    STATUS        current
    DESCRIPTION   "Egress CRC Errored Frames"
    ::= { byteTrmtFacilityCurrent15minEntry 3 }

byteTrmtFacilityCurrent15minElapsedTime OBJECT-TYPE
    SYNTAX        Integer32 (0..9000)
    MAX-ACCESS    read-only
    STATUS        current
    DESCRIPTION   "Elapsed 15Min"
    ::= { byteTrmtFacilityCurrent15minEntry 4 }

endOfByteTrmtFacilityCurrent15minTable OBJECT-TYPE
    SYNTAX        Integer32
    MAX-ACCESS    read-only
    STATUS        current
    DESCRIPTION   ""
    ::= { pmFacilityDataRecord 226 }

byteTrmtFacilityCurrent1dayTable OBJECT-TYPE
    SYNTAX        SEQUENCE OF ByteTrmtFacilityCurrent1dayEntry
    MAX-ACCESS    not-accessible
    STATUS        current
    DESCRIPTION   ""
    ::= { pmFacilityDataRecord 227 }

byteTrmtFacilityCurrent1dayEntry OBJECT-TYPE
    SYNTAX        ByteTrmtFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { byteTrmtFacilityCurrent1dayTable 1 }

ByteTrmtFacilityCurrent1dayEntry ::= SEQUENCE
  {    byteTrmtFacilityCurrent1dayFramesTrmt Counter64String,
    byteTrmtFacilityCurrent1dayBytesTrmt Counter64String,
    byteTrmtFacilityCurrent1dayCrcFramesEgress Counter64String,
    byteTrmtFacilityCurrent1dayElapsedTime Integer32 }

byteTrmtFacilityCurrent1dayFramesTrmt OBJECT-TYPE
    SYNTAX        Counter64String
    MAX-ACCESS    read-only
    STATUS        current
    DESCRIPTION   "Frames Transmitted"
    ::= { byteTrmtFacilityCurrent1dayEntry 1 }

byteTrmtFacilityCurrent1dayBytesTrmt OBJECT-TYPE
    SYNTAX        Counter64String
    MAX-ACCESS    read-only
    STATUS        current
    DESCRIPTION   "Bytes Transmitted"
    ::= { byteTrmtFacilityCurrent1dayEntry 2 }

byteTrmtFacilityCurrent1dayCrcFramesEgress OBJECT-TYPE
    SYNTAX        Counter64String
    MAX-ACCESS    read-only
    STATUS        current
    DESCRIPTION   "Egress CRC Errored Frames"
    ::= { byteTrmtFacilityCurrent1dayEntry 3 }

byteTrmtFacilityCurrent1dayElapsedTime OBJECT-TYPE
    SYNTAX        Integer32 (0..86400)
    MAX-ACCESS    read-only
    STATUS        current
    DESCRIPTION   "Elapsed 1Day"
    ::= { byteTrmtFacilityCurrent1dayEntry 4 }

endOfByteTrmtFacilityCurrent1dayTable OBJECT-TYPE
    SYNTAX        Integer32
    MAX-ACCESS    read-only
    STATUS        current
    DESCRIPTION   ""
    ::= { pmFacilityDataRecord 228 }

byteTrmtFacilityHistorical15minTable OBJECT-TYPE
    SYNTAX        SEQUENCE OF ByteTrmtFacilityHistorical15minEntry
    MAX-ACCESS    not-accessible
    STATUS        current
    DESCRIPTION   ""
    ::= { pmFacilityDataRecord 229 }

byteTrmtFacilityHistorical15minEntry OBJECT-TYPE
    SYNTAX        ByteTrmtFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  byteTrmtFacilityHistorical15minNumber
                }
    ::= { byteTrmtFacilityHistorical15minTable 1 }

ByteTrmtFacilityHistorical15minEntry ::= SEQUENCE
  {    byteTrmtFacilityHistorical15minNumber Integer32,
    byteTrmtFacilityHistorical15minFramesTrmt Counter64String,
    byteTrmtFacilityHistorical15minBytesTrmt Counter64String,
    byteTrmtFacilityHistorical15minCrcFramesEgress Counter64String,
    byteTrmtFacilityHistorical15minValidFlag TruthValue,
    byteTrmtFacilityHistorical15minTimeStamp DateAndTime }

byteTrmtFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { byteTrmtFacilityHistorical15minEntry 1 }

byteTrmtFacilityHistorical15minFramesTrmt OBJECT-TYPE
    SYNTAX        Counter64String
    MAX-ACCESS    read-only
    STATUS        current
    DESCRIPTION   "Frames Transmitted"
    ::= { byteTrmtFacilityHistorical15minEntry 2 }

byteTrmtFacilityHistorical15minBytesTrmt OBJECT-TYPE
    SYNTAX        Counter64String
    MAX-ACCESS    read-only
    STATUS        current
    DESCRIPTION   "Bytes Transmitted"
    ::= { byteTrmtFacilityHistorical15minEntry 3 }

byteTrmtFacilityHistorical15minCrcFramesEgress OBJECT-TYPE
    SYNTAX        Counter64String
    MAX-ACCESS    read-only
    STATUS        current
    DESCRIPTION   "Egress CRC Errored Frames"
    ::= { byteTrmtFacilityHistorical15minEntry 4 }

byteTrmtFacilityHistorical15minValidFlag OBJECT-TYPE
    SYNTAX        TruthValue
    MAX-ACCESS    read-only
    STATUS        current
    DESCRIPTION   "Valid Flag"
    ::= { byteTrmtFacilityHistorical15minEntry 5 }

byteTrmtFacilityHistorical15minTimeStamp OBJECT-TYPE
    SYNTAX        DateAndTime
    MAX-ACCESS    read-only
    STATUS        current
    DESCRIPTION   "Timestamp"
    ::= { byteTrmtFacilityHistorical15minEntry 6 }

endOfByteTrmtFacilityHistorical15minTable OBJECT-TYPE
    SYNTAX        Integer32
    MAX-ACCESS    read-only
    STATUS        current
    DESCRIPTION   ""
    ::= { pmFacilityDataRecord 230 }

byteTrmtFacilityHistorical1dayTable OBJECT-TYPE
    SYNTAX        SEQUENCE OF ByteTrmtFacilityHistorical1dayEntry
    MAX-ACCESS    not-accessible
    STATUS        current
    DESCRIPTION   ""
    ::= { pmFacilityDataRecord 231 }

byteTrmtFacilityHistorical1dayEntry OBJECT-TYPE
    SYNTAX        ByteTrmtFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  byteTrmtFacilityHistorical1dayNumber
                }
    ::= { byteTrmtFacilityHistorical1dayTable 1 }

ByteTrmtFacilityHistorical1dayEntry ::= SEQUENCE
  {    byteTrmtFacilityHistorical1dayNumber Integer32,
    byteTrmtFacilityHistorical1dayFramesTrmt Counter64String,
    byteTrmtFacilityHistorical1dayBytesTrmt Counter64String,
    byteTrmtFacilityHistorical1dayCrcFramesEgress Counter64String,
    byteTrmtFacilityHistorical1dayValidFlag TruthValue,
    byteTrmtFacilityHistorical1dayTimeStamp DateAndTime }

byteTrmtFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { byteTrmtFacilityHistorical1dayEntry 1 }

byteTrmtFacilityHistorical1dayFramesTrmt OBJECT-TYPE
    SYNTAX        Counter64String
    MAX-ACCESS    read-only
    STATUS        current
    DESCRIPTION   "Frames Transmitted"
    ::= { byteTrmtFacilityHistorical1dayEntry 2 }

byteTrmtFacilityHistorical1dayBytesTrmt OBJECT-TYPE
    SYNTAX        Counter64String
    MAX-ACCESS    read-only
    STATUS        current
    DESCRIPTION   "Bytes Transmitted"
    ::= { byteTrmtFacilityHistorical1dayEntry 3 }

byteTrmtFacilityHistorical1dayCrcFramesEgress OBJECT-TYPE
    SYNTAX        Counter64String
    MAX-ACCESS    read-only
    STATUS        current
    DESCRIPTION   "Egress CRC Errored Frames"
    ::= { byteTrmtFacilityHistorical1dayEntry 4 }

byteTrmtFacilityHistorical1dayValidFlag OBJECT-TYPE
    SYNTAX        TruthValue
    MAX-ACCESS    read-only
    STATUS        current
    DESCRIPTION   "Valid Flag"
    ::= { byteTrmtFacilityHistorical1dayEntry 5 }

byteTrmtFacilityHistorical1dayTimeStamp OBJECT-TYPE
    SYNTAX        DateAndTime
    MAX-ACCESS    read-only
    STATUS        current
    DESCRIPTION   "Timestamp"
    ::= { byteTrmtFacilityHistorical1dayEntry 6 }

endOfByteTrmtFacilityHistorical1dayTable OBJECT-TYPE
    SYNTAX        Integer32
    MAX-ACCESS    read-only
    STATUS        current
    DESCRIPTION   ""
    ::= { pmFacilityDataRecord 232 }

utlRxFacilityCurrent15minTable OBJECT-TYPE
    SYNTAX        SEQUENCE OF UtlRxFacilityCurrent15minEntry
    MAX-ACCESS    not-accessible
    STATUS        current
    DESCRIPTION   ""
    ::= { pmFacilityDataRecord 233 }

utlRxFacilityCurrent15minEntry OBJECT-TYPE
    SYNTAX        UtlRxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { utlRxFacilityCurrent15minTable 1 }

UtlRxFacilityCurrent15minEntry ::= SEQUENCE
  {    utlRxFacilityCurrent15minUtlHigh Unsigned32,
    utlRxFacilityCurrent15minUtlLow Unsigned32,
    utlRxFacilityCurrent15minUtlMean Unsigned32,
    utlRxFacilityCurrent15minElapsedTime Integer32 }

utlRxFacilityCurrent15minUtlHigh OBJECT-TYPE
    SYNTAX        Unsigned32
    UNITS         "%"
    MAX-ACCESS    read-only
    STATUS        current
    DESCRIPTION   "Utilization Recieve High"
    ::= { utlRxFacilityCurrent15minEntry 1 }

utlRxFacilityCurrent15minUtlLow OBJECT-TYPE
    SYNTAX        Unsigned32
    UNITS         "%"
    MAX-ACCESS    read-only
    STATUS        current
    DESCRIPTION   "Utilization Receive Low"
    ::= { utlRxFacilityCurrent15minEntry 2 }

utlRxFacilityCurrent15minUtlMean OBJECT-TYPE
    SYNTAX        Unsigned32
    UNITS         "%"
    MAX-ACCESS    read-only
    STATUS        current
    DESCRIPTION   "Utilization Receive Mean"
    ::= { utlRxFacilityCurrent15minEntry 3 }

utlRxFacilityCurrent15minElapsedTime OBJECT-TYPE
    SYNTAX        Integer32 (0..9000)
    MAX-ACCESS    read-only
    STATUS        current
    DESCRIPTION   "Elapsed 15Min"
    ::= { utlRxFacilityCurrent15minEntry 4 }

endOfUtlRxFacilityCurrent15minTable OBJECT-TYPE
    SYNTAX        Integer32
    MAX-ACCESS    read-only
    STATUS        current
    DESCRIPTION   ""
    ::= { pmFacilityDataRecord 234 }

utlRxFacilityCurrent1dayTable OBJECT-TYPE
    SYNTAX        SEQUENCE OF UtlRxFacilityCurrent1dayEntry
    MAX-ACCESS    not-accessible
    STATUS        current
    DESCRIPTION   ""
    ::= { pmFacilityDataRecord 235 }

utlRxFacilityCurrent1dayEntry OBJECT-TYPE
    SYNTAX        UtlRxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { utlRxFacilityCurrent1dayTable 1 }

UtlRxFacilityCurrent1dayEntry ::= SEQUENCE
  {    utlRxFacilityCurrent1dayUtlHigh Unsigned32,
    utlRxFacilityCurrent1dayUtlLow Unsigned32,
    utlRxFacilityCurrent1dayUtlMean Unsigned32,
    utlRxFacilityCurrent1dayElapsedTime Integer32 }

utlRxFacilityCurrent1dayUtlHigh OBJECT-TYPE
    SYNTAX        Unsigned32
    UNITS         "%"
    MAX-ACCESS    read-only
    STATUS        current
    DESCRIPTION   "Utilization Recieve High"
    ::= { utlRxFacilityCurrent1dayEntry 1 }

utlRxFacilityCurrent1dayUtlLow OBJECT-TYPE
    SYNTAX        Unsigned32
    UNITS         "%"
    MAX-ACCESS    read-only
    STATUS        current
    DESCRIPTION   "Utilization Receive Low"
    ::= { utlRxFacilityCurrent1dayEntry 2 }

utlRxFacilityCurrent1dayUtlMean OBJECT-TYPE
    SYNTAX        Unsigned32
    UNITS         "%"
    MAX-ACCESS    read-only
    STATUS        current
    DESCRIPTION   "Utilization Receive Mean"
    ::= { utlRxFacilityCurrent1dayEntry 3 }

utlRxFacilityCurrent1dayElapsedTime OBJECT-TYPE
    SYNTAX        Integer32 (0..86400)
    MAX-ACCESS    read-only
    STATUS        current
    DESCRIPTION   "Elapsed 1Day"
    ::= { utlRxFacilityCurrent1dayEntry 4 }

endOfUtlRxFacilityCurrent1dayTable OBJECT-TYPE
    SYNTAX        Integer32
    MAX-ACCESS    read-only
    STATUS        current
    DESCRIPTION   ""
    ::= { pmFacilityDataRecord 236 }

utlRxFacilityHistorical15minTable OBJECT-TYPE
    SYNTAX        SEQUENCE OF UtlRxFacilityHistorical15minEntry
    MAX-ACCESS    not-accessible
    STATUS        current
    DESCRIPTION   ""
    ::= { pmFacilityDataRecord 237 }

utlRxFacilityHistorical15minEntry OBJECT-TYPE
    SYNTAX        UtlRxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  utlRxFacilityHistorical15minNumber
                }
    ::= { utlRxFacilityHistorical15minTable 1 }

UtlRxFacilityHistorical15minEntry ::= SEQUENCE
  {    utlRxFacilityHistorical15minNumber Integer32,
    utlRxFacilityHistorical15minUtlHigh Unsigned32,
    utlRxFacilityHistorical15minUtlLow Unsigned32,
    utlRxFacilityHistorical15minUtlMean Unsigned32,
    utlRxFacilityHistorical15minValidFlag TruthValue,
    utlRxFacilityHistorical15minTimeStamp DateAndTime }

utlRxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { utlRxFacilityHistorical15minEntry 1 }

utlRxFacilityHistorical15minUtlHigh OBJECT-TYPE
    SYNTAX        Unsigned32
    UNITS         "%"
    MAX-ACCESS    read-only
    STATUS        current
    DESCRIPTION   "Utilization Recieve High"
    ::= { utlRxFacilityHistorical15minEntry 2 }

utlRxFacilityHistorical15minUtlLow OBJECT-TYPE
    SYNTAX        Unsigned32
    UNITS         "%"
    MAX-ACCESS    read-only
    STATUS        current
    DESCRIPTION   "Utilization Receive Low"
    ::= { utlRxFacilityHistorical15minEntry 3 }

utlRxFacilityHistorical15minUtlMean OBJECT-TYPE
    SYNTAX        Unsigned32
    UNITS         "%"
    MAX-ACCESS    read-only
    STATUS        current
    DESCRIPTION   "Utilization Receive Mean"
    ::= { utlRxFacilityHistorical15minEntry 4 }

utlRxFacilityHistorical15minValidFlag OBJECT-TYPE
    SYNTAX        TruthValue
    MAX-ACCESS    read-only
    STATUS        current
    DESCRIPTION   "Valid Flag"
    ::= { utlRxFacilityHistorical15minEntry 5 }

utlRxFacilityHistorical15minTimeStamp OBJECT-TYPE
    SYNTAX        DateAndTime
    MAX-ACCESS    read-only
    STATUS        current
    DESCRIPTION   "Timestamp"
    ::= { utlRxFacilityHistorical15minEntry 6 }

endOfUtlRxFacilityHistorical15minTable OBJECT-TYPE
    SYNTAX        Integer32
    MAX-ACCESS    read-only
    STATUS        current
    DESCRIPTION   ""
    ::= { pmFacilityDataRecord 238 }

utlRxFacilityHistorical1dayTable OBJECT-TYPE
    SYNTAX        SEQUENCE OF UtlRxFacilityHistorical1dayEntry
    MAX-ACCESS    not-accessible
    STATUS        current
    DESCRIPTION   ""
    ::= { pmFacilityDataRecord 239 }

utlRxFacilityHistorical1dayEntry OBJECT-TYPE
    SYNTAX        UtlRxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  utlRxFacilityHistorical1dayNumber
                }
    ::= { utlRxFacilityHistorical1dayTable 1 }

UtlRxFacilityHistorical1dayEntry ::= SEQUENCE
  {    utlRxFacilityHistorical1dayNumber Integer32,
    utlRxFacilityHistorical1dayUtlHigh Unsigned32,
    utlRxFacilityHistorical1dayUtlLow Unsigned32,
    utlRxFacilityHistorical1dayUtlMean Unsigned32,
    utlRxFacilityHistorical1dayValidFlag TruthValue,
    utlRxFacilityHistorical1dayTimeStamp DateAndTime }

utlRxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { utlRxFacilityHistorical1dayEntry 1 }

utlRxFacilityHistorical1dayUtlHigh OBJECT-TYPE
    SYNTAX        Unsigned32
    UNITS         "%"
    MAX-ACCESS    read-only
    STATUS        current
    DESCRIPTION   "Utilization Recieve High"
    ::= { utlRxFacilityHistorical1dayEntry 2 }

utlRxFacilityHistorical1dayUtlLow OBJECT-TYPE
    SYNTAX        Unsigned32
    UNITS         "%"
    MAX-ACCESS    read-only
    STATUS        current
    DESCRIPTION   "Utilization Receive Low"
    ::= { utlRxFacilityHistorical1dayEntry 3 }

utlRxFacilityHistorical1dayUtlMean OBJECT-TYPE
    SYNTAX        Unsigned32
    UNITS         "%"
    MAX-ACCESS    read-only
    STATUS        current
    DESCRIPTION   "Utilization Receive Mean"
    ::= { utlRxFacilityHistorical1dayEntry 4 }

utlRxFacilityHistorical1dayValidFlag OBJECT-TYPE
    SYNTAX        TruthValue
    MAX-ACCESS    read-only
    STATUS        current
    DESCRIPTION   "Valid Flag"
    ::= { utlRxFacilityHistorical1dayEntry 5 }

utlRxFacilityHistorical1dayTimeStamp OBJECT-TYPE
    SYNTAX        DateAndTime
    MAX-ACCESS    read-only
    STATUS        current
    DESCRIPTION   "Timestamp"
    ::= { utlRxFacilityHistorical1dayEntry 6 }

endOfUtlRxFacilityHistorical1dayTable OBJECT-TYPE
    SYNTAX        Integer32
    MAX-ACCESS    read-only
    STATUS        current
    DESCRIPTION   ""
    ::= { pmFacilityDataRecord 240 }

utlTxFacilityCurrent15minTable OBJECT-TYPE
    SYNTAX        SEQUENCE OF UtlTxFacilityCurrent15minEntry
    MAX-ACCESS    not-accessible
    STATUS        current
    DESCRIPTION   ""
    ::= { pmFacilityDataRecord 241 }

utlTxFacilityCurrent15minEntry OBJECT-TYPE
    SYNTAX        UtlTxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { utlTxFacilityCurrent15minTable 1 }

UtlTxFacilityCurrent15minEntry ::= SEQUENCE
  {    utlTxFacilityCurrent15minUtlHigh Unsigned32,
    utlTxFacilityCurrent15minUtlLow Unsigned32,
    utlTxFacilityCurrent15minUtlMean Unsigned32,
    utlTxFacilityCurrent15minElapsedTime Integer32 }

utlTxFacilityCurrent15minUtlHigh OBJECT-TYPE
    SYNTAX        Unsigned32
    UNITS         "%"
    MAX-ACCESS    read-only
    STATUS        current
    DESCRIPTION   "Utilization Transmit High"
    ::= { utlTxFacilityCurrent15minEntry 1 }

utlTxFacilityCurrent15minUtlLow OBJECT-TYPE
    SYNTAX        Unsigned32
    UNITS         "%"
    MAX-ACCESS    read-only
    STATUS        current
    DESCRIPTION   "Utilization Transmit Low"
    ::= { utlTxFacilityCurrent15minEntry 2 }

utlTxFacilityCurrent15minUtlMean OBJECT-TYPE
    SYNTAX        Unsigned32
    UNITS         "%"
    MAX-ACCESS    read-only
    STATUS        current
    DESCRIPTION   "Utilization Transmit Mean"
    ::= { utlTxFacilityCurrent15minEntry 3 }

utlTxFacilityCurrent15minElapsedTime OBJECT-TYPE
    SYNTAX        Integer32 (0..9000)
    MAX-ACCESS    read-only
    STATUS        current
    DESCRIPTION   "Elapsed 15Min"
    ::= { utlTxFacilityCurrent15minEntry 4 }

endOfUtlTxFacilityCurrent15minTable OBJECT-TYPE
    SYNTAX        Integer32
    MAX-ACCESS    read-only
    STATUS        current
    DESCRIPTION   ""
    ::= { pmFacilityDataRecord 242 }

utlTxFacilityCurrent1dayTable OBJECT-TYPE
    SYNTAX        SEQUENCE OF UtlTxFacilityCurrent1dayEntry
    MAX-ACCESS    not-accessible
    STATUS        current
    DESCRIPTION   ""
    ::= { pmFacilityDataRecord 243 }

utlTxFacilityCurrent1dayEntry OBJECT-TYPE
    SYNTAX        UtlTxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { utlTxFacilityCurrent1dayTable 1 }

UtlTxFacilityCurrent1dayEntry ::= SEQUENCE
  {    utlTxFacilityCurrent1dayUtlHigh Unsigned32,
    utlTxFacilityCurrent1dayUtlLow Unsigned32,
    utlTxFacilityCurrent1dayUtlMean Unsigned32,
    utlTxFacilityCurrent1dayElapsedTime Integer32 }

utlTxFacilityCurrent1dayUtlHigh OBJECT-TYPE
    SYNTAX        Unsigned32
    UNITS         "%"
    MAX-ACCESS    read-only
    STATUS        current
    DESCRIPTION   "Utilization Transmit High"
    ::= { utlTxFacilityCurrent1dayEntry 1 }

utlTxFacilityCurrent1dayUtlLow OBJECT-TYPE
    SYNTAX        Unsigned32
    UNITS         "%"
    MAX-ACCESS    read-only
    STATUS        current
    DESCRIPTION   "Utilization Transmit Low"
    ::= { utlTxFacilityCurrent1dayEntry 2 }

utlTxFacilityCurrent1dayUtlMean OBJECT-TYPE
    SYNTAX        Unsigned32
    UNITS         "%"
    MAX-ACCESS    read-only
    STATUS        current
    DESCRIPTION   "Utilization Transmit Mean"
    ::= { utlTxFacilityCurrent1dayEntry 3 }

utlTxFacilityCurrent1dayElapsedTime OBJECT-TYPE
    SYNTAX        Integer32 (0..86400)
    MAX-ACCESS    read-only
    STATUS        current
    DESCRIPTION   "Elapsed 1Day"
    ::= { utlTxFacilityCurrent1dayEntry 4 }

endOfUtlTxFacilityCurrent1dayTable OBJECT-TYPE
    SYNTAX        Integer32
    MAX-ACCESS    read-only
    STATUS        current
    DESCRIPTION   ""
    ::= { pmFacilityDataRecord 244 }

utlTxFacilityHistorical15minTable OBJECT-TYPE
    SYNTAX        SEQUENCE OF UtlTxFacilityHistorical15minEntry
    MAX-ACCESS    not-accessible
    STATUS        current
    DESCRIPTION   ""
    ::= { pmFacilityDataRecord 245 }

utlTxFacilityHistorical15minEntry OBJECT-TYPE
    SYNTAX        UtlTxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  utlTxFacilityHistorical15minNumber
                }
    ::= { utlTxFacilityHistorical15minTable 1 }

UtlTxFacilityHistorical15minEntry ::= SEQUENCE
  {    utlTxFacilityHistorical15minNumber Integer32,
    utlTxFacilityHistorical15minUtlHigh Unsigned32,
    utlTxFacilityHistorical15minUtlLow Unsigned32,
    utlTxFacilityHistorical15minUtlMean Unsigned32,
    utlTxFacilityHistorical15minValidFlag TruthValue,
    utlTxFacilityHistorical15minTimeStamp DateAndTime }

utlTxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { utlTxFacilityHistorical15minEntry 1 }

utlTxFacilityHistorical15minUtlHigh OBJECT-TYPE
    SYNTAX        Unsigned32
    UNITS         "%"
    MAX-ACCESS    read-only
    STATUS        current
    DESCRIPTION   "Utilization Transmit High"
    ::= { utlTxFacilityHistorical15minEntry 2 }

utlTxFacilityHistorical15minUtlLow OBJECT-TYPE
    SYNTAX        Unsigned32
    UNITS         "%"
    MAX-ACCESS    read-only
    STATUS        current
    DESCRIPTION   "Utilization Transmit Low"
    ::= { utlTxFacilityHistorical15minEntry 3 }

utlTxFacilityHistorical15minUtlMean OBJECT-TYPE
    SYNTAX        Unsigned32
    UNITS         "%"
    MAX-ACCESS    read-only
    STATUS        current
    DESCRIPTION   "Utilization Transmit Mean"
    ::= { utlTxFacilityHistorical15minEntry 4 }

utlTxFacilityHistorical15minValidFlag OBJECT-TYPE
    SYNTAX        TruthValue
    MAX-ACCESS    read-only
    STATUS        current
    DESCRIPTION   "Valid Flag"
    ::= { utlTxFacilityHistorical15minEntry 5 }

utlTxFacilityHistorical15minTimeStamp OBJECT-TYPE
    SYNTAX        DateAndTime
    MAX-ACCESS    read-only
    STATUS        current
    DESCRIPTION   "Timestamp"
    ::= { utlTxFacilityHistorical15minEntry 6 }

endOfUtlTxFacilityHistorical15minTable OBJECT-TYPE
    SYNTAX        Integer32
    MAX-ACCESS    read-only
    STATUS        current
    DESCRIPTION   ""
    ::= { pmFacilityDataRecord 246 }

utlTxFacilityHistorical1dayTable OBJECT-TYPE
    SYNTAX        SEQUENCE OF UtlTxFacilityHistorical1dayEntry
    MAX-ACCESS    not-accessible
    STATUS        current
    DESCRIPTION   ""
    ::= { pmFacilityDataRecord 247 }

utlTxFacilityHistorical1dayEntry OBJECT-TYPE
    SYNTAX        UtlTxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  utlTxFacilityHistorical1dayNumber
                }
    ::= { utlTxFacilityHistorical1dayTable 1 }

UtlTxFacilityHistorical1dayEntry ::= SEQUENCE
  {    utlTxFacilityHistorical1dayNumber Integer32,
    utlTxFacilityHistorical1dayUtlHigh Unsigned32,
    utlTxFacilityHistorical1dayUtlLow Unsigned32,
    utlTxFacilityHistorical1dayUtlMean Unsigned32,
    utlTxFacilityHistorical1dayValidFlag TruthValue,
    utlTxFacilityHistorical1dayTimeStamp DateAndTime }

utlTxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { utlTxFacilityHistorical1dayEntry 1 }

utlTxFacilityHistorical1dayUtlHigh OBJECT-TYPE
    SYNTAX        Unsigned32
    UNITS         "%"
    MAX-ACCESS    read-only
    STATUS        current
    DESCRIPTION   "Utilization Transmit High"
    ::= { utlTxFacilityHistorical1dayEntry 2 }

utlTxFacilityHistorical1dayUtlLow OBJECT-TYPE
    SYNTAX        Unsigned32
    UNITS         "%"
    MAX-ACCESS    read-only
    STATUS        current
    DESCRIPTION   "Utilization Transmit Low"
    ::= { utlTxFacilityHistorical1dayEntry 3 }

utlTxFacilityHistorical1dayUtlMean OBJECT-TYPE
    SYNTAX        Unsigned32
    UNITS         "%"
    MAX-ACCESS    read-only
    STATUS        current
    DESCRIPTION   "Utilization Transmit Mean"
    ::= { utlTxFacilityHistorical1dayEntry 4 }

utlTxFacilityHistorical1dayValidFlag OBJECT-TYPE
    SYNTAX        TruthValue
    MAX-ACCESS    read-only
    STATUS        current
    DESCRIPTION   "Valid Flag"
    ::= { utlTxFacilityHistorical1dayEntry 5 }

utlTxFacilityHistorical1dayTimeStamp OBJECT-TYPE
    SYNTAX        DateAndTime
    MAX-ACCESS    read-only
    STATUS        current
    DESCRIPTION   "Timestamp"
    ::= { utlTxFacilityHistorical1dayEntry 6 }

endOfUtlTxFacilityHistorical1dayTable OBJECT-TYPE
    SYNTAX        Integer32
    MAX-ACCESS    read-only
    STATUS        current
    DESCRIPTION   ""
    ::= { pmFacilityDataRecord 248 }

pcsRxFacilityCurrent15minTable OBJECT-TYPE
    SYNTAX        SEQUENCE OF PcsRxFacilityCurrent15minEntry
    MAX-ACCESS    not-accessible
    STATUS        current
    DESCRIPTION   ""
    ::= { pmFacilityDataRecord 249 }

pcsRxFacilityCurrent15minEntry OBJECT-TYPE
    SYNTAX        PcsRxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcsRxFacilityCurrent15minTable 1 }

PcsRxFacilityCurrent15minEntry ::= SEQUENCE
  {    pcsRxFacilityCurrent15minES Unsigned32,
    pcsRxFacilityCurrent15minCV Counter64String,
    pcsRxFacilityCurrent15minBBE Counter64String,
    pcsRxFacilityCurrent15minElapsedTime Integer32 }

pcsRxFacilityCurrent15minES OBJECT-TYPE
    SYNTAX        Unsigned32
    MAX-ACCESS    read-only
    STATUS        current
    DESCRIPTION   "Physical Coding Layer Errored Seconds"
    ::= { pcsRxFacilityCurrent15minEntry 1 }

pcsRxFacilityCurrent15minCV OBJECT-TYPE
    SYNTAX        Counter64String
    MAX-ACCESS    read-only
    STATUS        current
    DESCRIPTION   "Physical Coding Layer Coding Violations"
    ::= { pcsRxFacilityCurrent15minEntry 2 }

pcsRxFacilityCurrent15minBBE OBJECT-TYPE
    SYNTAX        Counter64String
    MAX-ACCESS    read-only
    STATUS        current
    DESCRIPTION   "PCS Background Block Errors"
    ::= { pcsRxFacilityCurrent15minEntry 3 }

pcsRxFacilityCurrent15minElapsedTime OBJECT-TYPE
    SYNTAX        Integer32 (0..9000)
    MAX-ACCESS    read-only
    STATUS        current
    DESCRIPTION   "Elapsed 15Min"
    ::= { pcsRxFacilityCurrent15minEntry 4 }

endOfPcsRxFacilityCurrent15minTable OBJECT-TYPE
    SYNTAX        Integer32
    MAX-ACCESS    read-only
    STATUS        current
    DESCRIPTION   ""
    ::= { pmFacilityDataRecord 250 }

pcsRxFacilityCurrent1dayTable OBJECT-TYPE
    SYNTAX        SEQUENCE OF PcsRxFacilityCurrent1dayEntry
    MAX-ACCESS    not-accessible
    STATUS        current
    DESCRIPTION   ""
    ::= { pmFacilityDataRecord 251 }

pcsRxFacilityCurrent1dayEntry OBJECT-TYPE
    SYNTAX        PcsRxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcsRxFacilityCurrent1dayTable 1 }

PcsRxFacilityCurrent1dayEntry ::= SEQUENCE
  {    pcsRxFacilityCurrent1dayES Unsigned32,
    pcsRxFacilityCurrent1dayCV Counter64String,
    pcsRxFacilityCurrent1dayBBE Counter64String,
    pcsRxFacilityCurrent1dayElapsedTime Integer32 }

pcsRxFacilityCurrent1dayES OBJECT-TYPE
    SYNTAX        Unsigned32
    MAX-ACCESS    read-only
    STATUS        current
    DESCRIPTION   "Physical Coding Layer Errored Seconds"
    ::= { pcsRxFacilityCurrent1dayEntry 1 }

pcsRxFacilityCurrent1dayCV OBJECT-TYPE
    SYNTAX        Counter64String
    MAX-ACCESS    read-only
    STATUS        current
    DESCRIPTION   "Physical Coding Layer Coding Violations"
    ::= { pcsRxFacilityCurrent1dayEntry 2 }

pcsRxFacilityCurrent1dayBBE OBJECT-TYPE
    SYNTAX        Counter64String
    MAX-ACCESS    read-only
    STATUS        current
    DESCRIPTION   "PCS Background Block Errors"
    ::= { pcsRxFacilityCurrent1dayEntry 3 }

pcsRxFacilityCurrent1dayElapsedTime OBJECT-TYPE
    SYNTAX        Integer32 (0..86400)
    MAX-ACCESS    read-only
    STATUS        current
    DESCRIPTION   "Elapsed 1Day"
    ::= { pcsRxFacilityCurrent1dayEntry 4 }

endOfPcsRxFacilityCurrent1dayTable OBJECT-TYPE
    SYNTAX        Integer32
    MAX-ACCESS    read-only
    STATUS        current
    DESCRIPTION   ""
    ::= { pmFacilityDataRecord 252 }

pcsRxFacilityHistorical15minTable OBJECT-TYPE
    SYNTAX        SEQUENCE OF PcsRxFacilityHistorical15minEntry
    MAX-ACCESS    not-accessible
    STATUS        current
    DESCRIPTION   ""
    ::= { pmFacilityDataRecord 253 }

pcsRxFacilityHistorical15minEntry OBJECT-TYPE
    SYNTAX        PcsRxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcsRxFacilityHistorical15minNumber
                }
    ::= { pcsRxFacilityHistorical15minTable 1 }

PcsRxFacilityHistorical15minEntry ::= SEQUENCE
  {    pcsRxFacilityHistorical15minNumber Integer32,
    pcsRxFacilityHistorical15minES Unsigned32,
    pcsRxFacilityHistorical15minCV Counter64String,
    pcsRxFacilityHistorical15minBBE Counter64String,
    pcsRxFacilityHistorical15minValidFlag TruthValue,
    pcsRxFacilityHistorical15minTimeStamp DateAndTime }

pcsRxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pcsRxFacilityHistorical15minEntry 1 }

pcsRxFacilityHistorical15minES OBJECT-TYPE
    SYNTAX        Unsigned32
    MAX-ACCESS    read-only
    STATUS        current
    DESCRIPTION   "Physical Coding Layer Errored Seconds"
    ::= { pcsRxFacilityHistorical15minEntry 2 }

pcsRxFacilityHistorical15minCV OBJECT-TYPE
    SYNTAX        Counter64String
    MAX-ACCESS    read-only
    STATUS        current
    DESCRIPTION   "Physical Coding Layer Coding Violations"
    ::= { pcsRxFacilityHistorical15minEntry 3 }

pcsRxFacilityHistorical15minBBE OBJECT-TYPE
    SYNTAX        Counter64String
    MAX-ACCESS    read-only
    STATUS        current
    DESCRIPTION   "PCS Background Block Errors"
    ::= { pcsRxFacilityHistorical15minEntry 4 }

pcsRxFacilityHistorical15minValidFlag OBJECT-TYPE
    SYNTAX        TruthValue
    MAX-ACCESS    read-only
    STATUS        current
    DESCRIPTION   "Valid Flag"
    ::= { pcsRxFacilityHistorical15minEntry 5 }

pcsRxFacilityHistorical15minTimeStamp OBJECT-TYPE
    SYNTAX        DateAndTime
    MAX-ACCESS    read-only
    STATUS        current
    DESCRIPTION   "Timestamp"
    ::= { pcsRxFacilityHistorical15minEntry 6 }

endOfPcsRxFacilityHistorical15minTable OBJECT-TYPE
    SYNTAX        Integer32
    MAX-ACCESS    read-only
    STATUS        current
    DESCRIPTION   ""
    ::= { pmFacilityDataRecord 254 }

pcsRxFacilityHistorical1dayTable OBJECT-TYPE
    SYNTAX        SEQUENCE OF PcsRxFacilityHistorical1dayEntry
    MAX-ACCESS    not-accessible
    STATUS        current
    DESCRIPTION   ""
    ::= { pmFacilityDataRecord 255 }

pcsRxFacilityHistorical1dayEntry OBJECT-TYPE
    SYNTAX        PcsRxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcsRxFacilityHistorical1dayNumber
                }
    ::= { pcsRxFacilityHistorical1dayTable 1 }

PcsRxFacilityHistorical1dayEntry ::= SEQUENCE
  {    pcsRxFacilityHistorical1dayNumber Integer32,
    pcsRxFacilityHistorical1dayES Unsigned32,
    pcsRxFacilityHistorical1dayCV Counter64String,
    pcsRxFacilityHistorical1dayBBE Counter64String,
    pcsRxFacilityHistorical1dayValidFlag TruthValue,
    pcsRxFacilityHistorical1dayTimeStamp DateAndTime }

pcsRxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pcsRxFacilityHistorical1dayEntry 1 }

pcsRxFacilityHistorical1dayES OBJECT-TYPE
    SYNTAX        Unsigned32
    MAX-ACCESS    read-only
    STATUS        current
    DESCRIPTION   "Physical Coding Layer Errored Seconds"
    ::= { pcsRxFacilityHistorical1dayEntry 2 }

pcsRxFacilityHistorical1dayCV OBJECT-TYPE
    SYNTAX        Counter64String
    MAX-ACCESS    read-only
    STATUS        current
    DESCRIPTION   "Physical Coding Layer Coding Violations"
    ::= { pcsRxFacilityHistorical1dayEntry 3 }

pcsRxFacilityHistorical1dayBBE OBJECT-TYPE
    SYNTAX        Counter64String
    MAX-ACCESS    read-only
    STATUS        current
    DESCRIPTION   "PCS Background Block Errors"
    ::= { pcsRxFacilityHistorical1dayEntry 4 }

pcsRxFacilityHistorical1dayValidFlag OBJECT-TYPE
    SYNTAX        TruthValue
    MAX-ACCESS    read-only
    STATUS        current
    DESCRIPTION   "Valid Flag"
    ::= { pcsRxFacilityHistorical1dayEntry 5 }

pcsRxFacilityHistorical1dayTimeStamp OBJECT-TYPE
    SYNTAX        DateAndTime
    MAX-ACCESS    read-only
    STATUS        current
    DESCRIPTION   "Timestamp"
    ::= { pcsRxFacilityHistorical1dayEntry 6 }

endOfPcsRxFacilityHistorical1dayTable OBJECT-TYPE
    SYNTAX        Integer32
    MAX-ACCESS    read-only
    STATUS        current
    DESCRIPTION   ""
    ::= { pmFacilityDataRecord 256 }

pcsTxFacilityCurrent15minTable OBJECT-TYPE
    SYNTAX        SEQUENCE OF PcsTxFacilityCurrent15minEntry
    MAX-ACCESS    not-accessible
    STATUS        current
    DESCRIPTION   ""
    ::= { pmFacilityDataRecord 257 }

pcsTxFacilityCurrent15minEntry OBJECT-TYPE
    SYNTAX        PcsTxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcsTxFacilityCurrent15minTable 1 }

PcsTxFacilityCurrent15minEntry ::= SEQUENCE
  {    pcsTxFacilityCurrent15minESTX Unsigned32,
    pcsTxFacilityCurrent15minCVTX Counter64String,
    pcsTxFacilityCurrent15minBBETX Counter64String,
    pcsTxFacilityCurrent15minElapsedTime Integer32 }

pcsTxFacilityCurrent15minESTX OBJECT-TYPE
    SYNTAX        Unsigned32
    MAX-ACCESS    read-only
    STATUS        current
    DESCRIPTION   "Physical Coding Layer Transmit Errored Seconds"
    ::= { pcsTxFacilityCurrent15minEntry 1 }

pcsTxFacilityCurrent15minCVTX OBJECT-TYPE
    SYNTAX        Counter64String
    MAX-ACCESS    read-only
    STATUS        current
    DESCRIPTION   "Physical Coding Layer Transmit Coding Violations"
    ::= { pcsTxFacilityCurrent15minEntry 2 }

pcsTxFacilityCurrent15minBBETX OBJECT-TYPE
    SYNTAX        Counter64String
    MAX-ACCESS    read-only
    STATUS        current
    DESCRIPTION   "Physical Coding Layer Tx Background Block Errors"
    ::= { pcsTxFacilityCurrent15minEntry 3 }

pcsTxFacilityCurrent15minElapsedTime OBJECT-TYPE
    SYNTAX        Integer32 (0..9000)
    MAX-ACCESS    read-only
    STATUS        current
    DESCRIPTION   "Elapsed 15Min"
    ::= { pcsTxFacilityCurrent15minEntry 4 }

endOfPcsTxFacilityCurrent15minTable OBJECT-TYPE
    SYNTAX        Integer32
    MAX-ACCESS    read-only
    STATUS        current
    DESCRIPTION   ""
    ::= { pmFacilityDataRecord 258 }

pcsTxFacilityCurrent1dayTable OBJECT-TYPE
    SYNTAX        SEQUENCE OF PcsTxFacilityCurrent1dayEntry
    MAX-ACCESS    not-accessible
    STATUS        current
    DESCRIPTION   ""
    ::= { pmFacilityDataRecord 259 }

pcsTxFacilityCurrent1dayEntry OBJECT-TYPE
    SYNTAX        PcsTxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcsTxFacilityCurrent1dayTable 1 }

PcsTxFacilityCurrent1dayEntry ::= SEQUENCE
  {    pcsTxFacilityCurrent1dayESTX Unsigned32,
    pcsTxFacilityCurrent1dayCVTX Counter64String,
    pcsTxFacilityCurrent1dayBBETX Counter64String,
    pcsTxFacilityCurrent1dayElapsedTime Integer32 }

pcsTxFacilityCurrent1dayESTX OBJECT-TYPE
    SYNTAX        Unsigned32
    MAX-ACCESS    read-only
    STATUS        current
    DESCRIPTION   "Physical Coding Layer Transmit Errored Seconds"
    ::= { pcsTxFacilityCurrent1dayEntry 1 }

pcsTxFacilityCurrent1dayCVTX OBJECT-TYPE
    SYNTAX        Counter64String
    MAX-ACCESS    read-only
    STATUS        current
    DESCRIPTION   "Physical Coding Layer Transmit Coding Violations"
    ::= { pcsTxFacilityCurrent1dayEntry 2 }

pcsTxFacilityCurrent1dayBBETX OBJECT-TYPE
    SYNTAX        Counter64String
    MAX-ACCESS    read-only
    STATUS        current
    DESCRIPTION   "Physical Coding Layer Tx Background Block Errors"
    ::= { pcsTxFacilityCurrent1dayEntry 3 }

pcsTxFacilityCurrent1dayElapsedTime OBJECT-TYPE
    SYNTAX        Integer32 (0..86400)
    MAX-ACCESS    read-only
    STATUS        current
    DESCRIPTION   "Elapsed 1Day"
    ::= { pcsTxFacilityCurrent1dayEntry 4 }

endOfPcsTxFacilityCurrent1dayTable OBJECT-TYPE
    SYNTAX        Integer32
    MAX-ACCESS    read-only
    STATUS        current
    DESCRIPTION   ""
    ::= { pmFacilityDataRecord 260 }

pcsTxFacilityHistorical15minTable OBJECT-TYPE
    SYNTAX        SEQUENCE OF PcsTxFacilityHistorical15minEntry
    MAX-ACCESS    not-accessible
    STATUS        current
    DESCRIPTION   ""
    ::= { pmFacilityDataRecord 261 }

pcsTxFacilityHistorical15minEntry OBJECT-TYPE
    SYNTAX        PcsTxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcsTxFacilityHistorical15minNumber
                }
    ::= { pcsTxFacilityHistorical15minTable 1 }

PcsTxFacilityHistorical15minEntry ::= SEQUENCE
  {    pcsTxFacilityHistorical15minNumber Integer32,
    pcsTxFacilityHistorical15minESTX Unsigned32,
    pcsTxFacilityHistorical15minCVTX Counter64String,
    pcsTxFacilityHistorical15minBBETX Counter64String,
    pcsTxFacilityHistorical15minValidFlag TruthValue,
    pcsTxFacilityHistorical15minTimeStamp DateAndTime }

pcsTxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pcsTxFacilityHistorical15minEntry 1 }

pcsTxFacilityHistorical15minESTX OBJECT-TYPE
    SYNTAX        Unsigned32
    MAX-ACCESS    read-only
    STATUS        current
    DESCRIPTION   "Physical Coding Layer Transmit Errored Seconds"
    ::= { pcsTxFacilityHistorical15minEntry 2 }

pcsTxFacilityHistorical15minCVTX OBJECT-TYPE
    SYNTAX        Counter64String
    MAX-ACCESS    read-only
    STATUS        current
    DESCRIPTION   "Physical Coding Layer Transmit Coding Violations"
    ::= { pcsTxFacilityHistorical15minEntry 3 }

pcsTxFacilityHistorical15minBBETX OBJECT-TYPE
    SYNTAX        Counter64String
    MAX-ACCESS    read-only
    STATUS        current
    DESCRIPTION   "Physical Coding Layer Tx Background Block Errors"
    ::= { pcsTxFacilityHistorical15minEntry 4 }

pcsTxFacilityHistorical15minValidFlag OBJECT-TYPE
    SYNTAX        TruthValue
    MAX-ACCESS    read-only
    STATUS        current
    DESCRIPTION   "Valid Flag"
    ::= { pcsTxFacilityHistorical15minEntry 5 }

pcsTxFacilityHistorical15minTimeStamp OBJECT-TYPE
    SYNTAX        DateAndTime
    MAX-ACCESS    read-only
    STATUS        current
    DESCRIPTION   "Timestamp"
    ::= { pcsTxFacilityHistorical15minEntry 6 }

endOfPcsTxFacilityHistorical15minTable OBJECT-TYPE
    SYNTAX        Integer32
    MAX-ACCESS    read-only
    STATUS        current
    DESCRIPTION   ""
    ::= { pmFacilityDataRecord 262 }

pcsTxFacilityHistorical1dayTable OBJECT-TYPE
    SYNTAX        SEQUENCE OF PcsTxFacilityHistorical1dayEntry
    MAX-ACCESS    not-accessible
    STATUS        current
    DESCRIPTION   ""
    ::= { pmFacilityDataRecord 263 }

pcsTxFacilityHistorical1dayEntry OBJECT-TYPE
    SYNTAX        PcsTxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  pcsTxFacilityHistorical1dayNumber
                }
    ::= { pcsTxFacilityHistorical1dayTable 1 }

PcsTxFacilityHistorical1dayEntry ::= SEQUENCE
  {    pcsTxFacilityHistorical1dayNumber Integer32,
    pcsTxFacilityHistorical1dayESTX Unsigned32,
    pcsTxFacilityHistorical1dayCVTX Counter64String,
    pcsTxFacilityHistorical1dayBBETX Counter64String,
    pcsTxFacilityHistorical1dayValidFlag TruthValue,
    pcsTxFacilityHistorical1dayTimeStamp DateAndTime }

pcsTxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pcsTxFacilityHistorical1dayEntry 1 }

pcsTxFacilityHistorical1dayESTX OBJECT-TYPE
    SYNTAX        Unsigned32
    MAX-ACCESS    read-only
    STATUS        current
    DESCRIPTION   "Physical Coding Layer Transmit Errored Seconds"
    ::= { pcsTxFacilityHistorical1dayEntry 2 }

pcsTxFacilityHistorical1dayCVTX OBJECT-TYPE
    SYNTAX        Counter64String
    MAX-ACCESS    read-only
    STATUS        current
    DESCRIPTION   "Physical Coding Layer Transmit Coding Violations"
    ::= { pcsTxFacilityHistorical1dayEntry 3 }

pcsTxFacilityHistorical1dayBBETX OBJECT-TYPE
    SYNTAX        Counter64String
    MAX-ACCESS    read-only
    STATUS        current
    DESCRIPTION   "Physical Coding Layer Tx Background Block Errors"
    ::= { pcsTxFacilityHistorical1dayEntry 4 }

pcsTxFacilityHistorical1dayValidFlag OBJECT-TYPE
    SYNTAX        TruthValue
    MAX-ACCESS    read-only
    STATUS        current
    DESCRIPTION   "Valid Flag"
    ::= { pcsTxFacilityHistorical1dayEntry 5 }

pcsTxFacilityHistorical1dayTimeStamp OBJECT-TYPE
    SYNTAX        DateAndTime
    MAX-ACCESS    read-only
    STATUS        current
    DESCRIPTION   "Timestamp"
    ::= { pcsTxFacilityHistorical1dayEntry 6 }

endOfPcsTxFacilityHistorical1dayTable OBJECT-TYPE
    SYNTAX        Integer32
    MAX-ACCESS    read-only
    STATUS        current
    DESCRIPTION   ""
    ::= { pmFacilityDataRecord 264 }

fec2FacilityCurrent15minTable OBJECT-TYPE
    SYNTAX        SEQUENCE OF Fec2FacilityCurrent15minEntry
    MAX-ACCESS    not-accessible
    STATUS        current
    DESCRIPTION   ""
    ::= { pmFacilityDataRecord 265 }

fec2FacilityCurrent15minEntry OBJECT-TYPE
    SYNTAX        Fec2FacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { fec2FacilityCurrent15minTable 1 }

Fec2FacilityCurrent15minEntry ::= SEQUENCE
  {    fec2FacilityCurrent15minCE Counter64String,
    fec2FacilityCurrent15minUBE Counter64String,
    fec2FacilityCurrent15minBERCE Counter64String,
    fec2FacilityCurrent15minElapsedTime Integer32 }

fec2FacilityCurrent15minCE OBJECT-TYPE
    SYNTAX        Counter64String
    MAX-ACCESS    read-only
    STATUS        current
    DESCRIPTION   "OTU FEC Corrected Errors"
    ::= { fec2FacilityCurrent15minEntry 1 }

fec2FacilityCurrent15minUBE OBJECT-TYPE
    SYNTAX        Counter64String
    MAX-ACCESS    read-only
    STATUS        current
    DESCRIPTION   "OTU FEC Uncorrected Block Errors"
    ::= { fec2FacilityCurrent15minEntry 2 }

fec2FacilityCurrent15minBERCE OBJECT-TYPE
    SYNTAX        Counter64String
    UNITS         "1.0E-18"
    MAX-ACCESS    read-only
    STATUS        current
    DESCRIPTION   "Bit Error Rate before Foward Error Correction (FEC) calculated from corrected errors"
    ::= { fec2FacilityCurrent15minEntry 3 }

fec2FacilityCurrent15minElapsedTime OBJECT-TYPE
    SYNTAX        Integer32 (0..9000)
    MAX-ACCESS    read-only
    STATUS        current
    DESCRIPTION   "Elapsed 15Min"
    ::= { fec2FacilityCurrent15minEntry 4 }

endOfFec2FacilityCurrent15minTable OBJECT-TYPE
    SYNTAX        Integer32
    MAX-ACCESS    read-only
    STATUS        current
    DESCRIPTION   ""
    ::= { pmFacilityDataRecord 266 }

fec2FacilityCurrent1dayTable OBJECT-TYPE
    SYNTAX        SEQUENCE OF Fec2FacilityCurrent1dayEntry
    MAX-ACCESS    not-accessible
    STATUS        current
    DESCRIPTION   ""
    ::= { pmFacilityDataRecord 267 }

fec2FacilityCurrent1dayEntry OBJECT-TYPE
    SYNTAX        Fec2FacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { fec2FacilityCurrent1dayTable 1 }

Fec2FacilityCurrent1dayEntry ::= SEQUENCE
  {    fec2FacilityCurrent1dayCE Counter64String,
    fec2FacilityCurrent1dayUBE Counter64String,
    fec2FacilityCurrent1dayBERCE Counter64String,
    fec2FacilityCurrent1dayElapsedTime Integer32 }

fec2FacilityCurrent1dayCE OBJECT-TYPE
    SYNTAX        Counter64String
    MAX-ACCESS    read-only
    STATUS        current
    DESCRIPTION   "OTU FEC Corrected Errors"
    ::= { fec2FacilityCurrent1dayEntry 1 }

fec2FacilityCurrent1dayUBE OBJECT-TYPE
    SYNTAX        Counter64String
    MAX-ACCESS    read-only
    STATUS        current
    DESCRIPTION   "OTU FEC Uncorrected Block Errors"
    ::= { fec2FacilityCurrent1dayEntry 2 }

fec2FacilityCurrent1dayBERCE OBJECT-TYPE
    SYNTAX        Counter64String
    UNITS         "1.0E-18"
    MAX-ACCESS    read-only
    STATUS        current
    DESCRIPTION   "Bit Error Rate before Foward Error Correction (FEC) calculated from corrected errors"
    ::= { fec2FacilityCurrent1dayEntry 3 }

fec2FacilityCurrent1dayElapsedTime OBJECT-TYPE
    SYNTAX        Integer32 (0..86400)
    MAX-ACCESS    read-only
    STATUS        current
    DESCRIPTION   "Elapsed 1Day"
    ::= { fec2FacilityCurrent1dayEntry 4 }

endOfFec2FacilityCurrent1dayTable OBJECT-TYPE
    SYNTAX        Integer32
    MAX-ACCESS    read-only
    STATUS        current
    DESCRIPTION   ""
    ::= { pmFacilityDataRecord 268 }

fec2FacilityHistorical15minTable OBJECT-TYPE
    SYNTAX        SEQUENCE OF Fec2FacilityHistorical15minEntry
    MAX-ACCESS    not-accessible
    STATUS        current
    DESCRIPTION   ""
    ::= { pmFacilityDataRecord 269 }

fec2FacilityHistorical15minEntry OBJECT-TYPE
    SYNTAX        Fec2FacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  fec2FacilityHistorical15minNumber
                }
    ::= { fec2FacilityHistorical15minTable 1 }

Fec2FacilityHistorical15minEntry ::= SEQUENCE
  {    fec2FacilityHistorical15minNumber Integer32,
    fec2FacilityHistorical15minCE Counter64String,
    fec2FacilityHistorical15minUBE Counter64String,
    fec2FacilityHistorical15minBERCE Counter64String,
    fec2FacilityHistorical15minValidFlag TruthValue,
    fec2FacilityHistorical15minTimeStamp DateAndTime }

fec2FacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { fec2FacilityHistorical15minEntry 1 }

fec2FacilityHistorical15minCE OBJECT-TYPE
    SYNTAX        Counter64String
    MAX-ACCESS    read-only
    STATUS        current
    DESCRIPTION   "OTU FEC Corrected Errors"
    ::= { fec2FacilityHistorical15minEntry 2 }

fec2FacilityHistorical15minUBE OBJECT-TYPE
    SYNTAX        Counter64String
    MAX-ACCESS    read-only
    STATUS        current
    DESCRIPTION   "OTU FEC Uncorrected Block Errors"
    ::= { fec2FacilityHistorical15minEntry 3 }

fec2FacilityHistorical15minBERCE OBJECT-TYPE
    SYNTAX        Counter64String
    UNITS         "1.0E-18"
    MAX-ACCESS    read-only
    STATUS        current
    DESCRIPTION   "Bit Error Rate before Foward Error Correction (FEC) calculated from corrected errors"
    ::= { fec2FacilityHistorical15minEntry 4 }

fec2FacilityHistorical15minValidFlag OBJECT-TYPE
    SYNTAX        TruthValue
    MAX-ACCESS    read-only
    STATUS        current
    DESCRIPTION   "Valid Flag"
    ::= { fec2FacilityHistorical15minEntry 5 }

fec2FacilityHistorical15minTimeStamp OBJECT-TYPE
    SYNTAX        DateAndTime
    MAX-ACCESS    read-only
    STATUS        current
    DESCRIPTION   "Timestamp"
    ::= { fec2FacilityHistorical15minEntry 6 }

endOfFec2FacilityHistorical15minTable OBJECT-TYPE
    SYNTAX        Integer32
    MAX-ACCESS    read-only
    STATUS        current
    DESCRIPTION   ""
    ::= { pmFacilityDataRecord 270 }

fec2FacilityHistorical1dayTable OBJECT-TYPE
    SYNTAX        SEQUENCE OF Fec2FacilityHistorical1dayEntry
    MAX-ACCESS    not-accessible
    STATUS        current
    DESCRIPTION   ""
    ::= { pmFacilityDataRecord 271 }

fec2FacilityHistorical1dayEntry OBJECT-TYPE
    SYNTAX        Fec2FacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  fec2FacilityHistorical1dayNumber
                }
    ::= { fec2FacilityHistorical1dayTable 1 }

Fec2FacilityHistorical1dayEntry ::= SEQUENCE
  {    fec2FacilityHistorical1dayNumber Integer32,
    fec2FacilityHistorical1dayCE Counter64String,
    fec2FacilityHistorical1dayUBE Counter64String,
    fec2FacilityHistorical1dayBERCE Counter64String,
    fec2FacilityHistorical1dayValidFlag TruthValue,
    fec2FacilityHistorical1dayTimeStamp DateAndTime }

fec2FacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { fec2FacilityHistorical1dayEntry 1 }

fec2FacilityHistorical1dayCE OBJECT-TYPE
    SYNTAX        Counter64String
    MAX-ACCESS    read-only
    STATUS        current
    DESCRIPTION   "OTU FEC Corrected Errors"
    ::= { fec2FacilityHistorical1dayEntry 2 }

fec2FacilityHistorical1dayUBE OBJECT-TYPE
    SYNTAX        Counter64String
    MAX-ACCESS    read-only
    STATUS        current
    DESCRIPTION   "OTU FEC Uncorrected Block Errors"
    ::= { fec2FacilityHistorical1dayEntry 3 }

fec2FacilityHistorical1dayBERCE OBJECT-TYPE
    SYNTAX        Counter64String
    UNITS         "1.0E-18"
    MAX-ACCESS    read-only
    STATUS        current
    DESCRIPTION   "Bit Error Rate before Foward Error Correction (FEC) calculated from corrected errors"
    ::= { fec2FacilityHistorical1dayEntry 4 }

fec2FacilityHistorical1dayValidFlag OBJECT-TYPE
    SYNTAX        TruthValue
    MAX-ACCESS    read-only
    STATUS        current
    DESCRIPTION   "Valid Flag"
    ::= { fec2FacilityHistorical1dayEntry 5 }

fec2FacilityHistorical1dayTimeStamp OBJECT-TYPE
    SYNTAX        DateAndTime
    MAX-ACCESS    read-only
    STATUS        current
    DESCRIPTION   "Timestamp"
    ::= { fec2FacilityHistorical1dayEntry 6 }

endOfFec2FacilityHistorical1dayTable OBJECT-TYPE
    SYNTAX        Integer32
    MAX-ACCESS    read-only
    STATUS        current
    DESCRIPTION   ""
    ::= { pmFacilityDataRecord 272 }

lldpFrameRxFacilityCurrent15minTable OBJECT-TYPE
    SYNTAX        SEQUENCE OF LldpFrameRxFacilityCurrent15minEntry
    MAX-ACCESS    not-accessible
    STATUS        current
    DESCRIPTION   ""
    ::= { pmFacilityDataRecord 273 }

lldpFrameRxFacilityCurrent15minEntry OBJECT-TYPE
    SYNTAX        LldpFrameRxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpFrameRxFacilityCurrent15minTable 1 }

LldpFrameRxFacilityCurrent15minEntry ::= SEQUENCE
  {    lldpFrameRxFacilityCurrent15minLLDPFramesRx Counter64String,
    lldpFrameRxFacilityCurrent15minLLDPFrameRxDiscards Counter64String,
    lldpFrameRxFacilityCurrent15minFrameRxErrors Unsigned32,
    lldpFrameRxFacilityCurrent15minElapsedTime Integer32 }

lldpFrameRxFacilityCurrent15minLLDPFramesRx OBJECT-TYPE
    SYNTAX        Counter64String
    MAX-ACCESS    read-only
    STATUS        current
    DESCRIPTION   "Total LLDP frames observed in receive direction or at specific entity"
    ::= { lldpFrameRxFacilityCurrent15minEntry 1 }

lldpFrameRxFacilityCurrent15minLLDPFrameRxDiscards OBJECT-TYPE
    SYNTAX        Counter64String
    MAX-ACCESS    read-only
    STATUS        current
    DESCRIPTION   "Total LLDP frames Discarded in receive direction or specific entity"
    ::= { lldpFrameRxFacilityCurrent15minEntry 2 }

lldpFrameRxFacilityCurrent15minFrameRxErrors OBJECT-TYPE
    SYNTAX        Unsigned32
    MAX-ACCESS    read-only
    STATUS        current
    DESCRIPTION   "Total LLDP Frame Errors in Rx direction"
    ::= { lldpFrameRxFacilityCurrent15minEntry 3 }

lldpFrameRxFacilityCurrent15minElapsedTime OBJECT-TYPE
    SYNTAX        Integer32 (0..9000)
    MAX-ACCESS    read-only
    STATUS        current
    DESCRIPTION   "Elapsed 15Min"
    ::= { lldpFrameRxFacilityCurrent15minEntry 4 }

endOfLldpFrameRxFacilityCurrent15minTable OBJECT-TYPE
    SYNTAX        Integer32
    MAX-ACCESS    read-only
    STATUS        current
    DESCRIPTION   ""
    ::= { pmFacilityDataRecord 274 }

lldpFrameRxFacilityCurrent1dayTable OBJECT-TYPE
    SYNTAX        SEQUENCE OF LldpFrameRxFacilityCurrent1dayEntry
    MAX-ACCESS    not-accessible
    STATUS        current
    DESCRIPTION   ""
    ::= { pmFacilityDataRecord 275 }

lldpFrameRxFacilityCurrent1dayEntry OBJECT-TYPE
    SYNTAX        LldpFrameRxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpFrameRxFacilityCurrent1dayTable 1 }

LldpFrameRxFacilityCurrent1dayEntry ::= SEQUENCE
  {    lldpFrameRxFacilityCurrent1dayLLDPFramesRx Counter64String,
    lldpFrameRxFacilityCurrent1dayLLDPFrameRxDiscards Counter64String,
    lldpFrameRxFacilityCurrent1dayFrameRxErrors Unsigned32,
    lldpFrameRxFacilityCurrent1dayElapsedTime Integer32 }

lldpFrameRxFacilityCurrent1dayLLDPFramesRx OBJECT-TYPE
    SYNTAX        Counter64String
    MAX-ACCESS    read-only
    STATUS        current
    DESCRIPTION   "Total LLDP frames observed in receive direction or at specific entity"
    ::= { lldpFrameRxFacilityCurrent1dayEntry 1 }

lldpFrameRxFacilityCurrent1dayLLDPFrameRxDiscards OBJECT-TYPE
    SYNTAX        Counter64String
    MAX-ACCESS    read-only
    STATUS        current
    DESCRIPTION   "Total LLDP frames Discarded in receive direction or specific entity"
    ::= { lldpFrameRxFacilityCurrent1dayEntry 2 }

lldpFrameRxFacilityCurrent1dayFrameRxErrors OBJECT-TYPE
    SYNTAX        Unsigned32
    MAX-ACCESS    read-only
    STATUS        current
    DESCRIPTION   "Total LLDP Frame Errors in Rx direction"
    ::= { lldpFrameRxFacilityCurrent1dayEntry 3 }

lldpFrameRxFacilityCurrent1dayElapsedTime OBJECT-TYPE
    SYNTAX        Integer32 (0..86400)
    MAX-ACCESS    read-only
    STATUS        current
    DESCRIPTION   "Elapsed 1Day"
    ::= { lldpFrameRxFacilityCurrent1dayEntry 4 }

endOfLldpFrameRxFacilityCurrent1dayTable OBJECT-TYPE
    SYNTAX        Integer32
    MAX-ACCESS    read-only
    STATUS        current
    DESCRIPTION   ""
    ::= { pmFacilityDataRecord 276 }

lldpFrameRxFacilityHistorical15minTable OBJECT-TYPE
    SYNTAX        SEQUENCE OF LldpFrameRxFacilityHistorical15minEntry
    MAX-ACCESS    not-accessible
    STATUS        current
    DESCRIPTION   ""
    ::= { pmFacilityDataRecord 277 }

lldpFrameRxFacilityHistorical15minEntry OBJECT-TYPE
    SYNTAX        LldpFrameRxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpFrameRxFacilityHistorical15minNumber
                }
    ::= { lldpFrameRxFacilityHistorical15minTable 1 }

LldpFrameRxFacilityHistorical15minEntry ::= SEQUENCE
  {    lldpFrameRxFacilityHistorical15minNumber Integer32,
    lldpFrameRxFacilityHistorical15minLLDPFramesRx Counter64String,
    lldpFrameRxFacilityHistorical15minLLDPFrameRxDiscards Counter64String,
    lldpFrameRxFacilityHistorical15minFrameRxErrors Unsigned32,
    lldpFrameRxFacilityHistorical15minValidFlag TruthValue,
    lldpFrameRxFacilityHistorical15minTimeStamp DateAndTime }

lldpFrameRxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lldpFrameRxFacilityHistorical15minEntry 1 }

lldpFrameRxFacilityHistorical15minLLDPFramesRx OBJECT-TYPE
    SYNTAX        Counter64String
    MAX-ACCESS    read-only
    STATUS        current
    DESCRIPTION   "Total LLDP frames observed in receive direction or at specific entity"
    ::= { lldpFrameRxFacilityHistorical15minEntry 2 }

lldpFrameRxFacilityHistorical15minLLDPFrameRxDiscards OBJECT-TYPE
    SYNTAX        Counter64String
    MAX-ACCESS    read-only
    STATUS        current
    DESCRIPTION   "Total LLDP frames Discarded in receive direction or specific entity"
    ::= { lldpFrameRxFacilityHistorical15minEntry 3 }

lldpFrameRxFacilityHistorical15minFrameRxErrors OBJECT-TYPE
    SYNTAX        Unsigned32
    MAX-ACCESS    read-only
    STATUS        current
    DESCRIPTION   "Total LLDP Frame Errors in Rx direction"
    ::= { lldpFrameRxFacilityHistorical15minEntry 4 }

lldpFrameRxFacilityHistorical15minValidFlag OBJECT-TYPE
    SYNTAX        TruthValue
    MAX-ACCESS    read-only
    STATUS        current
    DESCRIPTION   "Valid Flag"
    ::= { lldpFrameRxFacilityHistorical15minEntry 5 }

lldpFrameRxFacilityHistorical15minTimeStamp OBJECT-TYPE
    SYNTAX        DateAndTime
    MAX-ACCESS    read-only
    STATUS        current
    DESCRIPTION   "Timestamp"
    ::= { lldpFrameRxFacilityHistorical15minEntry 6 }

endOfLldpFrameRxFacilityHistorical15minTable OBJECT-TYPE
    SYNTAX        Integer32
    MAX-ACCESS    read-only
    STATUS        current
    DESCRIPTION   ""
    ::= { pmFacilityDataRecord 278 }

lldpFrameRxFacilityHistorical1dayTable OBJECT-TYPE
    SYNTAX        SEQUENCE OF LldpFrameRxFacilityHistorical1dayEntry
    MAX-ACCESS    not-accessible
    STATUS        current
    DESCRIPTION   ""
    ::= { pmFacilityDataRecord 279 }

lldpFrameRxFacilityHistorical1dayEntry OBJECT-TYPE
    SYNTAX        LldpFrameRxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpFrameRxFacilityHistorical1dayNumber
                }
    ::= { lldpFrameRxFacilityHistorical1dayTable 1 }

LldpFrameRxFacilityHistorical1dayEntry ::= SEQUENCE
  {    lldpFrameRxFacilityHistorical1dayNumber Integer32,
    lldpFrameRxFacilityHistorical1dayLLDPFramesRx Counter64String,
    lldpFrameRxFacilityHistorical1dayLLDPFrameRxDiscards Counter64String,
    lldpFrameRxFacilityHistorical1dayFrameRxErrors Unsigned32,
    lldpFrameRxFacilityHistorical1dayValidFlag TruthValue,
    lldpFrameRxFacilityHistorical1dayTimeStamp DateAndTime }

lldpFrameRxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lldpFrameRxFacilityHistorical1dayEntry 1 }

lldpFrameRxFacilityHistorical1dayLLDPFramesRx OBJECT-TYPE
    SYNTAX        Counter64String
    MAX-ACCESS    read-only
    STATUS        current
    DESCRIPTION   "Total LLDP frames observed in receive direction or at specific entity"
    ::= { lldpFrameRxFacilityHistorical1dayEntry 2 }

lldpFrameRxFacilityHistorical1dayLLDPFrameRxDiscards OBJECT-TYPE
    SYNTAX        Counter64String
    MAX-ACCESS    read-only
    STATUS        current
    DESCRIPTION   "Total LLDP frames Discarded in receive direction or specific entity"
    ::= { lldpFrameRxFacilityHistorical1dayEntry 3 }

lldpFrameRxFacilityHistorical1dayFrameRxErrors OBJECT-TYPE
    SYNTAX        Unsigned32
    MAX-ACCESS    read-only
    STATUS        current
    DESCRIPTION   "Total LLDP Frame Errors in Rx direction"
    ::= { lldpFrameRxFacilityHistorical1dayEntry 4 }

lldpFrameRxFacilityHistorical1dayValidFlag OBJECT-TYPE
    SYNTAX        TruthValue
    MAX-ACCESS    read-only
    STATUS        current
    DESCRIPTION   "Valid Flag"
    ::= { lldpFrameRxFacilityHistorical1dayEntry 5 }

lldpFrameRxFacilityHistorical1dayTimeStamp OBJECT-TYPE
    SYNTAX        DateAndTime
    MAX-ACCESS    read-only
    STATUS        current
    DESCRIPTION   "Timestamp"
    ::= { lldpFrameRxFacilityHistorical1dayEntry 6 }

endOfLldpFrameRxFacilityHistorical1dayTable OBJECT-TYPE
    SYNTAX        Integer32
    MAX-ACCESS    read-only
    STATUS        current
    DESCRIPTION   ""
    ::= { pmFacilityDataRecord 280 }

lldpFrameTxFacilityCurrent15minTable OBJECT-TYPE
    SYNTAX        SEQUENCE OF LldpFrameTxFacilityCurrent15minEntry
    MAX-ACCESS    not-accessible
    STATUS        current
    DESCRIPTION   ""
    ::= { pmFacilityDataRecord 281 }

lldpFrameTxFacilityCurrent15minEntry OBJECT-TYPE
    SYNTAX        LldpFrameTxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpFrameTxFacilityCurrent15minTable 1 }

LldpFrameTxFacilityCurrent15minEntry ::= SEQUENCE
  {    lldpFrameTxFacilityCurrent15minLLDPFramesTx Counter64String,
    lldpFrameTxFacilityCurrent15minLLDPFrameTxDiscards Counter64String,
    lldpFrameTxFacilityCurrent15minFrameTxErrors Unsigned32,
    lldpFrameTxFacilityCurrent15minElapsedTime Integer32 }

lldpFrameTxFacilityCurrent15minLLDPFramesTx OBJECT-TYPE
    SYNTAX        Counter64String
    MAX-ACCESS    read-only
    STATUS        current
    DESCRIPTION   "Total LLDP frames observed in transmit direction"
    ::= { lldpFrameTxFacilityCurrent15minEntry 1 }

lldpFrameTxFacilityCurrent15minLLDPFrameTxDiscards OBJECT-TYPE
    SYNTAX        Counter64String
    MAX-ACCESS    read-only
    STATUS        current
    DESCRIPTION   "Total LLDP frames Discarded in transmit direction"
    ::= { lldpFrameTxFacilityCurrent15minEntry 2 }

lldpFrameTxFacilityCurrent15minFrameTxErrors OBJECT-TYPE
    SYNTAX        Unsigned32
    MAX-ACCESS    read-only
    STATUS        current
    DESCRIPTION   "Total LLDP Frame Errors in Tx direction"
    ::= { lldpFrameTxFacilityCurrent15minEntry 3 }

lldpFrameTxFacilityCurrent15minElapsedTime OBJECT-TYPE
    SYNTAX        Integer32 (0..9000)
    MAX-ACCESS    read-only
    STATUS        current
    DESCRIPTION   "Elapsed 15Min"
    ::= { lldpFrameTxFacilityCurrent15minEntry 4 }

endOfLldpFrameTxFacilityCurrent15minTable OBJECT-TYPE
    SYNTAX        Integer32
    MAX-ACCESS    read-only
    STATUS        current
    DESCRIPTION   ""
    ::= { pmFacilityDataRecord 282 }

lldpFrameTxFacilityCurrent1dayTable OBJECT-TYPE
    SYNTAX        SEQUENCE OF LldpFrameTxFacilityCurrent1dayEntry
    MAX-ACCESS    not-accessible
    STATUS        current
    DESCRIPTION   ""
    ::= { pmFacilityDataRecord 283 }

lldpFrameTxFacilityCurrent1dayEntry OBJECT-TYPE
    SYNTAX        LldpFrameTxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpFrameTxFacilityCurrent1dayTable 1 }

LldpFrameTxFacilityCurrent1dayEntry ::= SEQUENCE
  {    lldpFrameTxFacilityCurrent1dayLLDPFramesTx Counter64String,
    lldpFrameTxFacilityCurrent1dayLLDPFrameTxDiscards Counter64String,
    lldpFrameTxFacilityCurrent1dayFrameTxErrors Unsigned32,
    lldpFrameTxFacilityCurrent1dayElapsedTime Integer32 }

lldpFrameTxFacilityCurrent1dayLLDPFramesTx OBJECT-TYPE
    SYNTAX        Counter64String
    MAX-ACCESS    read-only
    STATUS        current
    DESCRIPTION   "Total LLDP frames observed in transmit direction"
    ::= { lldpFrameTxFacilityCurrent1dayEntry 1 }

lldpFrameTxFacilityCurrent1dayLLDPFrameTxDiscards OBJECT-TYPE
    SYNTAX        Counter64String
    MAX-ACCESS    read-only
    STATUS        current
    DESCRIPTION   "Total LLDP frames Discarded in transmit direction"
    ::= { lldpFrameTxFacilityCurrent1dayEntry 2 }

lldpFrameTxFacilityCurrent1dayFrameTxErrors OBJECT-TYPE
    SYNTAX        Unsigned32
    MAX-ACCESS    read-only
    STATUS        current
    DESCRIPTION   "Total LLDP Frame Errors in Tx direction"
    ::= { lldpFrameTxFacilityCurrent1dayEntry 3 }

lldpFrameTxFacilityCurrent1dayElapsedTime OBJECT-TYPE
    SYNTAX        Integer32 (0..86400)
    MAX-ACCESS    read-only
    STATUS        current
    DESCRIPTION   "Elapsed 1Day"
    ::= { lldpFrameTxFacilityCurrent1dayEntry 4 }

endOfLldpFrameTxFacilityCurrent1dayTable OBJECT-TYPE
    SYNTAX        Integer32
    MAX-ACCESS    read-only
    STATUS        current
    DESCRIPTION   ""
    ::= { pmFacilityDataRecord 284 }

lldpFrameTxFacilityHistorical15minTable OBJECT-TYPE
    SYNTAX        SEQUENCE OF LldpFrameTxFacilityHistorical15minEntry
    MAX-ACCESS    not-accessible
    STATUS        current
    DESCRIPTION   ""
    ::= { pmFacilityDataRecord 285 }

lldpFrameTxFacilityHistorical15minEntry OBJECT-TYPE
    SYNTAX        LldpFrameTxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpFrameTxFacilityHistorical15minNumber
                }
    ::= { lldpFrameTxFacilityHistorical15minTable 1 }

LldpFrameTxFacilityHistorical15minEntry ::= SEQUENCE
  {    lldpFrameTxFacilityHistorical15minNumber Integer32,
    lldpFrameTxFacilityHistorical15minLLDPFramesTx Counter64String,
    lldpFrameTxFacilityHistorical15minLLDPFrameTxDiscards Counter64String,
    lldpFrameTxFacilityHistorical15minFrameTxErrors Unsigned32,
    lldpFrameTxFacilityHistorical15minValidFlag TruthValue,
    lldpFrameTxFacilityHistorical15minTimeStamp DateAndTime }

lldpFrameTxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lldpFrameTxFacilityHistorical15minEntry 1 }

lldpFrameTxFacilityHistorical15minLLDPFramesTx OBJECT-TYPE
    SYNTAX        Counter64String
    MAX-ACCESS    read-only
    STATUS        current
    DESCRIPTION   "Total LLDP frames observed in transmit direction"
    ::= { lldpFrameTxFacilityHistorical15minEntry 2 }

lldpFrameTxFacilityHistorical15minLLDPFrameTxDiscards OBJECT-TYPE
    SYNTAX        Counter64String
    MAX-ACCESS    read-only
    STATUS        current
    DESCRIPTION   "Total LLDP frames Discarded in transmit direction"
    ::= { lldpFrameTxFacilityHistorical15minEntry 3 }

lldpFrameTxFacilityHistorical15minFrameTxErrors OBJECT-TYPE
    SYNTAX        Unsigned32
    MAX-ACCESS    read-only
    STATUS        current
    DESCRIPTION   "Total LLDP Frame Errors in Tx direction"
    ::= { lldpFrameTxFacilityHistorical15minEntry 4 }

lldpFrameTxFacilityHistorical15minValidFlag OBJECT-TYPE
    SYNTAX        TruthValue
    MAX-ACCESS    read-only
    STATUS        current
    DESCRIPTION   "Valid Flag"
    ::= { lldpFrameTxFacilityHistorical15minEntry 5 }

lldpFrameTxFacilityHistorical15minTimeStamp OBJECT-TYPE
    SYNTAX        DateAndTime
    MAX-ACCESS    read-only
    STATUS        current
    DESCRIPTION   "Timestamp"
    ::= { lldpFrameTxFacilityHistorical15minEntry 6 }

endOfLldpFrameTxFacilityHistorical15minTable OBJECT-TYPE
    SYNTAX        Integer32
    MAX-ACCESS    read-only
    STATUS        current
    DESCRIPTION   ""
    ::= { pmFacilityDataRecord 286 }

lldpFrameTxFacilityHistorical1dayTable OBJECT-TYPE
    SYNTAX        SEQUENCE OF LldpFrameTxFacilityHistorical1dayEntry
    MAX-ACCESS    not-accessible
    STATUS        current
    DESCRIPTION   ""
    ::= { pmFacilityDataRecord 287 }

lldpFrameTxFacilityHistorical1dayEntry OBJECT-TYPE
    SYNTAX        LldpFrameTxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpFrameTxFacilityHistorical1dayNumber
                }
    ::= { lldpFrameTxFacilityHistorical1dayTable 1 }

LldpFrameTxFacilityHistorical1dayEntry ::= SEQUENCE
  {    lldpFrameTxFacilityHistorical1dayNumber Integer32,
    lldpFrameTxFacilityHistorical1dayLLDPFramesTx Counter64String,
    lldpFrameTxFacilityHistorical1dayLLDPFrameTxDiscards Counter64String,
    lldpFrameTxFacilityHistorical1dayFrameTxErrors Unsigned32,
    lldpFrameTxFacilityHistorical1dayValidFlag TruthValue,
    lldpFrameTxFacilityHistorical1dayTimeStamp DateAndTime }

lldpFrameTxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lldpFrameTxFacilityHistorical1dayEntry 1 }

lldpFrameTxFacilityHistorical1dayLLDPFramesTx OBJECT-TYPE
    SYNTAX        Counter64String
    MAX-ACCESS    read-only
    STATUS        current
    DESCRIPTION   "Total LLDP frames observed in transmit direction"
    ::= { lldpFrameTxFacilityHistorical1dayEntry 2 }

lldpFrameTxFacilityHistorical1dayLLDPFrameTxDiscards OBJECT-TYPE
    SYNTAX        Counter64String
    MAX-ACCESS    read-only
    STATUS        current
    DESCRIPTION   "Total LLDP frames Discarded in transmit direction"
    ::= { lldpFrameTxFacilityHistorical1dayEntry 3 }

lldpFrameTxFacilityHistorical1dayFrameTxErrors OBJECT-TYPE
    SYNTAX        Unsigned32
    MAX-ACCESS    read-only
    STATUS        current
    DESCRIPTION   "Total LLDP Frame Errors in Tx direction"
    ::= { lldpFrameTxFacilityHistorical1dayEntry 4 }

lldpFrameTxFacilityHistorical1dayValidFlag OBJECT-TYPE
    SYNTAX        TruthValue
    MAX-ACCESS    read-only
    STATUS        current
    DESCRIPTION   "Valid Flag"
    ::= { lldpFrameTxFacilityHistorical1dayEntry 5 }

lldpFrameTxFacilityHistorical1dayTimeStamp OBJECT-TYPE
    SYNTAX        DateAndTime
    MAX-ACCESS    read-only
    STATUS        current
    DESCRIPTION   "Timestamp"
    ::= { lldpFrameTxFacilityHistorical1dayEntry 6 }

endOfLldpFrameTxFacilityHistorical1dayTable OBJECT-TYPE
    SYNTAX        Integer32
    MAX-ACCESS    read-only
    STATUS        current
    DESCRIPTION   ""
    ::= { pmFacilityDataRecord 288 }

lldpTLVRxFacilityCurrent15minTable OBJECT-TYPE
    SYNTAX        SEQUENCE OF LldpTLVRxFacilityCurrent15minEntry
    MAX-ACCESS    not-accessible
    STATUS        current
    DESCRIPTION   ""
    ::= { pmFacilityDataRecord 289 }

lldpTLVRxFacilityCurrent15minEntry OBJECT-TYPE
    SYNTAX        LldpTLVRxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpTLVRxFacilityCurrent15minTable 1 }

LldpTLVRxFacilityCurrent15minEntry ::= SEQUENCE
  {    lldpTLVRxFacilityCurrent15minTLVRxDiscards Unsigned32,
    lldpTLVRxFacilityCurrent15minTLVRxUnknown Unsigned32,
    lldpTLVRxFacilityCurrent15minElapsedTime Integer32 }

lldpTLVRxFacilityCurrent15minTLVRxDiscards OBJECT-TYPE
    SYNTAX        Unsigned32
    MAX-ACCESS    read-only
    STATUS        current
    DESCRIPTION   "Number of TLV Discards in LLDP frames in Rx Direction"
    ::= { lldpTLVRxFacilityCurrent15minEntry 1 }

lldpTLVRxFacilityCurrent15minTLVRxUnknown OBJECT-TYPE
    SYNTAX        Unsigned32
    MAX-ACCESS    read-only
    STATUS        current
    DESCRIPTION   "Number of LLDP frames with unrecognized TLVs in Rx Direction"
    ::= { lldpTLVRxFacilityCurrent15minEntry 2 }

lldpTLVRxFacilityCurrent15minElapsedTime OBJECT-TYPE
    SYNTAX        Integer32 (0..9000)
    MAX-ACCESS    read-only
    STATUS        current
    DESCRIPTION   "Elapsed 15Min"
    ::= { lldpTLVRxFacilityCurrent15minEntry 3 }

endOfLldpTLVRxFacilityCurrent15minTable OBJECT-TYPE
    SYNTAX        Integer32
    MAX-ACCESS    read-only
    STATUS        current
    DESCRIPTION   ""
    ::= { pmFacilityDataRecord 290 }

lldpTLVRxFacilityCurrent1dayTable OBJECT-TYPE
    SYNTAX        SEQUENCE OF LldpTLVRxFacilityCurrent1dayEntry
    MAX-ACCESS    not-accessible
    STATUS        current
    DESCRIPTION   ""
    ::= { pmFacilityDataRecord 291 }

lldpTLVRxFacilityCurrent1dayEntry OBJECT-TYPE
    SYNTAX        LldpTLVRxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpTLVRxFacilityCurrent1dayTable 1 }

LldpTLVRxFacilityCurrent1dayEntry ::= SEQUENCE
  {    lldpTLVRxFacilityCurrent1dayTLVRxDiscards Unsigned32,
    lldpTLVRxFacilityCurrent1dayTLVRxUnknown Unsigned32,
    lldpTLVRxFacilityCurrent1dayElapsedTime Integer32 }

lldpTLVRxFacilityCurrent1dayTLVRxDiscards OBJECT-TYPE
    SYNTAX        Unsigned32
    MAX-ACCESS    read-only
    STATUS        current
    DESCRIPTION   "Number of TLV Discards in LLDP frames in Rx Direction"
    ::= { lldpTLVRxFacilityCurrent1dayEntry 1 }

lldpTLVRxFacilityCurrent1dayTLVRxUnknown OBJECT-TYPE
    SYNTAX        Unsigned32
    MAX-ACCESS    read-only
    STATUS        current
    DESCRIPTION   "Number of LLDP frames with unrecognized TLVs in Rx Direction"
    ::= { lldpTLVRxFacilityCurrent1dayEntry 2 }

lldpTLVRxFacilityCurrent1dayElapsedTime OBJECT-TYPE
    SYNTAX        Integer32 (0..86400)
    MAX-ACCESS    read-only
    STATUS        current
    DESCRIPTION   "Elapsed 1Day"
    ::= { lldpTLVRxFacilityCurrent1dayEntry 3 }

endOfLldpTLVRxFacilityCurrent1dayTable OBJECT-TYPE
    SYNTAX        Integer32
    MAX-ACCESS    read-only
    STATUS        current
    DESCRIPTION   ""
    ::= { pmFacilityDataRecord 292 }

lldpTLVRxFacilityHistorical15minTable OBJECT-TYPE
    SYNTAX        SEQUENCE OF LldpTLVRxFacilityHistorical15minEntry
    MAX-ACCESS    not-accessible
    STATUS        current
    DESCRIPTION   ""
    ::= { pmFacilityDataRecord 293 }

lldpTLVRxFacilityHistorical15minEntry OBJECT-TYPE
    SYNTAX        LldpTLVRxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpTLVRxFacilityHistorical15minNumber
                }
    ::= { lldpTLVRxFacilityHistorical15minTable 1 }

LldpTLVRxFacilityHistorical15minEntry ::= SEQUENCE
  {    lldpTLVRxFacilityHistorical15minNumber Integer32,
    lldpTLVRxFacilityHistorical15minTLVRxDiscards Unsigned32,
    lldpTLVRxFacilityHistorical15minTLVRxUnknown Unsigned32,
    lldpTLVRxFacilityHistorical15minValidFlag TruthValue,
    lldpTLVRxFacilityHistorical15minTimeStamp DateAndTime }

lldpTLVRxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lldpTLVRxFacilityHistorical15minEntry 1 }

lldpTLVRxFacilityHistorical15minTLVRxDiscards OBJECT-TYPE
    SYNTAX        Unsigned32
    MAX-ACCESS    read-only
    STATUS        current
    DESCRIPTION   "Number of TLV Discards in LLDP frames in Rx Direction"
    ::= { lldpTLVRxFacilityHistorical15minEntry 2 }

lldpTLVRxFacilityHistorical15minTLVRxUnknown OBJECT-TYPE
    SYNTAX        Unsigned32
    MAX-ACCESS    read-only
    STATUS        current
    DESCRIPTION   "Number of LLDP frames with unrecognized TLVs in Rx Direction"
    ::= { lldpTLVRxFacilityHistorical15minEntry 3 }

lldpTLVRxFacilityHistorical15minValidFlag OBJECT-TYPE
    SYNTAX        TruthValue
    MAX-ACCESS    read-only
    STATUS        current
    DESCRIPTION   "Valid Flag"
    ::= { lldpTLVRxFacilityHistorical15minEntry 4 }

lldpTLVRxFacilityHistorical15minTimeStamp OBJECT-TYPE
    SYNTAX        DateAndTime
    MAX-ACCESS    read-only
    STATUS        current
    DESCRIPTION   "Timestamp"
    ::= { lldpTLVRxFacilityHistorical15minEntry 5 }

endOfLldpTLVRxFacilityHistorical15minTable OBJECT-TYPE
    SYNTAX        Integer32
    MAX-ACCESS    read-only
    STATUS        current
    DESCRIPTION   ""
    ::= { pmFacilityDataRecord 294 }

lldpTLVRxFacilityHistorical1dayTable OBJECT-TYPE
    SYNTAX        SEQUENCE OF LldpTLVRxFacilityHistorical1dayEntry
    MAX-ACCESS    not-accessible
    STATUS        current
    DESCRIPTION   ""
    ::= { pmFacilityDataRecord 295 }

lldpTLVRxFacilityHistorical1dayEntry OBJECT-TYPE
    SYNTAX        LldpTLVRxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpTLVRxFacilityHistorical1dayNumber
                }
    ::= { lldpTLVRxFacilityHistorical1dayTable 1 }

LldpTLVRxFacilityHistorical1dayEntry ::= SEQUENCE
  {    lldpTLVRxFacilityHistorical1dayNumber Integer32,
    lldpTLVRxFacilityHistorical1dayTLVRxDiscards Unsigned32,
    lldpTLVRxFacilityHistorical1dayTLVRxUnknown Unsigned32,
    lldpTLVRxFacilityHistorical1dayValidFlag TruthValue,
    lldpTLVRxFacilityHistorical1dayTimeStamp DateAndTime }

lldpTLVRxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lldpTLVRxFacilityHistorical1dayEntry 1 }

lldpTLVRxFacilityHistorical1dayTLVRxDiscards OBJECT-TYPE
    SYNTAX        Unsigned32
    MAX-ACCESS    read-only
    STATUS        current
    DESCRIPTION   "Number of TLV Discards in LLDP frames in Rx Direction"
    ::= { lldpTLVRxFacilityHistorical1dayEntry 2 }

lldpTLVRxFacilityHistorical1dayTLVRxUnknown OBJECT-TYPE
    SYNTAX        Unsigned32
    MAX-ACCESS    read-only
    STATUS        current
    DESCRIPTION   "Number of LLDP frames with unrecognized TLVs in Rx Direction"
    ::= { lldpTLVRxFacilityHistorical1dayEntry 3 }

lldpTLVRxFacilityHistorical1dayValidFlag OBJECT-TYPE
    SYNTAX        TruthValue
    MAX-ACCESS    read-only
    STATUS        current
    DESCRIPTION   "Valid Flag"
    ::= { lldpTLVRxFacilityHistorical1dayEntry 4 }

lldpTLVRxFacilityHistorical1dayTimeStamp OBJECT-TYPE
    SYNTAX        DateAndTime
    MAX-ACCESS    read-only
    STATUS        current
    DESCRIPTION   "Timestamp"
    ::= { lldpTLVRxFacilityHistorical1dayEntry 5 }

endOfLldpTLVRxFacilityHistorical1dayTable OBJECT-TYPE
    SYNTAX        Integer32
    MAX-ACCESS    read-only
    STATUS        current
    DESCRIPTION   ""
    ::= { pmFacilityDataRecord 296 }

lldpTLVTxFacilityCurrent15minTable OBJECT-TYPE
    SYNTAX        SEQUENCE OF LldpTLVTxFacilityCurrent15minEntry
    MAX-ACCESS    not-accessible
    STATUS        current
    DESCRIPTION   ""
    ::= { pmFacilityDataRecord 297 }

lldpTLVTxFacilityCurrent15minEntry OBJECT-TYPE
    SYNTAX        LldpTLVTxFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpTLVTxFacilityCurrent15minTable 1 }

LldpTLVTxFacilityCurrent15minEntry ::= SEQUENCE
  {    lldpTLVTxFacilityCurrent15minTLVTxDiscards Unsigned32,
    lldpTLVTxFacilityCurrent15minTLVTxUnknown Unsigned32,
    lldpTLVTxFacilityCurrent15minElapsedTime Integer32 }

lldpTLVTxFacilityCurrent15minTLVTxDiscards OBJECT-TYPE
    SYNTAX        Unsigned32
    MAX-ACCESS    read-only
    STATUS        current
    DESCRIPTION   "Number of TLV Discards in LLDP frames in Tx Direction"
    ::= { lldpTLVTxFacilityCurrent15minEntry 1 }

lldpTLVTxFacilityCurrent15minTLVTxUnknown OBJECT-TYPE
    SYNTAX        Unsigned32
    MAX-ACCESS    read-only
    STATUS        current
    DESCRIPTION   "Number of LLDP frames with unrecognized TLVs in Tx Direction"
    ::= { lldpTLVTxFacilityCurrent15minEntry 2 }

lldpTLVTxFacilityCurrent15minElapsedTime OBJECT-TYPE
    SYNTAX        Integer32 (0..9000)
    MAX-ACCESS    read-only
    STATUS        current
    DESCRIPTION   "Elapsed 15Min"
    ::= { lldpTLVTxFacilityCurrent15minEntry 3 }

endOfLldpTLVTxFacilityCurrent15minTable OBJECT-TYPE
    SYNTAX        Integer32
    MAX-ACCESS    read-only
    STATUS        current
    DESCRIPTION   ""
    ::= { pmFacilityDataRecord 298 }

lldpTLVTxFacilityCurrent1dayTable OBJECT-TYPE
    SYNTAX        SEQUENCE OF LldpTLVTxFacilityCurrent1dayEntry
    MAX-ACCESS    not-accessible
    STATUS        current
    DESCRIPTION   ""
    ::= { pmFacilityDataRecord 299 }

lldpTLVTxFacilityCurrent1dayEntry OBJECT-TYPE
    SYNTAX        LldpTLVTxFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpTLVTxFacilityCurrent1dayTable 1 }

LldpTLVTxFacilityCurrent1dayEntry ::= SEQUENCE
  {    lldpTLVTxFacilityCurrent1dayTLVTxDiscards Unsigned32,
    lldpTLVTxFacilityCurrent1dayTLVTxUnknown Unsigned32,
    lldpTLVTxFacilityCurrent1dayElapsedTime Integer32 }

lldpTLVTxFacilityCurrent1dayTLVTxDiscards OBJECT-TYPE
    SYNTAX        Unsigned32
    MAX-ACCESS    read-only
    STATUS        current
    DESCRIPTION   "Number of TLV Discards in LLDP frames in Tx Direction"
    ::= { lldpTLVTxFacilityCurrent1dayEntry 1 }

lldpTLVTxFacilityCurrent1dayTLVTxUnknown OBJECT-TYPE
    SYNTAX        Unsigned32
    MAX-ACCESS    read-only
    STATUS        current
    DESCRIPTION   "Number of LLDP frames with unrecognized TLVs in Tx Direction"
    ::= { lldpTLVTxFacilityCurrent1dayEntry 2 }

lldpTLVTxFacilityCurrent1dayElapsedTime OBJECT-TYPE
    SYNTAX        Integer32 (0..86400)
    MAX-ACCESS    read-only
    STATUS        current
    DESCRIPTION   "Elapsed 1Day"
    ::= { lldpTLVTxFacilityCurrent1dayEntry 3 }

endOfLldpTLVTxFacilityCurrent1dayTable OBJECT-TYPE
    SYNTAX        Integer32
    MAX-ACCESS    read-only
    STATUS        current
    DESCRIPTION   ""
    ::= { pmFacilityDataRecord 300 }

lldpTLVTxFacilityHistorical15minTable OBJECT-TYPE
    SYNTAX        SEQUENCE OF LldpTLVTxFacilityHistorical15minEntry
    MAX-ACCESS    not-accessible
    STATUS        current
    DESCRIPTION   ""
    ::= { pmFacilityDataRecord 301 }

lldpTLVTxFacilityHistorical15minEntry OBJECT-TYPE
    SYNTAX        LldpTLVTxFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpTLVTxFacilityHistorical15minNumber
                }
    ::= { lldpTLVTxFacilityHistorical15minTable 1 }

LldpTLVTxFacilityHistorical15minEntry ::= SEQUENCE
  {    lldpTLVTxFacilityHistorical15minNumber Integer32,
    lldpTLVTxFacilityHistorical15minTLVTxDiscards Unsigned32,
    lldpTLVTxFacilityHistorical15minTLVTxUnknown Unsigned32,
    lldpTLVTxFacilityHistorical15minValidFlag TruthValue,
    lldpTLVTxFacilityHistorical15minTimeStamp DateAndTime }

lldpTLVTxFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lldpTLVTxFacilityHistorical15minEntry 1 }

lldpTLVTxFacilityHistorical15minTLVTxDiscards OBJECT-TYPE
    SYNTAX        Unsigned32
    MAX-ACCESS    read-only
    STATUS        current
    DESCRIPTION   "Number of TLV Discards in LLDP frames in Tx Direction"
    ::= { lldpTLVTxFacilityHistorical15minEntry 2 }

lldpTLVTxFacilityHistorical15minTLVTxUnknown OBJECT-TYPE
    SYNTAX        Unsigned32
    MAX-ACCESS    read-only
    STATUS        current
    DESCRIPTION   "Number of LLDP frames with unrecognized TLVs in Tx Direction"
    ::= { lldpTLVTxFacilityHistorical15minEntry 3 }

lldpTLVTxFacilityHistorical15minValidFlag OBJECT-TYPE
    SYNTAX        TruthValue
    MAX-ACCESS    read-only
    STATUS        current
    DESCRIPTION   "Valid Flag"
    ::= { lldpTLVTxFacilityHistorical15minEntry 4 }

lldpTLVTxFacilityHistorical15minTimeStamp OBJECT-TYPE
    SYNTAX        DateAndTime
    MAX-ACCESS    read-only
    STATUS        current
    DESCRIPTION   "Timestamp"
    ::= { lldpTLVTxFacilityHistorical15minEntry 5 }

endOfLldpTLVTxFacilityHistorical15minTable OBJECT-TYPE
    SYNTAX        Integer32
    MAX-ACCESS    read-only
    STATUS        current
    DESCRIPTION   ""
    ::= { pmFacilityDataRecord 302 }

lldpTLVTxFacilityHistorical1dayTable OBJECT-TYPE
    SYNTAX        SEQUENCE OF LldpTLVTxFacilityHistorical1dayEntry
    MAX-ACCESS    not-accessible
    STATUS        current
    DESCRIPTION   ""
    ::= { pmFacilityDataRecord 303 }

lldpTLVTxFacilityHistorical1dayEntry OBJECT-TYPE
    SYNTAX        LldpTLVTxFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpTLVTxFacilityHistorical1dayNumber
                }
    ::= { lldpTLVTxFacilityHistorical1dayTable 1 }

LldpTLVTxFacilityHistorical1dayEntry ::= SEQUENCE
  {    lldpTLVTxFacilityHistorical1dayNumber Integer32,
    lldpTLVTxFacilityHistorical1dayTLVTxDiscards Unsigned32,
    lldpTLVTxFacilityHistorical1dayTLVTxUnknown Unsigned32,
    lldpTLVTxFacilityHistorical1dayValidFlag TruthValue,
    lldpTLVTxFacilityHistorical1dayTimeStamp DateAndTime }

lldpTLVTxFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lldpTLVTxFacilityHistorical1dayEntry 1 }

lldpTLVTxFacilityHistorical1dayTLVTxDiscards OBJECT-TYPE
    SYNTAX        Unsigned32
    MAX-ACCESS    read-only
    STATUS        current
    DESCRIPTION   "Number of TLV Discards in LLDP frames in Tx Direction"
    ::= { lldpTLVTxFacilityHistorical1dayEntry 2 }

lldpTLVTxFacilityHistorical1dayTLVTxUnknown OBJECT-TYPE
    SYNTAX        Unsigned32
    MAX-ACCESS    read-only
    STATUS        current
    DESCRIPTION   "Number of LLDP frames with unrecognized TLVs in Tx Direction"
    ::= { lldpTLVTxFacilityHistorical1dayEntry 3 }

lldpTLVTxFacilityHistorical1dayValidFlag OBJECT-TYPE
    SYNTAX        TruthValue
    MAX-ACCESS    read-only
    STATUS        current
    DESCRIPTION   "Valid Flag"
    ::= { lldpTLVTxFacilityHistorical1dayEntry 4 }

lldpTLVTxFacilityHistorical1dayTimeStamp OBJECT-TYPE
    SYNTAX        DateAndTime
    MAX-ACCESS    read-only
    STATUS        current
    DESCRIPTION   "Timestamp"
    ::= { lldpTLVTxFacilityHistorical1dayEntry 5 }

endOfLldpTLVTxFacilityHistorical1dayTable OBJECT-TYPE
    SYNTAX        Integer32
    MAX-ACCESS    read-only
    STATUS        current
    DESCRIPTION   ""
    ::= { pmFacilityDataRecord 304 }

lldpTLVFacilityCurrent15minTable OBJECT-TYPE
    SYNTAX        SEQUENCE OF LldpTLVFacilityCurrent15minEntry
    MAX-ACCESS    not-accessible
    STATUS        current
    DESCRIPTION   ""
    ::= { pmFacilityDataRecord 305 }

lldpTLVFacilityCurrent15minEntry OBJECT-TYPE
    SYNTAX        LldpTLVFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpTLVFacilityCurrent15minTable 1 }

LldpTLVFacilityCurrent15minEntry ::= SEQUENCE
  {    lldpTLVFacilityCurrent15minTLVDiscards Unsigned32,
    lldpTLVFacilityCurrent15minTLVUnknown Unsigned32,
    lldpTLVFacilityCurrent15minAgeOuts Unsigned32,
    lldpTLVFacilityCurrent15minElapsedTime Integer32 }

lldpTLVFacilityCurrent15minTLVDiscards OBJECT-TYPE
    SYNTAX        Unsigned32
    MAX-ACCESS    read-only
    STATUS        current
    DESCRIPTION   "Number of TLV Discards in LLDP frames"
    ::= { lldpTLVFacilityCurrent15minEntry 1 }

lldpTLVFacilityCurrent15minTLVUnknown OBJECT-TYPE
    SYNTAX        Unsigned32
    MAX-ACCESS    read-only
    STATUS        current
    DESCRIPTION   "Number of LLDP frames with unrecognized TLVs"
    ::= { lldpTLVFacilityCurrent15minEntry 2 }

lldpTLVFacilityCurrent15minAgeOuts OBJECT-TYPE
    SYNTAX        Unsigned32
    MAX-ACCESS    read-only
    STATUS        current
    DESCRIPTION   "Number of LLDP Age Outs"
    ::= { lldpTLVFacilityCurrent15minEntry 3 }

lldpTLVFacilityCurrent15minElapsedTime OBJECT-TYPE
    SYNTAX        Integer32 (0..9000)
    MAX-ACCESS    read-only
    STATUS        current
    DESCRIPTION   "Elapsed 15Min"
    ::= { lldpTLVFacilityCurrent15minEntry 4 }

endOfLldpTLVFacilityCurrent15minTable OBJECT-TYPE
    SYNTAX        Integer32
    MAX-ACCESS    read-only
    STATUS        current
    DESCRIPTION   ""
    ::= { pmFacilityDataRecord 306 }

lldpTLVFacilityCurrent1dayTable OBJECT-TYPE
    SYNTAX        SEQUENCE OF LldpTLVFacilityCurrent1dayEntry
    MAX-ACCESS    not-accessible
    STATUS        current
    DESCRIPTION   ""
    ::= { pmFacilityDataRecord 307 }

lldpTLVFacilityCurrent1dayEntry OBJECT-TYPE
    SYNTAX        LldpTLVFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpTLVFacilityCurrent1dayTable 1 }

LldpTLVFacilityCurrent1dayEntry ::= SEQUENCE
  {    lldpTLVFacilityCurrent1dayTLVDiscards Unsigned32,
    lldpTLVFacilityCurrent1dayTLVUnknown Unsigned32,
    lldpTLVFacilityCurrent1dayAgeOuts Unsigned32,
    lldpTLVFacilityCurrent1dayElapsedTime Integer32 }

lldpTLVFacilityCurrent1dayTLVDiscards OBJECT-TYPE
    SYNTAX        Unsigned32
    MAX-ACCESS    read-only
    STATUS        current
    DESCRIPTION   "Number of TLV Discards in LLDP frames"
    ::= { lldpTLVFacilityCurrent1dayEntry 1 }

lldpTLVFacilityCurrent1dayTLVUnknown OBJECT-TYPE
    SYNTAX        Unsigned32
    MAX-ACCESS    read-only
    STATUS        current
    DESCRIPTION   "Number of LLDP frames with unrecognized TLVs"
    ::= { lldpTLVFacilityCurrent1dayEntry 2 }

lldpTLVFacilityCurrent1dayAgeOuts OBJECT-TYPE
    SYNTAX        Unsigned32
    MAX-ACCESS    read-only
    STATUS        current
    DESCRIPTION   "Number of LLDP Age Outs"
    ::= { lldpTLVFacilityCurrent1dayEntry 3 }

lldpTLVFacilityCurrent1dayElapsedTime OBJECT-TYPE
    SYNTAX        Integer32 (0..86400)
    MAX-ACCESS    read-only
    STATUS        current
    DESCRIPTION   "Elapsed 1Day"
    ::= { lldpTLVFacilityCurrent1dayEntry 4 }

endOfLldpTLVFacilityCurrent1dayTable OBJECT-TYPE
    SYNTAX        Integer32
    MAX-ACCESS    read-only
    STATUS        current
    DESCRIPTION   ""
    ::= { pmFacilityDataRecord 308 }

lldpTLVFacilityHistorical15minTable OBJECT-TYPE
    SYNTAX        SEQUENCE OF LldpTLVFacilityHistorical15minEntry
    MAX-ACCESS    not-accessible
    STATUS        current
    DESCRIPTION   ""
    ::= { pmFacilityDataRecord 309 }

lldpTLVFacilityHistorical15minEntry OBJECT-TYPE
    SYNTAX        LldpTLVFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpTLVFacilityHistorical15minNumber
                }
    ::= { lldpTLVFacilityHistorical15minTable 1 }

LldpTLVFacilityHistorical15minEntry ::= SEQUENCE
  {    lldpTLVFacilityHistorical15minNumber Integer32,
    lldpTLVFacilityHistorical15minTLVDiscards Unsigned32,
    lldpTLVFacilityHistorical15minTLVUnknown Unsigned32,
    lldpTLVFacilityHistorical15minAgeOuts Unsigned32,
    lldpTLVFacilityHistorical15minValidFlag TruthValue,
    lldpTLVFacilityHistorical15minTimeStamp DateAndTime }

lldpTLVFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lldpTLVFacilityHistorical15minEntry 1 }

lldpTLVFacilityHistorical15minTLVDiscards OBJECT-TYPE
    SYNTAX        Unsigned32
    MAX-ACCESS    read-only
    STATUS        current
    DESCRIPTION   "Number of TLV Discards in LLDP frames"
    ::= { lldpTLVFacilityHistorical15minEntry 2 }

lldpTLVFacilityHistorical15minTLVUnknown OBJECT-TYPE
    SYNTAX        Unsigned32
    MAX-ACCESS    read-only
    STATUS        current
    DESCRIPTION   "Number of LLDP frames with unrecognized TLVs"
    ::= { lldpTLVFacilityHistorical15minEntry 3 }

lldpTLVFacilityHistorical15minAgeOuts OBJECT-TYPE
    SYNTAX        Unsigned32
    MAX-ACCESS    read-only
    STATUS        current
    DESCRIPTION   "Number of LLDP Age Outs"
    ::= { lldpTLVFacilityHistorical15minEntry 4 }

lldpTLVFacilityHistorical15minValidFlag OBJECT-TYPE
    SYNTAX        TruthValue
    MAX-ACCESS    read-only
    STATUS        current
    DESCRIPTION   "Valid Flag"
    ::= { lldpTLVFacilityHistorical15minEntry 5 }

lldpTLVFacilityHistorical15minTimeStamp OBJECT-TYPE
    SYNTAX        DateAndTime
    MAX-ACCESS    read-only
    STATUS        current
    DESCRIPTION   "Timestamp"
    ::= { lldpTLVFacilityHistorical15minEntry 6 }

endOfLldpTLVFacilityHistorical15minTable OBJECT-TYPE
    SYNTAX        Integer32
    MAX-ACCESS    read-only
    STATUS        current
    DESCRIPTION   ""
    ::= { pmFacilityDataRecord 310 }

lldpTLVFacilityHistorical1dayTable OBJECT-TYPE
    SYNTAX        SEQUENCE OF LldpTLVFacilityHistorical1dayEntry
    MAX-ACCESS    not-accessible
    STATUS        current
    DESCRIPTION   ""
    ::= { pmFacilityDataRecord 311 }

lldpTLVFacilityHistorical1dayEntry OBJECT-TYPE
    SYNTAX        LldpTLVFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpTLVFacilityHistorical1dayNumber
                }
    ::= { lldpTLVFacilityHistorical1dayTable 1 }

LldpTLVFacilityHistorical1dayEntry ::= SEQUENCE
  {    lldpTLVFacilityHistorical1dayNumber Integer32,
    lldpTLVFacilityHistorical1dayTLVDiscards Unsigned32,
    lldpTLVFacilityHistorical1dayTLVUnknown Unsigned32,
    lldpTLVFacilityHistorical1dayAgeOuts Unsigned32,
    lldpTLVFacilityHistorical1dayValidFlag TruthValue,
    lldpTLVFacilityHistorical1dayTimeStamp DateAndTime }

lldpTLVFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lldpTLVFacilityHistorical1dayEntry 1 }

lldpTLVFacilityHistorical1dayTLVDiscards OBJECT-TYPE
    SYNTAX        Unsigned32
    MAX-ACCESS    read-only
    STATUS        current
    DESCRIPTION   "Number of TLV Discards in LLDP frames"
    ::= { lldpTLVFacilityHistorical1dayEntry 2 }

lldpTLVFacilityHistorical1dayTLVUnknown OBJECT-TYPE
    SYNTAX        Unsigned32
    MAX-ACCESS    read-only
    STATUS        current
    DESCRIPTION   "Number of LLDP frames with unrecognized TLVs"
    ::= { lldpTLVFacilityHistorical1dayEntry 3 }

lldpTLVFacilityHistorical1dayAgeOuts OBJECT-TYPE
    SYNTAX        Unsigned32
    MAX-ACCESS    read-only
    STATUS        current
    DESCRIPTION   "Number of LLDP Age Outs"
    ::= { lldpTLVFacilityHistorical1dayEntry 4 }

lldpTLVFacilityHistorical1dayValidFlag OBJECT-TYPE
    SYNTAX        TruthValue
    MAX-ACCESS    read-only
    STATUS        current
    DESCRIPTION   "Valid Flag"
    ::= { lldpTLVFacilityHistorical1dayEntry 5 }

lldpTLVFacilityHistorical1dayTimeStamp OBJECT-TYPE
    SYNTAX        DateAndTime
    MAX-ACCESS    read-only
    STATUS        current
    DESCRIPTION   "Timestamp"
    ::= { lldpTLVFacilityHistorical1dayEntry 6 }

endOfLldpTLVFacilityHistorical1dayTable OBJECT-TYPE
    SYNTAX        Integer32
    MAX-ACCESS    read-only
    STATUS        current
    DESCRIPTION   ""
    ::= { pmFacilityDataRecord 312 }

lldpFrameFacilityCurrent15minTable OBJECT-TYPE
    SYNTAX        SEQUENCE OF LldpFrameFacilityCurrent15minEntry
    MAX-ACCESS    not-accessible
    STATUS        current
    DESCRIPTION   ""
    ::= { pmFacilityDataRecord 313 }

lldpFrameFacilityCurrent15minEntry OBJECT-TYPE
    SYNTAX        LldpFrameFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpFrameFacilityCurrent15minTable 1 }

LldpFrameFacilityCurrent15minEntry ::= SEQUENCE
  {    lldpFrameFacilityCurrent15minLLDPFrames Counter64String,
    lldpFrameFacilityCurrent15minLLDPFrameDiscards Counter64String,
    lldpFrameFacilityCurrent15minFrameTxErrors Unsigned32,
    lldpFrameFacilityCurrent15minElapsedTime Integer32 }

lldpFrameFacilityCurrent15minLLDPFrames OBJECT-TYPE
    SYNTAX        Counter64String
    MAX-ACCESS    read-only
    STATUS        current
    DESCRIPTION   "Total LLDP frames observed"
    ::= { lldpFrameFacilityCurrent15minEntry 1 }

lldpFrameFacilityCurrent15minLLDPFrameDiscards OBJECT-TYPE
    SYNTAX        Counter64String
    MAX-ACCESS    read-only
    STATUS        current
    DESCRIPTION   "Total LLDP frames Discarded at specific entity"
    ::= { lldpFrameFacilityCurrent15minEntry 2 }

lldpFrameFacilityCurrent15minFrameTxErrors OBJECT-TYPE
    SYNTAX        Unsigned32
    MAX-ACCESS    read-only
    STATUS        current
    DESCRIPTION   "Total LLDP errored frames"
    ::= { lldpFrameFacilityCurrent15minEntry 3 }

lldpFrameFacilityCurrent15minElapsedTime OBJECT-TYPE
    SYNTAX        Integer32 (0..9000)
    MAX-ACCESS    read-only
    STATUS        current
    DESCRIPTION   "Elapsed 15Min"
    ::= { lldpFrameFacilityCurrent15minEntry 4 }

endOfLldpFrameFacilityCurrent15minTable OBJECT-TYPE
    SYNTAX        Integer32
    MAX-ACCESS    read-only
    STATUS        current
    DESCRIPTION   ""
    ::= { pmFacilityDataRecord 314 }

lldpFrameFacilityCurrent1dayTable OBJECT-TYPE
    SYNTAX        SEQUENCE OF LldpFrameFacilityCurrent1dayEntry
    MAX-ACCESS    not-accessible
    STATUS        current
    DESCRIPTION   ""
    ::= { pmFacilityDataRecord 315 }

lldpFrameFacilityCurrent1dayEntry OBJECT-TYPE
    SYNTAX        LldpFrameFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lldpFrameFacilityCurrent1dayTable 1 }

LldpFrameFacilityCurrent1dayEntry ::= SEQUENCE
  {    lldpFrameFacilityCurrent1dayLLDPFrames Counter64String,
    lldpFrameFacilityCurrent1dayLLDPFrameDiscards Counter64String,
    lldpFrameFacilityCurrent1dayFrameTxErrors Unsigned32,
    lldpFrameFacilityCurrent1dayElapsedTime Integer32 }

lldpFrameFacilityCurrent1dayLLDPFrames OBJECT-TYPE
    SYNTAX        Counter64String
    MAX-ACCESS    read-only
    STATUS        current
    DESCRIPTION   "Total LLDP frames observed"
    ::= { lldpFrameFacilityCurrent1dayEntry 1 }

lldpFrameFacilityCurrent1dayLLDPFrameDiscards OBJECT-TYPE
    SYNTAX        Counter64String
    MAX-ACCESS    read-only
    STATUS        current
    DESCRIPTION   "Total LLDP frames Discarded at specific entity"
    ::= { lldpFrameFacilityCurrent1dayEntry 2 }

lldpFrameFacilityCurrent1dayFrameTxErrors OBJECT-TYPE
    SYNTAX        Unsigned32
    MAX-ACCESS    read-only
    STATUS        current
    DESCRIPTION   "Total LLDP errored frames"
    ::= { lldpFrameFacilityCurrent1dayEntry 3 }

lldpFrameFacilityCurrent1dayElapsedTime OBJECT-TYPE
    SYNTAX        Integer32 (0..86400)
    MAX-ACCESS    read-only
    STATUS        current
    DESCRIPTION   "Elapsed 1Day"
    ::= { lldpFrameFacilityCurrent1dayEntry 4 }

endOfLldpFrameFacilityCurrent1dayTable OBJECT-TYPE
    SYNTAX        Integer32
    MAX-ACCESS    read-only
    STATUS        current
    DESCRIPTION   ""
    ::= { pmFacilityDataRecord 316 }

lldpFrameFacilityHistorical15minTable OBJECT-TYPE
    SYNTAX        SEQUENCE OF LldpFrameFacilityHistorical15minEntry
    MAX-ACCESS    not-accessible
    STATUS        current
    DESCRIPTION   ""
    ::= { pmFacilityDataRecord 317 }

lldpFrameFacilityHistorical15minEntry OBJECT-TYPE
    SYNTAX        LldpFrameFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpFrameFacilityHistorical15minNumber
                }
    ::= { lldpFrameFacilityHistorical15minTable 1 }

LldpFrameFacilityHistorical15minEntry ::= SEQUENCE
  {    lldpFrameFacilityHistorical15minNumber Integer32,
    lldpFrameFacilityHistorical15minLLDPFrames Counter64String,
    lldpFrameFacilityHistorical15minLLDPFrameDiscards Counter64String,
    lldpFrameFacilityHistorical15minFrameTxErrors Unsigned32,
    lldpFrameFacilityHistorical15minValidFlag TruthValue,
    lldpFrameFacilityHistorical15minTimeStamp DateAndTime }

lldpFrameFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lldpFrameFacilityHistorical15minEntry 1 }

lldpFrameFacilityHistorical15minLLDPFrames OBJECT-TYPE
    SYNTAX        Counter64String
    MAX-ACCESS    read-only
    STATUS        current
    DESCRIPTION   "Total LLDP frames observed"
    ::= { lldpFrameFacilityHistorical15minEntry 2 }

lldpFrameFacilityHistorical15minLLDPFrameDiscards OBJECT-TYPE
    SYNTAX        Counter64String
    MAX-ACCESS    read-only
    STATUS        current
    DESCRIPTION   "Total LLDP frames Discarded at specific entity"
    ::= { lldpFrameFacilityHistorical15minEntry 3 }

lldpFrameFacilityHistorical15minFrameTxErrors OBJECT-TYPE
    SYNTAX        Unsigned32
    MAX-ACCESS    read-only
    STATUS        current
    DESCRIPTION   "Total LLDP errored frames"
    ::= { lldpFrameFacilityHistorical15minEntry 4 }

lldpFrameFacilityHistorical15minValidFlag OBJECT-TYPE
    SYNTAX        TruthValue
    MAX-ACCESS    read-only
    STATUS        current
    DESCRIPTION   "Valid Flag"
    ::= { lldpFrameFacilityHistorical15minEntry 5 }

lldpFrameFacilityHistorical15minTimeStamp OBJECT-TYPE
    SYNTAX        DateAndTime
    MAX-ACCESS    read-only
    STATUS        current
    DESCRIPTION   "Timestamp"
    ::= { lldpFrameFacilityHistorical15minEntry 6 }

endOfLldpFrameFacilityHistorical15minTable OBJECT-TYPE
    SYNTAX        Integer32
    MAX-ACCESS    read-only
    STATUS        current
    DESCRIPTION   ""
    ::= { pmFacilityDataRecord 318 }

lldpFrameFacilityHistorical1dayTable OBJECT-TYPE
    SYNTAX        SEQUENCE OF LldpFrameFacilityHistorical1dayEntry
    MAX-ACCESS    not-accessible
    STATUS        current
    DESCRIPTION   ""
    ::= { pmFacilityDataRecord 319 }

lldpFrameFacilityHistorical1dayEntry OBJECT-TYPE
    SYNTAX        LldpFrameFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  lldpFrameFacilityHistorical1dayNumber
                }
    ::= { lldpFrameFacilityHistorical1dayTable 1 }

LldpFrameFacilityHistorical1dayEntry ::= SEQUENCE
  {    lldpFrameFacilityHistorical1dayNumber Integer32,
    lldpFrameFacilityHistorical1dayLLDPFrames Counter64String,
    lldpFrameFacilityHistorical1dayLLDPFrameDiscards Counter64String,
    lldpFrameFacilityHistorical1dayFrameTxErrors Unsigned32,
    lldpFrameFacilityHistorical1dayValidFlag TruthValue,
    lldpFrameFacilityHistorical1dayTimeStamp DateAndTime }

lldpFrameFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lldpFrameFacilityHistorical1dayEntry 1 }

lldpFrameFacilityHistorical1dayLLDPFrames OBJECT-TYPE
    SYNTAX        Counter64String
    MAX-ACCESS    read-only
    STATUS        current
    DESCRIPTION   "Total LLDP frames observed"
    ::= { lldpFrameFacilityHistorical1dayEntry 2 }

lldpFrameFacilityHistorical1dayLLDPFrameDiscards OBJECT-TYPE
    SYNTAX        Counter64String
    MAX-ACCESS    read-only
    STATUS        current
    DESCRIPTION   "Total LLDP frames Discarded at specific entity"
    ::= { lldpFrameFacilityHistorical1dayEntry 3 }

lldpFrameFacilityHistorical1dayFrameTxErrors OBJECT-TYPE
    SYNTAX        Unsigned32
    MAX-ACCESS    read-only
    STATUS        current
    DESCRIPTION   "Total LLDP errored frames"
    ::= { lldpFrameFacilityHistorical1dayEntry 4 }

lldpFrameFacilityHistorical1dayValidFlag OBJECT-TYPE
    SYNTAX        TruthValue
    MAX-ACCESS    read-only
    STATUS        current
    DESCRIPTION   "Valid Flag"
    ::= { lldpFrameFacilityHistorical1dayEntry 5 }

lldpFrameFacilityHistorical1dayTimeStamp OBJECT-TYPE
    SYNTAX        DateAndTime
    MAX-ACCESS    read-only
    STATUS        current
    DESCRIPTION   "Timestamp"
    ::= { lldpFrameFacilityHistorical1dayEntry 6 }

endOfLldpFrameFacilityHistorical1dayTable OBJECT-TYPE
    SYNTAX        Integer32
    MAX-ACCESS    read-only
    STATUS        current
    DESCRIPTION   ""
    ::= { pmFacilityDataRecord 320 }

rsFacilityCurrent15minTable OBJECT-TYPE
    SYNTAX        SEQUENCE OF RsFacilityCurrent15minEntry
    MAX-ACCESS    not-accessible
    STATUS        current
    DESCRIPTION   ""
    ::= { pmFacilityDataRecord 321 }

rsFacilityCurrent15minEntry OBJECT-TYPE
    SYNTAX        RsFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { rsFacilityCurrent15minTable 1 }

RsFacilityCurrent15minEntry ::= SEQUENCE
  {    rsFacilityCurrent15minES Unsigned32,
    rsFacilityCurrent15minSES Unsigned32,
    rsFacilityCurrent15minSEFS Unsigned32,
    rsFacilityCurrent15minOOFS Unsigned32,
    rsFacilityCurrent15minBBE Counter64String,
    rsFacilityCurrent15minElapsedTime Integer32 }

rsFacilityCurrent15minES OBJECT-TYPE
    SYNTAX        Unsigned32
    MAX-ACCESS    read-only
    STATUS        current
    DESCRIPTION   "Section / Regenerator Section Errored Seconds"
    ::= { rsFacilityCurrent15minEntry 1 }

rsFacilityCurrent15minSES OBJECT-TYPE
    SYNTAX        Unsigned32
    MAX-ACCESS    read-only
    STATUS        current
    DESCRIPTION   "Section Severely Errored Seconds"
    ::= { rsFacilityCurrent15minEntry 2 }

rsFacilityCurrent15minSEFS OBJECT-TYPE
    SYNTAX        Unsigned32
    MAX-ACCESS    read-only
    STATUS        current
    DESCRIPTION   "Section Severely Errored Frame Seconds"
    ::= { rsFacilityCurrent15minEntry 3 }

rsFacilityCurrent15minOOFS OBJECT-TYPE
    SYNTAX        Unsigned32
    MAX-ACCESS    read-only
    STATUS        current
    DESCRIPTION   "Section/RS Out-Of-Frame Seconds"
    ::= { rsFacilityCurrent15minEntry 4 }

rsFacilityCurrent15minBBE OBJECT-TYPE
    SYNTAX        Counter64String
    MAX-ACCESS    read-only
    STATUS        current
    DESCRIPTION   "Section/RS Background Block Errors"
    ::= { rsFacilityCurrent15minEntry 5 }

rsFacilityCurrent15minElapsedTime OBJECT-TYPE
    SYNTAX        Integer32 (0..9000)
    MAX-ACCESS    read-only
    STATUS        current
    DESCRIPTION   "Elapsed 15Min"
    ::= { rsFacilityCurrent15minEntry 6 }

endOfRsFacilityCurrent15minTable OBJECT-TYPE
    SYNTAX        Integer32
    MAX-ACCESS    read-only
    STATUS        current
    DESCRIPTION   ""
    ::= { pmFacilityDataRecord 322 }

rsFacilityCurrent1dayTable OBJECT-TYPE
    SYNTAX        SEQUENCE OF RsFacilityCurrent1dayEntry
    MAX-ACCESS    not-accessible
    STATUS        current
    DESCRIPTION   ""
    ::= { pmFacilityDataRecord 323 }

rsFacilityCurrent1dayEntry OBJECT-TYPE
    SYNTAX        RsFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { rsFacilityCurrent1dayTable 1 }

RsFacilityCurrent1dayEntry ::= SEQUENCE
  {    rsFacilityCurrent1dayES Unsigned32,
    rsFacilityCurrent1daySES Unsigned32,
    rsFacilityCurrent1daySEFS Unsigned32,
    rsFacilityCurrent1dayOOFS Unsigned32,
    rsFacilityCurrent1dayBBE Counter64String,
    rsFacilityCurrent1dayElapsedTime Integer32 }

rsFacilityCurrent1dayES OBJECT-TYPE
    SYNTAX        Unsigned32
    MAX-ACCESS    read-only
    STATUS        current
    DESCRIPTION   "Section / Regenerator Section Errored Seconds"
    ::= { rsFacilityCurrent1dayEntry 1 }

rsFacilityCurrent1daySES OBJECT-TYPE
    SYNTAX        Unsigned32
    MAX-ACCESS    read-only
    STATUS        current
    DESCRIPTION   "Section Severely Errored Seconds"
    ::= { rsFacilityCurrent1dayEntry 2 }

rsFacilityCurrent1daySEFS OBJECT-TYPE
    SYNTAX        Unsigned32
    MAX-ACCESS    read-only
    STATUS        current
    DESCRIPTION   "Section Severely Errored Frame Seconds"
    ::= { rsFacilityCurrent1dayEntry 3 }

rsFacilityCurrent1dayOOFS OBJECT-TYPE
    SYNTAX        Unsigned32
    MAX-ACCESS    read-only
    STATUS        current
    DESCRIPTION   "Section/RS Out-Of-Frame Seconds"
    ::= { rsFacilityCurrent1dayEntry 4 }

rsFacilityCurrent1dayBBE OBJECT-TYPE
    SYNTAX        Counter64String
    MAX-ACCESS    read-only
    STATUS        current
    DESCRIPTION   "Section/RS Background Block Errors"
    ::= { rsFacilityCurrent1dayEntry 5 }

rsFacilityCurrent1dayElapsedTime OBJECT-TYPE
    SYNTAX        Integer32 (0..86400)
    MAX-ACCESS    read-only
    STATUS        current
    DESCRIPTION   "Elapsed 1Day"
    ::= { rsFacilityCurrent1dayEntry 6 }

endOfRsFacilityCurrent1dayTable OBJECT-TYPE
    SYNTAX        Integer32
    MAX-ACCESS    read-only
    STATUS        current
    DESCRIPTION   ""
    ::= { pmFacilityDataRecord 324 }

rsFacilityHistorical15minTable OBJECT-TYPE
    SYNTAX        SEQUENCE OF RsFacilityHistorical15minEntry
    MAX-ACCESS    not-accessible
    STATUS        current
    DESCRIPTION   ""
    ::= { pmFacilityDataRecord 325 }

rsFacilityHistorical15minEntry OBJECT-TYPE
    SYNTAX        RsFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  rsFacilityHistorical15minNumber
                }
    ::= { rsFacilityHistorical15minTable 1 }

RsFacilityHistorical15minEntry ::= SEQUENCE
  {    rsFacilityHistorical15minNumber Integer32,
    rsFacilityHistorical15minES Unsigned32,
    rsFacilityHistorical15minSES Unsigned32,
    rsFacilityHistorical15minSEFS Unsigned32,
    rsFacilityHistorical15minOOFS Unsigned32,
    rsFacilityHistorical15minBBE Counter64String,
    rsFacilityHistorical15minValidFlag TruthValue,
    rsFacilityHistorical15minTimeStamp DateAndTime }

rsFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { rsFacilityHistorical15minEntry 1 }

rsFacilityHistorical15minES OBJECT-TYPE
    SYNTAX        Unsigned32
    MAX-ACCESS    read-only
    STATUS        current
    DESCRIPTION   "Section / Regenerator Section Errored Seconds"
    ::= { rsFacilityHistorical15minEntry 2 }

rsFacilityHistorical15minSES OBJECT-TYPE
    SYNTAX        Unsigned32
    MAX-ACCESS    read-only
    STATUS        current
    DESCRIPTION   "Section Severely Errored Seconds"
    ::= { rsFacilityHistorical15minEntry 3 }

rsFacilityHistorical15minSEFS OBJECT-TYPE
    SYNTAX        Unsigned32
    MAX-ACCESS    read-only
    STATUS        current
    DESCRIPTION   "Section Severely Errored Frame Seconds"
    ::= { rsFacilityHistorical15minEntry 4 }

rsFacilityHistorical15minOOFS OBJECT-TYPE
    SYNTAX        Unsigned32
    MAX-ACCESS    read-only
    STATUS        current
    DESCRIPTION   "Section/RS Out-Of-Frame Seconds"
    ::= { rsFacilityHistorical15minEntry 5 }

rsFacilityHistorical15minBBE OBJECT-TYPE
    SYNTAX        Counter64String
    MAX-ACCESS    read-only
    STATUS        current
    DESCRIPTION   "Section/RS Background Block Errors"
    ::= { rsFacilityHistorical15minEntry 6 }

rsFacilityHistorical15minValidFlag OBJECT-TYPE
    SYNTAX        TruthValue
    MAX-ACCESS    read-only
    STATUS        current
    DESCRIPTION   "Valid Flag"
    ::= { rsFacilityHistorical15minEntry 7 }

rsFacilityHistorical15minTimeStamp OBJECT-TYPE
    SYNTAX        DateAndTime
    MAX-ACCESS    read-only
    STATUS        current
    DESCRIPTION   "Timestamp"
    ::= { rsFacilityHistorical15minEntry 8 }

endOfRsFacilityHistorical15minTable OBJECT-TYPE
    SYNTAX        Integer32
    MAX-ACCESS    read-only
    STATUS        current
    DESCRIPTION   ""
    ::= { pmFacilityDataRecord 326 }

rsFacilityHistorical1dayTable OBJECT-TYPE
    SYNTAX        SEQUENCE OF RsFacilityHistorical1dayEntry
    MAX-ACCESS    not-accessible
    STATUS        current
    DESCRIPTION   ""
    ::= { pmFacilityDataRecord 327 }

rsFacilityHistorical1dayEntry OBJECT-TYPE
    SYNTAX        RsFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  rsFacilityHistorical1dayNumber
                }
    ::= { rsFacilityHistorical1dayTable 1 }

RsFacilityHistorical1dayEntry ::= SEQUENCE
  {    rsFacilityHistorical1dayNumber Integer32,
    rsFacilityHistorical1dayES Unsigned32,
    rsFacilityHistorical1daySES Unsigned32,
    rsFacilityHistorical1daySEFS Unsigned32,
    rsFacilityHistorical1dayOOFS Unsigned32,
    rsFacilityHistorical1dayBBE Counter64String,
    rsFacilityHistorical1dayValidFlag TruthValue,
    rsFacilityHistorical1dayTimeStamp DateAndTime }

rsFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { rsFacilityHistorical1dayEntry 1 }

rsFacilityHistorical1dayES OBJECT-TYPE
    SYNTAX        Unsigned32
    MAX-ACCESS    read-only
    STATUS        current
    DESCRIPTION   "Section / Regenerator Section Errored Seconds"
    ::= { rsFacilityHistorical1dayEntry 2 }

rsFacilityHistorical1daySES OBJECT-TYPE
    SYNTAX        Unsigned32
    MAX-ACCESS    read-only
    STATUS        current
    DESCRIPTION   "Section Severely Errored Seconds"
    ::= { rsFacilityHistorical1dayEntry 3 }

rsFacilityHistorical1daySEFS OBJECT-TYPE
    SYNTAX        Unsigned32
    MAX-ACCESS    read-only
    STATUS        current
    DESCRIPTION   "Section Severely Errored Frame Seconds"
    ::= { rsFacilityHistorical1dayEntry 4 }

rsFacilityHistorical1dayOOFS OBJECT-TYPE
    SYNTAX        Unsigned32
    MAX-ACCESS    read-only
    STATUS        current
    DESCRIPTION   "Section/RS Out-Of-Frame Seconds"
    ::= { rsFacilityHistorical1dayEntry 5 }

rsFacilityHistorical1dayBBE OBJECT-TYPE
    SYNTAX        Counter64String
    MAX-ACCESS    read-only
    STATUS        current
    DESCRIPTION   "Section/RS Background Block Errors"
    ::= { rsFacilityHistorical1dayEntry 6 }

rsFacilityHistorical1dayValidFlag OBJECT-TYPE
    SYNTAX        TruthValue
    MAX-ACCESS    read-only
    STATUS        current
    DESCRIPTION   "Valid Flag"
    ::= { rsFacilityHistorical1dayEntry 7 }

rsFacilityHistorical1dayTimeStamp OBJECT-TYPE
    SYNTAX        DateAndTime
    MAX-ACCESS    read-only
    STATUS        current
    DESCRIPTION   "Timestamp"
    ::= { rsFacilityHistorical1dayEntry 8 }

endOfRsFacilityHistorical1dayTable OBJECT-TYPE
    SYNTAX        Integer32
    MAX-ACCESS    read-only
    STATUS        current
    DESCRIPTION   ""
    ::= { pmFacilityDataRecord 328 }

msFacilityCurrent15minTable OBJECT-TYPE
    SYNTAX        SEQUENCE OF MsFacilityCurrent15minEntry
    MAX-ACCESS    not-accessible
    STATUS        current
    DESCRIPTION   ""
    ::= { pmFacilityDataRecord 329 }

msFacilityCurrent15minEntry OBJECT-TYPE
    SYNTAX        MsFacilityCurrent15minEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { msFacilityCurrent15minTable 1 }

MsFacilityCurrent15minEntry ::= SEQUENCE
  {    msFacilityCurrent15minES Unsigned32,
    msFacilityCurrent15minSES Unsigned32,
    msFacilityCurrent15minUAS Unsigned32,
    msFacilityCurrent15minBBE Counter64String,
    msFacilityCurrent15minElapsedTime Integer32 }

msFacilityCurrent15minES OBJECT-TYPE
    SYNTAX        Unsigned32
    MAX-ACCESS    read-only
    STATUS        current
    DESCRIPTION   "Line / Multiplex Section Errored Second"
    ::= { msFacilityCurrent15minEntry 1 }

msFacilityCurrent15minSES OBJECT-TYPE
    SYNTAX        Unsigned32
    MAX-ACCESS    read-only
    STATUS        current
    DESCRIPTION   "Line / Multiplex Section Severely Errored Seconds"
    ::= { msFacilityCurrent15minEntry 2 }

msFacilityCurrent15minUAS OBJECT-TYPE
    SYNTAX        Unsigned32
    MAX-ACCESS    read-only
    STATUS        current
    DESCRIPTION   "Line / Multiplex Section Unavailable Seconds"
    ::= { msFacilityCurrent15minEntry 3 }

msFacilityCurrent15minBBE OBJECT-TYPE
    SYNTAX        Counter64String
    MAX-ACCESS    read-only
    STATUS        current
    DESCRIPTION   "Line/MS BBE Background Block Errors"
    ::= { msFacilityCurrent15minEntry 4 }

msFacilityCurrent15minElapsedTime OBJECT-TYPE
    SYNTAX        Integer32 (0..9000)
    MAX-ACCESS    read-only
    STATUS        current
    DESCRIPTION   "Elapsed 15Min"
    ::= { msFacilityCurrent15minEntry 5 }

endOfMsFacilityCurrent15minTable OBJECT-TYPE
    SYNTAX        Integer32
    MAX-ACCESS    read-only
    STATUS        current
    DESCRIPTION   ""
    ::= { pmFacilityDataRecord 330 }

msFacilityCurrent1dayTable OBJECT-TYPE
    SYNTAX        SEQUENCE OF MsFacilityCurrent1dayEntry
    MAX-ACCESS    not-accessible
    STATUS        current
    DESCRIPTION   ""
    ::= { pmFacilityDataRecord 331 }

msFacilityCurrent1dayEntry OBJECT-TYPE
    SYNTAX        MsFacilityCurrent1dayEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { msFacilityCurrent1dayTable 1 }

MsFacilityCurrent1dayEntry ::= SEQUENCE
  {    msFacilityCurrent1dayES Unsigned32,
    msFacilityCurrent1daySES Unsigned32,
    msFacilityCurrent1dayUAS Unsigned32,
    msFacilityCurrent1dayBBE Counter64String,
    msFacilityCurrent1dayElapsedTime Integer32 }

msFacilityCurrent1dayES OBJECT-TYPE
    SYNTAX        Unsigned32
    MAX-ACCESS    read-only
    STATUS        current
    DESCRIPTION   "Line / Multiplex Section Errored Second"
    ::= { msFacilityCurrent1dayEntry 1 }

msFacilityCurrent1daySES OBJECT-TYPE
    SYNTAX        Unsigned32
    MAX-ACCESS    read-only
    STATUS        current
    DESCRIPTION   "Line / Multiplex Section Severely Errored Seconds"
    ::= { msFacilityCurrent1dayEntry 2 }

msFacilityCurrent1dayUAS OBJECT-TYPE
    SYNTAX        Unsigned32
    MAX-ACCESS    read-only
    STATUS        current
    DESCRIPTION   "Line / Multiplex Section Unavailable Seconds"
    ::= { msFacilityCurrent1dayEntry 3 }

msFacilityCurrent1dayBBE OBJECT-TYPE
    SYNTAX        Counter64String
    MAX-ACCESS    read-only
    STATUS        current
    DESCRIPTION   "Line/MS BBE Background Block Errors"
    ::= { msFacilityCurrent1dayEntry 4 }

msFacilityCurrent1dayElapsedTime OBJECT-TYPE
    SYNTAX        Integer32 (0..86400)
    MAX-ACCESS    read-only
    STATUS        current
    DESCRIPTION   "Elapsed 1Day"
    ::= { msFacilityCurrent1dayEntry 5 }

endOfMsFacilityCurrent1dayTable OBJECT-TYPE
    SYNTAX        Integer32
    MAX-ACCESS    read-only
    STATUS        current
    DESCRIPTION   ""
    ::= { pmFacilityDataRecord 332 }

msFacilityHistorical15minTable OBJECT-TYPE
    SYNTAX        SEQUENCE OF MsFacilityHistorical15minEntry
    MAX-ACCESS    not-accessible
    STATUS        current
    DESCRIPTION   ""
    ::= { pmFacilityDataRecord 333 }

msFacilityHistorical15minEntry OBJECT-TYPE
    SYNTAX        MsFacilityHistorical15minEntry
    MAX-ACCESS    not-accessible
    STATUS        current
    DESCRIPTION   ""
    INDEX       {
                  entityFacilityShelfNo,
                  entityFacilitySlotNo,
                  entityFacilityPortNo,
                  entityFacilityExtNo,
                  entityFacilityClassName,
                  msFacilityHistorical15minNumber
                }
    ::= { msFacilityHistorical15minTable 1 }

MsFacilityHistorical15minEntry ::= SEQUENCE
  {    msFacilityHistorical15minNumber Integer32,
    msFacilityHistorical15minES Unsigned32,
    msFacilityHistorical15minSES Unsigned32,
    msFacilityHistorical15minUAS Unsigned32,
    msFacilityHistorical15minBBE Counter64String,
    msFacilityHistorical15minValidFlag TruthValue,
    msFacilityHistorical15minTimeStamp DateAndTime }

msFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { msFacilityHistorical15minEntry 1 }

msFacilityHistorical15minES OBJECT-TYPE
    SYNTAX        Unsigned32
    MAX-ACCESS    read-only
    STATUS        current
    DESCRIPTION   "Line / Multiplex Section Errored Second"
    ::= { msFacilityHistorical15minEntry 2 }

msFacilityHistorical15minSES OBJECT-TYPE
    SYNTAX        Unsigned32
    MAX-ACCESS    read-only
    STATUS        current
    DESCRIPTION   "Line / Multiplex Section Severely Errored Seconds"
    ::= { msFacilityHistorical15minEntry 3 }

msFacilityHistorical15minUAS OBJECT-TYPE
    SYNTAX        Unsigned32
    MAX-ACCESS    read-only
    STATUS        current
    DESCRIPTION   "Line / Multiplex Section Unavailable Seconds"
    ::= { msFacilityHistorical15minEntry 4 }

msFacilityHistorical15minBBE OBJECT-TYPE
    SYNTAX        Counter64String
    MAX-ACCESS    read-only
    STATUS        current
    DESCRIPTION   "Line/MS BBE Background Block Errors"
    ::= { msFacilityHistorical15minEntry 5 }

msFacilityHistorical15minValidFlag OBJECT-TYPE
    SYNTAX        TruthValue
    MAX-ACCESS    read-only
    STATUS        current
    DESCRIPTION   "Valid Flag"
    ::= { msFacilityHistorical15minEntry 6 }

msFacilityHistorical15minTimeStamp OBJECT-TYPE
    SYNTAX        DateAndTime
    MAX-ACCESS    read-only
    STATUS        current
    DESCRIPTION   "Timestamp"
    ::= { msFacilityHistorical15minEntry 7 }

endOfMsFacilityHistorical15minTable OBJECT-TYPE
    SYNTAX        Integer32
    MAX-ACCESS    read-only
    STATUS        current
    DESCRIPTION   ""
    ::= { pmFacilityDataRecord 334 }

msFacilityHistorical1dayTable OBJECT-TYPE
    SYNTAX        SEQUENCE OF MsFacilityHistorical1dayEntry
    MAX-ACCESS    not-accessible
    STATUS        current
    DESCRIPTION   ""
    ::= { pmFacilityDataRecord 335 }

msFacilityHistorical1dayEntry OBJECT-TYPE
    SYNTAX        MsFacilityHistorical1dayEntry
    MAX-ACCESS    not-accessible
    STATUS        current
    DESCRIPTION   ""
    INDEX       {
                  entityFacilityShelfNo,
                  entityFacilitySlotNo,
                  entityFacilityPortNo,
                  entityFacilityExtNo,
                  entityFacilityClassName,
                  msFacilityHistorical1dayNumber
                }
    ::= { msFacilityHistorical1dayTable 1 }

MsFacilityHistorical1dayEntry ::= SEQUENCE
  {    msFacilityHistorical1dayNumber Integer32,
    msFacilityHistorical1dayES Unsigned32,
    msFacilityHistorical1daySES Unsigned32,
    msFacilityHistorical1dayUAS Unsigned32,
    msFacilityHistorical1dayBBE Counter64String,
    msFacilityHistorical1dayValidFlag TruthValue,
    msFacilityHistorical1dayTimeStamp DateAndTime }

msFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { msFacilityHistorical1dayEntry 1 }

msFacilityHistorical1dayES OBJECT-TYPE
    SYNTAX        Unsigned32
    MAX-ACCESS    read-only
    STATUS        current
    DESCRIPTION   "Line / Multiplex Section Errored Second"
    ::= { msFacilityHistorical1dayEntry 2 }

msFacilityHistorical1daySES OBJECT-TYPE
    SYNTAX        Unsigned32
    MAX-ACCESS    read-only
    STATUS        current
    DESCRIPTION   "Line / Multiplex Section Severely Errored Seconds"
    ::= { msFacilityHistorical1dayEntry 3 }

msFacilityHistorical1dayUAS OBJECT-TYPE
    SYNTAX        Unsigned32
    MAX-ACCESS    read-only
    STATUS        current
    DESCRIPTION   "Line / Multiplex Section Unavailable Seconds"
    ::= { msFacilityHistorical1dayEntry 4 }

msFacilityHistorical1dayBBE OBJECT-TYPE
    SYNTAX        Counter64String
    MAX-ACCESS    read-only
    STATUS        current
    DESCRIPTION   "Line/MS BBE Background Block Errors"
    ::= { msFacilityHistorical1dayEntry 5 }

msFacilityHistorical1dayValidFlag OBJECT-TYPE
    SYNTAX        TruthValue
    MAX-ACCESS    read-only
    STATUS        current
    DESCRIPTION   "Valid Flag"
    ::= { msFacilityHistorical1dayEntry 6 }

msFacilityHistorical1dayTimeStamp OBJECT-TYPE
    SYNTAX        DateAndTime
    MAX-ACCESS    read-only
    STATUS        current
    DESCRIPTION   "Timestamp"
    ::= { msFacilityHistorical1dayEntry 7 }

endOfMsFacilityHistorical1dayTable OBJECT-TYPE
    SYNTAX        Integer32
    MAX-ACCESS    read-only
    STATUS        current
    DESCRIPTION   ""
    ::= { pmFacilityDataRecord 336 }

endOfPmFacilityDataRecord OBJECT-TYPE
    SYNTAX        Integer32
    MAX-ACCESS    read-only
    STATUS        current
    DESCRIPTION   ""
    ::= { pmFacilityDataRecord 10000 }

facilityDataInstValueTable OBJECT-TYPE
    SYNTAX        SEQUENCE OF FacilityDataInstValueEntry
    MAX-ACCESS    not-accessible
    STATUS        current
    DESCRIPTION   ""
    ::= { pmFacilityDataValue 1 }

facilityDataInstValueEntry OBJECT-TYPE
    SYNTAX        FacilityDataInstValueEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { facilityDataInstValueTable 1 }

FacilityDataInstValueEntry ::= SEQUENCE
  {    facilityDataInstValueUtilizationRx Unsigned32,
    facilityDataInstValueUtilizationTx Unsigned32 }

facilityDataInstValueUtilizationRx OBJECT-TYPE
    SYNTAX        Unsigned32
    UNITS         "%"
    MAX-ACCESS    read-only
    STATUS        current
    DESCRIPTION   "Utilization Receive"
    ::= { facilityDataInstValueEntry 1 }

facilityDataInstValueUtilizationTx OBJECT-TYPE
    SYNTAX        Unsigned32
    UNITS         "%"
    MAX-ACCESS    read-only
    STATUS        current
    DESCRIPTION   "Utilization Transmit"
    ::= { facilityDataInstValueEntry 2 }

endOfFacilityDataInstValueTable OBJECT-TYPE
    SYNTAX        Integer32
    MAX-ACCESS    read-only
    STATUS        current
    DESCRIPTION   ""
    ::= { pmFacilityDataValue 2 }

endOfPmFacilityDataValue OBJECT-TYPE
    SYNTAX        Integer32
    MAX-ACCESS    read-only
    STATUS        current
    DESCRIPTION   ""
    ::= { pmFacilityDataValue 10000 }

facilityPhysInstValueTable OBJECT-TYPE
    SYNTAX        SEQUENCE OF FacilityPhysInstValueEntry
    MAX-ACCESS    not-accessible
    STATUS        current
    DESCRIPTION   ""
    ::= { pmFacilityPhysValue 1 }

facilityPhysInstValueEntry OBJECT-TYPE
    SYNTAX        FacilityPhysInstValueEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { facilityPhysInstValueTable 1 }

FacilityPhysInstValueEntry ::= SEQUENCE
  {    facilityPhysInstValueOutputPower Integer32,
    facilityPhysInstValueInputPower Integer32,
    facilityPhysInstValueLaserTemp Integer32,
    facilityPhysInstValueLaserBiasCurrentLevel Unsigned32,
    facilityPhysInstValuePrbsMaxBER Counter64String,
    facilityPhysInstValueAttenuationOfVoa Unsigned32,
    facilityPhysInstValueLocalOscTemp Integer32,
    facilityPhysInstValuePrbsElapsedTime Unsigned32,
    facilityPhysInstValueLocalOscBiasLevel Unsigned32,
    facilityPhysInstValuePrbsErrorFreeTime Unsigned32,
    facilityPhysInstValuePrbsAvgBER Counter64String,
    facilityPhysInstValueLogicalLanesSkew Integer32,
    facilityPhysInstValueRoundTripDelay Unsigned32,
    facilityPhysInstValueSignalToNoiseRatio Integer32,
    facilityPhysInstValueCarrierFreqOffset Integer32,
    facilityPhysInstValueLatency Unsigned32,
    facilityPhysInstValueDifferentialGroupDelay Integer32,
    facilityPhysInstValueLaserBiasCurrentNormalized Unsigned32,
    facilityPhysInstValueChromaticDispersion Integer32,
    facilityPhysInstValueChromaticDispComp Integer32,
    facilityPhysInstValueCalculatedTotalPower Integer32,
    facilityPhysInstValueCalculatedTotalPowerTx Integer32,
    facilityPhysInstValueQualityFactor Integer32,
    facilityPhysInstValueOutputPowerRaw Integer32,
    facilityPhysInstValueInputPowerRaw Integer32,
    facilityPhysInstValueDelayFrames Unsigned32,
    facilityPhysInstValueDelayTime Unsigned32 }

facilityPhysInstValueOutputPower OBJECT-TYPE
    SYNTAX        Integer32
    UNITS         "0.1 dBm"
    MAX-ACCESS    read-only
    STATUS        current
    DESCRIPTION   "Instantaneous Optical Power Transmitted (Output)"
    ::= { facilityPhysInstValueEntry 1 }

facilityPhysInstValueInputPower OBJECT-TYPE
    SYNTAX        Integer32
    UNITS         "0.1 dBm"
    MAX-ACCESS    read-only
    STATUS        current
    DESCRIPTION   "Total Optical Input Power Received"
    ::= { facilityPhysInstValueEntry 2 }

facilityPhysInstValueLaserTemp OBJECT-TYPE
    SYNTAX        Integer32
    UNITS         "0.1 degree Celsius"
    MAX-ACCESS    read-only
    STATUS        current
    DESCRIPTION   "Laser Temperature"
    ::= { facilityPhysInstValueEntry 3 }

facilityPhysInstValueLaserBiasCurrentLevel OBJECT-TYPE
    SYNTAX        Unsigned32
    UNITS         "0.001 A"
    MAX-ACCESS    read-only
    STATUS        current
    DESCRIPTION   "Laser Bias Current Level on demand"
    ::= { facilityPhysInstValueEntry 4 }

facilityPhysInstValuePrbsMaxBER OBJECT-TYPE
    SYNTAX        Counter64String
    UNITS         "1.0E-15"
    MAX-ACCESS    read-only
    STATUS        current
    DESCRIPTION   "Maximum measured BER for the PRBS Test signal during monitored time"
    ::= { facilityPhysInstValueEntry 5 }

facilityPhysInstValueAttenuationOfVoa OBJECT-TYPE
    SYNTAX        Unsigned32
    UNITS         "0.1 dB"
    MAX-ACCESS    read-only
    STATUS        current
    DESCRIPTION   "Variable Attenuator attenuation in dB"
    ::= { facilityPhysInstValueEntry 6 }

facilityPhysInstValueLocalOscTemp OBJECT-TYPE
    SYNTAX        Integer32
    UNITS         "0.1 degree Celsius"
    MAX-ACCESS    read-only
    STATUS        current
    DESCRIPTION   "Instantaneous Rx Laser Temperature (used for  Local Oscillator)"
    ::= { facilityPhysInstValueEntry 7 }

facilityPhysInstValuePrbsElapsedTime OBJECT-TYPE
    SYNTAX        Unsigned32
    UNITS         "s"
    MAX-ACCESS    read-only
    STATUS        current
    DESCRIPTION   "Time elapsed since  PRBS test monitoring started - reset"
    ::= { facilityPhysInstValueEntry 8 }

facilityPhysInstValueLocalOscBiasLevel OBJECT-TYPE
    SYNTAX        Unsigned32
    UNITS         "0.001 A"
    MAX-ACCESS    read-only
    STATUS        current
    DESCRIPTION   "Rx Laser Bias Current Level used for Local Oscillator"
    ::= { facilityPhysInstValueEntry 9 }

facilityPhysInstValuePrbsErrorFreeTime OBJECT-TYPE
    SYNTAX        Unsigned32
    UNITS         "s"
    MAX-ACCESS    read-only
    STATUS        current
    DESCRIPTION   "Time elapsed since last PRBS Error detected"
    ::= { facilityPhysInstValueEntry 10 }

facilityPhysInstValuePrbsAvgBER OBJECT-TYPE
    SYNTAX        Counter64String
    UNITS         "1.0E-15"
    MAX-ACCESS    read-only
    STATUS        current
    DESCRIPTION   "Average BER for the PRBS test signal during the monitored time"
    ::= { facilityPhysInstValueEntry 11 }

facilityPhysInstValueLogicalLanesSkew OBJECT-TYPE
    SYNTAX        Integer32
    UNITS         "ns"
    MAX-ACCESS    read-only
    STATUS        current
    DESCRIPTION   "Skew between logical lanes farthest apart"
    ::= { facilityPhysInstValueEntry 12 }

facilityPhysInstValueRoundTripDelay OBJECT-TYPE
    SYNTAX        Unsigned32 (0..30000000)
    UNITS         "ns"
    MAX-ACCESS    read-only
    STATUS        current
    DESCRIPTION   "Measured round trip delay"
    ::= { facilityPhysInstValueEntry 13 }

facilityPhysInstValueSignalToNoiseRatio OBJECT-TYPE
    SYNTAX        Integer32
    UNITS         "0.1 dB"
    MAX-ACCESS    read-only
    STATUS        current
    DESCRIPTION   "Signal-to-Noise Ratio measured by the module"
    ::= { facilityPhysInstValueEntry 14 }

facilityPhysInstValueCarrierFreqOffset OBJECT-TYPE
    SYNTAX        Integer32
    UNITS         "0.001 GHz"
    MAX-ACCESS    read-only
    STATUS        current
    DESCRIPTION   "Carrier Frequency Offset"
    ::= { facilityPhysInstValueEntry 15 }

facilityPhysInstValueLatency OBJECT-TYPE
    SYNTAX        Unsigned32 (0..300000)
    UNITS         "0.1 us"
    MAX-ACCESS    read-only
    STATUS        current
    DESCRIPTION   "Measured round trip delay"
    ::= { facilityPhysInstValueEntry 16 }

facilityPhysInstValueDifferentialGroupDelay OBJECT-TYPE
    SYNTAX        Integer32
    UNITS         "ps"
    MAX-ACCESS    read-only
    STATUS        current
    DESCRIPTION   "Differential Group Delay measured and compensated by the module"
    ::= { facilityPhysInstValueEntry 17 }

facilityPhysInstValueLaserBiasCurrentNormalized OBJECT-TYPE
    SYNTAX        Unsigned32
    UNITS         "%"
    MAX-ACCESS    read-only
    STATUS        current
    DESCRIPTION   "Instantaneous Laser Bias Current Normalized"
    ::= { facilityPhysInstValueEntry 18 }

facilityPhysInstValueChromaticDispersion OBJECT-TYPE
    SYNTAX        Integer32
    UNITS         "ps/nm"
    MAX-ACCESS    read-only
    STATUS        current
    DESCRIPTION   "Chromatic Dispersion Compensation"
    ::= { facilityPhysInstValueEntry 19 }

facilityPhysInstValueChromaticDispComp OBJECT-TYPE
    SYNTAX        Integer32
    UNITS         "ps/nm"
    MAX-ACCESS    read-only
    STATUS        current
    DESCRIPTION   "Chromatic Dispersion Compensation"
    ::= { facilityPhysInstValueEntry 20 }

facilityPhysInstValueCalculatedTotalPower OBJECT-TYPE
    SYNTAX        Integer32
    UNITS         "0.1 dBm"
    MAX-ACCESS    read-only
    STATUS        current
    DESCRIPTION   "Calculated OPR"
    ::= { facilityPhysInstValueEntry 21 }

facilityPhysInstValueCalculatedTotalPowerTx OBJECT-TYPE
    SYNTAX        Integer32
    UNITS         "0.1 dBm"
    MAX-ACCESS    read-only
    STATUS        current
    DESCRIPTION   "Calculated Optical Power Transmitted"
    ::= { facilityPhysInstValueEntry 22 }

facilityPhysInstValueQualityFactor OBJECT-TYPE
    SYNTAX        Integer32
    UNITS         "0.1 dB"
    MAX-ACCESS    read-only
    STATUS        current
    DESCRIPTION   "Quality Factor"
    ::= { facilityPhysInstValueEntry 23 }

facilityPhysInstValueOutputPowerRaw OBJECT-TYPE
    SYNTAX        Integer32
    UNITS         "0.1 dBm"
    MAX-ACCESS    read-only
    STATUS        current
    DESCRIPTION   "Raw Optical Power Transmitted (Output)"
    ::= { facilityPhysInstValueEntry 24 }

facilityPhysInstValueInputPowerRaw OBJECT-TYPE
    SYNTAX        Integer32
    UNITS         "0.1 dBm"
    MAX-ACCESS    read-only
    STATUS        current
    DESCRIPTION   "Raw Optical Power Received (Input)"
    ::= { facilityPhysInstValueEntry 25 }

facilityPhysInstValueDelayFrames OBJECT-TYPE
    SYNTAX        Unsigned32
    UNITS         "Frames"
    MAX-ACCESS    read-only
    STATUS        current
    DESCRIPTION   "Delay Measurement in Frames; frames before the delay indication is returned"
    ::= { facilityPhysInstValueEntry 26 }

facilityPhysInstValueDelayTime OBJECT-TYPE
    SYNTAX        Unsigned32
    UNITS         "0.1 us"
    MAX-ACCESS    read-only
    STATUS        current
    DESCRIPTION   "Delay measurement time; delay in frame translated into time"
    ::= { facilityPhysInstValueEntry 27 }

endOfFacilityPhysInstValueTable OBJECT-TYPE
    SYNTAX        Integer32
    MAX-ACCESS    read-only
    STATUS        current
    DESCRIPTION   ""
    ::= { pmFacilityPhysValue 2 }

endOfPmFacilityPhysValue OBJECT-TYPE
    SYNTAX        Integer32
    MAX-ACCESS    read-only
    STATUS        current
    DESCRIPTION   ""
    ::= { pmFacilityPhysValue 10000 }

facilityPhysThresholdTable OBJECT-TYPE
    SYNTAX        SEQUENCE OF FacilityPhysThresholdEntry
    MAX-ACCESS    not-accessible
    STATUS        current
    DESCRIPTION   ""
    ::= { pmFacilityPhysThreshold 1 }

facilityPhysThresholdEntry OBJECT-TYPE
    SYNTAX        FacilityPhysThresholdEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { facilityPhysThresholdTable 1 }

FacilityPhysThresholdEntry ::= SEQUENCE
  {    facilityPhysThresholdOpticalInputPwrLow Integer32,
    facilityPhysThresholdOpticalInputPwrHigh Integer32,
    facilityPhysThresholdConfigOpticalOutputPwrLow Integer32,
    facilityPhysThresholdConfigOpticalOutputPwrHigh Integer32,
    facilityPhysThresholdOpticalOutputPwrHigh Integer32,
    facilityPhysThresholdOpticalOutputPwrLow Integer32,
    facilityPhysThresholdLaserTempHighThres Integer32,
    facilityPhysThresholdLaserTempLowThres Integer32,
    facilityPhysThresholdRoundTripDelayLowThres Integer32,
    facilityPhysThresholdRoundTripDelayHighThres Integer32,
    facilityPhysThresholdLatencyLowThres Integer32,
    facilityPhysThresholdLatencyHighThres Integer32,
    facilityPhysThresholdChromaticDispersionHigh Integer32,
    facilityPhysThresholdChromaticDispersionLow Integer32,
    facilityPhysThresholdCarrierFreqOffsetLow Integer32,
    facilityPhysThresholdCarrierFreqOffsetHigh Integer32,
    facilityPhysThresholdDispersionCompensationLowThres Integer32,
    facilityPhysThresholdDispersionCompensationHighThres Integer32,
    facilityPhysThresholdDifferentialGroupDelayHigh Integer32,
    facilityPhysThresholdLogicalLanesSkewHigh Integer32,
    facilityPhysThresholdLaserBiasCurrentNormalized Unsigned32,
    facilityPhysThresholdLocalOscTempLowThres Integer32,
    facilityPhysThresholdLocalOscTempHighThres Integer32,
    facilityPhysThresholdSignalToNoiseRatioLow Integer32,
    facilityPhysThresholdQualityFactorLowThres Integer32 }

facilityPhysThresholdOpticalInputPwrLow OBJECT-TYPE
    SYNTAX        Integer32 (-450..260)
    UNITS         "0.1 dBm"
    MAX-ACCESS    read-write
    STATUS        current
    DESCRIPTION   "Optical Input Power Received"
    ::= { facilityPhysThresholdEntry 1 }

facilityPhysThresholdOpticalInputPwrHigh OBJECT-TYPE
    SYNTAX        Integer32 (-450..270)
    UNITS         "0.1 dBm"
    MAX-ACCESS    read-write
    STATUS        current
    DESCRIPTION   "Optical Input Power Received"
    ::= { facilityPhysThresholdEntry 2 }

facilityPhysThresholdConfigOpticalOutputPwrLow OBJECT-TYPE
    SYNTAX        Integer32 (-500..300)
    UNITS         "0.1 dBm"
    MAX-ACCESS    read-write
    STATUS        current
    DESCRIPTION   "Configurable threshold of the Optical Power Transmitted (output)"
    ::= { facilityPhysThresholdEntry 3 }

facilityPhysThresholdConfigOpticalOutputPwrHigh OBJECT-TYPE
    SYNTAX        Integer32 (-500..300)
    UNITS         "0.1 dBm"
    MAX-ACCESS    read-write
    STATUS        current
    DESCRIPTION   "Configurable high threshold of the Optical Power Transmitted (output)"
    ::= { facilityPhysThresholdEntry 4 }

facilityPhysThresholdOpticalOutputPwrHigh OBJECT-TYPE
    SYNTAX        Integer32
    UNITS         "0.1 dBm"
    MAX-ACCESS    read-only
    STATUS        current
    DESCRIPTION   "High fixed threshold of the Optical Power Transmitted (output)"
    ::= { facilityPhysThresholdEntry 5 }

facilityPhysThresholdOpticalOutputPwrLow OBJECT-TYPE
    SYNTAX        Integer32
    UNITS         "0.1 dBm"
    MAX-ACCESS    read-only
    STATUS        current
    DESCRIPTION   "Low fixed threshold of the Optical Power Transmitted (output)"
    ::= { facilityPhysThresholdEntry 6 }

facilityPhysThresholdLaserTempHighThres OBJECT-TYPE
    SYNTAX        Integer32
    UNITS         "0.1 degree Celsius"
    MAX-ACCESS    read-only
    STATUS        current
    DESCRIPTION   "Laser temperature fixed high threshold."
    ::= { facilityPhysThresholdEntry 7 }

facilityPhysThresholdLaserTempLowThres OBJECT-TYPE
    SYNTAX        Integer32
    UNITS         "0.1 degree Celsius"
    MAX-ACCESS    read-only
    STATUS        current
    DESCRIPTION   "Laser temperature fixed low threshold."
    ::= { facilityPhysThresholdEntry 8 }

facilityPhysThresholdRoundTripDelayLowThres OBJECT-TYPE
    SYNTAX        Integer32 (0..30000000)
    UNITS         "ns"
    MAX-ACCESS    read-write
    STATUS        current
    DESCRIPTION   "Configurable low threshold for round trip delay"
    ::= { facilityPhysThresholdEntry 9 }

facilityPhysThresholdRoundTripDelayHighThres OBJECT-TYPE
    SYNTAX        Integer32 (1..30000000)
    UNITS         "ns"
    MAX-ACCESS    read-write
    STATUS        current
    DESCRIPTION   "Configurable high threshold for round trip delay"
    ::= { facilityPhysThresholdEntry 10 }

facilityPhysThresholdLatencyLowThres OBJECT-TYPE
    SYNTAX        Integer32 (0..300000)
    UNITS         "0.1 us"
    MAX-ACCESS    read-write
    STATUS        current
    DESCRIPTION   "Configurable low threshold round trip delay"
    ::= { facilityPhysThresholdEntry 11 }

facilityPhysThresholdLatencyHighThres OBJECT-TYPE
    SYNTAX        Integer32 (1..300000)
    UNITS         "0.1 us"
    MAX-ACCESS    read-write
    STATUS        current
    DESCRIPTION   "Configurable high threshold for round trip delay"
    ::= { facilityPhysThresholdEntry 12 }

facilityPhysThresholdChromaticDispersionHigh OBJECT-TYPE
    SYNTAX        Integer32 (-100000..100000)
    UNITS         "ps/nm"
    MAX-ACCESS    read-write
    STATUS        current
    DESCRIPTION   "Chromatic Dispersion Compensation High Threshold"
    ::= { facilityPhysThresholdEntry 13 }

facilityPhysThresholdChromaticDispersionLow OBJECT-TYPE
    SYNTAX        Integer32 (-100000..100000)
    UNITS         "ps/nm"
    MAX-ACCESS    read-write
    STATUS        current
    DESCRIPTION   "Chromatic Dispersion Compensation Low Threshold"
    ::= { facilityPhysThresholdEntry 14 }

facilityPhysThresholdCarrierFreqOffsetLow OBJECT-TYPE
    SYNTAX        Integer32 (-32000..32000)
    UNITS         "0.001 GHz"
    MAX-ACCESS    read-write
    STATUS        current
    DESCRIPTION   "Carrier Frequency Offset Low TH"
    ::= { facilityPhysThresholdEntry 15 }

facilityPhysThresholdCarrierFreqOffsetHigh OBJECT-TYPE
    SYNTAX        Integer32 (-32000..32000)
    UNITS         "0.001 GHz"
    MAX-ACCESS    read-write
    STATUS        current
    DESCRIPTION   "Carrier Frequency Offset High TH"
    ::= { facilityPhysThresholdEntry 16 }

facilityPhysThresholdDispersionCompensationLowThres OBJECT-TYPE
    SYNTAX        Integer32 (-50000..50000)
    UNITS         "ps/nm"
    MAX-ACCESS    read-write
    STATUS        current
    DESCRIPTION   "Chromatic Dispersion Compensation Low Threshold"
    ::= { facilityPhysThresholdEntry 17 }

facilityPhysThresholdDispersionCompensationHighThres OBJECT-TYPE
    SYNTAX        Integer32 (-50000..50000)
    UNITS         "ps/nm"
    MAX-ACCESS    read-write
    STATUS        current
    DESCRIPTION   "Chromatic Dispersion Compensation High Threshold"
    ::= { facilityPhysThresholdEntry 18 }

facilityPhysThresholdDifferentialGroupDelayHigh OBJECT-TYPE
    SYNTAX        Integer32 (0..100)
    UNITS         "ps"
    MAX-ACCESS    read-write
    STATUS        current
    DESCRIPTION   "Differential Group Delay High TH"
    ::= { facilityPhysThresholdEntry 19 }

facilityPhysThresholdLogicalLanesSkewHigh OBJECT-TYPE
    SYNTAX        Integer32 (0..1000)
    UNITS         "ns"
    MAX-ACCESS    read-write
    STATUS        current
    DESCRIPTION   "Skew between logical lanes farthest apart high threshold"
    ::= { facilityPhysThresholdEntry 20 }

facilityPhysThresholdLaserBiasCurrentNormalized OBJECT-TYPE
    SYNTAX        Unsigned32
    UNITS         "%"
    MAX-ACCESS    read-only
    STATUS        current
    DESCRIPTION   "Laser Bias Current Normalized Fixed High Threshold."
    ::= { facilityPhysThresholdEntry 21 }

facilityPhysThresholdLocalOscTempLowThres OBJECT-TYPE
    SYNTAX        Integer32
    UNITS         "0.1 degree Celsius"
    MAX-ACCESS    read-only
    STATUS        current
    DESCRIPTION   "Rx Laser unsed for Local Oscillator Temperature Fixed Low Threshold"
    ::= { facilityPhysThresholdEntry 22 }

facilityPhysThresholdLocalOscTempHighThres OBJECT-TYPE
    SYNTAX        Integer32
    UNITS         "0.1 degree Celsius"
    MAX-ACCESS    read-only
    STATUS        current
    DESCRIPTION   "Rx Laser used for Local Oscillator Temperature Fixed High Threshold"
    ::= { facilityPhysThresholdEntry 23 }

facilityPhysThresholdSignalToNoiseRatioLow OBJECT-TYPE
    SYNTAX        Integer32 (70..240)
    UNITS         "0.1 dB"
    MAX-ACCESS    read-write
    STATUS        current
    DESCRIPTION   "Signal-to-Noise Ratio Low TH"
    ::= { facilityPhysThresholdEntry 24 }

facilityPhysThresholdQualityFactorLowThres OBJECT-TYPE
    SYNTAX        Integer32 (0..600)
    UNITS         "0.1 dB"
    MAX-ACCESS    read-write
    STATUS        current
    DESCRIPTION   "Quality Factor Low TH"
    ::= { facilityPhysThresholdEntry 25 }

endOfFacilityPhysThresholdTable OBJECT-TYPE
    SYNTAX        Integer32
    MAX-ACCESS    read-only
    STATUS        current
    DESCRIPTION   ""
    ::= { pmFacilityPhysThreshold 2 }

endOfPmFacilityPhysThreshold OBJECT-TYPE
    SYNTAX        Integer32
    MAX-ACCESS    read-only
    STATUS        current
    DESCRIPTION   ""
    ::= { pmFacilityPhysThreshold 10000 }

optFacilityHistorical15minTable OBJECT-TYPE
    SYNTAX        SEQUENCE OF OptFacilityHistorical15minEntry
    MAX-ACCESS    not-accessible
    STATUS        current
    DESCRIPTION   ""
    ::= { pmFacilityPhysRecord 1 }

optFacilityHistorical15minEntry OBJECT-TYPE
    SYNTAX        OptFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  optFacilityHistorical15minNumber
                }
    ::= { optFacilityHistorical15minTable 1 }

OptFacilityHistorical15minEntry ::= SEQUENCE
  {    optFacilityHistorical15minNumber Integer32,
    optFacilityHistorical15minLow Integer32,
    optFacilityHistorical15minMean Integer32,
    optFacilityHistorical15minHigh Integer32,
    optFacilityHistorical15minValidFlag TruthValue,
    optFacilityHistorical15minTimeStamp DateAndTime }

optFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { optFacilityHistorical15minEntry 1 }

optFacilityHistorical15minLow OBJECT-TYPE
    SYNTAX        Integer32
    UNITS         "0.1 dBm"
    MAX-ACCESS    read-only
    STATUS        current
    DESCRIPTION   "Optical Output Power Transmitted"
    ::= { optFacilityHistorical15minEntry 2 }

optFacilityHistorical15minMean OBJECT-TYPE
    SYNTAX        Integer32
    UNITS         "0.1 dBm"
    MAX-ACCESS    read-only
    STATUS        current
    DESCRIPTION   "Optical Output Power Transmitted"
    ::= { optFacilityHistorical15minEntry 3 }

optFacilityHistorical15minHigh OBJECT-TYPE
    SYNTAX        Integer32
    UNITS         "0.1 dBm"
    MAX-ACCESS    read-only
    STATUS        current
    DESCRIPTION   "Optical Output Power Transmitted"
    ::= { optFacilityHistorical15minEntry 4 }

optFacilityHistorical15minValidFlag OBJECT-TYPE
    SYNTAX        TruthValue
    MAX-ACCESS    read-only
    STATUS        current
    DESCRIPTION   "Valid Flag"
    ::= { optFacilityHistorical15minEntry 5 }

optFacilityHistorical15minTimeStamp OBJECT-TYPE
    SYNTAX        DateAndTime
    MAX-ACCESS    read-only
    STATUS        current
    DESCRIPTION   "Timestamp"
    ::= { optFacilityHistorical15minEntry 6 }

endOfOptFacilityHistorical15minTable OBJECT-TYPE
    SYNTAX        Integer32
    MAX-ACCESS    read-only
    STATUS        current
    DESCRIPTION   ""
    ::= { pmFacilityPhysRecord 2 }

optFacilityHistorical1dayTable OBJECT-TYPE
    SYNTAX        SEQUENCE OF OptFacilityHistorical1dayEntry
    MAX-ACCESS    not-accessible
    STATUS        current
    DESCRIPTION   ""
    ::= { pmFacilityPhysRecord 3 }

optFacilityHistorical1dayEntry OBJECT-TYPE
    SYNTAX        OptFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  optFacilityHistorical1dayNumber
                }
    ::= { optFacilityHistorical1dayTable 1 }

OptFacilityHistorical1dayEntry ::= SEQUENCE
  {    optFacilityHistorical1dayNumber Integer32,
    optFacilityHistorical1dayLow Integer32,
    optFacilityHistorical1dayMean Integer32,
    optFacilityHistorical1dayHigh Integer32,
    optFacilityHistorical1dayValidFlag TruthValue,
    optFacilityHistorical1dayTimeStamp DateAndTime }

optFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { optFacilityHistorical1dayEntry 1 }

optFacilityHistorical1dayLow OBJECT-TYPE
    SYNTAX        Integer32
    UNITS         "0.1 dBm"
    MAX-ACCESS    read-only
    STATUS        current
    DESCRIPTION   "Optical Output Power Transmitted"
    ::= { optFacilityHistorical1dayEntry 2 }

optFacilityHistorical1dayMean OBJECT-TYPE
    SYNTAX        Integer32
    UNITS         "0.1 dBm"
    MAX-ACCESS    read-only
    STATUS        current
    DESCRIPTION   "Optical Output Power Transmitted"
    ::= { optFacilityHistorical1dayEntry 3 }

optFacilityHistorical1dayHigh OBJECT-TYPE
    SYNTAX        Integer32
    UNITS         "0.1 dBm"
    MAX-ACCESS    read-only
    STATUS        current
    DESCRIPTION   "Optical Output Power Transmitted"
    ::= { optFacilityHistorical1dayEntry 4 }

optFacilityHistorical1dayValidFlag OBJECT-TYPE
    SYNTAX        TruthValue
    MAX-ACCESS    read-only
    STATUS        current
    DESCRIPTION   "Valid Flag"
    ::= { optFacilityHistorical1dayEntry 5 }

optFacilityHistorical1dayTimeStamp OBJECT-TYPE
    SYNTAX        DateAndTime
    MAX-ACCESS    read-only
    STATUS        current
    DESCRIPTION   "Timestamp"
    ::= { optFacilityHistorical1dayEntry 6 }

endOfOptFacilityHistorical1dayTable OBJECT-TYPE
    SYNTAX        Integer32
    MAX-ACCESS    read-only
    STATUS        current
    DESCRIPTION   ""
    ::= { pmFacilityPhysRecord 4 }

optFacilityHistorical1weekTable OBJECT-TYPE
    SYNTAX        SEQUENCE OF OptFacilityHistorical1weekEntry
    MAX-ACCESS    not-accessible
    STATUS        current
    DESCRIPTION   ""
    ::= { pmFacilityPhysRecord 5 }

optFacilityHistorical1weekEntry OBJECT-TYPE
    SYNTAX        OptFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  optFacilityHistorical1weekNumber
                }
    ::= { optFacilityHistorical1weekTable 1 }

OptFacilityHistorical1weekEntry ::= SEQUENCE
  {    optFacilityHistorical1weekNumber Integer32,
    optFacilityHistorical1weekLow Integer32,
    optFacilityHistorical1weekMean Integer32,
    optFacilityHistorical1weekHigh Integer32,
    optFacilityHistorical1weekValidFlag TruthValue,
    optFacilityHistorical1weekTimeStamp DateAndTime }

optFacilityHistorical1weekNumber OBJECT-TYPE
    SYNTAX        Integer32 (1..52)
    MAX-ACCESS    not-accessible
    STATUS        current
    DESCRIPTION   "Number 1week"
    ::= { optFacilityHistorical1weekEntry 1 }

optFacilityHistorical1weekLow OBJECT-TYPE
    SYNTAX        Integer32
    UNITS         "0.1 dBm"
    MAX-ACCESS    read-only
    STATUS        current
    DESCRIPTION   "Optical Output Power Transmitted"
    ::= { optFacilityHistorical1weekEntry 2 }

optFacilityHistorical1weekMean OBJECT-TYPE
    SYNTAX        Integer32
    UNITS         "0.1 dBm"
    MAX-ACCESS    read-only
    STATUS        current
    DESCRIPTION   "Optical Output Power Transmitted"
    ::= { optFacilityHistorical1weekEntry 3 }

optFacilityHistorical1weekHigh OBJECT-TYPE
    SYNTAX        Integer32
    UNITS         "0.1 dBm"
    MAX-ACCESS    read-only
    STATUS        current
    DESCRIPTION   "Optical Output Power Transmitted"
    ::= { optFacilityHistorical1weekEntry 4 }

optFacilityHistorical1weekValidFlag OBJECT-TYPE
    SYNTAX        TruthValue
    MAX-ACCESS    read-only
    STATUS        current
    DESCRIPTION   "Valid Flag"
    ::= { optFacilityHistorical1weekEntry 5 }

optFacilityHistorical1weekTimeStamp OBJECT-TYPE
    SYNTAX        DateAndTime
    MAX-ACCESS    read-only
    STATUS        current
    DESCRIPTION   "Timestamp"
    ::= { optFacilityHistorical1weekEntry 6 }

endOfOptFacilityHistorical1weekTable OBJECT-TYPE
    SYNTAX        Integer32
    MAX-ACCESS    read-only
    STATUS        current
    DESCRIPTION   ""
    ::= { pmFacilityPhysRecord 6 }

oprFacilityHistorical15minTable OBJECT-TYPE
    SYNTAX        SEQUENCE OF OprFacilityHistorical15minEntry
    MAX-ACCESS    not-accessible
    STATUS        current
    DESCRIPTION   ""
    ::= { pmFacilityPhysRecord 7 }

oprFacilityHistorical15minEntry OBJECT-TYPE
    SYNTAX        OprFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  oprFacilityHistorical15minNumber
                }
    ::= { oprFacilityHistorical15minTable 1 }

OprFacilityHistorical15minEntry ::= SEQUENCE
  {    oprFacilityHistorical15minNumber Integer32,
    oprFacilityHistorical15minLow Integer32,
    oprFacilityHistorical15minMean Integer32,
    oprFacilityHistorical15minHigh Integer32,
    oprFacilityHistorical15minValidFlag TruthValue,
    oprFacilityHistorical15minTimeStamp DateAndTime }

oprFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oprFacilityHistorical15minEntry 1 }

oprFacilityHistorical15minLow OBJECT-TYPE
    SYNTAX        Integer32
    UNITS         "0.1 dBm"
    MAX-ACCESS    read-only
    STATUS        current
    DESCRIPTION   "Optical Input Power Received"
    ::= { oprFacilityHistorical15minEntry 2 }

oprFacilityHistorical15minMean OBJECT-TYPE
    SYNTAX        Integer32
    UNITS         "0.1 dBm"
    MAX-ACCESS    read-only
    STATUS        current
    DESCRIPTION   "Optical Input Power Received"
    ::= { oprFacilityHistorical15minEntry 3 }

oprFacilityHistorical15minHigh OBJECT-TYPE
    SYNTAX        Integer32
    UNITS         "0.1 dBm"
    MAX-ACCESS    read-only
    STATUS        current
    DESCRIPTION   "Optical Input Power Received"
    ::= { oprFacilityHistorical15minEntry 4 }

oprFacilityHistorical15minValidFlag OBJECT-TYPE
    SYNTAX        TruthValue
    MAX-ACCESS    read-only
    STATUS        current
    DESCRIPTION   "Valid Flag"
    ::= { oprFacilityHistorical15minEntry 5 }

oprFacilityHistorical15minTimeStamp OBJECT-TYPE
    SYNTAX        DateAndTime
    MAX-ACCESS    read-only
    STATUS        current
    DESCRIPTION   "Timestamp"
    ::= { oprFacilityHistorical15minEntry 6 }

endOfOprFacilityHistorical15minTable OBJECT-TYPE
    SYNTAX        Integer32
    MAX-ACCESS    read-only
    STATUS        current
    DESCRIPTION   ""
    ::= { pmFacilityPhysRecord 8 }

oprFacilityHistorical1dayTable OBJECT-TYPE
    SYNTAX        SEQUENCE OF OprFacilityHistorical1dayEntry
    MAX-ACCESS    not-accessible
    STATUS        current
    DESCRIPTION   ""
    ::= { pmFacilityPhysRecord 9 }

oprFacilityHistorical1dayEntry OBJECT-TYPE
    SYNTAX        OprFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  oprFacilityHistorical1dayNumber
                }
    ::= { oprFacilityHistorical1dayTable 1 }

OprFacilityHistorical1dayEntry ::= SEQUENCE
  {    oprFacilityHistorical1dayNumber Integer32,
    oprFacilityHistorical1dayLow Integer32,
    oprFacilityHistorical1dayMean Integer32,
    oprFacilityHistorical1dayHigh Integer32,
    oprFacilityHistorical1dayValidFlag TruthValue,
    oprFacilityHistorical1dayTimeStamp DateAndTime }

oprFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oprFacilityHistorical1dayEntry 1 }

oprFacilityHistorical1dayLow OBJECT-TYPE
    SYNTAX        Integer32
    UNITS         "0.1 dBm"
    MAX-ACCESS    read-only
    STATUS        current
    DESCRIPTION   "Optical Input Power Received"
    ::= { oprFacilityHistorical1dayEntry 2 }

oprFacilityHistorical1dayMean OBJECT-TYPE
    SYNTAX        Integer32
    UNITS         "0.1 dBm"
    MAX-ACCESS    read-only
    STATUS        current
    DESCRIPTION   "Optical Input Power Received"
    ::= { oprFacilityHistorical1dayEntry 3 }

oprFacilityHistorical1dayHigh OBJECT-TYPE
    SYNTAX        Integer32
    UNITS         "0.1 dBm"
    MAX-ACCESS    read-only
    STATUS        current
    DESCRIPTION   "Optical Input Power Received"
    ::= { oprFacilityHistorical1dayEntry 4 }

oprFacilityHistorical1dayValidFlag OBJECT-TYPE
    SYNTAX        TruthValue
    MAX-ACCESS    read-only
    STATUS        current
    DESCRIPTION   "Valid Flag"
    ::= { oprFacilityHistorical1dayEntry 5 }

oprFacilityHistorical1dayTimeStamp OBJECT-TYPE
    SYNTAX        DateAndTime
    MAX-ACCESS    read-only
    STATUS        current
    DESCRIPTION   "Timestamp"
    ::= { oprFacilityHistorical1dayEntry 6 }

endOfOprFacilityHistorical1dayTable OBJECT-TYPE
    SYNTAX        Integer32
    MAX-ACCESS    read-only
    STATUS        current
    DESCRIPTION   ""
    ::= { pmFacilityPhysRecord 10 }

oprFacilityHistorical1weekTable OBJECT-TYPE
    SYNTAX        SEQUENCE OF OprFacilityHistorical1weekEntry
    MAX-ACCESS    not-accessible
    STATUS        current
    DESCRIPTION   ""
    ::= { pmFacilityPhysRecord 11 }

oprFacilityHistorical1weekEntry OBJECT-TYPE
    SYNTAX        OprFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  oprFacilityHistorical1weekNumber
                }
    ::= { oprFacilityHistorical1weekTable 1 }

OprFacilityHistorical1weekEntry ::= SEQUENCE
  {    oprFacilityHistorical1weekNumber Integer32,
    oprFacilityHistorical1weekLow Integer32,
    oprFacilityHistorical1weekMean Integer32,
    oprFacilityHistorical1weekHigh Integer32,
    oprFacilityHistorical1weekValidFlag TruthValue,
    oprFacilityHistorical1weekTimeStamp DateAndTime }

oprFacilityHistorical1weekNumber OBJECT-TYPE
    SYNTAX        Integer32 (1..52)
    MAX-ACCESS    not-accessible
    STATUS        current
    DESCRIPTION   "Number 1week"
    ::= { oprFacilityHistorical1weekEntry 1 }

oprFacilityHistorical1weekLow OBJECT-TYPE
    SYNTAX        Integer32
    UNITS         "0.1 dBm"
    MAX-ACCESS    read-only
    STATUS        current
    DESCRIPTION   "Optical Input Power Received"
    ::= { oprFacilityHistorical1weekEntry 2 }

oprFacilityHistorical1weekMean OBJECT-TYPE
    SYNTAX        Integer32
    UNITS         "0.1 dBm"
    MAX-ACCESS    read-only
    STATUS        current
    DESCRIPTION   "Optical Input Power Received"
    ::= { oprFacilityHistorical1weekEntry 3 }

oprFacilityHistorical1weekHigh OBJECT-TYPE
    SYNTAX        Integer32
    UNITS         "0.1 dBm"
    MAX-ACCESS    read-only
    STATUS        current
    DESCRIPTION   "Optical Input Power Received"
    ::= { oprFacilityHistorical1weekEntry 4 }

oprFacilityHistorical1weekValidFlag OBJECT-TYPE
    SYNTAX        TruthValue
    MAX-ACCESS    read-only
    STATUS        current
    DESCRIPTION   "Valid Flag"
    ::= { oprFacilityHistorical1weekEntry 5 }

oprFacilityHistorical1weekTimeStamp OBJECT-TYPE
    SYNTAX        DateAndTime
    MAX-ACCESS    read-only
    STATUS        current
    DESCRIPTION   "Timestamp"
    ::= { oprFacilityHistorical1weekEntry 6 }

endOfOprFacilityHistorical1weekTable OBJECT-TYPE
    SYNTAX        Integer32
    MAX-ACCESS    read-only
    STATUS        current
    DESCRIPTION   ""
    ::= { pmFacilityPhysRecord 12 }

lbcnFacilityHistorical15minTable OBJECT-TYPE
    SYNTAX        SEQUENCE OF LbcnFacilityHistorical15minEntry
    MAX-ACCESS    not-accessible
    STATUS        current
    DESCRIPTION   ""
    ::= { pmFacilityPhysRecord 13 }

lbcnFacilityHistorical15minEntry OBJECT-TYPE
    SYNTAX        LbcnFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  lbcnFacilityHistorical15minNumber
                }
    ::= { lbcnFacilityHistorical15minTable 1 }

LbcnFacilityHistorical15minEntry ::= SEQUENCE
  {    lbcnFacilityHistorical15minNumber Integer32,
    lbcnFacilityHistorical15minLow Unsigned32,
    lbcnFacilityHistorical15minMean Unsigned32,
    lbcnFacilityHistorical15minHigh Unsigned32,
    lbcnFacilityHistorical15minValidFlag TruthValue,
    lbcnFacilityHistorical15minTimeStamp DateAndTime }

lbcnFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { lbcnFacilityHistorical15minEntry 1 }

lbcnFacilityHistorical15minLow OBJECT-TYPE
    SYNTAX        Unsigned32
    UNITS         "%"
    MAX-ACCESS    read-only
    STATUS        current
    DESCRIPTION   "Laser Bias Current Normalized"
    ::= { lbcnFacilityHistorical15minEntry 2 }

lbcnFacilityHistorical15minMean OBJECT-TYPE
    SYNTAX        Unsigned32
    UNITS         "%"
    MAX-ACCESS    read-only
    STATUS        current
    DESCRIPTION   "Laser Bias Current Normalized"
    ::= { lbcnFacilityHistorical15minEntry 3 }

lbcnFacilityHistorical15minHigh OBJECT-TYPE
    SYNTAX        Unsigned32
    UNITS         "%"
    MAX-ACCESS    read-only
    STATUS        current
    DESCRIPTION   "Laser Bias Current Normalized"
    ::= { lbcnFacilityHistorical15minEntry 4 }

lbcnFacilityHistorical15minValidFlag OBJECT-TYPE
    SYNTAX        TruthValue
    MAX-ACCESS    read-only
    STATUS        current
    DESCRIPTION   "Valid Flag"
    ::= { lbcnFacilityHistorical15minEntry 5 }

lbcnFacilityHistorical15minTimeStamp OBJECT-TYPE
    SYNTAX        DateAndTime
    MAX-ACCESS    read-only
    STATUS        current
    DESCRIPTION   "Timestamp"
    ::= { lbcnFacilityHistorical15minEntry 6 }

endOfLbcnFacilityHistorical15minTable OBJECT-TYPE
    SYNTAX        Integer32
    MAX-ACCESS    read-only
    STATUS        current
    DESCRIPTION   ""
    ::= { pmFacilityPhysRecord 14 }

lbcnFacilityHistorical1dayTable OBJECT-TYPE
    SYNTAX        SEQUENCE OF LbcnFacilityHistorical1dayEntry
    MAX-ACCESS    not-accessible
    STATUS        current
    DESCRIPTION   ""
    ::= { pmFacilityPhysRecord 15 }

lbcnFacilityHistorical1dayEntry OBJECT-TYPE
    SYNTAX        LbcnFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  lbcnFacilityHistorical1dayNumber
                }
    ::= { lbcnFacilityHistorical1dayTable 1 }

LbcnFacilityHistorical1dayEntry ::= SEQUENCE
  {    lbcnFacilityHistorical1dayNumber Integer32,
    lbcnFacilityHistorical1dayLow Unsigned32,
    lbcnFacilityHistorical1dayMean Unsigned32,
    lbcnFacilityHistorical1dayHigh Unsigned32,
    lbcnFacilityHistorical1dayValidFlag TruthValue,
    lbcnFacilityHistorical1dayTimeStamp DateAndTime }

lbcnFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { lbcnFacilityHistorical1dayEntry 1 }

lbcnFacilityHistorical1dayLow OBJECT-TYPE
    SYNTAX        Unsigned32
    UNITS         "%"
    MAX-ACCESS    read-only
    STATUS        current
    DESCRIPTION   "Laser Bias Current Normalized"
    ::= { lbcnFacilityHistorical1dayEntry 2 }

lbcnFacilityHistorical1dayMean OBJECT-TYPE
    SYNTAX        Unsigned32
    UNITS         "%"
    MAX-ACCESS    read-only
    STATUS        current
    DESCRIPTION   "Laser Bias Current Normalized"
    ::= { lbcnFacilityHistorical1dayEntry 3 }

lbcnFacilityHistorical1dayHigh OBJECT-TYPE
    SYNTAX        Unsigned32
    UNITS         "%"
    MAX-ACCESS    read-only
    STATUS        current
    DESCRIPTION   "Laser Bias Current Normalized"
    ::= { lbcnFacilityHistorical1dayEntry 4 }

lbcnFacilityHistorical1dayValidFlag OBJECT-TYPE
    SYNTAX        TruthValue
    MAX-ACCESS    read-only
    STATUS        current
    DESCRIPTION   "Valid Flag"
    ::= { lbcnFacilityHistorical1dayEntry 5 }

lbcnFacilityHistorical1dayTimeStamp OBJECT-TYPE
    SYNTAX        DateAndTime
    MAX-ACCESS    read-only
    STATUS        current
    DESCRIPTION   "Timestamp"
    ::= { lbcnFacilityHistorical1dayEntry 6 }

endOfLbcnFacilityHistorical1dayTable OBJECT-TYPE
    SYNTAX        Integer32
    MAX-ACCESS    read-only
    STATUS        current
    DESCRIPTION   ""
    ::= { pmFacilityPhysRecord 16 }

lbcnFacilityHistorical1weekTable OBJECT-TYPE
    SYNTAX        SEQUENCE OF LbcnFacilityHistorical1weekEntry
    MAX-ACCESS    not-accessible
    STATUS        current
    DESCRIPTION   ""
    ::= { pmFacilityPhysRecord 17 }

lbcnFacilityHistorical1weekEntry OBJECT-TYPE
    SYNTAX        LbcnFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  lbcnFacilityHistorical1weekNumber
                }
    ::= { lbcnFacilityHistorical1weekTable 1 }

LbcnFacilityHistorical1weekEntry ::= SEQUENCE
  {    lbcnFacilityHistorical1weekNumber Integer32,
    lbcnFacilityHistorical1weekLow Unsigned32,
    lbcnFacilityHistorical1weekMean Unsigned32,
    lbcnFacilityHistorical1weekHigh Unsigned32,
    lbcnFacilityHistorical1weekValidFlag TruthValue,
    lbcnFacilityHistorical1weekTimeStamp DateAndTime }

lbcnFacilityHistorical1weekNumber OBJECT-TYPE
    SYNTAX        Integer32 (1..52)
    MAX-ACCESS    not-accessible
    STATUS        current
    DESCRIPTION   "Number 1week"
    ::= { lbcnFacilityHistorical1weekEntry 1 }

lbcnFacilityHistorical1weekLow OBJECT-TYPE
    SYNTAX        Unsigned32
    UNITS         "%"
    MAX-ACCESS    read-only
    STATUS        current
    DESCRIPTION   "Laser Bias Current Normalized"
    ::= { lbcnFacilityHistorical1weekEntry 2 }

lbcnFacilityHistorical1weekMean OBJECT-TYPE
    SYNTAX        Unsigned32
    UNITS         "%"
    MAX-ACCESS    read-only
    STATUS        current
    DESCRIPTION   "Laser Bias Current Normalized"
    ::= { lbcnFacilityHistorical1weekEntry 3 }

lbcnFacilityHistorical1weekHigh OBJECT-TYPE
    SYNTAX        Unsigned32
    UNITS         "%"
    MAX-ACCESS    read-only
    STATUS        current
    DESCRIPTION   "Laser Bias Current Normalized"
    ::= { lbcnFacilityHistorical1weekEntry 4 }

lbcnFacilityHistorical1weekValidFlag OBJECT-TYPE
    SYNTAX        TruthValue
    MAX-ACCESS    read-only
    STATUS        current
    DESCRIPTION   "Valid Flag"
    ::= { lbcnFacilityHistorical1weekEntry 5 }

lbcnFacilityHistorical1weekTimeStamp OBJECT-TYPE
    SYNTAX        DateAndTime
    MAX-ACCESS    read-only
    STATUS        current
    DESCRIPTION   "Timestamp"
    ::= { lbcnFacilityHistorical1weekEntry 6 }

endOfLbcnFacilityHistorical1weekTable OBJECT-TYPE
    SYNTAX        Integer32
    MAX-ACCESS    read-only
    STATUS        current
    DESCRIPTION   ""
    ::= { pmFacilityPhysRecord 18 }

rndTrpDlyFacilityHistorical15minTable OBJECT-TYPE
    SYNTAX        SEQUENCE OF RndTrpDlyFacilityHistorical15minEntry
    MAX-ACCESS    not-accessible
    STATUS        current
    DESCRIPTION   ""
    ::= { pmFacilityPhysRecord 19 }

rndTrpDlyFacilityHistorical15minEntry OBJECT-TYPE
    SYNTAX        RndTrpDlyFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  rndTrpDlyFacilityHistorical15minNumber
                }
    ::= { rndTrpDlyFacilityHistorical15minTable 1 }

RndTrpDlyFacilityHistorical15minEntry ::= SEQUENCE
  {    rndTrpDlyFacilityHistorical15minNumber Integer32,
    rndTrpDlyFacilityHistorical15minLow Unsigned32,
    rndTrpDlyFacilityHistorical15minMean Unsigned32,
    rndTrpDlyFacilityHistorical15minHigh Unsigned32,
    rndTrpDlyFacilityHistorical15minValidFlag TruthValue,
    rndTrpDlyFacilityHistorical15minTimeStamp DateAndTime }

rndTrpDlyFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { rndTrpDlyFacilityHistorical15minEntry 1 }

rndTrpDlyFacilityHistorical15minLow OBJECT-TYPE
    SYNTAX        Unsigned32
    UNITS         "ns"
    MAX-ACCESS    read-only
    STATUS        current
    DESCRIPTION   "Measured round trip delay low"
    ::= { rndTrpDlyFacilityHistorical15minEntry 2 }

rndTrpDlyFacilityHistorical15minMean OBJECT-TYPE
    SYNTAX        Unsigned32
    UNITS         "ns"
    MAX-ACCESS    read-only
    STATUS        current
    DESCRIPTION   "Measured round trip delay mean"
    ::= { rndTrpDlyFacilityHistorical15minEntry 3 }

rndTrpDlyFacilityHistorical15minHigh OBJECT-TYPE
    SYNTAX        Unsigned32
    UNITS         "ns"
    MAX-ACCESS    read-only
    STATUS        current
    DESCRIPTION   "Measured round trip delay high"
    ::= { rndTrpDlyFacilityHistorical15minEntry 4 }

rndTrpDlyFacilityHistorical15minValidFlag OBJECT-TYPE
    SYNTAX        TruthValue
    MAX-ACCESS    read-only
    STATUS        current
    DESCRIPTION   "Valid Flag"
    ::= { rndTrpDlyFacilityHistorical15minEntry 5 }

rndTrpDlyFacilityHistorical15minTimeStamp OBJECT-TYPE
    SYNTAX        DateAndTime
    MAX-ACCESS    read-only
    STATUS        current
    DESCRIPTION   "Timestamp"
    ::= { rndTrpDlyFacilityHistorical15minEntry 6 }

endOfRndTrpDlyFacilityHistorical15minTable OBJECT-TYPE
    SYNTAX        Integer32
    MAX-ACCESS    read-only
    STATUS        current
    DESCRIPTION   ""
    ::= { pmFacilityPhysRecord 20 }

rndTrpDlyFacilityHistorical1dayTable OBJECT-TYPE
    SYNTAX        SEQUENCE OF RndTrpDlyFacilityHistorical1dayEntry
    MAX-ACCESS    not-accessible
    STATUS        current
    DESCRIPTION   ""
    ::= { pmFacilityPhysRecord 21 }

rndTrpDlyFacilityHistorical1dayEntry OBJECT-TYPE
    SYNTAX        RndTrpDlyFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  rndTrpDlyFacilityHistorical1dayNumber
                }
    ::= { rndTrpDlyFacilityHistorical1dayTable 1 }

RndTrpDlyFacilityHistorical1dayEntry ::= SEQUENCE
  {    rndTrpDlyFacilityHistorical1dayNumber Integer32,
    rndTrpDlyFacilityHistorical1dayLow Unsigned32,
    rndTrpDlyFacilityHistorical1dayMean Unsigned32,
    rndTrpDlyFacilityHistorical1dayHigh Unsigned32,
    rndTrpDlyFacilityHistorical1dayValidFlag TruthValue,
    rndTrpDlyFacilityHistorical1dayTimeStamp DateAndTime }

rndTrpDlyFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { rndTrpDlyFacilityHistorical1dayEntry 1 }

rndTrpDlyFacilityHistorical1dayLow OBJECT-TYPE
    SYNTAX        Unsigned32
    UNITS         "ns"
    MAX-ACCESS    read-only
    STATUS        current
    DESCRIPTION   "Measured round trip delay low"
    ::= { rndTrpDlyFacilityHistorical1dayEntry 2 }

rndTrpDlyFacilityHistorical1dayMean OBJECT-TYPE
    SYNTAX        Unsigned32
    UNITS         "ns"
    MAX-ACCESS    read-only
    STATUS        current
    DESCRIPTION   "Measured round trip delay mean"
    ::= { rndTrpDlyFacilityHistorical1dayEntry 3 }

rndTrpDlyFacilityHistorical1dayHigh OBJECT-TYPE
    SYNTAX        Unsigned32
    UNITS         "ns"
    MAX-ACCESS    read-only
    STATUS        current
    DESCRIPTION   "Measured round trip delay high"
    ::= { rndTrpDlyFacilityHistorical1dayEntry 4 }

rndTrpDlyFacilityHistorical1dayValidFlag OBJECT-TYPE
    SYNTAX        TruthValue
    MAX-ACCESS    read-only
    STATUS        current
    DESCRIPTION   "Valid Flag"
    ::= { rndTrpDlyFacilityHistorical1dayEntry 5 }

rndTrpDlyFacilityHistorical1dayTimeStamp OBJECT-TYPE
    SYNTAX        DateAndTime
    MAX-ACCESS    read-only
    STATUS        current
    DESCRIPTION   "Timestamp"
    ::= { rndTrpDlyFacilityHistorical1dayEntry 6 }

endOfRndTrpDlyFacilityHistorical1dayTable OBJECT-TYPE
    SYNTAX        Integer32
    MAX-ACCESS    read-only
    STATUS        current
    DESCRIPTION   ""
    ::= { pmFacilityPhysRecord 22 }

rndTrpDlyFacilityHistorical1weekTable OBJECT-TYPE
    SYNTAX        SEQUENCE OF RndTrpDlyFacilityHistorical1weekEntry
    MAX-ACCESS    not-accessible
    STATUS        current
    DESCRIPTION   ""
    ::= { pmFacilityPhysRecord 23 }

rndTrpDlyFacilityHistorical1weekEntry OBJECT-TYPE
    SYNTAX        RndTrpDlyFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  rndTrpDlyFacilityHistorical1weekNumber
                }
    ::= { rndTrpDlyFacilityHistorical1weekTable 1 }

RndTrpDlyFacilityHistorical1weekEntry ::= SEQUENCE
  {    rndTrpDlyFacilityHistorical1weekNumber Integer32,
    rndTrpDlyFacilityHistorical1weekLow Unsigned32,
    rndTrpDlyFacilityHistorical1weekMean Unsigned32,
    rndTrpDlyFacilityHistorical1weekHigh Unsigned32,
    rndTrpDlyFacilityHistorical1weekValidFlag TruthValue,
    rndTrpDlyFacilityHistorical1weekTimeStamp DateAndTime }

rndTrpDlyFacilityHistorical1weekNumber OBJECT-TYPE
    SYNTAX        Integer32 (1..52)
    MAX-ACCESS    not-accessible
    STATUS        current
    DESCRIPTION   "Number 1week"
    ::= { rndTrpDlyFacilityHistorical1weekEntry 1 }

rndTrpDlyFacilityHistorical1weekLow OBJECT-TYPE
    SYNTAX        Unsigned32
    UNITS         "ns"
    MAX-ACCESS    read-only
    STATUS        current
    DESCRIPTION   "Measured round trip delay low"
    ::= { rndTrpDlyFacilityHistorical1weekEntry 2 }

rndTrpDlyFacilityHistorical1weekMean OBJECT-TYPE
    SYNTAX        Unsigned32
    UNITS         "ns"
    MAX-ACCESS    read-only
    STATUS        current
    DESCRIPTION   "Measured round trip delay mean"
    ::= { rndTrpDlyFacilityHistorical1weekEntry 3 }

rndTrpDlyFacilityHistorical1weekHigh OBJECT-TYPE
    SYNTAX        Unsigned32
    UNITS         "ns"
    MAX-ACCESS    read-only
    STATUS        current
    DESCRIPTION   "Measured round trip delay high"
    ::= { rndTrpDlyFacilityHistorical1weekEntry 4 }

rndTrpDlyFacilityHistorical1weekValidFlag OBJECT-TYPE
    SYNTAX        TruthValue
    MAX-ACCESS    read-only
    STATUS        current
    DESCRIPTION   "Valid Flag"
    ::= { rndTrpDlyFacilityHistorical1weekEntry 5 }

rndTrpDlyFacilityHistorical1weekTimeStamp OBJECT-TYPE
    SYNTAX        DateAndTime
    MAX-ACCESS    read-only
    STATUS        current
    DESCRIPTION   "Timestamp"
    ::= { rndTrpDlyFacilityHistorical1weekEntry 6 }

endOfRndTrpDlyFacilityHistorical1weekTable OBJECT-TYPE
    SYNTAX        Integer32
    MAX-ACCESS    read-only
    STATUS        current
    DESCRIPTION   ""
    ::= { pmFacilityPhysRecord 24 }

skewFacilityHistorical15minTable OBJECT-TYPE
    SYNTAX        SEQUENCE OF SkewFacilityHistorical15minEntry
    MAX-ACCESS    not-accessible
    STATUS        current
    DESCRIPTION   ""
    ::= { pmFacilityPhysRecord 25 }

skewFacilityHistorical15minEntry OBJECT-TYPE
    SYNTAX        SkewFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  skewFacilityHistorical15minNumber
                }
    ::= { skewFacilityHistorical15minTable 1 }

SkewFacilityHistorical15minEntry ::= SEQUENCE
  {    skewFacilityHistorical15minNumber Integer32,
    skewFacilityHistorical15minLow Integer32,
    skewFacilityHistorical15minMean Integer32,
    skewFacilityHistorical15minHigh Integer32,
    skewFacilityHistorical15minValidFlag TruthValue,
    skewFacilityHistorical15minTimeStamp DateAndTime }

skewFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { skewFacilityHistorical15minEntry 1 }

skewFacilityHistorical15minLow OBJECT-TYPE
    SYNTAX        Integer32
    UNITS         "ns"
    MAX-ACCESS    read-only
    STATUS        current
    DESCRIPTION   "Skew between logical lanes farthest apart low"
    ::= { skewFacilityHistorical15minEntry 2 }

skewFacilityHistorical15minMean OBJECT-TYPE
    SYNTAX        Integer32
    UNITS         "ns"
    MAX-ACCESS    read-only
    STATUS        current
    DESCRIPTION   "Skew between logical lanes farthest apart mean"
    ::= { skewFacilityHistorical15minEntry 3 }

skewFacilityHistorical15minHigh OBJECT-TYPE
    SYNTAX        Integer32
    UNITS         "ns"
    MAX-ACCESS    read-only
    STATUS        current
    DESCRIPTION   "Skew between logical lanes farthest apart high"
    ::= { skewFacilityHistorical15minEntry 4 }

skewFacilityHistorical15minValidFlag OBJECT-TYPE
    SYNTAX        TruthValue
    MAX-ACCESS    read-only
    STATUS        current
    DESCRIPTION   "Valid Flag"
    ::= { skewFacilityHistorical15minEntry 5 }

skewFacilityHistorical15minTimeStamp OBJECT-TYPE
    SYNTAX        DateAndTime
    MAX-ACCESS    read-only
    STATUS        current
    DESCRIPTION   "Timestamp"
    ::= { skewFacilityHistorical15minEntry 6 }

endOfSkewFacilityHistorical15minTable OBJECT-TYPE
    SYNTAX        Integer32
    MAX-ACCESS    read-only
    STATUS        current
    DESCRIPTION   ""
    ::= { pmFacilityPhysRecord 26 }

skewFacilityHistorical1dayTable OBJECT-TYPE
    SYNTAX        SEQUENCE OF SkewFacilityHistorical1dayEntry
    MAX-ACCESS    not-accessible
    STATUS        current
    DESCRIPTION   ""
    ::= { pmFacilityPhysRecord 27 }

skewFacilityHistorical1dayEntry OBJECT-TYPE
    SYNTAX        SkewFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  skewFacilityHistorical1dayNumber
                }
    ::= { skewFacilityHistorical1dayTable 1 }

SkewFacilityHistorical1dayEntry ::= SEQUENCE
  {    skewFacilityHistorical1dayNumber Integer32,
    skewFacilityHistorical1dayLow Integer32,
    skewFacilityHistorical1dayMean Integer32,
    skewFacilityHistorical1dayHigh Integer32,
    skewFacilityHistorical1dayValidFlag TruthValue,
    skewFacilityHistorical1dayTimeStamp DateAndTime }

skewFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { skewFacilityHistorical1dayEntry 1 }

skewFacilityHistorical1dayLow OBJECT-TYPE
    SYNTAX        Integer32
    UNITS         "ns"
    MAX-ACCESS    read-only
    STATUS        current
    DESCRIPTION   "Skew between logical lanes farthest apart low"
    ::= { skewFacilityHistorical1dayEntry 2 }

skewFacilityHistorical1dayMean OBJECT-TYPE
    SYNTAX        Integer32
    UNITS         "ns"
    MAX-ACCESS    read-only
    STATUS        current
    DESCRIPTION   "Skew between logical lanes farthest apart mean"
    ::= { skewFacilityHistorical1dayEntry 3 }

skewFacilityHistorical1dayHigh OBJECT-TYPE
    SYNTAX        Integer32
    UNITS         "ns"
    MAX-ACCESS    read-only
    STATUS        current
    DESCRIPTION   "Skew between logical lanes farthest apart high"
    ::= { skewFacilityHistorical1dayEntry 4 }

skewFacilityHistorical1dayValidFlag OBJECT-TYPE
    SYNTAX        TruthValue
    MAX-ACCESS    read-only
    STATUS        current
    DESCRIPTION   "Valid Flag"
    ::= { skewFacilityHistorical1dayEntry 5 }

skewFacilityHistorical1dayTimeStamp OBJECT-TYPE
    SYNTAX        DateAndTime
    MAX-ACCESS    read-only
    STATUS        current
    DESCRIPTION   "Timestamp"
    ::= { skewFacilityHistorical1dayEntry 6 }

endOfSkewFacilityHistorical1dayTable OBJECT-TYPE
    SYNTAX        Integer32
    MAX-ACCESS    read-only
    STATUS        current
    DESCRIPTION   ""
    ::= { pmFacilityPhysRecord 28 }

skewFacilityHistorical1weekTable OBJECT-TYPE
    SYNTAX        SEQUENCE OF SkewFacilityHistorical1weekEntry
    MAX-ACCESS    not-accessible
    STATUS        current
    DESCRIPTION   ""
    ::= { pmFacilityPhysRecord 29 }

skewFacilityHistorical1weekEntry OBJECT-TYPE
    SYNTAX        SkewFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  skewFacilityHistorical1weekNumber
                }
    ::= { skewFacilityHistorical1weekTable 1 }

SkewFacilityHistorical1weekEntry ::= SEQUENCE
  {    skewFacilityHistorical1weekNumber Integer32,
    skewFacilityHistorical1weekLow Integer32,
    skewFacilityHistorical1weekMean Integer32,
    skewFacilityHistorical1weekHigh Integer32,
    skewFacilityHistorical1weekValidFlag TruthValue,
    skewFacilityHistorical1weekTimeStamp DateAndTime }

skewFacilityHistorical1weekNumber OBJECT-TYPE
    SYNTAX        Integer32 (1..52)
    MAX-ACCESS    not-accessible
    STATUS        current
    DESCRIPTION   "Number 1week"
    ::= { skewFacilityHistorical1weekEntry 1 }

skewFacilityHistorical1weekLow OBJECT-TYPE
    SYNTAX        Integer32
    UNITS         "ns"
    MAX-ACCESS    read-only
    STATUS        current
    DESCRIPTION   "Skew between logical lanes farthest apart low"
    ::= { skewFacilityHistorical1weekEntry 2 }

skewFacilityHistorical1weekMean OBJECT-TYPE
    SYNTAX        Integer32
    UNITS         "ns"
    MAX-ACCESS    read-only
    STATUS        current
    DESCRIPTION   "Skew between logical lanes farthest apart mean"
    ::= { skewFacilityHistorical1weekEntry 3 }

skewFacilityHistorical1weekHigh OBJECT-TYPE
    SYNTAX        Integer32
    UNITS         "ns"
    MAX-ACCESS    read-only
    STATUS        current
    DESCRIPTION   "Skew between logical lanes farthest apart high"
    ::= { skewFacilityHistorical1weekEntry 4 }

skewFacilityHistorical1weekValidFlag OBJECT-TYPE
    SYNTAX        TruthValue
    MAX-ACCESS    read-only
    STATUS        current
    DESCRIPTION   "Valid Flag"
    ::= { skewFacilityHistorical1weekEntry 5 }

skewFacilityHistorical1weekTimeStamp OBJECT-TYPE
    SYNTAX        DateAndTime
    MAX-ACCESS    read-only
    STATUS        current
    DESCRIPTION   "Timestamp"
    ::= { skewFacilityHistorical1weekEntry 6 }

endOfSkewFacilityHistorical1weekTable OBJECT-TYPE
    SYNTAX        Integer32
    MAX-ACCESS    read-only
    STATUS        current
    DESCRIPTION   ""
    ::= { pmFacilityPhysRecord 30 }

snrFacilityHistorical15minTable OBJECT-TYPE
    SYNTAX        SEQUENCE OF SnrFacilityHistorical15minEntry
    MAX-ACCESS    not-accessible
    STATUS        current
    DESCRIPTION   ""
    ::= { pmFacilityPhysRecord 31 }

snrFacilityHistorical15minEntry OBJECT-TYPE
    SYNTAX        SnrFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  snrFacilityHistorical15minNumber
                }
    ::= { snrFacilityHistorical15minTable 1 }

SnrFacilityHistorical15minEntry ::= SEQUENCE
  {    snrFacilityHistorical15minNumber Integer32,
    snrFacilityHistorical15minLow Integer32,
    snrFacilityHistorical15minMean Integer32,
    snrFacilityHistorical15minHigh Integer32,
    snrFacilityHistorical15minValidFlag TruthValue,
    snrFacilityHistorical15minTimeStamp DateAndTime }

snrFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { snrFacilityHistorical15minEntry 1 }

snrFacilityHistorical15minLow OBJECT-TYPE
    SYNTAX        Integer32
    UNITS         "0.1 dB"
    MAX-ACCESS    read-only
    STATUS        current
    DESCRIPTION   "Signal-to-Noise Ratio Low"
    ::= { snrFacilityHistorical15minEntry 2 }

snrFacilityHistorical15minMean OBJECT-TYPE
    SYNTAX        Integer32
    UNITS         "0.1 dB"
    MAX-ACCESS    read-only
    STATUS        current
    DESCRIPTION   "Signal-to-Noise Ratio Mean"
    ::= { snrFacilityHistorical15minEntry 3 }

snrFacilityHistorical15minHigh OBJECT-TYPE
    SYNTAX        Integer32
    UNITS         "0.1 dB"
    MAX-ACCESS    read-only
    STATUS        current
    DESCRIPTION   "Signal-to-Noise Ratio High"
    ::= { snrFacilityHistorical15minEntry 4 }

snrFacilityHistorical15minValidFlag OBJECT-TYPE
    SYNTAX        TruthValue
    MAX-ACCESS    read-only
    STATUS        current
    DESCRIPTION   "Valid Flag"
    ::= { snrFacilityHistorical15minEntry 5 }

snrFacilityHistorical15minTimeStamp OBJECT-TYPE
    SYNTAX        DateAndTime
    MAX-ACCESS    read-only
    STATUS        current
    DESCRIPTION   "Timestamp"
    ::= { snrFacilityHistorical15minEntry 6 }

endOfSnrFacilityHistorical15minTable OBJECT-TYPE
    SYNTAX        Integer32
    MAX-ACCESS    read-only
    STATUS        current
    DESCRIPTION   ""
    ::= { pmFacilityPhysRecord 32 }

snrFacilityHistorical1dayTable OBJECT-TYPE
    SYNTAX        SEQUENCE OF SnrFacilityHistorical1dayEntry
    MAX-ACCESS    not-accessible
    STATUS        current
    DESCRIPTION   ""
    ::= { pmFacilityPhysRecord 33 }

snrFacilityHistorical1dayEntry OBJECT-TYPE
    SYNTAX        SnrFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  snrFacilityHistorical1dayNumber
                }
    ::= { snrFacilityHistorical1dayTable 1 }

SnrFacilityHistorical1dayEntry ::= SEQUENCE
  {    snrFacilityHistorical1dayNumber Integer32,
    snrFacilityHistorical1dayLow Integer32,
    snrFacilityHistorical1dayMean Integer32,
    snrFacilityHistorical1dayHigh Integer32,
    snrFacilityHistorical1dayValidFlag TruthValue,
    snrFacilityHistorical1dayTimeStamp DateAndTime }

snrFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { snrFacilityHistorical1dayEntry 1 }

snrFacilityHistorical1dayLow OBJECT-TYPE
    SYNTAX        Integer32
    UNITS         "0.1 dB"
    MAX-ACCESS    read-only
    STATUS        current
    DESCRIPTION   "Signal-to-Noise Ratio Low"
    ::= { snrFacilityHistorical1dayEntry 2 }

snrFacilityHistorical1dayMean OBJECT-TYPE
    SYNTAX        Integer32
    UNITS         "0.1 dB"
    MAX-ACCESS    read-only
    STATUS        current
    DESCRIPTION   "Signal-to-Noise Ratio Mean"
    ::= { snrFacilityHistorical1dayEntry 3 }

snrFacilityHistorical1dayHigh OBJECT-TYPE
    SYNTAX        Integer32
    UNITS         "0.1 dB"
    MAX-ACCESS    read-only
    STATUS        current
    DESCRIPTION   "Signal-to-Noise Ratio High"
    ::= { snrFacilityHistorical1dayEntry 4 }

snrFacilityHistorical1dayValidFlag OBJECT-TYPE
    SYNTAX        TruthValue
    MAX-ACCESS    read-only
    STATUS        current
    DESCRIPTION   "Valid Flag"
    ::= { snrFacilityHistorical1dayEntry 5 }

snrFacilityHistorical1dayTimeStamp OBJECT-TYPE
    SYNTAX        DateAndTime
    MAX-ACCESS    read-only
    STATUS        current
    DESCRIPTION   "Timestamp"
    ::= { snrFacilityHistorical1dayEntry 6 }

endOfSnrFacilityHistorical1dayTable OBJECT-TYPE
    SYNTAX        Integer32
    MAX-ACCESS    read-only
    STATUS        current
    DESCRIPTION   ""
    ::= { pmFacilityPhysRecord 34 }

snrFacilityHistorical1weekTable OBJECT-TYPE
    SYNTAX        SEQUENCE OF SnrFacilityHistorical1weekEntry
    MAX-ACCESS    not-accessible
    STATUS        current
    DESCRIPTION   ""
    ::= { pmFacilityPhysRecord 35 }

snrFacilityHistorical1weekEntry OBJECT-TYPE
    SYNTAX        SnrFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  snrFacilityHistorical1weekNumber
                }
    ::= { snrFacilityHistorical1weekTable 1 }

SnrFacilityHistorical1weekEntry ::= SEQUENCE
  {    snrFacilityHistorical1weekNumber Integer32,
    snrFacilityHistorical1weekLow Integer32,
    snrFacilityHistorical1weekMean Integer32,
    snrFacilityHistorical1weekHigh Integer32,
    snrFacilityHistorical1weekValidFlag TruthValue,
    snrFacilityHistorical1weekTimeStamp DateAndTime }

snrFacilityHistorical1weekNumber OBJECT-TYPE
    SYNTAX        Integer32 (1..52)
    MAX-ACCESS    not-accessible
    STATUS        current
    DESCRIPTION   "Number 1week"
    ::= { snrFacilityHistorical1weekEntry 1 }

snrFacilityHistorical1weekLow OBJECT-TYPE
    SYNTAX        Integer32
    UNITS         "0.1 dB"
    MAX-ACCESS    read-only
    STATUS        current
    DESCRIPTION   "Signal-to-Noise Ratio Low"
    ::= { snrFacilityHistorical1weekEntry 2 }

snrFacilityHistorical1weekMean OBJECT-TYPE
    SYNTAX        Integer32
    UNITS         "0.1 dB"
    MAX-ACCESS    read-only
    STATUS        current
    DESCRIPTION   "Signal-to-Noise Ratio Mean"
    ::= { snrFacilityHistorical1weekEntry 3 }

snrFacilityHistorical1weekHigh OBJECT-TYPE
    SYNTAX        Integer32
    UNITS         "0.1 dB"
    MAX-ACCESS    read-only
    STATUS        current
    DESCRIPTION   "Signal-to-Noise Ratio High"
    ::= { snrFacilityHistorical1weekEntry 4 }

snrFacilityHistorical1weekValidFlag OBJECT-TYPE
    SYNTAX        TruthValue
    MAX-ACCESS    read-only
    STATUS        current
    DESCRIPTION   "Valid Flag"
    ::= { snrFacilityHistorical1weekEntry 5 }

snrFacilityHistorical1weekTimeStamp OBJECT-TYPE
    SYNTAX        DateAndTime
    MAX-ACCESS    read-only
    STATUS        current
    DESCRIPTION   "Timestamp"
    ::= { snrFacilityHistorical1weekEntry 6 }

endOfSnrFacilityHistorical1weekTable OBJECT-TYPE
    SYNTAX        Integer32
    MAX-ACCESS    read-only
    STATUS        current
    DESCRIPTION   ""
    ::= { pmFacilityPhysRecord 36 }

cfotFacilityHistorical15minTable OBJECT-TYPE
    SYNTAX        SEQUENCE OF CfotFacilityHistorical15minEntry
    MAX-ACCESS    not-accessible
    STATUS        current
    DESCRIPTION   ""
    ::= { pmFacilityPhysRecord 37 }

cfotFacilityHistorical15minEntry OBJECT-TYPE
    SYNTAX        CfotFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  cfotFacilityHistorical15minNumber
                }
    ::= { cfotFacilityHistorical15minTable 1 }

CfotFacilityHistorical15minEntry ::= SEQUENCE
  {    cfotFacilityHistorical15minNumber Integer32,
    cfotFacilityHistorical15minLow Integer32,
    cfotFacilityHistorical15minMean Integer32,
    cfotFacilityHistorical15minHigh Integer32,
    cfotFacilityHistorical15minValidFlag TruthValue,
    cfotFacilityHistorical15minTimeStamp DateAndTime }

cfotFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { cfotFacilityHistorical15minEntry 1 }

cfotFacilityHistorical15minLow OBJECT-TYPE
    SYNTAX        Integer32
    UNITS         "0.001 GHz"
    MAX-ACCESS    read-only
    STATUS        current
    DESCRIPTION   "Carrier Frequency Offset Low"
    ::= { cfotFacilityHistorical15minEntry 2 }

cfotFacilityHistorical15minMean OBJECT-TYPE
    SYNTAX        Integer32
    UNITS         "0.001 GHz"
    MAX-ACCESS    read-only
    STATUS        current
    DESCRIPTION   "Carrier Frequency Offset Mean"
    ::= { cfotFacilityHistorical15minEntry 3 }

cfotFacilityHistorical15minHigh OBJECT-TYPE
    SYNTAX        Integer32
    UNITS         "0.001 GHz"
    MAX-ACCESS    read-only
    STATUS        current
    DESCRIPTION   "Carrier Frequency Offset High"
    ::= { cfotFacilityHistorical15minEntry 4 }

cfotFacilityHistorical15minValidFlag OBJECT-TYPE
    SYNTAX        TruthValue
    MAX-ACCESS    read-only
    STATUS        current
    DESCRIPTION   "Valid Flag"
    ::= { cfotFacilityHistorical15minEntry 5 }

cfotFacilityHistorical15minTimeStamp OBJECT-TYPE
    SYNTAX        DateAndTime
    MAX-ACCESS    read-only
    STATUS        current
    DESCRIPTION   "Timestamp"
    ::= { cfotFacilityHistorical15minEntry 6 }

endOfCfotFacilityHistorical15minTable OBJECT-TYPE
    SYNTAX        Integer32
    MAX-ACCESS    read-only
    STATUS        current
    DESCRIPTION   ""
    ::= { pmFacilityPhysRecord 38 }

cfotFacilityHistorical1dayTable OBJECT-TYPE
    SYNTAX        SEQUENCE OF CfotFacilityHistorical1dayEntry
    MAX-ACCESS    not-accessible
    STATUS        current
    DESCRIPTION   ""
    ::= { pmFacilityPhysRecord 39 }

cfotFacilityHistorical1dayEntry OBJECT-TYPE
    SYNTAX        CfotFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  cfotFacilityHistorical1dayNumber
                }
    ::= { cfotFacilityHistorical1dayTable 1 }

CfotFacilityHistorical1dayEntry ::= SEQUENCE
  {    cfotFacilityHistorical1dayNumber Integer32,
    cfotFacilityHistorical1dayLow Integer32,
    cfotFacilityHistorical1dayMean Integer32,
    cfotFacilityHistorical1dayHigh Integer32,
    cfotFacilityHistorical1dayValidFlag TruthValue,
    cfotFacilityHistorical1dayTimeStamp DateAndTime }

cfotFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { cfotFacilityHistorical1dayEntry 1 }

cfotFacilityHistorical1dayLow OBJECT-TYPE
    SYNTAX        Integer32
    UNITS         "0.001 GHz"
    MAX-ACCESS    read-only
    STATUS        current
    DESCRIPTION   "Carrier Frequency Offset Low"
    ::= { cfotFacilityHistorical1dayEntry 2 }

cfotFacilityHistorical1dayMean OBJECT-TYPE
    SYNTAX        Integer32
    UNITS         "0.001 GHz"
    MAX-ACCESS    read-only
    STATUS        current
    DESCRIPTION   "Carrier Frequency Offset Mean"
    ::= { cfotFacilityHistorical1dayEntry 3 }

cfotFacilityHistorical1dayHigh OBJECT-TYPE
    SYNTAX        Integer32
    UNITS         "0.001 GHz"
    MAX-ACCESS    read-only
    STATUS        current
    DESCRIPTION   "Carrier Frequency Offset High"
    ::= { cfotFacilityHistorical1dayEntry 4 }

cfotFacilityHistorical1dayValidFlag OBJECT-TYPE
    SYNTAX        TruthValue
    MAX-ACCESS    read-only
    STATUS        current
    DESCRIPTION   "Valid Flag"
    ::= { cfotFacilityHistorical1dayEntry 5 }

cfotFacilityHistorical1dayTimeStamp OBJECT-TYPE
    SYNTAX        DateAndTime
    MAX-ACCESS    read-only
    STATUS        current
    DESCRIPTION   "Timestamp"
    ::= { cfotFacilityHistorical1dayEntry 6 }

endOfCfotFacilityHistorical1dayTable OBJECT-TYPE
    SYNTAX        Integer32
    MAX-ACCESS    read-only
    STATUS        current
    DESCRIPTION   ""
    ::= { pmFacilityPhysRecord 40 }

cfotFacilityHistorical1weekTable OBJECT-TYPE
    SYNTAX        SEQUENCE OF CfotFacilityHistorical1weekEntry
    MAX-ACCESS    not-accessible
    STATUS        current
    DESCRIPTION   ""
    ::= { pmFacilityPhysRecord 41 }

cfotFacilityHistorical1weekEntry OBJECT-TYPE
    SYNTAX        CfotFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  cfotFacilityHistorical1weekNumber
                }
    ::= { cfotFacilityHistorical1weekTable 1 }

CfotFacilityHistorical1weekEntry ::= SEQUENCE
  {    cfotFacilityHistorical1weekNumber Integer32,
    cfotFacilityHistorical1weekLow Integer32,
    cfotFacilityHistorical1weekMean Integer32,
    cfotFacilityHistorical1weekHigh Integer32,
    cfotFacilityHistorical1weekValidFlag TruthValue,
    cfotFacilityHistorical1weekTimeStamp DateAndTime }

cfotFacilityHistorical1weekNumber OBJECT-TYPE
    SYNTAX        Integer32 (1..52)
    MAX-ACCESS    not-accessible
    STATUS        current
    DESCRIPTION   "Number 1week"
    ::= { cfotFacilityHistorical1weekEntry 1 }

cfotFacilityHistorical1weekLow OBJECT-TYPE
    SYNTAX        Integer32
    UNITS         "0.001 GHz"
    MAX-ACCESS    read-only
    STATUS        current
    DESCRIPTION   "Carrier Frequency Offset Low"
    ::= { cfotFacilityHistorical1weekEntry 2 }

cfotFacilityHistorical1weekMean OBJECT-TYPE
    SYNTAX        Integer32
    UNITS         "0.001 GHz"
    MAX-ACCESS    read-only
    STATUS        current
    DESCRIPTION   "Carrier Frequency Offset Mean"
    ::= { cfotFacilityHistorical1weekEntry 3 }

cfotFacilityHistorical1weekHigh OBJECT-TYPE
    SYNTAX        Integer32
    UNITS         "0.001 GHz"
    MAX-ACCESS    read-only
    STATUS        current
    DESCRIPTION   "Carrier Frequency Offset High"
    ::= { cfotFacilityHistorical1weekEntry 4 }

cfotFacilityHistorical1weekValidFlag OBJECT-TYPE
    SYNTAX        TruthValue
    MAX-ACCESS    read-only
    STATUS        current
    DESCRIPTION   "Valid Flag"
    ::= { cfotFacilityHistorical1weekEntry 5 }

cfotFacilityHistorical1weekTimeStamp OBJECT-TYPE
    SYNTAX        DateAndTime
    MAX-ACCESS    read-only
    STATUS        current
    DESCRIPTION   "Timestamp"
    ::= { cfotFacilityHistorical1weekEntry 6 }

endOfCfotFacilityHistorical1weekTable OBJECT-TYPE
    SYNTAX        Integer32
    MAX-ACCESS    read-only
    STATUS        current
    DESCRIPTION   ""
    ::= { pmFacilityPhysRecord 42 }

dgdFacilityHistorical15minTable OBJECT-TYPE
    SYNTAX        SEQUENCE OF DgdFacilityHistorical15minEntry
    MAX-ACCESS    not-accessible
    STATUS        current
    DESCRIPTION   ""
    ::= { pmFacilityPhysRecord 43 }

dgdFacilityHistorical15minEntry OBJECT-TYPE
    SYNTAX        DgdFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  dgdFacilityHistorical15minNumber
                }
    ::= { dgdFacilityHistorical15minTable 1 }

DgdFacilityHistorical15minEntry ::= SEQUENCE
  {    dgdFacilityHistorical15minNumber Integer32,
    dgdFacilityHistorical15minLow Integer32,
    dgdFacilityHistorical15minMean Integer32,
    dgdFacilityHistorical15minHigh Integer32,
    dgdFacilityHistorical15minValidFlag TruthValue,
    dgdFacilityHistorical15minTimeStamp DateAndTime }

dgdFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { dgdFacilityHistorical15minEntry 1 }

dgdFacilityHistorical15minLow OBJECT-TYPE
    SYNTAX        Integer32
    UNITS         "ps"
    MAX-ACCESS    read-only
    STATUS        current
    DESCRIPTION   "Differential Group Delay Low"
    ::= { dgdFacilityHistorical15minEntry 2 }

dgdFacilityHistorical15minMean OBJECT-TYPE
    SYNTAX        Integer32
    UNITS         "ps"
    MAX-ACCESS    read-only
    STATUS        current
    DESCRIPTION   "Differential Group Delay Mean"
    ::= { dgdFacilityHistorical15minEntry 3 }

dgdFacilityHistorical15minHigh OBJECT-TYPE
    SYNTAX        Integer32
    UNITS         "ps"
    MAX-ACCESS    read-only
    STATUS        current
    DESCRIPTION   "Differential Group Delay High"
    ::= { dgdFacilityHistorical15minEntry 4 }

dgdFacilityHistorical15minValidFlag OBJECT-TYPE
    SYNTAX        TruthValue
    MAX-ACCESS    read-only
    STATUS        current
    DESCRIPTION   "Valid Flag"
    ::= { dgdFacilityHistorical15minEntry 5 }

dgdFacilityHistorical15minTimeStamp OBJECT-TYPE
    SYNTAX        DateAndTime
    MAX-ACCESS    read-only
    STATUS        current
    DESCRIPTION   "Timestamp"
    ::= { dgdFacilityHistorical15minEntry 6 }

endOfDgdFacilityHistorical15minTable OBJECT-TYPE
    SYNTAX        Integer32
    MAX-ACCESS    read-only
    STATUS        current
    DESCRIPTION   ""
    ::= { pmFacilityPhysRecord 44 }

dgdFacilityHistorical1dayTable OBJECT-TYPE
    SYNTAX        SEQUENCE OF DgdFacilityHistorical1dayEntry
    MAX-ACCESS    not-accessible
    STATUS        current
    DESCRIPTION   ""
    ::= { pmFacilityPhysRecord 45 }

dgdFacilityHistorical1dayEntry OBJECT-TYPE
    SYNTAX        DgdFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  dgdFacilityHistorical1dayNumber
                }
    ::= { dgdFacilityHistorical1dayTable 1 }

DgdFacilityHistorical1dayEntry ::= SEQUENCE
  {    dgdFacilityHistorical1dayNumber Integer32,
    dgdFacilityHistorical1dayLow Integer32,
    dgdFacilityHistorical1dayMean Integer32,
    dgdFacilityHistorical1dayHigh Integer32,
    dgdFacilityHistorical1dayValidFlag TruthValue,
    dgdFacilityHistorical1dayTimeStamp DateAndTime }

dgdFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { dgdFacilityHistorical1dayEntry 1 }

dgdFacilityHistorical1dayLow OBJECT-TYPE
    SYNTAX        Integer32
    UNITS         "ps"
    MAX-ACCESS    read-only
    STATUS        current
    DESCRIPTION   "Differential Group Delay Low"
    ::= { dgdFacilityHistorical1dayEntry 2 }

dgdFacilityHistorical1dayMean OBJECT-TYPE
    SYNTAX        Integer32
    UNITS         "ps"
    MAX-ACCESS    read-only
    STATUS        current
    DESCRIPTION   "Differential Group Delay Mean"
    ::= { dgdFacilityHistorical1dayEntry 3 }

dgdFacilityHistorical1dayHigh OBJECT-TYPE
    SYNTAX        Integer32
    UNITS         "ps"
    MAX-ACCESS    read-only
    STATUS        current
    DESCRIPTION   "Differential Group Delay High"
    ::= { dgdFacilityHistorical1dayEntry 4 }

dgdFacilityHistorical1dayValidFlag OBJECT-TYPE
    SYNTAX        TruthValue
    MAX-ACCESS    read-only
    STATUS        current
    DESCRIPTION   "Valid Flag"
    ::= { dgdFacilityHistorical1dayEntry 5 }

dgdFacilityHistorical1dayTimeStamp OBJECT-TYPE
    SYNTAX        DateAndTime
    MAX-ACCESS    read-only
    STATUS        current
    DESCRIPTION   "Timestamp"
    ::= { dgdFacilityHistorical1dayEntry 6 }

endOfDgdFacilityHistorical1dayTable OBJECT-TYPE
    SYNTAX        Integer32
    MAX-ACCESS    read-only
    STATUS        current
    DESCRIPTION   ""
    ::= { pmFacilityPhysRecord 46 }

dgdFacilityHistorical1weekTable OBJECT-TYPE
    SYNTAX        SEQUENCE OF DgdFacilityHistorical1weekEntry
    MAX-ACCESS    not-accessible
    STATUS        current
    DESCRIPTION   ""
    ::= { pmFacilityPhysRecord 47 }

dgdFacilityHistorical1weekEntry OBJECT-TYPE
    SYNTAX        DgdFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  dgdFacilityHistorical1weekNumber
                }
    ::= { dgdFacilityHistorical1weekTable 1 }

DgdFacilityHistorical1weekEntry ::= SEQUENCE
  {    dgdFacilityHistorical1weekNumber Integer32,
    dgdFacilityHistorical1weekLow Integer32,
    dgdFacilityHistorical1weekMean Integer32,
    dgdFacilityHistorical1weekHigh Integer32,
    dgdFacilityHistorical1weekValidFlag TruthValue,
    dgdFacilityHistorical1weekTimeStamp DateAndTime }

dgdFacilityHistorical1weekNumber OBJECT-TYPE
    SYNTAX        Integer32 (1..52)
    MAX-ACCESS    not-accessible
    STATUS        current
    DESCRIPTION   "Number 1week"
    ::= { dgdFacilityHistorical1weekEntry 1 }

dgdFacilityHistorical1weekLow OBJECT-TYPE
    SYNTAX        Integer32
    UNITS         "ps"
    MAX-ACCESS    read-only
    STATUS        current
    DESCRIPTION   "Differential Group Delay Low"
    ::= { dgdFacilityHistorical1weekEntry 2 }

dgdFacilityHistorical1weekMean OBJECT-TYPE
    SYNTAX        Integer32
    UNITS         "ps"
    MAX-ACCESS    read-only
    STATUS        current
    DESCRIPTION   "Differential Group Delay Mean"
    ::= { dgdFacilityHistorical1weekEntry 3 }

dgdFacilityHistorical1weekHigh OBJECT-TYPE
    SYNTAX        Integer32
    UNITS         "ps"
    MAX-ACCESS    read-only
    STATUS        current
    DESCRIPTION   "Differential Group Delay High"
    ::= { dgdFacilityHistorical1weekEntry 4 }

dgdFacilityHistorical1weekValidFlag OBJECT-TYPE
    SYNTAX        TruthValue
    MAX-ACCESS    read-only
    STATUS        current
    DESCRIPTION   "Valid Flag"
    ::= { dgdFacilityHistorical1weekEntry 5 }

dgdFacilityHistorical1weekTimeStamp OBJECT-TYPE
    SYNTAX        DateAndTime
    MAX-ACCESS    read-only
    STATUS        current
    DESCRIPTION   "Timestamp"
    ::= { dgdFacilityHistorical1weekEntry 6 }

endOfDgdFacilityHistorical1weekTable OBJECT-TYPE
    SYNTAX        Integer32
    MAX-ACCESS    read-only
    STATUS        current
    DESCRIPTION   ""
    ::= { pmFacilityPhysRecord 48 }

cdFacilityHistorical15minTable OBJECT-TYPE
    SYNTAX        SEQUENCE OF CdFacilityHistorical15minEntry
    MAX-ACCESS    not-accessible
    STATUS        current
    DESCRIPTION   ""
    ::= { pmFacilityPhysRecord 49 }

cdFacilityHistorical15minEntry OBJECT-TYPE
    SYNTAX        CdFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  cdFacilityHistorical15minNumber
                }
    ::= { cdFacilityHistorical15minTable 1 }

CdFacilityHistorical15minEntry ::= SEQUENCE
  {    cdFacilityHistorical15minNumber Integer32,
    cdFacilityHistorical15minLow Integer32,
    cdFacilityHistorical15minMean Integer32,
    cdFacilityHistorical15minHigh Integer32,
    cdFacilityHistorical15minValidFlag TruthValue,
    cdFacilityHistorical15minTimeStamp DateAndTime }

cdFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { cdFacilityHistorical15minEntry 1 }

cdFacilityHistorical15minLow OBJECT-TYPE
    SYNTAX        Integer32
    UNITS         "ps/nm"
    MAX-ACCESS    read-only
    STATUS        current
    DESCRIPTION   "Chromatic Dispersion Compensation Low"
    ::= { cdFacilityHistorical15minEntry 2 }

cdFacilityHistorical15minMean OBJECT-TYPE
    SYNTAX        Integer32
    UNITS         "ps/nm"
    MAX-ACCESS    read-only
    STATUS        current
    DESCRIPTION   "Chromatic Dispersion Compensation Mean"
    ::= { cdFacilityHistorical15minEntry 3 }

cdFacilityHistorical15minHigh OBJECT-TYPE
    SYNTAX        Integer32
    UNITS         "ps/nm"
    MAX-ACCESS    read-only
    STATUS        current
    DESCRIPTION   "Chromatic Dispersion Compensation High"
    ::= { cdFacilityHistorical15minEntry 4 }

cdFacilityHistorical15minValidFlag OBJECT-TYPE
    SYNTAX        TruthValue
    MAX-ACCESS    read-only
    STATUS        current
    DESCRIPTION   "Valid Flag"
    ::= { cdFacilityHistorical15minEntry 5 }

cdFacilityHistorical15minTimeStamp OBJECT-TYPE
    SYNTAX        DateAndTime
    MAX-ACCESS    read-only
    STATUS        current
    DESCRIPTION   "Timestamp"
    ::= { cdFacilityHistorical15minEntry 6 }

endOfCdFacilityHistorical15minTable OBJECT-TYPE
    SYNTAX        Integer32
    MAX-ACCESS    read-only
    STATUS        current
    DESCRIPTION   ""
    ::= { pmFacilityPhysRecord 50 }

cdFacilityHistorical1dayTable OBJECT-TYPE
    SYNTAX        SEQUENCE OF CdFacilityHistorical1dayEntry
    MAX-ACCESS    not-accessible
    STATUS        current
    DESCRIPTION   ""
    ::= { pmFacilityPhysRecord 51 }

cdFacilityHistorical1dayEntry OBJECT-TYPE
    SYNTAX        CdFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  cdFacilityHistorical1dayNumber
                }
    ::= { cdFacilityHistorical1dayTable 1 }

CdFacilityHistorical1dayEntry ::= SEQUENCE
  {    cdFacilityHistorical1dayNumber Integer32,
    cdFacilityHistorical1dayLow Integer32,
    cdFacilityHistorical1dayMean Integer32,
    cdFacilityHistorical1dayHigh Integer32,
    cdFacilityHistorical1dayValidFlag TruthValue,
    cdFacilityHistorical1dayTimeStamp DateAndTime }

cdFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { cdFacilityHistorical1dayEntry 1 }

cdFacilityHistorical1dayLow OBJECT-TYPE
    SYNTAX        Integer32
    UNITS         "ps/nm"
    MAX-ACCESS    read-only
    STATUS        current
    DESCRIPTION   "Chromatic Dispersion Compensation Low"
    ::= { cdFacilityHistorical1dayEntry 2 }

cdFacilityHistorical1dayMean OBJECT-TYPE
    SYNTAX        Integer32
    UNITS         "ps/nm"
    MAX-ACCESS    read-only
    STATUS        current
    DESCRIPTION   "Chromatic Dispersion Compensation Mean"
    ::= { cdFacilityHistorical1dayEntry 3 }

cdFacilityHistorical1dayHigh OBJECT-TYPE
    SYNTAX        Integer32
    UNITS         "ps/nm"
    MAX-ACCESS    read-only
    STATUS        current
    DESCRIPTION   "Chromatic Dispersion Compensation High"
    ::= { cdFacilityHistorical1dayEntry 4 }

cdFacilityHistorical1dayValidFlag OBJECT-TYPE
    SYNTAX        TruthValue
    MAX-ACCESS    read-only
    STATUS        current
    DESCRIPTION   "Valid Flag"
    ::= { cdFacilityHistorical1dayEntry 5 }

cdFacilityHistorical1dayTimeStamp OBJECT-TYPE
    SYNTAX        DateAndTime
    MAX-ACCESS    read-only
    STATUS        current
    DESCRIPTION   "Timestamp"
    ::= { cdFacilityHistorical1dayEntry 6 }

endOfCdFacilityHistorical1dayTable OBJECT-TYPE
    SYNTAX        Integer32
    MAX-ACCESS    read-only
    STATUS        current
    DESCRIPTION   ""
    ::= { pmFacilityPhysRecord 52 }

cdFacilityHistorical1weekTable OBJECT-TYPE
    SYNTAX        SEQUENCE OF CdFacilityHistorical1weekEntry
    MAX-ACCESS    not-accessible
    STATUS        current
    DESCRIPTION   ""
    ::= { pmFacilityPhysRecord 53 }

cdFacilityHistorical1weekEntry OBJECT-TYPE
    SYNTAX        CdFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  cdFacilityHistorical1weekNumber
                }
    ::= { cdFacilityHistorical1weekTable 1 }

CdFacilityHistorical1weekEntry ::= SEQUENCE
  {    cdFacilityHistorical1weekNumber Integer32,
    cdFacilityHistorical1weekLow Integer32,
    cdFacilityHistorical1weekMean Integer32,
    cdFacilityHistorical1weekHigh Integer32,
    cdFacilityHistorical1weekValidFlag TruthValue,
    cdFacilityHistorical1weekTimeStamp DateAndTime }

cdFacilityHistorical1weekNumber OBJECT-TYPE
    SYNTAX        Integer32 (1..52)
    MAX-ACCESS    not-accessible
    STATUS        current
    DESCRIPTION   "Number 1week"
    ::= { cdFacilityHistorical1weekEntry 1 }

cdFacilityHistorical1weekLow OBJECT-TYPE
    SYNTAX        Integer32
    UNITS         "ps/nm"
    MAX-ACCESS    read-only
    STATUS        current
    DESCRIPTION   "Chromatic Dispersion Compensation Low"
    ::= { cdFacilityHistorical1weekEntry 2 }

cdFacilityHistorical1weekMean OBJECT-TYPE
    SYNTAX        Integer32
    UNITS         "ps/nm"
    MAX-ACCESS    read-only
    STATUS        current
    DESCRIPTION   "Chromatic Dispersion Compensation Mean"
    ::= { cdFacilityHistorical1weekEntry 3 }

cdFacilityHistorical1weekHigh OBJECT-TYPE
    SYNTAX        Integer32
    UNITS         "ps/nm"
    MAX-ACCESS    read-only
    STATUS        current
    DESCRIPTION   "Chromatic Dispersion Compensation High"
    ::= { cdFacilityHistorical1weekEntry 4 }

cdFacilityHistorical1weekValidFlag OBJECT-TYPE
    SYNTAX        TruthValue
    MAX-ACCESS    read-only
    STATUS        current
    DESCRIPTION   "Valid Flag"
    ::= { cdFacilityHistorical1weekEntry 5 }

cdFacilityHistorical1weekTimeStamp OBJECT-TYPE
    SYNTAX        DateAndTime
    MAX-ACCESS    read-only
    STATUS        current
    DESCRIPTION   "Timestamp"
    ::= { cdFacilityHistorical1weekEntry 6 }

endOfCdFacilityHistorical1weekTable OBJECT-TYPE
    SYNTAX        Integer32
    MAX-ACCESS    read-only
    STATUS        current
    DESCRIPTION   ""
    ::= { pmFacilityPhysRecord 54 }

latencyFacilityHistorical15minTable OBJECT-TYPE
    SYNTAX        SEQUENCE OF LatencyFacilityHistorical15minEntry
    MAX-ACCESS    not-accessible
    STATUS        current
    DESCRIPTION   ""
    ::= { pmFacilityPhysRecord 55 }

latencyFacilityHistorical15minEntry OBJECT-TYPE
    SYNTAX        LatencyFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  latencyFacilityHistorical15minNumber
                }
    ::= { latencyFacilityHistorical15minTable 1 }

LatencyFacilityHistorical15minEntry ::= SEQUENCE
  {    latencyFacilityHistorical15minNumber Integer32,
    latencyFacilityHistorical15minLow Unsigned32,
    latencyFacilityHistorical15minMean Unsigned32,
    latencyFacilityHistorical15minHigh Unsigned32,
    latencyFacilityHistorical15minValidFlag TruthValue,
    latencyFacilityHistorical15minTimeStamp DateAndTime }

latencyFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { latencyFacilityHistorical15minEntry 1 }

latencyFacilityHistorical15minLow OBJECT-TYPE
    SYNTAX        Unsigned32
    UNITS         "0.1 us"
    MAX-ACCESS    read-only
    STATUS        current
    DESCRIPTION   "Measured round trip delay"
    ::= { latencyFacilityHistorical15minEntry 2 }

latencyFacilityHistorical15minMean OBJECT-TYPE
    SYNTAX        Unsigned32
    UNITS         "0.1 us"
    MAX-ACCESS    read-only
    STATUS        current
    DESCRIPTION   "Measured round trip delay"
    ::= { latencyFacilityHistorical15minEntry 3 }

latencyFacilityHistorical15minHigh OBJECT-TYPE
    SYNTAX        Unsigned32
    UNITS         "0.1 us"
    MAX-ACCESS    read-only
    STATUS        current
    DESCRIPTION   "Measured round trip delay"
    ::= { latencyFacilityHistorical15minEntry 4 }

latencyFacilityHistorical15minValidFlag OBJECT-TYPE
    SYNTAX        TruthValue
    MAX-ACCESS    read-only
    STATUS        current
    DESCRIPTION   "Valid Flag"
    ::= { latencyFacilityHistorical15minEntry 5 }

latencyFacilityHistorical15minTimeStamp OBJECT-TYPE
    SYNTAX        DateAndTime
    MAX-ACCESS    read-only
    STATUS        current
    DESCRIPTION   "Timestamp"
    ::= { latencyFacilityHistorical15minEntry 6 }

endOfLatencyFacilityHistorical15minTable OBJECT-TYPE
    SYNTAX        Integer32
    MAX-ACCESS    read-only
    STATUS        current
    DESCRIPTION   ""
    ::= { pmFacilityPhysRecord 56 }

latencyFacilityHistorical1dayTable OBJECT-TYPE
    SYNTAX        SEQUENCE OF LatencyFacilityHistorical1dayEntry
    MAX-ACCESS    not-accessible
    STATUS        current
    DESCRIPTION   ""
    ::= { pmFacilityPhysRecord 57 }

latencyFacilityHistorical1dayEntry OBJECT-TYPE
    SYNTAX        LatencyFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  latencyFacilityHistorical1dayNumber
                }
    ::= { latencyFacilityHistorical1dayTable 1 }

LatencyFacilityHistorical1dayEntry ::= SEQUENCE
  {    latencyFacilityHistorical1dayNumber Integer32,
    latencyFacilityHistorical1dayLow Unsigned32,
    latencyFacilityHistorical1dayMean Unsigned32,
    latencyFacilityHistorical1dayHigh Unsigned32,
    latencyFacilityHistorical1dayValidFlag TruthValue,
    latencyFacilityHistorical1dayTimeStamp DateAndTime }

latencyFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { latencyFacilityHistorical1dayEntry 1 }

latencyFacilityHistorical1dayLow OBJECT-TYPE
    SYNTAX        Unsigned32
    UNITS         "0.1 us"
    MAX-ACCESS    read-only
    STATUS        current
    DESCRIPTION   "Measured round trip delay"
    ::= { latencyFacilityHistorical1dayEntry 2 }

latencyFacilityHistorical1dayMean OBJECT-TYPE
    SYNTAX        Unsigned32
    UNITS         "0.1 us"
    MAX-ACCESS    read-only
    STATUS        current
    DESCRIPTION   "Measured round trip delay"
    ::= { latencyFacilityHistorical1dayEntry 3 }

latencyFacilityHistorical1dayHigh OBJECT-TYPE
    SYNTAX        Unsigned32
    UNITS         "0.1 us"
    MAX-ACCESS    read-only
    STATUS        current
    DESCRIPTION   "Measured round trip delay"
    ::= { latencyFacilityHistorical1dayEntry 4 }

latencyFacilityHistorical1dayValidFlag OBJECT-TYPE
    SYNTAX        TruthValue
    MAX-ACCESS    read-only
    STATUS        current
    DESCRIPTION   "Valid Flag"
    ::= { latencyFacilityHistorical1dayEntry 5 }

latencyFacilityHistorical1dayTimeStamp OBJECT-TYPE
    SYNTAX        DateAndTime
    MAX-ACCESS    read-only
    STATUS        current
    DESCRIPTION   "Timestamp"
    ::= { latencyFacilityHistorical1dayEntry 6 }

endOfLatencyFacilityHistorical1dayTable OBJECT-TYPE
    SYNTAX        Integer32
    MAX-ACCESS    read-only
    STATUS        current
    DESCRIPTION   ""
    ::= { pmFacilityPhysRecord 58 }

latencyFacilityHistorical1weekTable OBJECT-TYPE
    SYNTAX        SEQUENCE OF LatencyFacilityHistorical1weekEntry
    MAX-ACCESS    not-accessible
    STATUS        current
    DESCRIPTION   ""
    ::= { pmFacilityPhysRecord 59 }

latencyFacilityHistorical1weekEntry OBJECT-TYPE
    SYNTAX        LatencyFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  latencyFacilityHistorical1weekNumber
                }
    ::= { latencyFacilityHistorical1weekTable 1 }

LatencyFacilityHistorical1weekEntry ::= SEQUENCE
  {    latencyFacilityHistorical1weekNumber Integer32,
    latencyFacilityHistorical1weekLow Unsigned32,
    latencyFacilityHistorical1weekMean Unsigned32,
    latencyFacilityHistorical1weekHigh Unsigned32,
    latencyFacilityHistorical1weekValidFlag TruthValue,
    latencyFacilityHistorical1weekTimeStamp DateAndTime }

latencyFacilityHistorical1weekNumber OBJECT-TYPE
    SYNTAX        Integer32 (1..52)
    MAX-ACCESS    not-accessible
    STATUS        current
    DESCRIPTION   "Number 1week"
    ::= { latencyFacilityHistorical1weekEntry 1 }

latencyFacilityHistorical1weekLow OBJECT-TYPE
    SYNTAX        Unsigned32
    UNITS         "0.1 us"
    MAX-ACCESS    read-only
    STATUS        current
    DESCRIPTION   "Measured round trip delay"
    ::= { latencyFacilityHistorical1weekEntry 2 }

latencyFacilityHistorical1weekMean OBJECT-TYPE
    SYNTAX        Unsigned32
    UNITS         "0.1 us"
    MAX-ACCESS    read-only
    STATUS        current
    DESCRIPTION   "Measured round trip delay"
    ::= { latencyFacilityHistorical1weekEntry 3 }

latencyFacilityHistorical1weekHigh OBJECT-TYPE
    SYNTAX        Unsigned32
    UNITS         "0.1 us"
    MAX-ACCESS    read-only
    STATUS        current
    DESCRIPTION   "Measured round trip delay"
    ::= { latencyFacilityHistorical1weekEntry 4 }

latencyFacilityHistorical1weekValidFlag OBJECT-TYPE
    SYNTAX        TruthValue
    MAX-ACCESS    read-only
    STATUS        current
    DESCRIPTION   "Valid Flag"
    ::= { latencyFacilityHistorical1weekEntry 5 }

latencyFacilityHistorical1weekTimeStamp OBJECT-TYPE
    SYNTAX        DateAndTime
    MAX-ACCESS    read-only
    STATUS        current
    DESCRIPTION   "Timestamp"
    ::= { latencyFacilityHistorical1weekEntry 6 }

endOfLatencyFacilityHistorical1weekTable OBJECT-TYPE
    SYNTAX        Integer32
    MAX-ACCESS    read-only
    STATUS        current
    DESCRIPTION   ""
    ::= { pmFacilityPhysRecord 60 }

cdcFacilityHistorical15minTable OBJECT-TYPE
    SYNTAX        SEQUENCE OF CdcFacilityHistorical15minEntry
    MAX-ACCESS    not-accessible
    STATUS        current
    DESCRIPTION   ""
    ::= { pmFacilityPhysRecord 61 }

cdcFacilityHistorical15minEntry OBJECT-TYPE
    SYNTAX        CdcFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  cdcFacilityHistorical15minNumber
                }
    ::= { cdcFacilityHistorical15minTable 1 }

CdcFacilityHistorical15minEntry ::= SEQUENCE
  {    cdcFacilityHistorical15minNumber Integer32,
    cdcFacilityHistorical15minLow Integer32,
    cdcFacilityHistorical15minMean Integer32,
    cdcFacilityHistorical15minHigh Integer32,
    cdcFacilityHistorical15minValidFlag TruthValue,
    cdcFacilityHistorical15minTimeStamp DateAndTime }

cdcFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { cdcFacilityHistorical15minEntry 1 }

cdcFacilityHistorical15minLow OBJECT-TYPE
    SYNTAX        Integer32
    UNITS         "ps/nm"
    MAX-ACCESS    read-only
    STATUS        current
    DESCRIPTION   "Chromatic Dispersion Compensation Low"
    ::= { cdcFacilityHistorical15minEntry 2 }

cdcFacilityHistorical15minMean OBJECT-TYPE
    SYNTAX        Integer32
    UNITS         "ps/nm"
    MAX-ACCESS    read-only
    STATUS        current
    DESCRIPTION   "Chromatic Dispersion Compensation Mean"
    ::= { cdcFacilityHistorical15minEntry 3 }

cdcFacilityHistorical15minHigh OBJECT-TYPE
    SYNTAX        Integer32
    UNITS         "ps/nm"
    MAX-ACCESS    read-only
    STATUS        current
    DESCRIPTION   "Chromatic Dispersion Compensation High"
    ::= { cdcFacilityHistorical15minEntry 4 }

cdcFacilityHistorical15minValidFlag OBJECT-TYPE
    SYNTAX        TruthValue
    MAX-ACCESS    read-only
    STATUS        current
    DESCRIPTION   "Valid Flag"
    ::= { cdcFacilityHistorical15minEntry 5 }

cdcFacilityHistorical15minTimeStamp OBJECT-TYPE
    SYNTAX        DateAndTime
    MAX-ACCESS    read-only
    STATUS        current
    DESCRIPTION   "Timestamp"
    ::= { cdcFacilityHistorical15minEntry 6 }

endOfCdcFacilityHistorical15minTable OBJECT-TYPE
    SYNTAX        Integer32
    MAX-ACCESS    read-only
    STATUS        current
    DESCRIPTION   ""
    ::= { pmFacilityPhysRecord 62 }

cdcFacilityHistorical1dayTable OBJECT-TYPE
    SYNTAX        SEQUENCE OF CdcFacilityHistorical1dayEntry
    MAX-ACCESS    not-accessible
    STATUS        current
    DESCRIPTION   ""
    ::= { pmFacilityPhysRecord 63 }

cdcFacilityHistorical1dayEntry OBJECT-TYPE
    SYNTAX        CdcFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  cdcFacilityHistorical1dayNumber
                }
    ::= { cdcFacilityHistorical1dayTable 1 }

CdcFacilityHistorical1dayEntry ::= SEQUENCE
  {    cdcFacilityHistorical1dayNumber Integer32,
    cdcFacilityHistorical1dayLow Integer32,
    cdcFacilityHistorical1dayMean Integer32,
    cdcFacilityHistorical1dayHigh Integer32,
    cdcFacilityHistorical1dayValidFlag TruthValue,
    cdcFacilityHistorical1dayTimeStamp DateAndTime }

cdcFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { cdcFacilityHistorical1dayEntry 1 }

cdcFacilityHistorical1dayLow OBJECT-TYPE
    SYNTAX        Integer32
    UNITS         "ps/nm"
    MAX-ACCESS    read-only
    STATUS        current
    DESCRIPTION   "Chromatic Dispersion Compensation Low"
    ::= { cdcFacilityHistorical1dayEntry 2 }

cdcFacilityHistorical1dayMean OBJECT-TYPE
    SYNTAX        Integer32
    UNITS         "ps/nm"
    MAX-ACCESS    read-only
    STATUS        current
    DESCRIPTION   "Chromatic Dispersion Compensation Mean"
    ::= { cdcFacilityHistorical1dayEntry 3 }

cdcFacilityHistorical1dayHigh OBJECT-TYPE
    SYNTAX        Integer32
    UNITS         "ps/nm"
    MAX-ACCESS    read-only
    STATUS        current
    DESCRIPTION   "Chromatic Dispersion Compensation High"
    ::= { cdcFacilityHistorical1dayEntry 4 }

cdcFacilityHistorical1dayValidFlag OBJECT-TYPE
    SYNTAX        TruthValue
    MAX-ACCESS    read-only
    STATUS        current
    DESCRIPTION   "Valid Flag"
    ::= { cdcFacilityHistorical1dayEntry 5 }

cdcFacilityHistorical1dayTimeStamp OBJECT-TYPE
    SYNTAX        DateAndTime
    MAX-ACCESS    read-only
    STATUS        current
    DESCRIPTION   "Timestamp"
    ::= { cdcFacilityHistorical1dayEntry 6 }

endOfCdcFacilityHistorical1dayTable OBJECT-TYPE
    SYNTAX        Integer32
    MAX-ACCESS    read-only
    STATUS        current
    DESCRIPTION   ""
    ::= { pmFacilityPhysRecord 64 }

cdcFacilityHistorical1weekTable OBJECT-TYPE
    SYNTAX        SEQUENCE OF CdcFacilityHistorical1weekEntry
    MAX-ACCESS    not-accessible
    STATUS        current
    DESCRIPTION   ""
    ::= { pmFacilityPhysRecord 65 }

cdcFacilityHistorical1weekEntry OBJECT-TYPE
    SYNTAX        CdcFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  cdcFacilityHistorical1weekNumber
                }
    ::= { cdcFacilityHistorical1weekTable 1 }

CdcFacilityHistorical1weekEntry ::= SEQUENCE
  {    cdcFacilityHistorical1weekNumber Integer32,
    cdcFacilityHistorical1weekLow Integer32,
    cdcFacilityHistorical1weekMean Integer32,
    cdcFacilityHistorical1weekHigh Integer32,
    cdcFacilityHistorical1weekValidFlag TruthValue,
    cdcFacilityHistorical1weekTimeStamp DateAndTime }

cdcFacilityHistorical1weekNumber OBJECT-TYPE
    SYNTAX        Integer32 (1..52)
    MAX-ACCESS    not-accessible
    STATUS        current
    DESCRIPTION   "Number 1week"
    ::= { cdcFacilityHistorical1weekEntry 1 }

cdcFacilityHistorical1weekLow OBJECT-TYPE
    SYNTAX        Integer32
    UNITS         "ps/nm"
    MAX-ACCESS    read-only
    STATUS        current
    DESCRIPTION   "Chromatic Dispersion Compensation Low"
    ::= { cdcFacilityHistorical1weekEntry 2 }

cdcFacilityHistorical1weekMean OBJECT-TYPE
    SYNTAX        Integer32
    UNITS         "ps/nm"
    MAX-ACCESS    read-only
    STATUS        current
    DESCRIPTION   "Chromatic Dispersion Compensation Mean"
    ::= { cdcFacilityHistorical1weekEntry 3 }

cdcFacilityHistorical1weekHigh OBJECT-TYPE
    SYNTAX        Integer32
    UNITS         "ps/nm"
    MAX-ACCESS    read-only
    STATUS        current
    DESCRIPTION   "Chromatic Dispersion Compensation High"
    ::= { cdcFacilityHistorical1weekEntry 4 }

cdcFacilityHistorical1weekValidFlag OBJECT-TYPE
    SYNTAX        TruthValue
    MAX-ACCESS    read-only
    STATUS        current
    DESCRIPTION   "Valid Flag"
    ::= { cdcFacilityHistorical1weekEntry 5 }

cdcFacilityHistorical1weekTimeStamp OBJECT-TYPE
    SYNTAX        DateAndTime
    MAX-ACCESS    read-only
    STATUS        current
    DESCRIPTION   "Timestamp"
    ::= { cdcFacilityHistorical1weekEntry 6 }

endOfCdcFacilityHistorical1weekTable OBJECT-TYPE
    SYNTAX        Integer32
    MAX-ACCESS    read-only
    STATUS        current
    DESCRIPTION   ""
    ::= { pmFacilityPhysRecord 66 }

qfactFacilityHistorical15minTable OBJECT-TYPE
    SYNTAX        SEQUENCE OF QfactFacilityHistorical15minEntry
    MAX-ACCESS    not-accessible
    STATUS        current
    DESCRIPTION   ""
    ::= { pmFacilityPhysRecord 67 }

qfactFacilityHistorical15minEntry OBJECT-TYPE
    SYNTAX        QfactFacilityHistorical15minEntry
    MAX-ACCESS    not-accessible
    STATUS        current
    DESCRIPTION   ""
    INDEX       {
                  entityDcnShelfNo,
                  entityDcnSlotNo,
                  entityDcnPortNo,
                  entityDcnExtNo,
                  entityDcnClassName,
                  qfactFacilityHistorical15minNumber
                }
    ::= { qfactFacilityHistorical15minTable 1 }

QfactFacilityHistorical15minEntry ::= SEQUENCE
  {    qfactFacilityHistorical15minNumber Integer32,
    qfactFacilityHistorical15minLow Integer32,
    qfactFacilityHistorical15minMean Integer32,
    qfactFacilityHistorical15minHigh Integer32,
    qfactFacilityHistorical15minValidFlag TruthValue,
    qfactFacilityHistorical15minTimeStamp DateAndTime }

qfactFacilityHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { qfactFacilityHistorical15minEntry 1 }

qfactFacilityHistorical15minLow OBJECT-TYPE
    SYNTAX        Integer32
    UNITS         "0.1 dB"
    MAX-ACCESS    read-only
    STATUS        current
    DESCRIPTION   "Quality Factor Low"
    ::= { qfactFacilityHistorical15minEntry 2 }

qfactFacilityHistorical15minMean OBJECT-TYPE
    SYNTAX        Integer32
    UNITS         "0.1 dB"
    MAX-ACCESS    read-only
    STATUS        current
    DESCRIPTION   "Quality Factor Mean"
    ::= { qfactFacilityHistorical15minEntry 3 }

qfactFacilityHistorical15minHigh OBJECT-TYPE
    SYNTAX        Integer32
    UNITS         "0.1 dB"
    MAX-ACCESS    read-only
    STATUS        current
    DESCRIPTION   "Quality Factor High"
    ::= { qfactFacilityHistorical15minEntry 4 }

qfactFacilityHistorical15minValidFlag OBJECT-TYPE
    SYNTAX        TruthValue
    MAX-ACCESS    read-only
    STATUS        current
    DESCRIPTION   "Valid Flag"
    ::= { qfactFacilityHistorical15minEntry 5 }

qfactFacilityHistorical15minTimeStamp OBJECT-TYPE
    SYNTAX        DateAndTime
    MAX-ACCESS    read-only
    STATUS        current
    DESCRIPTION   "Timestamp"
    ::= { qfactFacilityHistorical15minEntry 6 }

endOfQfactFacilityHistorical15minTable OBJECT-TYPE
    SYNTAX        Integer32
    MAX-ACCESS    read-only
    STATUS        current
    DESCRIPTION   ""
    ::= { pmFacilityPhysRecord 68 }

qfactFacilityHistorical1dayTable OBJECT-TYPE
    SYNTAX        SEQUENCE OF QfactFacilityHistorical1dayEntry
    MAX-ACCESS    not-accessible
    STATUS        current
    DESCRIPTION   ""
    ::= { pmFacilityPhysRecord 69 }

qfactFacilityHistorical1dayEntry OBJECT-TYPE
    SYNTAX        QfactFacilityHistorical1dayEntry
    MAX-ACCESS    not-accessible
    STATUS        current
    DESCRIPTION   ""
    INDEX       {
                  entityDcnShelfNo,
                  entityDcnSlotNo,
                  entityDcnPortNo,
                  entityDcnExtNo,
                  entityDcnClassName,
                  qfactFacilityHistorical1dayNumber
                }
    ::= { qfactFacilityHistorical1dayTable 1 }

QfactFacilityHistorical1dayEntry ::= SEQUENCE
  {    qfactFacilityHistorical1dayNumber Integer32,
    qfactFacilityHistorical1dayLow Integer32,
    qfactFacilityHistorical1dayMean Integer32,
    qfactFacilityHistorical1dayHigh Integer32,
    qfactFacilityHistorical1dayValidFlag TruthValue,
    qfactFacilityHistorical1dayTimeStamp DateAndTime }

qfactFacilityHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { qfactFacilityHistorical1dayEntry 1 }

qfactFacilityHistorical1dayLow OBJECT-TYPE
    SYNTAX        Integer32
    UNITS         "0.1 dB"
    MAX-ACCESS    read-only
    STATUS        current
    DESCRIPTION   "Quality Factor Low"
    ::= { qfactFacilityHistorical1dayEntry 2 }

qfactFacilityHistorical1dayMean OBJECT-TYPE
    SYNTAX        Integer32
    UNITS         "0.1 dB"
    MAX-ACCESS    read-only
    STATUS        current
    DESCRIPTION   "Quality Factor Mean"
    ::= { qfactFacilityHistorical1dayEntry 3 }

qfactFacilityHistorical1dayHigh OBJECT-TYPE
    SYNTAX        Integer32
    UNITS         "0.1 dB"
    MAX-ACCESS    read-only
    STATUS        current
    DESCRIPTION   "Quality Factor High"
    ::= { qfactFacilityHistorical1dayEntry 4 }

qfactFacilityHistorical1dayValidFlag OBJECT-TYPE
    SYNTAX        TruthValue
    MAX-ACCESS    read-only
    STATUS        current
    DESCRIPTION   "Valid Flag"
    ::= { qfactFacilityHistorical1dayEntry 5 }

qfactFacilityHistorical1dayTimeStamp OBJECT-TYPE
    SYNTAX        DateAndTime
    MAX-ACCESS    read-only
    STATUS        current
    DESCRIPTION   "Timestamp"
    ::= { qfactFacilityHistorical1dayEntry 6 }

endOfQfactFacilityHistorical1dayTable OBJECT-TYPE
    SYNTAX        Integer32
    MAX-ACCESS    read-only
    STATUS        current
    DESCRIPTION   ""
    ::= { pmFacilityPhysRecord 70 }

qfactFacilityHistorical1weekTable OBJECT-TYPE
    SYNTAX        SEQUENCE OF QfactFacilityHistorical1weekEntry
    MAX-ACCESS    not-accessible
    STATUS        current
    DESCRIPTION   ""
    ::= { pmFacilityPhysRecord 71 }

qfactFacilityHistorical1weekEntry OBJECT-TYPE
    SYNTAX        QfactFacilityHistorical1weekEntry
    MAX-ACCESS    not-accessible
    STATUS        current
    DESCRIPTION   ""
    INDEX       {
                  entityDcnShelfNo,
                  entityDcnSlotNo,
                  entityDcnPortNo,
                  entityDcnExtNo,
                  entityDcnClassName,
                  qfactFacilityHistorical1weekNumber
                }
    ::= { qfactFacilityHistorical1weekTable 1 }

QfactFacilityHistorical1weekEntry ::= SEQUENCE
  {    qfactFacilityHistorical1weekNumber Integer32,
    qfactFacilityHistorical1weekLow Integer32,
    qfactFacilityHistorical1weekMean Integer32,
    qfactFacilityHistorical1weekHigh Integer32,
    qfactFacilityHistorical1weekValidFlag TruthValue,
    qfactFacilityHistorical1weekTimeStamp DateAndTime }

qfactFacilityHistorical1weekNumber OBJECT-TYPE
    SYNTAX        Integer32 (1..52)
    MAX-ACCESS    not-accessible
    STATUS        current
    DESCRIPTION   "Number 1week"
    ::= { qfactFacilityHistorical1weekEntry 1 }

qfactFacilityHistorical1weekLow OBJECT-TYPE
    SYNTAX        Integer32
    UNITS         "0.1 dB"
    MAX-ACCESS    read-only
    STATUS        current
    DESCRIPTION   "Quality Factor Low"
    ::= { qfactFacilityHistorical1weekEntry 2 }

qfactFacilityHistorical1weekMean OBJECT-TYPE
    SYNTAX        Integer32
    UNITS         "0.1 dB"
    MAX-ACCESS    read-only
    STATUS        current
    DESCRIPTION   "Quality Factor Mean"
    ::= { qfactFacilityHistorical1weekEntry 3 }

qfactFacilityHistorical1weekHigh OBJECT-TYPE
    SYNTAX        Integer32
    UNITS         "0.1 dB"
    MAX-ACCESS    read-only
    STATUS        current
    DESCRIPTION   "Quality Factor High"
    ::= { qfactFacilityHistorical1weekEntry 4 }

qfactFacilityHistorical1weekValidFlag OBJECT-TYPE
    SYNTAX        TruthValue
    MAX-ACCESS    read-only
    STATUS        current
    DESCRIPTION   "Valid Flag"
    ::= { qfactFacilityHistorical1weekEntry 5 }

qfactFacilityHistorical1weekTimeStamp OBJECT-TYPE
    SYNTAX        DateAndTime
    MAX-ACCESS    read-only
    STATUS        current
    DESCRIPTION   "Timestamp"
    ::= { qfactFacilityHistorical1weekEntry 6 }

endOfQfactFacilityHistorical1weekTable OBJECT-TYPE
    SYNTAX        Integer32
    MAX-ACCESS    read-only
    STATUS        current
    DESCRIPTION   ""
    ::= { pmFacilityPhysRecord 72 }

endOfPmFacilityPhysRecord OBJECT-TYPE
    SYNTAX        Integer32
    MAX-ACCESS    read-only
    STATUS        current
    DESCRIPTION   ""
    ::= { pmFacilityPhysRecord 10000 }

terminPointPhysInstValueTable OBJECT-TYPE
    SYNTAX        SEQUENCE OF TerminPointPhysInstValueEntry
    MAX-ACCESS    not-accessible
    STATUS        current
    DESCRIPTION   ""
    ::= { pmTerminPointPhysValue 1 }

terminPointPhysInstValueEntry OBJECT-TYPE
    SYNTAX        TerminPointPhysInstValueEntry
    MAX-ACCESS    not-accessible
    STATUS        current
    DESCRIPTION   ""
    INDEX       {
                  entityTerminPointIndexNo1,
                  entityTerminPointIndexNo2,
                  entityTerminPointIndexNo3,
                  entityTerminPointIndexNo4,
                  entityTerminPointClassName
                }
    ::= { terminPointPhysInstValueTable 1 }

TerminPointPhysInstValueEntry ::= SEQUENCE
  {    terminPointPhysInstValueFiberConnAttenuation Integer32,
    terminPointPhysInstValueInputPower Integer32,
    terminPointPhysInstValueOutputPower Integer32 }

terminPointPhysInstValueFiberConnAttenuation OBJECT-TYPE
    SYNTAX        Integer32
    UNITS         "0.1 dB"
    MAX-ACCESS    read-only
    STATUS        current
    DESCRIPTION   "Fiber Connection Attenuation"
    ::= { terminPointPhysInstValueEntry 1 }

terminPointPhysInstValueInputPower OBJECT-TYPE
    SYNTAX        Integer32
    UNITS         "0.1 dBm"
    MAX-ACCESS    read-only
    STATUS        current
    DESCRIPTION   "Total Optical Input Power Received"
    ::= { terminPointPhysInstValueEntry 2 }

terminPointPhysInstValueOutputPower OBJECT-TYPE
    SYNTAX        Integer32
    UNITS         "0.1 dBm"
    MAX-ACCESS    read-only
    STATUS        current
    DESCRIPTION   "Instantaneous Optical Power Transmitted (Output)"
    ::= { terminPointPhysInstValueEntry 3 }

endOfTerminPointPhysInstValueTable OBJECT-TYPE
    SYNTAX        Integer32
    MAX-ACCESS    read-only
    STATUS        current
    DESCRIPTION   ""
    ::= { pmTerminPointPhysValue 2 }

endOfPmTerminPointPhysical OBJECT-TYPE
    SYNTAX        Integer32
    MAX-ACCESS    read-only
    STATUS        current
    DESCRIPTION   ""
    ::= { pmTerminPointPhysValue 10000 }

dsOptMuxCurrent15minTable OBJECT-TYPE
    SYNTAX        SEQUENCE OF DsOptMuxCurrent15minEntry
    MAX-ACCESS    not-accessible
    STATUS        current
    DESCRIPTION   ""
    ::= { pmOptMuxDataRecord 1 }

dsOptMuxCurrent15minEntry OBJECT-TYPE
    SYNTAX        DsOptMuxCurrent15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName
                }
    ::= { dsOptMuxCurrent15minTable 1 }

DsOptMuxCurrent15minEntry ::= SEQUENCE
  {    dsOptMuxCurrent15minDS Unsigned32,
    dsOptMuxCurrent15minElapsedTime Integer32 }

dsOptMuxCurrent15minDS OBJECT-TYPE
    SYNTAX        Unsigned32
    MAX-ACCESS    read-only
    STATUS        current
    DESCRIPTION   "Defect Seconds"
    ::= { dsOptMuxCurrent15minEntry 1 }

dsOptMuxCurrent15minElapsedTime OBJECT-TYPE
    SYNTAX        Integer32 (0..9000)
    MAX-ACCESS    read-only
    STATUS        current
    DESCRIPTION   "Elapsed 15Min"
    ::= { dsOptMuxCurrent15minEntry 2 }

endOfDsOptMuxCurrent15minTable OBJECT-TYPE
    SYNTAX        Integer32
    MAX-ACCESS    read-only
    STATUS        current
    DESCRIPTION   ""
    ::= { pmOptMuxDataRecord 2 }

dsOptMuxCurrent1dayTable OBJECT-TYPE
    SYNTAX        SEQUENCE OF DsOptMuxCurrent1dayEntry
    MAX-ACCESS    not-accessible
    STATUS        current
    DESCRIPTION   ""
    ::= { pmOptMuxDataRecord 3 }

dsOptMuxCurrent1dayEntry OBJECT-TYPE
    SYNTAX        DsOptMuxCurrent1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName
                }
    ::= { dsOptMuxCurrent1dayTable 1 }

DsOptMuxCurrent1dayEntry ::= SEQUENCE
  {    dsOptMuxCurrent1dayDS Unsigned32,
    dsOptMuxCurrent1dayElapsedTime Integer32 }

dsOptMuxCurrent1dayDS OBJECT-TYPE
    SYNTAX        Unsigned32
    MAX-ACCESS    read-only
    STATUS        current
    DESCRIPTION   "Defect Seconds"
    ::= { dsOptMuxCurrent1dayEntry 1 }

dsOptMuxCurrent1dayElapsedTime OBJECT-TYPE
    SYNTAX        Integer32 (0..86400)
    MAX-ACCESS    read-only
    STATUS        current
    DESCRIPTION   "Elapsed 1Day"
    ::= { dsOptMuxCurrent1dayEntry 2 }

endOfDsOptMuxCurrent1dayTable OBJECT-TYPE
    SYNTAX        Integer32
    MAX-ACCESS    read-only
    STATUS        current
    DESCRIPTION   ""
    ::= { pmOptMuxDataRecord 4 }

dsOptMuxHistorical15minTable OBJECT-TYPE
    SYNTAX        SEQUENCE OF DsOptMuxHistorical15minEntry
    MAX-ACCESS    not-accessible
    STATUS        current
    DESCRIPTION   ""
    ::= { pmOptMuxDataRecord 5 }

dsOptMuxHistorical15minEntry OBJECT-TYPE
    SYNTAX        DsOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  dsOptMuxHistorical15minNumber
                }
    ::= { dsOptMuxHistorical15minTable 1 }

DsOptMuxHistorical15minEntry ::= SEQUENCE
  {    dsOptMuxHistorical15minNumber Integer32,
    dsOptMuxHistorical15minDS Unsigned32,
    dsOptMuxHistorical15minValidFlag TruthValue,
    dsOptMuxHistorical15minTimeStamp DateAndTime }

dsOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { dsOptMuxHistorical15minEntry 1 }

dsOptMuxHistorical15minDS OBJECT-TYPE
    SYNTAX        Unsigned32
    MAX-ACCESS    read-only
    STATUS        current
    DESCRIPTION   "Defect Seconds"
    ::= { dsOptMuxHistorical15minEntry 2 }

dsOptMuxHistorical15minValidFlag OBJECT-TYPE
    SYNTAX        TruthValue
    MAX-ACCESS    read-only
    STATUS        current
    DESCRIPTION   "Valid Flag"
    ::= { dsOptMuxHistorical15minEntry 3 }

dsOptMuxHistorical15minTimeStamp OBJECT-TYPE
    SYNTAX        DateAndTime
    MAX-ACCESS    read-only
    STATUS        current
    DESCRIPTION   "Timestamp"
    ::= { dsOptMuxHistorical15minEntry 4 }

endOfDsOptMuxHistorical15minTable OBJECT-TYPE
    SYNTAX        Integer32
    MAX-ACCESS    read-only
    STATUS        current
    DESCRIPTION   ""
    ::= { pmOptMuxDataRecord 6 }

dsOptMuxHistorical1dayTable OBJECT-TYPE
    SYNTAX        SEQUENCE OF DsOptMuxHistorical1dayEntry
    MAX-ACCESS    not-accessible
    STATUS        current
    DESCRIPTION   ""
    ::= { pmOptMuxDataRecord 7 }

dsOptMuxHistorical1dayEntry OBJECT-TYPE
    SYNTAX        DsOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  dsOptMuxHistorical1dayNumber
                }
    ::= { dsOptMuxHistorical1dayTable 1 }

DsOptMuxHistorical1dayEntry ::= SEQUENCE
  {    dsOptMuxHistorical1dayNumber Integer32,
    dsOptMuxHistorical1dayDS Unsigned32,
    dsOptMuxHistorical1dayValidFlag TruthValue,
    dsOptMuxHistorical1dayTimeStamp DateAndTime }

dsOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { dsOptMuxHistorical1dayEntry 1 }

dsOptMuxHistorical1dayDS OBJECT-TYPE
    SYNTAX        Unsigned32
    MAX-ACCESS    read-only
    STATUS        current
    DESCRIPTION   "Defect Seconds"
    ::= { dsOptMuxHistorical1dayEntry 2 }

dsOptMuxHistorical1dayValidFlag OBJECT-TYPE
    SYNTAX        TruthValue
    MAX-ACCESS    read-only
    STATUS        current
    DESCRIPTION   "Valid Flag"
    ::= { dsOptMuxHistorical1dayEntry 3 }

dsOptMuxHistorical1dayTimeStamp OBJECT-TYPE
    SYNTAX        DateAndTime
    MAX-ACCESS    read-only
    STATUS        current
    DESCRIPTION   "Timestamp"
    ::= { dsOptMuxHistorical1dayEntry 4 }

endOfDsOptMuxHistorical1dayTable OBJECT-TYPE
    SYNTAX        Integer32
    MAX-ACCESS    read-only
    STATUS        current
    DESCRIPTION   ""
    ::= { pmOptMuxDataRecord 8 }

endOfPmOptMuxDataRecord OBJECT-TYPE
    SYNTAX        Integer32
    MAX-ACCESS    read-only
    STATUS        current
    DESCRIPTION   ""
    ::= { pmOptMuxDataRecord 10000 }

optMuxPhysInstValueTable OBJECT-TYPE
    SYNTAX        SEQUENCE OF OptMuxPhysInstValueEntry
    MAX-ACCESS    not-accessible
    STATUS        current
    DESCRIPTION   ""
    ::= { pmOptMuxPhysValue 1 }

optMuxPhysInstValueEntry OBJECT-TYPE
    SYNTAX        OptMuxPhysInstValueEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName
                }
    ::= { optMuxPhysInstValueTable 1 }

OptMuxPhysInstValueEntry ::= SEQUENCE
  {    optMuxPhysInstValueRemainingTime Unsigned32,
    optMuxPhysInstValueLaserBiasCurrentLevelAverage Unsigned32,
    optMuxPhysInstValueAttenuation Integer32,
    optMuxPhysInstValueLaserBiasCurrentLevel Unsigned32,
    optMuxPhysInstValueOscPowerReceived Integer32,
    optMuxPhysInstValuePumpLaser1Temp Integer32,
    optMuxPhysInstValuePumpLaser2Temp Integer32,
    optMuxPhysInstValueAttenuationOfVoa Unsigned32,
    optMuxPhysInstValueVariableGain Unsigned32,
    optMuxPhysInstValuePumpLaser3Temp Integer32,
    optMuxPhysInstValueLaserTemp Integer32,
    optMuxPhysInstValueOutputPowerEsmt Integer32,
    optMuxPhysInstValuePumpLaserBiasCurrent1 Unsigned32,
    optMuxPhysInstValuePumpLaserBiasCurrent2 Unsigned32,
    optMuxPhysInstValuePumpLaserBiasCurrent3 Unsigned32,
    optMuxPhysInstValueOperatingHours Unsigned32,
    optMuxPhysInstValueSubTemp Integer32,
    optMuxPhysInstValuePumpLaser4Temp Integer32,
    optMuxPhysInstValueTotalGainMeasurement Integer32,
    optMuxPhysInstValueCurrentEdfaOpt Integer32,
    optMuxPhysInstValuePumpLaserBiasCurrent4 Unsigned32,
    optMuxPhysInstValueRxLineAttenuation Integer32,
    optMuxPhysInstValueOscGain Unsigned32,
    optMuxPhysInstValueBackreflectionPowerReceived Integer32,
    optMuxPhysInstValueRamanEstSignalGain Unsigned32,
    optMuxPhysInstValueOutputPower Integer32,
    optMuxPhysInstValueInputPower Integer32,
    optMuxPhysInstValueTxLineAttenuation Integer32,
    optMuxPhysInstValueRamanPumpPower Integer32,
    optMuxPhysInstValueOscOutputPower Integer32,
    optMuxPhysInstValueBackreflectionTx Integer32,
    optMuxPhysInstValuePowerPerChannelTx Integer32,
    optMuxPhysInstValueAddChanAvg Integer32,
    optMuxPhysInstValueOcmTxLoss Integer32,
    optMuxPhysInstValueOcmRxLoss Integer32,
    optMuxPhysInstValueEffectiveGainNtoR Integer32,
    optMuxPhysInstValueEffectiveGainNtoC Integer32,
    optMuxPhysInstValueMidStageAttenuation Unsigned32,
    optMuxPhysInstValueEffectiveGainRtoN Integer32,
    optMuxPhysInstValueEffectiveGainCtoN Integer32,
    optMuxPhysInstValueOutputPowerRaw Integer32,
    optMuxPhysInstValueInputPowerRaw Integer32 }

optMuxPhysInstValueRemainingTime OBJECT-TYPE
    SYNTAX        Unsigned32
    UNITS         "min"
    MAX-ACCESS    read-only
    STATUS        current
    DESCRIPTION   "Time Remaining for Completion of OTDR Measurement. The timer is set by an Operation with parameter 'MEASURE'"
    ::= { optMuxPhysInstValueEntry 1 }

optMuxPhysInstValueLaserBiasCurrentLevelAverage OBJECT-TYPE
    SYNTAX        Unsigned32
    UNITS         "0.001 A"
    MAX-ACCESS    read-only
    STATUS        current
    DESCRIPTION   "Laser Bias Current Level averaged over 10 seconds"
    ::= { optMuxPhysInstValueEntry 2 }

optMuxPhysInstValueAttenuation OBJECT-TYPE
    SYNTAX        Integer32
    UNITS         "0.1 dB"
    MAX-ACCESS    read-only
    STATUS        current
    DESCRIPTION   "Signal attenuation in dB associated with Port. Generally, this parameter is used for the EDFA mid-stage access port (Port 2) and is the attenuation between the first stage transmit (Port 2 Tx) and the second stage receive (Port 2 Rx)."
    ::= { optMuxPhysInstValueEntry 3 }

optMuxPhysInstValueLaserBiasCurrentLevel OBJECT-TYPE
    SYNTAX        Unsigned32
    UNITS         "0.001 A"
    MAX-ACCESS    read-only
    STATUS        current
    DESCRIPTION   "Laser Bias Current Level on demand"
    ::= { optMuxPhysInstValueEntry 4 }

optMuxPhysInstValueOscPowerReceived OBJECT-TYPE
    SYNTAX        Integer32
    UNITS         "0.1 dBm"
    MAX-ACCESS    read-only
    STATUS        current
    DESCRIPTION   "Optical Supervisory Channel Input Power Received Current"
    ::= { optMuxPhysInstValueEntry 5 }

optMuxPhysInstValuePumpLaser1Temp OBJECT-TYPE
    SYNTAX        Integer32
    UNITS         "0.1 degree Celsius"
    MAX-ACCESS    read-only
    STATUS        current
    DESCRIPTION   "Laser 1 Temperature"
    ::= { optMuxPhysInstValueEntry 6 }

optMuxPhysInstValuePumpLaser2Temp OBJECT-TYPE
    SYNTAX        Integer32
    UNITS         "0.1 degree Celsius"
    MAX-ACCESS    read-only
    STATUS        current
    DESCRIPTION   "Laser 2 Temperature"
    ::= { optMuxPhysInstValueEntry 7 }

optMuxPhysInstValueAttenuationOfVoa OBJECT-TYPE
    SYNTAX        Unsigned32
    UNITS         "0.1 dB"
    MAX-ACCESS    read-only
    STATUS        current
    DESCRIPTION   "Variable Attenuator attenuation in dB"
    ::= { optMuxPhysInstValueEntry 8 }

optMuxPhysInstValueVariableGain OBJECT-TYPE
    SYNTAX        Unsigned32
    UNITS         "0.1 dB"
    MAX-ACCESS    read-only
    STATUS        current
    DESCRIPTION   "Variable Gain of EDFA"
    ::= { optMuxPhysInstValueEntry 9 }

optMuxPhysInstValuePumpLaser3Temp OBJECT-TYPE
    SYNTAX        Integer32
    UNITS         "0.1 degree Celsius"
    MAX-ACCESS    read-only
    STATUS        current
    DESCRIPTION   "Laser 3 Temperature"
    ::= { optMuxPhysInstValueEntry 10 }

optMuxPhysInstValueLaserTemp OBJECT-TYPE
    SYNTAX        Integer32
    UNITS         "0.1 degree Celsius"
    MAX-ACCESS    read-only
    STATUS        current
    DESCRIPTION   "Laser Temperature"
    ::= { optMuxPhysInstValueEntry 11 }

optMuxPhysInstValueOutputPowerEsmt OBJECT-TYPE
    SYNTAX        Integer32
    UNITS         "0.1 dBm"
    MAX-ACCESS    read-only
    STATUS        current
    DESCRIPTION   "Estimated Instantaneous Channel Power Transmitted"
    ::= { optMuxPhysInstValueEntry 12 }

optMuxPhysInstValuePumpLaserBiasCurrent1 OBJECT-TYPE
    SYNTAX        Unsigned32
    UNITS         "0.001 A"
    MAX-ACCESS    read-only
    STATUS        current
    DESCRIPTION   "Laser Bias Current Level for Laser Pump 1"
    ::= { optMuxPhysInstValueEntry 13 }

optMuxPhysInstValuePumpLaserBiasCurrent2 OBJECT-TYPE
    SYNTAX        Unsigned32
    UNITS         "0.001 A"
    MAX-ACCESS    read-only
    STATUS        current
    DESCRIPTION   "Laser Bias Current Level for Laser Pump 2"
    ::= { optMuxPhysInstValueEntry 14 }

optMuxPhysInstValuePumpLaserBiasCurrent3 OBJECT-TYPE
    SYNTAX        Unsigned32
    UNITS         "0.001 A"
    MAX-ACCESS    read-only
    STATUS        current
    DESCRIPTION   "Laser Bias Current Level for Laser Pump 3"
    ::= { optMuxPhysInstValueEntry 15 }

optMuxPhysInstValueOperatingHours OBJECT-TYPE
    SYNTAX        Unsigned32
    UNITS         "0.1 h"
    MAX-ACCESS    read-only
    STATUS        current
    DESCRIPTION   "Accumulated total of Operating Hours"
    ::= { optMuxPhysInstValueEntry 16 }

optMuxPhysInstValueSubTemp OBJECT-TYPE
    SYNTAX        Integer32
    UNITS         "0.1 degree Celsius"
    MAX-ACCESS    read-only
    STATUS        current
    DESCRIPTION   "Submodule Temperature"
    ::= { optMuxPhysInstValueEntry 17 }

optMuxPhysInstValuePumpLaser4Temp OBJECT-TYPE
    SYNTAX        Integer32
    UNITS         "0.1 degree Celsius"
    MAX-ACCESS    read-only
    STATUS        current
    DESCRIPTION   "Laser 4 Temperature"
    ::= { optMuxPhysInstValueEntry 18 }

optMuxPhysInstValueTotalGainMeasurement OBJECT-TYPE
    SYNTAX        Integer32
    UNITS         "0.1 dB"
    MAX-ACCESS    read-only
    STATUS        current
    DESCRIPTION   "Total Gain measured, sum of amplifier gain less other attenuation (such as VOA)."
    ::= { optMuxPhysInstValueEntry 19 }

optMuxPhysInstValueCurrentEdfaOpt OBJECT-TYPE
    SYNTAX        Integer32
    UNITS         "0.1 dBm"
    MAX-ACCESS    read-only
    STATUS        current
    DESCRIPTION   "Total optical output power from the EDFA amplifier."
    ::= { optMuxPhysInstValueEntry 20 }

optMuxPhysInstValuePumpLaserBiasCurrent4 OBJECT-TYPE
    SYNTAX        Unsigned32
    UNITS         "0.001 A"
    MAX-ACCESS    read-only
    STATUS        current
    DESCRIPTION   "Laser Bias Current Level for Laser Pump 4"
    ::= { optMuxPhysInstValueEntry 21 }

optMuxPhysInstValueRxLineAttenuation OBJECT-TYPE
    SYNTAX        Integer32
    UNITS         "0.1 dB"
    MAX-ACCESS    read-only
    STATUS        current
    DESCRIPTION   "Attenuation of Receive Fiber"
    ::= { optMuxPhysInstValueEntry 22 }

optMuxPhysInstValueOscGain OBJECT-TYPE
    SYNTAX        Unsigned32
    UNITS         "0.1 dB"
    MAX-ACCESS    read-only
    STATUS        current
    DESCRIPTION   "Current Raman OSC gain"
    ::= { optMuxPhysInstValueEntry 23 }

optMuxPhysInstValueBackreflectionPowerReceived OBJECT-TYPE
    SYNTAX        Integer32
    UNITS         "0.1 dB"
    MAX-ACCESS    read-only
    STATUS        current
    DESCRIPTION   "Back Reflection Received Current"
    ::= { optMuxPhysInstValueEntry 24 }

optMuxPhysInstValueRamanEstSignalGain OBJECT-TYPE
    SYNTAX        Unsigned32
    UNITS         "0.1 dB"
    MAX-ACCESS    read-only
    STATUS        current
    DESCRIPTION   "Current Estimated signal gain"
    ::= { optMuxPhysInstValueEntry 25 }

optMuxPhysInstValueOutputPower OBJECT-TYPE
    SYNTAX        Integer32
    UNITS         "0.1 dBm"
    MAX-ACCESS    read-only
    STATUS        current
    DESCRIPTION   "Instantaneous Optical Power Transmitted (Output)"
    ::= { optMuxPhysInstValueEntry 26 }

optMuxPhysInstValueInputPower OBJECT-TYPE
    SYNTAX        Integer32
    UNITS         "0.1 dBm"
    MAX-ACCESS    read-only
    STATUS        current
    DESCRIPTION   "Total Optical Input Power Received"
    ::= { optMuxPhysInstValueEntry 27 }

optMuxPhysInstValueTxLineAttenuation OBJECT-TYPE
    SYNTAX        Integer32
    UNITS         "0.1 dB"
    MAX-ACCESS    read-only
    STATUS        current
    DESCRIPTION   "Attenuation of Transmit Fiber"
    ::= { optMuxPhysInstValueEntry 28 }

optMuxPhysInstValueRamanPumpPower OBJECT-TYPE
    SYNTAX        Integer32
    UNITS         "0.1 dBm"
    MAX-ACCESS    read-only
    STATUS        current
    DESCRIPTION   "Total raman pump power"
    ::= { optMuxPhysInstValueEntry 29 }

optMuxPhysInstValueOscOutputPower OBJECT-TYPE
    SYNTAX        Integer32
    UNITS         "0.1 dBm"
    MAX-ACCESS    read-only
    STATUS        current
    DESCRIPTION   "Instantaneous OSC Optical Power Transmitted (Output)"
    ::= { optMuxPhysInstValueEntry 30 }

optMuxPhysInstValueBackreflectionTx OBJECT-TYPE
    SYNTAX        Integer32
    UNITS         "0.1 dB"
    MAX-ACCESS    read-only
    STATUS        current
    DESCRIPTION   "Physical Port Backreflection power, measured at Tx Port."
    ::= { optMuxPhysInstValueEntry 31 }

optMuxPhysInstValuePowerPerChannelTx OBJECT-TYPE
    SYNTAX        Integer32
    UNITS         "0.1 dBm"
    MAX-ACCESS    read-only
    STATUS        current
    DESCRIPTION   "Target output optical power for each channel."
    ::= { optMuxPhysInstValueEntry 32 }

optMuxPhysInstValueAddChanAvg OBJECT-TYPE
    SYNTAX        Integer32
    UNITS         "0.1 dBm"
    MAX-ACCESS    read-only
    STATUS        current
    DESCRIPTION   "Average output optical power for all add channels."
    ::= { optMuxPhysInstValueEntry 33 }

optMuxPhysInstValueOcmTxLoss OBJECT-TYPE
    SYNTAX        Integer32
    UNITS         "0.1 dB"
    MAX-ACCESS    read-only
    STATUS        current
    DESCRIPTION   "Fiber Connection Transmit Optical Channel Monitor Attenuation"
    ::= { optMuxPhysInstValueEntry 34 }

optMuxPhysInstValueOcmRxLoss OBJECT-TYPE
    SYNTAX        Integer32
    UNITS         "0.1 dB"
    MAX-ACCESS    read-only
    STATUS        current
    DESCRIPTION   "Fiber Connection Receive Optical Channel Monitor Attenuation"
    ::= { optMuxPhysInstValueEntry 35 }

optMuxPhysInstValueEffectiveGainNtoR OBJECT-TYPE
    SYNTAX        Integer32
    UNITS         "0.1 dB"
    MAX-ACCESS    read-only
    STATUS        current
    DESCRIPTION   "Effective Gain From N-port to R-port"
    ::= { optMuxPhysInstValueEntry 36 }

optMuxPhysInstValueEffectiveGainNtoC OBJECT-TYPE
    SYNTAX        Integer32
    UNITS         "0.1 dB"
    MAX-ACCESS    read-only
    STATUS        current
    DESCRIPTION   "Effective Gain From N-port to C-port"
    ::= { optMuxPhysInstValueEntry 37 }

optMuxPhysInstValueMidStageAttenuation OBJECT-TYPE
    SYNTAX        Unsigned32
    UNITS         "0.1 dB"
    MAX-ACCESS    read-only
    STATUS        current
    DESCRIPTION   "Attenuation at the EDFA mid-stage"
    ::= { optMuxPhysInstValueEntry 38 }

optMuxPhysInstValueEffectiveGainRtoN OBJECT-TYPE
    SYNTAX        Integer32
    UNITS         "0.1 dB"
    MAX-ACCESS    read-only
    STATUS        current
    DESCRIPTION   "Effective Gain From R-port to N-port"
    ::= { optMuxPhysInstValueEntry 39 }

optMuxPhysInstValueEffectiveGainCtoN OBJECT-TYPE
    SYNTAX        Integer32
    UNITS         "0.1 dB"
    MAX-ACCESS    read-only
    STATUS        current
    DESCRIPTION   "Effective Gain From C-port to N-port"
    ::= { optMuxPhysInstValueEntry 40 }

optMuxPhysInstValueOutputPowerRaw OBJECT-TYPE
    SYNTAX        Integer32
    UNITS         "0.1 dBm"
    MAX-ACCESS    read-only
    STATUS        current
    DESCRIPTION   "Raw Optical Power Transmitted (Output)"
    ::= { optMuxPhysInstValueEntry 41 }

optMuxPhysInstValueInputPowerRaw OBJECT-TYPE
    SYNTAX        Integer32
    UNITS         "0.1 dBm"
    MAX-ACCESS    read-only
    STATUS        current
    DESCRIPTION   "Raw Optical Power Received (Input)"
    ::= { optMuxPhysInstValueEntry 42 }

endOfOptMuxPhysInstValueTable OBJECT-TYPE
    SYNTAX        Integer32
    MAX-ACCESS    read-only
    STATUS        current
    DESCRIPTION   ""
    ::= { pmOptMuxPhysValue 2 }

endOfPmOptMuxPhysValue OBJECT-TYPE
    SYNTAX        Integer32
    MAX-ACCESS    read-only
    STATUS        current
    DESCRIPTION   ""
    ::= { pmOptMuxPhysValue 10000 }

optMuxPhysThresholdTable OBJECT-TYPE
    SYNTAX        SEQUENCE OF OptMuxPhysThresholdEntry
    MAX-ACCESS    not-accessible
    STATUS        current
    DESCRIPTION   ""
    ::= { pmOptMuxPhysThreshold 1 }

optMuxPhysThresholdEntry OBJECT-TYPE
    SYNTAX        OptMuxPhysThresholdEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName
                }
    ::= { optMuxPhysThresholdTable 1 }

OptMuxPhysThresholdEntry ::= SEQUENCE
  {    optMuxPhysThresholdRamanPumpPwrHighThres Integer32,
    optMuxPhysThresholdRamanPumpPwrLowThres Integer32,
    optMuxPhysThresholdPumpLaser1TempHighThres Integer32,
    optMuxPhysThresholdPumpLaser1TempLowThres Integer32,
    optMuxPhysThresholdPumpLaser2TempHighThres Integer32,
    optMuxPhysThresholdPumpLaser2TempLowThres Integer32,
    optMuxPhysThresholdPumpLaser3TempHighThres Integer32,
    optMuxPhysThresholdPumpLaser3TempLowThres Integer32,
    optMuxPhysThresholdPumpLaser4TempHighThres Integer32,
    optMuxPhysThresholdPumpLaser4TempLowThres Integer32,
    optMuxPhysThresholdUpperSubTempThres Integer32,
    optMuxPhysThresholdbrtxHighConfig Integer32,
    optMuxPhysThresholdBrPwrReceivedHighThres Integer32,
    optMuxPhysThresholdOpticalInputPwrHigh Integer32,
    optMuxPhysThresholdOpticalInputPwrLow Integer32,
    optMuxPhysThresholdAprHighThreshold Unsigned32,
    optMuxPhysThresholdConfigurableOpticalOutputPwrHigh Integer32,
    optMuxPhysThresholdConfigurableOpticalOutputPwrLow Integer32,
    optMuxPhysThresholdOpticalOutputPwrHigh Integer32,
    optMuxPhysThresholdOpticalOutputPwrLow Integer32,
    optMuxPhysThresholdLaserTempHighThres Integer32,
    optMuxPhysThresholdLaserTempLowThres Integer32,
    optMuxPhysThresholdOscPwrRcvHighThres Integer32,
    optMuxPhysThresholdOscPwrRcvLowThres Integer32,
    optMuxPhysThresholdAttTxHigh Integer32,
    optMuxPhysThresholdAttTxLow Integer32,
    optMuxPhysThresholdAttRxHigh Integer32,
    optMuxPhysThresholdAttRxLow Integer32 }

optMuxPhysThresholdRamanPumpPwrHighThres OBJECT-TYPE
    SYNTAX        Integer32
    UNITS         "0.1 dBm"
    MAX-ACCESS    read-only
    STATUS        current
    DESCRIPTION   "Raman Pump Power High threshold"
    ::= { optMuxPhysThresholdEntry 1 }

optMuxPhysThresholdRamanPumpPwrLowThres OBJECT-TYPE
    SYNTAX        Integer32
    UNITS         "0.1 dBm"
    MAX-ACCESS    read-only
    STATUS        current
    DESCRIPTION   "Raman Pump Power Low threshold"
    ::= { optMuxPhysThresholdEntry 2 }

optMuxPhysThresholdPumpLaser1TempHighThres OBJECT-TYPE
    SYNTAX        Integer32
    UNITS         "0.1 degree Celsius"
    MAX-ACCESS    read-only
    STATUS        current
    DESCRIPTION   "Laser 1 temperature fixed high threshold."
    ::= { optMuxPhysThresholdEntry 3 }

optMuxPhysThresholdPumpLaser1TempLowThres OBJECT-TYPE
    SYNTAX        Integer32
    UNITS         "0.1 degree Celsius"
    MAX-ACCESS    read-only
    STATUS        current
    DESCRIPTION   "Laser 1 temperature fixed low threshold."
    ::= { optMuxPhysThresholdEntry 4 }

optMuxPhysThresholdPumpLaser2TempHighThres OBJECT-TYPE
    SYNTAX        Integer32
    UNITS         "0.1 degree Celsius"
    MAX-ACCESS    read-only
    STATUS        current
    DESCRIPTION   "Laser 2 temperature fixed high threshold."
    ::= { optMuxPhysThresholdEntry 5 }

optMuxPhysThresholdPumpLaser2TempLowThres OBJECT-TYPE
    SYNTAX        Integer32
    UNITS         "0.1 degree Celsius"
    MAX-ACCESS    read-only
    STATUS        current
    DESCRIPTION   "Laser 2 temperature fixed low threshold"
    ::= { optMuxPhysThresholdEntry 6 }

optMuxPhysThresholdPumpLaser3TempHighThres OBJECT-TYPE
    SYNTAX        Integer32
    UNITS         "0.1 degree Celsius"
    MAX-ACCESS    read-only
    STATUS        current
    DESCRIPTION   "Laser 3 temperature fixed high threshold"
    ::= { optMuxPhysThresholdEntry 7 }

optMuxPhysThresholdPumpLaser3TempLowThres OBJECT-TYPE
    SYNTAX        Integer32
    UNITS         "0.1 degree Celsius"
    MAX-ACCESS    read-only
    STATUS        current
    DESCRIPTION   "Laser 3 temperature fixed low threshold"
    ::= { optMuxPhysThresholdEntry 8 }

optMuxPhysThresholdPumpLaser4TempHighThres OBJECT-TYPE
    SYNTAX        Integer32
    UNITS         "0.1 degree Celsius"
    MAX-ACCESS    read-only
    STATUS        current
    DESCRIPTION   "Laser 4 temperature fixed high threshold"
    ::= { optMuxPhysThresholdEntry 9 }

optMuxPhysThresholdPumpLaser4TempLowThres OBJECT-TYPE
    SYNTAX        Integer32
    UNITS         "0.1 degree Celsius"
    MAX-ACCESS    read-only
    STATUS        current
    DESCRIPTION   "Laser 4 temperature fixed low threshold"
    ::= { optMuxPhysThresholdEntry 10 }

optMuxPhysThresholdUpperSubTempThres OBJECT-TYPE
    SYNTAX        Integer32
    UNITS         "0.1 degree Celsius"
    MAX-ACCESS    read-only
    STATUS        current
    DESCRIPTION   "Submodule High Temperature Threshold"
    ::= { optMuxPhysThresholdEntry 11 }

optMuxPhysThresholdbrtxHighConfig OBJECT-TYPE
    SYNTAX        Integer32 (-300..-180)
    UNITS         "0.1 dB"
    MAX-ACCESS    read-write
    STATUS        current
    DESCRIPTION   "Backreflection power High Threshold, at Tx Port"
    ::= { optMuxPhysThresholdEntry 12 }

optMuxPhysThresholdBrPwrReceivedHighThres OBJECT-TYPE
    SYNTAX        Integer32 (-300..-180)
    UNITS         "0.1 dB"
    MAX-ACCESS    read-write
    STATUS        current
    DESCRIPTION   "Backreflection Input Received High Threshold"
    ::= { optMuxPhysThresholdEntry 13 }

optMuxPhysThresholdOpticalInputPwrHigh OBJECT-TYPE
    SYNTAX        Integer32 (-450..270)
    UNITS         "0.1 dBm"
    MAX-ACCESS    read-write
    STATUS        current
    DESCRIPTION   "Optical Input Power Received"
    ::= { optMuxPhysThresholdEntry 14 }

optMuxPhysThresholdOpticalInputPwrLow OBJECT-TYPE
    SYNTAX        Integer32 (-450..260)
    UNITS         "0.1 dBm"
    MAX-ACCESS    read-write
    STATUS        current
    DESCRIPTION   "Optical Input Power Received"
    ::= { optMuxPhysThresholdEntry 15 }

optMuxPhysThresholdAprHighThreshold OBJECT-TYPE
    SYNTAX        Unsigned32
    UNITS         "0.1 dBm"
    MAX-ACCESS    read-only
    STATUS        current
    DESCRIPTION   "Automatic Power Reduction High Threshold"
    ::= { optMuxPhysThresholdEntry 16 }

optMuxPhysThresholdConfigurableOpticalOutputPwrHigh OBJECT-TYPE
    SYNTAX        Integer32 (-500..300)
    UNITS         "0.1 dBm"
    MAX-ACCESS    read-write
    STATUS        current
    DESCRIPTION   "Configurable high threshold of the Optical Power Transmitted (output)"
    ::= { optMuxPhysThresholdEntry 17 }

optMuxPhysThresholdConfigurableOpticalOutputPwrLow OBJECT-TYPE
    SYNTAX        Integer32 (-500..300)
    UNITS         "0.1 dBm"
    MAX-ACCESS    read-write
    STATUS        current
    DESCRIPTION   "Configurable threshold of the Optical Power Transmitted (output)"
    ::= { optMuxPhysThresholdEntry 18 }

optMuxPhysThresholdOpticalOutputPwrHigh OBJECT-TYPE
    SYNTAX        Integer32
    UNITS         "0.1 dBm"
    MAX-ACCESS    read-only
    STATUS        current
    DESCRIPTION   "High fixed threshold of the Optical Power Transmitted (output)"
    ::= { optMuxPhysThresholdEntry 19 }

optMuxPhysThresholdOpticalOutputPwrLow OBJECT-TYPE
    SYNTAX        Integer32
    UNITS         "0.1 dBm"
    MAX-ACCESS    read-only
    STATUS        current
    DESCRIPTION   "Low fixed threshold of the Optical Power Transmitted (output)"
    ::= { optMuxPhysThresholdEntry 20 }

optMuxPhysThresholdLaserTempHighThres OBJECT-TYPE
    SYNTAX        Integer32
    UNITS         "0.1 degree Celsius"
    MAX-ACCESS    read-only
    STATUS        current
    DESCRIPTION   "Laser temperature fixed high threshold."
    ::= { optMuxPhysThresholdEntry 21 }

optMuxPhysThresholdLaserTempLowThres OBJECT-TYPE
    SYNTAX        Integer32
    UNITS         "0.1 degree Celsius"
    MAX-ACCESS    read-only
    STATUS        current
    DESCRIPTION   "Laser temperature fixed low threshold."
    ::= { optMuxPhysThresholdEntry 22 }

optMuxPhysThresholdOscPwrRcvHighThres OBJECT-TYPE
    SYNTAX        Integer32 (-470..-50)
    UNITS         "0.1 dBm"
    MAX-ACCESS    read-write
    STATUS        current
    DESCRIPTION   "Optical Supervisory Channel Input Power Received High Threshold"
    ::= { optMuxPhysThresholdEntry 23 }

optMuxPhysThresholdOscPwrRcvLowThres OBJECT-TYPE
    SYNTAX        Integer32 (-470..-50)
    UNITS         "0.1 dBm"
    MAX-ACCESS    read-write
    STATUS        current
    DESCRIPTION   "Optical Supervisory Channel Input Power Received Low Threshold"
    ::= { optMuxPhysThresholdEntry 24 }

optMuxPhysThresholdAttTxHigh OBJECT-TYPE
    SYNTAX        Integer32
    UNITS         "0.1 dB"
    MAX-ACCESS    read-write
    STATUS        current
    DESCRIPTION   "High Threshold of Attenuation on Transmit Fiber"
    ::= { optMuxPhysThresholdEntry 25 }

optMuxPhysThresholdAttTxLow OBJECT-TYPE
    SYNTAX        Integer32
    UNITS         "0.1 dB"
    MAX-ACCESS    read-write
    STATUS        current
    DESCRIPTION   "Low Threshold Attenuation on Transmit Fiber"
    ::= { optMuxPhysThresholdEntry 26 }

optMuxPhysThresholdAttRxHigh OBJECT-TYPE
    SYNTAX        Integer32
    UNITS         "0.1 dB"
    MAX-ACCESS    read-write
    STATUS        current
    DESCRIPTION   "High Threshold for Attenuation on Receive Fiber"
    ::= { optMuxPhysThresholdEntry 27 }

optMuxPhysThresholdAttRxLow OBJECT-TYPE
    SYNTAX        Integer32
    UNITS         "0.1 dB"
    MAX-ACCESS    read-write
    STATUS        current
    DESCRIPTION   "Low Threshold for Attenuation on Receive Fiber."
    ::= { optMuxPhysThresholdEntry 28 }

endOfOptMuxPhysThresholdTable OBJECT-TYPE
    SYNTAX        Integer32
    MAX-ACCESS    read-only
    STATUS        current
    DESCRIPTION   ""
    ::= { pmOptMuxPhysThreshold 2 }

endOfPmOptMuxPhysThreshold OBJECT-TYPE
    SYNTAX        Integer32
    MAX-ACCESS    read-only
    STATUS        current
    DESCRIPTION   ""
    ::= { pmOptMuxPhysThreshold 10000 }

brTxOptMuxHistorical15minTable OBJECT-TYPE
    SYNTAX        SEQUENCE OF BrTxOptMuxHistorical15minEntry
    MAX-ACCESS    not-accessible
    STATUS        current
    DESCRIPTION   ""
    ::= { pmOptMuxPhysRecord 1 }

brTxOptMuxHistorical15minEntry OBJECT-TYPE
    SYNTAX        BrTxOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  brTxOptMuxHistorical15minNumber
                }
    ::= { brTxOptMuxHistorical15minTable 1 }

BrTxOptMuxHistorical15minEntry ::= SEQUENCE
  {    brTxOptMuxHistorical15minNumber Integer32,
    brTxOptMuxHistorical15minLow Integer32,
    brTxOptMuxHistorical15minMean Integer32,
    brTxOptMuxHistorical15minHigh Integer32,
    brTxOptMuxHistorical15minValidFlag TruthValue,
    brTxOptMuxHistorical15minTimeStamp DateAndTime }

brTxOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { brTxOptMuxHistorical15minEntry 1 }

brTxOptMuxHistorical15minLow OBJECT-TYPE
    SYNTAX        Integer32
    UNITS         "0.1 dB"
    MAX-ACCESS    read-only
    STATUS        current
    DESCRIPTION   "Backreflection Power Low, measured at Tx Port"
    ::= { brTxOptMuxHistorical15minEntry 2 }

brTxOptMuxHistorical15minMean OBJECT-TYPE
    SYNTAX        Integer32
    UNITS         "0.1 dB"
    MAX-ACCESS    read-only
    STATUS        current
    DESCRIPTION   "Backreflection Power Average, measured at Tx Port"
    ::= { brTxOptMuxHistorical15minEntry 3 }

brTxOptMuxHistorical15minHigh OBJECT-TYPE
    SYNTAX        Integer32
    UNITS         "0.1 dB"
    MAX-ACCESS    read-only
    STATUS        current
    DESCRIPTION   "Backreflection Power High, measured at Tx Port"
    ::= { brTxOptMuxHistorical15minEntry 4 }

brTxOptMuxHistorical15minValidFlag OBJECT-TYPE
    SYNTAX        TruthValue
    MAX-ACCESS    read-only
    STATUS        current
    DESCRIPTION   "Valid Flag"
    ::= { brTxOptMuxHistorical15minEntry 5 }

brTxOptMuxHistorical15minTimeStamp OBJECT-TYPE
    SYNTAX        DateAndTime
    MAX-ACCESS    read-only
    STATUS        current
    DESCRIPTION   "Timestamp"
    ::= { brTxOptMuxHistorical15minEntry 6 }

endOfBrTxOptMuxHistorical15minTable OBJECT-TYPE
    SYNTAX        Integer32
    MAX-ACCESS    read-only
    STATUS        current
    DESCRIPTION   ""
    ::= { pmOptMuxPhysRecord 2 }

brTxOptMuxHistorical1dayTable OBJECT-TYPE
    SYNTAX        SEQUENCE OF BrTxOptMuxHistorical1dayEntry
    MAX-ACCESS    not-accessible
    STATUS        current
    DESCRIPTION   ""
    ::= { pmOptMuxPhysRecord 3 }

brTxOptMuxHistorical1dayEntry OBJECT-TYPE
    SYNTAX        BrTxOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  brTxOptMuxHistorical1dayNumber
                }
    ::= { brTxOptMuxHistorical1dayTable 1 }

BrTxOptMuxHistorical1dayEntry ::= SEQUENCE
  {    brTxOptMuxHistorical1dayNumber Integer32,
    brTxOptMuxHistorical1dayLow Integer32,
    brTxOptMuxHistorical1dayMean Integer32,
    brTxOptMuxHistorical1dayHigh Integer32,
    brTxOptMuxHistorical1dayValidFlag TruthValue,
    brTxOptMuxHistorical1dayTimeStamp DateAndTime }

brTxOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { brTxOptMuxHistorical1dayEntry 1 }

brTxOptMuxHistorical1dayLow OBJECT-TYPE
    SYNTAX        Integer32
    UNITS         "0.1 dB"
    MAX-ACCESS    read-only
    STATUS        current
    DESCRIPTION   "Backreflection Power Low, measured at Tx Port"
    ::= { brTxOptMuxHistorical1dayEntry 2 }

brTxOptMuxHistorical1dayMean OBJECT-TYPE
    SYNTAX        Integer32
    UNITS         "0.1 dB"
    MAX-ACCESS    read-only
    STATUS        current
    DESCRIPTION   "Backreflection Power Average, measured at Tx Port"
    ::= { brTxOptMuxHistorical1dayEntry 3 }

brTxOptMuxHistorical1dayHigh OBJECT-TYPE
    SYNTAX        Integer32
    UNITS         "0.1 dB"
    MAX-ACCESS    read-only
    STATUS        current
    DESCRIPTION   "Backreflection Power High, measured at Tx Port"
    ::= { brTxOptMuxHistorical1dayEntry 4 }

brTxOptMuxHistorical1dayValidFlag OBJECT-TYPE
    SYNTAX        TruthValue
    MAX-ACCESS    read-only
    STATUS        current
    DESCRIPTION   "Valid Flag"
    ::= { brTxOptMuxHistorical1dayEntry 5 }

brTxOptMuxHistorical1dayTimeStamp OBJECT-TYPE
    SYNTAX        DateAndTime
    MAX-ACCESS    read-only
    STATUS        current
    DESCRIPTION   "Timestamp"
    ::= { brTxOptMuxHistorical1dayEntry 6 }

endOfBrTxOptMuxHistorical1dayTable OBJECT-TYPE
    SYNTAX        Integer32
    MAX-ACCESS    read-only
    STATUS        current
    DESCRIPTION   ""
    ::= { pmOptMuxPhysRecord 4 }

brTxOptMuxHistorical1weekTable OBJECT-TYPE
    SYNTAX        SEQUENCE OF BrTxOptMuxHistorical1weekEntry
    MAX-ACCESS    not-accessible
    STATUS        current
    DESCRIPTION   ""
    ::= { pmOptMuxPhysRecord 5 }

brTxOptMuxHistorical1weekEntry OBJECT-TYPE
    SYNTAX        BrTxOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  brTxOptMuxHistorical1weekNumber
                }
    ::= { brTxOptMuxHistorical1weekTable 1 }

BrTxOptMuxHistorical1weekEntry ::= SEQUENCE
  {    brTxOptMuxHistorical1weekNumber Integer32,
    brTxOptMuxHistorical1weekLow Integer32,
    brTxOptMuxHistorical1weekMean Integer32,
    brTxOptMuxHistorical1weekHigh Integer32,
    brTxOptMuxHistorical1weekValidFlag TruthValue,
    brTxOptMuxHistorical1weekTimeStamp DateAndTime }

brTxOptMuxHistorical1weekNumber OBJECT-TYPE
    SYNTAX        Integer32 (1..52)
    MAX-ACCESS    not-accessible
    STATUS        current
    DESCRIPTION   "Number 1week"
    ::= { brTxOptMuxHistorical1weekEntry 1 }

brTxOptMuxHistorical1weekLow OBJECT-TYPE
    SYNTAX        Integer32
    UNITS         "0.1 dB"
    MAX-ACCESS    read-only
    STATUS        current
    DESCRIPTION   "Backreflection Power Low, measured at Tx Port"
    ::= { brTxOptMuxHistorical1weekEntry 2 }

brTxOptMuxHistorical1weekMean OBJECT-TYPE
    SYNTAX        Integer32
    UNITS         "0.1 dB"
    MAX-ACCESS    read-only
    STATUS        current
    DESCRIPTION   "Backreflection Power Average, measured at Tx Port"
    ::= { brTxOptMuxHistorical1weekEntry 3 }

brTxOptMuxHistorical1weekHigh OBJECT-TYPE
    SYNTAX        Integer32
    UNITS         "0.1 dB"
    MAX-ACCESS    read-only
    STATUS        current
    DESCRIPTION   "Backreflection Power High, measured at Tx Port"
    ::= { brTxOptMuxHistorical1weekEntry 4 }

brTxOptMuxHistorical1weekValidFlag OBJECT-TYPE
    SYNTAX        TruthValue
    MAX-ACCESS    read-only
    STATUS        current
    DESCRIPTION   "Valid Flag"
    ::= { brTxOptMuxHistorical1weekEntry 5 }

brTxOptMuxHistorical1weekTimeStamp OBJECT-TYPE
    SYNTAX        DateAndTime
    MAX-ACCESS    read-only
    STATUS        current
    DESCRIPTION   "Timestamp"
    ::= { brTxOptMuxHistorical1weekEntry 6 }

endOfBrTxOptMuxHistorical1weekTable OBJECT-TYPE
    SYNTAX        Integer32
    MAX-ACCESS    read-only
    STATUS        current
    DESCRIPTION   ""
    ::= { pmOptMuxPhysRecord 6 }

oscGainOptMuxHistorical15minTable OBJECT-TYPE
    SYNTAX        SEQUENCE OF OscGainOptMuxHistorical15minEntry
    MAX-ACCESS    not-accessible
    STATUS        current
    DESCRIPTION   ""
    ::= { pmOptMuxPhysRecord 7 }

oscGainOptMuxHistorical15minEntry OBJECT-TYPE
    SYNTAX        OscGainOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscGainOptMuxHistorical15minNumber
                }
    ::= { oscGainOptMuxHistorical15minTable 1 }

OscGainOptMuxHistorical15minEntry ::= SEQUENCE
  {    oscGainOptMuxHistorical15minNumber Integer32,
    oscGainOptMuxHistorical15minLow Unsigned32,
    oscGainOptMuxHistorical15minMean Unsigned32,
    oscGainOptMuxHistorical15minHigh Unsigned32,
    oscGainOptMuxHistorical15minValidFlag TruthValue,
    oscGainOptMuxHistorical15minTimeStamp DateAndTime }

oscGainOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oscGainOptMuxHistorical15minEntry 1 }

oscGainOptMuxHistorical15minLow OBJECT-TYPE
    SYNTAX        Unsigned32
    UNITS         "0.1 dB"
    MAX-ACCESS    read-only
    STATUS        current
    DESCRIPTION   "OSC Gain Low"
    ::= { oscGainOptMuxHistorical15minEntry 2 }

oscGainOptMuxHistorical15minMean OBJECT-TYPE
    SYNTAX        Unsigned32
    UNITS         "0.1 dB"
    MAX-ACCESS    read-only
    STATUS        current
    DESCRIPTION   "OSC Gain Average"
    ::= { oscGainOptMuxHistorical15minEntry 3 }

oscGainOptMuxHistorical15minHigh OBJECT-TYPE
    SYNTAX        Unsigned32
    UNITS         "0.1 dB"
    MAX-ACCESS    read-only
    STATUS        current
    DESCRIPTION   "OSC Gain High"
    ::= { oscGainOptMuxHistorical15minEntry 4 }

oscGainOptMuxHistorical15minValidFlag OBJECT-TYPE
    SYNTAX        TruthValue
    MAX-ACCESS    read-only
    STATUS        current
    DESCRIPTION   "Valid Flag"
    ::= { oscGainOptMuxHistorical15minEntry 5 }

oscGainOptMuxHistorical15minTimeStamp OBJECT-TYPE
    SYNTAX        DateAndTime
    MAX-ACCESS    read-only
    STATUS        current
    DESCRIPTION   "Timestamp"
    ::= { oscGainOptMuxHistorical15minEntry 6 }

endOfOscGainOptMuxHistorical15minTable OBJECT-TYPE
    SYNTAX        Integer32
    MAX-ACCESS    read-only
    STATUS        current
    DESCRIPTION   ""
    ::= { pmOptMuxPhysRecord 8 }

oscGainOptMuxHistorical1dayTable OBJECT-TYPE
    SYNTAX        SEQUENCE OF OscGainOptMuxHistorical1dayEntry
    MAX-ACCESS    not-accessible
    STATUS        current
    DESCRIPTION   ""
    ::= { pmOptMuxPhysRecord 9 }

oscGainOptMuxHistorical1dayEntry OBJECT-TYPE
    SYNTAX        OscGainOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscGainOptMuxHistorical1dayNumber
                }
    ::= { oscGainOptMuxHistorical1dayTable 1 }

OscGainOptMuxHistorical1dayEntry ::= SEQUENCE
  {    oscGainOptMuxHistorical1dayNumber Integer32,
    oscGainOptMuxHistorical1dayLow Unsigned32,
    oscGainOptMuxHistorical1dayMean Unsigned32,
    oscGainOptMuxHistorical1dayHigh Unsigned32,
    oscGainOptMuxHistorical1dayValidFlag TruthValue,
    oscGainOptMuxHistorical1dayTimeStamp DateAndTime }

oscGainOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oscGainOptMuxHistorical1dayEntry 1 }

oscGainOptMuxHistorical1dayLow OBJECT-TYPE
    SYNTAX        Unsigned32
    UNITS         "0.1 dB"
    MAX-ACCESS    read-only
    STATUS        current
    DESCRIPTION   "OSC Gain Low"
    ::= { oscGainOptMuxHistorical1dayEntry 2 }

oscGainOptMuxHistorical1dayMean OBJECT-TYPE
    SYNTAX        Unsigned32
    UNITS         "0.1 dB"
    MAX-ACCESS    read-only
    STATUS        current
    DESCRIPTION   "OSC Gain Average"
    ::= { oscGainOptMuxHistorical1dayEntry 3 }

oscGainOptMuxHistorical1dayHigh OBJECT-TYPE
    SYNTAX        Unsigned32
    UNITS         "0.1 dB"
    MAX-ACCESS    read-only
    STATUS        current
    DESCRIPTION   "OSC Gain High"
    ::= { oscGainOptMuxHistorical1dayEntry 4 }

oscGainOptMuxHistorical1dayValidFlag OBJECT-TYPE
    SYNTAX        TruthValue
    MAX-ACCESS    read-only
    STATUS        current
    DESCRIPTION   "Valid Flag"
    ::= { oscGainOptMuxHistorical1dayEntry 5 }

oscGainOptMuxHistorical1dayTimeStamp OBJECT-TYPE
    SYNTAX        DateAndTime
    MAX-ACCESS    read-only
    STATUS        current
    DESCRIPTION   "Timestamp"
    ::= { oscGainOptMuxHistorical1dayEntry 6 }

endOfOscGainOptMuxHistorical1dayTable OBJECT-TYPE
    SYNTAX        Integer32
    MAX-ACCESS    read-only
    STATUS        current
    DESCRIPTION   ""
    ::= { pmOptMuxPhysRecord 10 }

oscGainOptMuxHistorical1weekTable OBJECT-TYPE
    SYNTAX        SEQUENCE OF OscGainOptMuxHistorical1weekEntry
    MAX-ACCESS    not-accessible
    STATUS        current
    DESCRIPTION   ""
    ::= { pmOptMuxPhysRecord 11 }

oscGainOptMuxHistorical1weekEntry OBJECT-TYPE
    SYNTAX        OscGainOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscGainOptMuxHistorical1weekNumber
                }
    ::= { oscGainOptMuxHistorical1weekTable 1 }

OscGainOptMuxHistorical1weekEntry ::= SEQUENCE
  {    oscGainOptMuxHistorical1weekNumber Integer32,
    oscGainOptMuxHistorical1weekLow Unsigned32,
    oscGainOptMuxHistorical1weekMean Unsigned32,
    oscGainOptMuxHistorical1weekHigh Unsigned32,
    oscGainOptMuxHistorical1weekValidFlag TruthValue,
    oscGainOptMuxHistorical1weekTimeStamp DateAndTime }

oscGainOptMuxHistorical1weekNumber OBJECT-TYPE
    SYNTAX        Integer32 (1..52)
    MAX-ACCESS    not-accessible
    STATUS        current
    DESCRIPTION   "Number 1week"
    ::= { oscGainOptMuxHistorical1weekEntry 1 }

oscGainOptMuxHistorical1weekLow OBJECT-TYPE
    SYNTAX        Unsigned32
    UNITS         "0.1 dB"
    MAX-ACCESS    read-only
    STATUS        current
    DESCRIPTION   "OSC Gain Low"
    ::= { oscGainOptMuxHistorical1weekEntry 2 }

oscGainOptMuxHistorical1weekMean OBJECT-TYPE
    SYNTAX        Unsigned32
    UNITS         "0.1 dB"
    MAX-ACCESS    read-only
    STATUS        current
    DESCRIPTION   "OSC Gain Average"
    ::= { oscGainOptMuxHistorical1weekEntry 3 }

oscGainOptMuxHistorical1weekHigh OBJECT-TYPE
    SYNTAX        Unsigned32
    UNITS         "0.1 dB"
    MAX-ACCESS    read-only
    STATUS        current
    DESCRIPTION   "OSC Gain High"
    ::= { oscGainOptMuxHistorical1weekEntry 4 }

oscGainOptMuxHistorical1weekValidFlag OBJECT-TYPE
    SYNTAX        TruthValue
    MAX-ACCESS    read-only
    STATUS        current
    DESCRIPTION   "Valid Flag"
    ::= { oscGainOptMuxHistorical1weekEntry 5 }

oscGainOptMuxHistorical1weekTimeStamp OBJECT-TYPE
    SYNTAX        DateAndTime
    MAX-ACCESS    read-only
    STATUS        current
    DESCRIPTION   "Timestamp"
    ::= { oscGainOptMuxHistorical1weekEntry 6 }

endOfOscGainOptMuxHistorical1weekTable OBJECT-TYPE
    SYNTAX        Integer32
    MAX-ACCESS    read-only
    STATUS        current
    DESCRIPTION   ""
    ::= { pmOptMuxPhysRecord 12 }

atRcvOptMuxHistorical15minTable OBJECT-TYPE
    SYNTAX        SEQUENCE OF AtRcvOptMuxHistorical15minEntry
    MAX-ACCESS    not-accessible
    STATUS        current
    DESCRIPTION   ""
    ::= { pmOptMuxPhysRecord 13 }

atRcvOptMuxHistorical15minEntry OBJECT-TYPE
    SYNTAX        AtRcvOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  atRcvOptMuxHistorical15minNumber
                }
    ::= { atRcvOptMuxHistorical15minTable 1 }

AtRcvOptMuxHistorical15minEntry ::= SEQUENCE
  {    atRcvOptMuxHistorical15minNumber Integer32,
    atRcvOptMuxHistorical15minLow Integer32,
    atRcvOptMuxHistorical15minMean Integer32,
    atRcvOptMuxHistorical15minHigh Integer32,
    atRcvOptMuxHistorical15minValidFlag TruthValue,
    atRcvOptMuxHistorical15minTimeStamp DateAndTime }

atRcvOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { atRcvOptMuxHistorical15minEntry 1 }

atRcvOptMuxHistorical15minLow OBJECT-TYPE
    SYNTAX        Integer32
    UNITS         "0.1 dB"
    MAX-ACCESS    read-only
    STATUS        current
    DESCRIPTION   "Low Attenuation on Receive Fiber"
    ::= { atRcvOptMuxHistorical15minEntry 2 }

atRcvOptMuxHistorical15minMean OBJECT-TYPE
    SYNTAX        Integer32
    UNITS         "0.1 dB"
    MAX-ACCESS    read-only
    STATUS        current
    DESCRIPTION   "Mean Attenuation on Receive Fiber"
    ::= { atRcvOptMuxHistorical15minEntry 3 }

atRcvOptMuxHistorical15minHigh OBJECT-TYPE
    SYNTAX        Integer32
    UNITS         "0.1 dB"
    MAX-ACCESS    read-only
    STATUS        current
    DESCRIPTION   "High Attenuation on Receive Fiber"
    ::= { atRcvOptMuxHistorical15minEntry 4 }

atRcvOptMuxHistorical15minValidFlag OBJECT-TYPE
    SYNTAX        TruthValue
    MAX-ACCESS    read-only
    STATUS        current
    DESCRIPTION   "Valid Flag"
    ::= { atRcvOptMuxHistorical15minEntry 5 }

atRcvOptMuxHistorical15minTimeStamp OBJECT-TYPE
    SYNTAX        DateAndTime
    MAX-ACCESS    read-only
    STATUS        current
    DESCRIPTION   "Timestamp"
    ::= { atRcvOptMuxHistorical15minEntry 6 }

endOfAtRcvOptMuxHistorical15minTable OBJECT-TYPE
    SYNTAX        Integer32
    MAX-ACCESS    read-only
    STATUS        current
    DESCRIPTION   ""
    ::= { pmOptMuxPhysRecord 14 }

atRcvOptMuxHistorical1dayTable OBJECT-TYPE
    SYNTAX        SEQUENCE OF AtRcvOptMuxHistorical1dayEntry
    MAX-ACCESS    not-accessible
    STATUS        current
    DESCRIPTION   ""
    ::= { pmOptMuxPhysRecord 15 }

atRcvOptMuxHistorical1dayEntry OBJECT-TYPE
    SYNTAX        AtRcvOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  atRcvOptMuxHistorical1dayNumber
                }
    ::= { atRcvOptMuxHistorical1dayTable 1 }

AtRcvOptMuxHistorical1dayEntry ::= SEQUENCE
  {    atRcvOptMuxHistorical1dayNumber Integer32,
    atRcvOptMuxHistorical1dayLow Integer32,
    atRcvOptMuxHistorical1dayMean Integer32,
    atRcvOptMuxHistorical1dayHigh Integer32,
    atRcvOptMuxHistorical1dayValidFlag TruthValue,
    atRcvOptMuxHistorical1dayTimeStamp DateAndTime }

atRcvOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { atRcvOptMuxHistorical1dayEntry 1 }

atRcvOptMuxHistorical1dayLow OBJECT-TYPE
    SYNTAX        Integer32
    UNITS         "0.1 dB"
    MAX-ACCESS    read-only
    STATUS        current
    DESCRIPTION   "Low Attenuation on Receive Fiber"
    ::= { atRcvOptMuxHistorical1dayEntry 2 }

atRcvOptMuxHistorical1dayMean OBJECT-TYPE
    SYNTAX        Integer32
    UNITS         "0.1 dB"
    MAX-ACCESS    read-only
    STATUS        current
    DESCRIPTION   "Mean Attenuation on Receive Fiber"
    ::= { atRcvOptMuxHistorical1dayEntry 3 }

atRcvOptMuxHistorical1dayHigh OBJECT-TYPE
    SYNTAX        Integer32
    UNITS         "0.1 dB"
    MAX-ACCESS    read-only
    STATUS        current
    DESCRIPTION   "High Attenuation on Receive Fiber"
    ::= { atRcvOptMuxHistorical1dayEntry 4 }

atRcvOptMuxHistorical1dayValidFlag OBJECT-TYPE
    SYNTAX        TruthValue
    MAX-ACCESS    read-only
    STATUS        current
    DESCRIPTION   "Valid Flag"
    ::= { atRcvOptMuxHistorical1dayEntry 5 }

atRcvOptMuxHistorical1dayTimeStamp OBJECT-TYPE
    SYNTAX        DateAndTime
    MAX-ACCESS    read-only
    STATUS        current
    DESCRIPTION   "Timestamp"
    ::= { atRcvOptMuxHistorical1dayEntry 6 }

endOfAtRcvOptMuxHistorical1dayTable OBJECT-TYPE
    SYNTAX        Integer32
    MAX-ACCESS    read-only
    STATUS        current
    DESCRIPTION   ""
    ::= { pmOptMuxPhysRecord 16 }

atRcvOptMuxHistorical1weekTable OBJECT-TYPE
    SYNTAX        SEQUENCE OF AtRcvOptMuxHistorical1weekEntry
    MAX-ACCESS    not-accessible
    STATUS        current
    DESCRIPTION   ""
    ::= { pmOptMuxPhysRecord 17 }

atRcvOptMuxHistorical1weekEntry OBJECT-TYPE
    SYNTAX        AtRcvOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  atRcvOptMuxHistorical1weekNumber
                }
    ::= { atRcvOptMuxHistorical1weekTable 1 }

AtRcvOptMuxHistorical1weekEntry ::= SEQUENCE
  {    atRcvOptMuxHistorical1weekNumber Integer32,
    atRcvOptMuxHistorical1weekLow Integer32,
    atRcvOptMuxHistorical1weekMean Integer32,
    atRcvOptMuxHistorical1weekHigh Integer32,
    atRcvOptMuxHistorical1weekValidFlag TruthValue,
    atRcvOptMuxHistorical1weekTimeStamp DateAndTime }

atRcvOptMuxHistorical1weekNumber OBJECT-TYPE
    SYNTAX        Integer32 (1..52)
    MAX-ACCESS    not-accessible
    STATUS        current
    DESCRIPTION   "Number 1week"
    ::= { atRcvOptMuxHistorical1weekEntry 1 }

atRcvOptMuxHistorical1weekLow OBJECT-TYPE
    SYNTAX        Integer32
    UNITS         "0.1 dB"
    MAX-ACCESS    read-only
    STATUS        current
    DESCRIPTION   "Low Attenuation on Receive Fiber"
    ::= { atRcvOptMuxHistorical1weekEntry 2 }

atRcvOptMuxHistorical1weekMean OBJECT-TYPE
    SYNTAX        Integer32
    UNITS         "0.1 dB"
    MAX-ACCESS    read-only
    STATUS        current
    DESCRIPTION   "Mean Attenuation on Receive Fiber"
    ::= { atRcvOptMuxHistorical1weekEntry 3 }

atRcvOptMuxHistorical1weekHigh OBJECT-TYPE
    SYNTAX        Integer32
    UNITS         "0.1 dB"
    MAX-ACCESS    read-only
    STATUS        current
    DESCRIPTION   "High Attenuation on Receive Fiber"
    ::= { atRcvOptMuxHistorical1weekEntry 4 }

atRcvOptMuxHistorical1weekValidFlag OBJECT-TYPE
    SYNTAX        TruthValue
    MAX-ACCESS    read-only
    STATUS        current
    DESCRIPTION   "Valid Flag"
    ::= { atRcvOptMuxHistorical1weekEntry 5 }

atRcvOptMuxHistorical1weekTimeStamp OBJECT-TYPE
    SYNTAX        DateAndTime
    MAX-ACCESS    read-only
    STATUS        current
    DESCRIPTION   "Timestamp"
    ::= { atRcvOptMuxHistorical1weekEntry 6 }

endOfAtRcvOptMuxHistorical1weekTable OBJECT-TYPE
    SYNTAX        Integer32
    MAX-ACCESS    read-only
    STATUS        current
    DESCRIPTION   ""
    ::= { pmOptMuxPhysRecord 18 }

brOptMuxHistorical15minTable OBJECT-TYPE
    SYNTAX        SEQUENCE OF BrOptMuxHistorical15minEntry
    MAX-ACCESS    not-accessible
    STATUS        current
    DESCRIPTION   ""
    ::= { pmOptMuxPhysRecord 19 }

brOptMuxHistorical15minEntry OBJECT-TYPE
    SYNTAX        BrOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  brOptMuxHistorical15minNumber
                }
    ::= { brOptMuxHistorical15minTable 1 }

BrOptMuxHistorical15minEntry ::= SEQUENCE
  {    brOptMuxHistorical15minNumber Integer32,
    brOptMuxHistorical15minLow Integer32,
    brOptMuxHistorical15minMean Integer32,
    brOptMuxHistorical15minHigh Integer32,
    brOptMuxHistorical15minValidFlag TruthValue,
    brOptMuxHistorical15minTimeStamp DateAndTime }

brOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { brOptMuxHistorical15minEntry 1 }

brOptMuxHistorical15minLow OBJECT-TYPE
    SYNTAX        Integer32
    UNITS         "0.1 dB"
    MAX-ACCESS    read-only
    STATUS        current
    DESCRIPTION   "Back Reflection Received"
    ::= { brOptMuxHistorical15minEntry 2 }

brOptMuxHistorical15minMean OBJECT-TYPE
    SYNTAX        Integer32
    UNITS         "0.1 dB"
    MAX-ACCESS    read-only
    STATUS        current
    DESCRIPTION   "Back Reflection Received Average"
    ::= { brOptMuxHistorical15minEntry 3 }

brOptMuxHistorical15minHigh OBJECT-TYPE
    SYNTAX        Integer32
    UNITS         "0.1 dB"
    MAX-ACCESS    read-only
    STATUS        current
    DESCRIPTION   "Back Reflection Received High"
    ::= { brOptMuxHistorical15minEntry 4 }

brOptMuxHistorical15minValidFlag OBJECT-TYPE
    SYNTAX        TruthValue
    MAX-ACCESS    read-only
    STATUS        current
    DESCRIPTION   "Valid Flag"
    ::= { brOptMuxHistorical15minEntry 5 }

brOptMuxHistorical15minTimeStamp OBJECT-TYPE
    SYNTAX        DateAndTime
    MAX-ACCESS    read-only
    STATUS        current
    DESCRIPTION   "Timestamp"
    ::= { brOptMuxHistorical15minEntry 6 }

endOfBrOptMuxHistorical15minTable OBJECT-TYPE
    SYNTAX        Integer32
    MAX-ACCESS    read-only
    STATUS        current
    DESCRIPTION   ""
    ::= { pmOptMuxPhysRecord 20 }

brOptMuxHistorical1dayTable OBJECT-TYPE
    SYNTAX        SEQUENCE OF BrOptMuxHistorical1dayEntry
    MAX-ACCESS    not-accessible
    STATUS        current
    DESCRIPTION   ""
    ::= { pmOptMuxPhysRecord 21 }

brOptMuxHistorical1dayEntry OBJECT-TYPE
    SYNTAX        BrOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  brOptMuxHistorical1dayNumber
                }
    ::= { brOptMuxHistorical1dayTable 1 }

BrOptMuxHistorical1dayEntry ::= SEQUENCE
  {    brOptMuxHistorical1dayNumber Integer32,
    brOptMuxHistorical1dayLow Integer32,
    brOptMuxHistorical1dayMean Integer32,
    brOptMuxHistorical1dayHigh Integer32,
    brOptMuxHistorical1dayValidFlag TruthValue,
    brOptMuxHistorical1dayTimeStamp DateAndTime }

brOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { brOptMuxHistorical1dayEntry 1 }

brOptMuxHistorical1dayLow OBJECT-TYPE
    SYNTAX        Integer32
    UNITS         "0.1 dB"
    MAX-ACCESS    read-only
    STATUS        current
    DESCRIPTION   "Back Reflection Received"
    ::= { brOptMuxHistorical1dayEntry 2 }

brOptMuxHistorical1dayMean OBJECT-TYPE
    SYNTAX        Integer32
    UNITS         "0.1 dB"
    MAX-ACCESS    read-only
    STATUS        current
    DESCRIPTION   "Back Reflection Received Average"
    ::= { brOptMuxHistorical1dayEntry 3 }

brOptMuxHistorical1dayHigh OBJECT-TYPE
    SYNTAX        Integer32
    UNITS         "0.1 dB"
    MAX-ACCESS    read-only
    STATUS        current
    DESCRIPTION   "Back Reflection Received High"
    ::= { brOptMuxHistorical1dayEntry 4 }

brOptMuxHistorical1dayValidFlag OBJECT-TYPE
    SYNTAX        TruthValue
    MAX-ACCESS    read-only
    STATUS        current
    DESCRIPTION   "Valid Flag"
    ::= { brOptMuxHistorical1dayEntry 5 }

brOptMuxHistorical1dayTimeStamp OBJECT-TYPE
    SYNTAX        DateAndTime
    MAX-ACCESS    read-only
    STATUS        current
    DESCRIPTION   "Timestamp"
    ::= { brOptMuxHistorical1dayEntry 6 }

endOfBrOptMuxHistorical1dayTable OBJECT-TYPE
    SYNTAX        Integer32
    MAX-ACCESS    read-only
    STATUS        current
    DESCRIPTION   ""
    ::= { pmOptMuxPhysRecord 22 }

brOptMuxHistorical1weekTable OBJECT-TYPE
    SYNTAX        SEQUENCE OF BrOptMuxHistorical1weekEntry
    MAX-ACCESS    not-accessible
    STATUS        current
    DESCRIPTION   ""
    ::= { pmOptMuxPhysRecord 23 }

brOptMuxHistorical1weekEntry OBJECT-TYPE
    SYNTAX        BrOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  brOptMuxHistorical1weekNumber
                }
    ::= { brOptMuxHistorical1weekTable 1 }

BrOptMuxHistorical1weekEntry ::= SEQUENCE
  {    brOptMuxHistorical1weekNumber Integer32,
    brOptMuxHistorical1weekLow Integer32,
    brOptMuxHistorical1weekMean Integer32,
    brOptMuxHistorical1weekHigh Integer32,
    brOptMuxHistorical1weekValidFlag TruthValue,
    brOptMuxHistorical1weekTimeStamp DateAndTime }

brOptMuxHistorical1weekNumber OBJECT-TYPE
    SYNTAX        Integer32 (1..52)
    MAX-ACCESS    not-accessible
    STATUS        current
    DESCRIPTION   "Number 1week"
    ::= { brOptMuxHistorical1weekEntry 1 }

brOptMuxHistorical1weekLow OBJECT-TYPE
    SYNTAX        Integer32
    UNITS         "0.1 dB"
    MAX-ACCESS    read-only
    STATUS        current
    DESCRIPTION   "Back Reflection Received"
    ::= { brOptMuxHistorical1weekEntry 2 }

brOptMuxHistorical1weekMean OBJECT-TYPE
    SYNTAX        Integer32
    UNITS         "0.1 dB"
    MAX-ACCESS    read-only
    STATUS        current
    DESCRIPTION   "Back Reflection Received Average"
    ::= { brOptMuxHistorical1weekEntry 3 }

brOptMuxHistorical1weekHigh OBJECT-TYPE
    SYNTAX        Integer32
    UNITS         "0.1 dB"
    MAX-ACCESS    read-only
    STATUS        current
    DESCRIPTION   "Back Reflection Received High"
    ::= { brOptMuxHistorical1weekEntry 4 }

brOptMuxHistorical1weekValidFlag OBJECT-TYPE
    SYNTAX        TruthValue
    MAX-ACCESS    read-only
    STATUS        current
    DESCRIPTION   "Valid Flag"
    ::= { brOptMuxHistorical1weekEntry 5 }

brOptMuxHistorical1weekTimeStamp OBJECT-TYPE
    SYNTAX        DateAndTime
    MAX-ACCESS    read-only
    STATUS        current
    DESCRIPTION   "Timestamp"
    ::= { brOptMuxHistorical1weekEntry 6 }

endOfBrOptMuxHistorical1weekTable OBJECT-TYPE
    SYNTAX        Integer32
    MAX-ACCESS    read-only
    STATUS        current
    DESCRIPTION   ""
    ::= { pmOptMuxPhysRecord 24 }

estSigGainOptMuxHistorical15minTable OBJECT-TYPE
    SYNTAX        SEQUENCE OF EstSigGainOptMuxHistorical15minEntry
    MAX-ACCESS    not-accessible
    STATUS        current
    DESCRIPTION   ""
    ::= { pmOptMuxPhysRecord 25 }

estSigGainOptMuxHistorical15minEntry OBJECT-TYPE
    SYNTAX        EstSigGainOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  estSigGainOptMuxHistorical15minNumber
                }
    ::= { estSigGainOptMuxHistorical15minTable 1 }

EstSigGainOptMuxHistorical15minEntry ::= SEQUENCE
  {    estSigGainOptMuxHistorical15minNumber Integer32,
    estSigGainOptMuxHistorical15minLow Unsigned32,
    estSigGainOptMuxHistorical15minMean Unsigned32,
    estSigGainOptMuxHistorical15minHigh Unsigned32,
    estSigGainOptMuxHistorical15minValidFlag TruthValue,
    estSigGainOptMuxHistorical15minTimeStamp DateAndTime }

estSigGainOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { estSigGainOptMuxHistorical15minEntry 1 }

estSigGainOptMuxHistorical15minLow OBJECT-TYPE
    SYNTAX        Unsigned32
    UNITS         "0.1 dB"
    MAX-ACCESS    read-only
    STATUS        current
    DESCRIPTION   "Estimated signal gain low"
    ::= { estSigGainOptMuxHistorical15minEntry 2 }

estSigGainOptMuxHistorical15minMean OBJECT-TYPE
    SYNTAX        Unsigned32
    UNITS         "0.1 dB"
    MAX-ACCESS    read-only
    STATUS        current
    DESCRIPTION   "Estimated signal gain average"
    ::= { estSigGainOptMuxHistorical15minEntry 3 }

estSigGainOptMuxHistorical15minHigh OBJECT-TYPE
    SYNTAX        Unsigned32
    UNITS         "0.1 dB"
    MAX-ACCESS    read-only
    STATUS        current
    DESCRIPTION   "Estimated signal gain high"
    ::= { estSigGainOptMuxHistorical15minEntry 4 }

estSigGainOptMuxHistorical15minValidFlag OBJECT-TYPE
    SYNTAX        TruthValue
    MAX-ACCESS    read-only
    STATUS        current
    DESCRIPTION   "Valid Flag"
    ::= { estSigGainOptMuxHistorical15minEntry 5 }

estSigGainOptMuxHistorical15minTimeStamp OBJECT-TYPE
    SYNTAX        DateAndTime
    MAX-ACCESS    read-only
    STATUS        current
    DESCRIPTION   "Timestamp"
    ::= { estSigGainOptMuxHistorical15minEntry 6 }

endOfEstSigGainOptMuxHistorical15minTable OBJECT-TYPE
    SYNTAX        Integer32
    MAX-ACCESS    read-only
    STATUS        current
    DESCRIPTION   ""
    ::= { pmOptMuxPhysRecord 26 }

estSigGainOptMuxHistorical1dayTable OBJECT-TYPE
    SYNTAX        SEQUENCE OF EstSigGainOptMuxHistorical1dayEntry
    MAX-ACCESS    not-accessible
    STATUS        current
    DESCRIPTION   ""
    ::= { pmOptMuxPhysRecord 27 }

estSigGainOptMuxHistorical1dayEntry OBJECT-TYPE
    SYNTAX        EstSigGainOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  estSigGainOptMuxHistorical1dayNumber
                }
    ::= { estSigGainOptMuxHistorical1dayTable 1 }

EstSigGainOptMuxHistorical1dayEntry ::= SEQUENCE
  {    estSigGainOptMuxHistorical1dayNumber Integer32,
    estSigGainOptMuxHistorical1dayLow Unsigned32,
    estSigGainOptMuxHistorical1dayMean Unsigned32,
    estSigGainOptMuxHistorical1dayHigh Unsigned32,
    estSigGainOptMuxHistorical1dayValidFlag TruthValue,
    estSigGainOptMuxHistorical1dayTimeStamp DateAndTime }

estSigGainOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { estSigGainOptMuxHistorical1dayEntry 1 }

estSigGainOptMuxHistorical1dayLow OBJECT-TYPE
    SYNTAX        Unsigned32
    UNITS         "0.1 dB"
    MAX-ACCESS    read-only
    STATUS        current
    DESCRIPTION   "Estimated signal gain low"
    ::= { estSigGainOptMuxHistorical1dayEntry 2 }

estSigGainOptMuxHistorical1dayMean OBJECT-TYPE
    SYNTAX        Unsigned32
    UNITS         "0.1 dB"
    MAX-ACCESS    read-only
    STATUS        current
    DESCRIPTION   "Estimated signal gain average"
    ::= { estSigGainOptMuxHistorical1dayEntry 3 }

estSigGainOptMuxHistorical1dayHigh OBJECT-TYPE
    SYNTAX        Unsigned32
    UNITS         "0.1 dB"
    MAX-ACCESS    read-only
    STATUS        current
    DESCRIPTION   "Estimated signal gain high"
    ::= { estSigGainOptMuxHistorical1dayEntry 4 }

estSigGainOptMuxHistorical1dayValidFlag OBJECT-TYPE
    SYNTAX        TruthValue
    MAX-ACCESS    read-only
    STATUS        current
    DESCRIPTION   "Valid Flag"
    ::= { estSigGainOptMuxHistorical1dayEntry 5 }

estSigGainOptMuxHistorical1dayTimeStamp OBJECT-TYPE
    SYNTAX        DateAndTime
    MAX-ACCESS    read-only
    STATUS        current
    DESCRIPTION   "Timestamp"
    ::= { estSigGainOptMuxHistorical1dayEntry 6 }

endOfEstSigGainOptMuxHistorical1dayTable OBJECT-TYPE
    SYNTAX        Integer32
    MAX-ACCESS    read-only
    STATUS        current
    DESCRIPTION   ""
    ::= { pmOptMuxPhysRecord 28 }

estSigGainOptMuxHistorical1weekTable OBJECT-TYPE
    SYNTAX        SEQUENCE OF EstSigGainOptMuxHistorical1weekEntry
    MAX-ACCESS    not-accessible
    STATUS        current
    DESCRIPTION   ""
    ::= { pmOptMuxPhysRecord 29 }

estSigGainOptMuxHistorical1weekEntry OBJECT-TYPE
    SYNTAX        EstSigGainOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  estSigGainOptMuxHistorical1weekNumber
                }
    ::= { estSigGainOptMuxHistorical1weekTable 1 }

EstSigGainOptMuxHistorical1weekEntry ::= SEQUENCE
  {    estSigGainOptMuxHistorical1weekNumber Integer32,
    estSigGainOptMuxHistorical1weekLow Unsigned32,
    estSigGainOptMuxHistorical1weekMean Unsigned32,
    estSigGainOptMuxHistorical1weekHigh Unsigned32,
    estSigGainOptMuxHistorical1weekValidFlag TruthValue,
    estSigGainOptMuxHistorical1weekTimeStamp DateAndTime }

estSigGainOptMuxHistorical1weekNumber OBJECT-TYPE
    SYNTAX        Integer32 (1..52)
    MAX-ACCESS    not-accessible
    STATUS        current
    DESCRIPTION   "Number 1week"
    ::= { estSigGainOptMuxHistorical1weekEntry 1 }

estSigGainOptMuxHistorical1weekLow OBJECT-TYPE
    SYNTAX        Unsigned32
    UNITS         "0.1 dB"
    MAX-ACCESS    read-only
    STATUS        current
    DESCRIPTION   "Estimated signal gain low"
    ::= { estSigGainOptMuxHistorical1weekEntry 2 }

estSigGainOptMuxHistorical1weekMean OBJECT-TYPE
    SYNTAX        Unsigned32
    UNITS         "0.1 dB"
    MAX-ACCESS    read-only
    STATUS        current
    DESCRIPTION   "Estimated signal gain average"
    ::= { estSigGainOptMuxHistorical1weekEntry 3 }

estSigGainOptMuxHistorical1weekHigh OBJECT-TYPE
    SYNTAX        Unsigned32
    UNITS         "0.1 dB"
    MAX-ACCESS    read-only
    STATUS        current
    DESCRIPTION   "Estimated signal gain high"
    ::= { estSigGainOptMuxHistorical1weekEntry 4 }

estSigGainOptMuxHistorical1weekValidFlag OBJECT-TYPE
    SYNTAX        TruthValue
    MAX-ACCESS    read-only
    STATUS        current
    DESCRIPTION   "Valid Flag"
    ::= { estSigGainOptMuxHistorical1weekEntry 5 }

estSigGainOptMuxHistorical1weekTimeStamp OBJECT-TYPE
    SYNTAX        DateAndTime
    MAX-ACCESS    read-only
    STATUS        current
    DESCRIPTION   "Timestamp"
    ::= { estSigGainOptMuxHistorical1weekEntry 6 }

endOfEstSigGainOptMuxHistorical1weekTable OBJECT-TYPE
    SYNTAX        Integer32
    MAX-ACCESS    read-only
    STATUS        current
    DESCRIPTION   ""
    ::= { pmOptMuxPhysRecord 30 }

attrmtOptMuxHistorical15minTable OBJECT-TYPE
    SYNTAX        SEQUENCE OF AttrmtOptMuxHistorical15minEntry
    MAX-ACCESS    not-accessible
    STATUS        current
    DESCRIPTION   ""
    ::= { pmOptMuxPhysRecord 31 }

attrmtOptMuxHistorical15minEntry OBJECT-TYPE
    SYNTAX        AttrmtOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  attrmtOptMuxHistorical15minNumber
                }
    ::= { attrmtOptMuxHistorical15minTable 1 }

AttrmtOptMuxHistorical15minEntry ::= SEQUENCE
  {    attrmtOptMuxHistorical15minNumber Integer32,
    attrmtOptMuxHistorical15minLow Integer32,
    attrmtOptMuxHistorical15minHigh Integer32,
    attrmtOptMuxHistorical15minMean Integer32,
    attrmtOptMuxHistorical15minValidFlag TruthValue,
    attrmtOptMuxHistorical15minTimeStamp DateAndTime }

attrmtOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { attrmtOptMuxHistorical15minEntry 1 }

attrmtOptMuxHistorical15minLow OBJECT-TYPE
    SYNTAX        Integer32
    UNITS         "0.1 dB"
    MAX-ACCESS    read-only
    STATUS        current
    DESCRIPTION   "Low Attenuation on Transmit Fiber"
    ::= { attrmtOptMuxHistorical15minEntry 2 }

attrmtOptMuxHistorical15minHigh OBJECT-TYPE
    SYNTAX        Integer32
    UNITS         "0.1 dB"
    MAX-ACCESS    read-only
    STATUS        current
    DESCRIPTION   "High Attenuation on Transmit Fiber"
    ::= { attrmtOptMuxHistorical15minEntry 3 }

attrmtOptMuxHistorical15minMean OBJECT-TYPE
    SYNTAX        Integer32
    UNITS         "0.1 dB"
    MAX-ACCESS    read-only
    STATUS        current
    DESCRIPTION   "Mean Attenuation on Transmit Fiber"
    ::= { attrmtOptMuxHistorical15minEntry 4 }

attrmtOptMuxHistorical15minValidFlag OBJECT-TYPE
    SYNTAX        TruthValue
    MAX-ACCESS    read-only
    STATUS        current
    DESCRIPTION   "Valid Flag"
    ::= { attrmtOptMuxHistorical15minEntry 5 }

attrmtOptMuxHistorical15minTimeStamp OBJECT-TYPE
    SYNTAX        DateAndTime
    MAX-ACCESS    read-only
    STATUS        current
    DESCRIPTION   "Timestamp"
    ::= { attrmtOptMuxHistorical15minEntry 6 }

endOfAttrmtOptMuxHistorical15minTable OBJECT-TYPE
    SYNTAX        Integer32
    MAX-ACCESS    read-only
    STATUS        current
    DESCRIPTION   ""
    ::= { pmOptMuxPhysRecord 32 }

attrmtOptMuxHistorical1dayTable OBJECT-TYPE
    SYNTAX        SEQUENCE OF AttrmtOptMuxHistorical1dayEntry
    MAX-ACCESS    not-accessible
    STATUS        current
    DESCRIPTION   ""
    ::= { pmOptMuxPhysRecord 33 }

attrmtOptMuxHistorical1dayEntry OBJECT-TYPE
    SYNTAX        AttrmtOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  attrmtOptMuxHistorical1dayNumber
                }
    ::= { attrmtOptMuxHistorical1dayTable 1 }

AttrmtOptMuxHistorical1dayEntry ::= SEQUENCE
  {    attrmtOptMuxHistorical1dayNumber Integer32,
    attrmtOptMuxHistorical1dayLow Integer32,
    attrmtOptMuxHistorical1dayHigh Integer32,
    attrmtOptMuxHistorical1dayMean Integer32,
    attrmtOptMuxHistorical1dayValidFlag TruthValue,
    attrmtOptMuxHistorical1dayTimeStamp DateAndTime }

attrmtOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { attrmtOptMuxHistorical1dayEntry 1 }

attrmtOptMuxHistorical1dayLow OBJECT-TYPE
    SYNTAX        Integer32
    UNITS         "0.1 dB"
    MAX-ACCESS    read-only
    STATUS        current
    DESCRIPTION   "Low Attenuation on Transmit Fiber"
    ::= { attrmtOptMuxHistorical1dayEntry 2 }

attrmtOptMuxHistorical1dayHigh OBJECT-TYPE
    SYNTAX        Integer32
    UNITS         "0.1 dB"
    MAX-ACCESS    read-only
    STATUS        current
    DESCRIPTION   "High Attenuation on Transmit Fiber"
    ::= { attrmtOptMuxHistorical1dayEntry 3 }

attrmtOptMuxHistorical1dayMean OBJECT-TYPE
    SYNTAX        Integer32
    UNITS         "0.1 dB"
    MAX-ACCESS    read-only
    STATUS        current
    DESCRIPTION   "Mean Attenuation on Transmit Fiber"
    ::= { attrmtOptMuxHistorical1dayEntry 4 }

attrmtOptMuxHistorical1dayValidFlag OBJECT-TYPE
    SYNTAX        TruthValue
    MAX-ACCESS    read-only
    STATUS        current
    DESCRIPTION   "Valid Flag"
    ::= { attrmtOptMuxHistorical1dayEntry 5 }

attrmtOptMuxHistorical1dayTimeStamp OBJECT-TYPE
    SYNTAX        DateAndTime
    MAX-ACCESS    read-only
    STATUS        current
    DESCRIPTION   "Timestamp"
    ::= { attrmtOptMuxHistorical1dayEntry 6 }

endOfAttrmtOptMuxHistorical1dayTable OBJECT-TYPE
    SYNTAX        Integer32
    MAX-ACCESS    read-only
    STATUS        current
    DESCRIPTION   ""
    ::= { pmOptMuxPhysRecord 34 }

attrmtOptMuxHistorical1weekTable OBJECT-TYPE
    SYNTAX        SEQUENCE OF AttrmtOptMuxHistorical1weekEntry
    MAX-ACCESS    not-accessible
    STATUS        current
    DESCRIPTION   ""
    ::= { pmOptMuxPhysRecord 35 }

attrmtOptMuxHistorical1weekEntry OBJECT-TYPE
    SYNTAX        AttrmtOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  attrmtOptMuxHistorical1weekNumber
                }
    ::= { attrmtOptMuxHistorical1weekTable 1 }

AttrmtOptMuxHistorical1weekEntry ::= SEQUENCE
  {    attrmtOptMuxHistorical1weekNumber Integer32,
    attrmtOptMuxHistorical1weekLow Integer32,
    attrmtOptMuxHistorical1weekHigh Integer32,
    attrmtOptMuxHistorical1weekMean Integer32,
    attrmtOptMuxHistorical1weekValidFlag TruthValue,
    attrmtOptMuxHistorical1weekTimeStamp DateAndTime }

attrmtOptMuxHistorical1weekNumber OBJECT-TYPE
    SYNTAX        Integer32 (1..52)
    MAX-ACCESS    not-accessible
    STATUS        current
    DESCRIPTION   "Number 1week"
    ::= { attrmtOptMuxHistorical1weekEntry 1 }

attrmtOptMuxHistorical1weekLow OBJECT-TYPE
    SYNTAX        Integer32
    UNITS         "0.1 dB"
    MAX-ACCESS    read-only
    STATUS        current
    DESCRIPTION   "Low Attenuation on Transmit Fiber"
    ::= { attrmtOptMuxHistorical1weekEntry 2 }

attrmtOptMuxHistorical1weekHigh OBJECT-TYPE
    SYNTAX        Integer32
    UNITS         "0.1 dB"
    MAX-ACCESS    read-only
    STATUS        current
    DESCRIPTION   "High Attenuation on Transmit Fiber"
    ::= { attrmtOptMuxHistorical1weekEntry 3 }

attrmtOptMuxHistorical1weekMean OBJECT-TYPE
    SYNTAX        Integer32
    UNITS         "0.1 dB"
    MAX-ACCESS    read-only
    STATUS        current
    DESCRIPTION   "Mean Attenuation on Transmit Fiber"
    ::= { attrmtOptMuxHistorical1weekEntry 4 }

attrmtOptMuxHistorical1weekValidFlag OBJECT-TYPE
    SYNTAX        TruthValue
    MAX-ACCESS    read-only
    STATUS        current
    DESCRIPTION   "Valid Flag"
    ::= { attrmtOptMuxHistorical1weekEntry 5 }

attrmtOptMuxHistorical1weekTimeStamp OBJECT-TYPE
    SYNTAX        DateAndTime
    MAX-ACCESS    read-only
    STATUS        current
    DESCRIPTION   "Timestamp"
    ::= { attrmtOptMuxHistorical1weekEntry 6 }

endOfAttrmtOptMuxHistorical1weekTable OBJECT-TYPE
    SYNTAX        Integer32
    MAX-ACCESS    read-only
    STATUS        current
    DESCRIPTION   ""
    ::= { pmOptMuxPhysRecord 36 }

pumpPwrOptMuxHistorical15minTable OBJECT-TYPE
    SYNTAX        SEQUENCE OF PumpPwrOptMuxHistorical15minEntry
    MAX-ACCESS    not-accessible
    STATUS        current
    DESCRIPTION   ""
    ::= { pmOptMuxPhysRecord 37 }

pumpPwrOptMuxHistorical15minEntry OBJECT-TYPE
    SYNTAX        PumpPwrOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  pumpPwrOptMuxHistorical15minNumber
                }
    ::= { pumpPwrOptMuxHistorical15minTable 1 }

PumpPwrOptMuxHistorical15minEntry ::= SEQUENCE
  {    pumpPwrOptMuxHistorical15minNumber Integer32,
    pumpPwrOptMuxHistorical15minLow Integer32,
    pumpPwrOptMuxHistorical15minMean Integer32,
    pumpPwrOptMuxHistorical15minHigh Integer32,
    pumpPwrOptMuxHistorical15minValidFlag TruthValue,
    pumpPwrOptMuxHistorical15minTimeStamp DateAndTime }

pumpPwrOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { pumpPwrOptMuxHistorical15minEntry 1 }

pumpPwrOptMuxHistorical15minLow OBJECT-TYPE
    SYNTAX        Integer32
    UNITS         "0.1 dBm"
    MAX-ACCESS    read-only
    STATUS        current
    DESCRIPTION   "Total raman pump power low"
    ::= { pumpPwrOptMuxHistorical15minEntry 2 }

pumpPwrOptMuxHistorical15minMean OBJECT-TYPE
    SYNTAX        Integer32
    UNITS         "0.1 dBm"
    MAX-ACCESS    read-only
    STATUS        current
    DESCRIPTION   "Raman Pump Power Received Average"
    ::= { pumpPwrOptMuxHistorical15minEntry 3 }

pumpPwrOptMuxHistorical15minHigh OBJECT-TYPE
    SYNTAX        Integer32
    UNITS         "0.1 dBm"
    MAX-ACCESS    read-only
    STATUS        current
    DESCRIPTION   "Total raman pump power High"
    ::= { pumpPwrOptMuxHistorical15minEntry 4 }

pumpPwrOptMuxHistorical15minValidFlag OBJECT-TYPE
    SYNTAX        TruthValue
    MAX-ACCESS    read-only
    STATUS        current
    DESCRIPTION   "Valid Flag"
    ::= { pumpPwrOptMuxHistorical15minEntry 5 }

pumpPwrOptMuxHistorical15minTimeStamp OBJECT-TYPE
    SYNTAX        DateAndTime
    MAX-ACCESS    read-only
    STATUS        current
    DESCRIPTION   "Timestamp"
    ::= { pumpPwrOptMuxHistorical15minEntry 6 }

endOfPumpPwrOptMuxHistorical15minTable OBJECT-TYPE
    SYNTAX        Integer32
    MAX-ACCESS    read-only
    STATUS        current
    DESCRIPTION   ""
    ::= { pmOptMuxPhysRecord 38 }

pumpPwrOptMuxHistorical1dayTable OBJECT-TYPE
    SYNTAX        SEQUENCE OF PumpPwrOptMuxHistorical1dayEntry
    MAX-ACCESS    not-accessible
    STATUS        current
    DESCRIPTION   ""
    ::= { pmOptMuxPhysRecord 39 }

pumpPwrOptMuxHistorical1dayEntry OBJECT-TYPE
    SYNTAX        PumpPwrOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  pumpPwrOptMuxHistorical1dayNumber
                }
    ::= { pumpPwrOptMuxHistorical1dayTable 1 }

PumpPwrOptMuxHistorical1dayEntry ::= SEQUENCE
  {    pumpPwrOptMuxHistorical1dayNumber Integer32,
    pumpPwrOptMuxHistorical1dayLow Integer32,
    pumpPwrOptMuxHistorical1dayMean Integer32,
    pumpPwrOptMuxHistorical1dayHigh Integer32,
    pumpPwrOptMuxHistorical1dayValidFlag TruthValue,
    pumpPwrOptMuxHistorical1dayTimeStamp DateAndTime }

pumpPwrOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { pumpPwrOptMuxHistorical1dayEntry 1 }

pumpPwrOptMuxHistorical1dayLow OBJECT-TYPE
    SYNTAX        Integer32
    UNITS         "0.1 dBm"
    MAX-ACCESS    read-only
    STATUS        current
    DESCRIPTION   "Total raman pump power low"
    ::= { pumpPwrOptMuxHistorical1dayEntry 2 }

pumpPwrOptMuxHistorical1dayMean OBJECT-TYPE
    SYNTAX        Integer32
    UNITS         "0.1 dBm"
    MAX-ACCESS    read-only
    STATUS        current
    DESCRIPTION   "Raman Pump Power Received Average"
    ::= { pumpPwrOptMuxHistorical1dayEntry 3 }

pumpPwrOptMuxHistorical1dayHigh OBJECT-TYPE
    SYNTAX        Integer32
    UNITS         "0.1 dBm"
    MAX-ACCESS    read-only
    STATUS        current
    DESCRIPTION   "Total raman pump power High"
    ::= { pumpPwrOptMuxHistorical1dayEntry 4 }

pumpPwrOptMuxHistorical1dayValidFlag OBJECT-TYPE
    SYNTAX        TruthValue
    MAX-ACCESS    read-only
    STATUS        current
    DESCRIPTION   "Valid Flag"
    ::= { pumpPwrOptMuxHistorical1dayEntry 5 }

pumpPwrOptMuxHistorical1dayTimeStamp OBJECT-TYPE
    SYNTAX        DateAndTime
    MAX-ACCESS    read-only
    STATUS        current
    DESCRIPTION   "Timestamp"
    ::= { pumpPwrOptMuxHistorical1dayEntry 6 }

endOfPumpPwrOptMuxHistorical1dayTable OBJECT-TYPE
    SYNTAX        Integer32
    MAX-ACCESS    read-only
    STATUS        current
    DESCRIPTION   ""
    ::= { pmOptMuxPhysRecord 40 }

pumpPwrOptMuxHistorical1weekTable OBJECT-TYPE
    SYNTAX        SEQUENCE OF PumpPwrOptMuxHistorical1weekEntry
    MAX-ACCESS    not-accessible
    STATUS        current
    DESCRIPTION   ""
    ::= { pmOptMuxPhysRecord 41 }

pumpPwrOptMuxHistorical1weekEntry OBJECT-TYPE
    SYNTAX        PumpPwrOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  pumpPwrOptMuxHistorical1weekNumber
                }
    ::= { pumpPwrOptMuxHistorical1weekTable 1 }

PumpPwrOptMuxHistorical1weekEntry ::= SEQUENCE
  {    pumpPwrOptMuxHistorical1weekNumber Integer32,
    pumpPwrOptMuxHistorical1weekLow Integer32,
    pumpPwrOptMuxHistorical1weekMean Integer32,
    pumpPwrOptMuxHistorical1weekHigh Integer32,
    pumpPwrOptMuxHistorical1weekValidFlag TruthValue,
    pumpPwrOptMuxHistorical1weekTimeStamp DateAndTime }

pumpPwrOptMuxHistorical1weekNumber OBJECT-TYPE
    SYNTAX        Integer32 (1..52)
    MAX-ACCESS    not-accessible
    STATUS        current
    DESCRIPTION   "Number 1week"
    ::= { pumpPwrOptMuxHistorical1weekEntry 1 }

pumpPwrOptMuxHistorical1weekLow OBJECT-TYPE
    SYNTAX        Integer32
    UNITS         "0.1 dBm"
    MAX-ACCESS    read-only
    STATUS        current
    DESCRIPTION   "Total raman pump power low"
    ::= { pumpPwrOptMuxHistorical1weekEntry 2 }

pumpPwrOptMuxHistorical1weekMean OBJECT-TYPE
    SYNTAX        Integer32
    UNITS         "0.1 dBm"
    MAX-ACCESS    read-only
    STATUS        current
    DESCRIPTION   "Raman Pump Power Received Average"
    ::= { pumpPwrOptMuxHistorical1weekEntry 3 }

pumpPwrOptMuxHistorical1weekHigh OBJECT-TYPE
    SYNTAX        Integer32
    UNITS         "0.1 dBm"
    MAX-ACCESS    read-only
    STATUS        current
    DESCRIPTION   "Total raman pump power High"
    ::= { pumpPwrOptMuxHistorical1weekEntry 4 }

pumpPwrOptMuxHistorical1weekValidFlag OBJECT-TYPE
    SYNTAX        TruthValue
    MAX-ACCESS    read-only
    STATUS        current
    DESCRIPTION   "Valid Flag"
    ::= { pumpPwrOptMuxHistorical1weekEntry 5 }

pumpPwrOptMuxHistorical1weekTimeStamp OBJECT-TYPE
    SYNTAX        DateAndTime
    MAX-ACCESS    read-only
    STATUS        current
    DESCRIPTION   "Timestamp"
    ::= { pumpPwrOptMuxHistorical1weekEntry 6 }

endOfPumpPwrOptMuxHistorical1weekTable OBJECT-TYPE
    SYNTAX        Integer32
    MAX-ACCESS    read-only
    STATUS        current
    DESCRIPTION   ""
    ::= { pmOptMuxPhysRecord 42 }

oscOptOptMuxHistorical15minTable OBJECT-TYPE
    SYNTAX        SEQUENCE OF OscOptOptMuxHistorical15minEntry
    MAX-ACCESS    not-accessible
    STATUS        current
    DESCRIPTION   ""
    ::= { pmOptMuxPhysRecord 43 }

oscOptOptMuxHistorical15minEntry OBJECT-TYPE
    SYNTAX        OscOptOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscOptOptMuxHistorical15minNumber
                }
    ::= { oscOptOptMuxHistorical15minTable 1 }

OscOptOptMuxHistorical15minEntry ::= SEQUENCE
  {    oscOptOptMuxHistorical15minNumber Integer32,
    oscOptOptMuxHistorical15minLow Integer32,
    oscOptOptMuxHistorical15minMean Integer32,
    oscOptOptMuxHistorical15minHigh Integer32,
    oscOptOptMuxHistorical15minValidFlag TruthValue,
    oscOptOptMuxHistorical15minTimeStamp DateAndTime }

oscOptOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oscOptOptMuxHistorical15minEntry 1 }

oscOptOptMuxHistorical15minLow OBJECT-TYPE
    SYNTAX        Integer32
    UNITS         "0.1 dBm"
    MAX-ACCESS    read-only
    STATUS        current
    DESCRIPTION   "OSC Optical Output Power Transmitted"
    ::= { oscOptOptMuxHistorical15minEntry 2 }

oscOptOptMuxHistorical15minMean OBJECT-TYPE
    SYNTAX        Integer32
    UNITS         "0.1 dBm"
    MAX-ACCESS    read-only
    STATUS        current
    DESCRIPTION   "OSC Optical Output Power Transmitted"
    ::= { oscOptOptMuxHistorical15minEntry 3 }

oscOptOptMuxHistorical15minHigh OBJECT-TYPE
    SYNTAX        Integer32
    UNITS         "0.1 dBm"
    MAX-ACCESS    read-only
    STATUS        current
    DESCRIPTION   "OSC Optical Output Power Transmitted"
    ::= { oscOptOptMuxHistorical15minEntry 4 }

oscOptOptMuxHistorical15minValidFlag OBJECT-TYPE
    SYNTAX        TruthValue
    MAX-ACCESS    read-only
    STATUS        current
    DESCRIPTION   "Valid Flag"
    ::= { oscOptOptMuxHistorical15minEntry 5 }

oscOptOptMuxHistorical15minTimeStamp OBJECT-TYPE
    SYNTAX        DateAndTime
    MAX-ACCESS    read-only
    STATUS        current
    DESCRIPTION   "Timestamp"
    ::= { oscOptOptMuxHistorical15minEntry 6 }

endOfOscOptOptMuxHistorical15minTable OBJECT-TYPE
    SYNTAX        Integer32
    MAX-ACCESS    read-only
    STATUS        current
    DESCRIPTION   ""
    ::= { pmOptMuxPhysRecord 44 }

oscOptOptMuxHistorical1dayTable OBJECT-TYPE
    SYNTAX        SEQUENCE OF OscOptOptMuxHistorical1dayEntry
    MAX-ACCESS    not-accessible
    STATUS        current
    DESCRIPTION   ""
    ::= { pmOptMuxPhysRecord 45 }

oscOptOptMuxHistorical1dayEntry OBJECT-TYPE
    SYNTAX        OscOptOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscOptOptMuxHistorical1dayNumber
                }
    ::= { oscOptOptMuxHistorical1dayTable 1 }

OscOptOptMuxHistorical1dayEntry ::= SEQUENCE
  {    oscOptOptMuxHistorical1dayNumber Integer32,
    oscOptOptMuxHistorical1dayLow Integer32,
    oscOptOptMuxHistorical1dayMean Integer32,
    oscOptOptMuxHistorical1dayHigh Integer32,
    oscOptOptMuxHistorical1dayValidFlag TruthValue,
    oscOptOptMuxHistorical1dayTimeStamp DateAndTime }

oscOptOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oscOptOptMuxHistorical1dayEntry 1 }

oscOptOptMuxHistorical1dayLow OBJECT-TYPE
    SYNTAX        Integer32
    UNITS         "0.1 dBm"
    MAX-ACCESS    read-only
    STATUS        current
    DESCRIPTION   "OSC Optical Output Power Transmitted"
    ::= { oscOptOptMuxHistorical1dayEntry 2 }

oscOptOptMuxHistorical1dayMean OBJECT-TYPE
    SYNTAX        Integer32
    UNITS         "0.1 dBm"
    MAX-ACCESS    read-only
    STATUS        current
    DESCRIPTION   "OSC Optical Output Power Transmitted"
    ::= { oscOptOptMuxHistorical1dayEntry 3 }

oscOptOptMuxHistorical1dayHigh OBJECT-TYPE
    SYNTAX        Integer32
    UNITS         "0.1 dBm"
    MAX-ACCESS    read-only
    STATUS        current
    DESCRIPTION   "OSC Optical Output Power Transmitted"
    ::= { oscOptOptMuxHistorical1dayEntry 4 }

oscOptOptMuxHistorical1dayValidFlag OBJECT-TYPE
    SYNTAX        TruthValue
    MAX-ACCESS    read-only
    STATUS        current
    DESCRIPTION   "Valid Flag"
    ::= { oscOptOptMuxHistorical1dayEntry 5 }

oscOptOptMuxHistorical1dayTimeStamp OBJECT-TYPE
    SYNTAX        DateAndTime
    MAX-ACCESS    read-only
    STATUS        current
    DESCRIPTION   "Timestamp"
    ::= { oscOptOptMuxHistorical1dayEntry 6 }

endOfOscOptOptMuxHistorical1dayTable OBJECT-TYPE
    SYNTAX        Integer32
    MAX-ACCESS    read-only
    STATUS        current
    DESCRIPTION   ""
    ::= { pmOptMuxPhysRecord 46 }

oscOptOptMuxHistorical1weekTable OBJECT-TYPE
    SYNTAX        SEQUENCE OF OscOptOptMuxHistorical1weekEntry
    MAX-ACCESS    not-accessible
    STATUS        current
    DESCRIPTION   ""
    ::= { pmOptMuxPhysRecord 47 }

oscOptOptMuxHistorical1weekEntry OBJECT-TYPE
    SYNTAX        OscOptOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscOptOptMuxHistorical1weekNumber
                }
    ::= { oscOptOptMuxHistorical1weekTable 1 }

OscOptOptMuxHistorical1weekEntry ::= SEQUENCE
  {    oscOptOptMuxHistorical1weekNumber Integer32,
    oscOptOptMuxHistorical1weekLow Integer32,
    oscOptOptMuxHistorical1weekMean Integer32,
    oscOptOptMuxHistorical1weekHigh Integer32,
    oscOptOptMuxHistorical1weekValidFlag TruthValue,
    oscOptOptMuxHistorical1weekTimeStamp DateAndTime }

oscOptOptMuxHistorical1weekNumber OBJECT-TYPE
    SYNTAX        Integer32 (1..52)
    MAX-ACCESS    not-accessible
    STATUS        current
    DESCRIPTION   "Number 1week"
    ::= { oscOptOptMuxHistorical1weekEntry 1 }

oscOptOptMuxHistorical1weekLow OBJECT-TYPE
    SYNTAX        Integer32
    UNITS         "0.1 dBm"
    MAX-ACCESS    read-only
    STATUS        current
    DESCRIPTION   "OSC Optical Output Power Transmitted"
    ::= { oscOptOptMuxHistorical1weekEntry 2 }

oscOptOptMuxHistorical1weekMean OBJECT-TYPE
    SYNTAX        Integer32
    UNITS         "0.1 dBm"
    MAX-ACCESS    read-only
    STATUS        current
    DESCRIPTION   "OSC Optical Output Power Transmitted"
    ::= { oscOptOptMuxHistorical1weekEntry 3 }

oscOptOptMuxHistorical1weekHigh OBJECT-TYPE
    SYNTAX        Integer32
    UNITS         "0.1 dBm"
    MAX-ACCESS    read-only
    STATUS        current
    DESCRIPTION   "OSC Optical Output Power Transmitted"
    ::= { oscOptOptMuxHistorical1weekEntry 4 }

oscOptOptMuxHistorical1weekValidFlag OBJECT-TYPE
    SYNTAX        TruthValue
    MAX-ACCESS    read-only
    STATUS        current
    DESCRIPTION   "Valid Flag"
    ::= { oscOptOptMuxHistorical1weekEntry 5 }

oscOptOptMuxHistorical1weekTimeStamp OBJECT-TYPE
    SYNTAX        DateAndTime
    MAX-ACCESS    read-only
    STATUS        current
    DESCRIPTION   "Timestamp"
    ::= { oscOptOptMuxHistorical1weekEntry 6 }

endOfOscOptOptMuxHistorical1weekTable OBJECT-TYPE
    SYNTAX        Integer32
    MAX-ACCESS    read-only
    STATUS        current
    DESCRIPTION   ""
    ::= { pmOptMuxPhysRecord 48 }

oscPwrOptMuxHistorical15minTable OBJECT-TYPE
    SYNTAX        SEQUENCE OF OscPwrOptMuxHistorical15minEntry
    MAX-ACCESS    not-accessible
    STATUS        current
    DESCRIPTION   ""
    ::= { pmOptMuxPhysRecord 49 }

oscPwrOptMuxHistorical15minEntry OBJECT-TYPE
    SYNTAX        OscPwrOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscPwrOptMuxHistorical15minNumber
                }
    ::= { oscPwrOptMuxHistorical15minTable 1 }

OscPwrOptMuxHistorical15minEntry ::= SEQUENCE
  {    oscPwrOptMuxHistorical15minNumber Integer32,
    oscPwrOptMuxHistorical15minLow Integer32,
    oscPwrOptMuxHistorical15minMean Integer32,
    oscPwrOptMuxHistorical15minHigh Integer32,
    oscPwrOptMuxHistorical15minValidFlag TruthValue,
    oscPwrOptMuxHistorical15minTimeStamp DateAndTime }

oscPwrOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oscPwrOptMuxHistorical15minEntry 1 }

oscPwrOptMuxHistorical15minLow OBJECT-TYPE
    SYNTAX        Integer32
    UNITS         "0.1 dBm"
    MAX-ACCESS    read-only
    STATUS        current
    DESCRIPTION   "Optical Supervisory Channel Input Power Received Low"
    ::= { oscPwrOptMuxHistorical15minEntry 2 }

oscPwrOptMuxHistorical15minMean OBJECT-TYPE
    SYNTAX        Integer32
    UNITS         "0.1 dBm"
    MAX-ACCESS    read-only
    STATUS        current
    DESCRIPTION   "Optical Supervisory Channel Input Power Received Average"
    ::= { oscPwrOptMuxHistorical15minEntry 3 }

oscPwrOptMuxHistorical15minHigh OBJECT-TYPE
    SYNTAX        Integer32
    UNITS         "0.1 dBm"
    MAX-ACCESS    read-only
    STATUS        current
    DESCRIPTION   "Optical Supervisory Channel Input Power Received High"
    ::= { oscPwrOptMuxHistorical15minEntry 4 }

oscPwrOptMuxHistorical15minValidFlag OBJECT-TYPE
    SYNTAX        TruthValue
    MAX-ACCESS    read-only
    STATUS        current
    DESCRIPTION   "Valid Flag"
    ::= { oscPwrOptMuxHistorical15minEntry 5 }

oscPwrOptMuxHistorical15minTimeStamp OBJECT-TYPE
    SYNTAX        DateAndTime
    MAX-ACCESS    read-only
    STATUS        current
    DESCRIPTION   "Timestamp"
    ::= { oscPwrOptMuxHistorical15minEntry 6 }

endOfOscPwrOptMuxHistorical15minTable OBJECT-TYPE
    SYNTAX        Integer32
    MAX-ACCESS    read-only
    STATUS        current
    DESCRIPTION   ""
    ::= { pmOptMuxPhysRecord 50 }

oscPwrOptMuxHistorical1dayTable OBJECT-TYPE
    SYNTAX        SEQUENCE OF OscPwrOptMuxHistorical1dayEntry
    MAX-ACCESS    not-accessible
    STATUS        current
    DESCRIPTION   ""
    ::= { pmOptMuxPhysRecord 51 }

oscPwrOptMuxHistorical1dayEntry OBJECT-TYPE
    SYNTAX        OscPwrOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscPwrOptMuxHistorical1dayNumber
                }
    ::= { oscPwrOptMuxHistorical1dayTable 1 }

OscPwrOptMuxHistorical1dayEntry ::= SEQUENCE
  {    oscPwrOptMuxHistorical1dayNumber Integer32,
    oscPwrOptMuxHistorical1dayLow Integer32,
    oscPwrOptMuxHistorical1dayMean Integer32,
    oscPwrOptMuxHistorical1dayHigh Integer32,
    oscPwrOptMuxHistorical1dayValidFlag TruthValue,
    oscPwrOptMuxHistorical1dayTimeStamp DateAndTime }

oscPwrOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oscPwrOptMuxHistorical1dayEntry 1 }

oscPwrOptMuxHistorical1dayLow OBJECT-TYPE
    SYNTAX        Integer32
    UNITS         "0.1 dBm"
    MAX-ACCESS    read-only
    STATUS        current
    DESCRIPTION   "Optical Supervisory Channel Input Power Received Low"
    ::= { oscPwrOptMuxHistorical1dayEntry 2 }

oscPwrOptMuxHistorical1dayMean OBJECT-TYPE
    SYNTAX        Integer32
    UNITS         "0.1 dBm"
    MAX-ACCESS    read-only
    STATUS        current
    DESCRIPTION   "Optical Supervisory Channel Input Power Received Average"
    ::= { oscPwrOptMuxHistorical1dayEntry 3 }

oscPwrOptMuxHistorical1dayHigh OBJECT-TYPE
    SYNTAX        Integer32
    UNITS         "0.1 dBm"
    MAX-ACCESS    read-only
    STATUS        current
    DESCRIPTION   "Optical Supervisory Channel Input Power Received High"
    ::= { oscPwrOptMuxHistorical1dayEntry 4 }

oscPwrOptMuxHistorical1dayValidFlag OBJECT-TYPE
    SYNTAX        TruthValue
    MAX-ACCESS    read-only
    STATUS        current
    DESCRIPTION   "Valid Flag"
    ::= { oscPwrOptMuxHistorical1dayEntry 5 }

oscPwrOptMuxHistorical1dayTimeStamp OBJECT-TYPE
    SYNTAX        DateAndTime
    MAX-ACCESS    read-only
    STATUS        current
    DESCRIPTION   "Timestamp"
    ::= { oscPwrOptMuxHistorical1dayEntry 6 }

endOfOscPwrOptMuxHistorical1dayTable OBJECT-TYPE
    SYNTAX        Integer32
    MAX-ACCESS    read-only
    STATUS        current
    DESCRIPTION   ""
    ::= { pmOptMuxPhysRecord 52 }

oscPwrOptMuxHistorical1weekTable OBJECT-TYPE
    SYNTAX        SEQUENCE OF OscPwrOptMuxHistorical1weekEntry
    MAX-ACCESS    not-accessible
    STATUS        current
    DESCRIPTION   ""
    ::= { pmOptMuxPhysRecord 53 }

oscPwrOptMuxHistorical1weekEntry OBJECT-TYPE
    SYNTAX        OscPwrOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oscPwrOptMuxHistorical1weekNumber
                }
    ::= { oscPwrOptMuxHistorical1weekTable 1 }

OscPwrOptMuxHistorical1weekEntry ::= SEQUENCE
  {    oscPwrOptMuxHistorical1weekNumber Integer32,
    oscPwrOptMuxHistorical1weekLow Integer32,
    oscPwrOptMuxHistorical1weekMean Integer32,
    oscPwrOptMuxHistorical1weekHigh Integer32,
    oscPwrOptMuxHistorical1weekValidFlag TruthValue,
    oscPwrOptMuxHistorical1weekTimeStamp DateAndTime }

oscPwrOptMuxHistorical1weekNumber OBJECT-TYPE
    SYNTAX        Integer32 (1..52)
    MAX-ACCESS    not-accessible
    STATUS        current
    DESCRIPTION   "Number 1week"
    ::= { oscPwrOptMuxHistorical1weekEntry 1 }

oscPwrOptMuxHistorical1weekLow OBJECT-TYPE
    SYNTAX        Integer32
    UNITS         "0.1 dBm"
    MAX-ACCESS    read-only
    STATUS        current
    DESCRIPTION   "Optical Supervisory Channel Input Power Received Low"
    ::= { oscPwrOptMuxHistorical1weekEntry 2 }

oscPwrOptMuxHistorical1weekMean OBJECT-TYPE
    SYNTAX        Integer32
    UNITS         "0.1 dBm"
    MAX-ACCESS    read-only
    STATUS        current
    DESCRIPTION   "Optical Supervisory Channel Input Power Received Average"
    ::= { oscPwrOptMuxHistorical1weekEntry 3 }

oscPwrOptMuxHistorical1weekHigh OBJECT-TYPE
    SYNTAX        Integer32
    UNITS         "0.1 dBm"
    MAX-ACCESS    read-only
    STATUS        current
    DESCRIPTION   "Optical Supervisory Channel Input Power Received High"
    ::= { oscPwrOptMuxHistorical1weekEntry 4 }

oscPwrOptMuxHistorical1weekValidFlag OBJECT-TYPE
    SYNTAX        TruthValue
    MAX-ACCESS    read-only
    STATUS        current
    DESCRIPTION   "Valid Flag"
    ::= { oscPwrOptMuxHistorical1weekEntry 5 }

oscPwrOptMuxHistorical1weekTimeStamp OBJECT-TYPE
    SYNTAX        DateAndTime
    MAX-ACCESS    read-only
    STATUS        current
    DESCRIPTION   "Timestamp"
    ::= { oscPwrOptMuxHistorical1weekEntry 6 }

endOfOscPwrOptMuxHistorical1weekTable OBJECT-TYPE
    SYNTAX        Integer32
    MAX-ACCESS    read-only
    STATUS        current
    DESCRIPTION   ""
    ::= { pmOptMuxPhysRecord 54 }

optOptMuxHistorical15minTable OBJECT-TYPE
    SYNTAX        SEQUENCE OF OptOptMuxHistorical15minEntry
    MAX-ACCESS    not-accessible
    STATUS        current
    DESCRIPTION   ""
    ::= { pmOptMuxPhysRecord 55 }

optOptMuxHistorical15minEntry OBJECT-TYPE
    SYNTAX        OptOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  optOptMuxHistorical15minNumber
                }
    ::= { optOptMuxHistorical15minTable 1 }

OptOptMuxHistorical15minEntry ::= SEQUENCE
  {    optOptMuxHistorical15minNumber Integer32,
    optOptMuxHistorical15minLow Integer32,
    optOptMuxHistorical15minMean Integer32,
    optOptMuxHistorical15minHigh Integer32,
    optOptMuxHistorical15minValidFlag TruthValue,
    optOptMuxHistorical15minTimeStamp DateAndTime }

optOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { optOptMuxHistorical15minEntry 1 }

optOptMuxHistorical15minLow OBJECT-TYPE
    SYNTAX        Integer32
    UNITS         "0.1 dBm"
    MAX-ACCESS    read-only
    STATUS        current
    DESCRIPTION   "Optical Output Power Transmitted"
    ::= { optOptMuxHistorical15minEntry 2 }

optOptMuxHistorical15minMean OBJECT-TYPE
    SYNTAX        Integer32
    UNITS         "0.1 dBm"
    MAX-ACCESS    read-only
    STATUS        current
    DESCRIPTION   "Optical Output Power Transmitted"
    ::= { optOptMuxHistorical15minEntry 3 }

optOptMuxHistorical15minHigh OBJECT-TYPE
    SYNTAX        Integer32
    UNITS         "0.1 dBm"
    MAX-ACCESS    read-only
    STATUS        current
    DESCRIPTION   "Optical Output Power Transmitted"
    ::= { optOptMuxHistorical15minEntry 4 }

optOptMuxHistorical15minValidFlag OBJECT-TYPE
    SYNTAX        TruthValue
    MAX-ACCESS    read-only
    STATUS        current
    DESCRIPTION   "Valid Flag"
    ::= { optOptMuxHistorical15minEntry 5 }

optOptMuxHistorical15minTimeStamp OBJECT-TYPE
    SYNTAX        DateAndTime
    MAX-ACCESS    read-only
    STATUS        current
    DESCRIPTION   "Timestamp"
    ::= { optOptMuxHistorical15minEntry 6 }

endOfOptOptMuxHistorical15minTable OBJECT-TYPE
    SYNTAX        Integer32
    MAX-ACCESS    read-only
    STATUS        current
    DESCRIPTION   ""
    ::= { pmOptMuxPhysRecord 56 }

optOptMuxHistorical1dayTable OBJECT-TYPE
    SYNTAX        SEQUENCE OF OptOptMuxHistorical1dayEntry
    MAX-ACCESS    not-accessible
    STATUS        current
    DESCRIPTION   ""
    ::= { pmOptMuxPhysRecord 57 }

optOptMuxHistorical1dayEntry OBJECT-TYPE
    SYNTAX        OptOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  optOptMuxHistorical1dayNumber
                }
    ::= { optOptMuxHistorical1dayTable 1 }

OptOptMuxHistorical1dayEntry ::= SEQUENCE
  {    optOptMuxHistorical1dayNumber Integer32,
    optOptMuxHistorical1dayLow Integer32,
    optOptMuxHistorical1dayMean Integer32,
    optOptMuxHistorical1dayHigh Integer32,
    optOptMuxHistorical1dayValidFlag TruthValue,
    optOptMuxHistorical1dayTimeStamp DateAndTime }

optOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { optOptMuxHistorical1dayEntry 1 }

optOptMuxHistorical1dayLow OBJECT-TYPE
    SYNTAX        Integer32
    UNITS         "0.1 dBm"
    MAX-ACCESS    read-only
    STATUS        current
    DESCRIPTION   "Optical Output Power Transmitted"
    ::= { optOptMuxHistorical1dayEntry 2 }

optOptMuxHistorical1dayMean OBJECT-TYPE
    SYNTAX        Integer32
    UNITS         "0.1 dBm"
    MAX-ACCESS    read-only
    STATUS        current
    DESCRIPTION   "Optical Output Power Transmitted"
    ::= { optOptMuxHistorical1dayEntry 3 }

optOptMuxHistorical1dayHigh OBJECT-TYPE
    SYNTAX        Integer32
    UNITS         "0.1 dBm"
    MAX-ACCESS    read-only
    STATUS        current
    DESCRIPTION   "Optical Output Power Transmitted"
    ::= { optOptMuxHistorical1dayEntry 4 }

optOptMuxHistorical1dayValidFlag OBJECT-TYPE
    SYNTAX        TruthValue
    MAX-ACCESS    read-only
    STATUS        current
    DESCRIPTION   "Valid Flag"
    ::= { optOptMuxHistorical1dayEntry 5 }

optOptMuxHistorical1dayTimeStamp OBJECT-TYPE
    SYNTAX        DateAndTime
    MAX-ACCESS    read-only
    STATUS        current
    DESCRIPTION   "Timestamp"
    ::= { optOptMuxHistorical1dayEntry 6 }

endOfOptOptMuxHistorical1dayTable OBJECT-TYPE
    SYNTAX        Integer32
    MAX-ACCESS    read-only
    STATUS        current
    DESCRIPTION   ""
    ::= { pmOptMuxPhysRecord 58 }

optOptMuxHistorical1weekTable OBJECT-TYPE
    SYNTAX        SEQUENCE OF OptOptMuxHistorical1weekEntry
    MAX-ACCESS    not-accessible
    STATUS        current
    DESCRIPTION   ""
    ::= { pmOptMuxPhysRecord 59 }

optOptMuxHistorical1weekEntry OBJECT-TYPE
    SYNTAX        OptOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  optOptMuxHistorical1weekNumber
                }
    ::= { optOptMuxHistorical1weekTable 1 }

OptOptMuxHistorical1weekEntry ::= SEQUENCE
  {    optOptMuxHistorical1weekNumber Integer32,
    optOptMuxHistorical1weekLow Integer32,
    optOptMuxHistorical1weekMean Integer32,
    optOptMuxHistorical1weekHigh Integer32,
    optOptMuxHistorical1weekValidFlag TruthValue,
    optOptMuxHistorical1weekTimeStamp DateAndTime }

optOptMuxHistorical1weekNumber OBJECT-TYPE
    SYNTAX        Integer32 (1..52)
    MAX-ACCESS    not-accessible
    STATUS        current
    DESCRIPTION   "Number 1week"
    ::= { optOptMuxHistorical1weekEntry 1 }

optOptMuxHistorical1weekLow OBJECT-TYPE
    SYNTAX        Integer32
    UNITS         "0.1 dBm"
    MAX-ACCESS    read-only
    STATUS        current
    DESCRIPTION   "Optical Output Power Transmitted"
    ::= { optOptMuxHistorical1weekEntry 2 }

optOptMuxHistorical1weekMean OBJECT-TYPE
    SYNTAX        Integer32
    UNITS         "0.1 dBm"
    MAX-ACCESS    read-only
    STATUS        current
    DESCRIPTION   "Optical Output Power Transmitted"
    ::= { optOptMuxHistorical1weekEntry 3 }

optOptMuxHistorical1weekHigh OBJECT-TYPE
    SYNTAX        Integer32
    UNITS         "0.1 dBm"
    MAX-ACCESS    read-only
    STATUS        current
    DESCRIPTION   "Optical Output Power Transmitted"
    ::= { optOptMuxHistorical1weekEntry 4 }

optOptMuxHistorical1weekValidFlag OBJECT-TYPE
    SYNTAX        TruthValue
    MAX-ACCESS    read-only
    STATUS        current
    DESCRIPTION   "Valid Flag"
    ::= { optOptMuxHistorical1weekEntry 5 }

optOptMuxHistorical1weekTimeStamp OBJECT-TYPE
    SYNTAX        DateAndTime
    MAX-ACCESS    read-only
    STATUS        current
    DESCRIPTION   "Timestamp"
    ::= { optOptMuxHistorical1weekEntry 6 }

endOfOptOptMuxHistorical1weekTable OBJECT-TYPE
    SYNTAX        Integer32
    MAX-ACCESS    read-only
    STATUS        current
    DESCRIPTION   ""
    ::= { pmOptMuxPhysRecord 60 }

oprOptMuxHistorical15minTable OBJECT-TYPE
    SYNTAX        SEQUENCE OF OprOptMuxHistorical15minEntry
    MAX-ACCESS    not-accessible
    STATUS        current
    DESCRIPTION   ""
    ::= { pmOptMuxPhysRecord 61 }

oprOptMuxHistorical15minEntry OBJECT-TYPE
    SYNTAX        OprOptMuxHistorical15minEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oprOptMuxHistorical15minNumber
                }
    ::= { oprOptMuxHistorical15minTable 1 }

OprOptMuxHistorical15minEntry ::= SEQUENCE
  {    oprOptMuxHistorical15minNumber Integer32,
    oprOptMuxHistorical15minLow Integer32,
    oprOptMuxHistorical15minMean Integer32,
    oprOptMuxHistorical15minHigh Integer32,
    oprOptMuxHistorical15minValidFlag TruthValue,
    oprOptMuxHistorical15minTimeStamp DateAndTime }

oprOptMuxHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { oprOptMuxHistorical15minEntry 1 }

oprOptMuxHistorical15minLow OBJECT-TYPE
    SYNTAX        Integer32
    UNITS         "0.1 dBm"
    MAX-ACCESS    read-only
    STATUS        current
    DESCRIPTION   "Optical Input Power Received"
    ::= { oprOptMuxHistorical15minEntry 2 }

oprOptMuxHistorical15minMean OBJECT-TYPE
    SYNTAX        Integer32
    UNITS         "0.1 dBm"
    MAX-ACCESS    read-only
    STATUS        current
    DESCRIPTION   "Optical Input Power Received"
    ::= { oprOptMuxHistorical15minEntry 3 }

oprOptMuxHistorical15minHigh OBJECT-TYPE
    SYNTAX        Integer32
    UNITS         "0.1 dBm"
    MAX-ACCESS    read-only
    STATUS        current
    DESCRIPTION   "Optical Input Power Received"
    ::= { oprOptMuxHistorical15minEntry 4 }

oprOptMuxHistorical15minValidFlag OBJECT-TYPE
    SYNTAX        TruthValue
    MAX-ACCESS    read-only
    STATUS        current
    DESCRIPTION   "Valid Flag"
    ::= { oprOptMuxHistorical15minEntry 5 }

oprOptMuxHistorical15minTimeStamp OBJECT-TYPE
    SYNTAX        DateAndTime
    MAX-ACCESS    read-only
    STATUS        current
    DESCRIPTION   "Timestamp"
    ::= { oprOptMuxHistorical15minEntry 6 }

endOfOprOptMuxHistorical15minTable OBJECT-TYPE
    SYNTAX        Integer32
    MAX-ACCESS    read-only
    STATUS        current
    DESCRIPTION   ""
    ::= { pmOptMuxPhysRecord 62 }

oprOptMuxHistorical1dayTable OBJECT-TYPE
    SYNTAX        SEQUENCE OF OprOptMuxHistorical1dayEntry
    MAX-ACCESS    not-accessible
    STATUS        current
    DESCRIPTION   ""
    ::= { pmOptMuxPhysRecord 63 }

oprOptMuxHistorical1dayEntry OBJECT-TYPE
    SYNTAX        OprOptMuxHistorical1dayEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oprOptMuxHistorical1dayNumber
                }
    ::= { oprOptMuxHistorical1dayTable 1 }

OprOptMuxHistorical1dayEntry ::= SEQUENCE
  {    oprOptMuxHistorical1dayNumber Integer32,
    oprOptMuxHistorical1dayLow Integer32,
    oprOptMuxHistorical1dayMean Integer32,
    oprOptMuxHistorical1dayHigh Integer32,
    oprOptMuxHistorical1dayValidFlag TruthValue,
    oprOptMuxHistorical1dayTimeStamp DateAndTime }

oprOptMuxHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { oprOptMuxHistorical1dayEntry 1 }

oprOptMuxHistorical1dayLow OBJECT-TYPE
    SYNTAX        Integer32
    UNITS         "0.1 dBm"
    MAX-ACCESS    read-only
    STATUS        current
    DESCRIPTION   "Optical Input Power Received"
    ::= { oprOptMuxHistorical1dayEntry 2 }

oprOptMuxHistorical1dayMean OBJECT-TYPE
    SYNTAX        Integer32
    UNITS         "0.1 dBm"
    MAX-ACCESS    read-only
    STATUS        current
    DESCRIPTION   "Optical Input Power Received"
    ::= { oprOptMuxHistorical1dayEntry 3 }

oprOptMuxHistorical1dayHigh OBJECT-TYPE
    SYNTAX        Integer32
    UNITS         "0.1 dBm"
    MAX-ACCESS    read-only
    STATUS        current
    DESCRIPTION   "Optical Input Power Received"
    ::= { oprOptMuxHistorical1dayEntry 4 }

oprOptMuxHistorical1dayValidFlag OBJECT-TYPE
    SYNTAX        TruthValue
    MAX-ACCESS    read-only
    STATUS        current
    DESCRIPTION   "Valid Flag"
    ::= { oprOptMuxHistorical1dayEntry 5 }

oprOptMuxHistorical1dayTimeStamp OBJECT-TYPE
    SYNTAX        DateAndTime
    MAX-ACCESS    read-only
    STATUS        current
    DESCRIPTION   "Timestamp"
    ::= { oprOptMuxHistorical1dayEntry 6 }

endOfOprOptMuxHistorical1dayTable OBJECT-TYPE
    SYNTAX        Integer32
    MAX-ACCESS    read-only
    STATUS        current
    DESCRIPTION   ""
    ::= { pmOptMuxPhysRecord 64 }

oprOptMuxHistorical1weekTable OBJECT-TYPE
    SYNTAX        SEQUENCE OF OprOptMuxHistorical1weekEntry
    MAX-ACCESS    not-accessible
    STATUS        current
    DESCRIPTION   ""
    ::= { pmOptMuxPhysRecord 65 }

oprOptMuxHistorical1weekEntry OBJECT-TYPE
    SYNTAX        OprOptMuxHistorical1weekEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName,
                  oprOptMuxHistorical1weekNumber
                }
    ::= { oprOptMuxHistorical1weekTable 1 }

OprOptMuxHistorical1weekEntry ::= SEQUENCE
  {    oprOptMuxHistorical1weekNumber Integer32,
    oprOptMuxHistorical1weekLow Integer32,
    oprOptMuxHistorical1weekMean Integer32,
    oprOptMuxHistorical1weekHigh Integer32,
    oprOptMuxHistorical1weekValidFlag TruthValue,
    oprOptMuxHistorical1weekTimeStamp DateAndTime }

oprOptMuxHistorical1weekNumber OBJECT-TYPE
    SYNTAX        Integer32 (1..52)
    MAX-ACCESS    not-accessible
    STATUS        current
    DESCRIPTION   "Number 1week"
    ::= { oprOptMuxHistorical1weekEntry 1 }

oprOptMuxHistorical1weekLow OBJECT-TYPE
    SYNTAX        Integer32
    UNITS         "0.1 dBm"
    MAX-ACCESS    read-only
    STATUS        current
    DESCRIPTION   "Optical Input Power Received"
    ::= { oprOptMuxHistorical1weekEntry 2 }

oprOptMuxHistorical1weekMean OBJECT-TYPE
    SYNTAX        Integer32
    UNITS         "0.1 dBm"
    MAX-ACCESS    read-only
    STATUS        current
    DESCRIPTION   "Optical Input Power Received"
    ::= { oprOptMuxHistorical1weekEntry 3 }

oprOptMuxHistorical1weekHigh OBJECT-TYPE
    SYNTAX        Integer32
    UNITS         "0.1 dBm"
    MAX-ACCESS    read-only
    STATUS        current
    DESCRIPTION   "Optical Input Power Received"
    ::= { oprOptMuxHistorical1weekEntry 4 }

oprOptMuxHistorical1weekValidFlag OBJECT-TYPE
    SYNTAX        TruthValue
    MAX-ACCESS    read-only
    STATUS        current
    DESCRIPTION   "Valid Flag"
    ::= { oprOptMuxHistorical1weekEntry 5 }

oprOptMuxHistorical1weekTimeStamp OBJECT-TYPE
    SYNTAX        DateAndTime
    MAX-ACCESS    read-only
    STATUS        current
    DESCRIPTION   "Timestamp"
    ::= { oprOptMuxHistorical1weekEntry 6 }

endOfOprOptMuxHistorical1weekTable OBJECT-TYPE
    SYNTAX        Integer32
    MAX-ACCESS    read-only
    STATUS        current
    DESCRIPTION   ""
    ::= { pmOptMuxPhysRecord 66 }

endOfPmOptMuxPhysRecord OBJECT-TYPE
    SYNTAX        Integer32
    MAX-ACCESS    read-only
    STATUS        current
    DESCRIPTION   ""
    ::= { pmOptMuxPhysRecord 10000 }

frRcv2ShelfConnectionCurrent15minTable OBJECT-TYPE
    SYNTAX        SEQUENCE OF FrRcv2ShelfConnectionCurrent15minEntry
    MAX-ACCESS    not-accessible
    STATUS        current
    DESCRIPTION   ""
    ::= { pmShelfConnectionDataRecord 1 }

frRcv2ShelfConnectionCurrent15minEntry OBJECT-TYPE
    SYNTAX        FrRcv2ShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { frRcv2ShelfConnectionCurrent15minTable 1 }

FrRcv2ShelfConnectionCurrent15minEntry ::= SEQUENCE
  {    frRcv2ShelfConnectionCurrent15minGoodFrames Counter64String,
    frRcv2ShelfConnectionCurrent15minPauseFrames Counter64String,
    frRcv2ShelfConnectionCurrent15minCrcFrames Counter64String,
    frRcv2ShelfConnectionCurrent15minBytes Counter64String,
    frRcv2ShelfConnectionCurrent15minElapsedTime Integer32 }

frRcv2ShelfConnectionCurrent15minGoodFrames OBJECT-TYPE
    SYNTAX        Counter64String
    MAX-ACCESS    read-only
    STATUS        current
    DESCRIPTION   "Frames Received"
    ::= { frRcv2ShelfConnectionCurrent15minEntry 1 }

frRcv2ShelfConnectionCurrent15minPauseFrames OBJECT-TYPE
    SYNTAX        Counter64String
    MAX-ACCESS    read-only
    STATUS        current
    DESCRIPTION   "Pause Frames Received"
    ::= { frRcv2ShelfConnectionCurrent15minEntry 2 }

frRcv2ShelfConnectionCurrent15minCrcFrames OBJECT-TYPE
    SYNTAX        Counter64String
    MAX-ACCESS    read-only
    STATUS        current
    DESCRIPTION   "Received CRC Errors"
    ::= { frRcv2ShelfConnectionCurrent15minEntry 3 }

frRcv2ShelfConnectionCurrent15minBytes OBJECT-TYPE
    SYNTAX        Counter64String
    MAX-ACCESS    read-only
    STATUS        current
    DESCRIPTION   "Bytes Received"
    ::= { frRcv2ShelfConnectionCurrent15minEntry 4 }

frRcv2ShelfConnectionCurrent15minElapsedTime OBJECT-TYPE
    SYNTAX        Integer32 (0..9000)
    MAX-ACCESS    read-only
    STATUS        current
    DESCRIPTION   "Elapsed 15Min"
    ::= { frRcv2ShelfConnectionCurrent15minEntry 5 }

endOfFrRcv2ShelfConnectionCurrent15minTable OBJECT-TYPE
    SYNTAX        Integer32
    MAX-ACCESS    read-only
    STATUS        current
    DESCRIPTION   ""
    ::= { pmShelfConnectionDataRecord 2 }

frRcv2ShelfConnectionCurrent1dayTable OBJECT-TYPE
    SYNTAX        SEQUENCE OF FrRcv2ShelfConnectionCurrent1dayEntry
    MAX-ACCESS    not-accessible
    STATUS        current
    DESCRIPTION   ""
    ::= { pmShelfConnectionDataRecord 3 }

frRcv2ShelfConnectionCurrent1dayEntry OBJECT-TYPE
    SYNTAX        FrRcv2ShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { frRcv2ShelfConnectionCurrent1dayTable 1 }

FrRcv2ShelfConnectionCurrent1dayEntry ::= SEQUENCE
  {    frRcv2ShelfConnectionCurrent1dayGoodFrames Counter64String,
    frRcv2ShelfConnectionCurrent1dayPauseFrames Counter64String,
    frRcv2ShelfConnectionCurrent1dayCrcFrames Counter64String,
    frRcv2ShelfConnectionCurrent1dayBytes Counter64String,
    frRcv2ShelfConnectionCurrent1dayElapsedTime Integer32 }

frRcv2ShelfConnectionCurrent1dayGoodFrames OBJECT-TYPE
    SYNTAX        Counter64String
    MAX-ACCESS    read-only
    STATUS        current
    DESCRIPTION   "Frames Received"
    ::= { frRcv2ShelfConnectionCurrent1dayEntry 1 }

frRcv2ShelfConnectionCurrent1dayPauseFrames OBJECT-TYPE
    SYNTAX        Counter64String
    MAX-ACCESS    read-only
    STATUS        current
    DESCRIPTION   "Pause Frames Received"
    ::= { frRcv2ShelfConnectionCurrent1dayEntry 2 }

frRcv2ShelfConnectionCurrent1dayCrcFrames OBJECT-TYPE
    SYNTAX        Counter64String
    MAX-ACCESS    read-only
    STATUS        current
    DESCRIPTION   "Received CRC Errors"
    ::= { frRcv2ShelfConnectionCurrent1dayEntry 3 }

frRcv2ShelfConnectionCurrent1dayBytes OBJECT-TYPE
    SYNTAX        Counter64String
    MAX-ACCESS    read-only
    STATUS        current
    DESCRIPTION   "Bytes Received"
    ::= { frRcv2ShelfConnectionCurrent1dayEntry 4 }

frRcv2ShelfConnectionCurrent1dayElapsedTime OBJECT-TYPE
    SYNTAX        Integer32 (0..86400)
    MAX-ACCESS    read-only
    STATUS        current
    DESCRIPTION   "Elapsed 1Day"
    ::= { frRcv2ShelfConnectionCurrent1dayEntry 5 }

endOfFrRcv2ShelfConnectionCurrent1dayTable OBJECT-TYPE
    SYNTAX        Integer32
    MAX-ACCESS    read-only
    STATUS        current
    DESCRIPTION   ""
    ::= { pmShelfConnectionDataRecord 4 }

frRcv2ShelfConnectionHistorical15minTable OBJECT-TYPE
    SYNTAX        SEQUENCE OF FrRcv2ShelfConnectionHistorical15minEntry
    MAX-ACCESS    not-accessible
    STATUS        current
    DESCRIPTION   ""
    ::= { pmShelfConnectionDataRecord 5 }

frRcv2ShelfConnectionHistorical15minEntry OBJECT-TYPE
    SYNTAX        FrRcv2ShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  frRcv2ShelfConnectionHistorical15minNumber
                }
    ::= { frRcv2ShelfConnectionHistorical15minTable 1 }

FrRcv2ShelfConnectionHistorical15minEntry ::= SEQUENCE
  {    frRcv2ShelfConnectionHistorical15minNumber Integer32,
    frRcv2ShelfConnectionHistorical15minGoodFrames Counter64String,
    frRcv2ShelfConnectionHistorical15minPauseFrames Counter64String,
    frRcv2ShelfConnectionHistorical15minCrcFrames Counter64String,
    frRcv2ShelfConnectionHistorical15minBytes Counter64String,
    frRcv2ShelfConnectionHistorical15minValidFlag TruthValue,
    frRcv2ShelfConnectionHistorical15minTimeStamp DateAndTime }

frRcv2ShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { frRcv2ShelfConnectionHistorical15minEntry 1 }

frRcv2ShelfConnectionHistorical15minGoodFrames OBJECT-TYPE
    SYNTAX        Counter64String
    MAX-ACCESS    read-only
    STATUS        current
    DESCRIPTION   "Frames Received"
    ::= { frRcv2ShelfConnectionHistorical15minEntry 2 }

frRcv2ShelfConnectionHistorical15minPauseFrames OBJECT-TYPE
    SYNTAX        Counter64String
    MAX-ACCESS    read-only
    STATUS        current
    DESCRIPTION   "Pause Frames Received"
    ::= { frRcv2ShelfConnectionHistorical15minEntry 3 }

frRcv2ShelfConnectionHistorical15minCrcFrames OBJECT-TYPE
    SYNTAX        Counter64String
    MAX-ACCESS    read-only
    STATUS        current
    DESCRIPTION   "Received CRC Errors"
    ::= { frRcv2ShelfConnectionHistorical15minEntry 4 }

frRcv2ShelfConnectionHistorical15minBytes OBJECT-TYPE
    SYNTAX        Counter64String
    MAX-ACCESS    read-only
    STATUS        current
    DESCRIPTION   "Bytes Received"
    ::= { frRcv2ShelfConnectionHistorical15minEntry 5 }

frRcv2ShelfConnectionHistorical15minValidFlag OBJECT-TYPE
    SYNTAX        TruthValue
    MAX-ACCESS    read-only
    STATUS        current
    DESCRIPTION   "Valid Flag"
    ::= { frRcv2ShelfConnectionHistorical15minEntry 6 }

frRcv2ShelfConnectionHistorical15minTimeStamp OBJECT-TYPE
    SYNTAX        DateAndTime
    MAX-ACCESS    read-only
    STATUS        current
    DESCRIPTION   "Timestamp"
    ::= { frRcv2ShelfConnectionHistorical15minEntry 7 }

endOfFrRcv2ShelfConnectionHistorical15minTable OBJECT-TYPE
    SYNTAX        Integer32
    MAX-ACCESS    read-only
    STATUS        current
    DESCRIPTION   ""
    ::= { pmShelfConnectionDataRecord 6 }

frRcv2ShelfConnectionHistorical1dayTable OBJECT-TYPE
    SYNTAX        SEQUENCE OF FrRcv2ShelfConnectionHistorical1dayEntry
    MAX-ACCESS    not-accessible
    STATUS        current
    DESCRIPTION   ""
    ::= { pmShelfConnectionDataRecord 7 }

frRcv2ShelfConnectionHistorical1dayEntry OBJECT-TYPE
    SYNTAX        FrRcv2ShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  frRcv2ShelfConnectionHistorical1dayNumber
                }
    ::= { frRcv2ShelfConnectionHistorical1dayTable 1 }

FrRcv2ShelfConnectionHistorical1dayEntry ::= SEQUENCE
  {    frRcv2ShelfConnectionHistorical1dayNumber Integer32,
    frRcv2ShelfConnectionHistorical1dayGoodFrames Counter64String,
    frRcv2ShelfConnectionHistorical1dayPauseFrames Counter64String,
    frRcv2ShelfConnectionHistorical1dayCrcFrames Counter64String,
    frRcv2ShelfConnectionHistorical1dayBytes Counter64String,
    frRcv2ShelfConnectionHistorical1dayValidFlag TruthValue,
    frRcv2ShelfConnectionHistorical1dayTimeStamp DateAndTime }

frRcv2ShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { frRcv2ShelfConnectionHistorical1dayEntry 1 }

frRcv2ShelfConnectionHistorical1dayGoodFrames OBJECT-TYPE
    SYNTAX        Counter64String
    MAX-ACCESS    read-only
    STATUS        current
    DESCRIPTION   "Frames Received"
    ::= { frRcv2ShelfConnectionHistorical1dayEntry 2 }

frRcv2ShelfConnectionHistorical1dayPauseFrames OBJECT-TYPE
    SYNTAX        Counter64String
    MAX-ACCESS    read-only
    STATUS        current
    DESCRIPTION   "Pause Frames Received"
    ::= { frRcv2ShelfConnectionHistorical1dayEntry 3 }

frRcv2ShelfConnectionHistorical1dayCrcFrames OBJECT-TYPE
    SYNTAX        Counter64String
    MAX-ACCESS    read-only
    STATUS        current
    DESCRIPTION   "Received CRC Errors"
    ::= { frRcv2ShelfConnectionHistorical1dayEntry 4 }

frRcv2ShelfConnectionHistorical1dayBytes OBJECT-TYPE
    SYNTAX        Counter64String
    MAX-ACCESS    read-only
    STATUS        current
    DESCRIPTION   "Bytes Received"
    ::= { frRcv2ShelfConnectionHistorical1dayEntry 5 }

frRcv2ShelfConnectionHistorical1dayValidFlag OBJECT-TYPE
    SYNTAX        TruthValue
    MAX-ACCESS    read-only
    STATUS        current
    DESCRIPTION   "Valid Flag"
    ::= { frRcv2ShelfConnectionHistorical1dayEntry 6 }

frRcv2ShelfConnectionHistorical1dayTimeStamp OBJECT-TYPE
    SYNTAX        DateAndTime
    MAX-ACCESS    read-only
    STATUS        current
    DESCRIPTION   "Timestamp"
    ::= { frRcv2ShelfConnectionHistorical1dayEntry 7 }

endOfFrRcv2ShelfConnectionHistorical1dayTable OBJECT-TYPE
    SYNTAX        Integer32
    MAX-ACCESS    read-only
    STATUS        current
    DESCRIPTION   ""
    ::= { pmShelfConnectionDataRecord 8 }

macRxShelfConnectionCurrent15minTable OBJECT-TYPE
    SYNTAX        SEQUENCE OF MacRxShelfConnectionCurrent15minEntry
    MAX-ACCESS    not-accessible
    STATUS        current
    DESCRIPTION   ""
    ::= { pmShelfConnectionDataRecord 9 }

macRxShelfConnectionCurrent15minEntry OBJECT-TYPE
    SYNTAX        MacRxShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macRxShelfConnectionCurrent15minTable 1 }

MacRxShelfConnectionCurrent15minEntry ::= SEQUENCE
  {    macRxShelfConnectionCurrent15minGoodFrames Counter64String,
    macRxShelfConnectionCurrent15minOctRcv Counter64String,
    macRxShelfConnectionCurrent15minBroadcastFramesRcv Counter64String,
    macRxShelfConnectionCurrent15minMulticastFramesRcv Counter64String,
    macRxShelfConnectionCurrent15minElapsedTime Integer32 }

macRxShelfConnectionCurrent15minGoodFrames OBJECT-TYPE
    SYNTAX        Counter64String
    MAX-ACCESS    read-only
    STATUS        current
    DESCRIPTION   "Frames Received"
    ::= { macRxShelfConnectionCurrent15minEntry 1 }

macRxShelfConnectionCurrent15minOctRcv OBJECT-TYPE
    SYNTAX        Counter64String
    MAX-ACCESS    read-only
    STATUS        current
    DESCRIPTION   "Bytes Received"
    ::= { macRxShelfConnectionCurrent15minEntry 2 }

macRxShelfConnectionCurrent15minBroadcastFramesRcv OBJECT-TYPE
    SYNTAX        Counter64String
    MAX-ACCESS    read-only
    STATUS        current
    DESCRIPTION   "Broadcast Frames Received"
    ::= { macRxShelfConnectionCurrent15minEntry 3 }

macRxShelfConnectionCurrent15minMulticastFramesRcv OBJECT-TYPE
    SYNTAX        Counter64String
    MAX-ACCESS    read-only
    STATUS        current
    DESCRIPTION   "Multicast Frames Received"
    ::= { macRxShelfConnectionCurrent15minEntry 4 }

macRxShelfConnectionCurrent15minElapsedTime OBJECT-TYPE
    SYNTAX        Integer32 (0..9000)
    MAX-ACCESS    read-only
    STATUS        current
    DESCRIPTION   "Elapsed 15Min"
    ::= { macRxShelfConnectionCurrent15minEntry 5 }

endOfMacRxShelfConnectionCurrent15minTable OBJECT-TYPE
    SYNTAX        Integer32
    MAX-ACCESS    read-only
    STATUS        current
    DESCRIPTION   ""
    ::= { pmShelfConnectionDataRecord 10 }

macRxShelfConnectionCurrent1dayTable OBJECT-TYPE
    SYNTAX        SEQUENCE OF MacRxShelfConnectionCurrent1dayEntry
    MAX-ACCESS    not-accessible
    STATUS        current
    DESCRIPTION   ""
    ::= { pmShelfConnectionDataRecord 11 }

macRxShelfConnectionCurrent1dayEntry OBJECT-TYPE
    SYNTAX        MacRxShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macRxShelfConnectionCurrent1dayTable 1 }

MacRxShelfConnectionCurrent1dayEntry ::= SEQUENCE
  {    macRxShelfConnectionCurrent1dayGoodFrames Counter64String,
    macRxShelfConnectionCurrent1dayOctRcv Counter64String,
    macRxShelfConnectionCurrent1dayBroadcastFramesRcv Counter64String,
    macRxShelfConnectionCurrent1dayMulticastFramesRcv Counter64String,
    macRxShelfConnectionCurrent1dayElapsedTime Integer32 }

macRxShelfConnectionCurrent1dayGoodFrames OBJECT-TYPE
    SYNTAX        Counter64String
    MAX-ACCESS    read-only
    STATUS        current
    DESCRIPTION   "Frames Received"
    ::= { macRxShelfConnectionCurrent1dayEntry 1 }

macRxShelfConnectionCurrent1dayOctRcv OBJECT-TYPE
    SYNTAX        Counter64String
    MAX-ACCESS    read-only
    STATUS        current
    DESCRIPTION   "Bytes Received"
    ::= { macRxShelfConnectionCurrent1dayEntry 2 }

macRxShelfConnectionCurrent1dayBroadcastFramesRcv OBJECT-TYPE
    SYNTAX        Counter64String
    MAX-ACCESS    read-only
    STATUS        current
    DESCRIPTION   "Broadcast Frames Received"
    ::= { macRxShelfConnectionCurrent1dayEntry 3 }

macRxShelfConnectionCurrent1dayMulticastFramesRcv OBJECT-TYPE
    SYNTAX        Counter64String
    MAX-ACCESS    read-only
    STATUS        current
    DESCRIPTION   "Multicast Frames Received"
    ::= { macRxShelfConnectionCurrent1dayEntry 4 }

macRxShelfConnectionCurrent1dayElapsedTime OBJECT-TYPE
    SYNTAX        Integer32 (0..86400)
    MAX-ACCESS    read-only
    STATUS        current
    DESCRIPTION   "Elapsed 1Day"
    ::= { macRxShelfConnectionCurrent1dayEntry 5 }

endOfMacRxShelfConnectionCurrent1dayTable OBJECT-TYPE
    SYNTAX        Integer32
    MAX-ACCESS    read-only
    STATUS        current
    DESCRIPTION   ""
    ::= { pmShelfConnectionDataRecord 12 }

macRxShelfConnectionHistorical15minTable OBJECT-TYPE
    SYNTAX        SEQUENCE OF MacRxShelfConnectionHistorical15minEntry
    MAX-ACCESS    not-accessible
    STATUS        current
    DESCRIPTION   ""
    ::= { pmShelfConnectionDataRecord 13 }

macRxShelfConnectionHistorical15minEntry OBJECT-TYPE
    SYNTAX        MacRxShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macRxShelfConnectionHistorical15minNumber
                }
    ::= { macRxShelfConnectionHistorical15minTable 1 }

MacRxShelfConnectionHistorical15minEntry ::= SEQUENCE
  {    macRxShelfConnectionHistorical15minNumber Integer32,
    macRxShelfConnectionHistorical15minGoodFrames Counter64String,
    macRxShelfConnectionHistorical15minOctRcv Counter64String,
    macRxShelfConnectionHistorical15minBroadcastFramesRcv Counter64String,
    macRxShelfConnectionHistorical15minMulticastFramesRcv Counter64String,
    macRxShelfConnectionHistorical15minValidFlag TruthValue,
    macRxShelfConnectionHistorical15minTimeStamp DateAndTime }

macRxShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macRxShelfConnectionHistorical15minEntry 1 }

macRxShelfConnectionHistorical15minGoodFrames OBJECT-TYPE
    SYNTAX        Counter64String
    MAX-ACCESS    read-only
    STATUS        current
    DESCRIPTION   "Frames Received"
    ::= { macRxShelfConnectionHistorical15minEntry 2 }

macRxShelfConnectionHistorical15minOctRcv OBJECT-TYPE
    SYNTAX        Counter64String
    MAX-ACCESS    read-only
    STATUS        current
    DESCRIPTION   "Bytes Received"
    ::= { macRxShelfConnectionHistorical15minEntry 3 }

macRxShelfConnectionHistorical15minBroadcastFramesRcv OBJECT-TYPE
    SYNTAX        Counter64String
    MAX-ACCESS    read-only
    STATUS        current
    DESCRIPTION   "Broadcast Frames Received"
    ::= { macRxShelfConnectionHistorical15minEntry 4 }

macRxShelfConnectionHistorical15minMulticastFramesRcv OBJECT-TYPE
    SYNTAX        Counter64String
    MAX-ACCESS    read-only
    STATUS        current
    DESCRIPTION   "Multicast Frames Received"
    ::= { macRxShelfConnectionHistorical15minEntry 5 }

macRxShelfConnectionHistorical15minValidFlag OBJECT-TYPE
    SYNTAX        TruthValue
    MAX-ACCESS    read-only
    STATUS        current
    DESCRIPTION   "Valid Flag"
    ::= { macRxShelfConnectionHistorical15minEntry 6 }

macRxShelfConnectionHistorical15minTimeStamp OBJECT-TYPE
    SYNTAX        DateAndTime
    MAX-ACCESS    read-only
    STATUS        current
    DESCRIPTION   "Timestamp"
    ::= { macRxShelfConnectionHistorical15minEntry 7 }

endOfMacRxShelfConnectionHistorical15minTable OBJECT-TYPE
    SYNTAX        Integer32
    MAX-ACCESS    read-only
    STATUS        current
    DESCRIPTION   ""
    ::= { pmShelfConnectionDataRecord 14 }

macRxShelfConnectionHistorical1dayTable OBJECT-TYPE
    SYNTAX        SEQUENCE OF MacRxShelfConnectionHistorical1dayEntry
    MAX-ACCESS    not-accessible
    STATUS        current
    DESCRIPTION   ""
    ::= { pmShelfConnectionDataRecord 15 }

macRxShelfConnectionHistorical1dayEntry OBJECT-TYPE
    SYNTAX        MacRxShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macRxShelfConnectionHistorical1dayNumber
                }
    ::= { macRxShelfConnectionHistorical1dayTable 1 }

MacRxShelfConnectionHistorical1dayEntry ::= SEQUENCE
  {    macRxShelfConnectionHistorical1dayNumber Integer32,
    macRxShelfConnectionHistorical1dayGoodFrames Counter64String,
    macRxShelfConnectionHistorical1dayOctRcv Counter64String,
    macRxShelfConnectionHistorical1dayBroadcastFramesRcv Counter64String,
    macRxShelfConnectionHistorical1dayMulticastFramesRcv Counter64String,
    macRxShelfConnectionHistorical1dayValidFlag TruthValue,
    macRxShelfConnectionHistorical1dayTimeStamp DateAndTime }

macRxShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macRxShelfConnectionHistorical1dayEntry 1 }

macRxShelfConnectionHistorical1dayGoodFrames OBJECT-TYPE
    SYNTAX        Counter64String
    MAX-ACCESS    read-only
    STATUS        current
    DESCRIPTION   "Frames Received"
    ::= { macRxShelfConnectionHistorical1dayEntry 2 }

macRxShelfConnectionHistorical1dayOctRcv OBJECT-TYPE
    SYNTAX        Counter64String
    MAX-ACCESS    read-only
    STATUS        current
    DESCRIPTION   "Bytes Received"
    ::= { macRxShelfConnectionHistorical1dayEntry 3 }

macRxShelfConnectionHistorical1dayBroadcastFramesRcv OBJECT-TYPE
    SYNTAX        Counter64String
    MAX-ACCESS    read-only
    STATUS        current
    DESCRIPTION   "Broadcast Frames Received"
    ::= { macRxShelfConnectionHistorical1dayEntry 4 }

macRxShelfConnectionHistorical1dayMulticastFramesRcv OBJECT-TYPE
    SYNTAX        Counter64String
    MAX-ACCESS    read-only
    STATUS        current
    DESCRIPTION   "Multicast Frames Received"
    ::= { macRxShelfConnectionHistorical1dayEntry 5 }

macRxShelfConnectionHistorical1dayValidFlag OBJECT-TYPE
    SYNTAX        TruthValue
    MAX-ACCESS    read-only
    STATUS        current
    DESCRIPTION   "Valid Flag"
    ::= { macRxShelfConnectionHistorical1dayEntry 6 }

macRxShelfConnectionHistorical1dayTimeStamp OBJECT-TYPE
    SYNTAX        DateAndTime
    MAX-ACCESS    read-only
    STATUS        current
    DESCRIPTION   "Timestamp"
    ::= { macRxShelfConnectionHistorical1dayEntry 7 }

endOfMacRxShelfConnectionHistorical1dayTable OBJECT-TYPE
    SYNTAX        Integer32
    MAX-ACCESS    read-only
    STATUS        current
    DESCRIPTION   ""
    ::= { pmShelfConnectionDataRecord 16 }

macTxShelfConnectionCurrent15minTable OBJECT-TYPE
    SYNTAX        SEQUENCE OF MacTxShelfConnectionCurrent15minEntry
    MAX-ACCESS    not-accessible
    STATUS        current
    DESCRIPTION   ""
    ::= { pmShelfConnectionDataRecord 17 }

macTxShelfConnectionCurrent15minEntry OBJECT-TYPE
    SYNTAX        MacTxShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macTxShelfConnectionCurrent15minTable 1 }

MacTxShelfConnectionCurrent15minEntry ::= SEQUENCE
  {    macTxShelfConnectionCurrent15minFramesTrmt Counter64String,
    macTxShelfConnectionCurrent15minBytesTrmt Counter64String,
    macTxShelfConnectionCurrent15minBroadcastFramesTrmt Counter64String,
    macTxShelfConnectionCurrent15minMulticastFramesTrmt Counter64String,
    macTxShelfConnectionCurrent15minDiscardedFramesTrmt Counter64String,
    macTxShelfConnectionCurrent15minElapsedTime Integer32 }

macTxShelfConnectionCurrent15minFramesTrmt OBJECT-TYPE
    SYNTAX        Counter64String
    MAX-ACCESS    read-only
    STATUS        current
    DESCRIPTION   "Frames Transmitted"
    ::= { macTxShelfConnectionCurrent15minEntry 1 }

macTxShelfConnectionCurrent15minBytesTrmt OBJECT-TYPE
    SYNTAX        Counter64String
    MAX-ACCESS    read-only
    STATUS        current
    DESCRIPTION   "Bytes Transmitted"
    ::= { macTxShelfConnectionCurrent15minEntry 2 }

macTxShelfConnectionCurrent15minBroadcastFramesTrmt OBJECT-TYPE
    SYNTAX        Counter64String
    MAX-ACCESS    read-only
    STATUS        current
    DESCRIPTION   "Broadcast Frames Transmitted"
    ::= { macTxShelfConnectionCurrent15minEntry 3 }

macTxShelfConnectionCurrent15minMulticastFramesTrmt OBJECT-TYPE
    SYNTAX        Counter64String
    MAX-ACCESS    read-only
    STATUS        current
    DESCRIPTION   "Multicast / Broadcast Frames Transmitted"
    ::= { macTxShelfConnectionCurrent15minEntry 4 }

macTxShelfConnectionCurrent15minDiscardedFramesTrmt OBJECT-TYPE
    SYNTAX        Counter64String
    MAX-ACCESS    read-only
    STATUS        current
    DESCRIPTION   "Transmit Frames Discarded"
    ::= { macTxShelfConnectionCurrent15minEntry 5 }

macTxShelfConnectionCurrent15minElapsedTime OBJECT-TYPE
    SYNTAX        Integer32 (0..9000)
    MAX-ACCESS    read-only
    STATUS        current
    DESCRIPTION   "Elapsed 15Min"
    ::= { macTxShelfConnectionCurrent15minEntry 6 }

endOfMacTxShelfConnectionCurrent15minTable OBJECT-TYPE
    SYNTAX        Integer32
    MAX-ACCESS    read-only
    STATUS        current
    DESCRIPTION   ""
    ::= { pmShelfConnectionDataRecord 18 }

macTxShelfConnectionCurrent1dayTable OBJECT-TYPE
    SYNTAX        SEQUENCE OF MacTxShelfConnectionCurrent1dayEntry
    MAX-ACCESS    not-accessible
    STATUS        current
    DESCRIPTION   ""
    ::= { pmShelfConnectionDataRecord 19 }

macTxShelfConnectionCurrent1dayEntry OBJECT-TYPE
    SYNTAX        MacTxShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macTxShelfConnectionCurrent1dayTable 1 }

MacTxShelfConnectionCurrent1dayEntry ::= SEQUENCE
  {    macTxShelfConnectionCurrent1dayFramesTrmt Counter64String,
    macTxShelfConnectionCurrent1dayBytesTrmt Counter64String,
    macTxShelfConnectionCurrent1dayBroadcastFramesTrmt Counter64String,
    macTxShelfConnectionCurrent1dayMulticastFramesTrmt Counter64String,
    macTxShelfConnectionCurrent1dayDiscardedFramesTrmt Counter64String,
    macTxShelfConnectionCurrent1dayElapsedTime Integer32 }

macTxShelfConnectionCurrent1dayFramesTrmt OBJECT-TYPE
    SYNTAX        Counter64String
    MAX-ACCESS    read-only
    STATUS        current
    DESCRIPTION   "Frames Transmitted"
    ::= { macTxShelfConnectionCurrent1dayEntry 1 }

macTxShelfConnectionCurrent1dayBytesTrmt OBJECT-TYPE
    SYNTAX        Counter64String
    MAX-ACCESS    read-only
    STATUS        current
    DESCRIPTION   "Bytes Transmitted"
    ::= { macTxShelfConnectionCurrent1dayEntry 2 }

macTxShelfConnectionCurrent1dayBroadcastFramesTrmt OBJECT-TYPE
    SYNTAX        Counter64String
    MAX-ACCESS    read-only
    STATUS        current
    DESCRIPTION   "Broadcast Frames Transmitted"
    ::= { macTxShelfConnectionCurrent1dayEntry 3 }

macTxShelfConnectionCurrent1dayMulticastFramesTrmt OBJECT-TYPE
    SYNTAX        Counter64String
    MAX-ACCESS    read-only
    STATUS        current
    DESCRIPTION   "Multicast / Broadcast Frames Transmitted"
    ::= { macTxShelfConnectionCurrent1dayEntry 4 }

macTxShelfConnectionCurrent1dayDiscardedFramesTrmt OBJECT-TYPE
    SYNTAX        Counter64String
    MAX-ACCESS    read-only
    STATUS        current
    DESCRIPTION   "Transmit Frames Discarded"
    ::= { macTxShelfConnectionCurrent1dayEntry 5 }

macTxShelfConnectionCurrent1dayElapsedTime OBJECT-TYPE
    SYNTAX        Integer32 (0..86400)
    MAX-ACCESS    read-only
    STATUS        current
    DESCRIPTION   "Elapsed 1Day"
    ::= { macTxShelfConnectionCurrent1dayEntry 6 }

endOfMacTxShelfConnectionCurrent1dayTable OBJECT-TYPE
    SYNTAX        Integer32
    MAX-ACCESS    read-only
    STATUS        current
    DESCRIPTION   ""
    ::= { pmShelfConnectionDataRecord 20 }

macTxShelfConnectionHistorical15minTable OBJECT-TYPE
    SYNTAX        SEQUENCE OF MacTxShelfConnectionHistorical15minEntry
    MAX-ACCESS    not-accessible
    STATUS        current
    DESCRIPTION   ""
    ::= { pmShelfConnectionDataRecord 21 }

macTxShelfConnectionHistorical15minEntry OBJECT-TYPE
    SYNTAX        MacTxShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macTxShelfConnectionHistorical15minNumber
                }
    ::= { macTxShelfConnectionHistorical15minTable 1 }

MacTxShelfConnectionHistorical15minEntry ::= SEQUENCE
  {    macTxShelfConnectionHistorical15minNumber Integer32,
    macTxShelfConnectionHistorical15minFramesTrmt Counter64String,
    macTxShelfConnectionHistorical15minBytesTrmt Counter64String,
    macTxShelfConnectionHistorical15minBroadcastFramesTrmt Counter64String,
    macTxShelfConnectionHistorical15minMulticastFramesTrmt Counter64String,
    macTxShelfConnectionHistorical15minDiscardedFramesTrmt Counter64String,
    macTxShelfConnectionHistorical15minValidFlag TruthValue,
    macTxShelfConnectionHistorical15minTimeStamp DateAndTime }

macTxShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macTxShelfConnectionHistorical15minEntry 1 }

macTxShelfConnectionHistorical15minFramesTrmt OBJECT-TYPE
    SYNTAX        Counter64String
    MAX-ACCESS    read-only
    STATUS        current
    DESCRIPTION   "Frames Transmitted"
    ::= { macTxShelfConnectionHistorical15minEntry 2 }

macTxShelfConnectionHistorical15minBytesTrmt OBJECT-TYPE
    SYNTAX        Counter64String
    MAX-ACCESS    read-only
    STATUS        current
    DESCRIPTION   "Bytes Transmitted"
    ::= { macTxShelfConnectionHistorical15minEntry 3 }

macTxShelfConnectionHistorical15minBroadcastFramesTrmt OBJECT-TYPE
    SYNTAX        Counter64String
    MAX-ACCESS    read-only
    STATUS        current
    DESCRIPTION   "Broadcast Frames Transmitted"
    ::= { macTxShelfConnectionHistorical15minEntry 4 }

macTxShelfConnectionHistorical15minMulticastFramesTrmt OBJECT-TYPE
    SYNTAX        Counter64String
    MAX-ACCESS    read-only
    STATUS        current
    DESCRIPTION   "Multicast / Broadcast Frames Transmitted"
    ::= { macTxShelfConnectionHistorical15minEntry 5 }

macTxShelfConnectionHistorical15minDiscardedFramesTrmt OBJECT-TYPE
    SYNTAX        Counter64String
    MAX-ACCESS    read-only
    STATUS        current
    DESCRIPTION   "Transmit Frames Discarded"
    ::= { macTxShelfConnectionHistorical15minEntry 6 }

macTxShelfConnectionHistorical15minValidFlag OBJECT-TYPE
    SYNTAX        TruthValue
    MAX-ACCESS    read-only
    STATUS        current
    DESCRIPTION   "Valid Flag"
    ::= { macTxShelfConnectionHistorical15minEntry 7 }

macTxShelfConnectionHistorical15minTimeStamp OBJECT-TYPE
    SYNTAX        DateAndTime
    MAX-ACCESS    read-only
    STATUS        current
    DESCRIPTION   "Timestamp"
    ::= { macTxShelfConnectionHistorical15minEntry 8 }

endOfMacTxShelfConnectionHistorical15minTable OBJECT-TYPE
    SYNTAX        Integer32
    MAX-ACCESS    read-only
    STATUS        current
    DESCRIPTION   ""
    ::= { pmShelfConnectionDataRecord 22 }

macTxShelfConnectionHistorical1dayTable OBJECT-TYPE
    SYNTAX        SEQUENCE OF MacTxShelfConnectionHistorical1dayEntry
    MAX-ACCESS    not-accessible
    STATUS        current
    DESCRIPTION   ""
    ::= { pmShelfConnectionDataRecord 23 }

macTxShelfConnectionHistorical1dayEntry OBJECT-TYPE
    SYNTAX        MacTxShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macTxShelfConnectionHistorical1dayNumber
                }
    ::= { macTxShelfConnectionHistorical1dayTable 1 }

MacTxShelfConnectionHistorical1dayEntry ::= SEQUENCE
  {    macTxShelfConnectionHistorical1dayNumber Integer32,
    macTxShelfConnectionHistorical1dayFramesTrmt Counter64String,
    macTxShelfConnectionHistorical1dayBytesTrmt Counter64String,
    macTxShelfConnectionHistorical1dayBroadcastFramesTrmt Counter64String,
    macTxShelfConnectionHistorical1dayMulticastFramesTrmt Counter64String,
    macTxShelfConnectionHistorical1dayDiscardedFramesTrmt Counter64String,
    macTxShelfConnectionHistorical1dayValidFlag TruthValue,
    macTxShelfConnectionHistorical1dayTimeStamp DateAndTime }

macTxShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macTxShelfConnectionHistorical1dayEntry 1 }

macTxShelfConnectionHistorical1dayFramesTrmt OBJECT-TYPE
    SYNTAX        Counter64String
    MAX-ACCESS    read-only
    STATUS        current
    DESCRIPTION   "Frames Transmitted"
    ::= { macTxShelfConnectionHistorical1dayEntry 2 }

macTxShelfConnectionHistorical1dayBytesTrmt OBJECT-TYPE
    SYNTAX        Counter64String
    MAX-ACCESS    read-only
    STATUS        current
    DESCRIPTION   "Bytes Transmitted"
    ::= { macTxShelfConnectionHistorical1dayEntry 3 }

macTxShelfConnectionHistorical1dayBroadcastFramesTrmt OBJECT-TYPE
    SYNTAX        Counter64String
    MAX-ACCESS    read-only
    STATUS        current
    DESCRIPTION   "Broadcast Frames Transmitted"
    ::= { macTxShelfConnectionHistorical1dayEntry 4 }

macTxShelfConnectionHistorical1dayMulticastFramesTrmt OBJECT-TYPE
    SYNTAX        Counter64String
    MAX-ACCESS    read-only
    STATUS        current
    DESCRIPTION   "Multicast / Broadcast Frames Transmitted"
    ::= { macTxShelfConnectionHistorical1dayEntry 5 }

macTxShelfConnectionHistorical1dayDiscardedFramesTrmt OBJECT-TYPE
    SYNTAX        Counter64String
    MAX-ACCESS    read-only
    STATUS        current
    DESCRIPTION   "Transmit Frames Discarded"
    ::= { macTxShelfConnectionHistorical1dayEntry 6 }

macTxShelfConnectionHistorical1dayValidFlag OBJECT-TYPE
    SYNTAX        TruthValue
    MAX-ACCESS    read-only
    STATUS        current
    DESCRIPTION   "Valid Flag"
    ::= { macTxShelfConnectionHistorical1dayEntry 7 }

macTxShelfConnectionHistorical1dayTimeStamp OBJECT-TYPE
    SYNTAX        DateAndTime
    MAX-ACCESS    read-only
    STATUS        current
    DESCRIPTION   "Timestamp"
    ::= { macTxShelfConnectionHistorical1dayEntry 8 }

endOfMacTxShelfConnectionHistorical1dayTable OBJECT-TYPE
    SYNTAX        Integer32
    MAX-ACCESS    read-only
    STATUS        current
    DESCRIPTION   ""
    ::= { pmShelfConnectionDataRecord 24 }

macSzRxShelfConnectionCurrent15minTable OBJECT-TYPE
    SYNTAX        SEQUENCE OF MacSzRxShelfConnectionCurrent15minEntry
    MAX-ACCESS    not-accessible
    STATUS        current
    DESCRIPTION   ""
    ::= { pmShelfConnectionDataRecord 25 }

macSzRxShelfConnectionCurrent15minEntry OBJECT-TYPE
    SYNTAX        MacSzRxShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macSzRxShelfConnectionCurrent15minTable 1 }

MacSzRxShelfConnectionCurrent15minEntry ::= SEQUENCE
  {    macSzRxShelfConnectionCurrent15minBytesFrames64Rcv Counter64String,
    macSzRxShelfConnectionCurrent15minBytesFrames65Rcv Counter64String,
    macSzRxShelfConnectionCurrent15minBytesFrames128Rcv Counter64String,
    macSzRxShelfConnectionCurrent15minBytesFrames256Rcv Counter64String,
    macSzRxShelfConnectionCurrent15minBytesFrames512Rcv Counter64String,
    macSzRxShelfConnectionCurrent15minBytesFrames1024Rcv Counter64String,
    macSzRxShelfConnectionCurrent15minBytesFrames1519Rcv Counter64String,
    macSzRxShelfConnectionCurrent15minElapsedTime Integer32 }

macSzRxShelfConnectionCurrent15minBytesFrames64Rcv OBJECT-TYPE
    SYNTAX        Counter64String
    MAX-ACCESS    read-only
    STATUS        current
    DESCRIPTION   "64 Byte Frames Received"
    ::= { macSzRxShelfConnectionCurrent15minEntry 1 }

macSzRxShelfConnectionCurrent15minBytesFrames65Rcv OBJECT-TYPE
    SYNTAX        Counter64String
    MAX-ACCESS    read-only
    STATUS        current
    DESCRIPTION   "65-127 Byte Frames Received"
    ::= { macSzRxShelfConnectionCurrent15minEntry 2 }

macSzRxShelfConnectionCurrent15minBytesFrames128Rcv OBJECT-TYPE
    SYNTAX        Counter64String
    MAX-ACCESS    read-only
    STATUS        current
    DESCRIPTION   "128-255 Byte Frames Received"
    ::= { macSzRxShelfConnectionCurrent15minEntry 3 }

macSzRxShelfConnectionCurrent15minBytesFrames256Rcv OBJECT-TYPE
    SYNTAX        Counter64String
    MAX-ACCESS    read-only
    STATUS        current
    DESCRIPTION   "256-511 Byte Frames Received"
    ::= { macSzRxShelfConnectionCurrent15minEntry 4 }

macSzRxShelfConnectionCurrent15minBytesFrames512Rcv OBJECT-TYPE
    SYNTAX        Counter64String
    MAX-ACCESS    read-only
    STATUS        current
    DESCRIPTION   "512-1023 Byte Frames Received"
    ::= { macSzRxShelfConnectionCurrent15minEntry 5 }

macSzRxShelfConnectionCurrent15minBytesFrames1024Rcv OBJECT-TYPE
    SYNTAX        Counter64String
    MAX-ACCESS    read-only
    STATUS        current
    DESCRIPTION   "1024-1518 Byte Frames Received"
    ::= { macSzRxShelfConnectionCurrent15minEntry 6 }

macSzRxShelfConnectionCurrent15minBytesFrames1519Rcv OBJECT-TYPE
    SYNTAX        Counter64String
    MAX-ACCESS    read-only
    STATUS        current
    DESCRIPTION   "1519-Max Byte Frames Received"
    ::= { macSzRxShelfConnectionCurrent15minEntry 7 }

macSzRxShelfConnectionCurrent15minElapsedTime OBJECT-TYPE
    SYNTAX        Integer32 (0..9000)
    MAX-ACCESS    read-only
    STATUS        current
    DESCRIPTION   "Elapsed 15Min"
    ::= { macSzRxShelfConnectionCurrent15minEntry 8 }

endOfMacSzRxShelfConnectionCurrent15minTable OBJECT-TYPE
    SYNTAX        Integer32
    MAX-ACCESS    read-only
    STATUS        current
    DESCRIPTION   ""
    ::= { pmShelfConnectionDataRecord 26 }

macSzRxShelfConnectionCurrent1dayTable OBJECT-TYPE
    SYNTAX        SEQUENCE OF MacSzRxShelfConnectionCurrent1dayEntry
    MAX-ACCESS    not-accessible
    STATUS        current
    DESCRIPTION   ""
    ::= { pmShelfConnectionDataRecord 27 }

macSzRxShelfConnectionCurrent1dayEntry OBJECT-TYPE
    SYNTAX        MacSzRxShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macSzRxShelfConnectionCurrent1dayTable 1 }

MacSzRxShelfConnectionCurrent1dayEntry ::= SEQUENCE
  {    macSzRxShelfConnectionCurrent1dayBytesFrames64Rcv Counter64String,
    macSzRxShelfConnectionCurrent1dayBytesFrames65Rcv Counter64String,
    macSzRxShelfConnectionCurrent1dayBytesFrames128Rcv Counter64String,
    macSzRxShelfConnectionCurrent1dayBytesFrames256Rcv Counter64String,
    macSzRxShelfConnectionCurrent1dayBytesFrames512Rcv Counter64String,
    macSzRxShelfConnectionCurrent1dayBytesFrames1024Rcv Counter64String,
    macSzRxShelfConnectionCurrent1dayBytesFrames1519Rcv Counter64String,
    macSzRxShelfConnectionCurrent1dayElapsedTime Integer32 }

macSzRxShelfConnectionCurrent1dayBytesFrames64Rcv OBJECT-TYPE
    SYNTAX        Counter64String
    MAX-ACCESS    read-only
    STATUS        current
    DESCRIPTION   "64 Byte Frames Received"
    ::= { macSzRxShelfConnectionCurrent1dayEntry 1 }

macSzRxShelfConnectionCurrent1dayBytesFrames65Rcv OBJECT-TYPE
    SYNTAX        Counter64String
    MAX-ACCESS    read-only
    STATUS        current
    DESCRIPTION   "65-127 Byte Frames Received"
    ::= { macSzRxShelfConnectionCurrent1dayEntry 2 }

macSzRxShelfConnectionCurrent1dayBytesFrames128Rcv OBJECT-TYPE
    SYNTAX        Counter64String
    MAX-ACCESS    read-only
    STATUS        current
    DESCRIPTION   "128-255 Byte Frames Received"
    ::= { macSzRxShelfConnectionCurrent1dayEntry 3 }

macSzRxShelfConnectionCurrent1dayBytesFrames256Rcv OBJECT-TYPE
    SYNTAX        Counter64String
    MAX-ACCESS    read-only
    STATUS        current
    DESCRIPTION   "256-511 Byte Frames Received"
    ::= { macSzRxShelfConnectionCurrent1dayEntry 4 }

macSzRxShelfConnectionCurrent1dayBytesFrames512Rcv OBJECT-TYPE
    SYNTAX        Counter64String
    MAX-ACCESS    read-only
    STATUS        current
    DESCRIPTION   "512-1023 Byte Frames Received"
    ::= { macSzRxShelfConnectionCurrent1dayEntry 5 }

macSzRxShelfConnectionCurrent1dayBytesFrames1024Rcv OBJECT-TYPE
    SYNTAX        Counter64String
    MAX-ACCESS    read-only
    STATUS        current
    DESCRIPTION   "1024-1518 Byte Frames Received"
    ::= { macSzRxShelfConnectionCurrent1dayEntry 6 }

macSzRxShelfConnectionCurrent1dayBytesFrames1519Rcv OBJECT-TYPE
    SYNTAX        Counter64String
    MAX-ACCESS    read-only
    STATUS        current
    DESCRIPTION   "1519-Max Byte Frames Received"
    ::= { macSzRxShelfConnectionCurrent1dayEntry 7 }

macSzRxShelfConnectionCurrent1dayElapsedTime OBJECT-TYPE
    SYNTAX        Integer32 (0..86400)
    MAX-ACCESS    read-only
    STATUS        current
    DESCRIPTION   "Elapsed 1Day"
    ::= { macSzRxShelfConnectionCurrent1dayEntry 8 }

endOfMacSzRxShelfConnectionCurrent1dayTable OBJECT-TYPE
    SYNTAX        Integer32
    MAX-ACCESS    read-only
    STATUS        current
    DESCRIPTION   ""
    ::= { pmShelfConnectionDataRecord 28 }

macSzRxShelfConnectionHistorical15minTable OBJECT-TYPE
    SYNTAX        SEQUENCE OF MacSzRxShelfConnectionHistorical15minEntry
    MAX-ACCESS    not-accessible
    STATUS        current
    DESCRIPTION   ""
    ::= { pmShelfConnectionDataRecord 29 }

macSzRxShelfConnectionHistorical15minEntry OBJECT-TYPE
    SYNTAX        MacSzRxShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macSzRxShelfConnectionHistorical15minNumber
                }
    ::= { macSzRxShelfConnectionHistorical15minTable 1 }

MacSzRxShelfConnectionHistorical15minEntry ::= SEQUENCE
  {    macSzRxShelfConnectionHistorical15minNumber Integer32,
    macSzRxShelfConnectionHistorical15minBytesFrames64Rcv Counter64String,
    macSzRxShelfConnectionHistorical15minBytesFrames65Rcv Counter64String,
    macSzRxShelfConnectionHistorical15minBytesFrames128Rcv Counter64String,
    macSzRxShelfConnectionHistorical15minBytesFrames256Rcv Counter64String,
    macSzRxShelfConnectionHistorical15minBytesFrames512Rcv Counter64String,
    macSzRxShelfConnectionHistorical15minBytesFrames1024Rcv Counter64String,
    macSzRxShelfConnectionHistorical15minBytesFrames1519Rcv Counter64String,
    macSzRxShelfConnectionHistorical15minValidFlag TruthValue,
    macSzRxShelfConnectionHistorical15minTimeStamp DateAndTime }

macSzRxShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macSzRxShelfConnectionHistorical15minEntry 1 }

macSzRxShelfConnectionHistorical15minBytesFrames64Rcv OBJECT-TYPE
    SYNTAX        Counter64String
    MAX-ACCESS    read-only
    STATUS        current
    DESCRIPTION   "64 Byte Frames Received"
    ::= { macSzRxShelfConnectionHistorical15minEntry 2 }

macSzRxShelfConnectionHistorical15minBytesFrames65Rcv OBJECT-TYPE
    SYNTAX        Counter64String
    MAX-ACCESS    read-only
    STATUS        current
    DESCRIPTION   "65-127 Byte Frames Received"
    ::= { macSzRxShelfConnectionHistorical15minEntry 3 }

macSzRxShelfConnectionHistorical15minBytesFrames128Rcv OBJECT-TYPE
    SYNTAX        Counter64String
    MAX-ACCESS    read-only
    STATUS        current
    DESCRIPTION   "128-255 Byte Frames Received"
    ::= { macSzRxShelfConnectionHistorical15minEntry 4 }

macSzRxShelfConnectionHistorical15minBytesFrames256Rcv OBJECT-TYPE
    SYNTAX        Counter64String
    MAX-ACCESS    read-only
    STATUS        current
    DESCRIPTION   "256-511 Byte Frames Received"
    ::= { macSzRxShelfConnectionHistorical15minEntry 5 }

macSzRxShelfConnectionHistorical15minBytesFrames512Rcv OBJECT-TYPE
    SYNTAX        Counter64String
    MAX-ACCESS    read-only
    STATUS        current
    DESCRIPTION   "512-1023 Byte Frames Received"
    ::= { macSzRxShelfConnectionHistorical15minEntry 6 }

macSzRxShelfConnectionHistorical15minBytesFrames1024Rcv OBJECT-TYPE
    SYNTAX        Counter64String
    MAX-ACCESS    read-only
    STATUS        current
    DESCRIPTION   "1024-1518 Byte Frames Received"
    ::= { macSzRxShelfConnectionHistorical15minEntry 7 }

macSzRxShelfConnectionHistorical15minBytesFrames1519Rcv OBJECT-TYPE
    SYNTAX        Counter64String
    MAX-ACCESS    read-only
    STATUS        current
    DESCRIPTION   "1519-Max Byte Frames Received"
    ::= { macSzRxShelfConnectionHistorical15minEntry 8 }

macSzRxShelfConnectionHistorical15minValidFlag OBJECT-TYPE
    SYNTAX        TruthValue
    MAX-ACCESS    read-only
    STATUS        current
    DESCRIPTION   "Valid Flag"
    ::= { macSzRxShelfConnectionHistorical15minEntry 9 }

macSzRxShelfConnectionHistorical15minTimeStamp OBJECT-TYPE
    SYNTAX        DateAndTime
    MAX-ACCESS    read-only
    STATUS        current
    DESCRIPTION   "Timestamp"
    ::= { macSzRxShelfConnectionHistorical15minEntry 10 }

endOfMacSzRxShelfConnectionHistorical15minTable OBJECT-TYPE
    SYNTAX        Integer32
    MAX-ACCESS    read-only
    STATUS        current
    DESCRIPTION   ""
    ::= { pmShelfConnectionDataRecord 30 }

macSzRxShelfConnectionHistorical1dayTable OBJECT-TYPE
    SYNTAX        SEQUENCE OF MacSzRxShelfConnectionHistorical1dayEntry
    MAX-ACCESS    not-accessible
    STATUS        current
    DESCRIPTION   ""
    ::= { pmShelfConnectionDataRecord 31 }

macSzRxShelfConnectionHistorical1dayEntry OBJECT-TYPE
    SYNTAX        MacSzRxShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macSzRxShelfConnectionHistorical1dayNumber
                }
    ::= { macSzRxShelfConnectionHistorical1dayTable 1 }

MacSzRxShelfConnectionHistorical1dayEntry ::= SEQUENCE
  {    macSzRxShelfConnectionHistorical1dayNumber Integer32,
    macSzRxShelfConnectionHistorical1dayBytesFrames64Rcv Counter64String,
    macSzRxShelfConnectionHistorical1dayBytesFrames65Rcv Counter64String,
    macSzRxShelfConnectionHistorical1dayBytesFrames128Rcv Counter64String,
    macSzRxShelfConnectionHistorical1dayBytesFrames256Rcv Counter64String,
    macSzRxShelfConnectionHistorical1dayBytesFrames512Rcv Counter64String,
    macSzRxShelfConnectionHistorical1dayBytesFrames1024Rcv Counter64String,
    macSzRxShelfConnectionHistorical1dayBytesFrames1519Rcv Counter64String,
    macSzRxShelfConnectionHistorical1dayValidFlag TruthValue,
    macSzRxShelfConnectionHistorical1dayTimeStamp DateAndTime }

macSzRxShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macSzRxShelfConnectionHistorical1dayEntry 1 }

macSzRxShelfConnectionHistorical1dayBytesFrames64Rcv OBJECT-TYPE
    SYNTAX        Counter64String
    MAX-ACCESS    read-only
    STATUS        current
    DESCRIPTION   "64 Byte Frames Received"
    ::= { macSzRxShelfConnectionHistorical1dayEntry 2 }

macSzRxShelfConnectionHistorical1dayBytesFrames65Rcv OBJECT-TYPE
    SYNTAX        Counter64String
    MAX-ACCESS    read-only
    STATUS        current
    DESCRIPTION   "65-127 Byte Frames Received"
    ::= { macSzRxShelfConnectionHistorical1dayEntry 3 }

macSzRxShelfConnectionHistorical1dayBytesFrames128Rcv OBJECT-TYPE
    SYNTAX        Counter64String
    MAX-ACCESS    read-only
    STATUS        current
    DESCRIPTION   "128-255 Byte Frames Received"
    ::= { macSzRxShelfConnectionHistorical1dayEntry 4 }

macSzRxShelfConnectionHistorical1dayBytesFrames256Rcv OBJECT-TYPE
    SYNTAX        Counter64String
    MAX-ACCESS    read-only
    STATUS        current
    DESCRIPTION   "256-511 Byte Frames Received"
    ::= { macSzRxShelfConnectionHistorical1dayEntry 5 }

macSzRxShelfConnectionHistorical1dayBytesFrames512Rcv OBJECT-TYPE
    SYNTAX        Counter64String
    MAX-ACCESS    read-only
    STATUS        current
    DESCRIPTION   "512-1023 Byte Frames Received"
    ::= { macSzRxShelfConnectionHistorical1dayEntry 6 }

macSzRxShelfConnectionHistorical1dayBytesFrames1024Rcv OBJECT-TYPE
    SYNTAX        Counter64String
    MAX-ACCESS    read-only
    STATUS        current
    DESCRIPTION   "1024-1518 Byte Frames Received"
    ::= { macSzRxShelfConnectionHistorical1dayEntry 7 }

macSzRxShelfConnectionHistorical1dayBytesFrames1519Rcv OBJECT-TYPE
    SYNTAX        Counter64String
    MAX-ACCESS    read-only
    STATUS        current
    DESCRIPTION   "1519-Max Byte Frames Received"
    ::= { macSzRxShelfConnectionHistorical1dayEntry 8 }

macSzRxShelfConnectionHistorical1dayValidFlag OBJECT-TYPE
    SYNTAX        TruthValue
    MAX-ACCESS    read-only
    STATUS        current
    DESCRIPTION   "Valid Flag"
    ::= { macSzRxShelfConnectionHistorical1dayEntry 9 }

macSzRxShelfConnectionHistorical1dayTimeStamp OBJECT-TYPE
    SYNTAX        DateAndTime
    MAX-ACCESS    read-only
    STATUS        current
    DESCRIPTION   "Timestamp"
    ::= { macSzRxShelfConnectionHistorical1dayEntry 10 }

endOfMacSzRxShelfConnectionHistorical1dayTable OBJECT-TYPE
    SYNTAX        Integer32
    MAX-ACCESS    read-only
    STATUS        current
    DESCRIPTION   ""
    ::= { pmShelfConnectionDataRecord 32 }

macErrRxShelfConnectionCurrent15minTable OBJECT-TYPE
    SYNTAX        SEQUENCE OF MacErrRxShelfConnectionCurrent15minEntry
    MAX-ACCESS    not-accessible
    STATUS        current
    DESCRIPTION   ""
    ::= { pmShelfConnectionDataRecord 33 }

macErrRxShelfConnectionCurrent15minEntry OBJECT-TYPE
    SYNTAX        MacErrRxShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macErrRxShelfConnectionCurrent15minTable 1 }

MacErrRxShelfConnectionCurrent15minEntry ::= SEQUENCE
  {    macErrRxShelfConnectionCurrent15minCrcErrorsRcv Counter64String,
    macErrRxShelfConnectionCurrent15minOversizedFramesRcv Counter64String,
    macErrRxShelfConnectionCurrent15minUndersizedFramesRcv Counter64String,
    macErrRxShelfConnectionCurrent15minElapsedTime Integer32 }

macErrRxShelfConnectionCurrent15minCrcErrorsRcv OBJECT-TYPE
    SYNTAX        Counter64String
    MAX-ACCESS    read-only
    STATUS        current
    DESCRIPTION   "Received CRC Errors"
    ::= { macErrRxShelfConnectionCurrent15minEntry 1 }

macErrRxShelfConnectionCurrent15minOversizedFramesRcv OBJECT-TYPE
    SYNTAX        Counter64String
    MAX-ACCESS    read-only
    STATUS        current
    DESCRIPTION   "Oversized Frames Received"
    ::= { macErrRxShelfConnectionCurrent15minEntry 2 }

macErrRxShelfConnectionCurrent15minUndersizedFramesRcv OBJECT-TYPE
    SYNTAX        Counter64String
    MAX-ACCESS    read-only
    STATUS        current
    DESCRIPTION   "Undersized Frames Received"
    ::= { macErrRxShelfConnectionCurrent15minEntry 3 }

macErrRxShelfConnectionCurrent15minElapsedTime OBJECT-TYPE
    SYNTAX        Integer32 (0..9000)
    MAX-ACCESS    read-only
    STATUS        current
    DESCRIPTION   "Elapsed 15Min"
    ::= { macErrRxShelfConnectionCurrent15minEntry 4 }

endOfMacErrRxShelfConnectionCurrent15minTable OBJECT-TYPE
    SYNTAX        Integer32
    MAX-ACCESS    read-only
    STATUS        current
    DESCRIPTION   ""
    ::= { pmShelfConnectionDataRecord 34 }

macErrRxShelfConnectionCurrent1dayTable OBJECT-TYPE
    SYNTAX        SEQUENCE OF MacErrRxShelfConnectionCurrent1dayEntry
    MAX-ACCESS    not-accessible
    STATUS        current
    DESCRIPTION   ""
    ::= { pmShelfConnectionDataRecord 35 }

macErrRxShelfConnectionCurrent1dayEntry OBJECT-TYPE
    SYNTAX        MacErrRxShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macErrRxShelfConnectionCurrent1dayTable 1 }

MacErrRxShelfConnectionCurrent1dayEntry ::= SEQUENCE
  {    macErrRxShelfConnectionCurrent1dayCrcErrorsRcv Counter64String,
    macErrRxShelfConnectionCurrent1dayOversizedFramesRcv Counter64String,
    macErrRxShelfConnectionCurrent1dayUndersizedFramesRcv Counter64String,
    macErrRxShelfConnectionCurrent1dayElapsedTime Integer32 }

macErrRxShelfConnectionCurrent1dayCrcErrorsRcv OBJECT-TYPE
    SYNTAX        Counter64String
    MAX-ACCESS    read-only
    STATUS        current
    DESCRIPTION   "Received CRC Errors"
    ::= { macErrRxShelfConnectionCurrent1dayEntry 1 }

macErrRxShelfConnectionCurrent1dayOversizedFramesRcv OBJECT-TYPE
    SYNTAX        Counter64String
    MAX-ACCESS    read-only
    STATUS        current
    DESCRIPTION   "Oversized Frames Received"
    ::= { macErrRxShelfConnectionCurrent1dayEntry 2 }

macErrRxShelfConnectionCurrent1dayUndersizedFramesRcv OBJECT-TYPE
    SYNTAX        Counter64String
    MAX-ACCESS    read-only
    STATUS        current
    DESCRIPTION   "Undersized Frames Received"
    ::= { macErrRxShelfConnectionCurrent1dayEntry 3 }

macErrRxShelfConnectionCurrent1dayElapsedTime OBJECT-TYPE
    SYNTAX        Integer32 (0..86400)
    MAX-ACCESS    read-only
    STATUS        current
    DESCRIPTION   "Elapsed 1Day"
    ::= { macErrRxShelfConnectionCurrent1dayEntry 4 }

endOfMacErrRxShelfConnectionCurrent1dayTable OBJECT-TYPE
    SYNTAX        Integer32
    MAX-ACCESS    read-only
    STATUS        current
    DESCRIPTION   ""
    ::= { pmShelfConnectionDataRecord 36 }

macErrRxShelfConnectionHistorical15minTable OBJECT-TYPE
    SYNTAX        SEQUENCE OF MacErrRxShelfConnectionHistorical15minEntry
    MAX-ACCESS    not-accessible
    STATUS        current
    DESCRIPTION   ""
    ::= { pmShelfConnectionDataRecord 37 }

macErrRxShelfConnectionHistorical15minEntry OBJECT-TYPE
    SYNTAX        MacErrRxShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macErrRxShelfConnectionHistorical15minNumber
                }
    ::= { macErrRxShelfConnectionHistorical15minTable 1 }

MacErrRxShelfConnectionHistorical15minEntry ::= SEQUENCE
  {    macErrRxShelfConnectionHistorical15minNumber Integer32,
    macErrRxShelfConnectionHistorical15minCrcErrorsRcv Counter64String,
    macErrRxShelfConnectionHistorical15minOversizedFramesRcv Counter64String,
    macErrRxShelfConnectionHistorical15minUndersizedFramesRcv Counter64String,
    macErrRxShelfConnectionHistorical15minValidFlag TruthValue,
    macErrRxShelfConnectionHistorical15minTimeStamp DateAndTime }

macErrRxShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macErrRxShelfConnectionHistorical15minEntry 1 }

macErrRxShelfConnectionHistorical15minCrcErrorsRcv OBJECT-TYPE
    SYNTAX        Counter64String
    MAX-ACCESS    read-only
    STATUS        current
    DESCRIPTION   "Received CRC Errors"
    ::= { macErrRxShelfConnectionHistorical15minEntry 2 }

macErrRxShelfConnectionHistorical15minOversizedFramesRcv OBJECT-TYPE
    SYNTAX        Counter64String
    MAX-ACCESS    read-only
    STATUS        current
    DESCRIPTION   "Oversized Frames Received"
    ::= { macErrRxShelfConnectionHistorical15minEntry 3 }

macErrRxShelfConnectionHistorical15minUndersizedFramesRcv OBJECT-TYPE
    SYNTAX        Counter64String
    MAX-ACCESS    read-only
    STATUS        current
    DESCRIPTION   "Undersized Frames Received"
    ::= { macErrRxShelfConnectionHistorical15minEntry 4 }

macErrRxShelfConnectionHistorical15minValidFlag OBJECT-TYPE
    SYNTAX        TruthValue
    MAX-ACCESS    read-only
    STATUS        current
    DESCRIPTION   "Valid Flag"
    ::= { macErrRxShelfConnectionHistorical15minEntry 5 }

macErrRxShelfConnectionHistorical15minTimeStamp OBJECT-TYPE
    SYNTAX        DateAndTime
    MAX-ACCESS    read-only
    STATUS        current
    DESCRIPTION   "Timestamp"
    ::= { macErrRxShelfConnectionHistorical15minEntry 6 }

endOfMacErrRxShelfConnectionHistorical15minTable OBJECT-TYPE
    SYNTAX        Integer32
    MAX-ACCESS    read-only
    STATUS        current
    DESCRIPTION   ""
    ::= { pmShelfConnectionDataRecord 38 }

macErrRxShelfConnectionHistorical1dayTable OBJECT-TYPE
    SYNTAX        SEQUENCE OF MacErrRxShelfConnectionHistorical1dayEntry
    MAX-ACCESS    not-accessible
    STATUS        current
    DESCRIPTION   ""
    ::= { pmShelfConnectionDataRecord 39 }

macErrRxShelfConnectionHistorical1dayEntry OBJECT-TYPE
    SYNTAX        MacErrRxShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macErrRxShelfConnectionHistorical1dayNumber
                }
    ::= { macErrRxShelfConnectionHistorical1dayTable 1 }

MacErrRxShelfConnectionHistorical1dayEntry ::= SEQUENCE
  {    macErrRxShelfConnectionHistorical1dayNumber Integer32,
    macErrRxShelfConnectionHistorical1dayCrcErrorsRcv Counter64String,
    macErrRxShelfConnectionHistorical1dayOversizedFramesRcv Counter64String,
    macErrRxShelfConnectionHistorical1dayUndersizedFramesRcv Counter64String,
    macErrRxShelfConnectionHistorical1dayValidFlag TruthValue,
    macErrRxShelfConnectionHistorical1dayTimeStamp DateAndTime }

macErrRxShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macErrRxShelfConnectionHistorical1dayEntry 1 }

macErrRxShelfConnectionHistorical1dayCrcErrorsRcv OBJECT-TYPE
    SYNTAX        Counter64String
    MAX-ACCESS    read-only
    STATUS        current
    DESCRIPTION   "Received CRC Errors"
    ::= { macErrRxShelfConnectionHistorical1dayEntry 2 }

macErrRxShelfConnectionHistorical1dayOversizedFramesRcv OBJECT-TYPE
    SYNTAX        Counter64String
    MAX-ACCESS    read-only
    STATUS        current
    DESCRIPTION   "Oversized Frames Received"
    ::= { macErrRxShelfConnectionHistorical1dayEntry 3 }

macErrRxShelfConnectionHistorical1dayUndersizedFramesRcv OBJECT-TYPE
    SYNTAX        Counter64String
    MAX-ACCESS    read-only
    STATUS        current
    DESCRIPTION   "Undersized Frames Received"
    ::= { macErrRxShelfConnectionHistorical1dayEntry 4 }

macErrRxShelfConnectionHistorical1dayValidFlag OBJECT-TYPE
    SYNTAX        TruthValue
    MAX-ACCESS    read-only
    STATUS        current
    DESCRIPTION   "Valid Flag"
    ::= { macErrRxShelfConnectionHistorical1dayEntry 5 }

macErrRxShelfConnectionHistorical1dayTimeStamp OBJECT-TYPE
    SYNTAX        DateAndTime
    MAX-ACCESS    read-only
    STATUS        current
    DESCRIPTION   "Timestamp"
    ::= { macErrRxShelfConnectionHistorical1dayEntry 6 }

endOfMacErrRxShelfConnectionHistorical1dayTable OBJECT-TYPE
    SYNTAX        Integer32
    MAX-ACCESS    read-only
    STATUS        current
    DESCRIPTION   ""
    ::= { pmShelfConnectionDataRecord 40 }

macIcRxShelfConnectionCurrent15minTable OBJECT-TYPE
    SYNTAX        SEQUENCE OF MacIcRxShelfConnectionCurrent15minEntry
    MAX-ACCESS    not-accessible
    STATUS        current
    DESCRIPTION   ""
    ::= { pmShelfConnectionDataRecord 41 }

macIcRxShelfConnectionCurrent15minEntry OBJECT-TYPE
    SYNTAX        MacIcRxShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macIcRxShelfConnectionCurrent15minTable 1 }

MacIcRxShelfConnectionCurrent15minEntry ::= SEQUENCE
  {    macIcRxShelfConnectionCurrent15minGoodFrames Counter64String,
    macIcRxShelfConnectionCurrent15minOctRcv Counter64String,
    macIcRxShelfConnectionCurrent15minCrcErrorsRcv Counter64String,
    macIcRxShelfConnectionCurrent15minElapsedTime Integer32 }

macIcRxShelfConnectionCurrent15minGoodFrames OBJECT-TYPE
    SYNTAX        Counter64String
    MAX-ACCESS    read-only
    STATUS        current
    DESCRIPTION   "Frames Received"
    ::= { macIcRxShelfConnectionCurrent15minEntry 1 }

macIcRxShelfConnectionCurrent15minOctRcv OBJECT-TYPE
    SYNTAX        Counter64String
    MAX-ACCESS    read-only
    STATUS        current
    DESCRIPTION   "Bytes Received"
    ::= { macIcRxShelfConnectionCurrent15minEntry 2 }

macIcRxShelfConnectionCurrent15minCrcErrorsRcv OBJECT-TYPE
    SYNTAX        Counter64String
    MAX-ACCESS    read-only
    STATUS        current
    DESCRIPTION   "Received CRC Errors"
    ::= { macIcRxShelfConnectionCurrent15minEntry 3 }

macIcRxShelfConnectionCurrent15minElapsedTime OBJECT-TYPE
    SYNTAX        Integer32 (0..9000)
    MAX-ACCESS    read-only
    STATUS        current
    DESCRIPTION   "Elapsed 15Min"
    ::= { macIcRxShelfConnectionCurrent15minEntry 4 }

endOfMacIcRxShelfConnectionCurrent15minTable OBJECT-TYPE
    SYNTAX        Integer32
    MAX-ACCESS    read-only
    STATUS        current
    DESCRIPTION   ""
    ::= { pmShelfConnectionDataRecord 42 }

macIcRxShelfConnectionCurrent1dayTable OBJECT-TYPE
    SYNTAX        SEQUENCE OF MacIcRxShelfConnectionCurrent1dayEntry
    MAX-ACCESS    not-accessible
    STATUS        current
    DESCRIPTION   ""
    ::= { pmShelfConnectionDataRecord 43 }

macIcRxShelfConnectionCurrent1dayEntry OBJECT-TYPE
    SYNTAX        MacIcRxShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macIcRxShelfConnectionCurrent1dayTable 1 }

MacIcRxShelfConnectionCurrent1dayEntry ::= SEQUENCE
  {    macIcRxShelfConnectionCurrent1dayGoodFrames Counter64String,
    macIcRxShelfConnectionCurrent1dayOctRcv Counter64String,
    macIcRxShelfConnectionCurrent1dayCrcErrorsRcv Counter64String,
    macIcRxShelfConnectionCurrent1dayElapsedTime Integer32 }

macIcRxShelfConnectionCurrent1dayGoodFrames OBJECT-TYPE
    SYNTAX        Counter64String
    MAX-ACCESS    read-only
    STATUS        current
    DESCRIPTION   "Frames Received"
    ::= { macIcRxShelfConnectionCurrent1dayEntry 1 }

macIcRxShelfConnectionCurrent1dayOctRcv OBJECT-TYPE
    SYNTAX        Counter64String
    MAX-ACCESS    read-only
    STATUS        current
    DESCRIPTION   "Bytes Received"
    ::= { macIcRxShelfConnectionCurrent1dayEntry 2 }

macIcRxShelfConnectionCurrent1dayCrcErrorsRcv OBJECT-TYPE
    SYNTAX        Counter64String
    MAX-ACCESS    read-only
    STATUS        current
    DESCRIPTION   "Received CRC Errors"
    ::= { macIcRxShelfConnectionCurrent1dayEntry 3 }

macIcRxShelfConnectionCurrent1dayElapsedTime OBJECT-TYPE
    SYNTAX        Integer32 (0..86400)
    MAX-ACCESS    read-only
    STATUS        current
    DESCRIPTION   "Elapsed 1Day"
    ::= { macIcRxShelfConnectionCurrent1dayEntry 4 }

endOfMacIcRxShelfConnectionCurrent1dayTable OBJECT-TYPE
    SYNTAX        Integer32
    MAX-ACCESS    read-only
    STATUS        current
    DESCRIPTION   ""
    ::= { pmShelfConnectionDataRecord 44 }

macIcRxShelfConnectionHistorical15minTable OBJECT-TYPE
    SYNTAX        SEQUENCE OF MacIcRxShelfConnectionHistorical15minEntry
    MAX-ACCESS    not-accessible
    STATUS        current
    DESCRIPTION   ""
    ::= { pmShelfConnectionDataRecord 45 }

macIcRxShelfConnectionHistorical15minEntry OBJECT-TYPE
    SYNTAX        MacIcRxShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macIcRxShelfConnectionHistorical15minNumber
                }
    ::= { macIcRxShelfConnectionHistorical15minTable 1 }

MacIcRxShelfConnectionHistorical15minEntry ::= SEQUENCE
  {    macIcRxShelfConnectionHistorical15minNumber Integer32,
    macIcRxShelfConnectionHistorical15minGoodFrames Counter64String,
    macIcRxShelfConnectionHistorical15minOctRcv Counter64String,
    macIcRxShelfConnectionHistorical15minCrcErrorsRcv Counter64String,
    macIcRxShelfConnectionHistorical15minValidFlag TruthValue,
    macIcRxShelfConnectionHistorical15minTimeStamp DateAndTime }

macIcRxShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macIcRxShelfConnectionHistorical15minEntry 1 }

macIcRxShelfConnectionHistorical15minGoodFrames OBJECT-TYPE
    SYNTAX        Counter64String
    MAX-ACCESS    read-only
    STATUS        current
    DESCRIPTION   "Frames Received"
    ::= { macIcRxShelfConnectionHistorical15minEntry 2 }

macIcRxShelfConnectionHistorical15minOctRcv OBJECT-TYPE
    SYNTAX        Counter64String
    MAX-ACCESS    read-only
    STATUS        current
    DESCRIPTION   "Bytes Received"
    ::= { macIcRxShelfConnectionHistorical15minEntry 3 }

macIcRxShelfConnectionHistorical15minCrcErrorsRcv OBJECT-TYPE
    SYNTAX        Counter64String
    MAX-ACCESS    read-only
    STATUS        current
    DESCRIPTION   "Received CRC Errors"
    ::= { macIcRxShelfConnectionHistorical15minEntry 4 }

macIcRxShelfConnectionHistorical15minValidFlag OBJECT-TYPE
    SYNTAX        TruthValue
    MAX-ACCESS    read-only
    STATUS        current
    DESCRIPTION   "Valid Flag"
    ::= { macIcRxShelfConnectionHistorical15minEntry 5 }

macIcRxShelfConnectionHistorical15minTimeStamp OBJECT-TYPE
    SYNTAX        DateAndTime
    MAX-ACCESS    read-only
    STATUS        current
    DESCRIPTION   "Timestamp"
    ::= { macIcRxShelfConnectionHistorical15minEntry 6 }

endOfMacIcRxShelfConnectionHistorical15minTable OBJECT-TYPE
    SYNTAX        Integer32
    MAX-ACCESS    read-only
    STATUS        current
    DESCRIPTION   ""
    ::= { pmShelfConnectionDataRecord 46 }

macIcRxShelfConnectionHistorical1dayTable OBJECT-TYPE
    SYNTAX        SEQUENCE OF MacIcRxShelfConnectionHistorical1dayEntry
    MAX-ACCESS    not-accessible
    STATUS        current
    DESCRIPTION   ""
    ::= { pmShelfConnectionDataRecord 47 }

macIcRxShelfConnectionHistorical1dayEntry OBJECT-TYPE
    SYNTAX        MacIcRxShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macIcRxShelfConnectionHistorical1dayNumber
                }
    ::= { macIcRxShelfConnectionHistorical1dayTable 1 }

MacIcRxShelfConnectionHistorical1dayEntry ::= SEQUENCE
  {    macIcRxShelfConnectionHistorical1dayNumber Integer32,
    macIcRxShelfConnectionHistorical1dayGoodFrames Counter64String,
    macIcRxShelfConnectionHistorical1dayOctRcv Counter64String,
    macIcRxShelfConnectionHistorical1dayCrcErrorsRcv Counter64String,
    macIcRxShelfConnectionHistorical1dayValidFlag TruthValue,
    macIcRxShelfConnectionHistorical1dayTimeStamp DateAndTime }

macIcRxShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macIcRxShelfConnectionHistorical1dayEntry 1 }

macIcRxShelfConnectionHistorical1dayGoodFrames OBJECT-TYPE
    SYNTAX        Counter64String
    MAX-ACCESS    read-only
    STATUS        current
    DESCRIPTION   "Frames Received"
    ::= { macIcRxShelfConnectionHistorical1dayEntry 2 }

macIcRxShelfConnectionHistorical1dayOctRcv OBJECT-TYPE
    SYNTAX        Counter64String
    MAX-ACCESS    read-only
    STATUS        current
    DESCRIPTION   "Bytes Received"
    ::= { macIcRxShelfConnectionHistorical1dayEntry 3 }

macIcRxShelfConnectionHistorical1dayCrcErrorsRcv OBJECT-TYPE
    SYNTAX        Counter64String
    MAX-ACCESS    read-only
    STATUS        current
    DESCRIPTION   "Received CRC Errors"
    ::= { macIcRxShelfConnectionHistorical1dayEntry 4 }

macIcRxShelfConnectionHistorical1dayValidFlag OBJECT-TYPE
    SYNTAX        TruthValue
    MAX-ACCESS    read-only
    STATUS        current
    DESCRIPTION   "Valid Flag"
    ::= { macIcRxShelfConnectionHistorical1dayEntry 5 }

macIcRxShelfConnectionHistorical1dayTimeStamp OBJECT-TYPE
    SYNTAX        DateAndTime
    MAX-ACCESS    read-only
    STATUS        current
    DESCRIPTION   "Timestamp"
    ::= { macIcRxShelfConnectionHistorical1dayEntry 6 }

endOfMacIcRxShelfConnectionHistorical1dayTable OBJECT-TYPE
    SYNTAX        Integer32
    MAX-ACCESS    read-only
    STATUS        current
    DESCRIPTION   ""
    ::= { pmShelfConnectionDataRecord 48 }

macIcTxShelfConnectionCurrent15minTable OBJECT-TYPE
    SYNTAX        SEQUENCE OF MacIcTxShelfConnectionCurrent15minEntry
    MAX-ACCESS    not-accessible
    STATUS        current
    DESCRIPTION   ""
    ::= { pmShelfConnectionDataRecord 49 }

macIcTxShelfConnectionCurrent15minEntry OBJECT-TYPE
    SYNTAX        MacIcTxShelfConnectionCurrent15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macIcTxShelfConnectionCurrent15minTable 1 }

MacIcTxShelfConnectionCurrent15minEntry ::= SEQUENCE
  {    macIcTxShelfConnectionCurrent15minBytesTrmt Counter64String,
    macIcTxShelfConnectionCurrent15minFramesTrmt Counter64String,
    macIcTxShelfConnectionCurrent15minElapsedTime Integer32 }

macIcTxShelfConnectionCurrent15minBytesTrmt OBJECT-TYPE
    SYNTAX        Counter64String
    MAX-ACCESS    read-only
    STATUS        current
    DESCRIPTION   "Bytes Transmitted"
    ::= { macIcTxShelfConnectionCurrent15minEntry 1 }

macIcTxShelfConnectionCurrent15minFramesTrmt OBJECT-TYPE
    SYNTAX        Counter64String
    MAX-ACCESS    read-only
    STATUS        current
    DESCRIPTION   "Frames Transmitted"
    ::= { macIcTxShelfConnectionCurrent15minEntry 2 }

macIcTxShelfConnectionCurrent15minElapsedTime OBJECT-TYPE
    SYNTAX        Integer32 (0..9000)
    MAX-ACCESS    read-only
    STATUS        current
    DESCRIPTION   "Elapsed 15Min"
    ::= { macIcTxShelfConnectionCurrent15minEntry 3 }

endOfMacIcTxShelfConnectionCurrent15minTable OBJECT-TYPE
    SYNTAX        Integer32
    MAX-ACCESS    read-only
    STATUS        current
    DESCRIPTION   ""
    ::= { pmShelfConnectionDataRecord 50 }

macIcTxShelfConnectionCurrent1dayTable OBJECT-TYPE
    SYNTAX        SEQUENCE OF MacIcTxShelfConnectionCurrent1dayEntry
    MAX-ACCESS    not-accessible
    STATUS        current
    DESCRIPTION   ""
    ::= { pmShelfConnectionDataRecord 51 }

macIcTxShelfConnectionCurrent1dayEntry OBJECT-TYPE
    SYNTAX        MacIcTxShelfConnectionCurrent1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName
                }
    ::= { macIcTxShelfConnectionCurrent1dayTable 1 }

MacIcTxShelfConnectionCurrent1dayEntry ::= SEQUENCE
  {    macIcTxShelfConnectionCurrent1dayBytesTrmt Counter64String,
    macIcTxShelfConnectionCurrent1dayFramesTrmt Counter64String,
    macIcTxShelfConnectionCurrent1dayElapsedTime Integer32 }

macIcTxShelfConnectionCurrent1dayBytesTrmt OBJECT-TYPE
    SYNTAX        Counter64String
    MAX-ACCESS    read-only
    STATUS        current
    DESCRIPTION   "Bytes Transmitted"
    ::= { macIcTxShelfConnectionCurrent1dayEntry 1 }

macIcTxShelfConnectionCurrent1dayFramesTrmt OBJECT-TYPE
    SYNTAX        Counter64String
    MAX-ACCESS    read-only
    STATUS        current
    DESCRIPTION   "Frames Transmitted"
    ::= { macIcTxShelfConnectionCurrent1dayEntry 2 }

macIcTxShelfConnectionCurrent1dayElapsedTime OBJECT-TYPE
    SYNTAX        Integer32 (0..86400)
    MAX-ACCESS    read-only
    STATUS        current
    DESCRIPTION   "Elapsed 1Day"
    ::= { macIcTxShelfConnectionCurrent1dayEntry 3 }

endOfMacIcTxShelfConnectionCurrent1dayTable OBJECT-TYPE
    SYNTAX        Integer32
    MAX-ACCESS    read-only
    STATUS        current
    DESCRIPTION   ""
    ::= { pmShelfConnectionDataRecord 52 }

macIcTxShelfConnectionHistorical15minTable OBJECT-TYPE
    SYNTAX        SEQUENCE OF MacIcTxShelfConnectionHistorical15minEntry
    MAX-ACCESS    not-accessible
    STATUS        current
    DESCRIPTION   ""
    ::= { pmShelfConnectionDataRecord 53 }

macIcTxShelfConnectionHistorical15minEntry OBJECT-TYPE
    SYNTAX        MacIcTxShelfConnectionHistorical15minEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macIcTxShelfConnectionHistorical15minNumber
                }
    ::= { macIcTxShelfConnectionHistorical15minTable 1 }

MacIcTxShelfConnectionHistorical15minEntry ::= SEQUENCE
  {    macIcTxShelfConnectionHistorical15minNumber Integer32,
    macIcTxShelfConnectionHistorical15minBytesTrmt Counter64String,
    macIcTxShelfConnectionHistorical15minFramesTrmt Counter64String,
    macIcTxShelfConnectionHistorical15minValidFlag TruthValue,
    macIcTxShelfConnectionHistorical15minTimeStamp DateAndTime }

macIcTxShelfConnectionHistorical15minNumber OBJECT-TYPE
    SYNTAX        Integer32 (1..96)
    MAX-ACCESS    not-accessible
    STATUS        current
    DESCRIPTION   "A number between 1 and 96, which identifies the interval for
        which the set of statistics is available. The interval
        identified by 1 is the most recently completed 15 minute
        interval, and the interval identified by N is the interval
        immediately preceding the one identified by N-1."
    ::= { macIcTxShelfConnectionHistorical15minEntry 1 }

macIcTxShelfConnectionHistorical15minBytesTrmt OBJECT-TYPE
    SYNTAX        Counter64String
    MAX-ACCESS    read-only
    STATUS        current
    DESCRIPTION   "Bytes Transmitted"
    ::= { macIcTxShelfConnectionHistorical15minEntry 2 }

macIcTxShelfConnectionHistorical15minFramesTrmt OBJECT-TYPE
    SYNTAX        Counter64String
    MAX-ACCESS    read-only
    STATUS        current
    DESCRIPTION   "Frames Transmitted"
    ::= { macIcTxShelfConnectionHistorical15minEntry 3 }

macIcTxShelfConnectionHistorical15minValidFlag OBJECT-TYPE
    SYNTAX        TruthValue
    MAX-ACCESS    read-only
    STATUS        current
    DESCRIPTION   "Valid Flag"
    ::= { macIcTxShelfConnectionHistorical15minEntry 4 }

macIcTxShelfConnectionHistorical15minTimeStamp OBJECT-TYPE
    SYNTAX        DateAndTime
    MAX-ACCESS    read-only
    STATUS        current
    DESCRIPTION   "Timestamp"
    ::= { macIcTxShelfConnectionHistorical15minEntry 5 }

endOfMacIcTxShelfConnectionHistorical15minTable OBJECT-TYPE
    SYNTAX        Integer32
    MAX-ACCESS    read-only
    STATUS        current
    DESCRIPTION   ""
    ::= { pmShelfConnectionDataRecord 54 }

macIcTxShelfConnectionHistorical1dayTable OBJECT-TYPE
    SYNTAX        SEQUENCE OF MacIcTxShelfConnectionHistorical1dayEntry
    MAX-ACCESS    not-accessible
    STATUS        current
    DESCRIPTION   ""
    ::= { pmShelfConnectionDataRecord 55 }

macIcTxShelfConnectionHistorical1dayEntry OBJECT-TYPE
    SYNTAX        MacIcTxShelfConnectionHistorical1dayEntry
    MAX-ACCESS    not-accessible
    STATUS        current
    DESCRIPTION   ""
    INDEX       {
                  entityShelfConnShelfNo,
                  entityShelfConnSlotNo,
                  entityShelfConnPortNo,
                  entityShelfConnExtNo,
                  entityShelfConnClassName,
                  macIcTxShelfConnectionHistorical1dayNumber
                }
    ::= { macIcTxShelfConnectionHistorical1dayTable 1 }

MacIcTxShelfConnectionHistorical1dayEntry ::= SEQUENCE
  {    macIcTxShelfConnectionHistorical1dayNumber Integer32,
    macIcTxShelfConnectionHistorical1dayBytesTrmt Counter64String,
    macIcTxShelfConnectionHistorical1dayFramesTrmt Counter64String,
    macIcTxShelfConnectionHistorical1dayValidFlag TruthValue,
    macIcTxShelfConnectionHistorical1dayTimeStamp DateAndTime }

macIcTxShelfConnectionHistorical1dayNumber OBJECT-TYPE
    SYNTAX        Integer32 (1..31)
    MAX-ACCESS    not-accessible
    STATUS        current
    DESCRIPTION   "A number, which identifies the interval for
        which the set of statistics is available. The interval
        identified by 1 is the most recently completed 1 day
        interval."
    ::= { macIcTxShelfConnectionHistorical1dayEntry 1 }

macIcTxShelfConnectionHistorical1dayBytesTrmt OBJECT-TYPE
    SYNTAX        Counter64String
    MAX-ACCESS    read-only
    STATUS        current
    DESCRIPTION   "Bytes Transmitted"
    ::= { macIcTxShelfConnectionHistorical1dayEntry 2 }

macIcTxShelfConnectionHistorical1dayFramesTrmt OBJECT-TYPE
    SYNTAX        Counter64String
    MAX-ACCESS    read-only
    STATUS        current
    DESCRIPTION   "Frames Transmitted"
    ::= { macIcTxShelfConnectionHistorical1dayEntry 3 }

macIcTxShelfConnectionHistorical1dayValidFlag OBJECT-TYPE
    SYNTAX        TruthValue
    MAX-ACCESS    read-only
    STATUS        current
    DESCRIPTION   "Valid Flag"
    ::= { macIcTxShelfConnectionHistorical1dayEntry 4 }

macIcTxShelfConnectionHistorical1dayTimeStamp OBJECT-TYPE
    SYNTAX        DateAndTime
    MAX-ACCESS    read-only
    STATUS        current
    DESCRIPTION   "Timestamp"
    ::= { macIcTxShelfConnectionHistorical1dayEntry 5 }

endOfMacIcTxShelfConnectionHistorical1dayTable OBJECT-TYPE
    SYNTAX        Integer32
    MAX-ACCESS    read-only
    STATUS        current
    DESCRIPTION   ""
    ::= { pmShelfConnectionDataRecord 56 }


END
