-- **********************************************************
-- Copyright 2021 VMware, Inc.  All rights reserved.
-- **********************************************************

VMWARE-HZECC-AGENTCAP-MIB DEFINITIONS ::= BEGIN

IMPORTS
    MODULE-IDENTITY
       FROM SNMPv2-SMI
    vmwareAgentCapabilities
       FROM VMWARE-ROOT-MIB
    AGENT-CAPABILITIES
       FROM SNMPv2-CONF;

vmwHzeccAgentCapabilityMIB MODULE-IDENTITY
   LAST-UPDATED "202105170000Z"
   ORGANIZATION "VMware, Inc"
   CONTACT-INFO
      "VMware, Inc
      3401 Hillview Ave
      Palo Alto, CA 94304
      Tel: 1-877-486-9273 or 650-427-5000
      Fax: 650-427-5001
      Web: http://kb.vmware.com/kb/1013445
      "
   DESCRIPTION
     "This module defines agent capabilities for deployed
      Horizon Cloud Connector (Hze CC) agents by release.
      Releases of Horizon Cloud Connector (Hze CC)
      prior to 2.0 are not supported."

  REVISION     "202105170000Z"
   DESCRIPTION
     "Notifications sent by Hze CC as updated in 2.0 release"
        ::= { vmwareAgentCapabilities 140 }

vmwHzeccCapability OBJECT IDENTIFIER ::= { vmwHzeccAgentCapabilityMIB 1 }

vmwHZECCAgent2021v200 AGENT-CAPABILITIES
  PRODUCT-RELEASE
     "2.0.0"
  STATUS  current
  DESCRIPTION
     "Release 2.1.0.0 for VMware Horizon Cloud Connector supporting
     only SNMPv3 trap PDUs. It describes all the notifications
     sent from the Hzee CC appliance.
     "
  REFERENCE
     "http://www.vmware.com/products"
     -- REVISION 202105170000Z First Version.
     SUPPORTS VMWARE-HZECC-EVENT-MIB
     INCLUDES {
         vmwHzeccNotificationGroup
     }
   ::= { vmwHzeccCapability 4 }

END
