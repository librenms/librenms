-- **********************************************************
-- Copyright 2016 - 2022 VMware, Inc.  All rights reserved.
-- **********************************************************

VMWARE-VRNI-MIB DEFINITIONS ::= BEGIN

IMPORTS
   MODULE-IDENTITY, OBJECT-IDENTITY, OBJECT-TYPE, NOTIFICATION-TYPE
       FROM SNMPv2-SMI
   SnmpAdminString
       FROM SNMP-FRAMEWORK-MIB
   MODULE-COMPLIANCE, OBJECT-GROUP, NOTIFICATION-GROUP
       FROM SNMPv2-CONF
   TEXTUAL-CONVENTION, DateAndTime
       FROM SNMPv2-TC
   vmwNetworkInsight
       FROM VMWARE-ROOT-MIB
   VmwLongSnmpAdminString
       FROM VMWARE-TC-MIB;

    vmwNetworkInsightMIB MODULE-IDENTITY
    LAST-UPDATED "202308070000Z"
    ORGANIZATION "VMware, Inc"
    CONTACT-INFO
    "VMware, Inc
    3401 Hillview Ave
    Palo Alto, CA 94304
    Tel: 1-877-486-9273 or 650-427-5000
    Fax: 650-427-5001
    Web: http://communities.vmware.com/community/developer/forums/managementapi
    "

    DESCRIPTION
    "This MIB module is for VMware Aria Operations for Networks as described here:
    https://www.vmware.com/support/pubs/vrealize-network-insight-pubs.html
    "

    REVISION      "202308070000Z"
    DESCRIPTION
    "This is the sixteenth revision of VMware Aria Operations for Networks Manager SNMP notifications.
    It updates managed objects with three additional fields for all notifications as shown below:
        from : OBJECTS { vmwEventSeverity, vmwAffectedObject, vmwOperatorDesc, vmwVrniUrl, vmwTimestamp, vmwEventName}
        to : OBJECTS { vmwPlatformIP, vmwEventSeverity, vmwAffectedObject, vmwOperatorDesc, vmwVrniUrl, vmwTimestamp, vmwEventName, vmwAffectedObjectManager, vmwAffectedObjectParent }
    "

    REVISION      "202304200000Z"
    DESCRIPTION
    "This is the fifteenth revision of VMware Aria Operations for Networks Manager SNMP notifications.
    It adds seventy four notifications, see vmwNetworkInsightNotificationGroup15.
    "

    REVISION      "202209070000Z"
    DESCRIPTION
    "This is the fourteenth revision of VMware vRealize Network Insight Manager SNMP notifications.
    It adds eight new notifications, see vmwNetworkInsightNotificationGroup14.
    "

    REVISION      "202203300000Z"
    DESCRIPTION
    "This is the thirteenth revision of VMware vRealize Network Insight Manager SNMP notifications.
    It adds twenty four new notifications, see vmwNetworkInsightNotificationGroup13.
    "

    REVISION      "202110010000Z"
    DESCRIPTION
    "This is the twelfth revision of VMware vRealize Network Insight Manager SNMP notifications.
    It adds five new notifications, see vmwNetworkInsightNotificationGroup12.
    "

    REVISION      "202105240000Z"
    DESCRIPTION
    "This is the eleventh revision of VMware vRealize Network Insight Manager SNMP notifications.
    It adds nineteen new notifications, see vmwNetworkInsightNotificationGroup11.
    "

    REVISION      "202005200000Z"
    DESCRIPTION
    "This is the tenth revision of VMware vRealize Network Insight Manager SNMP notifications.
    It adds fifty two new notifications, see vmwNetworkInsightNotificationGroup10.
    "

    REVISION      "201908190000Z"
    DESCRIPTION
    "This is the ninth revision of VMware vRealize Network Insight Manager SNMP notifications.
    It adds two new notifications, see vmwNetworkInsightNotificationGroup9.
    "

    REVISION      "201906060000Z"
    DESCRIPTION
    "This is the eighth revision of VMware vRealize Network Insight Manager SNMP notifications.
    It adds two new notifications, see vmwNetworkInsightNotificationGroup8.
    "

    REVISION      "201903220000Z"
    DESCRIPTION
    "This is the seventh revision of VMware vRealize Network Insight Manager SNMP notifications.
    It adds seventeen new notifications, see vmwNetworkInsightNotificationGroup7.
    "

    REVISION      "201811270000Z"
    DESCRIPTION
    "This is the sixth revision of VMware vRealize Network Insight Manager SNMP notifications.
    It adds fourteen new notifications, see vmwNetworkInsightNotificationGroup6.
    "

    REVISION      "201809120000Z"
    DESCRIPTION
    "This is the fifth revision of VMware vRealize Network Insight Manager SNMP notifications.
    This revision introduces below changes, some of which are non backward compatible.
      a. All event notifications have their varbind contents changed
        from : OBJECTS { vmwAffectedObject, vmwEventSeverity, vmwVrniUrl, vmwTimestamp, vmwOperatorDesc, vmwEventName}
        to : OBJECTS { vmwEventSeverity, vmwAffectedObject, vmwOperatorDesc, vmwVrniUrl, vmwTimestamp, vmwEventName }

      b. Syntax changes for TC - VmwVrniSeverity
        was { cleared(0), info(1), major(2) }
        is now VmwVrniSeverity {Critical, Moderate, Warning, Info and CLEARED}

      c. Support for new events added, see vmwNetworkInsightNotificationGroup5
      "

    REVISION      "201709050000Z"
    DESCRIPTION
    "This is the fourth revision of VMware vRealize Network Insight Manager SNMP notifications.
    It adds fourteen new notifications, see vmwNetworkInsightNotificationGroup4.
    "

   REVISION     "201706010000Z"
   DESCRIPTION
    "This is the third revision of VMware vRealize Network Insight Manager SNMP notifications.
     This version added nineteen new notifications, see vmwNetworkInsightNotificationGroup3
     for complete listing."

    REVISION      "201702200000Z"
    DESCRIPTION
    "This is the second revision of VMware vRealize Network Insight Manager SNMP notifications.
     It introduces new notifications, see vmwNetworkInsightNotificationGroup2,
     and updates existing notifications to append the vmwEventName managed object."


    REVISION      "201610260000Z"
    DESCRIPTION
    "This is the first revision of VMware vRealize Network Insight Manager SNMP notifications."
    ::= { vmwNetworkInsight 1 }


vmwVRNIEvents OBJECT-IDENTITY
    STATUS  current
    DESCRIPTION
    "All notifications from VMware Aria Operations for Networks fall under this oid."
    ::= { vmwNetworkInsightMIB 0 }

vmwVRNIData OBJECT-IDENTITY
    STATUS  current
    DESCRIPTION
    "All variables that are sent in notifications fall under this oid."
    ::= { vmwNetworkInsightMIB 1 }

-- **********************************************************
-- Type definitions
-- **********************************************************

  VmwVrniSeverity ::= TEXTUAL-CONVENTION
    DISPLAY-HINT "255t"
    STATUS          current
    DESCRIPTION
        "Represents Event Severity, the values returned by TC are
        Critical - All events which are critical in nature towards overall health of environment, could be show stoppers if not fixed
        Moderate - Represents moderate severity, part of functionality could get affected
        Warning - Event which may not represent immediate issue but could soon become one if not addressed
        Info - Informational notifications
        CLEARED - Event was closed by system.
        "
    SYNTAX       OCTET STRING (SIZE (0..255))

-- **********************************************************
-- Notifications by an agent that implements this mib module
-- **********************************************************

vmwSnmpTrapsAreConfigured NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Initial trap to notify receiver that VMware Aria Operations for Networks is now configured to send SNMP traps"
   ::= { vmwVRNIEvents 101}


vmwSnmpTrapsAreDisabled NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Trap to notify receiver that VMware Aria Operations for Networks is no longer configured to send SNMP traps"
   ::= { vmwVRNIEvents 102}


vmwTestTrap NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Test Trap"
   ::= { vmwVRNIEvents 103}


vmwEntityDiscoveryChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Discovery Event"
   ::= { vmwVRNIEvents 20001}

vmwEntityPropertiesChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Property Change Event"
   ::= { vmwVRNIEvents 20002}

vmwFirewallNotInstalledOnHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Firewall Not Installed On Host Event"
   ::= { vmwVRNIEvents 20003}

vmwHostWithStaleFirewallRulesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host With Stale Firewall Rules Event"
   ::= { vmwVRNIEvents 20004}

vmwIpAddressChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Ip Address Change"
   ::= { vmwVRNIEvents 20005}

vmwL2GatewayAnomalyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "L2 Gateway Anomaly Event"
   ::= { vmwVRNIEvents 20006}

vmwL2NetworkAddressAnomalyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "L2 Network Address Anomaly Event"
   ::= { vmwVRNIEvents 20007}

vmwL2NetworkDiameterExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "L2 Network Diameter Exceeded Event"
   ::= { vmwVRNIEvents 20008}

vmwL2NetworkUplinkMissingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "L2 Network Uplink Missing Event"
   ::= { vmwVRNIEvents 20009}

vmwL2NetworkWithNoVMsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "L2 Network With No VMs Event"
   ::= { vmwVRNIEvents 20010}

vmwLayer2NetworkDiameterChangedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Layer2 Network Diameter Changed Event"
   ::= { vmwVRNIEvents 20011}

vmwMTUMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "MTU Mismatch Event"
   ::= { vmwVRNIEvents 20012}

vmwNetworkIsolationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Network Isolation Event"
   ::= { vmwVRNIEvents 20013}

vmwNoPathEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "No Path Event"
   ::= { vmwVRNIEvents 20014}

vmwSpoofguardDisabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Spoofguard Disabled Event"
   ::= { vmwVRNIEvents 20015}

vmwVMotionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VMotion Event"
   ::= { vmwVRNIEvents 20018}

vmwVMWithDisconnectedVnicsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VM With Disconnected Vnics Event"
   ::= { vmwVRNIEvents 20019}

vmwVMWithMulipleVnicsOnDifferentVxlansEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VM With Multiple Vnics On Different Vxlans Event"
   ::= { vmwVRNIEvents 20020}

vmwVMWithMulipleVnicsOnSameL2Event NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VM With Multiple Vnics On Same L2 Event"
   ::= { vmwVRNIEvents 20021}

vmwVMWithNoIpAddressEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VM With No Ip Address Event"
   ::= { vmwVRNIEvents 20022}

vmwVTEPMissingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VTEP Missing Event"
   ::= { vmwVRNIEvents 20023}

vmwL2Event NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "L2 Event"
   ::= { vmwVRNIEvents 20024}

vmwMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Membership Change"
   ::= { vmwVRNIEvents 20025}

vmwSecurityGroupMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Security Group Membership Change"
   ::= { vmwVRNIEvents 20026}

vmwFirewallRuleMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Firewall Rule Membership Change"
   ::= { vmwVRNIEvents 20027}

vmwVlanMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vlan Membership Change"
   ::= { vmwVRNIEvents 20028}

vmwVxlanMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vxlan Membership Change"
   ::= { vmwVRNIEvents 20029}

vmwDeleteChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Delete Event"
   ::= { vmwVRNIEvents 20030}

vmwVtepFailedPingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VTEP Ping Failure Event"
   ::= { vmwVRNIEvents 20031}

vmwEmptySearchStreamChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Search with no results"
   ::= { vmwVRNIEvents 20034}

vmwSearchStreamMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Search results changed"
   ::= { vmwVRNIEvents 20035}

vmwEmptySearchStreamProblemEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Search with no results (Problem)"
   ::= { vmwVRNIEvents 20036}

vmwSearchStreamMembershipProblemEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Search results changed (Problem)"
   ::= { vmwVRNIEvents 20037}

vmwOspfConfigurationMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "OSPF Mismatch Event"
   ::= { vmwVRNIEvents 20038}

vmwServiceVMNotHealthyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Service VM Not Healthy Event"
   ::= { vmwVRNIEvents 20039}

vmwServiceVMNotPoweredOnEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Service VM Not Powered On Event"
   ::= { vmwVRNIEvents 20040}

vmwServiceVMHighCPUUsageEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Service VM High CPU Usage Event"
   ::= { vmwVRNIEvents 20041}

vmwServiceVMHighMemoryUsageEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Service VM High Memory Usage Event"
   ::= { vmwVRNIEvents 20042}

vmwServiceVMHighDiskUsageEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Service VM High Disk Usage Event"
   ::= { vmwVRNIEvents 20043}

vmwIPSetPropertiesChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "IPSet Change"
   ::= { vmwVRNIEvents 20050}

vmwFirewallRulePropertiesChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Firewall Rule Change"
   ::= { vmwVRNIEvents 20051}

vmwSecurityGroupPropertiesChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Security Group Change"
   ::= { vmwVRNIEvents 20052}

vmwIPSetMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "IPSet Membership Change"
   ::= { vmwVRNIEvents 20053}

vmwFirewallRuleMaskEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Firewall Rule Masked Event"
   ::= { vmwVRNIEvents 20054}

vmwSecurityMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Security Membership Change"
   ::= { vmwVRNIEvents 20056}

vmwSecurityTagPropertiesChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Security Tag Change"
   ::= { vmwVRNIEvents 20057}

vmwSecurityTagMembershipChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Security Tag Membership Change"
   ::= { vmwVRNIEvents 20058}

vmwHostDatastoreChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host datastores changed"
   ::= { vmwVRNIEvents 20059}

vmwVMDatastoreChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VM datastores changed"
   ::= { vmwVRNIEvents 20060}

vmwVMSnapshotChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VM snapshot changed"
   ::= { vmwVRNIEvents 20061}

vmwVMVirtualDiskChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Virtual disk migrated"
   ::= { vmwVRNIEvents 20062}

vmwIPSetDefinitionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "IPSET Definition Mismatch Event"
   ::= { vmwVRNIEvents 20063}

vmwSegmentMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Segment Mismatch Event"
   ::= { vmwVRNIEvents 20064}

vmwVtepEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vtep Event"
   ::= { vmwVRNIEvents 20065}

vmwVtepConfigurationFaultEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vtep Configuration Fault Event"
   ::= { vmwVRNIEvents 20066}

vmwVtepSubnetMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vtep Subnet Mismatch Event"
   ::= { vmwVRNIEvents 20068}

vmwVtepCountMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vtep Count Mismatch Event"
   ::= { vmwVRNIEvents 20069}

vmwDLRNetworksNotReachableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "DLR Routing event"
   ::= { vmwVRNIEvents 20067}

vmwEdgeNetworksNotReachableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Edge Routing event"
   ::= { vmwVRNIEvents 20070}

vmwNiInfraChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NI Infra Change"
   ::= { vmwVRNIEvents 20089}

vmwDataSourceEnabledChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Data Source Enabled"
   ::= { vmwVRNIEvents 20090}

vmwDataSourceDisabledChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Data Source Disabled"
   ::= { vmwVRNIEvents 20091}

vmwDataSourceCreatedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Data Source Created"
   ::= { vmwVRNIEvents 20092}

vmwPlatformCpuCoreChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Platform CPU Change Event"
   ::= { vmwVRNIEvents 20093}

vmwPlatformDiskChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Platform Disk Change Event"
   ::= { vmwVRNIEvents 20094}

vmwPlatformMemoryChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Platform Memory Change Event"
   ::= { vmwVRNIEvents 20095}

vmwPlatformRebootedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Platform Reboot Change Event"
   ::= { vmwVRNIEvents 20096}

vmwProxyCpuCoreChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collector CPU Change Event"
   ::= { vmwVRNIEvents 20097}

vmwProxyDiskChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collector Disk Change Event"
   ::= { vmwVRNIEvents 20098}

vmwProxyMemoryChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collector Memory Change Event"
   ::= { vmwVRNIEvents 20099}

vmwProxyRebootedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collector Reboot Change Event"
   ::= { vmwVRNIEvents 20100}

vmwNIClusterChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Cluster Change Event"
   ::= { vmwVRNIEvents 20101}

vmwNISystemProxyChangeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "System Proxy Change Event"
   ::= { vmwVRNIEvents 20102}

vmwNIClusterCreateEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Cluster Create Event"
   ::= { vmwVRNIEvents 20103}

vmwThresholdExceededEventCpuReady NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Cpu Ready"
   ::= { vmwVRNIEvents 30001}

vmwThresholdExceededEventCpuCoStop NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Cpu Co Stop"
   ::= { vmwVRNIEvents 30002}

vmwThresholdExceededEventDiskCommandAbortRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Disk Command Abort Rule"
   ::= { vmwVRNIEvents 30003}

vmwThresholdExceededEventIODeviceLatencyRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded IO Device Latency Rule"
   ::= { vmwVRNIEvents 30004}

vmwThresholdExceededEventIOKernelLatencyRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded IO Kernel Latency Rule"
   ::= { vmwVRNIEvents 30005}

vmwThresholdExceededEventMemorySwapInRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Memory Swap In Rule"
   ::= { vmwVRNIEvents 30006}

vmwThresholdExceededEventMemorySwapOutRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Memory Swap Out Rule"
   ::= { vmwVRNIEvents 30007}

vmwThresholdExceededEventNetworkRxDropRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Memory Rx Drop Rule"
   ::= { vmwVRNIEvents 30008}

vmwThresholdExceededEventNetworkTxDropRule NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Exceeded Memory Tx Drop Rule"
   ::= { vmwVRNIEvents 30009}

vmwAWSRegionSGLimitEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS Region Security Group count near threshold."
   ::= { vmwVRNIEvents 30010}

vmwAWSVPCSGLimitEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS VPC Security Group count near threshold."
   ::= { vmwVRNIEvents 30011}

vmwAWSSGInboundRuleLimitEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS Security Group Inbound Rule count near threshold."
   ::= { vmwVRNIEvents 30012}

vmwAWSSGOutboundRuleLimitEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS Security Group Outbound Rule count near threshold."
   ::= { vmwVRNIEvents 30013}

vmwAWSInterfaceSGLimitEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS VPC Security Group count near threshold."
   ::= { vmwVRNIEvents 30014}

vmwPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Packet Drop Event"
   ::= { vmwVRNIEvents 30100}

vmwSwitchPortPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Switch Port Packet Drop"
   ::= { vmwVRNIEvents 30101}

vmwRouterInterfacePacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Router Interface Packet Drop"
   ::= { vmwVRNIEvents 30102}

vmwVnicPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vnic Packet Drop"
   ::= { vmwVRNIEvents 30103}

vmwVTEPUnderlayPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VTEP Underlay Packet Drop"
   ::= { vmwVRNIEvents 30104}

vmwPnicUnderlyingSwitchPortPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PNIC Underlying Switch Port Packet Drop"
   ::= { vmwVRNIEvents 30105}

vmwDevicePacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Device Packet Drop"
   ::= { vmwVRNIEvents 30106}

vmwThresholdExceededEventDatastoreFreeSpaceWarning NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "ThresholdExceededEventDatastoreFreeSpaceWarning"
   ::= { vmwVRNIEvents 30203}

vmwThresholdExceededEventDatastoreFreeSpaceCritical NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "ThresholdExceededEventDatastoreFreeSpaceCritical"
   ::= { vmwVRNIEvents 30204}

vmwThresholdExceededEventDatastoreReadLatency NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "ThresholdExceededEventDatastoreReadLatency"
   ::= { vmwVRNIEvents 30205}

vmwThresholdExceededEventDatastoreWriteLatency NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "ThresholdExceededEventDatastoreWriteLatency"
   ::= { vmwVRNIEvents 30206}

vmwDistributedFirewallApplyHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Distributed Firewall Apply Host Event"
   ::= { vmwVRNIEvents 35001}

vmwDistributedFirewallApplyVMEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Distributed Firewall Apply VM Event"
   ::= { vmwVRNIEvents 35002}

vmwNsxEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Event"
   ::= { vmwVRNIEvents 35003}

vmwFeatureImpactedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Feature Impacted Event"
   ::= { vmwVRNIEvents 35004}

vmwClusterFeatureVersionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Cluster Feature Mismatch Event"
   ::= { vmwVRNIEvents 36022}

vmwHostFeatureVersionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Feature Mismatch Event"
   ::= { vmwVRNIEvents 36023}

vmwFeatureVersionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Feature Version Mismatch Event"
   ::= { vmwVRNIEvents 36024}

vmwHostFeatureEnabledMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Feature Enabled Mismatch Event"
   ::= { vmwVRNIEvents 36025}

vmwHostFeatureInstalledMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Feature Installed Mismatch Event"
   ::= { vmwVRNIEvents 36026}

vmwHostVtepNotFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Vtep Not Found Event"
   ::= { vmwVRNIEvents 36027}

vmwHostVtepDisconnectedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Vtep Disconnected Event"
   ::= { vmwVRNIEvents 36028}

vmwHostVtepEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Vtep Event"
   ::= { vmwVRNIEvents 36029}

vmwClusterHostsVtepMTUMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Vtep Mtu Mismatch Event"
   ::= { vmwVRNIEvents 36030}

vmwFeatureUnhealthyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Feature Health Event"
   ::= { vmwVRNIEvents 36031}

vmwEdgeHANotConfiguredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Edge High Availability is not enabled Event"
   ::= { vmwVRNIEvents 36032}

vmwEdgeInterfacesDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or More NSX Edge Interfaces are down Event"
   ::= { vmwVRNIEvents 36033}

vmwModuleUnhealthyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Module Unhealthy Event"
   ::= { vmwVRNIEvents 36041}

vmwModuleNotLoadedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Module Not Loaded Event"
   ::= { vmwVRNIEvents 36042}

vmwModuleNetworkConnectionFailureEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Module Network Connection Failure Event"
   ::= { vmwVRNIEvents 36043}

vmwHostNetworkControlPlaneMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Control Plane Network Mismatch Event"
   ::= { vmwVRNIEvents 36044}

vmwHostNetworkControlPlaneConnectionFailureEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Control Plane Network Connection Failure Event"
   ::= { vmwVRNIEvents 36045}

vmwHostNetworkControlPlaneNotSyncedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Control Plane Sync Failure Event"
   ::= { vmwVRNIEvents 36046}

vmwNSXControllerClusterMajorityEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Controller Cluster Majority Event"
   ::= { vmwVRNIEvents 36047}

vmwNSXControllersVMOnSameHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Controllers VM On Same Host Event"
   ::= { vmwVRNIEvents 36048}

vmwVxLanRangeExhaustEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vxlan range exhaust  Event"
   ::= { vmwVRNIEvents 36049}

vmwNSXFirewallDefaultAllowAllRulesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Firewall Allow All Rules Event"
   ::= { vmwVRNIEvents 36050}

vmwLogicalRouterNoUplinkEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The NSX DLR is not configured with default route and may prevent external communication.
      Check if the router configuration is only for routing between internal networks, or if external access is required. If external access is required, then configure an uplink interface on the NSX distributed logical router.
      For more details about this event, please log into VMware Aria Operations for Networks, navigate to Settings -> Events"
   ::= { vmwVRNIEvents 36051}

vmwEdgeNotHAEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Edge not Highly Available Event"
   ::= { vmwVRNIEvents 36052}

vmwEdgeNotDeployedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Edge not deployed Event"
   ::= { vmwVRNIEvents 36053}

vmwEcmpIsEnabledAndStatefulServicesAreUpEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Edge Running with both ECMP and Stateful Edge Services Event"
   ::= { vmwVRNIEvents 36054}

vmwLogicalRouterDeployedOnEcmpEdgeHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Logical Router and ECMP Edge on Same Host Event"
   ::= { vmwVRNIEvents 36055}

vmwEdgeMissingInterfaceOSPFAreaMappingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Edge Interface to OSPF Area Mapping Missing Event"
   ::= { vmwVRNIEvents 36056}

vmwOspfInsecureAuthRouterEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more OSPF areas on the NSX Edge are using insecure authentication Event"
   ::= { vmwVRNIEvents 36057}

vmwNSXControllersDeployedCountEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Controller count  Event"
   ::= { vmwVRNIEvents 36058}

vmwNSXControllerNotActiveCountEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Controller Not Active  Event"
   ::= { vmwVRNIEvents 36059}

vmwNSXControllerEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Controller Event"
   ::= { vmwVRNIEvents 36060}

vmwNSXEcmpEdgeDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more NSX Edges in the ECMP Cluster are currently down"
   ::= { vmwVRNIEvents 36061}

vmwNSXMajorityEcmpEdgesDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The majority of NSX Edges in the ECMP Cluster are currently down"
   ::= { vmwVRNIEvents 36062}

vmwNSXAllEcmpEdgesDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "All NSX Edges in the ECMP Cluster are currently down"
   ::= { vmwVRNIEvents 36063}

vmwNSXEdgeMtuMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The MTU configured on one or more interfaces on the Edge does not match the MTU on the next hop router"
   ::= { vmwVRNIEvents 36064}

vmwNSXEdgeSplitBrainEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Both VMs of Edge HA are in active state"
   ::= { vmwVRNIEvents 36065}

vmwVirtualDistributedRoutingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VDR Port Unset Event"
   ::= { vmwVRNIEvents 36066}

vmwNSXComponentEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Service not running event"
   ::= { vmwVRNIEvents 35221}

vmwNSXBackupEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Backup not configured"
   ::= { vmwVRNIEvents 35222}

vmwNSXBackupAuditLogExcludedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Audit Log excluded from NSX Backup"
   ::= { vmwVRNIEvents 35223}

vmwNSXUnsecureBackupEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Backups not using secure FTP"
   ::= { vmwVRNIEvents 35224}

vmwNSXBackupSystemEventsExcludedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "System Event excluded from NSX Backup"
   ::= { vmwVRNIEvents 35225}

vmwNSXBackupNotScheduledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Scheduled backups are not enabled"
   ::= { vmwVRNIEvents 35226}

vmwNSXBackupNotRecordedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "No backup of the environment has been recorded"
   ::= { vmwVRNIEvents 35227}

vmwNSXNtpServerEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NTP Server not configured"
   ::= { vmwVRNIEvents 35228}

vmwNSXSysLogServerEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Syslog Server not configured"
   ::= { vmwVRNIEvents 35229}

vmwControllerSysLogServerEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Syslog Server not configured"
   ::= { vmwVRNIEvents 35230}

vmwNSXIpV6EnabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "IPv6 is enabled for NSX Manager"
   ::= { vmwVRNIEvents 35231}

vmwNSXOspfNeighborDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more OSPF Neighbors down"
   ::= { vmwVRNIEvents 35232}

vmwGenericNSXSystemEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX System Event (Warning)"
   ::= { vmwVRNIEvents 70000}

vmwOtherCriticalNSXEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX System Event (Critical)"
   ::= { vmwVRNIEvents 71000}

vmwFilterConfigApplyOnHostFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Filter Config Apply On Host Failed Event"
   ::= { vmwVRNIEvents 70001}

vmwRulesetLoadOnHostFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Ruleset Load On Host Failed Event"
   ::= { vmwVRNIEvents 70002}

vmwConfigUpdateOnHostFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Config Update On Host Failed Event"
   ::= { vmwVRNIEvents 70003}

vmwSpoofguardConfigUpdateOnHostFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Spoofguard Config Update On Host Failed Event"
   ::= { vmwVRNIEvents 70004}

vmwApplyRuleToVnicFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Apply Rule To Vnic Failed Event"
   ::= { vmwVRNIEvents 70005}

vmwContainerConfigUpdateOnVnicFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Container Config Update On Vnic Failed Event"
   ::= { vmwVRNIEvents 70006}

vmwSpoofguardApplyToVnicFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Spoofguard Apply To Vnic Failed Event"
   ::= { vmwVRNIEvents 70007}

vmwHostMessagingConfigurationFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Messaging Configuration Failed Event"
   ::= { vmwVRNIEvents 70008}

vmwHostMessagingConnectionReconfigurationFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Messaging Connection Reconfiguration Failed Event"
   ::= { vmwVRNIEvents 70009}

vmwHostMessagingConfigurationFailedNotificationSkippedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Messaging Configuration Failed Notification Skipped Event"
   ::= { vmwVRNIEvents 70010}

vmwHostMessagingInfrastructureDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Messaging Infrastructure Down Event"
   ::= { vmwVRNIEvents 70011}

vmwEdgeVMNotRespondingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Edge VM Responding Event"
   ::= { vmwVRNIEvents 70012}

vmwEdgeUnhealthyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Edge Health Event"
   ::= { vmwVRNIEvents 70013}

vmwEdgeVMCommunicationFailureEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Edge communication failure Event"
   ::= { vmwVRNIEvents 70014}

vmwNSXEdgeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Edge Event"
   ::= { vmwVRNIEvents 70015}

vmwPanEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Palo Alto Event"
   ::= { vmwVRNIEvents 80000}

vmwPanNsxNotInRegisteredStateEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Palo Alto NSX Registration Event"
   ::= { vmwVRNIEvents 80001}

vmwPanNsxDynamicUpdateDelayedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Palo Alto NSX Dynamic Update Event"
   ::= { vmwVRNIEvents 80002}

vmwPanDeviceInDisconnectedStateEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Palo Alto Device Disconnect Event"
   ::= { vmwVRNIEvents 80003}

vmwPanNsxServiceApplianceViewMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Palo Alto Service Device Mismatch Event"
   ::= { vmwVRNIEvents 80004}

vmwPanNsxFabricAgentNotFoundOnHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Fabric Agent Not Found Event"
   ::= { vmwVRNIEvents 80005}

vmwPanNsxServiceVMNotFoundOnHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Palo Alto Service VM Not Found Event"
   ::= { vmwVRNIEvents 80006}

vmwCheckpointEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Check Point Event"
   ::= { vmwVRNIEvents 80100}

vmwCheckpointNsxFabricAgentNotFoundOnHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Check Point NSX Fabric Agent Not Found Event"
   ::= { vmwVRNIEvents 80102}

vmwCheckpointNsxServiceVMNotFoundOnHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Check Point Service VM Not Found Event"
   ::= { vmwVRNIEvents 80103}

vmwCheckpointGatewaySicStatusNotCommunicatingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Check Point Gateway Sic Status Not Communicating Event"
   ::= { vmwVRNIEvents 80104}

vmwCheckpointNsxServiceApplianceViewMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Check Point Service VM Mismatch Event"
   ::= { vmwVRNIEvents 80105}

vmwCriticalHostNotAccessibleEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host with VMs running critical services is not accessible"
   ::= { vmwVRNIEvents 40001}

vmwIndexerLagEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Index Lag Event"
   ::= { vmwVRNIEvents 80501}

vmwIPFIXFlowDPPausedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "IPFIX Flow Data Provider Paused Event"
   ::= { vmwVRNIEvents 80502}

vmwGridProcessingStoppedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Grid Processing Stopped Event"
   ::= { vmwVRNIEvents 80503}

vmwUnableToSendEmailsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Unable to Send Emails Event"
   ::= { vmwVRNIEvents 80504}

vmwSMTPNotConfiguredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "SMPT Not Configured Event"
   ::= { vmwVRNIEvents 80505}

vmwSNMPNotConfiguredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "SNMP Not Configured Event"
   ::= { vmwVRNIEvents 80506}

vmwReindexingInProgressEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Redindexing In Process Event"
   ::= { vmwVRNIEvents 80507}

vmwNodesVersionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Node Version Mismatch Event"
   ::= { vmwVRNIEvents 80508}

vmwNotAllServicesRunningEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Not All Services Running Event"
   ::= { vmwVRNIEvents 80509}

vmwNotAllServicesHealthyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Not All Services Healthy Event"
   ::= { vmwVRNIEvents 80510}

vmwExpandPartitionFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Expand Partition Failed Event"
   ::= { vmwVRNIEvents 80511}

vmwDiskCleanupFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Disk Cleanup Failed Event"
   ::= { vmwVRNIEvents 80512}

vmwVacuumFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Vacuum Failed Event"
   ::= { vmwVRNIEvents 80513}

vmwConfigStoreCleanupFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Config Store Cleanup Failed Event"
   ::= { vmwVRNIEvents 80514}

vmwHBaseRetentionToolFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HBASE Retention Tool Failed Event"
   ::= { vmwVRNIEvents 80515}

vmwMetricStoreUpdaterFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Metric Store Updater Failed Event"
   ::= { vmwVRNIEvents 80516}

vmwCollectorLagEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collecter Lag Event"
   ::= { vmwVRNIEvents 80517}

vmwCollectionLagEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collection Lag Event"
   ::= { vmwVRNIEvents 80518}

vmwGridProcessingLagEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Grid Processing Lag Event"
   ::= { vmwVRNIEvents 80519}

vmwConnectionErrorEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Connection Error Event"
   ::= { vmwVRNIEvents 80520}

vmwNodeNotActiveEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Node Not Active Event"
   ::= { vmwVRNIEvents 80521}

vmwHighDiskUtilizationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "High Disk Utilization Event"
   ::= { vmwVRNIEvents 80522}

vmwIndexingAbortedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Indexing Aborted Event"
   ::= { vmwVRNIEvents 80523}

vmwUpgradeFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Upgrade Failed Event"
   ::= { vmwVRNIEvents 80524}

vmwFlowProcessingSuspendedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Flow Processing Suspended Event"
   ::= { vmwVRNIEvents 80525}

vmwVCNotOnSameProxyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VC_NOT_ON_SAME_PROXY_EVENT"
   ::= { vmwVRNIEvents 80643}

vmwNoDVSAvailableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NO_DVS_AVAILABLE_EVENT"
   ::= { vmwVRNIEvents 80642}

vmwUnknownInfobloxVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Infoblox version cannot be determined"
   ::= { vmwVRNIEvents 80641}

vmwUnsupportedInfobloxVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The version of Infoblox is not supported"
   ::= { vmwVRNIEvents 80640}

vmwIncorrectInfobloxCredentialEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Invalid credentials or insufficient privileges"
   ::= { vmwVRNIEvents 80639}

vmwInfobloxRecordLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The number of A records fetched from Infoblox exceeds the current limit"
   ::= { vmwVRNIEvents 80638}

vmwWebhookNotRunningEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "WEBHOOK_NOT_RUNNING_EVENT"
   ::= { vmwVRNIEvents 80637}

vmwIncorrectWebhookConfiguredOnAlertEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "INCORRECT_WEBHOOK_CONFIGURED_ON_ALERT_EVENT"
   ::= { vmwVRNIEvents 80636}

vmwWebhookNotEnabledOnAlertEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "WEBHOOK_NOT_ENABLED_ON_ALERT_EVENT"
   ::= { vmwVRNIEvents 80635}

vmwVRNIContentPackNotInstalledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "vRNI_CONTENT_PACK_NOT_INSTALLED_EVENT"
   ::= { vmwVRNIEvents 80634}

vmwUnsupportedVRNIContentPackVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "UNSUPPORTED_vRNI_CONTENT_PACK_VERSION_EVENT"
   ::= { vmwVRNIEvents 80633}

vmwUnsupportedLogInsightVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "UNSUPPORTED_LOG_INSIGHT_VERSION_EVENT"
   ::= { vmwVRNIEvents 80632}

vmwComputeManagersNotAddedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "COMPUTE_MANAGERS_NOT_ADDED_EVENT"
   ::= { vmwVRNIEvents 80631}

vmwComputeManagersNotFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "COMPUTE_MANAGERS_NOT_FOUND_EVENT"
   ::= { vmwVRNIEvents 80630}

vmwUnsupportedNSXTVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "UNSUPPORTED_NSXT_VERSION_EVENT"
   ::= { vmwVRNIEvents 80629}

vmwNotEmptyNodeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NOT_EMPTY_NODE_EVENT"
   ::= { vmwVRNIEvents 80628}

vmwFlowPhysicalNodeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "FLOW_PHYSICAL_NODE_EVENT"
   ::= { vmwVRNIEvents 80627}

vmwFlowCollectionErrorEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "FLOW_COLLECTION_ERROR_EVENT"
   ::= { vmwVRNIEvents 8061313}

vmwAWSThrottlingExceptionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS_THROTTLING_EXCEPTION_EVENT"
   ::= { vmwVRNIEvents 8061314}

vmwAWSFlowLogAccessDeniedExceptionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "AWS_FLOW_LOG_ACCESS_DENIED_EXCEPTION_EVENT"
   ::= { vmwVRNIEvents 8061315}

vmwNSXIPFIXStatusMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX_IPFIX_STATUS_MISMATCH_EVENT"
   ::= { vmwVRNIEvents 80626}

vmwNumVMsOrHostsNotFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NUM_VMS_OR_HOSTS_NOT_FOUND_EVENT"
   ::= { vmwVRNIEvents 80625}

vmwUnsupportedNSXVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "UNSUPPORTED_NSX_VERSION_EVENT"
   ::= { vmwVRNIEvents 806100018}

vmwPwdAuthModeDisabledAristaEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PWD_AUTH_MODE_DISABLED_ARISTA_EVENT"
   ::= { vmwVRNIEvents 806100012}

vmwHostnameResolutionErrorEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HOSTNAME_RESOLUTION_ERROR_EVENT"
   ::= { vmwVRNIEvents 80624}

vmwPrimaryNSXNotAddedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PRIMARY_NSX_NOT_ADDED_EVENT"
   ::= { vmwVRNIEvents 80623}

vmwDataProviderNotRunningEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "DATA_PROVIDER_NOT_RUNNING_EVENT"
   ::= { vmwVRNIEvents 80622}

vmwInvalidResponseFromDatasourceEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "INVALID_RESPONSE_FROM_DATASOURCE_EVENT"
   ::= { vmwVRNIEvents 80621}

vmwHostNotReachableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HOST_NOT_REACHABLE_EVENT"
   ::= { vmwVRNIEvents 80620}

vmwNSXControllerNotFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX_CONTROLLER_NOT_FOUND_EVENT"
   ::= { vmwVRNIEvents 80619}

vmwUnexpectedDSTypeOrVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "UNEXPECTED_DS_TYPE_OR_VERSION_EVENT"
   ::= { vmwVRNIEvents 80618}

vmwWarnConfigEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "WARN_CONFIG_EVENT"
   ::= { vmwVRNIEvents 80617}

vmwInvalidConfigEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "INVALID_CONFIG_EVENT"
   ::= { vmwVRNIEvents 80616}

vmwNotFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NOT_FOUND_EVENT"
   ::= { vmwVRNIEvents 80614}

vmwInsufficientPrivilegesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "INSUFFICIENT_PRIVILEGES_EVENT"
   ::= { vmwVRNIEvents 80613}

vmwPwdAuthModeDisabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PWD_AUTH_MODE_DISABLED_EVENT"
   ::= { vmwVRNIEvents 80612}

vmwFailedCredsEncryptEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "FAILED_CREDS_ENCRYPT_EVENT"
   ::= { vmwVRNIEvents 80611}

vmwSNMPConnectionInvalidEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "SNMP_CONNECTION_INVALID_EVENT"
   ::= { vmwVRNIEvents 80609}

vmwUnknownHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "UNKNOWN_HOST_EVENT"
   ::= { vmwVRNIEvents 80608}

vmwInvalidCredentialsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "INVALID_CREDENTIALS_EVENT"
   ::= { vmwVRNIEvents 80606}

vmwIncorrectConnectionStringEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "INCORRECT_CONNECTION_STRING_EVENT"
   ::= { vmwVRNIEvents 80605}

vmwConnectionRefusedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "CONNECTION_REFUSED_EVENT"
   ::= { vmwVRNIEvents 80603}

vmwTimeoutEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "TIMEOUT_EVENT"
   ::= { vmwVRNIEvents 80602}

vmwFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "FAILED_EVENT"
   ::= { vmwVRNIEvents 80601}

vmwNSXTEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Event"
   ::= { vmwVRNIEvents 80200}

vmwNSXTVcNotAddedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VC Not Added As Data Source Event"
   ::= { vmwVRNIEvents 80201}

vmwNSXTStandaloneHostsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Standalone hosts added in NSX-T Event"
   ::= { vmwVRNIEvents 80202}

vmwLargeSdmsDroppedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Data Processing Error"
   ::= { vmwVRNIEvents 80526}

vmwNSXTIPFixDFWStatusNotEnabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_DFW_STATUS_NOT_ENABLED_EVENT"
   ::= { vmwVRNIEvents 80650}

vmwNSXTIPFixPortIncorrectEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_PORT_INCORRECT_EVENT"
   ::= { vmwVRNIEvents 80649}

vmwNSXTIPFixCollectorAndIPFixProfileMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_COLLECTOR_AND_IPFIX_PROFILE_MISMATCH_EVENT"
   ::= { vmwVRNIEvents 80648}

vmwNSXTIPFixIPFixProfilePriorityNotZeroEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_IPFIX_PROFILE_PRIORITY_NOT_ZERO_EVENT"
   ::= { vmwVRNIEvents 80647}

vmwNSXTIPFixNoIPFixProfileEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_NO_IPFIX_PROFILE_EVENT"
   ::= { vmwVRNIEvents 80646}

vmwNSXTIPFixNoNewCollectorProfileCanBeAddedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_NO_NEW_COLLECTOR_PROFILE_CAN_BE_ADDED_EVENT"
   ::= { vmwVRNIEvents 80645}

vmwNSXTIPFixNoCollectorProfileEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSXT_IPFIX_NO_COLLECTOR_PROFILE_EVENT"
   ::= { vmwVRNIEvents 80644}

vmwNSXTSystemEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "These are the alarms/events reported by NSX-T. 'Source Component' specifies the entity emmitting this event.
      It can be Manager/Controller/Edge. Combination of fields like Source Component, Event Type, Severity and message can be used to troubleshoot NSX-T appliance.
      For further information, log into NSX-T Manager UI and visit Dashboard"
   ::= { vmwVRNIEvents 80203}

vmwNSXTNoUplinkConnectivityEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Tier-1 logical router is disconnected from Tier-0 router. Networks under this router are not reachable from outside and vice versa.
      For more details, please log into VMware Aria Operations for Networks, navigate to Settings -> Events"
   ::= { vmwVRNIEvents 80205}

vmwNSXTRoutingAdvertisementEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Routing advertisement is disabled for NSX-T Tier-1 logical router. Networks under this router are not reachable from outside.
      For more details, please log into VMware Aria Operations for Networks, navigate to Settings -> Events"
   ::= { vmwVRNIEvents 80206}

vmwNSXTManagerConnectivityDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Node has lost manager connectivity.
       For more details, please log into VMware Aria Operations for Networks, navigate to Settings -> Events"
   ::= { vmwVRNIEvents 80207}

vmwNSXTControllerConnectivityDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Node is not able to communicate with one or more controllers.
      For more details, please log into VMware Aria Operations for Networks, navigate to Settings -> Events"
   ::= { vmwVRNIEvents 80208}

vmwNSXTControllerConnectivityDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Node is not able to communicate with any of the controllers.
      For more details, please log into VMware Aria Operations for Networks, navigate to Settings -> Events"
   ::= { vmwVRNIEvents 80209}

vmwNSXTMtuMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The MTU configured on interface(s) of Tier-0 logical router do not match with the interface(s) of uplink switch/router from same L2 network. This may impact network performance.
      For more details, please log into VMware Aria Operations for Networks, navigate to Settings -> Events"
   ::= { vmwVRNIEvents 80210}

vmwNSXEdgeBGPNeighbourDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more BGP neighbours are not in established state.
      For more details, please log into VMware Aria Operations for Networks, navigate to Settings -> Events"
   ::= { vmwVRNIEvents 36067}

vmwAnalyticsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Meta event for Analytics Event
      For more details, please log into VMware Aria Operations for Networks, navigate to Settings -> Events"
   ::= { vmwVRNIEvents 37001}

vmwAnalyticsOutlierEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Meta event for Outlier Events
      For more details, please log into VMware Aria Operations for Networks, navigate to Settings -> Events.
      "
   ::= { vmwVRNIEvents 37002}

vmwAnalyticsThresholdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Meta event for Threshold Events
      For more details, please log into VMware Aria Operations for Networks, navigate to Settings -> Events"
   ::= { vmwVRNIEvents 37003}

vmwVMCEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Meta event for VMC Events.
      For more details, please log into VMware Aria Operations for Networks, navigate to Settings -> Events"
   ::= { vmwVRNIEvents 38001}

vmwPolicyManagerVrniDfwIPFixCollectorAbsent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VMware Aria Operations for Networks IPFIX Collector is absent on VMC Policy Manager.
      For more details, please log into VMware Aria Operations for Networks, navigate to Settings -> Events"
   ::= { vmwVRNIEvents 80652}

vmwPolicyManagerNoDfwIPFixProfile NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "DFW IPFIX Profile is absent on VMC Policy Manager.
      For more details, please log into VMware Aria Operations for Networks, navigate to Settings -> Events."
   ::= { vmwVRNIEvents 80651}

vmwNSXTExcludedVmFlowEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more VMs are not protected by NSX-T DFW firewall. VMware Aria Operations for Networks will not receive IPFIX flows for these VMs.
      Remove the relevant logical switches, logical ports or security groups from the NSX-T firewall exclusion list to enable flows.
      For more details about this event, please log into VMware Aria Operations for Networks, navigate to Settings -> Events"
   ::= { vmwVRNIEvents 80211}

vmwNSXTDoubleVlanTaggingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Communication will be disrupted because Vlan on uplink port of Tier 0 router is different than Vlan on the external gateway.
      Vlan is misconfigured on the tier-0 router. Make sure Vlan matches with the Vlan on the external gateway.
      For more details about this event, please log into VMware Aria Operations for Networks, navigate to Settings -> Events"
   ::= { vmwVRNIEvents 80212}

vmwNSXTNoTzAttachedOnTnEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Transport node is not attached to any transport zone. VMs might loose connectivity because of this.
      Ensure that the transport node is attached to some transport zone.
      For more details about this event, please log into VMware Aria Operations for Networks, navigate to Settings -> Events"
   ::= { vmwVRNIEvents 80213}

vmwNSXTVtepDeleteEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "All vteps are deleted from the transport node. VMs might loose connectivity because of this.
      Make sure vteps/vmknics are not deleted from the transport node. You may check all available vteps/vmknics in NSX-T->Fabric Nodes->Transport Node->Monitor of each of the impacted transport nodes.
      For more details about this event, please log into VMware Aria Operations for Networks, navigate to Settings -> Events"
   ::= { vmwVRNIEvents 80214}

vmwDuplicateL3SwitchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Same Switch or Router is added with different IPs. VM to VM path may not be generated.
      Delete duplicate Switches or Routers from Data Source.
      For more details about this event, please log into VMware Aria Operations for Networks, navigate to Settings -> Events"
   ::= { vmwVRNIEvents 80215}

vmwLBPoolMemberDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when pool member of load balancer is down.
      Ensure that pool member has not been disabled by the administrator.
      Ensure that pool/pool-member uses the correct Health Monitors which are getting required responses from the backend server.
      Ensure that backend server used by this pool member is functional.
      For more details, log into Load Balancer UI, navigate to Local Traffic -> Pools -> Pools List.
      Also check documentation at https://support.f5.com/csp/article/K12531
      Alternatively, you can log into VMware Aria Operations for Networks UI and search 'Pool Member where state = DISABLED'.
      For more details about this event, please log into VMware Aria Operations for Networks, navigate to Settings -> Events"
   ::= { vmwVRNIEvents 80216}

vmwLBPoolDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when pool of load balancer is down.
      Ensure that pool has at least one functional pool member.
      For more details, log into Load Balancer UI, navigate to Local Traffic -> Pools
      Also check documentation at https://support.f5.com/csp/article/K12531
      For more details about this event, please log into VMware Aria Operations for Networks, navigate to Settings -> Events"
   ::= { vmwVRNIEvents 80217}

vmwLBPoolEmptyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when pool of load balancer is empty.
      Ensure that pool has at least one pool member.
      For more details, log into Load Balancer UI, navigate to Local Traffic -> Pools
      Also check documentation at https://support.f5.com/csp/article/K12531
      Alternatively, you can log into VMware Aria Operations for Networks and search 'Pool where PoolMembers Count = 0'.
      For more details about this event, please log into VMware Aria Operations for Networks, navigate to Settings -> Events"
   ::= { vmwVRNIEvents 80218}

vmwLBPoolMemberVMDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when VM associated with pool member of load balancer is down.
      Check if VM associated with pool member is powered on and running.
      For more details about this event, please log into VMware Aria Operations for Networks, navigate to Settings -> Events"
   ::= { vmwVRNIEvents 80219}

vmwLBVirtualServerDisableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when virtual server of load balancer is disabled.
      To enable virtual server, open load balancer GUI and check virtual server state.
      For more details about this event, please log into VMware Aria Operations for Networks, navigate to Settings -> Events"
   ::= { vmwVRNIEvents 80220}

vmwLBServiceNodeIPNotFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when no NIC associated with IP of service node of load balancer is found.
      Ensure that VM which has IP of Service Node exist.
      For more details about this event, please log into VMware Aria Operations for Networks, navigate to Settings -> Events"
   ::= { vmwVRNIEvents 80221}

vmwLBServiceNodeMultipleNicFoundEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when multiple NICs associated with IP of service node of load balancer are found.
      For more details about this event, please log into VMware Aria Operations for Networks, navigate to Settings -> Events."
   ::= { vmwVRNIEvents 80222}

vmwKubernetesInsufficientPrivilegesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more Kubernetes Cluster Service Accounts do not have sufficient privileges.
      Please verify that all Kubernetes Cluster Service Accounts has List and Watch privileges.
      Refer - https://kubernetes.io/docs/reference/access-authn-authz/rbac/#service-account-permissions
      For more details about this event, please log into VMware Aria Operations for Networks, navigate to Settings -> Events"
   ::= { vmwVRNIEvents 80655}

vmwPKSKubernetesUnknownHostEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Please verify the Kubernetes Cluster API Servers are reachable from Collector VM.
      For more details about this event, please log into VMware Aria Operations for Networks, navigate to Settings -> Events"
   ::= { vmwVRNIEvents 80654}

vmwDatasourceIdentificationChangedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The data source identity information such as certificate or the key has changed.
      Re-verify the identity information on data source page in VMware Aria Operations for Networks.
      System will auto accept the new identification. If issue persists for more than an hour, please contact support.
      For more details about this event, please log into VMware Aria Operations for Networks, navigate to Settings -> Events"
   ::= { vmwVRNIEvents 80653}

vmwArkinApplicationMemberLimitEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Number of members in application exceeds supported limit.
      Reduce number of members in the application.
      For more details about this event, please log into VMware Aria Operations for Networks, navigate to Settings -> Events"
   ::= { vmwVRNIEvents 568}

vmwNSXTSwitchIpfixEnabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VMware Aria Operations for Networks does not support the IPFIX flow data from NSX-T Switches. It is configured to send IPFIX data to one of the VMware Aria Operations for Networks Collector VM. It may have corrupted existing flow data in the system.
      Remove VMware Aria Operations for Networks Collector VM IP Address from the NSX-T Switch collector profiles which are used in NSX-T Switch IPFIX profiles.
      For more details about this event, please log into VMware Aria Operations for Networks, navigate to Settings -> Events"
   ::= { vmwVRNIEvents 80223}

vmwUANIFileNotProvidedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Configuration file required by Generic Routers & Switches Data Source has not been provided while data source creation. To resolve this issue, please go to VMware Aria Operations for Networks web UI, under settings page, edit intended Generic Routers & Switches Data Source and add configuration file.
      For more details about this event, please log into VMware Aria Operations for Networks, navigate to Settings -> Events"
   ::= { vmwVRNIEvents 80657}

vmwUANIFileDoesNotExistEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Configuration file required by Generic Routers & Switches Data Source has been deleted manually or moved. To resolve this issue, please go to VMware Aria Operations for Networks web UI, under settings page, edit intended Generic Routers & Switches Data Source and add configuration file.
      For more details about this event, please log into VMware Aria Operations for Networks, navigate to Settings -> Events"
   ::= { vmwVRNIEvents 80658}

vmwNSXTStandaloneHostsWithoutVcEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "vCenter managing one or more fabric nodes in NSX-T is not added as a data source in VMware Aria Operations for Networks. Virtual Machines on those hosts will not be visible in VMware Aria Operations for Networks.
      Please add the vCenter server managing the standalone hosts as a datasource into VMware Aria Operations for Networks at- Settings -> Accounts and Data Sources -> Add Source -> VMware vCenter
      For more details about this event, please log into VMware Aria Operations for Networks, navigate to Settings -> Events"
   ::= { vmwVRNIEvents 80224}

vmwApplianceNotConfiguredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Collector VM configuration is incomplete.
      To reconfigure proxy, please run 'setup' CLI from console mode.
      https://docs.vmware.com/en/VMware-vRealize-Network-Insight/3.8/com.vmware.vrni.cli.doc/GUID-B48AD03A-5FC8-4396-9C27-9523307C688C.html
      For more details about this event, please log into VMware Aria Operations for Networks, navigate to Settings -> Events"
   ::= { vmwVRNIEvents 80527}

vmwSwitchPortOperationalDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Switchport operational status change detected. It is operationally down. This may impact the network traffic on the device.
      For more details about this event, please log into VMware Aria Operations for Networks, navigate to Settings -> Events"
   ::= { vmwVRNIEvents 30111}

vmwRouterInterfaceOperationalDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Router interface operational status change detected. It is operationally down. This may impact the network traffic on the device.
      For more details about this event, please log into VMware Aria Operations for Networks, navigate to Settings -> Events"
   ::= { vmwVRNIEvents 30112}

vmwUnderlayDeviceGenericEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This is generic representation for events on Underlay device.
      For more details about this event, please log into VMware Aria Operations for Networks, navigate to Settings -> Events"
   ::= { vmwVRNIEvents 30114}

vmwUnderlayDeviceFexOfflineEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A FEX has gone offline on the device. Please check the FEX status on the device. This may impact the network traffic on the device.
      For more details about this event, please log into VMware Aria Operations for Networks, navigate to Settings -> Events"
   ::= { vmwVRNIEvents 30115}

vmwUnderlayDeviceFanMalFunctionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A fan on the device is not either removed or not working. It may impact the overheating of the device.
      For more details about this event, please log into VMware Aria Operations for Networks, navigate to Settings -> Events"
   ::= { vmwVRNIEvents 30116}

vmwUnderlayDeviceTemperatureThresholdExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A module on the device has reported major/minor temperature alarm. Please check the sensor mentioned in the event message on the device.
      For more details about this event, please log into VMware Aria Operations for Networks, navigate to Settings -> Events"
   ::= { vmwVRNIEvents 30117}

vmwUnderlayDeviceFexFanMalFunctionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A fan on the FEX chassis is either removed or not working. It may impact the overheating of the FEX device.
      For more details about this event, please log into VMware Aria Operations for Networks, navigate to Settings -> Events"
   ::= { vmwVRNIEvents 30118}

vmwUnderlayDeviceFexPsMalFunctionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A Power supply on the FEX chassis is either removed or not working. It may impact the FEX device functionality.
      For more details about this event, please log into VMware Aria Operations for Networks, navigate to Settings -> Events"
   ::= { vmwVRNIEvents 30119}

vmwUnderlayDeviceModuleMalFunctionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A module/line card on the device is either removed or not working. This may impact the network traffic on the device.
      For more details about this event, please log into VMware Aria Operations for Networks, navigate to Settings -> Events"
   ::= { vmwVRNIEvents 30120}

vmwUnderlayDevicePsMalFunctionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A Power supply on the device is either removed or not working. It may impact the device functionality.
      For more details about this event, please log into VMware Aria Operations for Networks, navigate to Settings -> Events"
   ::= { vmwVRNIEvents 30121}

vmwUnderlayDeviceBfdSessionRemovedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A BFD session is deleted on the device. This will result in routing table changes and may impact the network traffic on the device.
      For more details about this event, please log into VMware Aria Operations for Networks, navigate to Settings -> Events"
   ::= { vmwVRNIEvents 30122}

vmwUnderlayDeviceLldpNeighbourRemovedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A LLDP neighbour is removed from the device. This will result in the network topology changes and may impact the network traffic on the device.
      For more details about this event, please log into VMware Aria Operations for Networks, navigate to Settings -> Events"
   ::= { vmwVRNIEvents 30123}

vmwThresholdExceededEventDataSourceCpuUsage NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A threshold-crossing CPU usage detected on host FRUs.
      For more details about this event, please log into VMware Aria Operations for Networks, navigate to Settings -> Events"
   ::= { vmwVRNIEvents 30198}

vmwThresholdExceededEventDataSourceMemoryUsage NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A threshold-crossing memory usage detected on host FRUs.
      For more details about this event, please log into VMware Aria Operations for Networks, navigate to Settings -> Events"
   ::= { vmwVRNIEvents 30199}

vmwThresholdExceededEventDataSourceTemperature NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "A threshold-crossing temperature detected on host FRUs.
      For more details about this event, please log into VMware Aria Operations for Networks, navigate to Settings -> Events"
   ::= { vmwVRNIEvents 30200}

vmwDeploymentDefMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Capacity configuration is mismatched. Please reconfigure.
      For more details about this event, please log into VMware Aria Operations for Networks, navigate to Settings -> Events"
   ::= { vmwVRNIEvents 80532}

vmwNsxtLatencyServiceConfigMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The Latency Service Config configured on NSX-T is different from this VMware Aria Operations for Networks deployment. As a result, VMware Aria Operations for Networks is not receiving Latency information from NSX-T.
      For more details about this event, please log into VMware Aria Operations for Networks, navigate to Settings -> Events"
   ::= { vmwVRNIEvents 80669}

vmwNsxtLatencyNodeGroupMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The Latency Node Group configured on NSX-T is different from this VMware Aria Operations for Networks deployment. As a result, VMware Aria Operations for Networks is not receiving Latency information from NSX-T.
      For more details about this event, please log into VMware Aria Operations for Networks, navigate to Settings -> Events"
   ::= { vmwVRNIEvents 80668}

vmwNsxtLatencyStatProfileMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The Latency Stat profile configured on NSX-T is different from this VMware Aria Operations for Networks deployment. As a result, VMware Aria Operations for Networks is not receiving Latency information from NSX-T.
      For more details about this event, please log into VMware Aria Operations for Networks, navigate to Settings -> Events"
   ::= { vmwVRNIEvents 80667}

vmwHybridConnectBgpStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when BGP status is Down.
      For more details about this event, please log into VMware Aria Operations for Networks, navigate to Settings -> Events"
   ::= { vmwVRNIEvents 1279}

vmwNSXTClusterBackUpDisabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Manager backup is not scheduled.
      For more details about this event, please log into VMware Aria Operations for Networks, navigate to Settings -> Events"
   ::= { vmwVRNIEvents 80256}

vmwNSXTDFWFirewallDisabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Distributed Firewall is disabled in the NSX-T Manager.
      For more details about this event, please log into VMware Aria Operations for Networks, navigate to Settings -> Events"
   ::= { vmwVRNIEvents 80257}

vmwNSXTComputeManagerConnectionStatusNotUpEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Compute Manager Connection status is not up.
      For more details about this event, please log into VMware Aria Operations for Networks, navigate to Settings -> Events"
   ::= { vmwVRNIEvents 80255}

vmwNSXTLogicalSwitchAdminStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Logical Switch Admin Status is 'Down'.
      For more details about this event, please log into VMware Aria Operations for Networks, navigate to Settings -> Events"
   ::= { vmwVRNIEvents 80252}

vmwNSXTLogicalPortOperationalStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Logical Port Operational Status is 'Down'. This could cause a communication failure between two virtual interfaces (VIFs) that are connected to the same logical switch, for example, you cannot ping one VM from another.
      For more details about this event, please log into VMware Aria Operations for Networks, navigate to Settings -> Events"
   ::= { vmwVRNIEvents 80253}

vmwNSXTLogicalPortOperationalStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Logical Port Operational Status is 'Unknown'. This could cause a communication failure between two virtual interfaces (VIFs) that are connected to the same logical switch, for example, you cannot ping one VM from another.
      For more details about this event, please log into VMware Aria Operations for Networks, navigate to Settings -> Events"
   ::= { vmwVRNIEvents 80254}

vmwNSXTLogicalPortReceivedPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Received packets are getting dropped on the NSX-T Logical Port and associated entities might get affected.
      For more details about this event, please log into VMware Aria Operations for Networks, navigate to Settings -> Events"
   ::= { vmwVRNIEvents 80258}

vmwNSXTLogicalPortTransmittedPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Transmitted packets are getting dropped on the NSX-T Logical Port and associated entities might get affected.
      For more details about this event, please log into VMware Aria Operations for Networks, navigate to Settings -> Events"
   ::= { vmwVRNIEvents 80259}

vmwNSXTLogicalSwitchReceivedPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Received packets are getting dropped on the NSX-T Logical Switch and associated entities might get affected.
      For more details about this event, please log into VMware Aria Operations for Networks, navigate to Settings -> Events"
   ::= { vmwVRNIEvents 80260}

vmwNSXTLogicalSwitchTransmittedPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Transmitted packets are getting dropped on the NSX-T Logical Switch and associated entities might get affected.
      For more details about this event, please log into VMware Aria Operations for Networks, navigate to Settings -> Events"
   ::= { vmwVRNIEvents 80261}

vmwNSXTRxPacketDropOnMPNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Received packets are getting dropped on NSX-T Management Node's network interface. This may impact the network traffic related to NSX-T management cluster.
      For more details about this event, please log into VMware Aria Operations for Networks, navigate to Settings -> Events"
   ::= { vmwVRNIEvents 80262}

vmwNSXTRxPacketDropOnEdgeTnNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Received packets are getting dropped on NSX-T Edge Node's network interface. This may impact the network traffic of edge cluster.
      For more details about this event, please log into VMware Aria Operations for Networks, navigate to Settings -> Events"
   ::= { vmwVRNIEvents 80263}

vmwNSXTRxPacketDropOnHostTnNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Received packets are getting dropped on NSX-T Host Node's network interface. This may impact the network traffic on ESXi Host.
      For more details about this event, please log into VMware Aria Operations for Networks, navigate to Settings -> Events"
   ::= { vmwVRNIEvents 80264}

vmwNSXTTxPacketDropOnMPNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Transmitted packets are getting dropped on NSX-T Management Node's network interface. This may impact the network traffic related to NSX-T management cluster.
      For more details about this event, please log into VMware Aria Operations for Networks, navigate to Settings -> Events"
   ::= { vmwVRNIEvents 80265}

vmwNSXTTxPacketDropOnEdgeTnNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Transmitted packets are getting dropped on NSX-T Edge Node's network interface. This may impact the network traffic of edge cluster.
      For more details about this event, please log into VMware Aria Operations for Networks, navigate to Settings -> Events"
   ::= { vmwVRNIEvents 80266}

vmwNSXTTxPacketDropOnHostTnNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Transmitted packets are getting dropped on NSX-T Host Node's network interface. This may impact the network traffic on ESXi Host.
      For more details about this event, please log into VMware Aria Operations for Networks, navigate to Settings -> Events"
   ::= { vmwVRNIEvents 80267}

vmwNSXTMPNodeServiceClusterManagerStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Cluster Manager Service has stopped running.
      For more details about this event, please log into VMware Aria Operations for Networks, navigate to Settings -> Events"
   ::= { vmwVRNIEvents 80424}

vmwNSXTMPNodeServiceCmInventoryStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely CM Inventory Service has stopped running.
      For more details about this event, please log into VMware Aria Operations for Networks, navigate to Settings -> Events"
   ::= { vmwVRNIEvents 80402}

vmwNSXTMPNodeServiceControllerStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Controller Service has stopped running.
      For more details about this event, please log into VMware Aria Operations for Networks, navigate to Settings -> Events"
   ::= { vmwVRNIEvents 80403}

vmwNSXTMPNodeServiceDataStoreStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely DataStore Service has stopped running.
      For more details about this event, please log into VMware Aria Operations for Networks, navigate to Settings -> Events"
   ::= { vmwVRNIEvents 80404}

vmwNSXTMPNodeServiceHttpStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely HTTP Service has stopped running.
      For more details about this event, please log into VMware Aria Operations for Networks, navigate to Settings -> Events"
   ::= { vmwVRNIEvents 80405}

vmwNSXTMPNodeServiceInstallUpgradeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Install Upgrade Service has stopped running.
      For more details about this event, please log into VMware Aria Operations for Networks, navigate to Settings -> Events"
   ::= { vmwVRNIEvents 80406}

vmwNSXTMPNodeServiceLiagentStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely LI Agent Service has stopped running.
      For more details about this event, please log into VMware Aria Operations for Networks, navigate to Settings -> Events"
   ::= { vmwVRNIEvents 80407}

vmwNSXTMPNodeServiceManagerStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Manager Service has stopped running.
      For more details about this event, please log into VMware Aria Operations for Networks, navigate to Settings -> Events"
   ::= { vmwVRNIEvents 80408}

vmwNSXTMPNodeServiceMgmtPlaneBusStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Management Plane Bus Service has stopped running.
      For more details about this event, please log into VMware Aria Operations for Networks, navigate to Settings -> Events"
   ::= { vmwVRNIEvents 80409}

vmwNSXTMPNodeServiceMigrationCoordinatorStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Migration Co-ordinator Service has stopped running.
      For more details about this event, please log into VMware Aria Operations for Networks, navigate to Settings -> Events"
   ::= { vmwVRNIEvents 80410}

vmwNSXTMPNodeServiceNodeMgmtStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Node Management Service has stopped running.
      For more details about this event, please log into VMware Aria Operations for Networks, navigate to Settings -> Events"
   ::= { vmwVRNIEvents 80411}

vmwNSXTMPNodeServiceNodeStatsStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Node Statistics has stopped running.
      For more details about this event, please log into VMware Aria Operations for Networks, navigate to Settings -> Events"
   ::= { vmwVRNIEvents 80412}

vmwNSXTMPNodeServiceNSXMessageBusStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Message Bus Service has stopped running.
      For more details about this event, please log into VMware Aria Operations for Networks, navigate to Settings -> Events"
   ::= { vmwVRNIEvents 80413}

vmwNSXTMPNodeServiceNSXPlatformClientStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Platform Client Service has stopped running.
      For more details about this event, please log into VMware Aria Operations for Networks, navigate to Settings -> Events"
   ::= { vmwVRNIEvents 80414}

vmwNSXTMPNodeServiceNSXUpgradeAgentStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Upgrade Agent Service has stopped running.
      For more details about this event, please log into VMware Aria Operations for Networks, navigate to Settings -> Events"
   ::= { vmwVRNIEvents 80415}

vmwNSXTMPNodeServiceNTPStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely NTP Service has stopped running.
      For more details about this event, please log into VMware Aria Operations for Networks, navigate to Settings -> Events"
   ::= { vmwVRNIEvents 80416}

vmwNSXTMPNodeServicePolicyStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Policy Service has stopped running.
      For more details about this event, please log into VMware Aria Operations for Networks, navigate to Settings -> Events"
   ::= { vmwVRNIEvents 80417}

vmwNSXTMPNodeServiceSearchStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Search Service has stopped running.
      For more details about this event, please log into VMware Aria Operations for Networks, navigate to Settings -> Events"
   ::= { vmwVRNIEvents 80418}

vmwNSXTMPNodeServiceSNMPStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely SNMP Service has stopped running.
      For more details about this event, please log into VMware Aria Operations for Networks, navigate to Settings -> Events"
   ::= { vmwVRNIEvents 80419}

vmwNSXTMPNodeServiceSSHStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely SSH Service has stopped running.
      For more details about this event, please log into VMware Aria Operations for Networks, navigate to Settings -> Events"
   ::= { vmwVRNIEvents 80420}

vmwNSXTMPNodeServiceSyslogStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Syslog Service has stopped running.
      For more details about this event, please log into VMware Aria Operations for Networks, navigate to Settings -> Events"
   ::= { vmwVRNIEvents 80421}

vmwNSXTMPNodeServiceTelemetryStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely Telemetry Service has stopped running.
      For more details about this event, please log into VMware Aria Operations for Networks, navigate to Settings -> Events"
   ::= { vmwVRNIEvents 80422}

vmwNSXTMPNodeServiceUIServiceStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One of the Services of the NSX-T Management Node, namely UI Service has stopped running.
      For more details about this event, please log into VMware Aria Operations for Networks, navigate to Settings -> Events"
   ::= { vmwVRNIEvents 80423}

vmwVMCHostPerClusterLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when the number of Hosts per Cluster in a VMC SDDC exceeds limit.
      For more details about this event, please log into VMware Aria Operations for Networks, navigate to Settings -> Events"
   ::= { vmwVRNIEvents 100053}

vmwVMCVMPerHostLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when the number of VMs per Host in a VMC SDDC exceeds limits.
      For more details about this event, please log into VMware Aria Operations for Networks, navigate to Settings -> Events"
   ::= { vmwVRNIEvents 100054}

vmwVMCClusterLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when the number of Clusters in a VMC SDDC exceeds limits.
      For more details about this event, please log into VMware Aria Operations for Networks, navigate to Settings -> Events"
   ::= { vmwVRNIEvents 100055}

vmwProtectionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This event is raised when any system protection limit is exceeded
      For more details about this event, please log into VMware Aria Operations for Networks, navigate to Settings -> Events"
   ::= { vmwVRNIEvents 100061}

vmwSwitchPortUptimeThresholdRecededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Up time of switch is less than expected.
      Check the operational status of the specified switch port.
      For more details about this event, please log into VMware Aria Operations for Networks, navigate to Settings -> Events"
   ::= { vmwVRNIEvents 30110}

vmwFdbConfigStoreCleanupFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Foundation Database (FDB) Config Store Cleanup Failed Event.
      Data Retention (Config Store Maintenance) service is not healthy.
      For more details about this event, please log into VMware Aria Operations for Networks, navigate to Settings -> Events"
   ::= { vmwVRNIEvents 80531}

vmwDiskAllocationInsufficientEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Appliance Disk not configured according to Disk Guidance.
      https://docs.vmware.com/en/VMware-vRealize-Network-Insight/5.1/com.vmware.vrni.using.doc/GUID-C96E9C78-6FA2-49EB-9791-8967A89B7698.html
      For more details about this event, please log into VMware Aria Operations for Networks, navigate to Settings -> Events"
   ::= { vmwVRNIEvents 80528}

vmwNSXTControllerNodeToControlClusterConnectivityEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T controller node has no control cluster connectivity.
      Check if the node has proper network connectivity with control cluster.
      For more details about this event, please log into VMware Aria Operations for Networks, navigate to Settings -> Events"
   ::= { vmwVRNIEvents 80225}

vmwNSXTControllerNodeToMgmtPlaneConnectivityEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T controller node has no management plane connectivity.
      Check if the node has proper network connectivity with management plane.
      For more details about this event, please log into VMware Aria Operations for Networks, navigate to Settings -> Events"
   ::= { vmwVRNIEvents 80226}

vmwNSXTMPNodeToMgmtClusterConnectivityEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T management node has no management cluster connectivity.
      Check if the node has proper network connectivity with management cluster.
      For more details about this event, please log into VMware Aria Operations for Networks, navigate to Settings -> Events"
   ::= { vmwVRNIEvents 80227}

vmwBigIpInsufficientShellAccessEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "No access to shell(ssh port 22) for F5 Load Balancer. VMware Aria Operations for Networks will not be able to fetch any information required for visibility.
      For more details about this event, please log into VMware Aria Operations for Networks, navigate to Settings -> Events"
   ::= { vmwVRNIEvents 80663}

vmwBigIpInsufficientPartitionAccessEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Insufficient Partition Access for F5 Load Balancer. VMware Aria Operations for Networks will not be able to fetch any information required for visibility.
      For more details about this event, please log into VMware Aria Operations for Networks, navigate to Settings -> Events"
   ::= { vmwVRNIEvents 80664}

vmwBigIpInsufficientRoleEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Insufficient Role for F5 Load Balancer. VMware Aria Operations for Networks will not be able to fetch any information required for visibility.
      For more details about this event, please log into VMware Aria Operations for Networks, navigate to Settings -> Events"
   ::= { vmwVRNIEvents 80665}

vmwNSXTLatencyCollectorMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The collector configured on NSX-T is different from this VMware Aria Operations for Networks deployment. As a result, VMware Aria Operations for Networks is not receiving Latency information from NSX-T.
      For more details about this event, please log into VMware Aria Operations for Networks, navigate to Settings -> Events"
   ::= { vmwVRNIEvents 80662}

vmwNSXTLatencyNoBFDProfileEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T, no BFD profile configured Event.
      BFD profile was deleted on NSX-T Manager after 'Virtual infrastructure Latency' was enabled at VMware Aria Operations for Networks. As a result, VMware Aria Operations for Networks is not assigning BFD profile on Transport zone. VMware Aria Operations for Networks will not receive Latency information from new transport zones.
      For more details about this event, please log into VMware Aria Operations for Networks, navigate to Settings -> Events"
   ::= { vmwVRNIEvents 80661}

vmwNSXTLatencyNotEnabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T latency collection is not enabled.
      Latency collection was disabled in the NSX-T Manager after it was enabled by VMware Aria Operations for Networks. As a result, VMware Aria Operations for Networks is not receiving latency information from the NSX-T.
      For more details about this event, please log into VMware Aria Operations for Networks, navigate to Settings -> Events"
   ::= { vmwVRNIEvents 80659}

vmwHardwareVTEPMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hardware Gateway Bindings Mismatch between NSX and switch.
      For more details about this event, please log into VMware Aria Operations for Networks, navigate to Settings -> Events"
   ::= { vmwVRNIEvents 80301}

vmwHardwareVTEPPortDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hardware Gateway Binding Switch Port is down.
      For more details about this event, please log into VMware Aria Operations for Networks, navigate to Settings -> Events"
   ::= { vmwVRNIEvents 80302}

vmwNSXVLatencyNoDataEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VMware Aria Operations for Networks Collector VM is not receiving network latency metrics from host.
      For more details about this event, please log into VMware Aria Operations for Networks, navigate to Settings -> Events"
   ::= { vmwVRNIEvents 100001}

vmwKubernetesBaseEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Event reported by kubernetes cluster. This is Kubernetes System Event.
      For more details about this event, please log into VMware Aria Operations for Networks, navigate to Settings -> Events"
   ::= { vmwVRNIEvents 1510}

vmwVMCVMLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Number of VMs in VMC SDDC exceeds limit.
      This event is raised when the number of VMs in a VMC SDDC exceeds limits.
      Delete VMs that are not in use.
      For more details about this event, please log into VMware Aria Operations for Networks, navigate to Settings -> Events"
   ::= { vmwVRNIEvents 100051}

vmwVMCHostLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Number of Hosts in VMC SDDC exceeds limit.
      This event is raised when the number of Hosts in a VMC SDDC exceeds limits.
      Contact VMC Support to increase the host limit within the VMC SDDC.
      For more details about this event, please log into VMware Aria Operations for Networks, navigate to Settings -> Events"
   ::= { vmwVRNIEvents 100052}

vmwVeloCloudEdgeDegradedTransQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge Transactional QOE has degraded.
      Verify that the Edge is in healthy state.
      For more details about this event, please log into VMware Aria Operations for Networks, navigate to Settings -> Events"
   ::= { vmwVRNIEvents 90012}

vmwVeloCloudEdgeDegradedVideoQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge Video QOE has Degraded.
      Verify that the Edge is in healthy state.
      For more details about this event, please log into VMware Aria Operations for Networks, navigate to Settings -> Events"
   ::= { vmwVRNIEvents 90011}

vmwVeloCloudEdgeDegradedVoiceQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge Voice QOE has Degraded.
      Verify that the Edge is in healthy state.
      For more details about this event, please log into VMware Aria Operations for Networks, navigate to Settings -> Events"
   ::= { vmwVRNIEvents 90010}

vmwVeloCloudEdgeDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge is not connected.
      Verify that the VeloCloud Edge is UP.
      For more details about this event, please log into VMware Aria Operations for Networks, navigate to Settings -> Events"
   ::= { vmwVRNIEvents 90001}

vmwVeloCloudLinkLostPacketEventRx NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Received Packet Loss observed on VeloCloud Link.
      Verify that the Link is in healthy state.
      For more details about this event, please log into VMware Aria Operations for Networks, navigate to Settings -> Events"
   ::= { vmwVRNIEvents 90013}

vmwVeloCloudLinkDegradedTransQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Link Transactional QOE has Degraded.
      Verify that the Link is in healthy state.
      For more details about this event, please log into VMware Aria Operations for Networks, navigate to Settings -> Events"
   ::= { vmwVRNIEvents 90009}

vmwVeloCloudLinkLostPacketEventTx NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Transmitted Packet Loss observed on VeloCloud Link.
      Verify that the Link is in healthy state.
      For more details about this event, please log into VMware Aria Operations for Networks, navigate to Settings -> Events"
   ::= { vmwVRNIEvents 90005}

vmwVeloCloudLinkDegradedVideoQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Link Video QOE has Degraded.
      Verify that the Link is in healthy state.
      For more details about this event, please log into VMware Aria Operations for Networks, navigate to Settings -> Events"
   ::= { vmwVRNIEvents 90008}

vmwVeloCloudLinkDegradedVoiceQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Link Voice QOE has Degraded.
      Verify that the Link is in healthy state.
      For more details about this event, please log into VMware Aria Operations for Networks, navigate to Settings -> Events"
   ::= { vmwVRNIEvents 90007}

vmwVeloCloudLinkDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge is not connected.
      Verify that the VeloCloud Link is UP.
      For more details about this event, please log into VMware Aria Operations for Networks, navigate to Settings -> Events"
   ::= { vmwVRNIEvents 90002}

vmwNSXTHostNodeMgmtConnectivityStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node has lost connectivity with NSX-T Manager node.
      Please ensure all the interfaces connecting the NSX-T Transport Node to manager are up.
      For more details about this event, please log into VMware Aria Operations for Networks, navigate to Settings -> Events"
   ::= { vmwVRNIEvents 80246}

vmwNSXTEdgeNodeCtlrConnectivityStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Node Controller connectivity is Unknown.
      NSX-T Manager can't determine the status of the Edge Transport Node's connectivity with controller nodes
      Please ensure all the interfaces connecting the NSX-T Transport Node to manager are up.
      For more details about this event, please log into VMware Aria Operations for Networks, navigate to Settings -> Events"
   ::= { vmwVRNIEvents 80247}

vmwNSXTHostNodeCtlrConnectivityStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Node is not able to communicate with any of the controllers.
      NSX-T Host Transport Node has lost connectivity with all the controller nodes
      Please ensure all the interfaces connecting the NSX-T Transport Node to controller nodes are up.
      For more details about this event, please log into VMware Aria Operations for Networks, navigate to Settings -> Events"
   ::= { vmwVRNIEvents 80248}

vmwNSXTHostNodeCtlrConnectivityStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Node is not able to to communicate with one or more controllers.
      NSX-T Host Transport Node has lost connectivity with some (but not all) of the controller nodes
      Please ensure all the interfaces connecting the NSX-T Transport Node to controller nodes are up.
      For more details about this event, please log into VMware Aria Operations for Networks, navigate to Settings -> Events"
   ::= { vmwVRNIEvents 80249}

vmwNSXTHostNodeCtlrConnectivityStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Node Controller connectivity is Unknown.
      NSX-T Manager can't determine the status of the Host Transport Node's connectivity with controller nodes
      Please ensure all the interfaces connecting the NSX-T Transport Node to controller nodes are up.
      For more details about this event, please log into VMware Aria Operations for Networks, navigate to Settings -> Events"
   ::= { vmwVRNIEvents 80250}

vmwNSXTHostNodePnicStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Pnic Status is 'Down'.
      All the pNICs of the NSX-T Host transport Node are down.
      Please check if all the pNICs are properly connected.
      For more details about this event, please log into VMware Aria Operations for Networks, navigate to Settings -> Events"
   ::= { vmwVRNIEvents 80228}

vmwNSXTHostNodePnicStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Pnic Status is 'Degraded'
      Some of the pNICs of the NSX-T Host transport Node are down.
      Please check if all the pNICs are properly connected.
      For more details about this event, please log into VMware Aria Operations for Networks, navigate to Settings -> Events"
   ::= { vmwVRNIEvents 80229}

vmwNSXTHostNodePnicStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Pnic Status is 'Unknown'.
      NSX-T Manager can't determine the status of some or all of the pNICs of the NSX-T Host Transport Node
      Please check if all the pNICs are properly connected.
      For more details about this event, please log into VMware Aria Operations for Networks, navigate to Settings -> Events"
   ::= { vmwVRNIEvents 80230}

vmwNSXTEdgeNodePnicStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Pnic Status is 'Down'.
      All the pNICs of the NSX-T Edge transport Node are down.
      Please check if all the pNICs are properly connected.
      For more details about this event, please log into VMware Aria Operations for Networks, navigate to Settings -> Events"
   ::= { vmwVRNIEvents 80237}

vmwNSXTEdgeNodePnicStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Pnic Status is 'Degraded'.
      Some of the pNICs of the NSX-T Edge transport Node are down.
      Please check if all the pNICs are properly connected.
      For more details about this event, please log into VMware Aria Operations for Networks, navigate to Settings -> Events"
   ::= { vmwVRNIEvents 80238}

vmwNSXTEdgeNodePnicStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Pnic Status is 'Unknown'.
      NSX-T Manager can't determine the status of some or all of the pNICs of the NSX-T Edge Transport Node
      Please check if all the pNICs are properly connected.
      For more details about this event, please log into VMware Aria Operations for Networks, navigate to Settings -> Events"
   ::= { vmwVRNIEvents 80239}

vmwNSXTHostNodeTunnelStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Tunnel Status is 'Down'.
      All the tunnel interfaces associated to the NSX-T Host transport Node are down.
      Please check the status of the tunnel interfaces for this NSX-T Transport Node
      For more details about this event, please log into VMware Aria Operations for Networks, navigate to Settings -> Events"
   ::= { vmwVRNIEvents 80231}

vmwNSXTHostNodeTunnelStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Tunnel Status is 'Degraded'.
      Some of the tunnel interfaces associated to the NSX-T Host transport Node are down.
      Please check the status of the tunnel interfaces for this NSX-T Transport Node
      For more details about this event, please log into VMware Aria Operations for Networks, navigate to Settings -> Events"
   ::= { vmwVRNIEvents 80232}

vmwNSXTHostNodeTunnelStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Tunnel Status is 'Unknown'.
      NSX-T Manager can't determine the status of some or all of the tunnel interfaces associated to the NSX-T Host Transport Node.
      Please check the status of the tunnel interfaces for this NSX-T Transport Node
      For more details about this event, please log into VMware Aria Operations for Networks, navigate to Settings -> Events"
   ::= { vmwVRNIEvents 80233}

vmwNSXTEdgeNodeTunnelStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Tunnel Status is 'Down'.
      All the tunnel interfaces associated to the NSX-T Edge transport Node are down.
      Please check the status of the tunnel interfaces for this NSX-T Transport Node
      For more details about this event, please log into VMware Aria Operations for Networks, navigate to Settings -> Events"
   ::= { vmwVRNIEvents 80240}

vmwNSXTEdgeNodeTunnelStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Tunnel Status is 'Degraded'.
      Some of the tunnel interfaces associated to the NSX-T Edge transport Node are down.
      Please check the status of the tunnel interfaces for this NSX-T Transport Node
      For more details about this event, please log into VMware Aria Operations for Networks, navigate to Settings -> Events"
   ::= { vmwVRNIEvents 80241}

vmwNSXTEdgeNodeTunnelStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Tunnel Status is 'Unknown'.
      NSX-T Manager can't determine the status of some or all of the tunnel interfaces associated to the NSX-T Edge Transport Node
      Please check the status of the tunnel interfaces for this NSX-T Transport Node
      For more details about this event, please log into VMware Aria Operations for Networks, navigate to Settings -> Events"
   ::= { vmwVRNIEvents 80242}

vmwNSXTHostNodeStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Roll-up Status is 'Down'.
      Some or all of the pNICs, management connection, control connections, tunnel statuses, agent statuses of NSX-T Host Transport Node are down.
      Please check the status of the pNICs, management & control connections, tunnels and agents for this NSX-T Transport Node.
      For more details about this event, please log into VMware Aria Operations for Networks, navigate to Settings -> Events"
   ::= { vmwVRNIEvents 80234}

vmwNSXTHostNodeStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Roll-up Status is 'Degraded'.
      Some or all of the pNICs, management connection, control connections, tunnel statuses, agent statuses of NSX-T Host Transport Node are in degraded state.
      Please check the status of the pNICs, management & control connections, tunnels and agents for this NSX-T Transport Node.
      For more details about this event, please log into VMware Aria Operations for Networks, navigate to Settings -> Events"
   ::= { vmwVRNIEvents 80235}

vmwNSXTHostNodeStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Transport Node Roll-up Status is 'Unknown'.
      NSX-T Manager can't determine the status of some or all of the pNICs, management connection, control connections, tunnel statuses, agent statuses of NSX-T Host Transport Node.
      Please check the status of the pNICs, management & control connections, tunnels and agents for this NSX-T Transport Node.
      For more details about this event, please log into VMware Aria Operations for Networks, navigate to Settings -> Events"
   ::= { vmwVRNIEvents 80236}

vmwNSXTEdgeNodeStatusDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Roll-up Status is 'Down'.
      Some or all of the pNICs, management connection, control connections, tunnel statuses, agent statuses of NSX-T Edge Transport Node are down.
      Please check the status of the pNICs, management & control connections, tunnels and agents for this NSX-T Transport Node.
      For more details about this event, please log into VMware Aria Operations for Networks, navigate to Settings -> Events"
   ::= { vmwVRNIEvents 80243}

vmwNSXTEdgeNodeStatusDegradedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Roll-up Status is 'Degraded'.
      Some or all of the pNICs, management connection, control connections, tunnel statuses, agent statuses of NSX-T Edge Transport Node are in degraded state.
      Please check the status of the pNICs, management & control connections, tunnels and agents for this NSX-T Transport Node.
      For more details about this event, please log into VMware Aria Operations for Networks, navigate to Settings -> Events"
   ::= { vmwVRNIEvents 80244}

vmwNSXTEdgeNodeStatusUnknownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Transport Node Roll-up Status is 'Unknown'.
      NSX-T Manager can't determine the status of some or all of the pNICs, management connection, control connections, tunnel statuses, agent statuses of NSX-T Edge Transport Node.
      Please check the status of the pNICs, management & control connections, tunnels and agents for this NSX-T Transport Node.
      For more details about this event, please log into VMware Aria Operations for Networks, navigate to Settings -> Events"
   ::= { vmwVRNIEvents 80245}

vmwNsxiApplianceAvailableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Intelligence Appliance is deployed within NSX-T. NSX-I data collection on the NSX-T Data source can now be enabled.
      Please visit to VMware Aria Operations for Networks -> Settings -> Data Sources -> NSX-T data souces to enable this data collection.
      For more details about this event, please log into VMware Aria Operations for Networks, navigate to Settings -> Events"
   ::= { vmwVRNIEvents 974}

vmwNsxiSubscriptionCreateFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Enabling data collection from NSX Intelligence was failed.
      Please check the NSX-Intelligence appliance and ensure it is reachable and in a healthy state.
      For more details about this event, please log into VMware Aria Operations for Networks, navigate to Settings -> Events"
   ::= { vmwVRNIEvents 975}

vmwNsxiSubscriptionDeleteFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Cleanup of NSX Intelligence appliance failed.
      Please check the NSX-Intelligence appliance and ensure it is reachable and in a healthy state
      For more details about this event, please log into VMware Aria Operations for Networks, navigate to Settings -> Events"
   ::= { vmwVRNIEvents 976}

vmwNsxiSubscriptionUpdateFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Failed to initiate data collection from NSX Intelligence.
      Please check the NSX-Intelligence appliance and ensure it is reachable and in a healthy state
      For more details about this event, please log into VMware Aria Operations for Networks, navigate to Settings -> Events"
   ::= { vmwVRNIEvents 977}

vmwNsxiSslHandshakeFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Intelligence SSL Handshake Failed.
      Please check the SSL certificates configured on NSX Intelligence Appliance.
      For more details about this event, please log into VMware Aria Operations for Networks, navigate to Settings -> Events -> Alert Definitions page"
   ::= { vmwVRNIEvents 978}

vmwAnalyticsThresholdCompositeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Alert generated as a result of the specified combination of metric crosses the upper or lower bound specified in the configuration.
      Please check details and remediation steps mentioned in alert.
      For more details about this event, please log into VMware Aria Operations for Networks, navigate to Settings -> Events"
   ::= { vmwVRNIEvents 37004}

vmwAnalyticsThresholdCompositeProblemEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Alert generated as a result of the specified combination of metric crosses the upper or lower bound specified in the configuration.
      Please check details and remediation steps mentioned in alert.
      For more details about this event, please log into VMware Aria Operations for Networks, navigate to Settings -> Events"
   ::= { vmwVRNIEvents 37006}

vmwLicenseExpiredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "License of this appliance has expired. Please apply a valid license to continue the data collection.
      For more details about this event, please log into VMware Aria Operations for Networks, navigate to Settings -> Events"
   ::= { vmwVRNIEvents 80537}

vmwInGracePeriodEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Applicance license is in Grace Period. Add valid licenses before grace period ends to continue the data collection.
      This event will remain open till it is fixed.
      For more details about this event, please log into VMware Aria Operations for Networks, navigate to Settings -> Events"
   ::= { vmwVRNIEvents 80538}

vmwFailedDatasourceOperationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Data Source Update Operation Failed. Details of the data source and failed operation are mentioned in the event vmwOperatorDesc field.
      Please check correctness of input data while performing update operations to a data source.
      For more details about this event, please log into VMware Aria Operations for Networks, navigate to Settings -> Events"
   ::= { vmwVRNIEvents 80672}

vmwNsxtNotificationWebhookDisabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The webhook configured to receive push notifications from NSX-T is no longer present in the data source. As a result, notifications received by VMware Aria Operations for Networks might be delayed.
      Please log into NSX-T and enable notifications for VMware Aria Operations for Networks.
      For more details about this event, please log into VMware Aria Operations for Networks, navigate to Settings -> Events"
   ::= { vmwVRNIEvents 80670}

vmwNatRuleLargeSubnetEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "IP address mentioned in the NAT Rules have a subnet of size greater than 16. Flows will be impacted due to large subnet size.
      For more details about this event, please log into VMware Aria Operations for Networks, navigate to Settings -> Events"
   ::= { vmwVRNIEvents 80270}

vmwNSXTHostNodeMaintenanceModeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Host Node is in Maintenance Mode.
      For uninterrupted operations, please disable Maintenance Mode on this Host Node if maintenance activity is completed.
      This event will be closed once host is host is out of maintenance mode.
      For more details about this event, please log into VMware Aria Operations for Networks, navigate to Settings -> Events"
   ::= { vmwVRNIEvents 80272}

vmwNSXTEdgeNodeMaintenanceModeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Edge Node is in Maintenance Mode.
      For uninterrupted operations, please disable Maintenance Mode on this edge node if maintenance activity is completed.
      For more details about this event, please log into VMware Aria Operations for Networks, navigate to Settings -> Events"
   ::= { vmwVRNIEvents 80271}

vmwSDWanLinkTrafficThresholdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "SD-WAN Link Traffic exceeded the threshold limit configured. Link details are available in event description vmwOperatorDesc field.
      Please check the Traffic Utilization section on VeloCloud Edge to get the visibility of Applications and clients for the Link.
      For more details about this event, please log into VMware Aria Operations for Networks, navigate to Settings -> Events"
   ::= { vmwVRNIEvents 90017}

vmwVMCCapacityThresholdBreachEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is raised for VMC on AWS when thresholds of an entity e.g Firewall Rule exceeds.
      Please log in to VMC, navigate to listings page of entity type mentioned in the event description vmwOperatorDesc field.
      Then delete any unused entities to ensure uninterrupted operations.
      For more details about this event, please log into VMware Aria Operations for Networks, navigate to Settings -> Events"
   ::= { vmwVRNIEvents 100056}

vmwNativeVlanMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Native VLAN ID configuration of the ports on each link should match.
      Please check mismatch mentioned in the event vmwAffectedObject field and correct the configuration.
      For more details about this event, please log into VMware Aria Operations for Networks, navigate to Settings -> Events"
   ::= { vmwVRNIEvents 110011}

vmwNativeVlanTaggingMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Native VLAN tagging of the ports on each link should match.
      Please check mismatch mentioned in the event and correct the configuration.
      For more details about this event, please log into VMware Aria Operations for Networks, navigate to Settings -> Events"
   ::= { vmwVRNIEvents 110012}

vmwSnapshotNotBuildingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Unable to load latest network map. The last successful network map snapshot was taken over 6 hours ago.
      Network map functionality may show obsolete state. If this event persists, please contact VMware support.
      For more details about this event, please log into VMware Aria Operations for Networks, navigate to Settings -> Events"
   ::= { vmwVRNIEvents 110013}

vmwProtectionActiveEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VMware Aria Operations for Networks is experiencing high-system usage. Safe mode has been turned on automatically to keep the system protected and responsive.
      Please contact VMware support to fix the problem.
      For more details about this event, please log into VMware Aria Operations for Networks, navigate to Settings -> Events -> Alert Definitions page"
   ::= { vmwVRNIEvents 110015}

vmwUnableToSendSNMPTrapsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VMware Aria Operations for Networks appliance failed to send SNMP Trap. This could be due to temporary network disruption.
      If problem persists, please check if SNMP Trap destination is reachable from VMware Aria Operations for Networks appliance.
      Please note that this trap is only sent if sendto() or getaddrinfo() fails from VMware Aria Operations for Networks appliance.
      To send a test trap, log into VMware Aria Operations for Networks -> Settings -> Alerts and Definition -> SNMP Trap Destinations page and click 'Send Test Trap'.
      Also note that ther
      For more details about this event, please log into VMware Aria Operations for Networks, navigate to Settings -> Events -> Alert Definitions page"
   ::= { vmwVRNIEvents 80539}

vmwStreamProcessingFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Realtime stream processing has failed in VMware Aria Operations for Networks appliance.
      Please contact VMware support immediately to resolve the issue.
      For more details about this event, please log into VMware Aria Operations for Networks, navigate to Settings -> Events -> Alert Definitions page"
   ::= { vmwVRNIEvents 80540}

vmwSNOWMandatoryPrivilegeMissingEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Required privileges are missing for the user in ServiceNow.
      Please make sure that the user used in VMware Aria Operations for Networks while adding SNOW account has been necessary privileges in SNOW UI.
      To check user details, please visit VMware Aria Operations for Networks -> Setting -> Data Sources page.
      To check required user permissions, please visit https://docs.vmware.com/en/VMware-vRealize-Network-Insight/6.4/com.vmware.vrni.using.doc/GUID-772EC526-DD22-4B3C-87A5-F55CA90ED5AE.html.
      For more details about this event, please log into VMware Aria Operations for Networks, navigate to Settings -> Events -> Alert Definitions page"
   ::= { vmwVRNIEvents 80604}

vmwVMCSDDCTGWConnectivityFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is raised when SDDC within SDDC Group loses connectivity with VTGW(VMware Transit Gateway).
      Please contact VMC on AWS Support.
      For more details about this event, please log into VMware Aria Operations for Networks, navigate to Settings -> Events -> Alert Definitions page"
   ::= { vmwVRNIEvents 38003}

vmwNSXTEdgeDVPGsIPFIXDisabledEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "As a protection mechanism, the flow collection for DVPGs, having NSX-T Edges connected, is disabled.
      Please enable DFW IPFIX on NSX-T, if not enabled already. Do not enable IPFIX on DVPGs having NSX-T Edge VMs connected.
      For more details about this event, please log into VMware Aria Operations for Networks, navigate to Settings -> Events -> Alert Definitions page"
   ::= { vmwVRNIEvents 80273}

vmwUnsupportedNsxAlbVersionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is triggered while adding the NSX ALB data source and if the version of NSX ALB is < 20.1.3.
      For more details about this event, please log into VMware Aria Operations for Networks, navigate to Settings -> Events -> Alert Definitions page"
   ::= { vmwVRNIEvents 80700}

vmwIpfixFlowLagEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is raised to notify users when there are excessive incoming flow records than what can be processed within the stipulated time window, the ipfix processor lags behind. Once the incoming flow records are back within the limits, the alert gets cleared. The time window for each source is defined in ipfix.configuration.
      For more details about this event, please log into VMware Aria Operations for Networks, navigate to Settings -> Events -> Alert Definitions page"
   ::= { vmwVRNIEvents 80541}

vmwNSXALBSystemEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "These are the alarms/events reported by NSXALB platform.
      You can see these alerts in NSX ALB platform under Operations -> All alerts.
      For more details about this event, please log into VMware Aria Operations for Networks, navigate to Settings -> Events -> Alert Definitions page"
   ::= { vmwVRNIEvents 3558}

vmwTkgiKubernetesNotReachableEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is triggered if the Kubernetes Clusters which are managed by TKGI are not reachable from collector.
      Please verify the Kubernetes Cluster Master hosts are reachable from Collector VM.
      For more details about this event, please log into VMware Aria Operations for Networks, navigate to Settings -> Events -> Alert Definitions page"
   ::= { vmwVRNIEvents 80800}

vmwTkgiClustersInsufficientPrivilegesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is triggered if the Kubernetes Clusters which are managed by TKGI doesn't sufficient privileges for fetching the k8s entities.
      It must have List and Watch privileges.
      For more details about this event, please log into VMware Aria Operations for Networks, navigate to Settings -> Events -> Alert Definitions page"
   ::= { vmwVRNIEvents 80801}

vmwNSXTRouterInterfaceRPFPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is generated when the RPF packet drop ratio exceeds the threshold value of 1%. Check RPF packet drop on the interface."
   ::= { vmwVRNIEvents 80274}

vmwChangeEventsDroppedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Realtime processing has stopped due to high system load. Some updates may be delayed. It is a temporary condition. The system should recover and clear the error by itself. If this message persists for more than 12 hours, please contact VMware customer support."
   ::= { vmwVRNIEvents 80542}

vmwHcxIXServiceStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Interconnect Service is not Up. Please verify HCX IX Service is in healthy state."
   ::= { vmwVRNIEvents 90501}

vmwHcxNEServiceStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Network Extension Service is not Up. Please verify HCX NE Service is in healthy state."
   ::= { vmwVRNIEvents 90503}

vmwHcxBMServiceStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Bulk Migration Service is not Up. Please verify HCX Bulk Migration Service is in healthy state."
   ::= { vmwVRNIEvents 90512}

vmwHcxVMotionServiceStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX vMotion Service is not Up. Please verify HCX VMotion Service is in healthy state."
   ::= { vmwVRNIEvents 90513}

vmwHcxIXApplianceEncryptionTunnelStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hybrid Interconnect Service Encryption Tunnel Status is not Up. Please verify HCX IX Appliance Encryption Tunnel is in healthy state."
   ::= { vmwVRNIEvents 90502}

vmwHcxNEApplianceEncryptionTunnelStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Network Extension Service Encryption Tunnel Status is not Up. Please verify HCX NE Appliance Encryption Tunnel is in healthy state."
   ::= { vmwVRNIEvents 90504}

vmwHcxIXApplianceServicePipelineStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hybrid Interconnect Service Pipeline Status is not Up. Please verify Hybrid Interconnect Service Pipeline is in healthy state."
   ::= { vmwVRNIEvents 90505}

vmwHcxNEApplianceServicePipelineStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Network Extension Service Pipeline Status is not Up. Please verify HCX Network Extension Service Pipeline is in healthy state."
   ::= { vmwVRNIEvents 90506}

vmwHcxIXApplianceServiceTransportStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hybrid Interconnect Service Transport Status is not Up. Please verify Hybrid Interconnect Service Transport is in healthy state."
   ::= { vmwVRNIEvents 90507}

vmwHcxNEApplianceServiceTransportStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Network Extension Service Transport Status is not Up. Please verify Network Extension Service Transport is in healthy state."
   ::= { vmwVRNIEvents 90508}

vmwHcxIXApplianceServiceSystemStateEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hybrid Interconnect Service System State is not Up. Please verify Hybrid Interconnect Service System is in healthy state."
   ::= { vmwVRNIEvents 90509}

vmwHcxNEApplianceServiceSystemStateEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Network Extension Service System State is not Up. Please verify Network Extension Service System is in healthy state."
   ::= { vmwVRNIEvents 90510}

vmwHcxIXServiceNotRunningEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Hybrid Interconnect Service is not running. Please verify Hybrid Interconnect Service is in healthy state."
   ::= { vmwVRNIEvents 90514}

vmwHcxNEServiceNotRunningEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Network Extension Service is not running. Please verify Network Extension Service is in healthy state."
   ::= { vmwVRNIEvents 90515}

vmwHcxWanOptServiceNotRunningEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "WAN Optimisation Service is not running. Please verify WAN Optimisation Service Service is in healthy state."
   ::= { vmwVRNIEvents 90516}

vmwPanLogInsightDroppedFlowEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Dropped flows are detected on Palo Alto device through VMware Aria Operations for Logs. "
   ::= { vmwVRNIEvents 80050}

vmwHcxConnectionRuleViolationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Connection Rule is violated for the Firewall Rules. Please verify HCX Applinace Tunnel for the violated firewall rules."
   ::= { vmwVRNIEvents 90518}

vmwHcxApplianceAllTunnelDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "No tunnels are in working state on HCX Appliance. Please verify the tunnels are working for the HCX Appliance."
   ::= { vmwVRNIEvents 90517}

vmwHcxMtuMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "MTU doesn't match for uplink network profiles in the HCX Service Mesh. Please correct the MTU values for the uplink network profiles."
   ::= { vmwVRNIEvents 90519}

vmwSwitchPortRPFPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "uRPF packet drop ratio is high for switch port. Please check uRPF packet drop on the interface."
   ::= { vmwVRNIEvents 30124}

vmwCPLogInsightDroppedFlowEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Dropped flows are detected on Check Point device through VMware Aria Operations for Logs."
   ::= { vmwVRNIEvents 80051}

vmwSNMPTrapEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "This alert is raised when incoming SNMP Trap is received by VMware Aria Operations for Networks."
   ::= { vmwVRNIEvents 110017}


vmwServiceRestartCountExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "One or more services restarted multiple times. Please verify the system is in a healthy state."
   ::= { vmwVRNIEvents 80544}

vmwHcxWanOptServiceStatusEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "WAN Optimisation Service is not Up. Please verify HCX WAN Optimisation Service is in healthy state."
   ::= { vmwVRNIEvents 90511}

vmwNsxtIpfixMultipleCollectorConfigurationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Multiple DFW IPFIX Collectors Configured. Please remove the stale collector IPs from NSX Policy DFW IPFIX collector profile. To automatically remove stale collector IPs from NSX Policy IPFIX collector profile, please uncheck the IPFIX checkbox on the Data Source edit page and check again after 30 minutes."
   ::= { vmwVRNIEvents 80275}

vmwHcxApplianceUnhealthyTunnelsEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Few tunnels on HCX Appliance are unhealthy. Please verify the tunnels are working for the HCX Appliance."
   ::= { vmwVRNIEvents 90520}

vmwHcxManagerVersionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The paired HCX Managers are running different software versions. Please upgrade the appropriate HCX Manager so that the paired HCX Managers are running similar version of software."
   ::= { vmwVRNIEvents 90521}

vmwHcxApplianceVersionMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "The paired HCX Appliances are running different software versions. Please upgrade the appropriate HCX Appliance so that the paired HCX Appliances are running similar version of software."
   ::= { vmwVRNIEvents 90522}

vmwIntentAlert NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Intent Alert"
   ::= { vmwVRNIEvents 400}

vmwKubernetesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Kubernetes Alert"
   ::= { vmwVRNIEvents 1509}

vmwSwitchPortBufferThresholdExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Switch Port Buffer Threshold Exceeded Alert"
   ::= { vmwVRNIEvents 30107}

vmwRouterInterfaceBufferThresholdExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Router Interface Buffer Threshold Exceeded Alert"
   ::= { vmwVRNIEvents 30108}

vmwBufferThresholdExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Buffer Threshold Exceeded Alert"
   ::= { vmwVRNIEvents 30109}

vmwPortOperationalDownEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Port Operational Down Alert"
   ::= { vmwVRNIEvents 30113}

vmwSwitchPortRxNetworkUsageThresholdExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PNIC Rx Network Usage Alert"
   ::= { vmwVRNIEvents 40000}

vmwSwitchPortTxNetworkUsageThresholdExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PNIC Tx Network Usage Alert"
   ::= { vmwVRNIEvents 40002}

vmwSwitchPortRxNetworkUsageThresholdExceededCriticalEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PNIC Rx Network Usage Critical Alert"
   ::= { vmwVRNIEvents 40003}

vmwSwitchPortTxNetworkUsageThresholdExceededCriticalEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "PNIC Tx Network Usage Critical Alert"
   ::= { vmwVRNIEvents 40004}

vmwManagementHostHighCPUUsageEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Management Host High CPU Usage"
   ::= { vmwVRNIEvents 40005}

vmwManagementHostHighCPUUsageCriticalEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Management Host High CPU Usage"
   ::= { vmwVRNIEvents 40006}

vmwHostUnHealthyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host Unhealthy Alert"
   ::= { vmwVRNIEvents 40007}

vmwNSXControllerFSAvailableThresholdRecededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX Controller Filesystem Disk Available Threshold Receded Alert"
   ::= { vmwVRNIEvents 40008}

vmwEdgeVmVnicRxPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Edge VM VNIC Rx Packet Drop Alert"
   ::= { vmwVRNIEvents 40011}

vmwEdgeVmVnicTxPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Edge VM VNIC Tx Packet Drop Alert"
   ::= { vmwVRNIEvents 40012}

vmwManagementHostPnicRxPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host pNIC Rx Packet Drop Alert"
   ::= { vmwVRNIEvents 40013}

vmwManagementHostPnicTxPacketDropEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Host pNIC Tx Packet Drop Alert"
   ::= { vmwVRNIEvents 40014}

vmwManagementHostConnectionStateDisconnectedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Management Host Connection State Disconnected Alert"
   ::= { vmwVRNIEvents 40015}

vmwAllThresholdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Threshold Alert"
   ::= { vmwVRNIEvents 37005}

vmwVTGWDuplicateRoutesEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VTGW Duplicate Routes Event"
   ::= { vmwVRNIEvents 38004}

vmwApplianceNotRegisteredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Appliance Not Registered Alert"
   ::= { vmwVRNIEvents 80529}

vmwRegCertExpiredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Appliance Registration Certificate Expired Alert"
   ::= { vmwVRNIEvents 80530}

vmwBackupFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Backup Failed Alert"
   ::= { vmwVRNIEvents 80533}

vmwAdditionalResourcesRequiredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Additional Resources Required Alert"
   ::= { vmwVRNIEvents 80534}

vmwCapacityReconfigurationRequiredEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Cluster Capacity Reconfiguration Required Alert"
   ::= { vmwVRNIEvents 80535}

vmwCapacityReconfigurationFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Cluster Capacity Reconfiguration Failed Alert"
   ::= { vmwVRNIEvents 80536}

vmwHighDiskIoUtilizationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "High Disk IO Utilization Alert"
   ::= { vmwVRNIEvents 80543}

vmwNsxtSystemEventApiEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T System Alert API is timed out"
   ::= { vmwVRNIEvents 80666}

vmwServiceNowAppLimitExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Number of applications in ServiceNow exceeds System limit"
   ::= { vmwVRNIEvents 80656}

vmwAzureFlowCollectionErrorEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Azure Flow Collection Error"
   ::= { vmwVRNIEvents 8061316}

vmwAzureNetworkWatcherStorageErrorEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Azure Network Watcher Storage Error"
   ::= { vmwVRNIEvents 8061317}

vmwAnalyticsMemoryLimitsExceededEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Analytics Memory Limits Exceeded Alert"
   ::= { vmwVRNIEvents 80600}

vmwHybridConnectAdvertisedSubnetsFailedEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "BGP routes advertisement failed alert"
   ::= { vmwVRNIEvents 1277}

vmwNSXTRxPacketDropOnNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Network Interface Received Packet Drop Alert on Management Node"
   ::= { vmwVRNIEvents 80268}

vmwNSXTTxPacketDropOnNicEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "NSX-T Network Interface Transmission Packet Drop Alert on Management Node"
   ::= { vmwVRNIEvents 80269}

vmwNSXTBGPNeighbourStateEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "BGP neighbor connection status change alert"
   ::= { vmwVRNIEvents 80251}

vmwVeloCloudEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Alert"
   ::= { vmwVRNIEvents 90000}

vmwVeloCloudEdgeL7ApplicationLostPacketEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge Packet Drop Alert"
   ::= { vmwVRNIEvents 90003}

vmwVeloCloudEdgeL7ApplicationRetransmittedPacketEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge Retransmitted Packet Alert"
   ::= { vmwVRNIEvents 90004}

vmwVeloCloudEdgeLocationNotSetEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud Edge Location Not Set Alert"
   ::= { vmwVRNIEvents 90006}

vmwVeloCloudTunnelDegradedVoiceQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Velocloud Tunnel Degraded Voice QOE Alert"
   ::= { vmwVRNIEvents 90014}

vmwVeloCloudTunnelDegradedVideoQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Velocloud Tunnel Degraded Video QOE Alert"
   ::= { vmwVRNIEvents 90015}

vmwVeloCloudTunnelDegradedTransQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Velocloud Tunnel Degraded Transaction QOE Alert"
   ::= { vmwVRNIEvents 90016}

vmwVeloCloudQoeEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "VeloCloud QOE Alert"
   ::= { vmwVRNIEvents 90018}

vmwHcxEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HCX Alert"
   ::= { vmwVRNIEvents 90500}

vmwLatencyNoDataEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Latency No Data Alert"
   ::= { vmwVRNIEvents 100000}

vmwLinkMtuMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Link MTU Mismatch Alert"
   ::= { vmwVRNIEvents 110000}

vmwPortModeMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Port Mode Mismatch Alert"
   ::= { vmwVRNIEvents 110001}

vmwPortTrunkMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Port Trunk Mismatch Alert"
   ::= { vmwVRNIEvents 110002}

vmwPortChannelMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Port Channel Mismatch Alert"
   ::= { vmwVRNIEvents 110003}

vmwDuplexMismatchEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Duplex Mismatch Alert"
   ::= { vmwVRNIEvents 110004}

vmwDuplicateMacAddressEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Duplicate Mac Address Alert"
   ::= { vmwVRNIEvents 110007}

vmwDuplicateIPAddressEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Duplicate IP Address Alert"
   ::= { vmwVRNIEvents 110008}

vmwSTPPathCostMethodInconsistencyEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "STP Path Cost Method Inconsistency Alert"
   ::= { vmwVRNIEvents 110009}

vmwHSRPSTPColocationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HSRP STP Colocation Alert"
   ::= { vmwVRNIEvents 110010}

vmwStigAccountPasswdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Stig Account Passwd Alert"
   ::= { vmwVRNIEvents 111001}

vmwStigConsolePasswdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Stig Console Passwd Alert"
   ::= { vmwVRNIEvents 111002}

vmwStigDefaultPasswdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Stig Default Passwd Alert"
   ::= { vmwVRNIEvents 111003}

vmwStigMgmtPasswdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Stig Mgmt Passwd Alert"
   ::= { vmwVRNIEvents 111004}

vmwStigPlaintextPasswdEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Stig Plaintext Passwd Alert"
   ::= { vmwVRNIEvents 111005}

vmwHSRPConfigurationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "HSRP Configuration Alert"
   ::= { vmwVRNIEvents 110014}

vmwLoopDetectionEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Loop Detection Alert"
   ::= { vmwVRNIEvents 115001}

vmwReachabilityEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Reachability Alert"
   ::= { vmwVRNIEvents 115002}

vmwSegmentationEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Segmentation Alert"
   ::= { vmwVRNIEvents 115003}

vmwUnderlayProblem NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Underlay Problem"
   ::= { vmwVRNIEvents 110005}

vmwSwitchPortProblem NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Switchport Problem"
   ::= { vmwVRNIEvents 110006}

vmwPathProblem NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Path Problem"
   ::= { vmwVRNIEvents 110016}

vmwInvalidIntentEvent NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Invalid Intent Alert"
   ::= { vmwVRNIEvents 111000}

vmwPassthroughEvents NOTIFICATION-TYPE
   OBJECTS { vmwPlatformIP, vmwEventSeverity, vmwAffectedObject, vmwOperatorDesc, vmwVrniUrl, vmwTimestamp, vmwEventName, vmwAffectedObjectManager, vmwAffectedObjectParent }
   STATUS current
   DESCRIPTION
      "Passthrough Alert"
   ::= { vmwVRNIEvents 2503}

-- **********************************************************
-- Notification parameters
-- **********************************************************

vmwAffectedObject OBJECT-TYPE
    SYNTAX          SnmpAdminString
    MAX-ACCESS      accessible-for-notify
    STATUS          current
    DESCRIPTION
        "Object affected by this event"
    ::= { vmwVRNIData 102}


vmwEventSeverity OBJECT-TYPE
    SYNTAX          VmwVrniSeverity
    MAX-ACCESS      accessible-for-notify
    STATUS          current
    DESCRIPTION
        "VMware Aria Operations for Networks Event Severity"
    ::= { vmwVRNIData 103}

vmwVrniUrl OBJECT-TYPE
    SYNTAX          SnmpAdminString
    MAX-ACCESS      accessible-for-notify
    STATUS          current
    DESCRIPTION
        "URL to VMware Aria Operations for Networks for this exact event"
    ::= { vmwVRNIData 104}


vmwTimestamp OBJECT-TYPE
    SYNTAX          DateAndTime
    MAX-ACCESS      accessible-for-notify
    STATUS          current
    DESCRIPTION
        "Time of first detection of event"
    ::= { vmwVRNIData 105}

vmwOperatorDesc OBJECT-TYPE
    SYNTAX          VmwLongSnmpAdminString
    MAX-ACCESS      accessible-for-notify
    STATUS          current
    DESCRIPTION
        "Human readable message of the event"
    ::= { vmwVRNIData 106}

vmwEventName OBJECT-TYPE
    SYNTAX          VmwLongSnmpAdminString
    MAX-ACCESS      accessible-for-notify
    STATUS          current
    DESCRIPTION
        "Event name"
    ::= { vmwVRNIData 107}

vmwAffectedObjectManager OBJECT-TYPE
    SYNTAX          VmwLongSnmpAdminString
    MAX-ACCESS      accessible-for-notify
    STATUS          current
    DESCRIPTION
        "Event Manager"
    ::= { vmwVRNIData 108}

vmwAffectedObjectParent OBJECT-TYPE
    SYNTAX          VmwLongSnmpAdminString
    MAX-ACCESS      accessible-for-notify
    STATUS          current
    DESCRIPTION
        "Higher-level entity of the affected object to uniquely identify problem entity"
    ::= { vmwVRNIData 109}

vmwPlatformIP OBJECT-TYPE
    SYNTAX          VmwLongSnmpAdminString
    MAX-ACCESS      accessible-for-notify
    STATUS          current
    DESCRIPTION
        "IP address of Operations for Networks platform"
    ::= { vmwVRNIData 110}

-- conformance information
vmwNetworkInsightMIBConformance OBJECT IDENTIFIER ::= { vmwNetworkInsightMIB 99 }
vmwNetworkInsightMIBCompliances OBJECT IDENTIFIER ::=
                                        { vmwNetworkInsightMIBConformance 1 }
vmwNetworkInsightMIBGroups OBJECT IDENTIFIER ::= { vmwNetworkInsightMIBConformance 2 }

-- compliance statements
vmwNetworkInsightMIBBasicCompliance MODULE-COMPLIANCE
    STATUS     deprecated
    DESCRIPTION
        "The compliance statement for entities which implement
        VMWARE-NSX-MANAGER-MIB."
    MODULE -- this module
    MANDATORY-GROUPS { vmwNetworkInsightNotificationInfoGroup1,
                             vmwNetworkInsightNotificationGroup1 }
    ::= { vmwNetworkInsightMIBCompliances 3 }

vmwNetworkInsightNotificationInfoGroup1 OBJECT-GROUP
    OBJECTS {
    vmwAffectedObject,
    vmwEventSeverity,
    vmwVrniUrl,
    vmwTimestamp,
    vmwOperatorDesc,
    vmwEventName
    }
    STATUS current
    DESCRIPTION
    "These objects provide details in NSX Manager notifications."
    ::= { vmwNetworkInsightMIBGroups 2 }

vmwNetworkInsightNotificationGroup1 NOTIFICATION-GROUP
  NOTIFICATIONS {
    vmwSnmpTrapsAreConfigured,
        vmwSnmpTrapsAreDisabled,
        vmwTestTrap,
        vmwEntityDiscoveryChangeEvent,
        vmwEntityPropertiesChangeEvent,
        vmwFirewallNotInstalledOnHostEvent,
        vmwHostWithStaleFirewallRulesEvent,
        vmwIpAddressChangeEvent,
        vmwL2GatewayAnomalyEvent,
        vmwL2NetworkAddressAnomalyEvent,
        vmwL2NetworkDiameterExceededEvent,
        vmwL2NetworkUplinkMissingEvent,
        vmwL2NetworkWithNoVMsEvent,
        vmwLayer2NetworkDiameterChangedEvent,
        vmwMTUMismatchEvent,
        vmwNetworkIsolationEvent,
        vmwNoPathEvent,
        vmwSpoofguardDisabledEvent,
        vmwVMotionEvent,
        vmwVMWithDisconnectedVnicsEvent,
        vmwVMWithMulipleVnicsOnDifferentVxlansEvent,
        vmwVMWithMulipleVnicsOnSameL2Event,
        vmwVMWithNoIpAddressEvent,
        vmwVTEPMissingEvent,
        vmwL2Event,
        vmwMembershipChangeEvent,
        vmwSecurityGroupMembershipChangeEvent,
        vmwFirewallRuleMembershipChangeEvent,
        vmwVlanMembershipChangeEvent,
        vmwVxlanMembershipChangeEvent,
        vmwDeleteChangeEvent,
        vmwVtepFailedPingEvent,
        vmwEmptySearchStreamChangeEvent,
        vmwSearchStreamMembershipChangeEvent,
        vmwEmptySearchStreamProblemEvent,
        vmwSearchStreamMembershipProblemEvent,
        vmwOspfConfigurationMismatchEvent,
        vmwServiceVMNotHealthyEvent,
        vmwServiceVMNotPoweredOnEvent,
        vmwServiceVMHighCPUUsageEvent,
        vmwServiceVMHighMemoryUsageEvent,
        vmwServiceVMHighDiskUsageEvent,
        vmwIPSetPropertiesChangeEvent,
        vmwFirewallRulePropertiesChangeEvent,
        vmwSecurityGroupPropertiesChangeEvent,
        vmwIPSetMembershipChangeEvent,
        vmwFirewallRuleMaskEvent,
        vmwSecurityMembershipChangeEvent,
        vmwSecurityTagPropertiesChangeEvent,
        vmwSecurityTagMembershipChangeEvent,
        vmwHostDatastoreChangeEvent,
        vmwVMDatastoreChangeEvent,
        vmwVMSnapshotChangeEvent,
        vmwVMVirtualDiskChangeEvent,
        vmwIPSetDefinitionMismatchEvent,
        vmwSegmentMismatchEvent,
        vmwVtepEvent,
        vmwVtepConfigurationFaultEvent,
        vmwVtepSubnetMismatchEvent,
        vmwVtepCountMismatchEvent,
        vmwDLRNetworksNotReachableEvent,
        vmwEdgeNetworksNotReachableEvent,
        vmwThresholdExceededEventCpuReady,
        vmwThresholdExceededEventCpuCoStop,
        vmwThresholdExceededEventDiskCommandAbortRule,
        vmwThresholdExceededEventIODeviceLatencyRule,
        vmwThresholdExceededEventIOKernelLatencyRule,
        vmwThresholdExceededEventMemorySwapInRule,
        vmwThresholdExceededEventMemorySwapOutRule,
        vmwThresholdExceededEventNetworkRxDropRule,
        vmwThresholdExceededEventNetworkTxDropRule,
        vmwPacketDropEvent,
        vmwSwitchPortPacketDropEvent,
        vmwRouterInterfacePacketDropEvent,
        vmwVnicPacketDropEvent,
        vmwVTEPUnderlayPacketDropEvent,
        vmwPnicUnderlyingSwitchPortPacketDropEvent,
        vmwDevicePacketDropEvent,
        vmwThresholdExceededEventDatastoreFreeSpaceWarning,
        vmwThresholdExceededEventDatastoreFreeSpaceCritical,
        vmwThresholdExceededEventDatastoreReadLatency,
        vmwThresholdExceededEventDatastoreWriteLatency,
        vmwDistributedFirewallApplyHostEvent,
        vmwDistributedFirewallApplyVMEvent,
        vmwNsxEvent,
        vmwFeatureImpactedEvent,
        vmwClusterFeatureVersionMismatchEvent,
        vmwHostFeatureVersionMismatchEvent,
        vmwFeatureVersionMismatchEvent,
        vmwHostFeatureEnabledMismatchEvent,
        vmwHostFeatureInstalledMismatchEvent,
        vmwHostVtepNotFoundEvent,
        vmwHostVtepDisconnectedEvent,
        vmwHostVtepEvent,
        vmwClusterHostsVtepMTUMismatchEvent,
        vmwFeatureUnhealthyEvent,
        vmwEdgeHANotConfiguredEvent,
        vmwEdgeInterfacesDownEvent,
        vmwModuleUnhealthyEvent,
        vmwModuleNotLoadedEvent,
        vmwModuleNetworkConnectionFailureEvent,
        vmwHostNetworkControlPlaneMismatchEvent,
        vmwHostNetworkControlPlaneConnectionFailureEvent,
        vmwHostNetworkControlPlaneNotSyncedEvent,
        vmwNSXControllerClusterMajorityEvent,
        vmwNSXControllersVMOnSameHostEvent,
        vmwVxLanRangeExhaustEvent,
        vmwNSXFirewallDefaultAllowAllRulesEvent,
        vmwEdgeNotHAEvent,
        vmwEdgeNotDeployedEvent,
        vmwEcmpIsEnabledAndStatefulServicesAreUpEvent,
        vmwLogicalRouterDeployedOnEcmpEdgeHostEvent,
        vmwEdgeMissingInterfaceOSPFAreaMappingEvent,
        vmwOspfInsecureAuthRouterEvent,
        vmwNSXControllersDeployedCountEvent,
        vmwNSXControllerNotActiveCountEvent,
        vmwNSXControllerEvent,
        vmwNSXBackupEvent,
        vmwNSXUnsecureBackupEvent,
        vmwNSXBackupSystemEventsExcludedEvent,
        vmwNSXBackupNotScheduledEvent,
        vmwNSXBackupNotRecordedEvent,
        vmwNSXNtpServerEvent,
        vmwNSXSysLogServerEvent,
        vmwControllerSysLogServerEvent,
        vmwGenericNSXSystemEvent,
        vmwOtherCriticalNSXEvent,
        vmwFilterConfigApplyOnHostFailedEvent,
        vmwRulesetLoadOnHostFailedEvent,
        vmwConfigUpdateOnHostFailedEvent,
        vmwSpoofguardConfigUpdateOnHostFailedEvent,
        vmwApplyRuleToVnicFailedEvent,
        vmwContainerConfigUpdateOnVnicFailedEvent,
        vmwSpoofguardApplyToVnicFailedEvent,
        vmwHostMessagingConfigurationFailedEvent,
        vmwHostMessagingConnectionReconfigurationFailedEvent,
        vmwHostMessagingConfigurationFailedNotificationSkippedEvent,
        vmwHostMessagingInfrastructureDownEvent,
        vmwEdgeVMNotRespondingEvent,
        vmwEdgeUnhealthyEvent,
        vmwEdgeVMCommunicationFailureEvent,
        vmwNSXEdgeEvent,
        vmwPanEvent,
        vmwPanNsxNotInRegisteredStateEvent,
        vmwPanNsxDynamicUpdateDelayedEvent,
        vmwPanDeviceInDisconnectedStateEvent,
        vmwPanNsxServiceApplianceViewMismatchEvent,
        vmwPanNsxFabricAgentNotFoundOnHostEvent,
        vmwPanNsxServiceVMNotFoundOnHostEvent
}
    STATUS current
    DESCRIPTION
    "Set of notifications (traps, informs) supported in this version."
    ::= { vmwNetworkInsightMIBGroups 3 }

vmwNetworkInsightMIBBasicCompliance2 MODULE-COMPLIANCE
    STATUS     deprecated
    DESCRIPTION
        "The compliance statement for entities which implement
         VMWARE-VRNI-MIB second version."
    MODULE -- this module
    MANDATORY-GROUPS { vmwNetworkInsightNotificationInfoGroup2,
                       vmwNetworkInsightNotificationGroup1,
                       vmwNetworkInsightNotificationGroup2
                      }
    ::= { vmwNetworkInsightMIBCompliances 30 }

vmwNetworkInsightNotificationInfoGroup2 OBJECT-GROUP
    OBJECTS {
    vmwAffectedObject,
    vmwEventSeverity,
    vmwVrniUrl,
    vmwTimestamp,
    vmwOperatorDesc,
    vmwEventName
    }
    STATUS deprecated
    DESCRIPTION
    "These events provide details in NSX Manager notifications."
    ::= { vmwNetworkInsightMIBGroups 20 }

vmwNetworkInsightNotificationGroup2 NOTIFICATION-GROUP
       NOTIFICATIONS {
       vmwLogicalRouterNoUplinkEvent,
       vmwNSXComponentEvent,
       vmwNSXBackupEvent,
       vmwNSXBackupAuditLogExcludedEvent,
       vmwNSXUnsecureBackupEvent,
       vmwNSXBackupSystemEventsExcludedEvent,
       vmwNSXBackupNotScheduledEvent,
       vmwNSXBackupNotRecordedEvent,
       vmwNSXNtpServerEvent,
       vmwNSXSysLogServerEvent,
       vmwControllerSysLogServerEvent
       }
       STATUS current
       DESCRIPTION
            "Set of added notifications (traps, informs) since last revision."
        ::= { vmwNetworkInsightMIBGroups 30 }

vmwNetworkInsightMIBBasicCompliance3 MODULE-COMPLIANCE
    STATUS     deprecated
    DESCRIPTION
        "The compliance statement for entities which implement
         VMWARE-VRNI-MIB second version."
    MODULE -- this module
    MANDATORY-GROUPS { vmwNetworkInsightNotificationInfoGroup2,
                       vmwNetworkInsightNotificationGroup1,
                       vmwNetworkInsightNotificationGroup2,
                       vmwNetworkInsightNotificationGroup3
                      }
    ::= { vmwNetworkInsightMIBCompliances 35 }

vmwNetworkInsightNotificationGroup3 NOTIFICATION-GROUP
       NOTIFICATIONS {
        vmwMTUMismatchEvent,
        vmwVMWithMulipleVnicsOnSameL2Event,
        vmwMembershipChangeEvent,
        vmwSecurityGroupMembershipChangeEvent,
        vmwFirewallRuleMembershipChangeEvent,
        vmwVlanMembershipChangeEvent,
        vmwVxlanMembershipChangeEvent,
        vmwSearchStreamMembershipChangeEvent,
        vmwIPSetMembershipChangeEvent,
        vmwSecurityMembershipChangeEvent,
        vmwVtepEvent,
        vmwPacketDropEvent,
        vmwSwitchPortPacketDropEvent,
        vmwRouterInterfacePacketDropEvent,
        vmwVnicPacketDropEvent,
        vmwVTEPUnderlayPacketDropEvent,
        vmwPnicUnderlyingSwitchPortPacketDropEvent,
        vmwHostFeatureVersionMismatchEvent,
        vmwSpoofguardConfigUpdateOnHostFailedEvent,
        vmwNSXEcmpEdgeDownEvent,
        vmwNSXMajorityEcmpEdgesDownEvent,
        vmwNSXAllEcmpEdgesDownEvent
       }
       STATUS current
       DESCRIPTION
            "Set of added notifications (traps, informs) since last revision."
        ::= { vmwNetworkInsightMIBGroups 40 }

vmwNetworkInsightMIBBasicCompliance4 MODULE-COMPLIANCE
    STATUS     deprecated
    DESCRIPTION
        "The compliance statement for entities which implement
         VMWARE-VRNI-MIB second version."
    MODULE -- this module
    MANDATORY-GROUPS { vmwNetworkInsightNotificationInfoGroup2,
                       vmwNetworkInsightNotificationGroup1,
                       vmwNetworkInsightNotificationGroup2,
                       vmwNetworkInsightNotificationGroup3,
                       vmwNetworkInsightNotificationGroup4
                      }
    ::= { vmwNetworkInsightMIBCompliances 45 }

vmwNetworkInsightNotificationGroup4 NOTIFICATION-GROUP
       NOTIFICATIONS {
       vmwNSXEdgeSplitBrainEvent,
       vmwNSXIpV6EnabledEvent,
       vmwNSXOspfNeighborDownEvent,
       vmwCheckpointEvent,
       vmwNSXEdgeMtuMismatchEvent,
       vmwCheckpointNsxFabricAgentNotFoundOnHostEvent,
       vmwCheckpointNsxServiceVMNotFoundOnHostEvent,
       vmwCheckpointGatewaySicStatusNotCommunicatingEvent,
       vmwCheckpointNsxServiceApplianceViewMismatchEvent,
       vmwCriticalHostNotAccessibleEvent,
       vmwVlanMembershipChangeEvent,
       vmwClusterFeatureVersionMismatchEvent,
       vmwHostFeatureVersionMismatchEvent,
       vmwConfigUpdateOnHostFailedEvent
       }
       STATUS current
       DESCRIPTION
            "Set of added notifications (traps, informs) since last revision."
        ::= { vmwNetworkInsightMIBGroups 50 }

vmwNetworkInsightNotificationInfoGroup3 OBJECT-GROUP
    OBJECTS {
    vmwEventSeverity,
    vmwAffectedObject,
    vmwOperatorDesc,
    vmwVrniUrl,
    vmwTimestamp,
    vmwEventName
    }
    STATUS current
    DESCRIPTION
    "These objects provide details in VMware Aria Operations for Networks notifications."
    ::= { vmwNetworkInsightMIBGroups 55 }

vmwNetworkInsightMIBBasicCompliance5 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5
                      }
    ::= { vmwNetworkInsightMIBCompliances 60 }

vmwNetworkInsightMIBBasicCompliance6 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6
                      }
    ::= { vmwNetworkInsightMIBCompliances 70 }

vmwNetworkInsightMIBBasicCompliance7 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7
                      }
    ::= { vmwNetworkInsightMIBCompliances 80 }

vmwNetworkInsightMIBBasicCompliance8 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8
                      }
    ::= { vmwNetworkInsightMIBCompliances 90 }

vmwNetworkInsightMIBBasicCompliance9 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9
                      }
    ::= { vmwNetworkInsightMIBCompliances 100 }

vmwNetworkInsightMIBBasicCompliance10 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10
                      }
    ::= { vmwNetworkInsightMIBCompliances 110 }

vmwNetworkInsightMIBBasicCompliance11 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10,
                       vmwNetworkInsightNotificationGroup11
                      }
    ::= { vmwNetworkInsightMIBCompliances 120 }

vmwNetworkInsightMIBBasicCompliance12 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10,
                       vmwNetworkInsightNotificationGroup11,
                       vmwNetworkInsightNotificationGroup12
                      }
    ::= { vmwNetworkInsightMIBCompliances 130 }

vmwNetworkInsightMIBBasicCompliance13 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10,
                       vmwNetworkInsightNotificationGroup11,
                       vmwNetworkInsightNotificationGroup12,
                       vmwNetworkInsightNotificationGroup13
                      }
    ::= { vmwNetworkInsightMIBCompliances 140 }

vmwNetworkInsightMIBBasicCompliance14 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10,
                       vmwNetworkInsightNotificationGroup11,
                       vmwNetworkInsightNotificationGroup12,
                       vmwNetworkInsightNotificationGroup13,
                       vmwNetworkInsightNotificationGroup14
                      }
    ::= { vmwNetworkInsightMIBCompliances 150 }

vmwNetworkInsightMIBBasicCompliance15 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10,
                       vmwNetworkInsightNotificationGroup11,
                       vmwNetworkInsightNotificationGroup12,
                       vmwNetworkInsightNotificationGroup13,
                       vmwNetworkInsightNotificationGroup14,
                       vmwNetworkInsightNotificationGroup15
                      }
    ::= { vmwNetworkInsightMIBCompliances 160 }

vmwNetworkInsightNotificationInfoGroup4 OBJECT-GROUP
    OBJECTS {
    vmwPlatformIP,
    vmwEventSeverity,
    vmwAffectedObject,
    vmwOperatorDesc,
    vmwVrniUrl,
    vmwTimestamp,
    vmwEventName,
    vmwAffectedObjectManager,
    vmwAffectedObjectParent
    }
    STATUS current
    DESCRIPTION
    "These objects provide details in VMware Aria Operations for Networks notifications."
    ::= { vmwNetworkInsightMIBGroups 170 }

vmwNetworkInsightMIBBasicCompliance16 MODULE-COMPLIANCE
    STATUS     current
    DESCRIPTION
        "The compliance statement for entities which implement
         VMWARE-VRNI-MIB latest version."
    MODULE -- this module
    MANDATORY-GROUPS { vmwNetworkInsightNotificationInfoGroup4,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6,
                       vmwNetworkInsightNotificationGroup7,
                       vmwNetworkInsightNotificationGroup8,
                       vmwNetworkInsightNotificationGroup9,
                       vmwNetworkInsightNotificationGroup10,
                       vmwNetworkInsightNotificationGroup11,
                       vmwNetworkInsightNotificationGroup12,
                       vmwNetworkInsightNotificationGroup13,
                       vmwNetworkInsightNotificationGroup14,
                       vmwNetworkInsightNotificationGroup15,
                       vmwNetworkInsightNotificationGroup16
                      }
    ::= { vmwNetworkInsightMIBCompliances 175 }

vmwNetworkInsightNotificationGroup5 NOTIFICATION-GROUP
       NOTIFICATIONS {
          vmwNiInfraChangeEvent,
          vmwDataSourceEnabledChangeEvent,
          vmwDataSourceDisabledChangeEvent,
          vmwDataSourceCreatedEvent,
          vmwPlatformCpuCoreChangeEvent,
          vmwPlatformDiskChangeEvent,
          vmwPlatformMemoryChangeEvent,
          vmwPlatformRebootedEvent,
          vmwProxyCpuCoreChangeEvent,
          vmwProxyDiskChangeEvent,
          vmwProxyMemoryChangeEvent,
          vmwProxyRebootedEvent,
          vmwNIClusterChangeEvent,
          vmwNISystemProxyChangeEvent,
          vmwNIClusterCreateEvent,
          vmwAWSRegionSGLimitEvent,
          vmwAWSVPCSGLimitEvent,
          vmwAWSSGInboundRuleLimitEvent,
          vmwAWSSGOutboundRuleLimitEvent,
          vmwAWSInterfaceSGLimitEvent,
          vmwVirtualDistributedRoutingEvent,
          vmwIndexerLagEvent,
          vmwIPFIXFlowDPPausedEvent,
          vmwGridProcessingStoppedEvent,
          vmwUnableToSendEmailsEvent,
          vmwSMTPNotConfiguredEvent,
          vmwSNMPNotConfiguredEvent,
          vmwReindexingInProgressEvent,
          vmwNodesVersionMismatchEvent,
          vmwNotAllServicesRunningEvent,
          vmwNotAllServicesHealthyEvent,
          vmwExpandPartitionFailedEvent,
          vmwDiskCleanupFailedEvent,
          vmwVacuumFailedEvent,
          vmwConfigStoreCleanupFailedEvent,
          vmwHBaseRetentionToolFailedEvent,
          vmwMetricStoreUpdaterFailedEvent,
          vmwCollectorLagEvent,
          vmwCollectionLagEvent,
          vmwGridProcessingLagEvent,
          vmwConnectionErrorEvent,
          vmwNodeNotActiveEvent,
          vmwHighDiskUtilizationEvent,
          vmwIndexingAbortedEvent,
          vmwUpgradeFailedEvent,
          vmwFlowProcessingSuspendedEvent,
          vmwVCNotOnSameProxyEvent,
          vmwNoDVSAvailableEvent,
          vmwUnknownInfobloxVersionEvent,
          vmwUnsupportedInfobloxVersionEvent,
          vmwIncorrectInfobloxCredentialEvent,
          vmwInfobloxRecordLimitExceededEvent,
          vmwWebhookNotRunningEvent,
          vmwIncorrectWebhookConfiguredOnAlertEvent,
          vmwWebhookNotEnabledOnAlertEvent,
          vmwVRNIContentPackNotInstalledEvent,
          vmwUnsupportedVRNIContentPackVersionEvent,
          vmwUnsupportedLogInsightVersionEvent,
          vmwComputeManagersNotAddedEvent,
          vmwComputeManagersNotFoundEvent,
          vmwUnsupportedNSXTVersionEvent,
          vmwNotEmptyNodeEvent,
          vmwFlowPhysicalNodeEvent,
          vmwFlowCollectionErrorEvent,
          vmwAWSThrottlingExceptionEvent,
          vmwAWSFlowLogAccessDeniedExceptionEvent,
          vmwNSXIPFIXStatusMismatchEvent,
          vmwNumVMsOrHostsNotFoundEvent,
          vmwUnsupportedNSXVersionEvent,
          vmwPwdAuthModeDisabledAristaEvent,
          vmwHostnameResolutionErrorEvent,
          vmwPrimaryNSXNotAddedEvent,
          vmwDataProviderNotRunningEvent,
          vmwInvalidResponseFromDatasourceEvent,
          vmwHostNotReachableEvent,
          vmwNSXControllerNotFoundEvent,
          vmwUnexpectedDSTypeOrVersionEvent,
          vmwWarnConfigEvent,
          vmwInvalidConfigEvent,
          vmwNotFoundEvent,
          vmwInsufficientPrivilegesEvent,
          vmwPwdAuthModeDisabledEvent,
          vmwFailedCredsEncryptEvent,
          vmwSNMPConnectionInvalidEvent,
          vmwUnknownHostEvent,
          vmwInvalidCredentialsEvent,
          vmwIncorrectConnectionStringEvent,
          vmwConnectionRefusedEvent,
          vmwTimeoutEvent,
          vmwFailedEvent,
          vmwNSXTEvent,
          vmwNSXTVcNotAddedEvent,
          vmwNSXTStandaloneHostsEvent,
          vmwLargeSdmsDroppedEvent,
          vmwNSXTIPFixDFWStatusNotEnabledEvent,
          vmwNSXTIPFixPortIncorrectEvent,
          vmwNSXTIPFixCollectorAndIPFixProfileMismatchEvent,
          vmwNSXTIPFixIPFixProfilePriorityNotZeroEvent,
          vmwNSXTIPFixNoIPFixProfileEvent,
          vmwNSXTIPFixNoNewCollectorProfileCanBeAddedEvent,
          vmwNSXTIPFixNoCollectorProfileEvent
          }
       STATUS current
       DESCRIPTION
            "Set of added notifications (traps, informs) since last revision."
        ::= { vmwNetworkInsightMIBGroups 65 }

  vmwNetworkInsightNotificationGroup6 NOTIFICATION-GROUP
       NOTIFICATIONS {
          vmwNSXTSystemEvent,
          vmwNSXTNoUplinkConnectivityEvent,
          vmwNSXTRoutingAdvertisementEvent,
          vmwNSXTManagerConnectivityDownEvent,
          vmwNSXTControllerConnectivityDegradedEvent,
          vmwNSXTControllerConnectivityDownEvent,
          vmwNSXTMtuMismatchEvent,
          vmwNSXEdgeBGPNeighbourDownEvent,
          vmwAnalyticsEvent,
          vmwAnalyticsOutlierEvent,
          vmwAnalyticsThresholdEvent,
          vmwVMCEvent,
          vmwPolicyManagerVrniDfwIPFixCollectorAbsent,
          vmwPolicyManagerNoDfwIPFixProfile
       }
       STATUS current
       DESCRIPTION
            "Set of added notifications (traps, informs) for 4.0.0 release."
        ::= { vmwNetworkInsightMIBGroups 75 }

  vmwNetworkInsightNotificationGroup7 NOTIFICATION-GROUP
       NOTIFICATIONS {
          vmwNSXTDoubleVlanTaggingEvent,
          vmwNSXTVtepDeleteEvent,
          vmwNSXTNoTzAttachedOnTnEvent,
          vmwNSXTExcludedVmFlowEvent,
          vmwKubernetesInsufficientPrivilegesEvent,
          vmwPKSKubernetesUnknownHostEvent,
          vmwDatasourceIdentificationChangedEvent,
          vmwLBPoolMemberDownEvent,
          vmwLBPoolDownEvent,
          vmwLBPoolMemberVMDownEvent,
          vmwLBServiceNodeIPNotFoundEvent,
          vmwLBServiceNodeMultipleNicFoundEvent,
          vmwLBVirtualServerDisableEvent,
          vmwLBPoolEmptyEvent,
          vmwDuplicateL3SwitchEvent,
          vmwArkinApplicationMemberLimitEvent,
          vmwNSXTSwitchIpfixEnabledEvent
       }
       STATUS current
       DESCRIPTION
            "Set of added notifications (traps, informs) for 4.1.0 release."
        ::= { vmwNetworkInsightMIBGroups 85 }

  vmwNetworkInsightNotificationGroup8 NOTIFICATION-GROUP
       NOTIFICATIONS {
          vmwUANIFileNotProvidedEvent,
          vmwUANIFileDoesNotExistEvent
       }
       STATUS current
       DESCRIPTION
            "Set of added notifications (traps, informs) for 4.2.0 release."
        ::= { vmwNetworkInsightMIBGroups 95 }

  vmwNetworkInsightNotificationGroup9 NOTIFICATION-GROUP
       NOTIFICATIONS {
          vmwNSXTStandaloneHostsWithoutVcEvent,
          vmwApplianceNotConfiguredEvent
       }
       STATUS current
       DESCRIPTION
            "Set of added notifications (traps, informs) for 5.0.0 release."
        ::= { vmwNetworkInsightMIBGroups 105 }

  vmwNetworkInsightNotificationGroup10 NOTIFICATION-GROUP
       NOTIFICATIONS {
          vmwSwitchPortUptimeThresholdRecededEvent,
          vmwFdbConfigStoreCleanupFailedEvent,
          vmwDiskAllocationInsufficientEvent,
          vmwNSXTControllerNodeToControlClusterConnectivityEvent,
          vmwNSXTControllerNodeToMgmtPlaneConnectivityEvent,
          vmwNSXTMPNodeToMgmtClusterConnectivityEvent,
          vmwBigIpInsufficientShellAccessEvent,
          vmwBigIpInsufficientPartitionAccessEvent,
          vmwBigIpInsufficientRoleEvent,
          vmwNSXTLatencyCollectorMismatchEvent,
          vmwNSXTLatencyNoBFDProfileEvent,
          vmwNSXTLatencyNotEnabledEvent,
          vmwHardwareVTEPMismatchEvent,
          vmwHardwareVTEPPortDownEvent,
          vmwNSXVLatencyNoDataEvent,
          vmwKubernetesBaseEvent,
          vmwVMCVMLimitExceededEvent,
          vmwVMCHostLimitExceededEvent,
          vmwVeloCloudEdgeDegradedTransQoeEvent,
          vmwVeloCloudEdgeDegradedVideoQoeEvent,
          vmwVeloCloudEdgeDegradedVoiceQoeEvent,
          vmwVeloCloudEdgeDownEvent,
          vmwVeloCloudLinkLostPacketEventRx,
          vmwVeloCloudLinkDegradedTransQoeEvent,
          vmwVeloCloudLinkLostPacketEventTx,
          vmwVeloCloudLinkDegradedVideoQoeEvent,
          vmwVeloCloudLinkDegradedVoiceQoeEvent,
          vmwVeloCloudLinkDownEvent,
          vmwNSXTHostNodeMgmtConnectivityStatusDownEvent,
          vmwNSXTEdgeNodeCtlrConnectivityStatusUnknownEvent,
          vmwNSXTHostNodeCtlrConnectivityStatusDownEvent,
          vmwNSXTHostNodeCtlrConnectivityStatusDegradedEvent,
          vmwNSXTHostNodeCtlrConnectivityStatusUnknownEvent,
          vmwNSXTHostNodePnicStatusDownEvent,
          vmwNSXTHostNodePnicStatusDegradedEvent,
          vmwNSXTHostNodePnicStatusUnknownEvent,
          vmwNSXTEdgeNodePnicStatusDownEvent,
          vmwNSXTEdgeNodePnicStatusDegradedEvent,
          vmwNSXTEdgeNodePnicStatusUnknownEvent,
          vmwNSXTHostNodeTunnelStatusDownEvent,
          vmwNSXTHostNodeTunnelStatusDegradedEvent,
          vmwNSXTHostNodeTunnelStatusUnknownEvent,
          vmwNSXTEdgeNodeTunnelStatusDownEvent,
          vmwNSXTEdgeNodeTunnelStatusDegradedEvent,
          vmwNSXTEdgeNodeTunnelStatusUnknownEvent,
          vmwNSXTHostNodeStatusDownEvent,
          vmwNSXTHostNodeStatusDegradedEvent,
          vmwNSXTHostNodeStatusUnknownEvent,
          vmwNSXTEdgeNodeStatusDownEvent,
          vmwNSXTEdgeNodeStatusDegradedEvent,
          vmwNSXTEdgeNodeStatusUnknownEvent,
          vmwSwitchPortOperationalDownEvent,
          vmwRouterInterfaceOperationalDownEvent,
          vmwUnderlayDeviceGenericEvent,
          vmwUnderlayDeviceFexOfflineEvent,
          vmwUnderlayDeviceFanMalFunctionEvent,
          vmwUnderlayDeviceTemperatureThresholdExceededEvent,
          vmwUnderlayDeviceFexFanMalFunctionEvent,
          vmwUnderlayDeviceFexPsMalFunctionEvent,
          vmwUnderlayDeviceModuleMalFunctionEvent,
          vmwUnderlayDevicePsMalFunctionEvent,
          vmwUnderlayDeviceBfdSessionRemovedEvent,
          vmwUnderlayDeviceLldpNeighbourRemovedEvent,
          vmwThresholdExceededEventDataSourceCpuUsage,
          vmwThresholdExceededEventDataSourceMemoryUsage,
          vmwThresholdExceededEventDataSourceTemperature,
          vmwDeploymentDefMismatchEvent,
          vmwNsxtLatencyServiceConfigMismatchEvent,
          vmwNsxtLatencyNodeGroupMismatchEvent,
          vmwNsxtLatencyStatProfileMismatchEvent,
          vmwHybridConnectBgpStatusDownEvent,
          vmwNSXTClusterBackUpDisabledEvent,
          vmwNSXTDFWFirewallDisabledEvent,
          vmwNSXTComputeManagerConnectionStatusNotUpEvent,
          vmwNSXTLogicalSwitchAdminStatusDownEvent,
          vmwNSXTLogicalPortOperationalStatusDownEvent,
          vmwNSXTLogicalPortOperationalStatusUnknownEvent,
          vmwNSXTLogicalPortReceivedPacketDropEvent,
          vmwNSXTLogicalPortTransmittedPacketDropEvent,
          vmwNSXTLogicalSwitchReceivedPacketDropEvent,
          vmwNSXTLogicalSwitchTransmittedPacketDropEvent,
          vmwNSXTRxPacketDropOnMPNicEvent,
          vmwNSXTRxPacketDropOnEdgeTnNicEvent,
          vmwNSXTRxPacketDropOnHostTnNicEvent,
          vmwNSXTTxPacketDropOnMPNicEvent,
          vmwNSXTTxPacketDropOnEdgeTnNicEvent,
          vmwNSXTTxPacketDropOnHostTnNicEvent,
          vmwNSXTMPNodeServiceClusterManagerStatusEvent,
          vmwNSXTMPNodeServiceCmInventoryStatusEvent,
          vmwNSXTMPNodeServiceControllerStatusEvent,
          vmwNSXTMPNodeServiceDataStoreStatusEvent,
          vmwNSXTMPNodeServiceHttpStatusEvent,
          vmwNSXTMPNodeServiceInstallUpgradeEvent,
          vmwNSXTMPNodeServiceLiagentStatusEvent,
          vmwNSXTMPNodeServiceManagerStatusEvent,
          vmwNSXTMPNodeServiceMgmtPlaneBusStatusEvent,
          vmwNSXTMPNodeServiceMigrationCoordinatorStatusEvent,
          vmwNSXTMPNodeServiceNodeMgmtStatusEvent,
          vmwNSXTMPNodeServiceNodeStatsStatusEvent,
          vmwNSXTMPNodeServiceNSXMessageBusStatusEvent,
          vmwNSXTMPNodeServiceNSXPlatformClientStatusEvent,
          vmwNSXTMPNodeServiceNSXUpgradeAgentStatusEvent,
          vmwNSXTMPNodeServiceNTPStatusEvent,
          vmwNSXTMPNodeServicePolicyStatusEvent,
          vmwNSXTMPNodeServiceSearchStatusEvent,
          vmwNSXTMPNodeServiceSNMPStatusEvent,
          vmwNSXTMPNodeServiceSSHStatusEvent,
          vmwNSXTMPNodeServiceSyslogStatusEvent,
          vmwNSXTMPNodeServiceTelemetryStatusEvent,
          vmwNSXTMPNodeServiceUIServiceStatusEvent,
          vmwVMCHostPerClusterLimitExceededEvent,
          vmwVMCVMPerHostLimitExceededEvent,
          vmwVMCClusterLimitExceededEvent,
          vmwProtectionEvent
       }
       STATUS current
       DESCRIPTION
            "Set of added notifications (traps, informs) for 5.2.0 release."
        ::= { vmwNetworkInsightMIBGroups 115 }

  vmwNetworkInsightNotificationGroup11 NOTIFICATION-GROUP
       NOTIFICATIONS {
          vmwNsxiApplianceAvailableEvent,
          vmwNsxiSubscriptionCreateFailedEvent,
          vmwNsxiSubscriptionDeleteFailedEvent,
          vmwNsxiSubscriptionUpdateFailedEvent,
          vmwNsxiSslHandshakeFailedEvent,
          vmwAnalyticsThresholdCompositeEvent,
          vmwAnalyticsThresholdCompositeProblemEvent,
          vmwLicenseExpiredEvent,
          vmwInGracePeriodEvent,
          vmwFailedDatasourceOperationEvent,
          vmwNsxtNotificationWebhookDisabledEvent,
          vmwNatRuleLargeSubnetEvent,
          vmwNSXTHostNodeMaintenanceModeEvent,
          vmwNSXTEdgeNodeMaintenanceModeEvent,
          vmwSDWanLinkTrafficThresholdEvent,
          vmwVMCCapacityThresholdBreachEvent,
          vmwNativeVlanMismatchEvent,
          vmwNativeVlanTaggingMismatchEvent,
          vmwSnapshotNotBuildingEvent
       }
       STATUS current
       DESCRIPTION
            "Set of added notifications (traps, informs) for 6.2.0 release."
        ::= { vmwNetworkInsightMIBGroups 125 }

  vmwNetworkInsightNotificationGroup12 NOTIFICATION-GROUP
       NOTIFICATIONS {
          vmwProtectionActiveEvent,
          vmwUnableToSendSNMPTrapsEvent,
          vmwStreamProcessingFailedEvent,
          vmwSNOWMandatoryPrivilegeMissingEvent,
          vmwVMCSDDCTGWConnectivityFailedEvent
       }
       STATUS current
       DESCRIPTION
            "Set of added notifications (traps, informs) for 6.4.0 release."
        ::= { vmwNetworkInsightMIBGroups 135 }

  vmwNetworkInsightNotificationGroup13 NOTIFICATION-GROUP
       NOTIFICATIONS {
          vmwNSXTEdgeDVPGsIPFIXDisabledEvent,
          vmwUnsupportedNsxAlbVersionEvent,
          vmwIpfixFlowLagEvent,
          vmwNSXALBSystemEvent,
          vmwTkgiKubernetesNotReachableEvent,
          vmwTkgiClustersInsufficientPrivilegesEvent,
          vmwNSXTRouterInterfaceRPFPacketDropEvent,
          vmwChangeEventsDroppedEvent,
          vmwHcxIXServiceStatusEvent,
          vmwHcxNEServiceStatusEvent,
          vmwHcxBMServiceStatusEvent,
          vmwHcxVMotionServiceStatusEvent,
          vmwHcxIXApplianceEncryptionTunnelStatusEvent,
          vmwHcxNEApplianceEncryptionTunnelStatusEvent,
          vmwHcxIXApplianceServicePipelineStatusEvent,
          vmwHcxNEApplianceServicePipelineStatusEvent,
          vmwHcxIXApplianceServiceTransportStatusEvent,
          vmwHcxNEApplianceServiceTransportStatusEvent,
          vmwHcxIXApplianceServiceSystemStateEvent,
          vmwHcxNEApplianceServiceSystemStateEvent,
          vmwHcxIXServiceNotRunningEvent,
          vmwHcxNEServiceNotRunningEvent,
          vmwHcxWanOptServiceNotRunningEvent,
          vmwPanLogInsightDroppedFlowEvent
       }
       STATUS current
       DESCRIPTION
            "Set of added notifications (traps, informs) for 6.6.0 release."
        ::= { vmwNetworkInsightMIBGroups 145 }

  vmwNetworkInsightNotificationGroup14 NOTIFICATION-GROUP
       NOTIFICATIONS {
         vmwHcxConnectionRuleViolationEvent,
         vmwHcxApplianceAllTunnelDownEvent,
         vmwHcxMtuMismatchEvent,
         vmwSwitchPortRPFPacketDropEvent,
         vmwCPLogInsightDroppedFlowEvent,
         vmwSNMPTrapEvent,
         vmwServiceRestartCountExceededEvent,
         vmwHcxWanOptServiceStatusEvent
       }
       STATUS current
       DESCRIPTION
            "Set of added notifications (traps, informs) for 6.8.0 release."
        ::= { vmwNetworkInsightMIBGroups 155 }

  vmwNetworkInsightNotificationGroup15 NOTIFICATION-GROUP
       NOTIFICATIONS {
         vmwNsxtIpfixMultipleCollectorConfigurationEvent,
         vmwHcxApplianceUnhealthyTunnelsEvent,
         vmwHcxManagerVersionMismatchEvent,
         vmwHcxApplianceVersionMismatchEvent,
         vmwIntentAlert,
         vmwKubernetesEvent,
         vmwSwitchPortBufferThresholdExceededEvent,
         vmwRouterInterfaceBufferThresholdExceededEvent,
         vmwBufferThresholdExceededEvent,
         vmwPortOperationalDownEvent,
         vmwSwitchPortRxNetworkUsageThresholdExceededEvent,
         vmwSwitchPortTxNetworkUsageThresholdExceededEvent,
         vmwSwitchPortRxNetworkUsageThresholdExceededCriticalEvent,
         vmwSwitchPortTxNetworkUsageThresholdExceededCriticalEvent,
         vmwManagementHostHighCPUUsageEvent,
         vmwManagementHostHighCPUUsageCriticalEvent,
         vmwHostUnHealthyEvent,
         vmwNSXControllerFSAvailableThresholdRecededEvent,
         vmwEdgeVmVnicRxPacketDropEvent,
         vmwEdgeVmVnicTxPacketDropEvent,
         vmwManagementHostPnicRxPacketDropEvent,
         vmwManagementHostPnicTxPacketDropEvent,
         vmwManagementHostConnectionStateDisconnectedEvent,
         vmwAllThresholdEvent,
         vmwVTGWDuplicateRoutesEvent,
         vmwApplianceNotRegisteredEvent,
         vmwRegCertExpiredEvent,
         vmwBackupFailedEvent,
         vmwAdditionalResourcesRequiredEvent,
         vmwCapacityReconfigurationRequiredEvent,
         vmwCapacityReconfigurationFailedEvent,
         vmwHighDiskIoUtilizationEvent,
         vmwNsxtSystemEventApiEvent,
         vmwServiceNowAppLimitExceededEvent,
         vmwAzureFlowCollectionErrorEvent,
         vmwAzureNetworkWatcherStorageErrorEvent,
         vmwAnalyticsMemoryLimitsExceededEvent,
         vmwHybridConnectAdvertisedSubnetsFailedEvent,
         vmwNSXTRxPacketDropOnNicEvent,
         vmwNSXTTxPacketDropOnNicEvent,
         vmwNSXTBGPNeighbourStateEvent,
         vmwVeloCloudEvent,
         vmwVeloCloudEdgeL7ApplicationLostPacketEvent,
         vmwVeloCloudEdgeL7ApplicationRetransmittedPacketEvent,
         vmwVeloCloudEdgeLocationNotSetEvent,
         vmwVeloCloudTunnelDegradedVoiceQoeEvent,
         vmwVeloCloudTunnelDegradedVideoQoeEvent,
         vmwVeloCloudTunnelDegradedTransQoeEvent,
         vmwVeloCloudQoeEvent,
         vmwHcxEvent,
         vmwLatencyNoDataEvent,
         vmwLinkMtuMismatchEvent,
         vmwPortModeMismatchEvent,
         vmwPortTrunkMismatchEvent,
         vmwPortChannelMismatchEvent,
         vmwDuplexMismatchEvent,
         vmwDuplicateMacAddressEvent,
         vmwDuplicateIPAddressEvent,
         vmwSTPPathCostMethodInconsistencyEvent,
         vmwHSRPSTPColocationEvent,
         vmwStigAccountPasswdEvent,
         vmwStigConsolePasswdEvent,
         vmwStigDefaultPasswdEvent,
         vmwStigMgmtPasswdEvent,
         vmwStigPlaintextPasswdEvent,
         vmwHSRPConfigurationEvent,
         vmwLoopDetectionEvent,
         vmwReachabilityEvent,
         vmwSegmentationEvent,
         vmwUnderlayProblem,
         vmwSwitchPortProblem,
         vmwPathProblem,
         vmwInvalidIntentEvent,
         vmwPassthroughEvents
       }
       STATUS current
       DESCRIPTION
            "Set of added notifications (traps, informs) for 6.10.0 release."
        ::= { vmwNetworkInsightMIBGroups 165 }


  vmwNetworkInsightNotificationGroup16 NOTIFICATION-GROUP
         NOTIFICATIONS {
            vmwPassthroughEvents
         }
         STATUS current
         DESCRIPTION
              "Set of added notifications (traps, informs) for 6.11.0 release."
          ::= { vmwNetworkInsightMIBGroups 180 }
END
