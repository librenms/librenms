RFC1215-MIB DEFINITIONS ::= BEGIN

-- This is really only part of RFC-1215.  The other part is built into
-- the Emissary MIB compiler as of Emissary release 4.0.
--
-- Importing RFC1215, below, is technically illegal, since technically
-- we're importing from this module to this module, but it does the
-- right thing and we know it's harmless, at least for Emissary.  The
-- problem is that RFC-1215, unlike every other standard MIB module,
-- defines both SMI-like stuff (the TRAP-TYPE macro, which is part of
-- the language definition for the SNMPv1 dialect of ASN.1) and
-- MIB-like stuff (the following trap definitions).  Emissary has the
-- SMI-like stuff wired in under the module name "RFC-1215", but the
-- trap definitions come from this file.
--
-- We could kludge up a fix for this, but since doing it this way is
-- harmless, it's not worth it.

IMPORTS
	snmp, ifIndex, egpNeighAddr
		FROM RFC1213-MIB
	TRAP-TYPE
		FROM RFC-1215;

  coldStart TRAP-TYPE
      ENTERPRISE  snmp
      DESCRIPTION
		  "A coldStart trap signifies that the sending
		  protocol entity is reinitializing itself such
		  that the agent's configuration or the rotocol
		  entity implementation may be altered."
      ::= 0

  warmStart TRAP-TYPE
      ENTERPRISE  snmp
      DESCRIPTION
		  "A warmStart trap signifies that the sending
		  protocol entity is reinitializing itself such
		  that neither the agent configuration nor the
		  protocol entity implementation is altered."
      ::= 1

  linkDown TRAP-TYPE
      ENTERPRISE  snmp
      VARIABLES   { ifIndex }
      DESCRIPTION
		  "A linkDown trap signifies that the sending
		  protocol entity recognizes a failure in one of
		  the communication links represented in the
		  agent's configuration."
      ::= 2

  linkUp TRAP-TYPE
      ENTERPRISE  snmp
      VARIABLES   { ifIndex }
      DESCRIPTION
		  "A linkUp trap signifies that the sending
		  protocol entity recognizes that one of the
		  communication links represented in the agent's
		  configuration has come up."
      ::= 3

  authenticationFailure TRAP-TYPE
      ENTERPRISE  snmp
      DESCRIPTION
		  "An authenticationFailure trap signifies that
		  the sending protocol entity is the addressee
		  of a protocol message that is not properly
		  authenticated.  While implementations of the
		  SNMP must be capable of generating this trap,
		  they must also be capable of suppressing the
		  emission of such traps via an implementation-
		  specific mechanism."
      ::= 4


  egpNeighborLoss TRAP-TYPE
      ENTERPRISE  snmp
      VARIABLES   { egpNeighAddr }
      DESCRIPTION
		  "An egpNeighborLoss trap signifies that an EGP
		  neighbor for whom the sending protocol entity
		  was an EGP peer has been marked down and the
		  peer relationship no longer obtains."
      ::= 5

END
