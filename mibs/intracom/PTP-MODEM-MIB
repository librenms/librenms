PTP-MODEM-MIB DEFINITIONS ::= BEGIN
                                                
   IMPORTS
   MODULE-IDENTITY, OBJECT-TYPE,
   NOTIFICATION-TYPE, OBJECT-IDENTITY,
   Integer32, Counter32, Counter64, Unsigned32, IpAddress, TimeTicks
   FROM SNMPv2-SMI
   TEXTUAL-CONVENTION, DateAndTime, RowStatus, TruthValue
   FROM SNMPv2-TC
   MODULE-COMPLIANCE, OBJECT-GROUP,
   NOTIFICATION-GROUP
   FROM SNMPv2-CONF
   InetAddressType, InetAddress
   FROM INET-ADDRESS-MIB
   SnmpAdminString
   FROM SNMP-FRAMEWORK-MIB
   intracom
   FROM ICOM-SMI;
   
   --=========================================================
   --PTP MODEM MIB MODULE
   --=========================================================
   ptpModemMIB MODULE-IDENTITY
 
   LAST-UPDATED "201901170000Z"
   ORGANIZATION "Intracom Telecom S.A."
   CONTACT-INFO
   "   
        Evagelos Martzelis 
          
          Intracom S.A.
          Systems Software Development Dept.
          A3 building
          19.7Km Markopoulo Ave
          GR-19002 Peania, Athens
          Greece
          tel: +30-210-6674057

          emar@intracom.gr   
   "

   DESCRIPTION
         "This is the management information for ptp modems and ODU station.
         "

   REVISION    "201901170000Z"  -- January 17, 2019
   DESCRIPTION "
        Addition of oduChannelTxFreqEntry.
   "

   REVISION    "201812130000Z"  -- dtzou: December 13, 2018
   DESCRIPTION "
        Addition of oduStringBootLoaderVersion in oduVersionEntry.
   "

   REVISION    "201802150000Z"  -- dtzou: February 15, 2018
   DESCRIPTION "
        Addition of slave1FpgaVersion in modemVersionEntry.
   "

   REVISION    "201706070000Z"  -- dtzou: June 07, 2017
   DESCRIPTION "
        Addition of oduCfgAntennaAlignMode in oduConfigEntry
        and oduStatusAntennaAlignMode in oduStatusEntry.
   "

   REVISION    "201705230000Z"  -- dtzou: May 23, 2017
   DESCRIPTION "
        Addition of oduTxPowerLicenseFailure, ptpAtpcMaxTxPowerLicenseFail
        and ptpAtpcMinTxPowerLicenseFail
   "

   REVISION    "201704190000Z"  -- dtzou: April 19, 2017
   DESCRIPTION "
        Addition of modemActiveTddRxRatio in modemStatusEntry.
        Addition of modemStatusAirLinkDistance in modemStatusEntry.
        Addition of modemSuppTDDTxRatioBitMap in modemSuppCapabilitiesEntry.
   "
   
   REVISION    "201701270000Z"  -- rbas: January 27, 2017
   DESCRIPTION "
		Rename of modemTddTxRatio to modemCfgTddTxRatio in modemConfigEntry
        Addition of modemActiveTddTxRatio in modemStatusEntry.
   "
   
   REVISION    "201701230000Z"  -- rbas: January 23, 2017
   DESCRIPTION "
        Addition of modemTddRole and modemTddTxRatio value in modemConfigEntry.
   "
   
   REVISION    "201611250000Z"  -- dtzou: November 25, 2016
   DESCRIPTION "
        Addition of profileEnhancedACM value in modemPHYprofile.
   "
   
   REVISION    "201609260000Z"  -- tks: September 26, 2016
   DESCRIPTION "
        Addition of modemRemoteAddressTable.
   "

   REVISION    "201608310000Z"  -- dtzou: August 31, 2016
   DESCRIPTION "
        Addition of modemMaxATPCTxPower and modemMinATPCTxPower in modemAdaptiveConfEntry
   "
   
  REVISION    "201604050000Z"  -- tks: April 05, 2016
   DESCRIPTION "

        o  Addition of the Textual Conventions PtpModemChannelBWType.
        o  Extension of the value range of oduBandSelection object by changing the syntax from
           INTEGER to PtpModemChannelBWType but with the same enumeration as before with
           the addition of values supporting 10MHz, 30MHz, 50MHZ, 112MHZ
        o  Addition of the read-only object modemStatusSuppCapId.
        o  Addition of read-only objects modemStatusSuppCapTxPhymodId, modemStatusSuppCapRxPhymodId, 
           to get the Tx and Rx phymodes currently used.
        o  Addition of modemSuppCapabilitiesTable that models supported Modem Capabilities combinations
           for the modem types that can be used in the system.
        o  Addition of modemSuppCapPhymodCapacityTable, that models the modem supported phymod capacities 
           per supported modem phymode, i.e Modulation and FEC Rate types combinations and 
           supported Modem Capabilities combination.
    "

   REVISION    "201602100000Z"  -- dtzou: Feb. 10, 2016
   DESCRIPTION "
        Change default value of modemMaxAutoPHYmod.
   "
   
   REVISION    "201601260000Z"  -- dtzou: Jan. 26, 2016
   DESCRIPTION "
        New modemRxSpectralInversion added in modemConfigEntry.
   "

   REVISION    "201512020000Z"  -- dtzou: Dec. 02, 2015
   DESCRIPTION "
        Update description of oduRadioAlarms.
   "
   
   REVISION    "201509230000Z"  -- dtzou: Sept. 23, 2015
   DESCRIPTION "
        oduInterferenceScanAction, oduInterferenceScanConfigEntry
        oduInterferenceScanMeasureEntry, oduInterferenceScanStatusEntry
        added.
   "
   
   REVISION    "201509180000Z"  -- dtzou: Sept. 18, 2015
   DESCRIPTION "
        The default value of modemRxLdpcDecodersStressThresh
        has changed to 0xFFFFFFFF.
   "
   
   REVISION    "201506260000Z"  -- rbas: June 26, 2015
   DESCRIPTION "
        - oduBandSelection updated description 
          (the ptp500MhzBand(8) value is added for the EBAND)
		- updated description regarding the unit value (MHz of KHz) of the
		  oduSetTxFrequency, oduCurrentTxFrequency, oduCurrentRxFrequency, 
		  oduFirstFreq, oduLastFreq, oduFreqStep, oduDuplexSpacing
		  non V/E-Band systems use KHz units
		  V/E-Band systems use MHz units
   "
   REVISION    "201506230000Z"  -- rbas: June 23, 2015
   DESCRIPTION "

        strnAntennaConfig is N/A at the EBAND
   "
   
   REVISION    "201502260000Z"  -- dtzou: Feb. 26, 2015
   DESCRIPTION "

        oduBandSelection updated description
   "
   
  REVISION    "201502060000Z"  -- dtzou: Feb. 06, 2015
   DESCRIPTION "

        New value added for strnAntennaStartAction.
   "

  REVISION    "201412150000Z"  -- dtzou: Dec 15, 2014
   DESCRIPTION "

        modemChangesInPHYMode1..modemChangesInPHYMode16 added in
        modemPermormanceCountersEntry.
   "

  REVISION    "201410210000Z"  -- rbas: Oct 21, 2014
   DESCRIPTION "

        strnAntennaConfig is N/A at the OSDRS
   "

  REVISION    "201406180000Z"  -- dtzou: June 18, 2014
   DESCRIPTION "

        Init action added in strnAntennaStartAction.
   "

  REVISION    "201406030000Z"  -- dtzou: June 03, 2014
   DESCRIPTION "

        ptpModemPhymodLicenseFailure trap added. 
        Valid for OmniBAS-2W-16E1 and OmniBAS-8W
   "

  REVISION    "201403180000Z"  -- dtzou: March 18, 2014
   DESCRIPTION "

        o  modemTxAirthroughput, modemRxAirthroughput valid also for OmniBAS-8W
        o  Updated description for modemEthTxWireByteCounterLow, modemEthTxWireByteCounterHigh 
   "

  REVISION    "201402270000Z"  -- dtzou: February 27, 2017
   DESCRIPTION "

        o  oduRadioModel valid for all PTP_FODU systems (STRN-PtP, OB XRe, OSDR-PtP) 
   "

  REVISION    "201311180000Z"  -- dtzou: November 18, 2013
   DESCRIPTION "

        o  New oduCfgDuplexSpacing, oduDuplexSpacing have been added in oduConfigEntry and oduCapabilitiesEntry
           respectively for duplex spacing setting.
   "

  REVISION    "201310010000Z"  -- dtzou: October 01, 2013
   DESCRIPTION "

        o  New oduBootLoaderVersion has been added in OduVersionEntry for SODU version identification. 
           It is valid for all system types except OmniBAS-XR 
    "

    REVISION    "201307180000Z"  -- dtzou: July 18, 2013
    DESCRIPTION
         "
            PTP-STN:
            o Addition of strnAntennaGenConfigTable
            o Addition of strnAntennaAutoConfigTable
            o Addition of strnAntennaAutoFineConfigTable
            o Addition of strnAntennaManualConfigTable
            o Addition of strnAntennaCurrentStatusTable
            o Addition of strnAntennaMeasurementTable
            o Addition of strnAntennaPeakTable
            o Addition of strnAntennaStartAction scalar object
            o Addition of strnAntennaNotificationObjects
            o Addition of modemLinkId, modemLinkIdCheck objects in ModemConfigEntry
            o Updated Information for modemStatLinkStatus
            o Addition of oduRadioModel in oduVersionEntry
            o Addition of remoteModemLinkId in modemRemoteStatusEntry
         "

  REVISION    "201307090000Z"  -- dtzou: July 09, 2013
   DESCRIPTION "

        o  New oduModelSubType has been added in OduVersionEntry for SODU version identification. 
           It is valid for OmniBAS 4W-HE and OMNIBAS 2W-16E1 
    "

  REVISION    "201307030000Z"  -- dtzou: July 03, 2013
   DESCRIPTION "

        o  New value ptp14MhzNarrowBand(6) has been added in OID oduBandSelection for RBW4 256QAM 14MHz channel. 
           It is valid for OmniBAS 4W-HE and OMNIBAS 2W-16E1 
    "
    REVISION    "201304160000Z"  -- dtzou: April 14, 2013
    DESCRIPTION
         "
            OMNIBAS-2W-16E1 (NEPTUNE MODEMS):
            o Addition of modemClockSourceEntry
         "

    REVISION    "201303130000Z"  -- rbas: March 13, 2013
    DESCRIPTION 
         "  
            PTP_FODU:
            o Addition of ODU SODU in oduModelType 
            o SODU has the same behaviour as FLEX FODU:
              - oduThresAlarms and oduThresAlarmsNotification
              - oduAnalogueMonitorEntry.oduMonitorPlus7V
              - oduAnalogueMonitorEntry.oduMonitorMinus5V
              - oduAnalogueMonitorEntry.oduMonitorPlus6point5V
              - oduAnalogueMonitorEntry.oduMonitorMinus48V
            o SODU inventory codes are added (oduInventoryInfoTable)
         "

    REVISION    "201302150000Z"  -- rbas: Feb 15, 2013
    DESCRIPTION 
         "  
            PTP_FODU:
            o oduAutoUpdate accepted value is auto only
            o oduTestType is applicable with accepted test value loopBackONTest
              oduTestType description is updated, too.
         "

    REVISION    "201302130000Z"  -- rbas: Feb 13, 2013
    DESCRIPTION 
         "  
            smilint changes:
            o ptpFlexModemMHSIndex got a range restriction
            o oduTestTimeout and oduTestTimer status is made current
            o NOTIFICATION-GROUPS syntax is fixed
            o reverse chronological order in revisions is fixed
         "

    REVISION    "201302060000Z"  -- rbas: Feb 06, 2013
    DESCRIPTION 
         "  
            o OMNIBAS-2W-16E1 and PTP_FODU (NEPTUNE modems): ptpNeptuneRedAlarm and ptpNeptuneRedAlarm are added.
         "

    REVISION    "201301300000Z"  -- rbas: Jan 30, 2013
    DESCRIPTION 
         "  
            o OMNIBAS-XR: modemMinAutoPHYMod has value range 1..16
         "

    REVISION    "201301040000Z"  -- rbas: Jan 04, 2013
    DESCRIPTION 
         "  
            o OMNIBAS-4W-HE and OMNIBAS-2W-16E1: modemMinAutoPHYMod has value range 1..16
         "

    REVISION    "201211300000Z"  -- rbas: Nov 30, 2012
    DESCRIPTION 
         "  
            o NEPTUNE modem:
              Addition of new OID modemEthRxShortEvents in modemEthernetCountersEntry
              Added information for the modemStatLinkIndicator.
              Valid for system OmniBAS-2W-16E1 only
         "

    REVISION    "201211190000Z"  -- emar: Nov 19, 2012
    DESCRIPTION 
         "  
            o NEPTUNE modem:
              Addition of new OIDs modemTxAirthroughput, modemRxAirthroughput
              Changed description of modemStatLinkIndicator 
              Valid for system OmniBAS-2W-16E1 only    
         "

  REVISION    "201211080000Z"  -- emar: November 08, 2012
   DESCRIPTION "

        o  Addition of oduProductCode, oduRfuProductCode, 
           Valid for system OmniBAS-4W, OmniBAS-2W, OmniBAS-4W-HE, OmniBAS-2W-16E1. 
    "

   REVISION    "201211020000Z"  -- emar: November 02, 2012
   DESCRIPTION "

        o  Addition of oduTestNotification
           Valid for system OmniBAS-4W, OmniBAS-2W, OmniBAS-4W-HE, OmniBAS-2W-16E1. 

    "

    REVISION    "201209260000Z"  -- emar: Sep 26, 2012
    DESCRIPTION 
         "  
            o Addition of new OIDs oduTestType, oduTestTimeout, oduTestTimer 
              Valid for system OmniBAS-4W, OmniBAS-2W, OmniBAS-4W-HE, OmniBAS-2W-16E1.    
         "

    REVISION    "201209200000Z"  -- emar: Sep 20, 2012
    DESCRIPTION 
         "  
            o Changed description of OID ptpFlexModemMHSRobustness
         "

    REVISION    "201209180000Z"  -- emar: Sep 18, 2012
    DESCRIPTION 
         "  
            o MHS specification modification. Default value of object 
              ptpFlexModemMHSRobustness changed from off to on(7)
         "

    REVISION    "201207300000Z"  -- emar: July 30, 2012
    DESCRIPTION 
         "  
            o Addition of new table ptpFlexModemMHSTable 
	          valid for 4wHE or 2w16E1 or XR      
         "


    REVISION    "201207170000Z"  -- emar: July 17, 2012
    DESCRIPTION "
                   o The  objects oduSetTxPower, oduMaxTxPower, oduMinTxPower, oduCurrentTxPowerwibas_ap
                      have been changed from unsigned to signed integer.
         
    "

   REVISION    "201206180000Z"  -- emar: June 18, 2012
    DESCRIPTION "
                   o The  OID  muteModulationChangeTrap changed with muteRxModulationChangeTrap 
                   o The OID   muteTxModulationChangeTrap added

    "

    REVISION    "201206100000Z"  -- emar: June 11, 2012
    DESCRIPTION "
                       
                       o The value range of the OID  muteModulationChangeTrap OID has been changed:
		          The new values are shown below:
			   modTxRxTrapOff(0),     
			   modTxOnRxOffTrap(1), 
			   modTxOffRxOnTrap(2), 
			   modTxRxTrapOn(3)     

                     "

         REVISION    "201206060000Z"  -- rbas: June 6, 2012
         DESCRIPTION " smilint changes
                       o The oduMonitorPlus6_5 is changed to oduMonitorPlus6point5
                     "

         REVISION    "201205160000Z"  -- rbas: May 16, 2012
         DESCRIPTION " smilint changes
                       o modemSecondsInPhyChanges is removed from modemPermormanceCountersEntry 
                         (it was never implemented)
                       o The default value of oduTemperature is changed to 0
                       o The default value of modemStatFail is changed to 0
                       o The modemConfigEntryIndex got a range restriction
                       o The modemStatusEntryIndex got a range restriction
                       o The modemPermormanceCountersEntryIndex got a range restriction
                       o The modemEthernetCountersEntryIndex got a range restriction
                       o The modemVersionEntryIndex got a range restriction
                       o The modemRemoteStatusEntryIndex got a range restriction
                       o The modemAdaptiveConfEntryIndex got a range restriction
                       o The xpicModemStatusCountersIndex got a range restriction
                       o The acquireModemCountersIndex got a range restriction
                       o The fecCountersIndex got a range restriction
                       o The modemThreshAlarmConfEntryIndex got a range restriction
                       o The g826CounterIndex got a range restriction
                       o The oduConfigEntryIndex got a range restriction
                       o The oduCapabilitiesEntryIndex got a range restriction
                       o The oduStatusEntryIndex got a range restriction
                       o The oduAnalogueMonitorEntryIndex got a range restriction
                       o The oduVersionEntryIndex got a range restriction
                       o The oduAlarmConfigurationEntryIndex got a range restriction
                       o The oduCfgTypeIndex got a range restriction
                       o The oduRFUVersionIndex got a range restriction
                       o The oduServChanStatIndex got a range restriction
                       o The modemXpicConfIndex  got a range restriction
                       o The default oduConfigPower changed to the proper enum.
                       o The units of conformance are fixed
                     "

         REVISION    "201205100000Z"  -- emar: May 10, 2012
         DESCRIPTION "
                       o New Trap ptpModemTxPHYModulationChange has been added.  

                       o New Trap ptpModemRxPHYModulationChange has been added.
                       
                       o New muteModulationChangeTrap OID has been added.
                     "

         REVISION    "201205040000Z"  -- emar: May 4, 2012
         DESCRIPTION "
                       o OID oduSetTxPower added description about 
                         value interpretation for PTP_R products 

                       o Oid oduPinRSSIThres changed description about 
                         value interpretation from  -0.1dbm to -1dbm

                     "

         REVISION    "201203200000Z"  -- emar: March 20, 2012
         DESCRIPTION "
                       o Trap ptpRemoteModemStatLinkStatusChange  
                         has been updated, new value linkStatusUnknown(3)
                         has been added 

                       o Oid remoteModemLinkStatus has been updated,
                         new value linkStatusUnknown(3)has been added

                       o The description of oduRFUModelType  
                         has been updated
                     "

         REVISION    "201202170000Z"  -- emar: Feb 17, 2012
         DESCRIPTION "
                       o The size of the objects  oduRFUModelNumber, oduRFUSerialNumber 
                         has been changed.
                     "

         REVISION    "201201250000Z"  -- emar: Jan 25, 2012
         DESCRIPTION "
                       o Object  modemStatFail value meaning has been changed.
                         The change affects Oid modemStatFail and the alarm 
                          ptpModemFailureChange.
                         
                          Bit value meaning:
                      
                          bit0: Clock PLL info               
                           - 0: PLL locked   (Alarm ceased)               
                           - 1: PLL UnLocked (Alarm raised)                 
                          bit1: Receiver's PLL info          
                           - 0: PLL Locked    (Alarm ceased)              
                           - 1: PLL Unlocked  (Alarm raised) 
                          bit2: Transmiter's PLL info               
                           - 0: PLL Locked     (Alarm ceased)            
                           - 1: PLL Unlocked   (Alarm raised) 
                          bit3: Modem Chip Failure              
                          - 0: Modem Chip OK        (Alarm ceased)       
                          - 1: Modem Chip Failure   (Alarm raised)
                          bit4: Modem Chip Lock  
                          - 0: Modem Chip Locked    (Alarm ceased)
                          - 1: Modem Chip Unlocked (Alarm raised)                     
                       "

         REVISION    "201201230000Z"  -- emar: Jan 23, 2012
         DESCRIPTION "
                      o Object modemAlarmThreshStatus description has been updated
                        new bit2 has been added, see details below

                        bit2: Modem PHY modulation configuration is not supported.                                                    
                               The Alarm is raised, when the modem Physical Modulation value stored in
                               the configuration, is not supported by the inserted modem in the system.                                            
                               - 0: Alarm ceased
                               - 1: Alarm raised
                   "

   REVISION    "201112020000Z"  -- emar: Dec 2, 2011
   DESCRIPTION "
               o Object oduThresAlarms description has been updated
                 bit3 and bit4 are not used in case of RFU ODU 
  
    "

   REVISION    "201111240000Z"  -- emar: Nov 24, 2011
   DESCRIPTION "
               o  The default value of the oduTempThres has changed to 65
  
    "

 REVISION    "201111230000Z"  -- emar: Nov 23, 2011
   DESCRIPTION "
               o  The name RFU is used in ODU version info.
  
               o  The Oid oduRFUCLIE has been obselete.
                   It is not used any more

    "

   REVISION    "201109060000Z"  -- emar: Sep 6, 2011
   DESCRIPTION "
               o  The name of the value of the OID modemXpicConfEnabled
                  in the modemXpicGroupConfEntry has been changed from 
                  xpicModemEnabled(1) to xpicenabled(1) and
                  ptpModemEnabled(2) to xpicdisabled(2) .
    "

   REVISION    "201108300000Z"  -- emar: Aug 30, 2011
   DESCRIPTION "
               o  New values ptp40MhzBand(4), ptp20MhzBand(5) have been added in OID
                  oduBandSelection. The is valid for
                  for OmniBAS 2w and OMNIBAS 4W
    "

   REVISION    "201107220000Z"  -- emar: Jul 22, 2011
   DESCRIPTION "
               o  The calculation of the value of 
                  modemRxNormalizedMSEThresh has 
                  changed to 0.1db step.
                  Defined in the description of the Oid.

               o  The default value of the OID
                   modemRxLdpcDecodersStressThresh
                   has changed to 1.
                  
               o  Added the ODU service channel 
                  table 

               o  Added the Odu config type table. 
                  
               o  Added the Odu RFU version table.
                  
    "

   REVISION    "201107080000Z"  -- emar: Jul 8, 2011
   DESCRIPTION "
               o  Added new tables oduCfgTypeTable, oduRFUVersionTable
                  to support ODU RFU. ODU tables have been modified 
                  to support ODU RFU.
    "

   REVISION    "201103100000Z"  -- emar: Mar 10, 2011
   DESCRIPTION "
               o  Added counters for G.826 performance 
                  measurements on radio link.
                  Valid for  for Omnibas-4W and Omnibas-2W products.
               o  Added compliance information

               o  Updated description of the OID modemXpicConfIndex 

               o  Updated description of the OID  modemStatPHYModValue

               o  Updated description of the OID modemStatRxPHYModValue
    "   

   REVISION    "201101201008Z"  -- emar: January 20, 2011
   DESCRIPTION "
             Changes for Omnibas-4W  Omnibas-2W products.
              o Oid modemPHYprofile has been updated, with a new value  profileExtraCapacity(3)
              o Oid oduPinRSSIThres has been updated the description
              o Oid oduTempThres has been changed the range (-128..127) 
              o Oid oduAlarmConfTempLoThresh has been changed the range(-128..127)
   "

   REVISION    "201011301008Z"  -- emar: November 30, 2010
   DESCRIPTION "
           Changes for Omnibas-4W  Omnibas-2W products.
           o Added OID ModemStatusEntry.modemAlarmThreshStatus                                               
           o Added notification ptpNotificationObjects.ptpmodemAlarmThreshStatusAlarm 
           o Added table  modemThreshAlarmConfTable
           o Changed description in  oduStatusEntry.oduThresAlarms     B2
           o Changed description in  oduStatusEntry.oduGenConfigAlarm  B5
           o Added OID oduAlarmConfigurationEntry.oduAlarmConfTempLoThresh
           o Changed description in OID  oduAlarmConfigurationEntry.oduTempThres 
           o Changed description in notification oduNotificationObjects.oduThresAlarmsNotification                                                           
           o Changed description in notification oduNotificationObjects.oduGenConfigAlarmNotification
    "

   REVISION    "201011111008Z"  -- emar: November 11, 2010
   DESCRIPTION "
               o  Added the ptpXpicModeAlarm Alarm 
                        for Omnibas-4W product.
    "

   REVISION    "201010141642Z"  -- emar: October 14, 2010
   DESCRIPTION "
               o  Added the Xpic Modem configuration Table 
                        for Omnibas-4W product.
    "

   REVISION    "201009210000Z"  -- emar: Sep 21, 2010
   DESCRIPTION "
               o  Added the xpic Modem Status Counters 
                         for Omnibas-4W product and 
                        the acquire Modem Counters ,
                        and FEC Counters feature
                        for Omnibas-4W and Omnibas-2W products.

               o   Changed the value range of the OID     
                   modemMinAutoPHYMod       
                   The allowed value range has only one   
                   value which is 1. 

    "

      ::= { intracom 55 } 

   --=====================================================================
   modemConfigMibObjects  OBJECT-IDENTITY
   STATUS   current
   DESCRIPTION    " 7 objects for ptp modem MIB"
      ::= { ptpModemMIB 1 }      


   ---=========================================================
   -------------- Textual Conventions 
   ---=========================================================
  -- Definition of textual conventions                
   
   PtpPHYProfileType ::= TEXTUAL-CONVENTION

   STATUS current
   DESCRIPTION 
         " Ptp PHY profile type"
   SYNTAX INTEGER {   
      profOptimumGain(0),
      profileNormal(1),
      profileOptimumCapacity(2),
      profileExtraCapacity(3),
      profileOptimumLatency(4),
      profileEnhancedACM(5)
      }

   PtpACMode ::= TEXTUAL-CONVENTION

   STATUS current
   DESCRIPTION 
         " Ptp ACM Mode"
   SYNTAX INTEGER {   
      manual(0),
      auto(1)
      }

   PtpRestartMode ::= TEXTUAL-CONVENTION

   STATUS current
   DESCRIPTION 
         " Ptp Restart Mode"
   SYNTAX INTEGER {   
      none(0),
      restart(1)
      }

   PtpErrorStatus ::= TEXTUAL-CONVENTION

   STATUS current
   DESCRIPTION 
         " Ptp Error Status"
   SYNTAX INTEGER {   
      noErrorStatus(0),
      errorStatus(1)
      }

   PtpLinkStatus ::= TEXTUAL-CONVENTION

   STATUS current
   DESCRIPTION 
         " Ptp Link Status"
   SYNTAX INTEGER {   
      waitLock(0),
      lock(1),
      failed(2),
      waitAlign(3),
      waitLinkId(4),
      waitLinkIdAuto(5),
      sleep(6)         
      }


   PtpLinkErrorState ::= TEXTUAL-CONVENTION

   STATUS current
   DESCRIPTION 
         " Ptp Modem Error State"
   SYNTAX INTEGER {   
      success(0),
      failAtAGC(1),
      failAtTiming(2),
      failAtFreqSweep(3),
      errorInMSE(4),
      bitError(5),
      serviceError(6),
      failAtBLIND(7),
      failOnTimeOut(10),
      stopped(11),
      fatalError(12)
      }

   PtpCounterOperation ::= TEXTUAL-CONVENTION

   STATUS current
   DESCRIPTION 
         " Ptp Operation action"
   SYNTAX INTEGER {   
      stopCounter(0),
      startCounter(1),
      resetCounter(2)
      }

  PtpOperationState ::= TEXTUAL-CONVENTION

   STATUS current
   DESCRIPTION 
         " Ptp Operation State"
   SYNTAX INTEGER {   
      operationStateOFF(0),
      operationStateON(1)
      }

  PtpReferenceLevel ::= TEXTUAL-CONVENTION

   STATUS current
   DESCRIPTION 
         " Ptp Reference level "
   SYNTAX INTEGER {   
      levelHigh(0),
      levelLow(1)
      }

  PtpModemProtMode ::= TEXTUAL-CONVENTION

   STATUS current
   DESCRIPTION 
         " Ptp operation mode"
   SYNTAX INTEGER {   
      none(0),
      working(1),
      protect(2)
      }
      
  PtpModemLinkStatus ::= TEXTUAL-CONVENTION

   STATUS current
   DESCRIPTION 
         " Link Status "
   SYNTAX INTEGER {   
      unlocked(0),
      locked(1),
      offLine(2),
      linkStatusUnknown(3)
     }
      
   PtpOnOffOper ::= TEXTUAL-CONVENTION

   STATUS current
   DESCRIPTION 
         " Ptp Restart Mode"
   SYNTAX INTEGER {   
      off(0),
      on(1)
      }
      
  PtpModemPowerModeState ::= TEXTUAL-CONVENTION

   STATUS current
   DESCRIPTION 
         " Modem power mode state "
   SYNTAX INTEGER {   
            manual(0),  
            optimum(1), 
            max(2)
      }


  PtpModemChannelBWType ::= TEXTUAL-CONVENTION
      STATUS      current
      DESCRIPTION
          "Modem Channel BW type.
          "
      SYNTAX      INTEGER {
            ptp7MhzBand              (0),
            ptp14MhzBand             (1),
            ptp28MhzBand             (2),
            ptp56MhzBand             (3),
            ptp40MhzBand             (4),
            ptp20MhzBand             (5),
            ptp14MhzNarrowBand       (6),
            ptp250MhzBand            (7),
            ptp500MhzBand            (8),
            ptp10MhzBand             (9),
            ptp30MhzBand             (10),
            ptp50MhzBand             (11),
            ptp112MhzBand            (12),
            ptp750MhzBand            (13),
            ptp1000MhzBand           (14),
            ptp1500MhzBand           (15),
            ptp100MhzBand            (16),
            ptp62Point5MhzBand       (17),
            ptp125MhzBand            (18),
            ptp2000MhzBand           (19),
            ptp60MhzBand             (20),
            ptp80MhzBand             (21)
      }

	TddTxRatio ::= TEXTUAL-CONVENTION
      STATUS      current
      DESCRIPTION
          "Modem Tdd Tx Ratio Type.
          "
      SYNTAX      INTEGER {
            one2one    (1), 
			two2one    (2),
			three2one  (3),
			five2one   (4),
			seven2one  (5),
			eleven2one (6),
			one2two    (7),
			one2three  (8),
			one2five   (9),
			one2seven  (10),
			one2eleven (11)
      }
	  
	CfgAirEncryptAdminState ::= TEXTUAL-CONVENTION
      STATUS      current
      DESCRIPTION
          "Modem Air Encryption Admin State Type.
          "
      SYNTAX      INTEGER {
            airEncryptionOn    (1),
			      airEncryptionOff   (2)
      }
	
  CfgForceCfgSet ::= TEXTUAL-CONVENTION
      STATUS      current
      DESCRIPTION
          "Force set modem configuration state.
          "
      SYNTAX      INTEGER {
            forceSetCfgTrue    (1),
            forceSetCfgFalse   (2)
      }

      -- Error Conditions:    see ptp_mib.h

  OduChannelBWIndexType ::= TEXTUAL-CONVENTION
      STATUS      current
      DESCRIPTION
          "Modem Channel BW index values."
      SYNTAX      INTEGER {
            ptp7MhzBand        (1),
            ptp14MhzBand       (2),
            ptp28MhzBand       (3),
            ptp56MhzBand       (4),
            ptp40MhzBand       (5),
            ptp20MhzBand       (6),
            ptp14MhzNarrowBand (7),
            ptp250MhzBand      (8),
            ptp500MhzBand      (9),
            ptp10MhzBand       (10),
            ptp30MhzBand       (11),
            ptp50MhzBand       (12),
            ptp112MhzBand      (13),
            ptp750MhzBand      (14),
            ptp1000MhzBand     (15),
            ptp1500MhzBand     (16),
            ptp100MhzBand      (17),
            ptp62Point5MhzBand (18),
            ptp125MhzBand      (19),
            ptp2000MhzBand     (20),
            ptp60MhzBand       (21),
            ptp80MhzBand       (22)
      }

 ---=========================================================

   --=========================================================                                      
   -- MODEM MIB CONTROL OBJECTS
   --=========================================================

   --=========================================================                                      
   -- MODEM CONFIGURATION TABLE
   --=========================================================
   
   modemConfig OBJECT IDENTIFIER ::= {    modemConfigMibObjects 1 }

   
   modemConfigTable OBJECT-TYPE
      SYNTAX       SEQUENCE OF   ModemConfigEntry
      MAX-ACCESS   not-accessible
      STATUS       current
      DESCRIPTION  " 
          This table models the Modem Configuration general parameters.
                   "    
      ::= { modemConfig  1 }

   modemConfigEntry OBJECT-TYPE 
      SYNTAX       ModemConfigEntry
      MAX-ACCESS   not-accessible
      STATUS       current
      DESCRIPTION  " "
      INDEX  {modemConfigEntryIndex} 
      ::={modemConfigTable 1 }

    ModemConfigEntry ::= SEQUENCE {                   
      
        modemConfigEntryIndex  INTEGER,
        modemPHYprofile         PtpPHYProfileType,
        modemACMmode     PtpACMode,
        modemPHYmodulationVal      INTEGER,
        modemRestart   PtpRestartMode,
        modemConfigDownLoadValues INTEGER,
        modemLinkId  INTEGER,
        modemLinkIdCheck  INTEGER,
        modemRxSpectralInversion INTEGER,
        modemTddRole INTEGER,
        modemCfgTddTxRatio TddTxRatio,
        modemCfgAirEncryptAdminState CfgAirEncryptAdminState,
        modemCfgForceCfgSet CfgForceCfgSet
   }   
   
   modemConfigEntryIndex   OBJECT-TYPE 
      SYNTAX       INTEGER (1)
      MAX-ACCESS   not-accessible
      STATUS       current
      DESCRIPTION  "Index of the ModemConfigEntry. 
                    It is restricted to 1 instance."
      ::= { modemConfigEntry 1 }

   modemPHYprofile OBJECT-TYPE 
      SYNTAX       PtpPHYProfileType
      MAX-ACCESS   read-write
      STATUS       current
      DESCRIPTION  " Modem PHY Profile 
                     Value Range  profOptimumGain(0),       
                                  profileNormal(1),         
                                  profileOptimumCapacity(2),
                                  profileExtraCapacity(3),
                                  profileOptimumLatency(4),
                                  profileEnhancedACM(5) 
      " 
      DEFVAL {profOptimumGain}
      ::= { modemConfigEntry 2 }   
      
   modemACMmode OBJECT-TYPE 
      SYNTAX       PtpACMode
      MAX-ACCESS   read-write
      STATUS       current
      DESCRIPTION  "  Modem ACM mode
                      Value Range manual(0),   
                                  auto(1)
      " 
      DEFVAL {manual}
      ::= { modemConfigEntry 3 } 

    modemPHYmodulationVal OBJECT-TYPE 
      SYNTAX       INTEGER(1..16)
      MAX-ACCESS   read-write
      STATUS       current
      DESCRIPTION  " 
                    Modem configuration physical Mode value.
                    Value Range 1..16
                   " 
      DEFVAL {1}
      ::= { modemConfigEntry 4 }     
   
   modemRestart OBJECT-TYPE 
      SYNTAX       PtpRestartMode
      MAX-ACCESS   read-write
      STATUS       current
      DESCRIPTION  " Action Restart Modem
                     Value Range none(0),      
                                 restart(1)    
      " 
      DEFVAL {none}
      ::= { modemConfigEntry 5 }  
      
   modemConfigDownLoadValues OBJECT-TYPE 
       SYNTAX       INTEGER {notDownloadValue(1),
                             downloadValue(2)}
       MAX-ACCESS   read-write
       STATUS       current
       DESCRIPTION
           "     
                When set to value 2, the manager 
                 downloads the stored values of the 
                 OIDs modemPHYprofile, modemACMmode,
                      modemPHYmodulationVal.
           "
       ::= { modemConfigEntry 6 }  

   modemLinkId OBJECT-TYPE 
       SYNTAX       INTEGER(1..65535)
       MAX-ACCESS   read-write
       STATUS       current
       DESCRIPTION  
           " This is a configuration unique number which must be identical at both sides 
             of the link. Using this number the system identifies that has link with the right 
             remote system. This object is applicable only when the object modemLinkIdCheck is 
             set as used otherwise it includes only a preconfigured value but that LinkId value 
             is neither transmitted not used to check the link validity. The object is applicable 
             only for Antenna Alignment Handling. " 
      DEFVAL { 1 }
      ::= { modemConfigEntry 7 }  

   modemLinkIdCheck OBJECT-TYPE 
       SYNTAX       INTEGER{notUsed(0),used(1)}
       MAX-ACCESS   read-write
       STATUS       current
       DESCRIPTION  
           " When modemLinkIdCheck is used(1) then modemLinkId is valid to be send to the peer 
            and used for the link validity check. The object is applicable only for Antenna Alignment 
            Handling. " 
      DEFVAL { 0 }
      ::= { modemConfigEntry 8 }  

   modemRxSpectralInversion OBJECT-TYPE
       SYNTAX           INTEGER{disable(0), enable(1)}
       MAX-ACCESS       read-write
       STATUS           current
       DESCRIPTION 
           "When modemRxSpectralInversion is enable(1) then spectral inversion is applied
             to the received signal. The object is applicable only for OmniBAS-8W/OmniBAS-2WCX."
      DEFVAL { 0 }
      ::= { modemConfigEntry 9 }
   
  modemTddRole OBJECT-TYPE
    SYNTAX INTEGER{master (1),
    slave (2)}
    MAX-ACCESS read-write
    STATUS current
    DESCRIPTION
    " This object indicates the role of the modem in the TDD communication in relation to its PTP peer. "
    DEFVAL { master }
    ::= { modemConfigEntry 10 }

  modemCfgTddTxRatio OBJECT-TYPE
    SYNTAX TddTxRatio
    MAX-ACCESS read-write
    STATUS current
    DESCRIPTION
      "This object specifies the configured Tx-Ratio between Master and Slave at TDD 
              communication. The first value refers to the Tx Ratio of Master unit.
              The object can be configured in either Master or Slave unit but it actually applies
              in a unit that has TDD Master role."
    DEFVAL { one2one }
    ::= { modemConfigEntry 11 }

  modemCfgAirEncryptAdminState OBJECT-TYPE
    SYNTAX CfgAirEncryptAdminState
    MAX-ACCESS read-write
    STATUS current
    DESCRIPTION
      "The modemCfgAirEncryptAdminState controls, on a per
            modem basis,  whether Air Data Encryption is enabled or disabled. 
            The value airEncryptionOn(1) means that Air Data Encryption is
            enabled; the value airEncryptionOff(2) means that it is not." 
    DEFVAL { airEncryptionOff }
    ::= { modemConfigEntry 12 }

  modemCfgForceCfgSet OBJECT-TYPE
    SYNTAX CfgForceCfgSet
    MAX-ACCESS read-write
    STATUS current
    DESCRIPTION
      "The modemCfgForceCfgSet is used to forcefully update modem configuration.
              The value forceSetCfgTrue(1) forces the update of modem configuration.
              Currently used to force the new AES encryption key.
              The value forceSetCfgFalse(2) does nothing." 
    DEFVAL { forceSetCfgFalse }
    ::= { modemConfigEntry 13 }
   
   --=========================================================                                      
   -- MODEM PHY MODULATION TABLE
   --=========================================================
   
   modemPHYModulationTable OBJECT-TYPE
      SYNTAX       SEQUENCE OF   ModemPHYModulationEntry
      MAX-ACCESS   not-accessible
      STATUS       current
      DESCRIPTION  " 
                    This table models the modem PHY Modulation parameters.
                   "    
      ::= { modemConfig  2 }

   modemPHYModulationEntry OBJECT-TYPE 
      SYNTAX       ModemPHYModulationEntry
      MAX-ACCESS   not-accessible
      STATUS       current
      DESCRIPTION  " "
      INDEX  {modemPHYModulationEntryIndex} 
      ::={modemPHYModulationTable 1 }

    ModemPHYModulationEntry ::= SEQUENCE {                       
        modemPHYModulationEntryIndex  INTEGER,
        modemPHYDescription           OCTET STRING
   }   
  
   modemPHYModulationEntryIndex   OBJECT-TYPE 
      SYNTAX       INTEGER(1..16)
      MAX-ACCESS   not-accessible
      STATUS       current
      DESCRIPTION  "Index of the modemPHYModulationEntry. 
                    It is restricted to 16 instances."
      ::= { modemPHYModulationEntry 1 }

   modemPHYDescription OBJECT-TYPE 
      SYNTAX    OCTET STRING (SIZE (0..80))
      MAX-ACCESS   read-only
      STATUS       current
      DESCRIPTION  " String providing a textual description of attributes of this phymode value." 
      ::= { modemPHYModulationEntry 2 } 
 
 
   --=========================================================                                      
   -- MODEM STATUS TABLE
   --=========================================================

   modemStatusTable OBJECT-TYPE
      SYNTAX       SEQUENCE OF   ModemStatusEntry
      MAX-ACCESS   not-accessible
      STATUS       current
      DESCRIPTION  " 
                     This table models the table with modem Status information. 
                   "    
      ::= { modemConfig  3 }

   modemStatusEntry OBJECT-TYPE 
      SYNTAX       ModemStatusEntry
      MAX-ACCESS   not-accessible
      STATUS       current
      DESCRIPTION  " "
      INDEX  {modemStatusEntryIndex} 
      ::={modemStatusTable 1 }

    ModemStatusEntry ::= SEQUENCE {                   
      
        modemStatusEntryIndex  INTEGER,
        modemStatTemperature     INTEGER,
        modemStatFail         INTEGER,
        modemStatLinkStatus  PtpLinkStatus,
        modemStatLinkError  PtpLinkErrorState,
        modemStatLinkIndicator   INTEGER,
        modemStatPHYModValue   INTEGER,
        modemStatTxSymbolRate   Unsigned32,
        modemStatRxNormalizedMSE   INTEGER,
        modemStatRxPHYModValue  INTEGER,
        rxLdpcDecodersStress Unsigned32,
        modemprotectionMode PtpModemProtMode,
        modemPowerStatus INTEGER,
        modemAlarmThreshStatus INTEGER, 
        modemTxAirthroughput  Unsigned32,
        modemRxAirthroughput  Unsigned32,
        modemStatusSuppCapTxPhymodId   Unsigned32,
        modemStatusSuppCapRxPhymodId   Unsigned32,
        modemStatusSuppCapId  Unsigned32,
        modemActiveTddTxRatio Unsigned32,
        modemActiveTddRxRatio  Unsigned32,
        modemStatusAirLinkDistance  Unsigned32,
        modemStatusAirEncryptOperState INTEGER,
        modemActualMaxATPCTxPower INTEGER,
        modemActualMinATPCTxPower INTEGER
   }   
   
   modemStatusEntryIndex   OBJECT-TYPE 
      SYNTAX      INTEGER (1)
      MAX-ACCESS   not-accessible
      STATUS       current
      DESCRIPTION  "Index of the modemStatusEntry. 
                    It is restricted to 1 instance."
      ::= { modemStatusEntry 1 }

   modemStatTemperature OBJECT-TYPE 
      SYNTAX      INTEGER(-255..255)
      MAX-ACCESS   read-only
      STATUS       current
      DESCRIPTION  " Modem temperature.
                     The actual value is calculated with 10 " 
      ::= { modemStatusEntry 2 }   
      
   modemStatFail OBJECT-TYPE 
      SYNTAX       INTEGER
      MAX-ACCESS   read-only
      STATUS       current
      DESCRIPTION  " Modem failure information
                     The information is bitfield.
                     Bit value meaning:

                     bit0: Clock PLL info               
                      - 0: PLL locked   (Alarm ceased)               
                      - 1: PLL UnLocked (Alarm raised)                 
                     bit1: Receiver's PLL info          
                      - 0: PLL Locked    (Alarm ceased)              
                      - 1: PLL Unlocked  (Alarm raised) 
                     bit2: Transmiter's PLL info             
                      - 0: PLL Locked     (Alarm ceased)            
                      - 1: PLL Unlocked   (Alarm raised) 
                     bit3: Modem Chip Failure              
                     - 0: Modem Chip OK        (Alarm ceased)       
                     - 1: Modem Chip Failure   (Alarm raised) 
                    bit4: Modem Chip Lock  
                     - 0: Modem Chip Locked    (Alarm ceased)
                     - 1: Modem Chip Unlocked (Alarm raised)                     
                     bit5..bit31: not used          

      " 
      ::= { modemStatusEntry 3 } 

    modemStatLinkStatus OBJECT-TYPE 
      SYNTAX       PtpLinkStatus
      MAX-ACCESS   read-only
      STATUS       current
      DESCRIPTION  "  Link Status information
                      Value Range waitLock(0),       
                                  lock(1),          
                                  failed(2),
    				              waitAlign(3),
                                  waitLinkId(4),
                                  waitLinkIdAuto(5),
                                  sleep(6)         
         
      " 
      ::= { modemStatusEntry 4 } 
      
    modemStatLinkError OBJECT-TYPE 
      SYNTAX       PtpLinkErrorState
      MAX-ACCESS   read-only
      STATUS       current
      DESCRIPTION  " Link Error information
                     Value Range success(0),             
                                 failAtAGC(1),           
                                 failAtTiming(2),        
                                 failAtFreqSweep(3),     
                                 errorInMSE(4),          
                                 bitError(5),            
                                 serviceError(6),        
                                 failAtBLIND(7),         
                                 failOnTimeOut(10),      
                                 stopped(11),            
                                 fatalError(12)
      " 
      ::= { modemStatusEntry 5 } 

   modemStatLinkIndicator OBJECT-TYPE 
      SYNTAX       INTEGER
      MAX-ACCESS   read-only
      STATUS       current
      DESCRIPTION  "
        Lock indicators.
        The information is bitfield.
        In the following lines there is the bit value meaning:
            bit0: Timing  
                - 0: Unlocked 
                - 1: Locked
                    
            bit1..2: Preample
                - 0: Unlocked 
                - 1: Verified 
                - 2: Locked  
                - rest valus unused  
    
            bit3: AGC Lock
                - 0: UnLocked    
                - 1: Locked  
                Valid for NEPTUNE modem only. Not supported in VBAND system

            bit4: IMC (Internal Management Communication) Failure:
                - 0: False
                - 1: True   
                               
            bit5: LDPC Unlock
                - 0: Locked   
                - 1: Unlocked 

            bit6: LDPC corrected BER
                - 0: Off    
                - 1: On  
                Valid for NEPTUNE modem only

            bit7: LDPC uncorrected BER
                - 0: Off    
                - 1: On  
                Valid for NEPTUNE modem only

            bit8: GFP BER
                - 0: Off    
                - 1: On  
                Valid for NEPTUNE modem only. Not supported in VBAND system

            bit9: CRS Init
                - 0: Off    
                - 1: On  
                Valid for NEPTUNE modem only. Not supported in VBAND system

            bit10: Superframe Lock
                - 0: Unlocked
                - 1: Locked
                Valid for NEPTUNE modem only

            bit11: GFP Lock
                - 0: UnLocked    
                - 1: Locked
                Valid for NEPTUNE modem only

            bit12: L1 RAI Received
                - 0: Off    
                - 1: On  
                Valid for NEPTUNE modem only

            bit13: MSE Lock
                - 0: UnLocked    
                - 1: Locked
                Valid for NEPTUNE modem only

            bit14: Yellow Alarm
                - 0: ceased    
                - 1: raised
                When raised check the bits 0,3,6,7,8,9,13 of modemStatLinkIndicator
                Valid for NEPTUNE modem only

            bit15: Red Alarm
                - 0: ceased    
                - 1: raised
                When raised check the bits 1,2,5,10,11 of modemStatLinkIndicator
                Valid for NEPTUNE modem only

            bit16: MSE_minPhymode Lock
                -0:UnLocked
                -1:Locked
                Valid for NEPTUNE modem only

            bit17: Min Phymode Lock
                -0:UnLocked
                -1:Locked
                Valid for NEPTUNE modem only     

            bit18: XPIC Active Status
                -0:Inactive
                -1:Active
                Valid for NEPTUNE XPIC modem only

            bit19: XPIC Lock
                -0:UnLocked
                -1:Locked
                Valid for NEPTUNE XPIC modem only

            bit20: XPIC_PAIR Comm Lock
                -0:UnLocked
                -1:Locked
                Valid for NEPTUNE XPIC modem only

            bit21: XPIC_Sweeper Inactive Status
                -0:Active
                -1:Inactive
                
            bit22..bit31: not used
        "
      ::= { modemStatusEntry 6 }   
      
    modemStatPHYModValue OBJECT-TYPE 
      SYNTAX       INTEGER(1..16)
      MAX-ACCESS   read-only
      STATUS       current
      DESCRIPTION  "  Current Tx PHY Modulation value.
                      Value Range 1..16.
                      This value is used as index in the modemPHYModulationEntry.
                   " 
      ::= { modemStatusEntry 7 } 
  
    modemStatTxSymbolRate OBJECT-TYPE 
      SYNTAX      Unsigned32
      MAX-ACCESS   read-only
      STATUS       current
      DESCRIPTION  " Transimit Symbol rate information for incoming flow " 
      ::= { modemStatusEntry 8 } 

    modemStatRxNormalizedMSE OBJECT-TYPE 
      SYNTAX      INTEGER(-255..255)
      MAX-ACCESS   read-only
      STATUS       current
      DESCRIPTION  "  Information about received normalized MSE
                      This info is counted in 0.1 dB steps." 
      ::= { modemStatusEntry 9 } 

    modemStatRxPHYModValue OBJECT-TYPE 
      SYNTAX       INTEGER(1..16)
      MAX-ACCESS   read-only
      STATUS       current
      DESCRIPTION  "  Current Rx PHY Modulation value.
                      Value Range 1..16
                      This value is used as index in the modemPHYModulationEntry.
                                             Value 16 means not valid  profile.                                            
                   "
      ::= { modemStatusEntry 10 } 
     
    rxLdpcDecodersStress OBJECT-TYPE 
      SYNTAX      Unsigned32
      MAX-ACCESS   read-only
      STATUS       current
      DESCRIPTION  " Receive LDPC Decodes Stress 
                   "
      ::= { modemStatusEntry 11 } 
  
    modemprotectionMode OBJECT-TYPE 
      SYNTAX      PtpModemProtMode
      MAX-ACCESS   read-only
      STATUS       current
      DESCRIPTION  " Modem Protection Mode 
                     Value Range none(0),      
                                 working(1),   
                                 protect(2)
      "
      ::= { modemStatusEntry 12 } 

      
   modemPowerStatus OBJECT-TYPE 
      SYNTAX       INTEGER
      MAX-ACCESS   read-only
      STATUS       current
      DESCRIPTION  "
        Modem Power Power status
        The information is bitfield.
        In the following lines there is the value meaning of each bit:
            bit0: Power Fault
            bit1: Fault 48V ODU
            bit2: Fault 48V
            bit3: Power Fault of 1.2V
            bit4: Power Fault of 1.8V
            bit5: Power Fault of 2.5V
            bit6: Power Fault of 10V and 5.1V
            bit7..bit31: not used               
        "
      ::= { modemStatusEntry 13 }   

   modemAlarmThreshStatus OBJECT-TYPE 
      SYNTAX       INTEGER
      MAX-ACCESS   read-only
      STATUS       current
      DESCRIPTION  "
        Modem threshhold status Alarm.
        The information is bitfield.
        In the following lines there is the value meaning of each bit:
            bit0: Rx NormalizedMSE Alarm (SNR)
                  - 0: Alarm ceased  
                  - 1: Alarm raised  
            bit1: Rx Ldpc Decoders Stress Alarm
                  - 0: Alarm ceased
                  - 1: Alarm raised
            bit2: Modem PHY modulation configuration is not supported.                                                    
                  The Alarm is raised, when the modem Physical Modulation value stored in
                  the configuration, is not supported by the inserted modem in the system.                                            
                  - 0: Alarm ceased
                  - 1: Alarm raised
            bit3: The Alarm is raised when modemStatTemperature exceeds an internal
                  High temperature threshold.
                  The Alarm is ceased when modemStatTemperature falls lower than an
                  internal Low temperature threshold.
                  - 0: Alarm ceased
                  - 1: Alarm raised
            bit4..bit31: not used
        "
      ::= { modemStatusEntry 14 }
      
   modemTxAirthroughput OBJECT-TYPE 
      SYNTAX    Unsigned32
      MAX-ACCESS   read-only
      STATUS       current
      DESCRIPTION  " 
                     Max Tx throughput on the air 
                     Applicable only for the NEPTUNE modems
                   " 
      ::= { modemStatusEntry 15 }   
      
   modemRxAirthroughput OBJECT-TYPE 
      SYNTAX    Unsigned32
      MAX-ACCESS   read-only
      STATUS       current
      DESCRIPTION  " 
                     Max Rx throughput on the air  
                     Applicable only for the NEPTUNE modems
                   " 
      ::= { modemStatusEntry 16 }   

    modemStatusSuppCapTxPhymodId   OBJECT-TYPE
        SYNTAX              Unsigned32 (1..16)
        MAX-ACCESS          read-only
        STATUS              current
        DESCRIPTION
           " Modem Tx PHYmode Index 1 to 16, i.e. the modemSuppCapPhymodIndex 
            for the Tx PHYmode of the specific Modem Capabilities combination indicated 
            by modemSuppCapabilitiesIndex. The Indexing from 1 to 16 corrresponds to 
            indexing of phymodes from lower air capacity to higher air capacity."
        ::= { modemStatusEntry 17 }

    modemStatusSuppCapRxPhymodId   OBJECT-TYPE
        SYNTAX              Unsigned32 (1..16)
        MAX-ACCESS          read-only
        STATUS              current
        DESCRIPTION
           " Modem Rx PHYmode Index 1 to 16, i.e. the modemSuppCapPhymodIndex 
            for the Rx PHYmode of the specific Modem Capabilities combination indicated 
            by modemStatusSuppCapId. The Indexing from 1 to 16 corrresponds to 
            indexing of phymodes from lower air capacity to higher air capacity."
        ::= { modemStatusEntry 18 }

   modemStatusSuppCapId   OBJECT-TYPE
       SYNTAX              Unsigned32
       MAX-ACCESS          read-only
       STATUS              current
       DESCRIPTION
          " The index of current supported Modem Capabilities combination, 
            in the ModemSuppCapabilitiesTable. "
       ::= { modemStatusEntry 19 }
	   
   modemActiveTddTxRatio OBJECT-TYPE
       SYNTAX           Unsigned32 (1..1000)
       MAX-ACCESS       read-only
       STATUS           current
       DESCRIPTION 
           "This object specifies the parts per thousand of the current
            Active Tx rate in relation to the maximum aggregate rate."
      ::= { modemStatusEntry 20 }

   modemActiveTddRxRatio OBJECT-TYPE
       SYNTAX           Unsigned32 (1..1000)
       MAX-ACCESS       read-only
       STATUS           current
       DESCRIPTION
           "This object specifies the parts per thousand of the current
            Active Rx rate in relation to the maximum aggregate rate."
      ::= { modemStatusEntry 21 }

   modemStatusAirLinkDistance OBJECT-TYPE
       SYNTAX        Unsigned32
       UNITS         "centimeters"
       MAX-ACCESS    read-only
       STATUS        current
       DESCRIPTION
           "The TDD measured air link distance. Valid only after the link
            has been established."
       ::= { modemStatusEntry 22 }

   modemStatusAirEncryptOperState   OBJECT-TYPE
       SYNTAX INTEGER {
                        working (1),
                        notWorking (2)
                      }
       MAX-ACCESS          read-only
       STATUS              current
       DESCRIPTION
          " The object indicates the operational state of the Air Encryption.
            Not Working reasons can be due to Air Encryption being disabled at the
            peer modem or because the peer mode has a different Encryption key. "
       ::= { modemStatusEntry 23 }

   modemActualMaxATPCTxPower   OBJECT-TYPE 
      SYNTAX       INTEGER (-32767..32767)
      MAX-ACCESS   read-only
      STATUS       current
      DESCRIPTION  
          "Modem Actual Maximum ATPC Tx Power value in tenths of dBms" 
      ::= { modemStatusEntry 24 }

   modemActualMinATPCTxPower   OBJECT-TYPE 
      SYNTAX       INTEGER (-32767..32767)
      MAX-ACCESS   read-only
      STATUS       current
      DESCRIPTION  
          "Modem Actual Minimum ATPC Tx Power value in tenths of dBms" 
      ::= { modemStatusEntry 25 }

   --=========================================================
   -- MODEM PERMORMANCE COUNTERS TABLE
   --=========================================================

   modemPermormanceCountersTable OBJECT-TYPE
      SYNTAX       SEQUENCE OF   ModemPermormanceCountersEntry
      MAX-ACCESS   not-accessible
      STATUS       current
      DESCRIPTION  " 
                     This table models the modem performance counters information 
                   "    
      ::= { modemConfig  4 }

   modemPermormanceCountersEntry OBJECT-TYPE 
      SYNTAX       ModemPermormanceCountersEntry
      MAX-ACCESS   not-accessible
      STATUS       current
      DESCRIPTION  " "
      INDEX  {modemPermormanceCountersEntryIndex} 
      ::={modemPermormanceCountersTable 1 }

    ModemPermormanceCountersEntry ::= SEQUENCE {                   
      
        modemPermormanceCountersEntryIndex  INTEGER,
        modemSecondsOutOfService   Counter32,
        modemSecondsInService      Counter32,        
        modemNumberOfPhyChanges    Counter32,
        modemSecondsInPhyChanges1  Counter32,
        modemSecondsInPhyChanges2  Counter32,
        modemSecondsInPhyChanges3  Counter32,
        modemSecondsInPhyChanges4  Counter32,
        modemSecondsInPhyChanges5  Counter32,
        modemSecondsInPhyChanges6  Counter32,
        modemSecondsInPhyChanges7  Counter32,
        modemSecondsInPhyChanges8  Counter32,
        modemSecondsInPhyChanges9  Counter32,
        modemSecondsInPhyChanges10 Counter32,
        modemSecondsInPhyChanges11 Counter32,
        modemSecondsInPhyChanges12 Counter32,
        modemSecondsInPhyChanges13 Counter32,
        modemSecondsInPhyChanges14 Counter32,
        modemSecondsInPhyChanges15 Counter32,
        modemSecondsInPhyChanges16 Counter32,
        modemCountersControl PtpCounterOperation,
        modemChangesInPHYMode1     Counter32,
        modemChangesInPHYMode2     Counter32,
        modemChangesInPHYMode3     Counter32,
        modemChangesInPHYMode4     Counter32,
        modemChangesInPHYMode5     Counter32,
        modemChangesInPHYMode6     Counter32,
        modemChangesInPHYMode7     Counter32,
        modemChangesInPHYMode8     Counter32,
        modemChangesInPHYMode9     Counter32,
        modemChangesInPHYMode10    Counter32,
        modemChangesInPHYMode11    Counter32,
        modemChangesInPHYMode12    Counter32,
        modemChangesInPHYMode13    Counter32,
        modemChangesInPHYMode14    Counter32,
        modemChangesInPHYMode15    Counter32,
        modemChangesInPHYMode16    Counter32
   }   
  
   modemPermormanceCountersEntryIndex   OBJECT-TYPE 
      SYNTAX       INTEGER (1)
      MAX-ACCESS   not-accessible
      STATUS       current
      DESCRIPTION  "Index of the modemPHYModulationEntry. 
                   It is restricted to 1 instance.
                   "
      ::= { modemPermormanceCountersEntry 1 }

   modemSecondsOutOfService OBJECT-TYPE 
      SYNTAX    Counter32
      MAX-ACCESS   read-only
      STATUS       current
      DESCRIPTION  " 
                     Number of seconds Out Of Service counter 
                   " 
      ::= { modemPermormanceCountersEntry 2 }   

   modemSecondsInService OBJECT-TYPE 
      SYNTAX    Counter32
      MAX-ACCESS   read-only
      STATUS       current
      DESCRIPTION  " 
                     Number of seconds in service counter 
                   " 
      ::= { modemPermormanceCountersEntry 3 }   

   modemNumberOfPhyChanges OBJECT-TYPE 
      SYNTAX    Counter32
      MAX-ACCESS   read-only
      STATUS       current
      DESCRIPTION  " 
                    Number of  physical  changes counter 
                   " 
      ::= { modemPermormanceCountersEntry 4 } 
      
   modemSecondsInPhyChanges1 OBJECT-TYPE 
      SYNTAX    Counter32
      MAX-ACCESS   read-only
      STATUS       current
      DESCRIPTION  " 
                     First counter of seconds in physical mode 
                   " 
      ::= { modemPermormanceCountersEntry 5 }   
      
   modemSecondsInPhyChanges2 OBJECT-TYPE 
      SYNTAX    Counter32
      MAX-ACCESS   read-only
      STATUS       current
      DESCRIPTION  " 
                     Second counter of seconds in physical mode  
                   " 
      ::= { modemPermormanceCountersEntry 6 }   
      
   modemSecondsInPhyChanges3 OBJECT-TYPE 
      SYNTAX    Counter32
      MAX-ACCESS   read-only
      STATUS       current
      DESCRIPTION  " 
                     Third counter of seconds in physical mode 
                   " 
      ::= { modemPermormanceCountersEntry 7 }   
      
   modemSecondsInPhyChanges4 OBJECT-TYPE 
      SYNTAX    Counter32
      MAX-ACCESS   read-only
      STATUS       current
      DESCRIPTION  " 
                     Fourth counter of seconds in physical mode  
                   " 
      ::= { modemPermormanceCountersEntry 8 }   
      
   modemSecondsInPhyChanges5 OBJECT-TYPE 
      SYNTAX    Counter32
      MAX-ACCESS   read-only
      STATUS       current
      DESCRIPTION  " 
                     Fifth counter of seconds in physical mode  
                   " 
      ::= { modemPermormanceCountersEntry 9 }   
      
   modemSecondsInPhyChanges6 OBJECT-TYPE 
      SYNTAX    Counter32
      MAX-ACCESS   read-only
      STATUS       current
      DESCRIPTION  " 
                    Sixth counter of seconds in physical mode 
                   " 
      ::= { modemPermormanceCountersEntry 10 }   
      
   modemSecondsInPhyChanges7 OBJECT-TYPE 
      SYNTAX    Counter32
      MAX-ACCESS   read-only
      STATUS       current
      DESCRIPTION  " 
                    Seventh counter of seconds in physical mode  
                   " 
      ::= { modemPermormanceCountersEntry 11 }   
      
   modemSecondsInPhyChanges8 OBJECT-TYPE 
      SYNTAX    Counter32
      MAX-ACCESS   read-only
      STATUS       current
      DESCRIPTION  " 
                    Eighth counter of seconds in physical mode  
                   " 
      ::= { modemPermormanceCountersEntry 12 }   
      
   modemSecondsInPhyChanges9 OBJECT-TYPE 
      SYNTAX    Counter32
      MAX-ACCESS   read-only
      STATUS       current
      DESCRIPTION  " 
                     Ninth counter of seconds in physical mode  
                   " 
      ::= { modemPermormanceCountersEntry 13 }   
      
   modemSecondsInPhyChanges10 OBJECT-TYPE 
      SYNTAX    Counter32
      MAX-ACCESS   read-only
      STATUS       current
      DESCRIPTION  " 
                     Tenth counter of seconds in physical mode  
                   " 
      ::= { modemPermormanceCountersEntry 14 }   
      
   modemSecondsInPhyChanges11 OBJECT-TYPE 
      SYNTAX    Counter32
      MAX-ACCESS   read-only
      STATUS       current
      DESCRIPTION  " 
                     Eleventh counter of seconds in physical mode  
                   " 
      ::= { modemPermormanceCountersEntry 15 }   
      
   modemSecondsInPhyChanges12 OBJECT-TYPE 
      SYNTAX    Counter32
      MAX-ACCESS   read-only
      STATUS       current
      DESCRIPTION  " 
                     Twelfth counter of seconds in physical mode 
                   " 
      ::= { modemPermormanceCountersEntry 16 }   
      
   modemSecondsInPhyChanges13 OBJECT-TYPE 
      SYNTAX    Counter32
      MAX-ACCESS   read-only
      STATUS       current
      DESCRIPTION  " 
                     Thirteenth counter of seconds in physical mode  
                   " 
      ::= { modemPermormanceCountersEntry 17 }   
      
   modemSecondsInPhyChanges14 OBJECT-TYPE 
      SYNTAX    Counter32
      MAX-ACCESS   read-only
      STATUS       current
      DESCRIPTION  " 
                     Fourteenth counter of seconds in physical mode 
                   " 
      ::= { modemPermormanceCountersEntry 18 }   

   modemSecondsInPhyChanges15 OBJECT-TYPE 
      SYNTAX    Counter32
      MAX-ACCESS   read-only
      STATUS       current
      DESCRIPTION  " 
                    Fifteenth counter of seconds in physical mode  
                   " 
      ::= { modemPermormanceCountersEntry 19 }   

   modemSecondsInPhyChanges16 OBJECT-TYPE 
      SYNTAX    Counter32
      MAX-ACCESS   read-only
      STATUS       current
      DESCRIPTION  " 
                     Sixteenth counter of seconds in physical mode  
                   " 
      ::= { modemPermormanceCountersEntry 20 }   

   modemCountersControl OBJECT-TYPE 
      SYNTAX    PtpCounterOperation
      MAX-ACCESS   read-write
      STATUS       current
      DESCRIPTION  "
                    Counters control 
                    Value Range stopCounter(0),   
                                startCounter(1),  
                                resetCounter(2)   
                   " 
      DEFVAL {stopCounter}
      ::= { modemPermormanceCountersEntry 21 }

   modemChangesInPHYMode1 OBJECT-TYPE
      SYNTAX       Counter32
      MAX-ACCESS   read-only
      STATUS       current
      DESCRIPTION  
          "The object counts the number of times that the modem operates in PHYmode with
           modemPHYModulationEntryIndex 1."
      ::= { modemPermormanceCountersEntry 22 }

   modemChangesInPHYMode2 OBJECT-TYPE
      SYNTAX       Counter32
      MAX-ACCESS   read-only
      STATUS       current
      DESCRIPTION  
          "The object counts the number of times that the modem operates in PHYmode with
           modemPHYModulationEntryIndex 2."
      ::= { modemPermormanceCountersEntry 23 }

   modemChangesInPHYMode3 OBJECT-TYPE
      SYNTAX       Counter32
      MAX-ACCESS   read-only
      STATUS       current
      DESCRIPTION  
          "The object counts the number of times that the modem operates in PHYmode with
           modemPHYModulationEntryIndex 3."
      ::= { modemPermormanceCountersEntry 24 }

   modemChangesInPHYMode4 OBJECT-TYPE
      SYNTAX       Counter32
      MAX-ACCESS   read-only
      STATUS       current
      DESCRIPTION  
          "The object counts the number of times that the modem operates in PHYmode with
           modemPHYModulationEntryIndex 4."
      ::= { modemPermormanceCountersEntry 25 }

   modemChangesInPHYMode5 OBJECT-TYPE
      SYNTAX       Counter32
      MAX-ACCESS   read-only
      STATUS       current
      DESCRIPTION  
          "The object counts the number of times that the modem operates in PHYmode with
           modemPHYModulationEntryIndex 5."
      ::= { modemPermormanceCountersEntry 26 }

   modemChangesInPHYMode6 OBJECT-TYPE
      SYNTAX       Counter32
      MAX-ACCESS   read-only
      STATUS       current
      DESCRIPTION  
          "The object counts the number of times that the modem operates in PHYmode with
           modemPHYModulationEntryIndex 6."
      ::= { modemPermormanceCountersEntry 27 }

   modemChangesInPHYMode7 OBJECT-TYPE
      SYNTAX       Counter32
      MAX-ACCESS   read-only
      STATUS       current
      DESCRIPTION  
          "The object counts the number of times that the modem operates in PHYmode with
           modemPHYModulationEntryIndex 7."
      ::= { modemPermormanceCountersEntry 28 }

   modemChangesInPHYMode8 OBJECT-TYPE
      SYNTAX       Counter32
      MAX-ACCESS   read-only
      STATUS       current
      DESCRIPTION  
          "The object counts the number of times that the modem operates in PHYmode with
           modemPHYModulationEntryIndex 8."
      ::= { modemPermormanceCountersEntry 29 }

   modemChangesInPHYMode9 OBJECT-TYPE
      SYNTAX       Counter32
      MAX-ACCESS   read-only
      STATUS       current
      DESCRIPTION  
          "The object counts the number of times that the modem operates in PHYmode with
           modemPHYModulationEntryIndex 9."
      ::= { modemPermormanceCountersEntry 30 }

   modemChangesInPHYMode10 OBJECT-TYPE
      SYNTAX       Counter32
      MAX-ACCESS   read-only
      STATUS       current
      DESCRIPTION  
          "The object counts the number of times that the modem operates in PHYmode with
           modemPHYModulationEntryIndex 10."
      ::= { modemPermormanceCountersEntry 31 }

   modemChangesInPHYMode11 OBJECT-TYPE
      SYNTAX       Counter32
      MAX-ACCESS   read-only
      STATUS       current
      DESCRIPTION  
          "The object counts the number of times that the modem operates in PHYmode with
           modemPHYModulationEntryIndex 11."
      ::= { modemPermormanceCountersEntry 32 }

   modemChangesInPHYMode12 OBJECT-TYPE
      SYNTAX       Counter32
      MAX-ACCESS   read-only
      STATUS       current
      DESCRIPTION  
          "The object counts the number of times that the modem operates in PHYmode with
           modemPHYModulationEntryIndex 12."
      ::= { modemPermormanceCountersEntry 33 }

   modemChangesInPHYMode13 OBJECT-TYPE
      SYNTAX       Counter32
      MAX-ACCESS   read-only
      STATUS       current
      DESCRIPTION  
          "The object counts the number of times that the modem operates in PHYmode with
           modemPHYModulationEntryIndex 13."
      ::= { modemPermormanceCountersEntry 34 }

   modemChangesInPHYMode14 OBJECT-TYPE
      SYNTAX       Counter32
      MAX-ACCESS   read-only
      STATUS       current
      DESCRIPTION  
          "The object counts the number of times that the modem operates in PHYmode with
           modemPHYModulationEntryIndex 14."
      ::= { modemPermormanceCountersEntry 35 }

   modemChangesInPHYMode15 OBJECT-TYPE
      SYNTAX       Counter32
      MAX-ACCESS   read-only
      STATUS       current
      DESCRIPTION  
          "The object counts the number of times that the modem operates in PHYmode with
           modemPHYModulationEntryIndex 15."
      ::= { modemPermormanceCountersEntry 36 }

   modemChangesInPHYMode16 OBJECT-TYPE
      SYNTAX       Counter32
      MAX-ACCESS   read-only
      STATUS       current
      DESCRIPTION  
          "The object counts the number of times that the modem operates in PHYmode with
           modemPHYModulationEntryIndex 16."
      ::= { modemPermormanceCountersEntry 37 }

  --=========================================================                                      
   --  ETHERNET COUNTERS TABLE
   --=========================================================

   modemEthernetCountersTable OBJECT-TYPE
      SYNTAX       SEQUENCE OF   ModemEthernetCountersEntry
      MAX-ACCESS   not-accessible
      STATUS       current
      DESCRIPTION  " 
                     This table models the modem ethernet counters information 
                   "    
      ::= { modemConfig  6 }

   modemEthernetCountersEntry OBJECT-TYPE 
      SYNTAX       ModemEthernetCountersEntry
      MAX-ACCESS   not-accessible
      STATUS       current
      DESCRIPTION  " "
      INDEX  {modemEthernetCountersEntryIndex} 
      ::={modemEthernetCountersTable 1 }

    ModemEthernetCountersEntry ::= SEQUENCE {                   
        modemEthernetCountersEntryIndex  INTEGER,
        modemEthTxPacketCounter    Counter32,
        modemEthRxPacketCounter    Counter32,
        modemEthRxCrcErrors    Counter32,
        modemEthCountersControl PtpCounterOperation,
        modemEthRxTruncatedFrames Counter32,
        modemEthRxLongEvents      Counter32,
        modemEthRxVlanTagsDetected Counter32,
        modemEthRxUnsupportedOpCodes Counter32,
        modemEthRxpauseFrames    Counter32,
        modemEthRxControlFrames  Counter32,
        modemEthRxDribbleNibbles Counter32,
        modemEthRxBroadCasts     Counter32,
        modemEthRxMultiCasts     Counter32,
        modemEthRxOutOfRangeErrors Counter32,
        modemEthRxLengthCheckErrors Counter32,
        modemEthRxCodeErrors   Counter32,
        modemEthRxFalseCarrierErrors Counter32,
        modemEthRxDvEvent Counter32,
        modemEthRxPreviousPacketDropped Counter32,
        modemEthRxByteCounterLow Counter32,
        modemEthRxByteCounterHigh Counter32,
        modemEthRxBitRate Counter32,
        modemEthTxVlanTags Counter32,
        modemEthTxBackPressuresEvents Counter32,
        modemEthTxPauseFrames  Counter32,
        modemEthTxControlFrames  Counter32,
        modemEthTxWireByteCounterLow  Counter32,
        modemEthTxWireByteCounterHigh Counter32,
        modemEthTxUnderRuns Counter32,
        modemEthTxGiants Counter32,
        modemEthTxLateCollisions Counter32,
        modemEthTxMaxCollisions Counter32,
        modemEthTxExcessiveDefers Counter32,
        modemEthTxNonExcessiveDefers Counter32,
        modemEthTxBroadCasts Counter32,
        modemEthTxMulticasts Counter32,
        modemEthTxReserved Counter32,
        modemEthTxLengthCheckErrors Counter32,
        modemEthTxCrcErrors Counter32,
        modemEthTxCollisions Counter32,
        modemEthTxByteCounterLow Counter32,
        modemEthTxByteCounterHigh Counter32,
        modemEthTxBitRate Counter32,
        modemEthCommulativeTime Unsigned32,
        modemEthRateTime INTEGER,
        modemEthRxBitRateHigh Counter32,
        modemEthTxBitRateHigh Counter32,
        modemEthRxShortEvents Counter32
   }   
  
   modemEthernetCountersEntryIndex   OBJECT-TYPE 
      SYNTAX       INTEGER (1)
      MAX-ACCESS   not-accessible
      STATUS       current
      DESCRIPTION  "Index of the modemPHYModulationEntry. 
                    It is restricted to 1 instance.
                   "
      ::= { modemEthernetCountersEntry 1 }

   modemEthTxPacketCounter OBJECT-TYPE 
      SYNTAX    Counter32
      MAX-ACCESS   read-only
      STATUS       current
      DESCRIPTION  " 
                     Ethernet transmit packets counter  
                   " 
      ::= { modemEthernetCountersEntry 2 }   

   modemEthRxPacketCounter OBJECT-TYPE 
      SYNTAX    Counter32
      MAX-ACCESS   read-only
      STATUS       current
      DESCRIPTION  " 
                     Ethernet received packets counter 
                   " 
      ::= { modemEthernetCountersEntry 3 }   

   modemEthRxCrcErrors OBJECT-TYPE 
      SYNTAX    Counter32
      MAX-ACCESS   read-only
      STATUS       current
      DESCRIPTION  " 
                     Ethernet Rx CRC errors counter 
                   "
      ::= { modemEthernetCountersEntry 4 }   

   modemEthCountersControl OBJECT-TYPE 
      SYNTAX    PtpCounterOperation
      MAX-ACCESS   read-write
      STATUS       current
      DESCRIPTION  " 
                    Ethernet counters control operation 
                     Value Range stopCounter(0),                          
                                 startCounter(1),    
                                 resetCounter(2)
                   " 
      DEFVAL {stopCounter}
      ::= { modemEthernetCountersEntry 5 }   
  
   modemEthRxTruncatedFrames OBJECT-TYPE 
      SYNTAX    Counter32
      MAX-ACCESS   read-only
      STATUS       current
      DESCRIPTION  " 
                    Ethernet Rx truncated frames counter 
                   "
      ::= { modemEthernetCountersEntry 6 }   

   modemEthRxLongEvents OBJECT-TYPE 
      SYNTAX    Counter32
      MAX-ACCESS   read-only
      STATUS       current
      DESCRIPTION  " 
                     Ethernet Rx long events frames counter 
                   "
      ::= { modemEthernetCountersEntry 7 }   

   modemEthRxVlanTagsDetected OBJECT-TYPE 
      SYNTAX    Counter32
      MAX-ACCESS   read-only
      STATUS       current
      DESCRIPTION  " 
                    Ethernet Rx vlan tags detected frames counter 
                   "
      ::= { modemEthernetCountersEntry 8 }   

   modemEthRxUnsupportedOpCodes OBJECT-TYPE 
      SYNTAX    Counter32
      MAX-ACCESS   read-only
      STATUS       current
      DESCRIPTION  " 
                     EthernetRx unsupported opcode frames counter 
                   "
      ::= { modemEthernetCountersEntry 9 }   

   modemEthRxpauseFrames OBJECT-TYPE 
      SYNTAX    Counter32
      MAX-ACCESS   read-only
      STATUS       current
      DESCRIPTION  " 
                     EthernetRx pause frames counter 
                   "
      ::= { modemEthernetCountersEntry 10 }   

   modemEthRxControlFrames OBJECT-TYPE 
      SYNTAX    Counter32
      MAX-ACCESS   read-only
      STATUS       current
      DESCRIPTION  " 
                     Ethernet Rx control frames counter 
                   "
      ::= { modemEthernetCountersEntry 11 }   

   modemEthRxDribbleNibbles OBJECT-TYPE 
      SYNTAX    Counter32
      MAX-ACCESS   read-only
      STATUS       current
      DESCRIPTION  " 
                      Ethernet Rx dribble nibbles frames counter 
                   "
      ::= { modemEthernetCountersEntry 12 }   

   modemEthRxBroadCasts OBJECT-TYPE 
      SYNTAX    Counter32
      MAX-ACCESS   read-only
      STATUS       current
      DESCRIPTION  " 
                     Ethernet Rx broadcasts frames counter 
                   "
      ::= { modemEthernetCountersEntry 13 }   

   modemEthRxMultiCasts OBJECT-TYPE 
      SYNTAX    Counter32
      MAX-ACCESS   read-only
      STATUS       current
      DESCRIPTION  " 
                     Ethernet Rx multiCasts frames counter 
                   "
      ::= { modemEthernetCountersEntry 14 }   

   modemEthRxOutOfRangeErrors OBJECT-TYPE 
      SYNTAX    Counter32
      MAX-ACCESS   read-only
      STATUS       current
      DESCRIPTION  " 
                     Ethernet Rx out of range errors frames counter 
                   "
      ::= { modemEthernetCountersEntry 15 }   

   modemEthRxLengthCheckErrors OBJECT-TYPE 
      SYNTAX    Counter32
      MAX-ACCESS   read-only
      STATUS       current
      DESCRIPTION  " 
                     Ethernet Rx length check errors frames counter 
                   "
      ::= { modemEthernetCountersEntry 16 }   

   modemEthRxCodeErrors OBJECT-TYPE 
      SYNTAX    Counter32
      MAX-ACCESS   read-only
      STATUS       current
      DESCRIPTION  " 
                     EthernetRx code errors frames counter 
                   "
      ::= { modemEthernetCountersEntry 17 }   

   modemEthRxFalseCarrierErrors OBJECT-TYPE 
      SYNTAX    Counter32
      MAX-ACCESS   read-only
      STATUS       current
      DESCRIPTION  " 
                    Ethernet Rx false carrier errors frames counter 
                   "
      ::= { modemEthernetCountersEntry 18 }   

   modemEthRxDvEvent OBJECT-TYPE 
      SYNTAX    Counter32
      MAX-ACCESS   read-only
      STATUS       current
      DESCRIPTION  " 
                     Ethernet Rx dv events frames counter 
                   "
      ::= { modemEthernetCountersEntry 19 }   

   modemEthRxPreviousPacketDropped OBJECT-TYPE 
      SYNTAX    Counter32
      MAX-ACCESS   read-only
      STATUS       current
      DESCRIPTION  " 
                     Ethernet Rx previous packet dropped frames counter 
                   "
      ::= { modemEthernetCountersEntry 20 }   

   modemEthRxByteCounterLow OBJECT-TYPE 
      SYNTAX    Counter32
      MAX-ACCESS   read-only
      STATUS       current
      DESCRIPTION  " 
                     Ethernet Rx byte low counter 
                   "
      ::= { modemEthernetCountersEntry 21 }   

   modemEthRxByteCounterHigh OBJECT-TYPE 
      SYNTAX    Counter32
      MAX-ACCESS   read-only
      STATUS       current
      DESCRIPTION  " 
                    Ethernet Rx byte high  counter
                   "
      ::= { modemEthernetCountersEntry 22 }   

   modemEthRxBitRate OBJECT-TYPE 
      SYNTAX    Counter32
      MAX-ACCESS   read-only
      STATUS       current
      DESCRIPTION  " 
                    Ethernet Rx bit rate  counter low   
                   "
      ::= { modemEthernetCountersEntry 23 }   

   modemEthTxVlanTags OBJECT-TYPE 
      SYNTAX    Counter32
      MAX-ACCESS   read-only
      STATUS       current
      DESCRIPTION  " 
                    Ethernet Tx vlan taged frames counter 
                   "
      ::= { modemEthernetCountersEntry 24 }   

   modemEthTxBackPressuresEvents OBJECT-TYPE 
      SYNTAX    Counter32
      MAX-ACCESS   read-only
      STATUS       current
      DESCRIPTION  " 
                     Ethernet Tx back pressures events frames counter 
                   "
      ::= { modemEthernetCountersEntry 25 }   

   modemEthTxPauseFrames OBJECT-TYPE 
      SYNTAX    Counter32
      MAX-ACCESS   read-only
      STATUS       current
      DESCRIPTION  " 
                     Ethernet Tx paused frames counter 
                   "
      ::= { modemEthernetCountersEntry 26}   

   modemEthTxControlFrames OBJECT-TYPE 
      SYNTAX    Counter32
      MAX-ACCESS   read-only
      STATUS       current
      DESCRIPTION  " 
                     Ethernet Tx control frames counter 
                   "
      ::= { modemEthernetCountersEntry 27 }   

   modemEthTxWireByteCounterLow OBJECT-TYPE 
      SYNTAX    Counter32
      MAX-ACCESS   read-only
      STATUS       current
      DESCRIPTION  " 
                     Ethernet Tx wire byte low counter.
                     Used for L1 Eth stats in Neptune 
                   "
      ::= { modemEthernetCountersEntry 28 }   

   modemEthTxWireByteCounterHigh OBJECT-TYPE 
      SYNTAX    Counter32
      MAX-ACCESS   read-only
      STATUS       current
      DESCRIPTION  " 
                    Ethernet Tx wire byte high counter.
                    Used for L1 Eth stats in Neptune  
                   "
      ::= { modemEthernetCountersEntry 29 }   

   modemEthTxUnderRuns OBJECT-TYPE 
      SYNTAX    Counter32
      MAX-ACCESS   read-only
      STATUS       current
      DESCRIPTION  " 
                    Ethernet Tx underRuns counter 
                   "
      ::= { modemEthernetCountersEntry 30 }   

   modemEthTxGiants OBJECT-TYPE 
      SYNTAX    Counter32
      MAX-ACCESS   read-only
      STATUS       current
      DESCRIPTION  " 
                    Ethernet Tx giants counter 
                   "
      ::= { modemEthernetCountersEntry 31 }   

   modemEthTxLateCollisions OBJECT-TYPE 
      SYNTAX    Counter32
      MAX-ACCESS   read-only
      STATUS       current
      DESCRIPTION  " 
                    Ethernet Tx late collisions frames counter 
                   "
      ::= { modemEthernetCountersEntry 32 }   
      
   modemEthTxMaxCollisions OBJECT-TYPE 
      SYNTAX    Counter32
      MAX-ACCESS   read-only
      STATUS       current
      DESCRIPTION  " 
                    Ethernet Tx max collisions frames counter 
                   "
      ::= { modemEthernetCountersEntry 33 }   

   modemEthTxExcessiveDefers OBJECT-TYPE 
      SYNTAX    Counter32
      MAX-ACCESS   read-only
      STATUS       current
      DESCRIPTION  " 
                    Ethernet Tx excessive defer frames counter 
                    "
      ::= { modemEthernetCountersEntry 34 }   


   modemEthTxNonExcessiveDefers OBJECT-TYPE 
      SYNTAX    Counter32
      MAX-ACCESS   read-only
      STATUS       current
      DESCRIPTION  " 
                     Ethernet Tx nonexcessive defer frames counter  
                   "
      ::= { modemEthernetCountersEntry 35 }   

   modemEthTxBroadCasts OBJECT-TYPE 
      SYNTAX    Counter32
      MAX-ACCESS   read-only
      STATUS       current
      DESCRIPTION  " 
                    Ethernet Tx broadcasts frames counter
                   "
      ::= { modemEthernetCountersEntry 36 }   

   modemEthTxMulticasts OBJECT-TYPE 
      SYNTAX    Counter32
      MAX-ACCESS   read-only
      STATUS       current
      DESCRIPTION  " 
                    Ethernet Tx multicasts frames counter 
                   "
      ::= { modemEthernetCountersEntry 37 }   

   modemEthTxReserved OBJECT-TYPE 
      SYNTAX    Counter32
      MAX-ACCESS   read-only
      STATUS       current
      DESCRIPTION  " 
                     Ethernet Tx Reserved counter  
                     Currently not used 
                   "
      ::= { modemEthernetCountersEntry 38 }   

   modemEthTxLengthCheckErrors OBJECT-TYPE 
      SYNTAX    Counter32
      MAX-ACCESS   read-only
      STATUS       current
      DESCRIPTION  " 
                    Ethernet Tx length check errors counter 
                   "
      ::= { modemEthernetCountersEntry 39 }   

   modemEthTxCrcErrors OBJECT-TYPE 
      SYNTAX    Counter32
      MAX-ACCESS   read-only
      STATUS       current
      DESCRIPTION  " 
                    Ethernet Tx CRC errors counter  
                   "
      ::= { modemEthernetCountersEntry 40 }   

   modemEthTxCollisions OBJECT-TYPE 
      SYNTAX    Counter32
      MAX-ACCESS   read-only
      STATUS       current
      DESCRIPTION  " 
                    Ethernet Tx collisions counter 
                   "
      ::= { modemEthernetCountersEntry 41 }   

   modemEthTxByteCounterLow OBJECT-TYPE 
      SYNTAX    Counter32
      MAX-ACCESS   read-only
      STATUS       current
      DESCRIPTION  " 
                    Ethernet Tx byte low counter 
                   "
      ::= { modemEthernetCountersEntry 42 }   

   modemEthTxByteCounterHigh OBJECT-TYPE 
      SYNTAX    Counter32
      MAX-ACCESS   read-only
      STATUS       current
      DESCRIPTION  " 
                    Ethernet Tx byte high counter 
                   "
      ::= { modemEthernetCountersEntry 43 }   

   modemEthTxBitRate OBJECT-TYPE 
      SYNTAX    Counter32
      MAX-ACCESS   read-only
      STATUS       current
      DESCRIPTION  " 
                    Ethernet Tx bit Rate counter  Low 
                   "
      ::= { modemEthernetCountersEntry 44 }   

   modemEthCommulativeTime   OBJECT-TYPE 
      SYNTAX       Unsigned32
      MAX-ACCESS   read-only
      STATUS       current
      DESCRIPTION  " 
                    Ethernet Counters commulative time in seconds
                   "
      ::= { modemEthernetCountersEntry 45 }

   modemEthRateTime   OBJECT-TYPE 
      SYNTAX       INTEGER(1..255)
      MAX-ACCESS   read-write
      STATUS       current
      DESCRIPTION  " 
                     Ethernet Rate time  in seconds
                   "
      DEFVAL {1}
      ::= { modemEthernetCountersEntry 46 }
      
   modemEthRxBitRateHigh OBJECT-TYPE 
      SYNTAX    Counter32
      MAX-ACCESS   read-only
      STATUS       current
      DESCRIPTION  " 
                    Ethernet Rx bit rate  counter High  
                   "
      ::= { modemEthernetCountersEntry 47 }   

   modemEthTxBitRateHigh OBJECT-TYPE 
      SYNTAX    Counter32
      MAX-ACCESS   read-only
      STATUS       current
      DESCRIPTION  " 
                     Ethernet Tx bit rate  counter High   
                   "
      ::= { modemEthernetCountersEntry 48 }   

   modemEthRxShortEvents OBJECT-TYPE 
      SYNTAX    Counter32
      MAX-ACCESS   read-only
      STATUS       current
      DESCRIPTION  " 
                     Ethernet Rx counter of frames having length shorter than 53 Bytes 
                     (min packet length when MAC Supression applies).
                     Applicable only for the NEPTUNE modems
                   "
      ::= { modemEthernetCountersEntry 49 }


   --=========================================================                                      
   --  ETHERNET HIGH CAPACITY COUNTERS TABLE
   --=========================================================

   modemEthernetHcCountersTable OBJECT-TYPE
      SYNTAX       SEQUENCE OF   ModemEthernetHcCountersEntry
      MAX-ACCESS   not-accessible
      STATUS       current
      DESCRIPTION  " 
                     This table models the modem ethernet counters information fog High Capacity
                     interfaces.
                   "    
      ::= { modemConfig  22 }

   modemEthernetHcCountersEntry OBJECT-TYPE 
      SYNTAX       ModemEthernetHcCountersEntry
      MAX-ACCESS   not-accessible
      STATUS       current
      DESCRIPTION  " " 
      INDEX  {modemEthernetHcCountersEntryIndex} 
      ::={modemEthernetHcCountersTable 1 }

    ModemEthernetHcCountersEntry ::= SEQUENCE {                   
        modemEthernetHcCountersEntryIndex  INTEGER,
        modemEthHcTxPacketCounter    Counter64,
        modemEthHcRxPacketCounter    Counter64
   }

   modemEthernetHcCountersEntryIndex   OBJECT-TYPE 
      SYNTAX       INTEGER (1)
      MAX-ACCESS   not-accessible
      STATUS       current
      DESCRIPTION  "Index of the modemEthernetHcCountersEntry. 
                    It is restricted to 1 instance.
                   " 
      ::= { modemEthernetHcCountersEntry 1 }

   modemEthHcTxPacketCounter OBJECT-TYPE 
      SYNTAX    Counter64
      MAX-ACCESS   read-only
      STATUS       current
      DESCRIPTION  " 
                     Ethernet transmit packets counter for High Capacity interface (eg 10 Gbps).
                   " 
      ::= { modemEthernetHcCountersEntry 2 } 

   modemEthHcRxPacketCounter OBJECT-TYPE 
      SYNTAX    Counter64
      MAX-ACCESS   read-only
      STATUS       current
      DESCRIPTION  " 
                     Ethernet received packets counter for High Capacity interface (eg 10 Gbps).
                   " 
      ::= { modemEthernetHcCountersEntry 3 } 


   --=========================================================                                      
   --  MODEM TEST TABLE
   --=========================================================      

   modemTestTable OBJECT-TYPE
      SYNTAX       SEQUENCE OF   ModemTestEntry
      MAX-ACCESS   not-accessible
      STATUS       current
      DESCRIPTION  " 
          This table models the Modem Test general parameters.
                   "    
      ::= { modemConfig  23 }

   modemTestEntry OBJECT-TYPE 
      SYNTAX       ModemTestEntry
      MAX-ACCESS   not-accessible
      STATUS       current
      DESCRIPTION  " " 
      INDEX  {modemTestEntryIndex} 
      ::={modemTestTable 1 }

    ModemTestEntry ::= SEQUENCE {                   

        modemTestEntryIndex  INTEGER,
        modemTestType INTEGER,
        modemTestTimeout  Integer32,
        modemTestTimer Integer32
   }   

   modemTestEntryIndex   OBJECT-TYPE 
      SYNTAX       INTEGER (1)
      MAX-ACCESS   not-accessible
      STATUS       current
      DESCRIPTION  "Index of the ModemTestEntry. 
                    It is restricted to 1 instance.
                   " 
      ::= { modemTestEntry 1 }

   modemTestType OBJECT-TYPE 
       SYNTAX       INTEGER {noTest(0),
                             analogLoopBackONTest(1)}
       MAX-ACCESS   read-write
       STATUS       current
       DESCRIPTION
           "     
                The ModemTest Type that is ordered to be performed.
           " 
       DEFVAL {0}
       ::= { modemTestEntry 2 }  

   modemTestTimeout  OBJECT-TYPE
      SYNTAX   Integer32 (0..172800)
      UNITS    "seconds" 
      MAX-ACCESS  read-write
      STATUS  current
      DESCRIPTION
        "modemtest timeout, in seconds. 0 means not active time supervision of modem test." 
      DEFVAL {0}
      ::= { modemTestEntry 3 }

   modemTestTimer OBJECT-TYPE
      SYNTAX   Integer32 (0..172800)
      UNITS    "seconds" 
      MAX-ACCESS  read-only
      STATUS  current
      DESCRIPTION
        "Modem Test current Timer value, in seconds." 
      ::= { modemTestEntry 4}

   --=========================================================
   --  MODEM PHC TABLE
   --=========================================================

   ptpFlexModemPHCTable OBJECT-TYPE
      SYNTAX       SEQUENCE OF  PtpFlexModemPHCEntry
      MAX-ACCESS   not-accessible
      STATUS       current
      DESCRIPTION  "Table that models Packet Header Compression Header configuration information."
      ::= { modemConfig  24}

   ptpFlexModemPHCEntry OBJECT-TYPE
      SYNTAX       PtpFlexModemPHCEntry
      MAX-ACCESS   not-accessible
      STATUS       current
      DESCRIPTION  ""
      INDEX {ptpFlexModemPHCIndex}
      ::= { ptpFlexModemPHCTable 1 }

   PtpFlexModemPHCEntry ::= SEQUENCE {
      ptpFlexModemPHCIndex  Unsigned32,
      ptpFlexModemPHCState  TruthValue,
      ptpFlexModemPHCAging Unsigned32,
      ptpFlexModemPHCRobustness TruthValue,
      ptpFlexModemPHCMode  BITS,
      ptpFlexModemPHCAutoResetTimer Unsigned32
   }

   ptpFlexModemPHCIndex     OBJECT-TYPE
      SYNTAX       Unsigned32
      MAX-ACCESS   not-accessible
      STATUS       current
      DESCRIPTION
         "The modem index."
      ::= { ptpFlexModemPHCEntry 1 }

   ptpFlexModemPHCState OBJECT-TYPE
       SYNTAX       TruthValue
       MAX-ACCESS   read-write
       STATUS       current
       DESCRIPTION
           " Enable (true) or Disable (false) the Packet Header Compression."
       DEFVAL {false}
       ::= { ptpFlexModemPHCEntry 2 }

   ptpFlexModemPHCAging OBJECT-TYPE
       SYNTAX       Unsigned32 (1..511)
       UNITS        "seconds"
       MAX-ACCESS   read-write
       STATUS       current
       DESCRIPTION
           " Aging Timeout for each compressed Packet Header learnt by the system
             Value range    1..511
             All other values are not used.
             Default value 10 seconds."
       DEFVAL {10}
       ::= { ptpFlexModemPHCEntry 3 }

   ptpFlexModemPHCRobustness OBJECT-TYPE
       SYNTAX       TruthValue
       MAX-ACCESS   read-write
       STATUS       current
       DESCRIPTION
           " When value is set to true, a more efficient application of MAC Header
             Compression feature is utilized in traffic cases with unstable Radio Link
             (due to fading, interference etc)."
       DEFVAL {true}
       ::= { ptpFlexModemPHCEntry 4 }

   ptpFlexModemPHCMode OBJECT-TYPE
       SYNTAX       BITS { l2eth(0),
                           mpls(1),
                           ipv4(2),
                           l4port(3)
      }
       MAX-ACCESS   read-write
       STATUS       current
       DESCRIPTION
           " Specify the Mode of Packet Header Compression, the fields
           that will be compressed. Various combinations of fields compressions
           are supported.

            The bit l2eth (0) indicates that the Layer 2 Ethernet Header will be compressed.

            The bit mpls (1) indicates that MPLS label(s) will be compressed.

            The bit ipv4 (2) indicates that IPv4 Header will be compressed.

            The bit l4port (3) indicates L4 Port ids will be compressed.

            The default value for ptpFlexModemPHCMode object is
            empty set, which means no enumerated values are set."
       DEFVAL { { } }
       ::= { ptpFlexModemPHCEntry 5 }

   ptpFlexModemPHCAutoResetTimer OBJECT-TYPE
       SYNTAX       Unsigned32 (0..4095)
       UNITS        "seconds"
       MAX-ACCESS   read-write
       STATUS       current
       DESCRIPTION
           "Auto Reset Timeout of all learnt Packet Header Compression for modem.
            The value is counted in seconds
            Value range    0..4095 sec
            All other values are not used.
            Default value = 30, i.e. no auto-reset."
       DEFVAL { 30 }
       ::= { ptpFlexModemPHCEntry 6 }


   --================================================================ 
   -- PTP NOTIFICATIONS OBJECTS
   --================================================================
   
   ptpNotificationObjects OBJECT IDENTIFIER 
   ::= { modemConfig  7}     --- traps
   
   ptpModemFailureChange NOTIFICATION-TYPE
      OBJECTS {modemStatFail}
      STATUS current
      DESCRIPTION "
                    A trap indicating modem connection failure status                                   
                    [OmniBAS-2W, OmniBAS-4W  implementation]
                        The NMS forwards the following information to the operator:
                      
                        varbind[0].oid = oid_sysUpTime.0 = 1.3.6.1.2.1.1.3.0
                        varbind[0].val = NMS agent time (in centiseconds)
                   
                        varbind[1].oid = oid_snmpTrapOID.0 = 1.3.6.1.6.3.1.1.4.1.0
                        varbind[1].val = ptpModemFailureChange
                                       = 1.3.6.1.4.1.1807.55.1.1.7.1
                        varbind[2].oid = OidmodemStatFail
                                       = 1.3.6.1.4.1.1807.55.1.1.3.1.3
                        varbind[2].val = modemStatFail
                    
                      where
                      -- modemStatFail is the driver received status information
                          Modem failure information
                          The information is bitfield.
                          Bit value meaning:
                      
                          bit0: Clock PLL info               
                           - 0: PLL locked   (Alarm ceased)               
                           - 1: PLL UnLocked (Alarm raised)                 
                          bit1: Receiver's PLL info          
                           - 0: PLL Locked    (Alarm ceased)              
                           - 1: PLL Unlocked  (Alarm raised) 
                          bit2: Transmiter's PLL info             
                           - 0: PLL Locked     (Alarm ceased)            
                           - 1: PLL Unlocked   (Alarm raised) 
                          bit3: Modem Chip Failure              
                          - 0: Modem Chip OK        (Alarm ceased)       
                          - 1: Modem Chip Failure   (Alarm raised) 
                          bit4: Modem Chip Lock  
                           - 0: Modem Chip Locked    (Alarm ceased)
                           - 1: Modem Chip Unlocked (Alarm raised)                   
                          bit5..bit31: not used 
                  "
         ::= { ptpNotificationObjects 1}
   
   ptpmodemStatLinkStatusChange NOTIFICATION-TYPE
      OBJECTS {modemStatLinkStatus}
      STATUS current
      DESCRIPTION "
                    The trap signals the changes in Link status 
                    [OmniBAS-2W, OmniBAS-4W  implementation]
                    The NMS forwards the following information to the operator:
                     
                       varbind[0].oid = oid_sysUpTime.0 = 1.3.6.1.2.1.1.3.0
                       varbind[0].val = NMS agent time (in centiseconds)
                   
                       varbind[1].oid = oid_snmpTrapOID.0 = 1.3.6.1.6.3.1.1.4.1.0
                       varbind[1].val = ptpModemFailureChange
                                      = 1.3.6.1.4.1.1807.55.1.1.7.2
                       varbind[2].oid = OidModemStatLinkStatus
                                      = 1.3.6.1.4.1.1807.55.1.1.3.1.4
                       varbind[2].val = modemStatLinkStatus
                    
                     where
                     -- modemStatLinkStatus is the driver received link status information
                        (waitLock(0), lock(1), failed(2))
                  "
         ::= { ptpNotificationObjects 2}

   ptpRemoteModemStatLinkStatusChange NOTIFICATION-TYPE
      OBJECTS {remoteModemLinkStatus}
      STATUS current
      DESCRIPTION "
                    The trap signals the changes in remote Link status.  
                    [OmniBAS-2W, OmniBAS-4W  implementation]                  
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpRemoteModemStatLinkStatusChange
                                    = 1.3.6.1.4.1.1807.55.1.1.7.3
                     varbind[2].oid = OidRemoteModemLinkStatus
                                    = 1.3.6.1.4.1.1807.55.1.1.9.1.2
                     varbind[2].val = remoteModemLinkStatus
                   
                   where
                   -- remoteModemLinkStatus is the driver received remote link status information
                      (unLocked(0), locked(1), offLine(2), linkStatusUnknown(3) )
                  "
         ::= { ptpNotificationObjects 3}

   ptpXpicModeAlarm NOTIFICATION-TYPE
      OBJECTS {modemXpicConfEnabled}
      STATUS current
      DESCRIPTION "
                    The trap signals the changes in xpic modem configuration mode.  
                    [OmniBAS-4W  implementation]                  
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpXpicModeAlarm
                                    = 1.3.6.1.4.1.1807.55.1.1.7.4
                     varbind[2].oid = oid_modemXpicConfEnabled
                                    = 1.3.6.1.4.1.1807.55.1.1.14.1.2
                     varbind[2].val = modemXpicConfEnabled
                   
                   where
                   -- modemXpicConfEnabled is the driver received xpic modem mode information
                      (xpicenabled(1), xpicdisabled(2))
            
                  "
         ::= { ptpNotificationObjects 4}

   ptpmodemAlarmThreshStatusAlarm NOTIFICATION-TYPE
      OBJECTS {modemAlarmThreshStatus}
      STATUS current
      DESCRIPTION "
                    The trap signals the changes in modem threshhold status.  
                    [OmniBAS-2W, OmniBAS-4W  implementation]                  
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpmodemAlarmThreshStatusAlarm
                                    = 1.3.6.1.4.1.1807.55.1.1.7.5
                     varbind[2].oid = oid_modemAlarmThreshStatus
                                    = 1.3.6.1.4.1.1807.55.1.1.3.1.14
                     varbind[2].val = modemAlarmThreshStatus
                   
                   where
                   -- modemAlarmThreshStatus is the driver received modem threshhold information.
                                 bit0: Rx NormalizedMSE Alarm (SNR)
                                       - 0: Alarm ceased  
                                       - 1: Alarm raised  
                                 bit1: Rx Ldpc Decoders Stress Alarm
                                       - 0: Alarm ceased
                                       - 1: Alarm raised
                                 bit2: Modem PHY modulation configuration is not supported.                                                    
                                       The Alarm is raised, when the modem Physical Modulation value stored in
                                       the configuration, is not supported by the inserted modem in the system.                                            
                                       - 0: Alarm ceased
                                       - 1: Alarm raised
                                 bit3: The Alarm is raised when modemStatTemperature exceeds an internal
                                       High temperature threshold.
                                       The Alarm is ceased when modemStatTemperature falls lower than an
                                       internal Low temperature threshold.
                                       - 0: Alarm ceased
                                       - 1: Alarm raised
                                 bit4..bit31: not used
                  "
         ::= { ptpNotificationObjects 5}

   ptpModemTxPHYModulationChange NOTIFICATION-TYPE
      OBJECTS {modemPHYDescription}
      STATUS current
      DESCRIPTION "
                    The trap signals the changes in PHY Modulation Description for Tx direction.  
                    [OmniBAS-2W, OmniBAS-4W  implementation]                  
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpModemTxPHYModulationChange
                                    = 1.3.6.1.4.1.1807.55.1.1.7.6
                     varbind[2].oid = oid_modemPHYDescription
                                    = 1.3.6.1.4.1.1807.55.1.1.2.1.2
                     varbind[2].val = modemPHYDescription
                   
                   The severity of the trap is warning

                   where
                   -- modemPHYDescription is Modem PHY Modulation Description for Tx direction
                   The severity of the trap is warning

                  "
         ::= { ptpNotificationObjects 6}

   ptpModemRxPHYModulationChange NOTIFICATION-TYPE
      OBJECTS {modemPHYDescription}
      STATUS current
      DESCRIPTION "
                    The trap signals the changes in PHY Modulation Description for Tx direction.
                    [OmniBAS-2W, OmniBAS-4W  implementation]                  
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpModemRxPHYModulationChange
                                    = 1.3.6.1.4.1.1807.55.1.1.7.7

                     varbind[2].oid = oid_modemPHYDescription
                                    = 1.3.6.1.4.1.1807.55.1.1.2.1.2
                     varbind[2].val = modemPHYDescription

                     The severity of the trap is warning
                   
                     where
                     -- modemPHYDescription is Modem PHY Modulation Description for Rx direction
                  "
         ::= { ptpNotificationObjects 7}

   ptpNeptuneYellowAlarm NOTIFICATION-TYPE
      OBJECTS {modemStatLinkIndicator}
      STATUS current
      DESCRIPTION "
                    The trap signals the changes in the bit14 of modemStatLinkIndicator.
                    [Neptune  implementation]
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpNeptuneYellowAlarm
                                    = 1.3.6.1.4.1.1807.55.1.1.7.8

                     varbind[2].oid = oid_modemStatLinkIndicator
                                    = 1.3.6.1.4.1.1807.55.1.1.3.1.6
                     varbind[2].val = modemStatLinkIndicator

                     The severity of the trap is warning
                   
                     where
                     -- modemPHYDescription is Modem PHY Modulation Description for Rx direction
                  "
         ::= { ptpNotificationObjects 8}

   ptpNeptuneRedAlarm NOTIFICATION-TYPE
      OBJECTS {modemStatLinkIndicator}
      STATUS current
      DESCRIPTION "
                    The trap signals the changes in the bit15 of modemStatLinkIndicator.
                    [Neptune  implementation]
                    The NMS forwards the following information to the operator:
                   
                     varbind[0].oid = oid_sysUpTime.0 = 1.3.6.1.2.1.1.3.0
                     varbind[0].val = NMS agent time (in centiseconds)
                   
                     varbind[1].oid = oid_snmpTrapOID.0 = 1.3.6.1.6.3.1.1.4.1.0
                     varbind[1].val = ptpNeptuneRedAlarm
                                    = 1.3.6.1.4.1.1807.55.1.1.7.9

                     varbind[2].oid = oid_modemStatLinkIndicator
                                    = 1.3.6.1.4.1.1807.55.1.1.3.1.6
                     varbind[2].val = modemStatLinkIndicator

                     The severity of the trap is critical
                   
                     where
                     -- modemPHYDescription is Modem PHY Modulation Description for Rx direction
                  "
         ::= { ptpNotificationObjects 9}

   ptpModemPhymodLicenseFailure NOTIFICATION-TYPE
      OBJECTS {modemPHYDescription}
      STATUS current
      DESCRIPTION "
                     A trap indicating that the configured PHY mode is not licensed.       
                     The NMS forwards the following information to the operator:
                     
                        varbind[0].oid = oid_sysUpTime.0 = 1.3.6.1.2.1.1.3.0
                        varbind[0].val = NMS agent time (in centiseconds)
                  
                        varbind[1].oid = oid_snmpTrapOID.0 = 1.3.6.1.6.3.1.1.4.1.0
                        varbind[1].val = ptpModemPhymodLicenseFailure
                                       = 1.3.6.1.4.1.1807.55.1.1.2.1.1

                        varbind[2].oid = oid_modemPHYDescription.modemPHYModulationEntryIndex
                                       = 1.3.6.1.4.1.1807.55.1.1.2.1.2.modemPHYModulationEntryIndex
                        varbind[2].val = modemPHYDescription
  
                     The severity of the trap is warning.
                  "
         ::= { ptpNotificationObjects 10}

   ptpAtpcMaxTxPowerLicenseFail NOTIFICATION-TYPE
      OBJECTS { modemMaxATPCTxPower }
      STATUS current
      DESCRIPTION 
          " A trap indicating that the configured Max ATPC Tx Power is not licensed.       
          The NMS forwards the following information to the operator:
                     
              varbind[0].oid = oid_sysUpTime.0 = 1.3.6.1.2.1.1.3.0
              varbind[0].val = NMS agent time (in centiseconds)
                  
              varbind[1].oid = oid_snmpTrapOID.0 = 1.3.6.1.6.3.1.1.4.1.0
              varbind[1].val = ptpAtpcMaxTxPowerLicenseFail
                             = 1.3.6.1.4.1.1807.55.1.1.7.11

              varbind[2].oid = oid_modemMaxATPCTxPower.modemAdaptiveConfEntryIndex
                             = .1.3.6.1.4.1.1807.55.1.1.10.1.7.modemAdaptiveConfEntryIndex
              varbind[2].val = modemMaxATPCTxPower
  
              The severity of the trap is warning."
      ::= { ptpNotificationObjects 11}

   ptpAtpcMinTxPowerLicenseFail NOTIFICATION-TYPE
      OBJECTS { modemMinATPCTxPower }
      STATUS current
      DESCRIPTION
          " A trap indicating that the configured Min ATPC Tx Power is not licensed.       
          The NMS forwards the following information to the operator:
                     
              varbind[0].oid = oid_sysUpTime.0 = 1.3.6.1.2.1.1.3.0
              varbind[0].val = NMS agent time (in centiseconds)
                  
              varbind[1].oid = oid_snmpTrapOID.0 = 1.3.6.1.6.3.1.1.4.1.0
              varbind[1].val = ptpAtpcMinTxPowerLicenseFail
                             = 1.3.6.1.4.1.1807.55.1.1.7.12

              varbind[2].oid = oid_ modemMinATPCTxPower.modemAdaptiveConfEntryIndex
                             = .1.3.6.1.4.1.1807.55.1.1.10.1.8.modemAdaptiveConfEntryIndex
              varbind[2].val = modemMinATPCTxPower
  
              The severity of the trap is warning."
      ::= { ptpNotificationObjects 12}

   ptpAirEncryptionFailure NOTIFICATION-TYPE
      OBJECTS {modemStatusAirEncryptOperState}
      STATUS current
      DESCRIPTION " 
                 A trap indicating modem Air Ecpryption failure                                  
                     The NMS forwards the following information to the operator:
                     varbind[0].oid = oid_sysUpTime.0 = 1.3.6.1.2.1.1.3.0
                     varbind[0].val = NMS agent time (in centiseconds)
                     varbind[1].oid = oid_snmpTrapOID.0 = 1.3.6.1.6.3.1.1.4.1.0
                     varbind[1].val = ptpAirEncryptionFailure
                                    = 1.3.6.1.4.1.1807.55.1.1.7.13
                     varbind[2].oid = OidmodemStatusAirEncryptOperState
                                    = 1.3.6.1.4.1.1807.55.1.1.3.1.23
                     varbind[2].val = modemStatusAirEncryptOperState
                   where
                   -- modemStatusAirEncryptOperState is the driver received status information
                       for Modem Air Encryption operational status
                       (working (1), notWorking (2)).
               " 
      ::= { ptpNotificationObjects 13}

    ptpModemTestNotification NOTIFICATION-TYPE
      OBJECTS {modemTestType, modemTestTimeout}
      STATUS current
      DESCRIPTION " 
           A trap indicating the active Modem Test Type

            The NMS forwards the following information to the operator:
               varbind[0].oid = oid_sysUpTime.0 = 1.3.6.1.2.1.1.3.0
               varbind[0].val = NMS agent time (in centiseconds)

               varbind[1].oid = oid_snmpTrapOID.0 = 1.3.6.1.6.3.1.1.4.1.0
               varbind[1].val = ptpModemTestNotification
                              = .1.3.6.1.4.1.1807.55.1.1.7.14

               varbind[2].oid = modemTestType
                              = .1.3.6.1.4.1.1807.55.1.1.23.1.2
               varbind[2].val = modemTestType Value

               varbind[3].oid = modemTestTimeout
                              = .1.3.6.1.4.1.1807.55.1.1.23.1.3
               varbind[3].val = modemTestTimeout Value

             where
                  modemTestType  Value indicates the test type that has been started,

                  modemTestTimeout Value is the received modem test timeout value
                  for the period till the test completion.
                  Value meaning:
                     0: Indicates that the test is not active
                     Other : Indicates Analogue loopback-on test Active

             - Alarm type: Event

             "  
      ::= { ptpNotificationObjects 14}

   ptpModemRemoteXPICStatusChange NOTIFICATION-TYPE
      OBJECTS {xpicModemStatusRAITxMuted}
      STATUS current
      DESCRIPTION " 
                    The trap signals the changes in the Remote XPIC Modem Status 
                    The NMS forwards the following information to the operator:

                       varbind[0].oid = oid_sysUpTime.0 = 1.3.6.1.2.1.1.3.0
                       varbind[0].val = NMS agent time (in centiseconds)

                       varbind[1].oid = oid_snmpTrapOID.0 = 1.3.6.1.6.3.1.1.4.1.0
                       varbind[1].val = ptpModemRemoteXPICStatusChange 
                                      = 1.3.6.1.4.1.1807.55.1.1.7.15
                       varbind[2].oid = OidXpicModemStatusRAITxMuted
                                      = 1.3.6.1.4.1.1807.55.1.1.3.1.4
                       varbind[2].val = xpicModemStatusRAITxMuted 

                     where
                     -- xpicModemStatusRAITxMuted is the driver received Remote XPIC Modem status information
                     -- (true(1) is Remote XPIC Modem failed, false(2) is Remote XPIC Modem OK)
                  " 
      ::= { ptpNotificationObjects 15}

   --================================================================ 
   -- PTP MODEM VERSION OBJECTS
   --================================================================

   modemVersionTable OBJECT-TYPE
      SYNTAX       SEQUENCE OF   ModemVersionEntry
      MAX-ACCESS   not-accessible
      STATUS       current
      DESCRIPTION  " 
                     This table models the modem Versions information  
                   "    
      ::= { modemConfig  8 }

   modemVersionEntry OBJECT-TYPE 
      SYNTAX       ModemVersionEntry
      MAX-ACCESS   not-accessible
      STATUS       current
      DESCRIPTION  " "
      INDEX  {modemVersionEntryIndex} 
      ::={modemVersionTable 1 }

    ModemVersionEntry ::= SEQUENCE {
        modemVersionEntryIndex  INTEGER,
        modemVersionStr  OCTET STRING, 
        fpgaVersion    Unsigned32,
        slave1FpgaVersion Unsigned32
   }   
   
   modemVersionEntryIndex   OBJECT-TYPE 
      SYNTAX       INTEGER (1)
      MAX-ACCESS   not-accessible
      STATUS       current
      DESCRIPTION  "
                    Index of the ModemVersionEntry. 
                    It is restricted to 1 instance.
                   "
      ::= { modemVersionEntry 1 }
      
   modemVersionStr OBJECT-TYPE 
      SYNTAX       OCTET STRING
      MAX-ACCESS   read-only
      STATUS       current
      DESCRIPTION  " 
                     Modem Version information
                   "
      ::= { modemVersionEntry 2 }   
 
    fpgaVersion OBJECT-TYPE 
      SYNTAX       Unsigned32
      MAX-ACCESS   read-only
      STATUS       current
      DESCRIPTION  " 
                     FPGA Version information
                   "
      ::= { modemVersionEntry 3 }

    slave1FpgaVersion   OBJECT-TYPE
      SYNTAX       Unsigned32
      MAX-ACCESS   read-only
      STATUS       current
      DESCRIPTION  "
                     Secondary FPGA Version information
                   "
      ::= { modemVersionEntry 4 }

   --================================================================ 
   -- PTP REMOTE MODEM STATUS OBJECTS
   --================================================================

   modemRemoteStatusTable OBJECT-TYPE
      SYNTAX       SEQUENCE OF   ModemRemoteStatusEntry
      MAX-ACCESS   not-accessible
      STATUS       current
      DESCRIPTION  " 
                    This table models the remote modem Status information
                   "    
      ::= { modemConfig  9 }

   modemRemoteStatusEntry OBJECT-TYPE 
      SYNTAX       ModemRemoteStatusEntry
      MAX-ACCESS   not-accessible
      STATUS       current
      DESCRIPTION  " "
      INDEX  {modemRemoteStatusEntryIndex} 
      ::={modemRemoteStatusTable 1 }

    ModemRemoteStatusEntry ::= SEQUENCE {
        modemRemoteStatusEntryIndex  INTEGER,
        remoteModemLinkStatus  PtpModemLinkStatus,
        remoteModemIpAddress  IpAddress,
        remoteModemSlot INTEGER,
        remoteModemLinkId  INTEGER,
        remoteModemLinkRebootMode INTEGER
   }   
   
   modemRemoteStatusEntryIndex   OBJECT-TYPE 
      SYNTAX       INTEGER (1)
      MAX-ACCESS   not-accessible
      STATUS       current
      DESCRIPTION  "
                    Index of the modemRemoteStatusEntryIndex. 
                    It is restricted to 1 instance.
                   "
      ::= { modemRemoteStatusEntry 1 }
      
   remoteModemLinkStatus OBJECT-TYPE 
      SYNTAX       PtpModemLinkStatus
      MAX-ACCESS   read-only
      STATUS       current
      DESCRIPTION  " 
                     Remote Modem Link Status  information
                     Value Range unlocked(0),     
                                 locked(1),       
                                 offLine(2),
                                 linkStatusUnknown(3)
                   "
      ::= { modemRemoteStatusEntry 2 } 

   remoteModemIpAddress             OBJECT-TYPE
      SYNTAX                               IpAddress
      MAX-ACCESS                           read-only
      STATUS                               current
      DESCRIPTION    
                   "
                    This object indicates the IP address 
                    that has been allocated to the remote modem
                   "
   ::= { modemRemoteStatusEntry 3 }
   
  remoteModemSlot   OBJECT-TYPE 
      SYNTAX       INTEGER(0..255)
      MAX-ACCESS   read-only
      STATUS       current
      DESCRIPTION  
      " Remote Station slot"
      ::= { modemRemoteStatusEntry 4 }

  remoteModemLinkId OBJECT-TYPE 
      SYNTAX       INTEGER(1..65535)
      MAX-ACCESS   read-only
      STATUS       current
      DESCRIPTION  
          " Remote LinkId received from the remote peer modem. This is a configuration unique number which must be identical 
            at both sides of the link. Using this number the system identifies that has link with the right remote system.
            This object is applicable only when the object modemLinkIdCheck is set as used otherwise it includes only a 
            preconfigured value but that LinkId value is not used to check the link validity.
            The object is applicable only for Antenna Alignment Handling." 
      ::= { modemRemoteStatusEntry 5 }

  remoteModemLinkRebootMode OBJECT-TYPE 
      SYNTAX       INTEGER {
                            none(1),
                            modemLevel(2),
                            systemLevel(3)
                           }
      MAX-ACCESS   read-write
      STATUS       current
      DESCRIPTION  " 
                     It triggers a reboot at remote air-link side when the value is other than none(1).
                     Reboot at modem level (2) or system level (3).
                   " 
      ::= { modemRemoteStatusEntry 6 }  


   --================================================================ 
   -- PTP MODEM ADAPTIVE CONFIGURATION OBJECTS
   --================================================================

   modemAdaptiveConfTable OBJECT-TYPE
      SYNTAX       SEQUENCE OF   ModemAdaptiveConfEntry
      MAX-ACCESS   not-accessible
      STATUS       current
      DESCRIPTION  " 
                    This table models the modem adaptive configuration information
                   "    
      ::= { modemConfig  10 }

   modemAdaptiveConfEntry OBJECT-TYPE 
      SYNTAX       ModemAdaptiveConfEntry
      MAX-ACCESS   not-accessible
      STATUS       current
      DESCRIPTION  " "
      INDEX  {modemAdaptiveConfEntryIndex} 
      ::={modemAdaptiveConfTable 1 }

    ModemAdaptiveConfEntry ::= SEQUENCE {
        modemAdaptiveConfEntryIndex  INTEGER,
        modemPowerMode  PtpModemPowerModeState,
        modemOptimumRSSI  INTEGER,
        modemMaxAutoPHYmod INTEGER,
        modemMinAutoPHYmod INTEGER,
        modemAdaptiveConfDownLoadValues INTEGER,
        modemMaxATPCTxPower  INTEGER,
        modemMinATPCTxPower  INTEGER,
        modemAutoMaxPowerMode INTEGER
   }   
   
   modemAdaptiveConfEntryIndex   OBJECT-TYPE 
      SYNTAX       INTEGER (1)
      MAX-ACCESS   not-accessible
      STATUS       current
      DESCRIPTION  "
                    Index of the modemAdaptiveConfEntryIndex. 
                    It is restricted to 1 instance.
                   "
      ::= { modemAdaptiveConfEntry 1 }
      
   modemPowerMode OBJECT-TYPE 
      SYNTAX       PtpModemPowerModeState
      MAX-ACCESS   read-write
      STATUS       current
      DESCRIPTION  " 
                     Modem power mode inforamtion
                     Value Range 
                                 manual(0),     
                                 optimum(1),       
                                 max(2)
                   "
      DEFVAL {manual}
      ::= { modemAdaptiveConfEntry 2 } 

   modemOptimumRSSI             OBJECT-TYPE
      SYNTAX                    INTEGER
      MAX-ACCESS                read-write
      STATUS                    current
      DESCRIPTION    
                   "
                      This object indicates the modem 
                      optimum RSSI value  
                      The value is calculated                        
                      in 0.1dBm step
                   "
   DEFVAL {250}
   ::= { modemAdaptiveConfEntry 3 }
   
  modemMaxAutoPHYmod   OBJECT-TYPE 
      SYNTAX       INTEGER(1..16)
      MAX-ACCESS   read-write
      STATUS       current
      DESCRIPTION  
      " Modem maximum auto physical mode "
      DEFVAL {1}
      ::= { modemAdaptiveConfEntry 4 }
    
  modemMinAutoPHYmod   OBJECT-TYPE 
      SYNTAX       INTEGER(1..16)
      MAX-ACCESS   read-write
      STATUS       current
      DESCRIPTION  
      " Modem minimum auto physical mode 

        Value range:         
        OMNIBAS-4W: 1
        OMNIBAS-4W-HE: 1..16
        OMNIBAS-2W: 1
        OMNIBAS-2W-16E1: 1..16
        OMNIBAS-XR: 1..16
        OMNIBAS-8W: 1
      "
      DEFVAL {1}
      ::= { modemAdaptiveConfEntry 5 }

   modemAdaptiveConfDownLoadValues OBJECT-TYPE 
      SYNTAX       INTEGER { notDownloadValue(1),
                             downloadValue(2) }
      MAX-ACCESS   read-write
      STATUS       current
      DESCRIPTION
          " When set to downLoadValue (2), the manager downloads the 
          values of the OIDs 
             modemPowerMode, modemOptimumRSSI, modemMaxAutoPHYmod, 
             modemMinAutoPHYmod, modemMaxATPCTxPower, modemMinATPCTxPower,
             modemAutoMaxPowerMode."
      ::= { modemAdaptiveConfEntry 6 }  

   modemMaxATPCTxPower   OBJECT-TYPE 
      SYNTAX       INTEGER (-32767..32767)
      MAX-ACCESS   read-write
      STATUS       current
      DESCRIPTION  
          "Modem Maximum ATPC Tx Power value in tenths of dBms" 
      DEFVAL {9999}
      ::= { modemAdaptiveConfEntry 7 }

   modemMinATPCTxPower   OBJECT-TYPE 
      SYNTAX       INTEGER (-32767..32767)
      MAX-ACCESS   read-write
      STATUS       current
      DESCRIPTION  
          "Modem Minimum ATPC Tx Power value in tenths of dBms" 
      DEFVAL {-9999}
      ::= { modemAdaptiveConfEntry 8}

   modemAutoMaxPowerMode OBJECT-TYPE 
      SYNTAX       INTEGER { maxSNR (1),
                             maxPower (2)
                           }             
      MAX-ACCESS   read-write
      STATUS       current
      DESCRIPTION  "Type of power control mode when modemPowerMode = max at PTPv3 modems.
                    Value maxSNR is Auto Max SNR controlled power.
                    Value maxPower is Auto Max Power.
                   " 
      DEFVAL {maxSNR}
      ::= { modemAdaptiveConfEntry 9 } 



   --=========================================================                                      
   -- XPIC MODEM STATUS COUNTERS TABLE
   --=========================================================

   xpicModemStatusCountersTable OBJECT-TYPE
      SYNTAX       SEQUENCE OF   XpicModemStatusCountersEntry
      MAX-ACCESS   not-accessible
      STATUS       current
      DESCRIPTION  " 
                     This table models the cross polarization
                     interference cancellation (XPIC) modem status 
                     information. It is applicable
                     only for for Omnibas-4W products. 
                   "    
      ::= { modemConfig  11 }

   xpicModemStatusCountersEntry OBJECT-TYPE 
      SYNTAX       XpicModemStatusCountersEntry
      MAX-ACCESS   not-accessible
      STATUS       current
      DESCRIPTION  " "
      INDEX  {xpicModemStatusCountersIndex} 
      ::={xpicModemStatusCountersTable 1 }

    XpicModemStatusCountersEntry ::= SEQUENCE {                   
      
        xpicModemStatusCountersIndex  INTEGER,
        xpdStatusCounter   INTEGER,
        xpicsweepStatus     INTEGER,
        xpdCalibration     INTEGER,
        xpicModemStatusRAITxMuted TruthValue
     }   
  
   xpicModemStatusCountersIndex   OBJECT-TYPE 
      SYNTAX       INTEGER (1)
      MAX-ACCESS   not-accessible
      STATUS       current
      DESCRIPTION  "Index of the xpicModemStatusCountersEntry. 
                   It is restricted to 1 instance.
                   "
      ::= { xpicModemStatusCountersEntry 1 }

   xpdStatusCounter OBJECT-TYPE 
      SYNTAX    INTEGER
      MAX-ACCESS   read-only
      STATUS       current
      DESCRIPTION  " 
                    The OID represents the cross 
                    polarization discrimination(XPD) 
                    counter.
     
                    The value is calculated      
                    in 0.1dB step.              
                   " 
      ::= { xpicModemStatusCountersEntry 2 }   

    xpicsweepStatus OBJECT-TYPE 
      SYNTAX    INTEGER{ xpicSlaveSweepDone(0),
                         xweepInProgress(1)}
      MAX-ACCESS   read-only
      STATUS       current
      DESCRIPTION  " 
                     The oid represents the 
                     xpic sweep Status state
 
                   "
      ::= { xpicModemStatusCountersEntry 3 } 
      
   xpdCalibration OBJECT-TYPE 
      SYNTAX    INTEGER{ xpdSuccess(0),
                         xpdMismatch(1),
                         xpdTimeOut(2)}

      MAX-ACCESS   read-only
      STATUS       current
      DESCRIPTION  " 
                     The oid represents the    
                     XPD calibration state 
                   "
      ::= { xpicModemStatusCountersEntry 4 }   

    xpicModemStatusRAITxMuted OBJECT-TYPE 
      SYNTAX       TruthValue
      MAX-ACCESS   read-only
      STATUS       current
      DESCRIPTION  "  
                     When true, the Remote Modem of this XPIC Modem has failed and 
                     the local Modem sets tx-mute to ON.
                     When false, the Remote Modem of this XPIC Modem works successfully.
                   " 
      ::= { xpicModemStatusCountersEntry 5 }

   --=========================================================                                      
   -- ACQUIRE MODEM COUNTERS TABLE
   --=========================================================

   acquireModemCountersTable OBJECT-TYPE
      SYNTAX       SEQUENCE OF   AcquireModemCountersEntry
      MAX-ACCESS   not-accessible
      STATUS       current
      DESCRIPTION  " 
                     This table models the acquire 
                     counters. It is applicable
                     both for for Omnibas-4W and 
                     Omnibas-2W products. 
                   "    
      ::= { modemConfig  12 }

   acquireModemCountersEntry OBJECT-TYPE 
      SYNTAX       AcquireModemCountersEntry
      MAX-ACCESS   not-accessible
      STATUS       current
      DESCRIPTION  " "
      INDEX  {acquireModemCountersIndex} 
      ::={acquireModemCountersTable 1 }

    AcquireModemCountersEntry ::= SEQUENCE {                   
      
        acquireModemCountersIndex  INTEGER,
        numOfLolEvents   Counter32,
        acquireModemCounterReset INTEGER
     }   
  
   acquireModemCountersIndex   OBJECT-TYPE 
      SYNTAX       INTEGER (1)
      MAX-ACCESS   not-accessible
      STATUS       current
      DESCRIPTION  "Index of the acquireModemCountersEntry. 
                   It is restricted to 1 instance.
                   "
      ::= { acquireModemCountersEntry 1 }

   numOfLolEvents OBJECT-TYPE 
      SYNTAX    Counter32
      MAX-ACCESS   read-only
      STATUS       current
      DESCRIPTION  " 
                    The OID represents the link out 
                    of lock (LOL) counter.          
                   " 
      ::= { acquireModemCountersEntry 2 } 
       
    acquireModemCounterReset OBJECT-TYPE 
      SYNTAX    INTEGER{noResetCounter(0),
                        resetCounter(1)
                         }
      MAX-ACCESS   read-write
      STATUS       current
      DESCRIPTION  " 
                    The OID used to reset the numOfLooEvents counter. 
    
                   " 
      DEFVAL {noResetCounter}
      ::= { acquireModemCountersEntry 3 }   

   --=========================================================                                      
   -- FEC COUNTERS TABLE
   --=========================================================

   fecCountersTable OBJECT-TYPE
      SYNTAX       SEQUENCE OF   FecCountersEntry
      MAX-ACCESS   not-accessible
      STATUS       current
      DESCRIPTION  " 
                     This table models the forward error 
                     correction(FEC) counters.It is applicable
                     both for for Omnibas-4W and 
                     Omnibas-2W products. 
                   "    
      ::= { modemConfig  13 }

   fecCountersEntry OBJECT-TYPE 
      SYNTAX       FecCountersEntry
      MAX-ACCESS   not-accessible
      STATUS       current
      DESCRIPTION  " "
      INDEX  {fecCountersIndex} 
      ::={fecCountersTable 1 }

    FecCountersEntry ::= SEQUENCE {                   
      
        fecCountersIndex  INTEGER,
        fecBlockCounter   Counter64,
        fecUncorBlockCounter     Counter64,
        fecCountersReset     INTEGER
     }   
  
   fecCountersIndex   OBJECT-TYPE 
      SYNTAX       INTEGER (1)
      MAX-ACCESS   not-accessible
      STATUS       current
      DESCRIPTION  "Index of the FecCountersEntry. 
                   It is restricted to 1 instance.
                   "
      ::= { fecCountersEntry 1 }

   fecBlockCounter OBJECT-TYPE 
      SYNTAX    Counter64
      MAX-ACCESS   read-only
      STATUS       current
      DESCRIPTION  " 
                    The OID represents the 
                    the forward error correction
                    block counter.
             
                   " 
      ::= { fecCountersEntry 2 }   

   fecUncorBlockCounter OBJECT-TYPE 
      SYNTAX    Counter64
      MAX-ACCESS   read-only
      STATUS       current
      DESCRIPTION  " 
                     The OID represents the 
                    the forward error correction
                    uncorBlock counter.
                   " 
      ::= { fecCountersEntry 3 } 
      
    fecCountersReset OBJECT-TYPE 
      SYNTAX    INTEGER{fecNoResetCounter(0),
                        fecResetCounter(1)
                         }
      MAX-ACCESS   read-write
      STATUS       current
      DESCRIPTION  " 
                    The OID used to reset the FEC counters. 
   
                   " 
      DEFVAL {fecNoResetCounter}
      ::= { fecCountersEntry 4 }

   --========================================================
   --========================================================
   --  XPIC Modem Configuration Table
   --========================================================
   
      modemXpicGroupConfTable OBJECT-TYPE 
         SYNTAX       SEQUENCE OF  ModemXpicGroupConfEntry
         MAX-ACCESS   not-accessible
         STATUS       current
         DESCRIPTION  "
              [Omnibas-4W implementation]
               This table refers only to XPIC modems,
               so it is is applicable only in OmniBAS-4W.

               Table of configuration settings regarding Xpic modem 
               functionality. 
               
               There are automatically created rows for each possible Xpic modem.
           "
         ::= { modemConfig 14 }   
         
      modemXpicGroupConfEntry OBJECT-TYPE 
         SYNTAX       ModemXpicGroupConfEntry
         MAX-ACCESS   not-accessible
         STATUS       current
         DESCRIPTION  "XPIC Modem."
         INDEX {modemXpicConfIndex}
         ::= { modemXpicGroupConfTable 1 }       
      
      ModemXpicGroupConfEntry ::= SEQUENCE {    
          modemXpicConfIndex         INTEGER,
          modemXpicConfEnabled       INTEGER,
          modemXpicConfPreambleType  INTEGER
      }
      
      modemXpicConfIndex     OBJECT-TYPE 
         SYNTAX       INTEGER (1)
         MAX-ACCESS   not-accessible
         STATUS       current
         DESCRIPTION  "

           The index is 1 for all modems.
           "
         ::= { modemXpicGroupConfEntry 1 }     
      
      modemXpicConfEnabled    OBJECT-TYPE 
         SYNTAX       INTEGER {xpicenabled(1),
                               xpicdisabled(2)}
         MAX-ACCESS   read-write
         STATUS       current
         DESCRIPTION  "
               Xpic Modem Enable/ ptp Modem enable.
               Valid values are: xpicenabled(1), xpicdisabled(2)."
         DEFVAL {xpicdisabled}
         ::= { modemXpicGroupConfEntry 2 } 

      modemXpicConfPreambleType    OBJECT-TYPE 
         SYNTAX       INTEGER {lockOddModem(1),
                               lockEvenModem(2)}
         MAX-ACCESS   read-write
         STATUS       current
         DESCRIPTION  " 
               Xpic Preamble Pattern Indicator. 
               The preamble pattern type is used to differentiate 
               the two streams of an XPIC link. Orthogonal preambles are assigned at both ends, 
               so that the corresponding modems do not lock to the wrong signal. 
               The name of the preamble patterns is based on their use in the systems, where
               they are fixed and not provisioned by the user.
               The pattern lockOddModem is the one that is used by OmniBAS Split systems at the modems 
               at odd system slots. 
               The orthogonal to that pattern lockEvenModem is the one that is used by OmniBAS Split systems 
               at the modems at even system slots."  
         DEFVAL { lockOddModem}
         ::= { modemXpicGroupConfEntry 3 }

  --=========================================================                                      
   -- MODEM THRESHHOLD ALARM CONFIGURATION TABLE
   --========================================================

   modemThreshAlarmConfTable OBJECT-TYPE
      SYNTAX       SEQUENCE OF   ModemThreshAlarmConfEntry
      MAX-ACCESS   not-accessible
      STATUS       current
      DESCRIPTION  " 
                     This table models the modem threshhold Alarm Configuration information 
                   "    
      ::= { modemConfig 15 }

   modemThreshAlarmConfEntry OBJECT-TYPE 
      SYNTAX       ModemThreshAlarmConfEntry
      MAX-ACCESS   not-accessible
      STATUS       current
      DESCRIPTION  " "
      INDEX  {modemThreshAlarmConfEntryIndex} 
      ::={modemThreshAlarmConfTable 1 }

    ModemThreshAlarmConfEntry ::= SEQUENCE {                   
      
        modemThreshAlarmConfEntryIndex  INTEGER,
        modemRxNormalizedMSEThresh  INTEGER,
        modemRxLdpcDecodersStressThresh     Unsigned32,
        muteRxModulationChangeTrap  INTEGER,
	muteTxModulationChangeTrap  INTEGER
   }   
   
   modemThreshAlarmConfEntryIndex   OBJECT-TYPE 
      SYNTAX       INTEGER (1)
      MAX-ACCESS   not-accessible
      STATUS       current
      DESCRIPTION  "
                    Index of the ModemThreshAlarmConfEntry. 
                    It is restricted to 1 instance.
                   "
      ::= { modemThreshAlarmConfEntry 1 }

   modemRxNormalizedMSEThresh OBJECT-TYPE 
      SYNTAX       INTEGER
      MAX-ACCESS   read-write
      STATUS       current
      DESCRIPTION  " 
                     The Oid indicates the modem plain SNR
                     The value is calculated  
                     in 0.1dB step
                   "
      DEFVAL {0}
      ::= { modemThreshAlarmConfEntry 2 }   

   modemRxLdpcDecodersStressThresh OBJECT-TYPE 
      SYNTAX       Unsigned32
      MAX-ACCESS   read-write
      STATUS       current
      DESCRIPTION  " 
                     Modem Rx LDPC Decodes stress threshold.
                     The value range is in range [0..4294967295]. 
                   "
      DEFVAL {4294967295}
      ::= { modemThreshAlarmConfEntry 3 }
      
   muteRxModulationChangeTrap OBJECT-TYPE 
       SYNTAX       INTEGER {modRxTrapOff(0),
                                               modRxTrapOn(1) }
       MAX-ACCESS   read-write
       STATUS       current
       DESCRIPTION
           "     
                Administration command to turn on/Off
                the Physical modulation change traps. 
                Value meaning: 
		modRxTrapOff(0),    : Turns off RxPhyTrap modulation change trap.
                modRxTrapOn(1)     :Turns on RxPhyTrap  modulation change trap.     
           "
       DEFVAL {modRxTrapOff}
       ::= { modemThreshAlarmConfEntry 4 }  

   muteTxModulationChangeTrap OBJECT-TYPE 
       SYNTAX       INTEGER {modTxTrapOff(0),
                                               modTxTrapOn(1) }
       MAX-ACCESS   read-write
       STATUS       current
       DESCRIPTION
           "     
                Administration command to turn on/Off
                the Physical modulation change traps. 
                Value meaning: 
			modTxTrapOff(0),    : Turns off TxPhyTrap modulation change trap.
                        modTxTrapOn(1)     :Turns on  TxPhyTrap  modulation change trap.     
            "
       DEFVAL {modTxTrapOff}
       ::= { modemThreshAlarmConfEntry 5 }  

   --=========================================================                                      
   -- G826 COUNTERS TABLE
   --=========================================================

   g826CountersTable OBJECT-TYPE
      SYNTAX       SEQUENCE OF   G826CountersEntry
      MAX-ACCESS   not-accessible
      STATUS       current
      DESCRIPTION  " 
                     This table models the G.826 performance 
                     measurements on radio link. It is applicable
                     both for Omnibas-4W and Omnibas-2W products. 
                   "    
      ::= { modemConfig  16 }

   g826CountersEntry OBJECT-TYPE 
      SYNTAX       G826CountersEntry
      MAX-ACCESS   not-accessible
      STATUS       current
      DESCRIPTION  " "
      INDEX  {g826CounterIndex} 
      ::={g826CountersTable 1 }

    G826CountersEntry ::= SEQUENCE {
        g826CounterIndex  INTEGER,
        errorBlockCounter   Counter64,
        backGroundBlockErrorsCounter  Counter64,
        errorSecondsCounter Counter32,
        severelyErroredSecondsCounter Counter32,
        availlableSecCounter Counter32,
        unavailableSecondsCounter Counter32,
        g826CounterControl INTEGER
     }   
  
   g826CounterIndex   OBJECT-TYPE 
      SYNTAX       INTEGER (1)
      MAX-ACCESS   not-accessible
      STATUS       current
      DESCRIPTION  "Index of the G826CountersEntry. 
                   It is restricted to 1 instance.
                   "
      ::= { g826CountersEntry 1 }

  errorBlockCounter OBJECT-TYPE 
      SYNTAX    Counter64
      MAX-ACCESS   read-only
      STATUS       current
      DESCRIPTION  " 
                     The OID represents the 
                    the error block counter.
                   " 
      ::= { g826CountersEntry 2 } 

  backGroundBlockErrorsCounter OBJECT-TYPE 
      SYNTAX    Counter64
      MAX-ACCESS   read-only
      STATUS       current
      DESCRIPTION  " 
                     The OID represents the 
                    the background block error 
                    counter.
                   " 
      ::= { g826CountersEntry 3 } 

  errorSecondsCounter OBJECT-TYPE 
      SYNTAX    Counter32
      MAX-ACCESS   read-only
      STATUS       current
      DESCRIPTION  " 
                     The OID represents the 
                    the error seconds counter.
                   " 
      ::= { g826CountersEntry 4 } 

  severelyErroredSecondsCounter OBJECT-TYPE 
      SYNTAX    Counter32
      MAX-ACCESS   read-only
      STATUS       current
      DESCRIPTION  " 
                     The OID represents the 
                     the severely errored seconds
                     counter.
                   " 
      ::= { g826CountersEntry 5 } 

     availlableSecCounter OBJECT-TYPE 
      SYNTAX    Counter32
      MAX-ACCESS   read-only
      STATUS       current
      DESCRIPTION  " 
                     The OID represents the 
                    the available seconds counter.
                   " 
      ::= { g826CountersEntry 6 } 

  unavailableSecondsCounter OBJECT-TYPE 
      SYNTAX    Counter32
      MAX-ACCESS   read-only
      STATUS       current
      DESCRIPTION  " 
                     The OID represents the 
                    the unavailable seconds counter.
                   " 
      ::= { g826CountersEntry 7 } 
      
    g826CounterControl OBJECT-TYPE 
      SYNTAX    INTEGER{ none(0),
                         reset(1)
                         }
      MAX-ACCESS   read-write
      STATUS       current
      DESCRIPTION  " 
                    The OID used to reset the g826 counters. 
   
                   " 
      DEFVAL {none}
      ::= { g826CountersEntry 8 }


 --==========================================================
   ptpFlexModemMHSTable OBJECT-TYPE 
      SYNTAX       SEQUENCE OF  PtpFlexModemMHSEntry
      MAX-ACCESS   not-accessible
      STATUS       current
      DESCRIPTION  " Table that models Modem MAC SuppressionHeader configuration information of an OMNIBAS system,4wHE or 2w16E1 or XR"
      ::= { modemConfig  17}

   ptpFlexModemMHSEntry OBJECT-TYPE 
      SYNTAX       PtpFlexModemMHSEntry
      MAX-ACCESS   not-accessible
      STATUS       current
      DESCRIPTION  ""
      INDEX {ptpFlexModemMHSIndex}
      ::= { ptpFlexModemMHSTable 1 }    

   PtpFlexModemMHSEntry ::= SEQUENCE { 

   ptpFlexModemMHSIndex     INTEGER,
   ptpFlexModemMHSSupprState  INTEGER,
   ptpFlexModemMHSAging INTEGER,
   ptpFlexModemMHSRobustness INTEGER,
   ptpFlexModemMHSAutoResetTimer INTEGER
   }
   
   ptpFlexModemMHSIndex     OBJECT-TYPE 
      SYNTAX       INTEGER (1..8)
      MAX-ACCESS   not-accessible
      STATUS       current
      DESCRIPTION  
         "The number of modems in an OmniBas system
	   The value range of the index is system depended 
	   as shown below:
           OB-4W-HE the range is 1..4
	   OB-2w16E1 the range is 1..2
           OB-XR the range is 1
	 "
      ::= { ptpFlexModemMHSEntry 1 }  

ptpFlexModemMHSSupprState OBJECT-TYPE 
       SYNTAX       INTEGER { disable (0), enable (1)}
       MAX-ACCESS   read-write
       STATUS       current
       DESCRIPTION
           " Enable or Disable the MAC Address Suppression
              Value range 
	      FlexModemMHSSupprState 0 disabled
	      FlexModemMHSSupprState 1 enabled
	      All other values are not used.
	      default value disable(0)
	   "
       DEFVAL {disable}    
       ::= { ptpFlexModemMHSEntry  2}  
	
ptpFlexModemMHSAging OBJECT-TYPE 
       SYNTAX       INTEGER (1..511)
       MAX-ACCESS   read-write
       STATUS       current
       DESCRIPTION
           " Aging Timeout of the suppressed MAC Addresses learnt by the system
	     Value range    1..511
	     All other values are not used.
	     Default value 10 
	   "
       DEFVAL {10}    
       ::= { ptpFlexModemMHSEntry 3}  

ptpFlexModemMHSRobustness OBJECT-TYPE 
       SYNTAX       INTEGER { on (7), off (3)}
       MAX-ACCESS   read-write
       STATUS       current
       DESCRIPTION
           "              
             When value is set to on, a more efficient application of MAC Header S
             uppression feature is utilized in traffic cases with unstable Radio Link 
             (due to fading, interference etc).

              Value Range: {on | off}
              Default value: on
	          All other values are not used. 
	   "
       DEFVAL {on}    
       ::= { ptpFlexModemMHSEntry 4}  

ptpFlexModemMHSAutoResetTimer OBJECT-TYPE 
       SYNTAX       INTEGER (0..4095)
       MAX-ACCESS   read-write
       STATUS       current
       DESCRIPTION
           " 
                CAM Auto Reset Timeout of the MAC header suppressor for modem 
                The value is counted in seconds
	            Value range    0..4095 sec
	            All other values are not used.
	            Default value = 0, i.e. no CAM auto-reset.
	   "
       DEFVAL {0}    
       ::= { ptpFlexModemMHSEntry 5} 

--==========================================================
  modemClockSourceTable OBJECT-TYPE
      SYNTAX       SEQUENCE OF  ModemClockSourceEntry
      MAX-ACCESS   not-accessible
      STATUS       current
      DESCRIPTION  " Table that models clock source configuration per modem slot for the case of Neptune Modem"
      ::= { modemConfig  18 }

  modemClockSourceEntry OBJECT-TYPE
      SYNTAX       ModemClockSourceEntry
      MAX-ACCESS   not-accessible
      STATUS       current
      DESCRIPTION  ""
      INDEX { modemClockSourceIndex }
      ::= { modemClockSourceTable 1 }

  ModemClockSourceEntry::= SEQUENCE {
      modemClockSourceIndex     INTEGER,
      modemClockSource          INTEGER
  }

  modemClockSourceIndex   OBJECT-TYPE
      SYNTAX              INTEGER(1)
      MAX-ACCESS          not-accessible
      STATUS              current
      DESCRIPTION
         " The index is 1 for all modems "
      ::= { modemClockSourceEntry 1 }

  modemClockSource OBJECT-TYPE
      SYNTAX       INTEGER { air (0),
                             external(1)
                           }
      MAX-ACCESS   read-write
      STATUS       current
      DESCRIPTION
          " External means in practice that the modem gets the system clock source.
            Air means that the air-received clock is used by the modem.
	        Default value air(0)."
      DEFVAL { air }
      ::= { modemClockSourceEntry 2 }

--==========================================================                                      
-- SUPPORTED MODEM CAPABILITIES TABLE
--==========================================================
  modemSuppCapabilitiesTable OBJECT-TYPE
      SYNTAX       SEQUENCE OF  ModemSuppCapabilitiesEntry
      MAX-ACCESS   not-accessible
      STATUS       current
      DESCRIPTION  " Table that models supported Modem Capabilities combinations
                     for the modem types that can be used in the system."
      ::= { modemConfig  19 }

  modemSuppCapabilitiesEntry OBJECT-TYPE
      SYNTAX       ModemSuppCapabilitiesEntry
      MAX-ACCESS   not-accessible
      STATUS       current
      DESCRIPTION  ""
      INDEX { modemSuppCapabilitiesIndex }
      ::= { modemSuppCapabilitiesTable 1 }

  ModemSuppCapabilitiesEntry::= SEQUENCE {
      modemSuppCapabilitiesIndex       Unsigned32,
      modemSuppCapModemType            INTEGER,
      modemSuppCapBitMap               BITS,
      modemSuppCapChannelBW            PtpModemChannelBWType,
      modemSuppCapPHYProfile           PtpPHYProfileType, 
      modemSuppCapPHYprofileVersion    SnmpAdminString,
      modemSuppPhymodeBitMap           BITS,
      modemSuppTDDTxRatioBitMap        BITS
  }

  modemSuppCapabilitiesIndex   OBJECT-TYPE
      SYNTAX              Unsigned32
      MAX-ACCESS          not-accessible
      STATUS              current
      DESCRIPTION
         " A sequential index of supported Modem Capabilities combination, 
           presented by the ModemSuppCapabilitiesEntry. "
      ::= { modemSuppCapabilitiesEntry 1 }

  modemSuppCapModemType   OBJECT-TYPE
      SYNTAX              INTEGER{   
                                  npt(1),
                                  pvg(2)
      }
      MAX-ACCESS          read-only
      STATUS              current
      DESCRIPTION
         " The modem type. "
      ::= { modemSuppCapabilitiesEntry 2 }

  modemSuppCapBitMap  OBJECT-TYPE
      SYNTAX              BITS{   
                                  xpicEnabled       (0),
                                  atpcEnabled       (1),
                                  jumboUnfragmented (2)
      }
      MAX-ACCESS          read-only
      STATUS              current
      DESCRIPTION
         " The modem Capabilities combination bitmap. 
           Bit-0 set to 1 means that XPIC is supported and enabled and 0 that XPIC is not supported
           or disabled. 
           Bit-1 equal to 0 implies no ATPC applied (Adaptive mode, Manual and Auto / Manual Power).
           Bit-1 set to 1 means Auto, i.e. ATPC enabled (adaptive mode, Auto / Optimum and Auto / Max Power).  
           Bit-2 set to 1 means that Unfragmented Jumbo handling is supported 
           otherwise Fragmented Jumbo handling is supported. "
           
      ::= { modemSuppCapabilitiesEntry 3 }

  modemSuppCapChannelBW   OBJECT-TYPE
      SYNTAX              PtpModemChannelBWType
      MAX-ACCESS          read-only
      STATUS              current
      DESCRIPTION
         " The modem supported Channel Bandwidth value for this Modem Capabilities combination."
      ::= { modemSuppCapabilitiesEntry 4 }


  modemSuppCapPHYProfile   OBJECT-TYPE
      SYNTAX              PtpPHYProfileType
      MAX-ACCESS          read-only
      STATUS              current
      DESCRIPTION
         " The modem supported PHY Profile value for this Modem Capabilities combination."
      ::= { modemSuppCapabilitiesEntry 5 }

  modemSuppCapPHYprofileVersion       OBJECT-TYPE
      SYNTAX       SnmpAdminString
      MAX-ACCESS   read-only
      STATUS       current
      DESCRIPTION
          "Modem profile version.
          "
      ::= { modemSuppCapabilitiesEntry 6 }

  modemSuppPhymodeBitMap   OBJECT-TYPE
      SYNTAX              BITS {   
                                  phymodeId1  (0),
                                  phymodeId2  (1),
                                  phymodeId3  (2),
                                  phymodeId4  (3),
                                  phymodeId5  (4),
                                  phymodeId6  (5),
                                  phymodeId7  (6),
                                  phymodeId8  (7),
                                  phymodeId9  (8),
                                  phymodeId10  (9),
                                  phymodeId11  (10),
                                  phymodeId12  (11),
                                  phymodeId13  (12),
                                  phymodeId14  (13),
                                  phymodeId15  (14),
                                  phymodeId16  (15)
      }
      MAX-ACCESS          read-only
      STATUS              current
      DESCRIPTION
         " The modem supported PHYmodes for this Modem Capabilities combination. 
         Each bit set to 1, indicates one of the PHYmodes supported from 1 to 16, 
         i.e. bit-0 corresponds to phymodeId = 1, bit-15 to phmodeId = 16, 
         where the phymodeId is the modemSuppCapPhymodIndex of the modemSuppCapPhymodCapacityTable.
         For invalid modemSuppCapabilites Entries, the modemSuppPhymodeBitMap is 0."
      ::= { modemSuppCapabilitiesEntry 7 }

  modemSuppTDDTxRatioBitMap   OBJECT-TYPE
      SYNTAX BITS {
                    one2one (1),
                    two2one (2),
                    three2one (3),
                    five2one (4),
                    seven2one (5),
                    eleven2one (6),
                    one2two (7),
                    one2three (8),
                    one2five (9),
                    one2seven (10),
                    one2eleven (11)
      }
      MAX-ACCESS          read-only
      STATUS              current
      DESCRIPTION
         " The modem supported TDD Tx Ratios for this Modem Capabilities combination.
         Each bit set to 1, indicates one of the TDD Tx Ratios supported.
         Not supported TDD Tx Ratios have their corresponding bit set to 0."
      ::= { modemSuppCapabilitiesEntry 8 }

   --=========================================================
   -- SUPPORTED MODEM PHY MODULATION CAPACITIES TABLE
   --=========================================================
   
   modemSuppCapPhymodCapacityTable OBJECT-TYPE
      SYNTAX       SEQUENCE OF   ModemSuppCapPhymodCapacityEntry
      MAX-ACCESS   not-accessible
      STATUS       current
      DESCRIPTION  " 
                    This table models the modem supported phymod capacities per supported
                    modem phymode, i.e Modulation and FEC Rate types combinations and
                    supported Modem Capabilities combination.
                   "    
      ::= { modemConfig  20 }

   modemSuppCapPhymodCapacityEntry OBJECT-TYPE 
      SYNTAX       ModemSuppCapPhymodCapacityEntry
      MAX-ACCESS   not-accessible
      STATUS       current
      DESCRIPTION  " "
      INDEX  {modemSuppCapabilitiesIndex, modemSuppCapPhymodIndex} 
      ::={modemSuppCapPhymodCapacityTable 1 }

    ModemSuppCapPhymodCapacityEntry ::= SEQUENCE {
        modemSuppCapPhymodIndex               Unsigned32,
        modemSuppCapPhymodName                SnmpAdminString,      
        modemSuppCapPhymodAirCapacity         Unsigned32,
        modemSuppCapPhymodCfgId               Unsigned32          
    }   

    modemSuppCapPhymodIndex   OBJECT-TYPE
        SYNTAX              Unsigned32 (1..16)
        MAX-ACCESS          not-accessible
        STATUS              current
        DESCRIPTION
           " Modem PHYmode Index 1 to 16, i.e. the supported PHYmodes of the specific Modem Capabilities combination
            indicated by modemSuppCapabilitiesIndex. Valid modemSuppCapPhymodIndex values are indicated in the bits
            set to 1 of the modemSuppPhymodeBitMap. The Indexing from 1 to 16 corrresponds to indexing of phymodes 
            from lower air capacity to higher air capacity."
        ::= { modemSuppCapPhymodCapacityEntry 1 }


    modemSuppCapPhymodName   OBJECT-TYPE
        SYNTAX              SnmpAdminString
        MAX-ACCESS          read-only
        STATUS              current
        DESCRIPTION
           " Modem Phymode (Modulation plus FEC type)Name that can be used as phymode identifier."
        ::= { modemSuppCapPhymodCapacityEntry 2 }


    modemSuppCapPhymodAirCapacity         OBJECT-TYPE
        SYNTAX       Unsigned32
        UNITS        "Kbits/sec"
        MAX-ACCESS   read-only
        STATUS       current
        DESCRIPTION
            "Maximum air capacity for this phymode (modulation and fec combination) in Kbits/sec.
            "
        ::= { modemSuppCapPhymodCapacityEntry 3 }

    modemSuppCapPhymodCfgId   OBJECT-TYPE
        SYNTAX              Unsigned32 (1..16)
        MAX-ACCESS          read-only
        STATUS              current
        DESCRIPTION
           "The configuration Phymode Id that is used to configure this phymode."
        ::= { modemSuppCapPhymodCapacityEntry 4 }

      
   --=========================================================                                      
   -- REMOTE MODEM IP ADDRESSING TABLE
   --=========================================================
   
   modemRemoteAddressTable OBJECT-TYPE
      SYNTAX       SEQUENCE OF   ModemRemoteAddressEntry
      MAX-ACCESS   not-accessible
      STATUS       current
      DESCRIPTION  " 
                    This table models the IP addresses information of the addresses
                    allocated to the system with the remote peer modem.
                   "    
      ::= { modemConfig  21 }

   modemRemoteAddressEntry OBJECT-TYPE 
      SYNTAX       ModemRemoteAddressEntry
      MAX-ACCESS   not-accessible
      STATUS       current
      DESCRIPTION  " "
      INDEX  {modemRemoteStatusEntryIndex, modemRemoteAddressAddrType, modemRemoteAddressAddr} 
      ::={modemRemoteAddressTable 1 }

    ModemRemoteAddressEntry ::= SEQUENCE {
        modemRemoteAddressAddrType          InetAddressType,
        modemRemoteAddressAddr              InetAddress,      
        modemRemoteAddressRowStatus         RowStatus        
    }   

   
    modemRemoteAddressAddrType         	        OBJECT-TYPE
        SYNTAX                	                InetAddressType
        MAX-ACCESS            	                not-accessible
        STATUS                	                current
        DESCRIPTION "The type of the IP Address of the Remote Modem of this entry. ipv4 (1), ipv6 (2)."
        ::= { modemRemoteAddressEntry 1 }
    
    modemRemoteAddressAddr                          OBJECT-TYPE
        SYNTAX                		            InetAddress                        
        MAX-ACCESS            		            not-accessible
        STATUS                		            current
        DESCRIPTION "The IP address of this remote modem of this entry. The type of
                     this address is determined by the value of the modemRemoteAddressAddrType."
        ::= { modemRemoteAddressEntry 2 }

    modemRemoteAddressRowStatus    OBJECT-TYPE
        SYNTAX                     RowStatus
        MAX-ACCESS                 read-only
        STATUS                     current
        DESCRIPTION  
        " It is the rowStatus of the modemRemoteAddressTable. 
        "
        ::= { modemRemoteAddressEntry 3 }

   --=========================================================                                      
   -- INTRALINK ODU MIB CONTROL OBJECTS
   --=========================================================


  --=========================================================                                      
   -- ODU CONFIGURATION TABLE
   --=========================================================
   oduConfig OBJECT IDENTIFIER ::= {    modemConfigMibObjects 2 }

   oduConfigTable OBJECT-TYPE
      SYNTAX       SEQUENCE OF   OduConfigEntry
      MAX-ACCESS   not-accessible
      STATUS       current
      DESCRIPTION  " 
                     This table models the ODU Configuration general parameters 
                   "    
      ::= { oduConfig  1 }

   oduConfigEntry OBJECT-TYPE 
      SYNTAX       OduConfigEntry
      MAX-ACCESS   not-accessible
      STATUS       current
      DESCRIPTION  " "
      INDEX  {oduConfigEntryIndex} 
      ::={oduConfigTable 1 }

    OduConfigEntry ::= SEQUENCE {                   
      
        oduConfigEntryIndex   INTEGER,
        oduBandSelection      PtpModemChannelBWType,
        oduSetTxFrequency     INTEGER,
        oduSetTxPower INTEGER,
        oduMute PtpOperationState,
        oduLoop PtpOperationState,
        oduRestart PtpRestartMode,
        oduConfigDownLoadValues INTEGER,
        oduConfigPower PtpOnOffOper,
        oduAutoUpdate  INTEGER,
        oduUpdateNow   INTEGER,
        oduTestType     INTEGER,
        oduTestTimeout  Integer32,
        oduTestTimer    Integer32,
        oduCfgDuplexSpacing INTEGER,
        oduCfgAntennaAlignMode INTEGER
   }   
   
   oduConfigEntryIndex   OBJECT-TYPE 
      SYNTAX       INTEGER (1)
      MAX-ACCESS   not-accessible
      STATUS       current
      DESCRIPTION  "
                    Index of the OduConfigEntry. 
                    It is restricted to 1 instance.
                   "
      ::= { oduConfigEntry 1 }

   oduBandSelection OBJECT-TYPE 
      SYNTAX       PtpModemChannelBWType
      MAX-ACCESS   read-write
      STATUS       current
      DESCRIPTION  " 
                     PTP ODU bandwidth selection 
                       Value Range for non-V/E-BAND systems:
                           ptp7MhzBand(0) - default value 
                           ptp14MhzBand(1),   
                           ptp28MhzBand(2),   
                           ptp56MhzBand(3),
                           ptp40MhzBand(4),
                           ptp20MhzBand(5),
                           ptp14MhzNarrowBand(6),
                           ptp10MhzBand(9),
                           ptp30MhzBand(10),
                           ptp50MhzBand(11),
                           ptp112MhzBand(12)
                       Value Range (and default value) for V-BAND systems:
                           ptp250MhzBand(7),
					             Value Range E-BAND systems:
					                 ptp250MhzBand(7), - default value
						               ptp500MhzBand(8)
                       Values for E-BAND-GX systems:    
                           ptp750MhzBand (13),
                           ptp1000MhzBand (14),
                           ptp1500MhzBand (15)
                       Value for OmniBAS-BX systems
                           ptp100MhzBand (16)
                   " 
      DEFVAL { 0 }
      ::= { oduConfigEntry 2 }   
      
   oduSetTxFrequency OBJECT-TYPE 
      SYNTAX       INTEGER
      MAX-ACCESS   read-write
      STATUS       current
      DESCRIPTION  "  
                    Odu Set Tx Frequency
					non V/E-BAND systems: in KHz
					V/E-BAND systems: in MHz
                   " 
      DEFVAL {0}
      ::= { oduConfigEntry 3 } 

    oduSetTxPower OBJECT-TYPE 
      SYNTAX       INTEGER(-32767..32767)
      MAX-ACCESS   read-write
      STATUS       current
      DESCRIPTION  " 
                      ODU set Tx Power.
                      The value is calculated 
                      in 0.5dbm for products with
                      type PTP_R and
                      in 0.1dBm step for the 
                      rest products

                   "
      ::= { oduConfigEntry 4 }     

    oduMute OBJECT-TYPE 
      SYNTAX       PtpOperationState
      MAX-ACCESS   read-write
      STATUS       current
      DESCRIPTION  "  
                      ODU Mute enable/disable action  
                      Value Range  operationStateOFF(0),
                                   operationStateON(1)
                   " 
      DEFVAL {operationStateON}
      ::= { oduConfigEntry 5 }  
      
    oduLoop OBJECT-TYPE 
      SYNTAX       PtpOperationState
      MAX-ACCESS   read-write
      STATUS       current
      DESCRIPTION  " 
                     ODU Loop enable/disable action 
                      Value Range  operationStateOFF(0),
                                   operationStateON(1)

                      This OID is not used in case of 
                      ODU RFU
                   " 
      DEFVAL {operationStateOFF}

      ::= { oduConfigEntry 6 }     
   
   oduRestart OBJECT-TYPE 
      SYNTAX       PtpRestartMode
      MAX-ACCESS   read-write
      STATUS       current
      DESCRIPTION  " 
                     Action Restart ODU
                     Value Range none(0),   
                                 restart(1) 
                   " 
      DEFVAL {none}
      ::= { oduConfigEntry 7 }     
      
   oduConfigDownLoadValues OBJECT-TYPE 
       SYNTAX       INTEGER {notDownloadValue(1),
                             downloadValue(2)}
       MAX-ACCESS   read-write
       STATUS       current
       DESCRIPTION
           "     
                When set to value 2, the manager 
                 downloads the stored values of the 
                 OIDs oduBandSelection, oduSetTxFrequency,
                         oduSetTxPower.
           "
       ::= { oduConfigEntry 8 }  

    oduConfigPower OBJECT-TYPE 
      SYNTAX       PtpOnOffOper
      MAX-ACCESS   read-write
      STATUS       current
      DESCRIPTION  " 
                     ODU Power ON/OFF action 
                     Value Range off(0),     
                                 on(1)
                   " 
      DEFVAL {off}

      ::= { oduConfigEntry 9 }  

    oduAutoUpdate OBJECT-TYPE 
        SYNTAX       INTEGER {oduManual(0),
                              oduAuto(1)}
       MAX-ACCESS   read-write
       STATUS       current
       DESCRIPTION
           " 
             ODU Update Mode.
             values:
             0: manual
             1: auto
             Default value: manual

             PTP_FODU:
             Default value (and only accepted value): auto
           "
       DEFVAL {oduManual}
      ::= { oduConfigEntry 10 }  

    oduUpdateNow OBJECT-TYPE 
        SYNTAX       INTEGER {oduNone(0),
                              oduNow(1)}
       MAX-ACCESS   read-write
       STATUS       current
       DESCRIPTION
           "  
              ODU force Update.
           "
        DEFVAL {oduNone}
      ::= { oduConfigEntry 11 }

   oduTestType OBJECT-TYPE
   SYNTAX       INTEGER {noTest(0),
                         loopBackONTest(1),
                         dCPowerOFFTest(2),
                         muteONTest(3)}
       MAX-ACCESS   read-write
       STATUS       current
       DESCRIPTION
           " The ODU Test Type that is ordered to be performed.
             Valid for system OmniBAS-4W, OmniBAS-2W, OmniBAS-4W-HE, OmniBAS-2W-16E1 and PTP_FODU
             Applies to products: All Omnibas products except XR. No loopback for split-REMEC.

             Values:
             0: noTest
             1: loopBackONTest
             2: dCPowerOFFTest
             3: muteONTest
             - muteONTest(3) test has not been available


             PTP_FODU:
             Only loopBackONTest is available
           "
       DEFVAL { noTest }

       ::= { oduConfigEntry 12 } 

   oduTestTimeout  OBJECT-TYPE
     SYNTAX   Integer32 (0..1440)
     MAX-ACCESS read-write
     STATUS  current  
     DESCRIPTION "ODU test timeout, in minutes. 0 means not active time supervision of ODU test.
                Loopback-on, DCPower-off or Mute-on tests are supervised, having this timeout."
   DEFVAL {0}
   ::= { oduConfigEntry 13 }

   oduTestTimer OBJECT-TYPE
     SYNTAX   Integer32 (0..1440)
     MAX-ACCESS read-only
     STATUS  current
        DESCRIPTION  "ODU Mute-ON current Timer value, in minutes. ."
    ::= { oduConfigEntry 14}

   oduCfgDuplexSpacing OBJECT-TYPE
      SYNTAX              INTEGER { noConfig(0),
                                    factory(1010000),
                                    customized(1008000)}
      MAX-ACCESS          read-write
      STATUS              current
      DESCRIPTION
         "The ODU Duplex Spacing capability is used internally in the system to estimate the 
         Rx_Frequency. The unit is KHz. This object is set equal to the provisioned value of 
         Duplex Spacing while if no provisioning is performed then is equal to 0 indicating 
         that the factory setup is valid. Configuration is valid only for ODU Radio Band of 
         18 GHz. The factory setup for this Band is 1010000 KHz. If oduCfgDuplexSpacing is 
         noConfig (0) then the Agent will not download this object to the system."
      DEFVAL {noConfig}
   ::= { oduConfigEntry 15 } 

   oduCfgAntennaAlignMode OBJECT-TYPE
      SYNTAX              INTEGER { disable(1),
                                    enable (2),
                                    auto (3)}
      MAX-ACCESS          read-write
      STATUS              current
      DESCRIPTION
         "Operation Mode for Antenna Alignment."
      DEFVAL { auto }
      ::= { oduConfigEntry 16 }
   
  --=========================================================                                      
   -- ODU CAPABILITIES TABLE
   --=========================================================

   oduCapabilitiesTable OBJECT-TYPE
      SYNTAX       SEQUENCE OF   OduCapabilitiesEntry
      MAX-ACCESS   not-accessible
      STATUS       current
      DESCRIPTION  " 
                     This table models the ODU Capabilities information
                   "    
      ::= { oduConfig  2 }

   oduCapabilitiesEntry OBJECT-TYPE 
      SYNTAX       OduCapabilitiesEntry
      MAX-ACCESS   not-accessible
      STATUS       current
      DESCRIPTION  " "
      INDEX  {oduCapabilitiesEntryIndex} 
      ::={oduCapabilitiesTable 1 }

    OduCapabilitiesEntry ::= SEQUENCE {                   
      
        oduCapabilitiesEntryIndex  INTEGER,
        oduBand         PtpReferenceLevel,
        oduSpectrumInversion     PtpOperationState,
        oduLoopBackSI PtpOperationState,
        oduFirstFreq Unsigned32,
        oduLastFreq Unsigned32,
        oduFreqStep Unsigned32,
        oduMaxTxPower INTEGER,
        oduMinTxPower INTEGER,
        oduDuplexSpacing Integer32
   }   
   
   oduCapabilitiesEntryIndex   OBJECT-TYPE 
      SYNTAX       INTEGER (1)
      MAX-ACCESS   not-accessible
      STATUS       current
      DESCRIPTION  "
                     Index of the OduCapabilitiesEntry. 
                     It is restricted to 1 instance.
                   "
      ::= { oduCapabilitiesEntry 1 }

   oduBand OBJECT-TYPE 
      SYNTAX       PtpReferenceLevel
      MAX-ACCESS   read-only
      STATUS       current
      DESCRIPTION  " 
                     Odu Band
                     Value Range levelHigh(0),  
                                 levelLow(1)
                   "
      ::= { oduCapabilitiesEntry 2 }   
      
   oduSpectrumInversion OBJECT-TYPE 
      SYNTAX       PtpOperationState
      MAX-ACCESS   read-only
      STATUS       current
      DESCRIPTION  "  
                      Odu Spectrum Inversion
                      Value Range  operationStateOFF(0),
                                   operationStateON(1)

                      In case of ODU RFU, this OID 
                      represents TX SI

                    "
      ::= { oduCapabilitiesEntry 3 } 

    oduLoopBackSI OBJECT-TYPE 
      SYNTAX       PtpOperationState
      MAX-ACCESS   read-only
      STATUS       current
      DESCRIPTION  "  
                      ODU loop back SI.
                      Value Range  operationStateOFF(0),
                                   operationStateON(1)


                     This OID is not used in case of RFU ODU

                     "
      ::= { oduCapabilitiesEntry 4 }     

    oduFirstFreq OBJECT-TYPE 
      SYNTAX       Unsigned32
      MAX-ACCESS   read-only
      STATUS       current
      DESCRIPTION  " 
                     ODU  first Frequency.
                     non V/E-BAND systems: 
					 The value is calculated     
                     in 1KHz step
					 V/E-BAND systems: 
					 The value is calculated     
                     in 1MHz step
                   "
      ::= { oduCapabilitiesEntry 5 }  
      
    oduLastFreq OBJECT-TYPE 
      SYNTAX       Unsigned32
      MAX-ACCESS   read-only
      STATUS       current
      DESCRIPTION  " 
                     ODU  last Frequency.
                     non V/E-BAND systems: 
					 The value is calculated     
                     in 1KHz step
					 V/E-BAND systems: 
					 The value is calculated     
                     in 1MHz step
                   "
      ::= { oduCapabilitiesEntry 6 }     
   
   oduFreqStep OBJECT-TYPE 
      SYNTAX       Unsigned32
      MAX-ACCESS   read-only
      STATUS       current
      DESCRIPTION  " 
                     ODU  Frequency Step.
                     non V/E-BAND systems: 
					 The value is calculated     
                     in 1KHz step
					 V/E-BAND systems: 
					 The value is calculated     
                     in 1MHz step
                   "
      ::= { oduCapabilitiesEntry 7 } 
      
   oduMaxTxPower OBJECT-TYPE 
      SYNTAX       INTEGER(-32767..32767)
      MAX-ACCESS   read-only
      STATUS       current
      DESCRIPTION  " 
                     ODU  maximum Tx Power.
                     The value is calculated  
                     in 0.1dBm step
                   "
      ::= { oduCapabilitiesEntry 8 } 

   oduMinTxPower OBJECT-TYPE 
       SYNTAX       INTEGER(-32767..32767)
      MAX-ACCESS   read-only
      STATUS       current
      DESCRIPTION  " 
                     ODU  minimum Tx Power
                     The value is calculated  
                     in 0.1dBm step
                   "
      ::= { oduCapabilitiesEntry 9 } 

   oduDuplexSpacing OBJECT-TYPE
      SYNTAX       Integer32
      MAX-ACCESS   read-only
      STATUS       current
      DESCRIPTION  
         "The ODU Duplex Spacing capability is used internally in 
         the system to estimate the Rx_Frequency. 
		 non V/E-BAND systems: The unit is KHz. 
		 V/E-BAND systems: The unit is MHz. 
         This object is equal to the Actual Duplex Spacing, either
         at factory setup or manually configured (ONLY in the case of
         18 GHz RFU Radio Band by means of the oduCfgDuplexSpacing object.
         Configuration is valid ONLY for OmniBAS-XR. For the other card
         types its oduCfgDuplexSpacing object value should be 0)."
      ::= { oduCapabilitiesEntry 10 } 

  --=========================================================                                      
   -- ODU STATUS TABLE
   --=========================================================
   oduStatusTable OBJECT-TYPE
      SYNTAX       SEQUENCE OF   OduStatusEntry
      MAX-ACCESS   not-accessible
      STATUS       current
      DESCRIPTION  " 
                     This table models the ODU Status information
                   "    
      ::= { oduConfig  3 }

   oduStatusEntry OBJECT-TYPE 
      SYNTAX       OduStatusEntry
      MAX-ACCESS   not-accessible
      STATUS       current
      DESCRIPTION  " "
      INDEX  {oduStatusEntryIndex} 
      ::={oduStatusTable 1 }

    OduStatusEntry ::= SEQUENCE {                   
      
        oduStatusEntryIndex  INTEGER,
        oduOperStatus        PtpErrorStatus,
        oduCurrentTxFrequency     Unsigned32,
        oduCurrentTxPower INTEGER,
        oduRadioAlarms INTEGER,
        oduThresAlarms INTEGER,
        oduPower PtpOnOffOper,
        oduCurrentRxFrequency  Unsigned32,
        oduStatusMute PtpOperationState,
        oduUpdateStatus INTEGER,
        oduGenConfigAlarm INTEGER,
        oduStatusAntennaAlignMode INTEGER,
        oduSlowFadingStatus INTEGER,
        oduFastFadingStatus INTEGER,
        oduCoChannelInterfereDetectStatus INTEGER,
        oduStrongAdjChannelPresenceStatus INTEGER,
        oduStatusBRAL Integer32,
        oduINRStatus Integer32,
        oduInterferenceDegrStatus Integer32,
        oduStatusDuplexerState INTEGER
   }

   oduStatusEntryIndex   OBJECT-TYPE 
      SYNTAX       INTEGER (1)
      MAX-ACCESS   not-accessible
      STATUS       current
      DESCRIPTION  "
                     Index of the OduStatusEntry. 
                     It is restricted to 1 instance.
                   "
      ::= { oduStatusEntry 1 }

   oduOperStatus OBJECT-TYPE 
      SYNTAX       PtpErrorStatus
      MAX-ACCESS   read-only
      STATUS       current
      DESCRIPTION  " 
                     Odu operation status
                     Value Range noErrorStatus(0),                      
                                 errorStatus(1)    
                    "
      ::= { oduStatusEntry 2 }   
      
   oduCurrentTxFrequency OBJECT-TYPE 
      SYNTAX       Unsigned32
      MAX-ACCESS   read-only
      STATUS       current
      DESCRIPTION  "  
                      Odu current Tx Frequency
                      non V/E-BAND systems: 
					  The value is calculated     
                      in 1KHz step
					  V/E-BAND systems: 
					  The value is calculated     
                      in 1MHz step
                    "
      ::= { oduStatusEntry 3 } 

    oduCurrentTxPower OBJECT-TYPE 
      SYNTAX       INTEGER(-32767..32767)
      MAX-ACCESS   read-only
      STATUS       current
      DESCRIPTION  "  
                      ODU current Tx Power.
                      The value is calculated 
                      in 0.1dBm step
                    "
      ::= { oduStatusEntry 4 }     

    oduRadioAlarms OBJECT-TYPE 
      SYNTAX       INTEGER
      MAX-ACCESS   read-only
      STATUS       current
      DESCRIPTION  " 
        Odu Radio Alarms.
        The information is bitfield.
        The bit value meaning is shown below:
            bit0: Pin(RSSI) Detection input radio power alarm from remote radio
                  Unit ( RSSI)
                - 0: RSSI ceased 
                - 1: RSSI raised
            bit1: Pout (ALC) AGC Loop Control Set by ODU if the Tx AGC loop is
                  unable to stabilize Tx output power within the desired limits
                - 0: ALC ceased   
                - 1: ALC raised
            bit2: Lock Detection in receiver's PLL
                - 0: Locked           
                - 1: Unlocked     
            bit3: Lock Detection in transmiter's PLL
                - 0: Locked    
                - 1: Unlocked         
            bit4: Frequency Out of range Errors Alarm
                - 0: Frequency in range  
                - 1: Frequency Out of range
            bit5: Lock Detection in microwave
                - 0: LD_MW ceased
                - 1: LD_MW raised
            bit6: Lock Detection in Loop Back
                - 0: LD_LB ceased
                - 1: LD_LB raised
            ***  bit6 is not used in case of 
                 RFU ODU
            bit7: Power Out of range Errors Alarm
                - 0: Power in range  
                - 1: Power Out of range
            bit8: Radio initialization failure Alarm
                -0: Radio initialization OK
                -1: Radio initialization failure
            bit9..bit31: not used
        "
      ::= { oduStatusEntry 5 }  
    
    oduThresAlarms OBJECT-TYPE 
      SYNTAX       INTEGER
      MAX-ACCESS   read-only
      STATUS       current
      DESCRIPTION  " 
        Odu Threshold Alarms.
        The information is bitfield.
        The bit value meaning is affected by  OID oduModelType
        only for bit which this is clearly stated in the following description.
        The bit value meaning is shown below:
            bit0: This bit denotes different information depending on OID
                  oduModelType, as shown below:
                  - When OID oduModelType(b7-b6) is Intralink ODU Bit0 is not USED
                  - When OID oduModelType(b7-b6) is FLEX ODU or SODU Bit0 indicates Power
                    supply threshold alarm for -48V.
                  Alarm set if the relevant voltage falls below the ODU DC
                  defined thresholds. Status sent to IDU:
                  - 0:  Alarm ceased 
                  - 1:  Alarm raised
            ***  bit0 is not used in case of RFU ODU
            bit1: Power supply threshold alarm for +6.5V.
                  Alarm set if the relevant voltage falls below the ODU DC
                  defined thresholds. Status sent to IDU:
                  - 0: Alarm ceased
                  - 1: Alarm raised
             ***  bit1 is not used in case of RFU ODU
            bit2: High Temperature threshold alarm.
                  Alarm set if ODU measured temperature is above user defined
                  high temperature limit (max temp). Status sent to IDU:
                  - 0: Alarm ceased
                  - 1: Alarm raised
            bit3: This bit denotes different information depending on OID
                  oduModelType, as shown below:
                  - When OID oduModelType(b7-b6) is Intralink ODU Bit3 indicates
                    Power supply threshold alarm for -12V
                  - When OID oduModelType(b7-b6) is FLEX ODU or SODU Bit3 indicates Power
                    supply threshold alarm for -5V.
                    Alarm set if the relevant voltage falls below the ODU DC
                    defined thresholds. Status sent to IDU:
                    - 0: Alarm ceased   
                    - 1: Alarm raised     
             ***  bit3 is not used in case of RFU ODU   
            bit4: This bit denotes different information depending on OID
                  oduModelType, as shown below:
                  - When OID oduModelType(b7-b6) is Intralink ODU Bit4 indicates
                    Power supply threshold alarm for +12V 
                  - When OID oduModelType(b7-b6) is FLEX ODU or SODU and
                    -- oduModelType(b5-b0) is 0x07 or 0x08 
                        Bit4 indicates Power supply V_PA threshold alarm for +12V
                    -- oduModelType(b5-b0) is 0x0D or 0x0F or 0x26
                        Bit4 indicates Power supply V_PA threshold alarm for +9.5V
                    -- oduModelType(b5-b0) is 0x12 or 0x17 or 0x1A
                        Bit4 indicates Power supply V_PA threshold alarm for +7.6V 
                  Alarm set if the relevant voltage falls below the ODU DC
                  defined thresholds. Status sent to IDU:
                  - 0: Alarm ceased
                  - 1: Alarm raised
            ***  bit4 is not used in case of RFU ODU
            bit5: Power supply threshold  alarm for +5V
                  Alarm set if the relevant voltage falls below the ODU DC
                  defined thresholds. Status sent to IDU:
                  - 0: Alarm ceased
                  - 1: Alarm raised
             ***  bit5 is not used in case of RFU ODU
            bit6: Input power from the remote Radio Unit.
                  Alarm set if  Pin Rx ODU less than a user defined threshold. 
                  Status sent to IDU:
                  - 0: Input radio power not detected
                  - 1: Input radio power detected
            bit7: Detection of Minimum ODU input power as sensed by Tx cable
                  detector (Pif)
                  - 0: Pif detection OFF
                  - 1: Pif detection ON
             ***  bit7 is not used in case of RFU ODU
            bit8..bit31: not used
        "
      ::= { oduStatusEntry 6 }
      
    oduPower OBJECT-TYPE 
      SYNTAX       PtpOnOffOper
      MAX-ACCESS   read-only
      STATUS       current
      DESCRIPTION  " 
                     ODU Power ON/OFF operation status 
                     Value Range off(0),   
                                 on(1)
                   "

      ::= { oduStatusEntry 7 }     

   oduCurrentRxFrequency OBJECT-TYPE 
      SYNTAX       Unsigned32
      MAX-ACCESS   read-only
      STATUS       current
      DESCRIPTION  "  
                      Odu current Rx Frequency
                      non V/E-BAND systems: 
					  The value is calculated     
                      in 1KHz step
					  V/E-BAND systems: 
					  The value is calculated     
                      in 1MHz step
                   "
      ::= { oduStatusEntry 8 } 

    oduStatusMute OBJECT-TYPE 
      SYNTAX       PtpOperationState
      MAX-ACCESS   read-only
      STATUS       current
      DESCRIPTION  "  
                      ODU Mute enable/disable operation state 
                      Value Range  operationStateOFF(0),
                                   operationStateON(1)
                                   
                   " 
      ::= { oduStatusEntry 9 }
      
    oduUpdateStatus OBJECT-TYPE 
        SYNTAX       INTEGER {oduStatUpdated(0),
                              oduStatNeedUpdate(1),
                              oduStatUpdateNow(2),
                              oduStatUpdateFail(3)}
       MAX-ACCESS   read-only
       STATUS       current
       DESCRIPTION
           "  
             ODU Update Status
           "
      ::= { oduStatusEntry 10 }  

    oduGenConfigAlarm OBJECT-TYPE 
      SYNTAX       INTEGER
      MAX-ACCESS   read-only
      STATUS       current
      DESCRIPTION  "
        Odu General configuration Alarms.
        The information is bitfield.
        The bit value meaning is shown below:
            bit0: Odu invalid Model Type
                  The Alarm is raised, when the inserted ODU in the system, 
                  has an invalid (unsupported) Model Type.
                  - 0: The inserted ODU has valid Model Type (Alarm ceased)
                  - 1: The inserted ODU has invalid Model Type (Alarm raised)
            bit1: Odu bandwidth configuration mismatch                                                                       
                  The Alarm is raised, when the Odu bandwidth value stored in
                  the configuration, does not collocate with the installed
                  ODU hardware.                                                          
                  - 0: Alarm ceased
                  - 1: Alarm raised
            ***  bit1 is not used in case of RFU ODU
            bit2: Calibration Alarm
            bit3: Pif max Alarm  ***  bit3 is not used in case of RFU ODU
            bit4: Low If Alarm   ***  bit4 is not used in case of RFU ODU
            bit5: Low Temperature Alarm
            bit6: - not used
            bit7: ODU table error  ***  bit7 is not used in case of RFU ODU
            bit8..bit31: - not used
        "
      ::= { oduStatusEntry 11 }   

    oduStatusAntennaAlignMode OBJECT-TYPE
      SYNTAX              INTEGER { disabled(1),
                                    enabled (2)}
      MAX-ACCESS          read-only
      STATUS              current
      DESCRIPTION
          "Actual Operation Mode for Antenna Alignment." 
      ::= { oduStatusEntry 12 }
   
   oduSlowFadingStatus OBJECT-TYPE
      SYNTAX              INTEGER {
                          notAvailable (1),
                          raised (2),
                          ceased (3) 
                          }
      MAX-ACCESS          read-only
      STATUS              current
      DESCRIPTION
          "Slow Fading Detection Status. If true then Slow Fading is detected.
           It is notAvailable when oduAlarmConfLinkQualityAdminState is false." 
      ::= { oduStatusEntry 13 }

   oduFastFadingStatus OBJECT-TYPE
      SYNTAX              INTEGER {
                          notAvailable (1),
                          raised (2),
                          ceased (3) 
                          }
      MAX-ACCESS          read-only
      STATUS              current
      DESCRIPTION
          "Fast Fading Detection Status. If true then Fast Fading is detected.
           It is notAvailable when oduAlarmConfLinkQualityAdminState is false." 
      ::= { oduStatusEntry 14 }

   oduCoChannelInterfereDetectStatus OBJECT-TYPE
      SYNTAX              INTEGER {
                          notAvailable (1),
                          raised (2),
                          ceased (3) 
                          }
      MAX-ACCESS          read-only
      STATUS              current
      DESCRIPTION
          "Cochannel Interference Detection Status. If true then Cochannel Interference is detected.
           It is notAvailable when oduAlarmConfLinkQualityAdminState is false." 
      ::= { oduStatusEntry 15 }

   oduStrongAdjChannelPresenceStatus OBJECT-TYPE
      SYNTAX              INTEGER {
                          notAvailable (1),
                          raised (2),
                          ceased (3) 
                          }
      MAX-ACCESS          read-only
      STATUS              current
      DESCRIPTION
          "Strong Adjacent Channel presence Status. If true then Strong Adjacent Channel is present.
           It is notAvailable when oduAlarmConfLinkQualityAdminState is false." 
      ::= { oduStatusEntry 16 }
   
   oduStatusBRAL OBJECT-TYPE
       SYNTAX      Integer32 
       UNITS       "0.1 dB" 
       MAX-ACCESS  read-only
       STATUS      current
       DESCRIPTION
           "Below Reference Attenuation Level (in tenths of dB)." 
       ::= { oduStatusEntry 17 }

   oduINRStatus OBJECT-TYPE
       SYNTAX      Integer32 
       UNITS       "0.1 dB" 
       MAX-ACCESS  read-only
       STATUS      current
       DESCRIPTION
           "Interference to Noise Ratio (in tenths of dB)." 
       ::= { oduStatusEntry 18 }

   oduInterferenceDegrStatus OBJECT-TYPE
       SYNTAX      Integer32 
       UNITS       "0.1 dB" 
       MAX-ACCESS  read-only
       STATUS      current
       DESCRIPTION
           "Interference Degradation (in tenths of dB)." 
       ::= { oduStatusEntry 19 }

   oduStatusDuplexerState OBJECT-TYPE
       SYNTAX      INTEGER {duplexerNotAvail (1),
                            duplexerError (2),
                            duplexerAdjusting (3),
                            duplexerReady (4)}
       MAX-ACCESS  read-only
       STATUS      current
       DESCRIPTION
           "
             ODU Duplexer Status
           "
      ::= { oduStatusEntry 20 }

  --=========================================================                                      
   -- ODU ANALOGUE MONITOR TABLE
   --=========================================================
   oduAnalogueMonitorTable OBJECT-TYPE
      SYNTAX       SEQUENCE OF   OduAnalogueMonitorEntry
      MAX-ACCESS   not-accessible
      STATUS       current
      DESCRIPTION  " 
                     This table models the ODU Analogue Monitor information
                   "    
      ::= { oduConfig  4 }

   oduAnalogueMonitorEntry OBJECT-TYPE 
      SYNTAX       OduAnalogueMonitorEntry
      MAX-ACCESS   not-accessible
      STATUS       current
      DESCRIPTION  " "
      INDEX  {oduAnalogueMonitorEntryIndex} 
      ::={oduAnalogueMonitorTable 1 }

    OduAnalogueMonitorEntry ::= SEQUENCE {                   
      
        oduAnalogueMonitorEntryIndex  INTEGER,
        oduTemperature        INTEGER,
        oduRSSI     INTEGER,
        oduPif INTEGER,
        oduPoutVdet INTEGER,
        oduMonitorPlus5V INTEGER,
        oduMonitorPlus7V INTEGER,
        oduMonitorMinus5V INTEGER,
        oduMonitorPlus6point5V INTEGER,
        oduMonitorMinus48V INTEGER
   }   
   
   oduAnalogueMonitorEntryIndex   OBJECT-TYPE 
      SYNTAX       INTEGER (1)
      MAX-ACCESS   not-accessible
      STATUS       current
      DESCRIPTION  "
                     Index of the OduAnalogueMonitorEntry. 
                     It is restricted to 1 instance.
                   "
      ::= { oduAnalogueMonitorEntry 1 }

   oduTemperature OBJECT-TYPE 
      SYNTAX       INTEGER(-127..127)
      MAX-ACCESS   read-only
      STATUS       current
      DESCRIPTION  " 
                     Odu temperature
                     Value Range -127..127
                     The value is calculated   
                     in 0.1 step.
                   "
      ::= { oduAnalogueMonitorEntry 2 }   
      
   oduRSSI OBJECT-TYPE 
      SYNTAX       INTEGER(0..65535)
      MAX-ACCESS   read-only
      STATUS       current
      DESCRIPTION  "  
                      Odu input power from the remote Radio Unit (RSSI)
                      The value is calculated     
                      in -0.1dBm step. 
                    "
      ::= { oduAnalogueMonitorEntry 3 } 

    oduPif OBJECT-TYPE 
      SYNTAX       INTEGER(-32767..32767)
      MAX-ACCESS   read-only
      STATUS       current
      DESCRIPTION  "  ODU Radio power in cable before Air (Pif).
                       The value is calculated     
                       in 0.1dBm step. 
                        Value Range -32767..32767
    
                       In case of RFU Odu, OID oduPif is not used .
                       "
      ::= { oduAnalogueMonitorEntry 4 }     

    oduPoutVdet OBJECT-TYPE 
      SYNTAX       INTEGER(-32767..32767)
      MAX-ACCESS   read-only
      STATUS       current
      DESCRIPTION  " 
                   Odu power output volt detector.
                   The value is calculated   
                   in 0.1dBm step.   
                   Value Range -32767..32767

                   In case of RFU Odu, OID oduPoutVdet is not used .
    "
      ::= { oduAnalogueMonitorEntry 5 }  
    
    oduMonitorPlus5V OBJECT-TYPE 
      SYNTAX       INTEGER
      MAX-ACCESS   read-only
      STATUS       current
      DESCRIPTION  " 
             Odu monitor +5 volt.
             The value is calculated   
             in 0.1V step.        
                                                   
               oduMonitorPlus5V  shows +5V.
                                                   
             - When OID oduModelType(b7-b6) is unknown oduMonitorPlus5V is not used.             

             In case of RFU Odu, OID oduMonitorPlus5V is not used .

    "
      ::= { oduAnalogueMonitorEntry 6 }

    oduMonitorPlus7V OBJECT-TYPE 
      SYNTAX       INTEGER
      MAX-ACCESS   read-only
      STATUS       current
      DESCRIPTION  " 
             Odu monitor +7 volt.
             The value is calculated   
             in 0.1V step.   
               
             - This OID shows +12V when               
               the OID oduModelType(b7-b6) is Intralink ODU.
                              
             - When OID oduModelType(b7-b6) is FLEX ODU or SODU 
                          oduMonitorPlus7V shows V_PA with the following volts:                   
                            -- When oduModelType(b5-b0) is 0x07 or 0x08 
                               oduMonitorPlus7V shows V_PA +12V                     
                            -- When oduModelType(b5-b0) is 0x0D or 0x0F or 0x26 
                               oduMonitorPlus7V shows V_PA +9.5V                     
                            -- When oduModelType(b5-b0) is 0x12 or 0x17 or 0x1A  
                                oduMonitorPlus7V shows V_PA +7.6V             
             - When OID oduModelType(b7-b6) is unknown oduMonitorPlus7V is not used.
     
                     In case of RFU Odu, OID oduMonitorPlus7V is not used .

    "
      ::= { oduAnalogueMonitorEntry 7 }

    oduMonitorMinus5V OBJECT-TYPE 
      SYNTAX       INTEGER
      MAX-ACCESS   read-only
      STATUS       current
      DESCRIPTION  " 
             
             The value is calculated   
             in 0.1V step.          
             
             - When OID oduModelType(b7-b6) is Intralink ODU.            
               oduMonitorMinus5V  shows -12V.

             - When OID oduModelType(b7-b6) is FLEX ODU or SODU 
               oduMonitorMinus5V  shows -5V.        

             - When OID oduModelType(b7-b6) is unknown oduMonitorMinus5V is not used.             

         In case of RFU Odu, OID oduMonitorMinus5V is not used .

    "
      ::= { oduAnalogueMonitorEntry 8 }

    oduMonitorPlus6point5V OBJECT-TYPE 
      SYNTAX       INTEGER
      MAX-ACCESS   read-only
      STATUS       current
      DESCRIPTION  " 
             Odu monitor +6.5 volt.
             The value is calculated   
             in 0.1V step.        
             
             - When OID oduModelType(b7-b6) is Intralink ODU.            
               oduMonitorPlus6point5V  shows +6.5.

             - When OID oduModelType(b7-b6) is FLEX ODU or SODU 
               oduMonitorPlus6point5V  shows +6.5V.

             - When OID oduModelType(b7-b6) is unknown oduMonitorPlus6point5V is not used.             

         In case of RFU Odu, OID oduMonitorPlus6point5V is not used .

    "
      ::= { oduAnalogueMonitorEntry 9 }
      
    oduMonitorMinus48V OBJECT-TYPE 
      SYNTAX       INTEGER
      MAX-ACCESS   read-only
      STATUS       current
      DESCRIPTION  " 
             Odu monitor -48 volt.
             In order to obtain the 
             absolute value of the measured 
             voltage, the returned of the 
             OID must be divided by 100.
            
             - When OID oduModelType(b7-b6) is Intralink ODU.            
               oduMonitorMinus48V is not used

             - When OID oduModelType(b7-b6) is FLEX ODU 
               oduMonitorMinus48V  shows -48V.

             - When OID oduModelType(b7-b6) is unknown oduMonitorMinus48V is not used.             

         In case of RFU Odu, OID oduMonitorMinus48V is not used .
    "
      ::= { oduAnalogueMonitorEntry 10 }

  --=========================================================                                      
   -- ODU VERSION TABLE
   --========================================================
   oduVersionTable OBJECT-TYPE
      SYNTAX       SEQUENCE OF   OduVersionEntry
      MAX-ACCESS   not-accessible
      STATUS       current
      DESCRIPTION  " 
                     This table models the ODU Version information
                     This table is not used in case of RFU ODU
                   "    
      ::= { oduConfig  5 }

   oduVersionEntry OBJECT-TYPE 
      SYNTAX       OduVersionEntry
      MAX-ACCESS   not-accessible
      STATUS       current
      DESCRIPTION  " "
      INDEX  {oduVersionEntryIndex} 
      ::={oduVersionTable 1 }

    OduVersionEntry ::= SEQUENCE {                   
        oduVersionEntryIndex       INTEGER,
        oduModelType               OCTET STRING,
        oduSerialNumber            OCTET STRING,
        oduID                      OCTET STRING,
        oduVersion                 OCTET STRING,
        oduSysSWver                OCTET STRING,
        oduProductCode             OCTET STRING,
        oduModelSubType            OCTET STRING,
        oduBootLoaderVersion       INTEGER,
        oduRadioModel              Unsigned32,
        oduStringBootLoaderVersion OCTET STRING
   }   
   
   oduVersionEntryIndex   OBJECT-TYPE 
      SYNTAX       INTEGER (1)
      MAX-ACCESS   not-accessible
      STATUS       current
      DESCRIPTION  "
                    Index of the oduVersionEntry. 
                    It is restricted to 1 instance.
                   "
      ::= { oduVersionEntry 1 }

   oduModelType OBJECT-TYPE 
      SYNTAX       OCTET STRING
      MAX-ACCESS   read-only
      STATUS       current
      DESCRIPTION  " 
                      The format of oduModelType is 
                      two characters which are in range
                      of '0..9' or 'A..F'    
                      
                      The value encoding is shown below:                 
                      Odu Model Type
                         - When oduModelType(b7-b6) is 00b
                           Model Type is FLEX ODU

                         - When oduModelType(b7-b6) is 01b
                           Model Type is  Intralink ODU.           
                           
                         - When oduModelType(b7-b6) is 10b
                           Model Type is  SODU ODU
                         
                         - When OID oduModelType(b7-b6) is 11b
                           and bits b5-b0 are not equal to zero 
                           Model Type is CFs.

                         - When OID oduModelType(b7-b6) is 11b
                           and bits b5-b0 are 000000b
                           Model Type is Unknown ODU.

                   "
      ::= { oduVersionEntry 2 }   
      
   oduSerialNumber OBJECT-TYPE 
      SYNTAX       OCTET STRING (SIZE (0..6))
      MAX-ACCESS   read-only
      STATUS       current
      DESCRIPTION  "  Odu Serial Number
                      N/A for SODU ODUs"
      ::= { oduVersionEntry 3 } 

   oduID OBJECT-TYPE 
      SYNTAX       OCTET STRING (SIZE (0..4))
      MAX-ACCESS   read-only
      STATUS       current
      DESCRIPTION  "  ODU ID 
                      N/A for SODU ODUs"
      ::= { oduVersionEntry 4 }     
    
   oduVersion OBJECT-TYPE 
      SYNTAX       OCTET STRING (SIZE (0..2))
      MAX-ACCESS   read-only
      STATUS       current
      DESCRIPTION  "  ODU software version"
      ::= { oduVersionEntry 5 }     
      
   oduSysSWver OBJECT-TYPE 
      SYNTAX       OCTET STRING (SIZE (0..2))
      MAX-ACCESS   read-only
      STATUS       current
      DESCRIPTION  "  ODU update software version"
      ::= { oduVersionEntry 6 }  
      
  oduProductCode OBJECT-TYPE
      SYNTAX       OCTET STRING (SIZE (0..18))
      MAX-ACCESS   read-only
      STATUS       current
      DESCRIPTION  "  ODU Product Code
                      N/A for SODU ODUs"
      ::= { oduVersionEntry 7 } 

   oduModelSubType OBJECT-TYPE
      SYNTAX       OCTET STRING (SIZE (0..1))
      MAX-ACCESS   read-only
      STATUS       current
      DESCRIPTION
          " The format of oduModelSubType is two characters which are in range
             of '0..9' or 'A..F'

             The value encoding is shown below:
                      Odu Model SubType:
                         - When bit0 is 0: CFe Version-1 with RFU service channel
                         - When bit0 is 1: CFe Version-2
                          
                           bit1-bit7: Not used
          "
      ::= { oduVersionEntry 8 }   

   oduBootLoaderVersion OBJECT-TYPE
      SYNTAX       INTEGER(0..255)
      MAX-ACCESS   read-only
      STATUS       current
      DESCRIPTION  
          "Odu Boot Loader Version Number. Valid for SODU and SF ODUs for all 
          system types except OmniBAS-XR.
          Value 255 means not available ODU."
      ::= { oduVersionEntry 9 }  

  oduRadioModel OBJECT-TYPE 
      SYNTAX       Unsigned32
      MAX-ACCESS   read-only
      STATUS       current
      DESCRIPTION  
          "Radio Model Type. Valid only for PTP_FODU systems."
      ::= { oduVersionEntry 10 }  

   oduStringBootLoaderVersion OBJECT-TYPE
      SYNTAX       OCTET STRING
      MAX-ACCESS   read-only
      STATUS       current
      DESCRIPTION  
          "Odu Boot Loader Version String. Valid for SODU and SF ODUs for all 
          system types except OmniBAS-XR."
      ::= { oduVersionEntry 11 }

  --=========================================================                                      
   -- ODU ALARM CONFIGURATION TABLE
   --========================================================

   oduAlarmConfigurationTable OBJECT-TYPE
      SYNTAX       SEQUENCE OF   OduAlarmConfigurationEntry
      MAX-ACCESS   not-accessible
      STATUS       current
      DESCRIPTION  " 
                     This table models the ODU Alarm Configuration information 
                   "    
      ::= { oduConfig  6 }

   oduAlarmConfigurationEntry OBJECT-TYPE 
      SYNTAX       OduAlarmConfigurationEntry
      MAX-ACCESS   not-accessible
      STATUS       current
      DESCRIPTION  " "
      INDEX  {oduAlarmConfigurationEntryIndex} 
      ::={oduAlarmConfigurationTable 1 }

    OduAlarmConfigurationEntry ::= SEQUENCE {                   
      
        oduAlarmConfigurationEntryIndex  INTEGER,
        oduPinRSSIThres  INTEGER,
        oduTempThres     INTEGER,
        oduAlarmConfDownLoadValues INTEGER,
        oduAlarmConfTempLoThresh INTEGER,
        oduAlarmConfLinkQualityAdminState TruthValue,
        oduAlarmConfSupprState BITS
   }   
   
   oduAlarmConfigurationEntryIndex   OBJECT-TYPE 
      SYNTAX       INTEGER (1)
      MAX-ACCESS   not-accessible
      STATUS       current
      DESCRIPTION  "
                    Index of the OduAlarmConfigurationEntry. 
                    It is restricted to 1 instance.
                   "
      ::= { oduAlarmConfigurationEntry 1 }

   oduPinRSSIThres OBJECT-TYPE 
      SYNTAX       INTEGER(0..255)
      MAX-ACCESS   read-write
      STATUS       current
      DESCRIPTION  " 
                     Odu RSSI Threshold
                     Value range 0..255
                     The value is multiplied
                      with -1dbm 
                     "
      DEFVAL {0}
      ::= { oduAlarmConfigurationEntry 2 }   
      
   oduTempThres OBJECT-TYPE 
      SYNTAX       INTEGER(-128..127)
      MAX-ACCESS   read-write
      STATUS       current
      DESCRIPTION  "  
                     Odu High temperature threshold
                     Value range -128..127
                   "
      DEFVAL {65}
      ::= { oduAlarmConfigurationEntry 3 } 

   oduAlarmConfDownLoadValues OBJECT-TYPE 
       SYNTAX       INTEGER {notDownloadValue(1),
                             downloadValue(2)}
       MAX-ACCESS   read-write
       STATUS       current
       DESCRIPTION
           "     
                When set to value 2, the manager 
                 downloads the stored values of the 
                 OIDs oduPinRSSIThres, oduTempThres.
           "
       ::= { oduAlarmConfigurationEntry 4 }  

   oduAlarmConfTempLoThresh OBJECT-TYPE 
      SYNTAX       INTEGER(-128..127)
      MAX-ACCESS   read-write
      STATUS       current
      DESCRIPTION  "  
                     Odu Low temperature threshold
                     Value range -128..127
                   "
      DEFVAL {0}
      ::= { oduAlarmConfigurationEntry 5 } 

   oduAlarmConfLinkQualityAdminState OBJECT-TYPE 
      SYNTAX       TruthValue
      MAX-ACCESS   read-write
      STATUS       current
      DESCRIPTION  "  
                     When true, the ODU Link Quality Alarms Notifications, oduSlowFadingDetection,
                     oduFastFadingDetection, oduCoChannelInterfereDetection, oduStrongAdjChannelPresence,
                     are enabled to be spawned otherwise no ODU Link Quality Alarm is issued.
                     Similarly when false, the ODU link Quality Alarm Statuses, oduSlowFadingStatus,
                     oduFastFadingStatus, oduCoChannelInterfereDetectStatus, oduStrongAdjChannelPresenceStatus,
                     oduStatusBRAL, are not available.
                   " 
      DEFVAL { false }
      ::= { oduAlarmConfigurationEntry 6 }

   oduAlarmConfSupprState OBJECT-TYPE
       SYNTAX      BITS {
                     sfd(0),
                     ffd(1),
                     coChannelInterfereDetect(2),
                     strongAdjChannelPresence(3) }
       MAX-ACCESS  read-write
       STATUS      current
       DESCRIPTION
          "The object sets the suppression state of the Radio Link Quality Alarms.  The
           values mean:

             sfd
                When bit 0 is set, the Radio Link Quality Alarms Notification, oduSlowFadingDetection,
                is suppressed and not spawned when oduAlarmConfLinkQualityAdminState is enabled.

             ffd
                When bit 1 is set, the Radio Link Quality Alarms Notification, oduFastFadingDetection,
                is suppressed and not spawned when oduAlarmConfLinkQualityAdminState is enabled.

             CoChannelInterfereDetect
                When bit 2 is set, the Radio Link Quality Alarms Notification, oduCoChannelInterfereDetection,
                is suppressed and not spawned when oduAlarmConfLinkQualityAdminState is enabled.

             StrongAdjChannelPresence
                When bit 3 is set, the Radio Link Quality Alarms Notification, oduStrongAdjChannelPresence,
                is suppressed and not spawned when oduAlarmConfLinkQualityAdminState is enabled." 
       DEFVAL { {} }
       ::= { oduAlarmConfigurationEntry 7 }

  --=========================================================                                      
   -- ODU CONFIGURATION TYPE TABLE  RFU
   --========================================================

   oduCfgTypeTable OBJECT-TYPE
      SYNTAX       SEQUENCE OF   OduCfgTypeEntry
      MAX-ACCESS   not-accessible
      STATUS       current
      DESCRIPTION  " 
                     This table models the ODU Configuration Type information
                   "    
      ::= { oduConfig  8 }

   oduCfgTypeEntry OBJECT-TYPE 
      SYNTAX       OduCfgTypeEntry
      MAX-ACCESS   not-accessible
      STATUS       current
      DESCRIPTION  " "
      INDEX  {oduCfgTypeIndex} 
      ::={oduCfgTypeTable 1 }

    OduCfgTypeEntry ::= SEQUENCE {                   
      
        oduCfgTypeIndex  INTEGER,
        oduConfigType    INTEGER,
        oduActualType  INTEGER
    }

   oduCfgTypeIndex   OBJECT-TYPE 
      SYNTAX       INTEGER (1)
      MAX-ACCESS   not-accessible
      STATUS       current
      DESCRIPTION  "
                    Index of the oduCfgTypeEntry. 
                    It is restricted to 1 instance.
                   "
      ::= { oduCfgTypeEntry 1 }

     oduConfigType OBJECT-TYPE 
       SYNTAX       INTEGER {autoOduType(0),
                             intracomOdu(1),
                             rfuOdu(2)}
        MAX-ACCESS   read-write
        STATUS       current
        DESCRIPTION  " 
                       Odu Configuration Type
                     "
        DEFVAL {autoOduType}
        ::= { oduCfgTypeEntry 2 }   

     oduActualType OBJECT-TYPE 
       SYNTAX       INTEGER {unKnownType(0),
                             intracomOdu(1),
                             rfuOdu(2)}
        MAX-ACCESS   read-only
        STATUS       current
        DESCRIPTION  " 
                       Odu Type
                     "
        ::= { oduCfgTypeEntry 3 }   

  --=========================================================                                      
   -- ODU RFU VERSION TABLE 
   --========================================================

   oduRFUVersionTable OBJECT-TYPE
      SYNTAX       SEQUENCE OF   OduRFUVersionEntry
      MAX-ACCESS   not-accessible
      STATUS       current
      DESCRIPTION  " 
                     This table models the ODU RFU Version information 
                     This table is not used in case of Intracom ODU, Flex ODU
                   "    
      ::= { oduConfig  9 }

   oduRFUVersionEntry OBJECT-TYPE 
      SYNTAX       OduRFUVersionEntry
      MAX-ACCESS   not-accessible
      STATUS       current
      DESCRIPTION  " "
      INDEX  {oduRFUVersionIndex} 
      ::={oduRFUVersionTable 1 }

    OduRFUVersionEntry ::= SEQUENCE {                   
      
        oduRFUVersionIndex  INTEGER,
        oduRFUModelType     OCTET STRING,    
        oduRFUModelNumber   OCTET STRING,  
        oduRFUSerialNumber  OCTET STRING,         
        oduRFUOEM OCTET STRING, 
        oduRFUCLIE OCTET STRING,                     
        oduSWVersion OCTET STRING,                  
        oduUpdateSWVersion OCTET STRING,
        oduRfuProductCode OCTET STRING                  
    }

   oduRFUVersionIndex   OBJECT-TYPE 
      SYNTAX       INTEGER (1)
      MAX-ACCESS   not-accessible
      STATUS       current
      DESCRIPTION  "
                    Index of the oduRFUVersionEntry. 
                    It is restricted to 1 instance.
                   "
      ::= { oduRFUVersionEntry 1 }

   oduRFUModelType OBJECT-TYPE 
      SYNTAX       OCTET STRING
      MAX-ACCESS   read-only
      STATUS       current
      DESCRIPTION  " 
                      The format of oduRFUModelType is 
                      two characters which are in range
                      of '0..9' or 'A..F'    
                      
                      The value encoding is shown below:                 
                      Odu RFU Model Type
                        0x00: legacy
	                    0x01: RBW1
	                    0x02: RBW0
	                    0x03: RBW2
	                    0x04: RBW3/4	
	                    0x20: CTT-Lite ETSI
	                    0x21: CTT-Lite ANSI
	                    0x30: CTT-S     ETSI
	                    0x31: CTT-S     ANSI
	                    0x40: CTT-H    ETSI
	                    0x41: CTT-H    ANSI

                      The valid oduRFUModelType values 
                      are 0x00..0xFF and the output format 
                      will be XxXX: RFU (e.g '0x04: RFU')
                      The 0xC0 value indicates  Unknown Model type and
                      the output format will be '0xC0:  Unknown'
                        
                   "
      ::= { oduRFUVersionEntry 2 }   

      oduRFUModelNumber OBJECT-TYPE 
           SYNTAX       OCTET STRING
           MAX-ACCESS   read-only
           STATUS       current
           DESCRIPTION  "  Odu RFU Model Number"
           ::= { oduRFUVersionEntry 3 } 

      oduRFUSerialNumber OBJECT-TYPE 
           SYNTAX       OCTET STRING
           MAX-ACCESS   read-only
           STATUS       current
           DESCRIPTION  "  Odu RFU Serial Number"
           ::= { oduRFUVersionEntry 4 } 
     
        oduRFUOEM OBJECT-TYPE 
           SYNTAX       OCTET STRING
           MAX-ACCESS   read-only
           STATUS       current
           DESCRIPTION  "  ODU RFU OEM
                           RFU Radio Band. Valid Values: 
                           6, 7, 8, 11, 13, 15, 18, 23, 26, 
                           32, 38 in GHz. "
           ::= { oduRFUVersionEntry 5 }     
         
        oduRFUCLIE OBJECT-TYPE 
           SYNTAX       OCTET STRING (SIZE (0..11))
           MAX-ACCESS   read-only
           STATUS       current
           DESCRIPTION  "  
                           This object is obselete.
                           It is not used.
           "
           ::= { oduRFUVersionEntry 6 }     

        oduSWVersion OBJECT-TYPE 
           SYNTAX       OCTET STRING (SIZE (0..10))
           MAX-ACCESS   read-only
           STATUS       current
           DESCRIPTION  "  ODU RFU software version"
           ::= { oduRFUVersionEntry 7 }     

        oduUpdateSWVersion OBJECT-TYPE 
           SYNTAX       OCTET STRING (SIZE (0..10))
           MAX-ACCESS   read-only
           STATUS       current
           DESCRIPTION  "  ODU RFU update software version"
           ::= { oduRFUVersionEntry 8 }
           
         oduRfuProductCode OBJECT-TYPE
            SYNTAX       OCTET STRING (SIZE (0..18))
            MAX-ACCESS   read-only
            STATUS       current
            DESCRIPTION  "  ODU Rfu Product Code"
            ::= { oduRFUVersionEntry 9 } 
    
  --=========================================================                                      
   -- ODU SERVICE CHANNEL STATISTICS 
   --========================================================

   oduServChanStatTable OBJECT-TYPE
      SYNTAX       SEQUENCE OF   OduServChanStatEntry
      MAX-ACCESS   not-accessible
      STATUS       current
      DESCRIPTION  " 
                     This table models the ODU 
                     service channel statistics
                   "    
      ::= { oduConfig  10 }

   oduServChanStatEntry OBJECT-TYPE 
      SYNTAX       OduServChanStatEntry
      MAX-ACCESS   not-accessible
      STATUS       current
      DESCRIPTION  " "
      INDEX  {oduServChanStatIndex} 
      ::={oduServChanStatTable 1 }

    OduServChanStatEntry ::= SEQUENCE {                   
      
        oduServChanStatIndex  INTEGER,
        oduCrcErrors         Counter32,    
        oduTotalCrcErrors   Counter32,  
        iduCrcErrors  Counter32,         
        oduDisconnects Counter32, 
        oduResetCmds Counter32,                     
        oduCountCtrl INTEGER,
        oduSfdAlarmsCounter Counter64,
        oduFfdAlarmsCounter Counter64,
        oduLinkQualityMonUpTime TimeTicks,
        oduCoChannelInterfereDetectAlarmsCounter Counter64,
        oduStrongAdjChannelPresenceAlarmsCounter Counter64
    }

   oduServChanStatIndex   OBJECT-TYPE 
      SYNTAX       INTEGER (1)
      MAX-ACCESS   not-accessible
      STATUS       current
      DESCRIPTION  "
                    Index of the oduServChanStatEntry. 
                    It is restricted to 1 instance.
                   "
      ::= { oduServChanStatEntry 1 }


    oduCrcErrors OBJECT-TYPE 
      SYNTAX       Counter32
      MAX-ACCESS   read-only
      STATUS       current
      DESCRIPTION  " 
            ODU CRC Errors	 : The CRC errors of the ODU
            Not affected by Counters Control
			and reset only with ODU reset.

    "
      ::= { oduServChanStatEntry 2 }      

    oduTotalCrcErrors OBJECT-TYPE 
      SYNTAX       Counter32
      MAX-ACCESS   read-only
      STATUS       current
      DESCRIPTION  " 

        The ODU CRC errors between ODU resets. 
        The IDU stores and reports total ODU
	    CRC errors between previous ODU resets . 
        Cleared by Counters Control and it starts 
        counting ODU CRC errors after counter reset.
            
    "
      ::= { oduServChanStatEntry 3 }

    iduCrcErrors OBJECT-TYPE 
      SYNTAX       Counter32
      MAX-ACCESS   read-only
      STATUS       current
      DESCRIPTION  " 

            The IDU CRC Errors.  
            Cleared by Counters Control

    "
      ::= { oduServChanStatEntry 4 }

    oduDisconnects OBJECT-TYPE 
      SYNTAX       Counter32
      MAX-ACCESS   read-only
      STATUS       current
      DESCRIPTION  " 

            The ODU disconnects, which are reported by IDU.
            Cleared by Counters Control

    "
      ::= { oduServChanStatEntry 5 }


    oduResetCmds OBJECT-TYPE 
      SYNTAX       Counter32
      MAX-ACCESS   read-only
      STATUS       current
      DESCRIPTION  " 

            Counter of reset command that IDU sends to ODU.  
            Cleared by Counters Control.
    "
      ::= { oduServChanStatEntry 6 }

    oduCountCtrl OBJECT-TYPE 
      SYNTAX       INTEGER {none(0),
                             resetCnt(1)}

      MAX-ACCESS   read-write
      STATUS       current
      DESCRIPTION  " 
            Counter reset command.
    "
      ::= { oduServChanStatEntry 7 }

    oduSfdAlarmsCounter OBJECT-TYPE 
      SYNTAX       Counter64
      MAX-ACCESS   read-only
      STATUS       current
      DESCRIPTION  " 

            Counter of Raised Slow Fading Detection Alarms.  
            Cleared by Counters Control.
    " 
      ::= { oduServChanStatEntry 8 }

    oduFfdAlarmsCounter OBJECT-TYPE 
      SYNTAX       Counter64
      MAX-ACCESS   read-only
      STATUS       current
      DESCRIPTION  " 

            Counter of Raised Fast Fading Detection Alarms.  
            Cleared by Counters Control.
    " 
      ::= { oduServChanStatEntry 9 }

    oduLinkQualityMonUpTime OBJECT-TYPE 
      SYNTAX       TimeTicks
      MAX-ACCESS   read-only
      STATUS       current
      DESCRIPTION  " 

            Time in hundredths of seconds that the Radio Link Monitoring is active.
            Cleared by Counters Control.
    " 
      ::= { oduServChanStatEntry 10 }

    oduCoChannelInterfereDetectAlarmsCounter OBJECT-TYPE 
      SYNTAX       Counter64
      MAX-ACCESS   read-only
      STATUS       current
      DESCRIPTION  " 

            Counter of Raised Cochannel Interference Detect Alarms.  
            Cleared by Counters Control.
    " 
      ::= { oduServChanStatEntry 11 }

    oduStrongAdjChannelPresenceAlarmsCounter OBJECT-TYPE 
      SYNTAX       Counter64
      MAX-ACCESS   read-only
      STATUS       current
      DESCRIPTION  " 

            Counter of Raised Strong Adjacent Channel Presence Alarms.  
            Cleared by Counters Control.
    " 
      ::= { oduServChanStatEntry 12 }

  --=========================================================                                      
   -- ODU INVENTORY INFO TABLE (applicable for SODU)
   --========================================================
   oduInventoryInfoTable OBJECT-TYPE
      SYNTAX       SEQUENCE OF   OduInventoryInfoEntry
      MAX-ACCESS   not-accessible
      STATUS       current
      DESCRIPTION  " 
                     This table models the SODU ODU Version information
                   "    
      ::= { oduConfig  11 }

   oduInventoryInfoEntry OBJECT-TYPE 
      SYNTAX       OduInventoryInfoEntry
      MAX-ACCESS   not-accessible
      STATUS       current
      DESCRIPTION  " "
      INDEX  {oduInventoryInfoEntryIndex} 
      ::={oduInventoryInfoTable 1 }

    OduInventoryInfoEntry ::= SEQUENCE {                   
      
        oduInventoryInfoEntryIndex  INTEGER,
        oduZCode                    OCTET STRING,
        oduZSerial                  OCTET STRING,
        oduIfYCode                  OCTET STRING,
        oduIfYSerial                OCTET STRING,
        oduTxRxYCode                OCTET STRING,
        oduTxRxYSerial              OCTET STRING
   }   

   oduInventoryInfoEntryIndex   OBJECT-TYPE 
      SYNTAX       INTEGER (1)
      MAX-ACCESS   not-accessible
      STATUS       current
      DESCRIPTION  "
                    Index of the oduInventoryInfoEntry. 
                    It is restricted to 1 instance.
                   "
      ::= { oduInventoryInfoEntry 1 }

   oduZCode OBJECT-TYPE 
      SYNTAX       OCTET STRING (SIZE (0..32))
      MAX-ACCESS   read-only
      STATUS       current
      DESCRIPTION  "  "
      ::= { oduInventoryInfoEntry 2 }     

   oduZSerial OBJECT-TYPE 
      SYNTAX       OCTET STRING (SIZE (0..32))
      MAX-ACCESS   read-only
      STATUS       current
      DESCRIPTION  "  "
      ::= { oduInventoryInfoEntry 3 }     

   oduIfYCode OBJECT-TYPE 
      SYNTAX       OCTET STRING (SIZE (0..32))
      MAX-ACCESS   read-only
      STATUS       current
      DESCRIPTION  "  "
      ::= { oduInventoryInfoEntry 4 }     

   oduIfYSerial OBJECT-TYPE 
      SYNTAX       OCTET STRING (SIZE (0..32))
      MAX-ACCESS   read-only
      STATUS       current
      DESCRIPTION  "  "
      ::= { oduInventoryInfoEntry 5 }     

   oduTxRxYCode OBJECT-TYPE 
      SYNTAX       OCTET STRING (SIZE (0..32))
      MAX-ACCESS   read-only
      STATUS       current
      DESCRIPTION  "  "
      ::= { oduInventoryInfoEntry 6 }     

   oduTxRxYSerial OBJECT-TYPE 
      SYNTAX       OCTET STRING (SIZE (0..32))
      MAX-ACCESS   read-only
      STATUS       current
      DESCRIPTION  "  "
      ::= { oduInventoryInfoEntry 7 }     

   --===================================================================
   -- oduInterferenceScanConfigTable
   --===================================================================  
   oduInterferenceScanConfigTable OBJECT-TYPE
      SYNTAX       SEQUENCE OF   OduInterferenceScanConfigEntry
      MAX-ACCESS   not-accessible
      STATUS       current
      DESCRIPTION  
          "This table models the ODU PTP Interference Scan Configuration parameters.
          Valid for STRN V-Band."    
      ::= { oduConfig  12 }

   oduInterferenceScanConfigEntry OBJECT-TYPE 
      SYNTAX       OduInterferenceScanConfigEntry
      MAX-ACCESS   not-accessible
      STATUS       current
      DESCRIPTION  " "
      INDEX  { oduInterferenceScanConfigIndex  } 
      ::={ oduInterferenceScanConfigTable 1 }

    OduInterferenceScanConfigEntry ::= SEQUENCE {
        oduInterferenceScanConfigIndex      Integer32,
        oduInterferenceScanStep             Integer32
   }   
   
   oduInterferenceScanConfigIndex   OBJECT-TYPE 
      SYNTAX       Integer32 (1)
      MAX-ACCESS   not-accessible
      STATUS       current
      DESCRIPTION  
          "Index of the oduInterferenceScanConfigEntry.
           It is restricted to 1 instance."
      ::= { oduInterferenceScanConfigEntry 1 }
	 
   oduInterferenceScanStep   OBJECT-TYPE
      SYNTAX        Integer32
      MAX-ACCESS    read-write
      STATUS        current
      DESCRIPTION
          "It specifies the Frequency step used to perform
          the Interference Scanning. The units are as indicated
          by the value of oduInterferenceScanStepScale."
      DEFVAL { 125 }
      ::= { oduInterferenceScanConfigEntry 2 }

   oduInterferenceScanStepScale   OBJECT-TYPE
      SYNTAX        INTEGER
                    { hz (1),
                      khz(2),
                      mhz(3),
                      ghz(4) }
      MAX-ACCESS    read-write
      STATUS        current
      DESCRIPTION
          "It specifies the Scale of the Frequency step in used to perform 
          the Interference Scanning.
          Applicable at ULFX80-CN."
      DEFVAL { mhz }
      ::= { oduInterferenceScanConfigEntry 3 }

   --===================================================================
   -- oduInterferenceScanStatusTable
   --===================================================================  
   oduInterferenceScanStatusTable OBJECT-TYPE
      SYNTAX       SEQUENCE OF   OduInterferenceScanStatusEntry
      MAX-ACCESS   not-accessible
      STATUS       current
      DESCRIPTION  
          "This table models the ODU Interference Scanning Status parameters."    
      ::= { oduConfig  13 }

   oduInterferenceScanStatusEntry OBJECT-TYPE
      SYNTAX       OduInterferenceScanStatusEntry
      MAX-ACCESS   not-accessible
      STATUS       current
      DESCRIPTION  " "
      INDEX  { oduInterferenceScanStatusIndex   } 
      ::={ oduInterferenceScanStatusTable 1 }

   OduInterferenceScanStatusEntry ::= SEQUENCE {
        oduInterferenceScanStatusIndex                  Integer32,
        oduInterferenceScanStatus                       INTEGER,
        oduInterferenceScanStatusDateTime               DateAndTime,
        oduInterferenceScanStatusAzimuth                Integer32,
        oduInterferenceScanStatusElevation              Integer32,
        oduInterferenceScanStatusLastStep               Integer32,
        oduInterferenceScanStatusLastNoOfFreqs          Integer32,
        oduInterferenceScanStatusMode                   INTEGER,
        oduInterferenceScanStatusStartFreq              Integer32,
        oduInterferenceScanStatusEndFreq                Integer32,
        oduInterferenceScanStatusTotalNoOfFreqs         Integer32
   }   
     
   oduInterferenceScanStatusIndex   OBJECT-TYPE 
      SYNTAX       Integer32 (1)
      MAX-ACCESS   not-accessible
      STATUS       current
      DESCRIPTION  
          "Index of the oduInterferenceScanStatusEntry. 
          It is restricted to 1 instance."
      ::= { oduInterferenceScanStatusEntry 1 }

   oduInterferenceScanStatus OBJECT-TYPE
        SYNTAX      INTEGER  { notStarted(1),
                               inProgress(2),
                               scanOK(3),
                               scanFailed(4)
                             }
        MAX-ACCESS  read-only
        STATUS      current
        DESCRIPTION
            " Interference Last Scan Status."
        ::= { oduInterferenceScanStatusEntry  2 }
 
   oduInterferenceScanStatusDateTime OBJECT-TYPE
        SYNTAX         DateAndTime
        MAX-ACCESS     read-only
        STATUS    current
        DESCRIPTION
             "The date and time at which the last Interference Scan 
             Measurement has started."
        ::= { oduInterferenceScanStatusEntry 3 }   
        
   oduInterferenceScanStatusAzimuth    OBJECT-TYPE 
      SYNTAX        Integer32 (-900..900)
      MAX-ACCESS    read-only
      STATUS        current
      DESCRIPTION  
          "Antenna Azimuth Position (-900 up to 900) in tenths of degrees
           at the last interference frequency scan."
      ::= { oduInterferenceScanStatusEntry 4 }
          
   oduInterferenceScanStatusElevation    OBJECT-TYPE 
      SYNTAX        Integer32 (-150..150)
      MAX-ACCESS    read-only
      STATUS        current
      DESCRIPTION  
          "Antenna Elevation position (-150 up to 150) in tenths of degrees
           at last interference frequency scan."
      ::= { oduInterferenceScanStatusEntry 5 }

   oduInterferenceScanStatusLastStep   OBJECT-TYPE 
      SYNTAX        Integer32
      MAX-ACCESS    read-only
      STATUS        current
      DESCRIPTION  
          "It specifies the Frequency step used to perform 
          the Last Interference Scanning. The units are as indicated
          by the value of oduInterferenceScanStepScale."
      ::= { oduInterferenceScanStatusEntry 6 }

   oduInterferenceScanStatusLastNoOfFreqs   OBJECT-TYPE 
      SYNTAX        Integer32
      MAX-ACCESS    read-only
      STATUS        current
      DESCRIPTION  
          "It specifies the number of scanned frequncies in the last 
          performed interference scanning. If the scan is in-progress 
          then 0 is specified as object value."
      ::= { oduInterferenceScanStatusEntry 7 }

   oduInterferenceScanStatusMode OBJECT-TYPE
      SYNTAX      INTEGER  { local(1),
                             link(2)}
      MAX-ACCESS  read-only
      STATUS      current
      DESCRIPTION
          "Interference Last Scan Status."
      ::= { oduInterferenceScanStatusEntry  8 }

   oduInterferenceScanStatusStartFreq OBJECT-TYPE
       SYNTAX      Integer32 
       MAX-ACCESS  read-only
       STATUS      current
       DESCRIPTION
           "First Scanned and recorded frequency.
            The units are as indicated by the value of oduInterferenceScanStepScale."
       ::= { oduInterferenceScanStatusEntry 9 }

   oduInterferenceScanStatusEndFreq OBJECT-TYPE
       SYNTAX      Integer32 
       MAX-ACCESS  read-only
       STATUS      current
       DESCRIPTION
           "Last Scanned and recorded frequency. 
            The units are as indicated by the value of oduInterferenceScanStepScale."
       ::= { oduInterferenceScanStatusEntry 10 }

   oduInterferenceScanStatusTotalNoOfFreqs OBJECT-TYPE
       SYNTAX      Integer32
       MAX-ACCESS  read-only
       STATUS      current
       DESCRIPTION
           "It specifies the total number of frequencies that will be scanned
            at the seesion of the scanning measurement."
       ::= { oduInterferenceScanStatusEntry 11 }

   --===================================================================
   -- oduInterferenceScanMeasureTable
   --===================================================================  
   oduInterferenceScanMeasureTable OBJECT-TYPE   
       SYNTAX      SEQUENCE OF OduInterferenceScanMeasureEntry
       MAX-ACCESS  not-accessible
       STATUS      current
       DESCRIPTION
           "This table contains the Last Scan Interference Measurements. The object
           oduInterferenceScanStatusLastNoOfFreqs includes the number of measurements
           i.e. the number of the entries of this table."
        ::= { oduConfig 14 }
        
   oduInterferenceScanMeasureEntry OBJECT-TYPE
       SYNTAX      OduInterferenceScanMeasureEntry
       MAX-ACCESS  not-accessible
       STATUS      current
       DESCRIPTION     
           "An entry in the oduInterferenceScanMeasureEntry."
       INDEX { oduInterferenceScanMeasureIndex }
       ::= { oduInterferenceScanMeasureTable 1 }

    OduInterferenceScanMeasureEntry ::= SEQUENCE {
        oduInterferenceScanMeasureIndex       	Integer32,
        oduInterferenceScanMeasureCenterFreq   	Integer32,
        oduInterferenceScanMeasureRSSI 	        Integer32,
        oduInterferenceScanMeasureSPAlarm       TruthValue
    }    

   oduInterferenceScanMeasureIndex OBJECT-TYPE
       SYNTAX      Integer32(1..32768)
       MAX-ACCESS  not-accessible
       STATUS      current
       DESCRIPTION 
           "Measurement entries."
       ::= { oduInterferenceScanMeasureEntry 1 }

   oduInterferenceScanMeasureCenterFreq OBJECT-TYPE
       SYNTAX      Integer32 
       MAX-ACCESS  read-only
       STATUS      current
       DESCRIPTION
           "Scanned and recorded center frequency. 
            The units are as indicated by the value of oduInterferenceScanStepScale."
       ::= { oduInterferenceScanMeasureEntry 2 }   

   oduInterferenceScanMeasureRSSI OBJECT-TYPE
       SYNTAX      Integer32 
       MAX-ACCESS  read-only
       STATUS      current
       DESCRIPTION
           "-1000..300. Values in tenths of dBm. This value should 
           be divided by 10 (/10) in order to get the actual value 
           e.g. a value of 173 stands for 173/10 = 17,3db."
       ::= { oduInterferenceScanMeasureEntry 3 }

   oduInterferenceScanMeasureSPAlarm OBJECT-TYPE
    SYNTAX      TruthValue
    MAX-ACCESS  read-only
    STATUS      current
    DESCRIPTION
       "If false then no Signal Presence Alarm exists at the Radio Link
        otherwise Signal Presence Alarm exists.
       " 
    ::= { oduInterferenceScanMeasureEntry 4 }

   --===================================================================
   -- oduInterferenceScanAction (SCALAR)
   --===================================================================  
   oduInterferenceScanAction OBJECT-TYPE
       SYNTAX      INTEGER { noAction (1), 
                             startScan (2),
                             stopScan(3)
                           }
       MAX-ACCESS  read-write
       STATUS      current
       DESCRIPTION 
           "On demand action related to Interference Scanning. 
            When startScan is ordered then the local unit starts 
            Interference Scanning.
            The object is not persistent at system restart."
       ::= { oduConfig  15 }

   --===================================================================
   -- oduChannelTxFreqTable
   --===================================================================  
   oduChannelTxFreqTable  OBJECT-TYPE
      SYNTAX       SEQUENCE OF   OduChannelTxFreqEntry
      MAX-ACCESS   not-accessible
      STATUS       current
      DESCRIPTION  
          "This table provides the min and max Tx Frequencies
          for a specific Channel Bandwidth. "
      ::= { oduConfig  16 }

   oduChannelTxFreqEntry OBJECT-TYPE
      SYNTAX       OduChannelTxFreqEntry
      MAX-ACCESS   not-accessible
      STATUS       current
      DESCRIPTION  
          "An entry in the oduChannelTxFreqEntry"
      INDEX  { oduChannelTxFreqBWIndex }
      ::={oduChannelTxFreqTable 1 }

   OduChannelTxFreqEntry ::= SEQUENCE {
        oduChannelTxFreqBWIndex   OduChannelBWIndexType,
        oduMinTxFrequency         Integer32,
        oduMaxTxFrequency         Integer32
   }

   oduChannelTxFreqBWIndex OBJECT-TYPE
      SYNTAX               OduChannelBWIndexType
      MAX-ACCESS           not-accessible
      STATUS               current
      DESCRIPTION  
          "PTP ODU bandwidth index "
      ::= { oduChannelTxFreqEntry 1 }

   oduMinTxFrequency OBJECT-TYPE
      SYNTAX         Integer32
      UNITS          "KHz"
      MAX-ACCESS     read-only
      STATUS         current
      DESCRIPTION  
          "Odu Min Tx Frequency. Value 0 indicates invalid cases, 
          i.e. not connected Odu or bandwidth not valid for the 
          specific modem."
      ::= { oduChannelTxFreqEntry 2 }

   oduMaxTxFrequency OBJECT-TYPE
      SYNTAX         Integer32
      UNITS          "KHz"
      MAX-ACCESS     read-only
      STATUS         current
      DESCRIPTION  
          "Odu Max Tx Frequency. Value 0 indicates invalid cases, 
          i.e. not connected Odu or bandwidth not valid for the 
          specific modem."
      ::= { oduChannelTxFreqEntry 3 }

   --================================================================ 
   -- ODU NOTIFICATIONS OBJECTS
   --================================================================
   
   oduNotificationObjects OBJECT IDENTIFIER 
   ::= { oduConfig  7}     --- traps
   
   oduOperationStatusFail NOTIFICATION-TYPE
      OBJECTS {oduOperStatus}
      STATUS current
      DESCRIPTION "
            A trap indicating Odu operation status
           [OmniBAS-2W, OmniBAS-4W  implementation]
            The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oduOperationStatusFail
                              = 1.3.6.1.4.1.1807.55.1.2.7.1
               varbind[2].oid = OidoduOperStatus
                              = 1.3.6.1.4.1.1807.55.1.2.3.1.2
               varbind[2].val = oduOperStatus
             
             where
             -- oduOperStatus is the driver received ODU operation status information
                (noErrorStatus(0), errorStatus(1))
      "
         ::= { oduNotificationObjects 1}

   oduRadioAlarmsNotification NOTIFICATION-TYPE
      OBJECTS {oduRadioAlarms}
      STATUS current
      DESCRIPTION "
            A trap indicating Odu Radio Alarms
           [OmniBAS-2W, OmniBAS-4W  implementation]            
            The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oduRadioAlarmsNotification
                              = 1.3.6.1.4.1.1807.55.1.2.7.2
               varbind[2].oid = OidoduRadioAlarms
                              = 1.3.6.1.4.1.1807.55.1.2.3.1.2
               varbind[2].val = oduRadioAlarms
             
             where
             -- oduRadioAlarms is the driver received ODU radio alarm information.
                The information is bitfield with the following bit value meaning:

                bit0: Pin(RSSI)
                      Detection input radio power  alarm from remote radio Unit ( RSSI)
                      - 0: RSSI ceased 
                      - 1: RSSI raised
                bit1: Pout (ALC) AGC Loop Control Set by ODU if the Tx AGC loop 
                      is unable to stabilize Tx output power within the desired limits
                      - 0: ALC ceased   
                      - 1: ALC raised
                bit2: Lock Detection in receiver's PLL
                      - 0: Locked           
                      - 1: Unlocked     
                bit3: Lock Detection in transmiter's PLL
                      - 0: Locked    
                      - 1: Unlocked         
                bit4: Frequency Out of range Errors Alarm
                      - 0: Frequency in range  
                      - 1: Frequency Out of range
                bit5: Lock Detection in microwave
                      - 0: LD_MW ceased
                      - 1: LD_MW raised
                bit6: Lock Detection in Loop Back
                      - 0: LD_LB ceased
                      - 1: LD_LB raised
                bit7: Power Out of range Errors Alarm
                      - 0: Power in range  
                      - 1: Power Out of range              
                bit8..bit31: not used
              "
         ::= { oduNotificationObjects 2}

   oduThresAlarmsNotification NOTIFICATION-TYPE
      OBJECTS {oduThresAlarms}
      STATUS current
      DESCRIPTION "
            A trap indicating Odu thresholds alarm.
            [OmniBAS-2W, OmniBAS-4W  implementation] 
            The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oduThresAlarmsNotification
                              = 1.3.6.1.4.1.1807.55.1.2.7.3
               varbind[2].oid = OidOduThreshAlarm
                              = 1.3.6.1.4.1.1807.55.1.2.3.1.6
               varbind[2].val = oduThresAlarms
             
             where
            -- oduThresAlarms is the driver received ODU threshold alarm information.
               The information is bitfield.
               The bit value meaning is affected by  OID oduModelType only for
               bit which this is clearly stated in the following description.
               The bit value meaning is shown below:

               bit0: This bit denotes different information depending on OID
                     oduModelType, as shown below:
                     - When OID oduModelType(b7-b6) is Intralink ODU Bit0 is not USED
                     - When OID oduModelType(b7-b6) is FLEX ODU or SODU Bit0 indicates
                       Power supply threshold alarm for -48V
                       Alarm set if the relevant voltage falls below the ODU DC
                       defined thresholds, status sent to IDU   
                       - 0:  Alarm ceased 
                       - 1:  Alarm raised
                bit1: Power supply threshold alarm for +6.5V
                      Alarm set if the relevant voltage falls below the ODU DC
                      defined thresholds, status sent to IDU   
                      - 0: Alarm ceased   
                      - 1: Alarm raised
                bit2: High Temperature threshold alarm
                      Alarm set if ODU measured temperature is above user defined 
                      high temperature limit (max temp), status sent to IDU
                      - 0: Alarm ceased        
                      - 1: Alarm raised    
                bit3: This bit denotes different information depending on OID
                      oduModelType, as shown below:
                      - When OID oduModelType(b7-b6) is Intralink ODU Bit3
                        indicates Power supply threshold alarm for -12V
                      - When OID oduModelType(b7-b6) is FLEX ODU or SODU Bit3 indicates
                        Power supply threshold alarm for -5V
                      Alarm set if the relevant voltage falls below the ODU DC
                      defined thresholds, status sent to IDU
                      - 0: Alarm ceased   
                      - 1: Alarm raised 
                 ***  bit3 is not used in case of RFU ODU       
                bit4: This bit denotes different information depending on OID
                      oduModelType, as shown below:
                      - When OID oduModelType(b7-b6) is Intralink ODU Bit4
                        indicates Power supply threshold alarm for +12V 
                      - When OID oduModelType(b7-b6) is FLEX ODU or SODU and
                        - oduModelType(b5-b0) is 0x07 or 0x08
                          Bit4 indicates Power supply V_PA threshold alarm for +12V
                        - oduModelType(b5-b0) is 0x0D or 0x0F or 0x26
                          Bit4 indicates Power supply V_PA threshold alarm for +9.5V
                        - oduModelType(b5-b0) is 0x12 or 0x17 or 0x1A
                          Bit4 indicates Power supply V_PA threshold alarm for +7.6V ) 
                                                            
                      Alarm set if the relevant voltage falls below the ODU DC
                      defined thresholds, status sent to IDU   
                      - 0: Alarm ceased
                      - 1: Alarm raised
                    ***  bit4 is not used in case of RFU ODU  

                bit5: Power supply threshold  alarm for +5V         
                      Alarm set if the relevant voltage falls below the ODU DC
                      defined thresholds, status sent to IDU  
                      - 0: Alarm ceased
                      - 1: Alarm raised
                bit6: Input power from the remote Radio Unit
                      Alarm set if Pin Rx ODU less than a user defined threshold. 
                      Status sent to IDU:
                      - 0: Input radio power not detected
                      - 1: Input radio power detected
                bit7: Detection of Minimum ODU input power as sensed by Tx cable detector (Pif)
                      - 0: Pif detection OFF
                      - 1: Pif detection ON
                bit8..bit31: not used
      "
         ::= { oduNotificationObjects 3}

   oduUpdateStatAlarmsNotification NOTIFICATION-TYPE
      OBJECTS {oduUpdateStatus}
      STATUS current
      DESCRIPTION "
           A trap indicating Odu Update Status alarm
           [OmniBAS-2W, OmniBAS-4W  implementation]  
           The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oduUpdateStatAlarmsNotification
                              = 1.3.6.1.4.1.1807.55.1.2.7.4
               varbind[2].oid = OidOduUpdateStatus
                              = 1.3.6.1.4.1.1807.55.1.2.3.1.10
               varbind[2].val = oduUpdateStatus
             
             where
             -- oduUpdateStatus is the driver received ODU update status information
                (  oduStatUpdated(0), oduStatNeedUpdate(1), oduStatUpdateNow(2), oduStatUpdateFail(3))
         "
         ::= { oduNotificationObjects 4}
         
   oduGenConfigAlarmNotification NOTIFICATION-TYPE
      OBJECTS {oduGenConfigAlarm}
      STATUS current
      DESCRIPTION "
           A trap indicating Odu general configuration alarms 
           [OmniBAS-2W, OmniBAS-4W  implementation]           
            The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oduGenConfigAlarmNotification
                              = 1.3.6.1.4.1.1807.55.1.2.7.5
               varbind[2].oid = OidOduGenConfigAlarm
                              = 1.3.6.1.4.1.1807.55.1.2.3.1.11
               varbind[2].val = oduGenConfigAlarm
             
             where
               -- oduGenConfigAlarm is the driver received ODU general
                  configuration alarm information. The information is bitfield
                  with the following bit value meaning:
                  bit0: Odu invalid Model Type
                        The Alarm is raised, when the inserted ODU in the system, 
                        has an invalid (unsupported) Model Type.
                        - 0: The inserted ODU has valid Model Type (Alarm ceased)
                        - 1: The inserted ODU has invalid Model Type (Alarm raised)
                  bit1: Odu bandwidth configuration mismatch
                        The Alarm is raised, when the Odu bandwidth value stored
                        in the configuration, does not collocate with the
                        installed ODU hardware.
                        - 0: Alarm ceased
                        - 1: Alarm raised
                  bit2: Calibration Alarm
                  bit3: Pif max Alarm
                  bit4: Low If Alarm
                  bit5: Low Temperature Alarm
                  bit6: - not used
                  bit7..bit31: - not used
             "
         ::= { oduNotificationObjects 5}
 
   oduTestNotification NOTIFICATION-TYPE
      OBJECTS {oduTestType}
      STATUS current
      DESCRIPTION "
           A trap indicating the active Odu Test Type
             
           [OmniBAS-2W, OmniBAS-4W, OmniBAS-2W-16E1, OmniBAS-4W-HE  implementation] 
           [Applies to products: All Omnibas products except XR. No loopback for split-REMEC.]      
            The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oduTestTypeAlarmNotification
                              = 1.3.6.1.4.1.1807.55.1.2.7.6

               varbind[2].oid = oduTestType
                              = 1.3.6.1.4.1.1807.55.1.2.1.1.12
               varbind[2].val = oduTestType Value
             
             where
                  oduTestType Value is the driver received ODU test type indication
                  Value meaning:

                     0: Indicates that the test is not active
                     1: Indicates that loop back test 
                     2: Indicates dc Power Off test 
                     3: Indicates mute On test (Currently not available)
                     other values not applicable

             - Alarm type: Event

             - raise conditions: oduTestType !=0
             - cease conditions: oduTestType =0

             "
         ::= { oduNotificationObjects 6}
         
   oduTxPowerLicenseFailure NOTIFICATION-TYPE
      OBJECTS { oduSetTxPower }
      STATUS current
      DESCRIPTION 
          " A trap indicating that the configured ODU Tx Power is not licensed.       
          The NMS forwards the following information to the operator:
                     
              varbind[0].oid = oid_sysUpTime.0 = 1.3.6.1.2.1.1.3.0
              varbind[0].val = NMS agent time (in centiseconds)
                  
              varbind[1].oid = oid_snmpTrapOID.0 = 1.3.6.1.6.3.1.1.4.1.0
              varbind[1].val = oduTxPowerLicenseFailure
                             = 1.3.6.1.4.1.1807.55.1.2.7.7

              varbind[2].oid = oid_oduSetTxPower.oduConfigEntryIndex
                             = .1.3.6.1.4.1.1807.55.1.2.1.1.4.oduConfigEntryIndex
              varbind[2].val = oduSetTxPower
  
              The severity of the trap is warning."
      ::= { oduNotificationObjects 7}

   oduSlowFadingDetection NOTIFICATION-TYPE
      OBJECTS { oduSlowFadingStatus }
      STATUS current
      DESCRIPTION 
          " A notification indicating that Slow Fading Alarm is raised or ceased.       
           The NMS forwards the following information to the operator:

              varbind[0].oid = oid_sysUpTime.0 = 1.3.6.1.2.1.1.3.0
              varbind[0].val = NMS agent time (in centiseconds)

              varbind[1].oid = oid_snmpTrapOID.0 = 1.3.6.1.6.3.1.1.4.1.0
              varbind[1].val = oduSlowFadingDetection 
                             = 1.3.6.1.4.1.1807.55.1.2.7.8

              varbind[2].oid = oduSlowFadingStatus.oduStatusEntryIndex
                             = .1.3.6.1.4.1.1807.55.1.2.3.1.13.oduStatusEntryIndex
              varbind[2].val = oduSlowFadingStatus

              The severity of the trap is warning." 
      ::= { oduNotificationObjects 8}

   oduFastFadingDetection NOTIFICATION-TYPE
      OBJECTS { oduFastFadingStatus }
      STATUS current
      DESCRIPTION 
          " A notification indicating that Fast Fading Alarm is raised or ceased.       
            The NMS forwards the following information to the operator:

              varbind[0].oid = oid_sysUpTime.0 = 1.3.6.1.2.1.1.3.0
              varbind[0].val = NMS agent time (in centiseconds)

              varbind[1].oid = oid_snmpTrapOID.0 = 1.3.6.1.6.3.1.1.4.1.0
              varbind[1].val = oduFastFadingDetection 
                             = 1.3.6.1.4.1.1807.55.1.2.7.9

              varbind[2].oid = oduFastFadingStatus.oduStatusEntryIndex
                             = .1.3.6.1.4.1.1807.55.1.2.3.1.14.oduStatusEntryIndex
              varbind[2].val = oduFastFadingStatus

              The severity of the trap is warning." 
      ::= { oduNotificationObjects 9}


   oduCoChannelInterfereDetection NOTIFICATION-TYPE
      OBJECTS { oduCoChannelInterfereDetectStatus }
      STATUS current
      DESCRIPTION 
          " A notification indicating that Cochannel Interference Detection Alarm 
            is raised or ceased.
           The NMS forwards the following information to the operator:

              varbind[0].oid = oid_sysUpTime.0 = 1.3.6.1.2.1.1.3.0
              varbind[0].val = NMS agent time (in centiseconds)

              varbind[1].oid = oid_snmpTrapOID.0 = 1.3.6.1.6.3.1.1.4.1.0
              varbind[1].val = oduCoChannelInterfereDetection
                             = 1.3.6.1.4.1.1807.55.1.2.7.10

              varbind[2].oid = oduCoChannelInterfereDetectStatus.oduStatusEntryIndex
                             = .1.3.6.1.4.1.1807.55.1.2.3.1.15.oduStatusEntryIndex
              varbind[2].val = oduCoChannelInterfereDetectStatus

              The severity of the trap is warning." 
      ::= { oduNotificationObjects 10}

   oduStrongAdjChannelPresence NOTIFICATION-TYPE
      OBJECTS { oduStrongAdjChannelPresenceStatus}
      STATUS current
      DESCRIPTION 
          " A notification indicating that Strong Adjacent Channel Presence Alarm 
            is raised or ceased.
           The NMS forwards the following information to the operator:

              varbind[0].oid = oid_sysUpTime.0 = 1.3.6.1.2.1.1.3.0
              varbind[0].val = NMS agent time (in centiseconds)

              varbind[1].oid = oid_snmpTrapOID.0 = 1.3.6.1.6.3.1.1.4.1.0
              varbind[1].val = oduStrongAdjChannelPresence 
                             = 1.3.6.1.4.1.1807.55.1.2.7.11

              varbind[2].oid = oduStrongAdjChannelPresenceStatus.oduStatusEntryIndex
                             = .1.3.6.1.4.1.1807.55.1.2.3.1.16.oduStatusEntryIndex
              varbind[2].val = oduStrongAdjChannelPresenceStatus

              The severity of the trap is warning." 
      ::= { oduNotificationObjects 11}


   -- STRN Antenna Objects
   strnAntennaConfig OBJECT IDENTIFIER ::= { modemConfigMibObjects 3 } 

   --===================================================================
   -- strnAntennaGenConfigTable
   --===================================================================  
   strnAntennaGenConfigTable OBJECT-TYPE
      SYNTAX       SEQUENCE OF   StrnAntennaGenConfigEntry
      MAX-ACCESS   not-accessible
      STATUS       current
      DESCRIPTION  
          "This table models the STRN-PTP Antenna Configuration general parameters.
          N/A for the OSDRS (same holds for every strnAntennaConfig object).
		  N/A for the EBAND (same holds for every strnAntennaConfig object)"    
      ::= { strnAntennaConfig  1 }

   strnAntennaGenConfigEntry OBJECT-TYPE 
      SYNTAX       StrnAntennaGenConfigEntry
      MAX-ACCESS   not-accessible
      STATUS       current
      DESCRIPTION  " "
      INDEX  { strnAntennaGenConfigEntryIndex  } 
      ::={ strnAntennaGenConfigTable 1 }

    StrnAntennaGenConfigEntry ::= SEQUENCE {                   
        strnAntennaGenConfigEntryIndex      INTEGER,
        strnAntennaAlignConf                INTEGER,
        strnAntennaAzimuthRefPos            INTEGER
   }   
   
   strnAntennaGenConfigEntryIndex   OBJECT-TYPE 
      SYNTAX       INTEGER (1)
      MAX-ACCESS   not-accessible
      STATUS       current
      DESCRIPTION  
          "Index of the StrnAntennaGenConfigEntry. It is restricted to 1 instance."
      ::= { strnAntennaGenConfigEntry 1 }
	 
   strnAntennaAlignConf    OBJECT-TYPE 
      SYNTAX        INTEGER {manual(0),auto(1)}
      MAX-ACCESS    read-write
      STATUS        current
      DESCRIPTION  
          "It specifies the way that the Antenna Alignment is performed. Manually 
           or Automatically."
      DEFVAL { 0 }
      ::= { strnAntennaGenConfigEntry 2 }
	
    strnAntennaAzimuthRefPos    OBJECT-TYPE 
      SYNTAX        INTEGER (0..3599)
      MAX-ACCESS    read-write
      STATUS        current
      DESCRIPTION  
          "Reference Position to start measuring the Azimuth angle of the STRN Unit. 
           North is considered as the Reference Position."
      DEFVAL { 0 }
      ::= { strnAntennaGenConfigEntry 3 }

   --===================================================================
   -- strnAntennaAutoConfigTable
   --===================================================================  
   strnAntennaAutoConfigTable OBJECT-TYPE
      SYNTAX       SEQUENCE OF StrnAntennaAutoConfigEntry
      MAX-ACCESS   not-accessible
      STATUS       current
      DESCRIPTION  
          "This table models the STRN-PTP Antenna Auto Configuration  parameters."    
      ::= { strnAntennaConfig  2 }

   strnAntennaAutoConfigEntry OBJECT-TYPE 
      SYNTAX       StrnAntennaAutoConfigEntry
      MAX-ACCESS   not-accessible
      STATUS       current
      DESCRIPTION  " "
      INDEX  { strnAntennaAutoConfigEntryIndex } 
      ::={ strnAntennaAutoConfigTable 1 }

   StrnAntennaAutoConfigEntry ::= SEQUENCE {                   
        strnAntennaAutoConfigEntryIndex  INTEGER,
        strnAntennaVerificationScan      INTEGER,
        strnAntennaSavedPeakDegrThresh   INTEGER,
        strnAntennaSavedPeakTestTimeout  INTEGER        
   }   
   
   strnAntennaAutoConfigEntryIndex   OBJECT-TYPE 
      SYNTAX       INTEGER (1)
      MAX-ACCESS   not-accessible
      STATUS       current
      DESCRIPTION  "Index of the StrnAntennaAutoConfigEntry. 
                    It is restricted to 1 instance."
      ::= { strnAntennaAutoConfigEntry 1 }
	
   strnAntennaVerificationScan    OBJECT-TYPE 
      SYNTAX        INTEGER {enable(0),disable(1)}
      MAX-ACCESS    read-write
      STATUS        current
      DESCRIPTION  
          "Enables / disables an evaluation of the peaks found at the initial scan.
           Valid (applicable) only when strnAntennaAlignConf = auto."
      DEFVAL { 1 }
      ::= { strnAntennaAutoConfigEntry 2 }
      
     strnAntennaSavedPeakDegrThresh    OBJECT-TYPE 
      SYNTAX        INTEGER (0..100)
      MAX-ACCESS    read-write
      STATUS        current
      DESCRIPTION  
          "If stored Antenna alignment parameter exists then the STRN tries to use them 
           before attempting Antenna initialization and Initial Scan. It checks then if the 
           RSSI / SNR results of this evaluation have a difference not bigger than the value 
           indicated by savedpeakdegrthesh then these stored parameters can be used and antenna 
           is considered as aligned. Valid (applicable) only when strnAntennaAlignConf = auto.
           Values in Tenths of  dB e.g. a value of 173 stands for 173/10 = 17,3dB."
      DEFVAL { 30 }
      ::= { strnAntennaAutoConfigEntry 3 }
      
   strnAntennaSavedPeakTestTimeout    OBJECT-TYPE 
      SYNTAX        INTEGER (100..20000)
      MAX-ACCESS    read-write
      STATUS        current
      DESCRIPTION  
          "Timeout used to evaluate the stored antenna alignment parameters to evaluate the 
           RSSI / SNR results of this evaluation have a difference not bigger than the value 
           indicated by savedpeakdegrthesh. Valid (applicable) only when strnAntennaAlignConf = auto.
           Values in ms 173."
      DEFVAL { 10000 }
      ::= { strnAntennaAutoConfigEntry 4 }

   --===================================================================
   -- strnAntennaAutoFineConfigTable
   --===================================================================  
   strnAntennaAutoFineConfigTable OBJECT-TYPE
      SYNTAX       SEQUENCE OF   StrnAntennaAutoFineConfigEntry
      MAX-ACCESS   not-accessible
      STATUS       current
      DESCRIPTION  
          "This table models the STRN-PTP Antenna Auto Fine Tuning Configuration  parameters."    
      ::= { strnAntennaConfig  3 }

   strnAntennaAutoFineConfigEntry OBJECT-TYPE 
      SYNTAX       StrnAntennaAutoFineConfigEntry
      MAX-ACCESS   not-accessible
      STATUS       current
      DESCRIPTION  " "
      INDEX  { strnAntennaAutoFineConfigEntryIndex   } 
      ::={ strnAntennaAutoFineConfigTable 1 }

   StrnAntennaAutoFineConfigEntry ::= SEQUENCE {                   
        strnAntennaAutoFineConfigEntryIndex       INTEGER,
        strnAntennaAutoFineTune                   INTEGER,
        strnAntennaMaxFineTunes                   INTEGER,
        strnAntennaAutoFineTuneDegrThresh         INTEGER,
        strnAntennaAutoFineTuneTimeout            INTEGER
   }   
   
   strnAntennaAutoFineConfigEntryIndex   OBJECT-TYPE 
      SYNTAX       INTEGER (1)
      MAX-ACCESS   not-accessible
      STATUS       current
      DESCRIPTION  
          "Index of the StrnAntennaAutoFineConfigEntry. It is restricted to 1 instance."
      ::= { strnAntennaAutoFineConfigEntry 1 }
      
   strnAntennaAutoFineTune    OBJECT-TYPE 
      SYNTAX        INTEGER {enable(0),disable(1)}
      MAX-ACCESS    read-write
      STATUS        current
      DESCRIPTION  
          "Automatic continues fine tuning status"
      DEFVAL { 1 }
      ::= { strnAntennaAutoFineConfigEntry 2 }

   strnAntennaMaxFineTunes    OBJECT-TYPE 
      SYNTAX        INTEGER (1..10)
      MAX-ACCESS    read-write
      STATUS        current
      DESCRIPTION  
         "Maximum Number of Fine Tunes performed to find better RSSI/SNR."
      DEFVAL { 3 }
      ::= { strnAntennaAutoFineConfigEntry 3 }

   strnAntennaAutoFineTuneDegrThresh    OBJECT-TYPE 
      SYNTAX        INTEGER (0..100)
      MAX-ACCESS    read-write
      STATUS        current
      DESCRIPTION  
          "At fine tuning, the STRN checks if the RSSI / SNR results of the position found 
           by fine tuning are better that the values of the previous found peak. If no better 
           peak is found then the last peak is verified that has a difference not bigger than 
           the value indicated by autofinedegrthesh. If verified then antenna is considered as 
           aligned. Valid (applicable) only when alignconf = auto and autofinetune = enable. 
           Values in Tenths of dB e.g. a value of 173 stands for 173/10 = 17,3db. "
      DEFVAL { 30 }
      ::= { strnAntennaAutoFineConfigEntry 4 }
      
   strnAntennaAutoFineTuneTimeout    OBJECT-TYPE 
      SYNTAX        INTEGER (100..20000)
      MAX-ACCESS    read-write
      STATUS        current
      DESCRIPTION  
          "Automatic Fine Tuning Timeout. At timeout the degradation of current peak is checked 
           and if not within the RSSI/SNR limits then a new fine tuning is performed. Valid 
           (applicable) only when alignconf = auto and autofinetune = enable. Values in ms 173 
           stands for 173ms. "
      DEFVAL { 10000 }
      ::= { strnAntennaAutoFineConfigEntry 5 }

   --===================================================================
   -- strnAntennaManualConfigTable
   --===================================================================  
   strnAntennaManualConfigTable OBJECT-TYPE
      SYNTAX       SEQUENCE OF   StrnAntennaManualConfigEntry
      MAX-ACCESS   not-accessible
      STATUS       current
      DESCRIPTION  
          "This table models the STRN-PTP Antenna Manual Configuration  parameters."    
      ::= { strnAntennaConfig  4 }

   strnAntennaManualConfigEntry OBJECT-TYPE 
      SYNTAX       StrnAntennaManualConfigEntry
      MAX-ACCESS   not-accessible
      STATUS       current
      DESCRIPTION  " "
      INDEX  { strnAntennaManualConfigEntryIndex } 
      ::={ strnAntennaManualConfigTable 1 }

    StrnAntennaManualConfigEntry ::= SEQUENCE {                   
        strnAntennaManualConfigEntryIndex     INTEGER,
        strnAntennaCfgAzimuth                 INTEGER,
        strnAntennaCfgElevation               INTEGER
   }   
   
   strnAntennaManualConfigEntryIndex   OBJECT-TYPE 
      SYNTAX       INTEGER (1)
      MAX-ACCESS   not-accessible
      STATUS       current
      DESCRIPTION  
          "Index of the StrnAntennaManualConfigEntry. It is restricted to 1 instance."
      ::= { strnAntennaManualConfigEntry 1 }
    
   strnAntennaCfgAzimuth    OBJECT-TYPE 
      SYNTAX        INTEGER
      MAX-ACCESS    read-write
      STATUS        current
      DESCRIPTION  
          "Manually Configured Azimuth Position (-900 up to 900)."
      ::= { strnAntennaManualConfigEntry 2 }
          
   strnAntennaCfgElevation    OBJECT-TYPE 
      SYNTAX        INTEGER
      MAX-ACCESS    read-write
      STATUS        current
      DESCRIPTION  
          "Manually Configured Elevation (-150 up to 150)."
      ::= { strnAntennaManualConfigEntry 3 }

   --===================================================================
   -- strnAntennaCurrentStatusTable
   --===================================================================  
   strnAntennaCurrentStatusTable OBJECT-TYPE
      SYNTAX       SEQUENCE OF   StrnAntennaCurrentStatusEntry
      MAX-ACCESS   not-accessible
      STATUS       current
      DESCRIPTION  
          "This table models the STRN-PTP Antenna Alignment Current Status parameters."    
      ::= { strnAntennaConfig  5 }

   strnAntennaCurrentStatusEntry OBJECT-TYPE 
      SYNTAX       StrnAntennaCurrentStatusEntry
      MAX-ACCESS   not-accessible
      STATUS       current
      DESCRIPTION  " "
      INDEX  { strnAntennaCurrentStatusEntryIndex   } 
      ::={ strnAntennaCurrentStatusTable 1 }

   StrnAntennaCurrentStatusEntry ::= SEQUENCE {                   
        strnAntennaCurrentStatusEntryIndex              INTEGER,
        strnAntennaCurrentStatusAzimuth                 INTEGER,
        strnAntennaCurrentStatusElevation               INTEGER,
        strnAntennaCurrentStatusRSSI                    INTEGER,
        strnAntennaCurrentStatusSNR                     INTEGER,
        strnAntennaCurrentStatusModemLock               INTEGER,
        strnAntennaCurrentStatusAlignmentState          INTEGER,
        strnAntennaCurrentStatusNumMeasurementElements  INTEGER,
        strnAntennaCurrentStatusNumPeakElements         INTEGER,
        strnAntennaCurrentAntennaFailureAlarmStatus     INTEGER,
        strnAntennaCurrentAntennaPolarization           INTEGER
   }   
   
   strnAntennaCurrentStatusEntryIndex   OBJECT-TYPE 
      SYNTAX       INTEGER (1)
      MAX-ACCESS   not-accessible
      STATUS       current
      DESCRIPTION  
          "Index of the StrnAntennaCurrentStatusEntry. It is restricted to 1 instance."
      ::= { strnAntennaCurrentStatusEntry 1 }
    
   strnAntennaCurrentStatusAzimuth    OBJECT-TYPE 
      SYNTAX        INTEGER
      MAX-ACCESS    read-only
      STATUS        current
      DESCRIPTION  
          "Current Azimuth Position (-900 up to 900) in tenths of degrees."
      ::= { strnAntennaCurrentStatusEntry 2 }
          
   strnAntennaCurrentStatusElevation    OBJECT-TYPE 
      SYNTAX        INTEGER
      MAX-ACCESS    read-only
      STATUS        current
      DESCRIPTION  
          "Current Elevation (-150 up to 150) in tenths of degrees."
      ::= { strnAntennaCurrentStatusEntry 3 }
      
   strnAntennaCurrentStatusRSSI    OBJECT-TYPE 
      SYNTAX      INTEGER 
      MAX-ACCESS  read-only
      STATUS      current
      DESCRIPTION
          "-1000..300dbm. Values in tenths of dBm. This value should be divided by 10 (/10) in
           order to get the actual value e.g. a value of 173 stands for 173/10 = 17,3db."
      ::= { strnAntennaCurrentStatusEntry  4 }
      
   strnAntennaCurrentStatusSNR OBJECT-TYPE
        SYNTAX      INTEGER 
        MAX-ACCESS  read-only
        STATUS      current
        DESCRIPTION
            "0..450db. Values in tenths of dB. This value should be divided by 10 (/10) in
             order to get the actual value e.g. a value of 173 stands for 173/10 = 17,3db."
        ::= { strnAntennaCurrentStatusEntry  5 }
        
   strnAntennaCurrentStatusModemLock OBJECT-TYPE
        SYNTAX      INTEGER  {lock(0),unlock(1)}
        MAX-ACCESS  read-only
        STATUS      current
        DESCRIPTION
            " Modem Lock Status."
        ::= { strnAntennaCurrentStatusEntry  6 }
	
   strnAntennaCurrentStatusAlignmentState    OBJECT-TYPE 
      SYNTAX        INTEGER {notAligned(0),
                             validatingAlignment(1),
                             aligning(2),
                             fineTuning(3),
                             aligned(4),
                             monitoring(5),
                             motorFailure(6)}
      MAX-ACCESS    read-only
      STATUS        current
      DESCRIPTION  
          "NOT_ALIGNED: The antenna has not been aligned yet, or the alignment has failed.
           VALIDATING_ALIGNMENT: The antenna is validating the saved peak (i.e. align saved)		
           ALIGNING: The antenna is currently executing the alignment procedure, including a possible validation scan (i.e. align normal).
           FINE_TUNING: The antenna is currently executing the fine-tune procedure.
           ALIGNED: The antenna has been successfully aligned (and possibly fine-tuned).
           MONITORING: The antenna has been successfully aligned, and is monitoring the signal to detect degradation and automatically fine-tune.
           MOTOR_FAILURE: mechanical issue with the antenna."
      ::= { strnAntennaCurrentStatusEntry  7 }

   strnAntennaCurrentStatusNumMeasurementElements    OBJECT-TYPE 
      SYNTAX        INTEGER
      MAX-ACCESS    read-only
      STATUS        current
      DESCRIPTION  
          "Number of  valid STRN Measurement elements"
      ::= { strnAntennaCurrentStatusEntry  8 }
  
   strnAntennaCurrentStatusNumPeakElements    OBJECT-TYPE 
      SYNTAX        INTEGER
      MAX-ACCESS    read-only
      STATUS        current
      DESCRIPTION  
          "Number of  valid STRN Peak Elements."
      ::= { strnAntennaCurrentStatusEntry  9 }

   strnAntennaCurrentAntennaFailureAlarmStatus  OBJECT-TYPE 
        SYNTAX       INTEGER {on(1), off(2)}
        MAX-ACCESS   read-only
        STATUS       current
        DESCRIPTION  
            "STRN Antenna Failure alarm status  
             on(1):  means that  STRN antenna failure alarm exists
             off(2): no STN antenna failure alarm exists."
        ::= { strnAntennaCurrentStatusEntry  10 }

   strnAntennaCurrentAntennaPolarization   OBJECT-TYPE
        SYNTAX      INTEGER { clockwise (0), 
                              anticlockwise (1)
                            }
        MAX-ACCESS  read-only
        STATUS      current
        DESCRIPTION 
            " Circular Polarization type of the STRN Antenna Alignment."
        ::= { strnAntennaCurrentStatusEntry 11 }  

   --===================================================================
   -- strnAntennaMeasurementTable
   --===================================================================  
   strnAntennaMeasurementTable OBJECT-TYPE   
        SYNTAX      SEQUENCE OF StrnAntennaMeasurementEntry
        MAX-ACCESS  not-accessible
        STATUS      current
        DESCRIPTION
            "This table contains STRN Antenna Measurements Info. Number of entries is 
            variable and the actual size declared by strnAntennaCurrentStatusMeasurementElements."
        ::= { strnAntennaConfig  6 }
        
   strnAntennaMeasurementEntry OBJECT-TYPE
       SYNTAX      StrnAntennaMeasurementEntry
       MAX-ACCESS  not-accessible
       STATUS      current
       DESCRIPTION     
           "An entry in the strnAntennaMeasurementTable."
       INDEX  { strnAntennaMeasurementIndex }
       ::= { strnAntennaMeasurementTable 1 }

   StrnAntennaMeasurementEntry ::= SEQUENCE {
       strnAntennaMeasurementIndex      INTEGER,
       strnAntennaMeasurementAzimuth   	INTEGER,
       strnAntennaMeasurementElevation 	INTEGER,
       strnAntennaMeasurementRssi	    INTEGER,                                                  
       strnAntennaMeasurementSnr	    INTEGER,
       strnAntennaMeasurementModemLock 	INTEGER                    
   }    

   strnAntennaMeasurementIndex OBJECT-TYPE
       SYNTAX      INTEGER (1..228)
       MAX-ACCESS  not-accessible
       STATUS      current
       DESCRIPTION
           " "
       ::= { strnAntennaMeasurementEntry 1 }
            
   strnAntennaMeasurementAzimuth OBJECT-TYPE
       SYNTAX      INTEGER 
       MAX-ACCESS  read-only
       STATUS      current
       DESCRIPTION 
           "-900..900 round configured azimuth in tenths of degrees. This value should be 
             divided by 10 (/10) in order to get the actual value"
       ::= { strnAntennaMeasurementEntry 2 }    
                
   strnAntennaMeasurementElevation OBJECT-TYPE
       SYNTAX      INTEGER 
       MAX-ACCESS  read-only
       STATUS      current
       DESCRIPTION
           "-150..150 round to configured elevation in tenths of degrees.
            This value should be divided by 10 (/10) in order to get the actual value."
       ::= { strnAntennaMeasurementEntry 3 }        
                
   strnAntennaMeasurementRssi OBJECT-TYPE
      SYNTAX      INTEGER 
      MAX-ACCESS  read-only
      STATUS      current
      DESCRIPTION
          "-1000..300. Values in tenths of dBm
           This value should be divided by 10 (/10) in order to get the actual value e.g. a value 
           of 173 stands for 173/10 = 17,3db."
      ::= { strnAntennaMeasurementEntry 4 }           
            
   strnAntennaMeasurementSnr OBJECT-TYPE
       SYNTAX      INTEGER 
       MAX-ACCESS  read-only
       STATUS      current
       DESCRIPTION
           "0..450. Values in dB. This value should be divided by 10 (/10) in order to get the actual 
            value e.g. a value of 173 stands for 173/10 = 17,3db. "
       ::= { strnAntennaMeasurementEntry 5 }          
                
   strnAntennaMeasurementModemLock OBJECT-TYPE
       SYNTAX      INTEGER  {lock(0),unlock(1)}
       MAX-ACCESS  read-only
       STATUS      current
       DESCRIPTION
           "Modem Lock Status at measurement instance."
       ::= { strnAntennaMeasurementEntry 6 }
                
   --===================================================================
   -- strnAntennaPeakTable
   --===================================================================  
   strnAntennaPeakTable OBJECT-TYPE   
       SYNTAX      SEQUENCE OF StrnAntennaPeakEntry
       MAX-ACCESS  not-accessible
       STATUS      current
       DESCRIPTION
           "This table contains Stn Antenna Peak Info. Number of entries is 
            variable and the actual size declared by strnAntennaPeakElements."
        ::= { strnAntennaConfig  7 }
        
   strnAntennaPeakEntry OBJECT-TYPE
       SYNTAX      StrnAntennaPeakEntry
       MAX-ACCESS  not-accessible
       STATUS      current
       DESCRIPTION     
           "An entry in the strnAntennaPeakTable."
       INDEX           { strnAntennaPeakIndex }
       ::= { strnAntennaPeakTable 1 }

    StrnAntennaPeakEntry ::= SEQUENCE {
        strnAntennaPeakIndex       	INTEGER,
        strnAntennaPeakAzimuth   	INTEGER,
        strnAntennaPeakElevation 	INTEGER,
        strnAntennaPeakRssi         INTEGER,        
        strnAntennaPeakSnr          INTEGER                                                         		   
    }    

   strnAntennaPeakIndex OBJECT-TYPE
       SYNTAX      INTEGER(1..15)
       MAX-ACCESS  not-accessible
       STATUS      current
       DESCRIPTION 
           "1..15 valid entries."
       ::= { strnAntennaPeakEntry 1 }
            
   strnAntennaPeakAzimuth OBJECT-TYPE
       SYNTAX      INTEGER 
       MAX-ACCESS  read-only
       STATUS      current
       DESCRIPTION 
           " -900..900 tenths of degrees round configured azimuth."
       ::= { strnAntennaPeakEntry 2 }    
                
   strnAntennaPeakElevation OBJECT-TYPE
       SYNTAX      INTEGER 
       MAX-ACCESS  read-only
       STATUS      current
       DESCRIPTION
           "-150..150  round to configured elevation. Values in tenths of degrees."
       ::= { strnAntennaPeakEntry 3 }        
                
   strnAntennaPeakRssi OBJECT-TYPE
       SYNTAX      INTEGER 
       MAX-ACCESS  read-only
       STATUS      current
       DESCRIPTION
           "-1000..300. Values in tenths of dBm. This value should be divided by 10 (/10) 
            in order to get the actual value e.g. a value of 173 stands for 173/10 = 17,3db."
       ::= { strnAntennaPeakEntry 4 }           
            
   strnAntennaPeakSnr OBJECT-TYPE
       SYNTAX      INTEGER 
       MAX-ACCESS  read-only
       STATUS      current
       DESCRIPTION
           "0..450. Values in tenths of dB. This value should be divided by 10 (/10) in order 
            to get the actual value e.g. a value of 173 stands for 173/10 = 17,3db."
       ::= { strnAntennaPeakEntry 5 }

   --===================================================================
   -- strnAntennaStartAction (SCALAR)
   --===================================================================  
   strnAntennaStartAction OBJECT-TYPE
       SYNTAX      INTEGER {noAction (0), 
                            startAlign (1), 
                            startFineTuning (2),
                            init(3),
                            park(4),
                            calibrate(5)}
       MAX-ACCESS  read-write
       STATUS      current
       DESCRIPTION 
           "On demand action related to STRN Antenna Alignment. 
            When init is ordered then move the antenna to the central position.
            When startAlign is ordered then antenna starts auto alignment.
            When startFineTuning is ordered then antenna starts Fine Tuning.
            When park is ordered then antenna parks to a specified position.
            When calibrate is ordered then antenna performs self-calibration, 
                for optimum antenna position tracking. This action may also 
                be performed automatically when required by the device.
            When an action is ordered to run then other running actions are cleared.
            The object is not persistent at system restart."
       ::= { strnAntennaConfig  8 }

   --================================================================ 
   -- STRN ANTENNA NOTIFICATIONS OBJECTS
   --================================================================
   strnAntennaNotificationObjects OBJECT IDENTIFIER 
   ::= { strnAntennaConfig  9}     
   
   strnAntennaFailureAlarm NOTIFICATION-TYPE
      OBJECTS {strnAntennaCurrentAntennaFailureAlarmStatus}
      STATUS current
      DESCRIPTION 
          " A trap indicating STRN Antenna Failure Alarm Status
            The NMS forwards the following information to the operator:
               varbind[0].oid = oid_sysUpTime.0 = 1.3.6.1.2.1.1.3.0
               varbind[0].val = NMS agent time (in centiseconds)
             
               varbind[1].oid = oid_snmpTrapOID.0 = 1.3.6.1.6.3.1.1.4.1.0
               varbind[1].val = oid_stnAntennaFailureAlarm
                              = 1.3.6.1.4.1.1807.55.1.3.9.1
               varbind[2].oid = oid_strnAntennaCurrentAntennaFailureAlarmStatus
                              = 1.3.6.1.4.1.1807.55.1.3.5.1.10
               varbind[2].val = strnAntennaCurrentAntennaFailureAlarmStatus
         "
     ::= { strnAntennaNotificationObjects 1}


   -- conformance information
   ptpMibConformance OBJECT IDENTIFIER ::= { modemConfigMibObjects  6 }

   ptpMibConfGroups      OBJECT IDENTIFIER ::= { ptpMibConformance 1 }

   ptpMibCompliances OBJECT IDENTIFIER ::= { ptpMibConformance 2 }

   -- compliance statements
   ptpMibCompliance MODULE-COMPLIANCE
   STATUS  current
   DESCRIPTION
         "The compliance statement for license entities"
      MODULE  -- this module
      MANDATORY-GROUPS { modemConfigGroup,
                         modemPHYModulationGroup,
                         modemStatusGroup,
                         modemPermormanceCountersGroup,
                         modemEthernetCountersGroup,
                         modemEthernetHcCountersGroup,
                         ptpNotificationObjectsGroup,
                         modemVersionGroup,
                         modemRemoteStatusGroup,
                         modemAdaptiveConfGroup,
                         xpicModemStatusCountersGroup,
                         acquireModemCountersGroup,
                         fecCountersGroup,
                         modemXpicGroupConfGroup,
                         modemThreshAlarmConfGroup,
                         g826CountersGroup,
                         ptpFlexModemMHSGroup,
                         oduConfigGroup,
                         oduCapabilitiesGroup,
                         oduStatusGroup,
                         oduAnalogueMonitorGroup,
                         oduVersionGroup,
                         oduAlarmConfigurationGroup,
                         oduNotificationObjectsGroup,
                         oduRFUConfTypeGroup,
                         oduRFUersionGroup,
                         oduServChanStatGroup,
                         modemClockSourceGroup,
                         strnAntennaGenConfigGroup,
                         strnAntennaAutoConfigGroup,
                         strnAntennaAutoFineConfigGroup,
                         strnAntennaManualConfigGroup,
                         strnAntennaCurrentStatusGroup,
                         strnAntennaMeasurementGroup,
                         strnAntennaPeakGroup,
                         strnAntennaNotificationObjectsGroup,
                         oduInterferenceScanConfigGroup,
                         oduInterferenceScanStatusGroup,
                         oduInterferenceScanMeasureGroup,
                         oduInventoryInfoGroup,
                         modemSuppCapabilitiesGroup,
                         modemSuppCapPhymodCapacityGroup,
                         modemRemoteAddressGroup,
                         modemTestGroup,
                         oduChannelTxFreqGroup,
                         ptpFlexModemPHCGroup
                         }
      ::= { ptpMibCompliances 1 }

   
   -- units of conformance   
   modemConfigGroup OBJECT-GROUP
   OBJECTS { --modemConfigEntryIndex,
             modemPHYprofile,
             modemACMmode,
             modemPHYmodulationVal,
             modemRestart,
             modemConfigDownLoadValues,
             modemLinkId,
             modemLinkIdCheck,
             modemRxSpectralInversion,
             modemTddRole,
             modemCfgTddTxRatio,
             modemCfgAirEncryptAdminState,
             modemCfgForceCfgSet
            }
   STATUS  current
   DESCRIPTION
         "A collection of objects providing the Modem Configuration general parameters information"
      ::= { ptpMibConfGroups 1 }
      
   modemPHYModulationGroup OBJECT-GROUP
   OBJECTS { --modemPHYModulationEntryIndex, 
             modemPHYDescription
   }
   STATUS  current
   DESCRIPTION
         "A collection of objects providing the modem PHY Modulation parameters."
      ::= { ptpMibConfGroups 2 }        

   modemStatusGroup OBJECT-GROUP
   OBJECTS { --modemStatusEntryIndex,
             modemStatTemperature,
             modemStatFail,
             modemStatLinkStatus,
             modemStatLinkError,
             modemStatLinkIndicator,
             modemStatPHYModValue,
             modemStatTxSymbolRate,
             modemStatRxNormalizedMSE,
             modemStatRxPHYModValue,
             rxLdpcDecodersStress,
             modemprotectionMode,
             modemPowerStatus,
             modemAlarmThreshStatus,
             modemTxAirthroughput,  
             modemRxAirthroughput, 
             modemStatusSuppCapTxPhymodId,
             modemStatusSuppCapRxPhymodId,
             modemStatusSuppCapId,
             modemActiveTddTxRatio,
             modemActiveTddRxRatio,
             modemStatusAirLinkDistance,
             modemStatusAirEncryptOperState,
             modemActualMaxATPCTxPower,
             modemActualMinATPCTxPower
        }
   STATUS  current
   DESCRIPTION
         "A collection of objects providing the modem Status information"
      ::= { ptpMibConfGroups 3 }        

   modemPermormanceCountersGroup OBJECT-GROUP
   OBJECTS { --modemPermormanceCountersEntryIndex,
             modemSecondsOutOfService,
             modemSecondsInService,
             modemNumberOfPhyChanges,             
             modemSecondsInPhyChanges1,
             modemSecondsInPhyChanges2,
             modemSecondsInPhyChanges3,
             modemSecondsInPhyChanges4,
             modemSecondsInPhyChanges5,
             modemSecondsInPhyChanges6,
             modemSecondsInPhyChanges7,
             modemSecondsInPhyChanges8,
             modemSecondsInPhyChanges9,
             modemSecondsInPhyChanges10,
             modemSecondsInPhyChanges11,
             modemSecondsInPhyChanges12,
             modemSecondsInPhyChanges13,
             modemSecondsInPhyChanges14,
             modemSecondsInPhyChanges15,
             modemSecondsInPhyChanges16,
             modemCountersControl,
             modemChangesInPHYMode1,
             modemChangesInPHYMode2,
             modemChangesInPHYMode3,
             modemChangesInPHYMode4,
             modemChangesInPHYMode5,
             modemChangesInPHYMode6,
             modemChangesInPHYMode7,
             modemChangesInPHYMode8,
             modemChangesInPHYMode9,
             modemChangesInPHYMode10,
             modemChangesInPHYMode11,
             modemChangesInPHYMode12,
             modemChangesInPHYMode13,
             modemChangesInPHYMode14,
             modemChangesInPHYMode15,
             modemChangesInPHYMode16      
             }
   STATUS  current
   DESCRIPTION
         "A collection of objects providing the modem performance counters information."
      ::= { ptpMibConfGroups 4 }        

   modemEthernetCountersGroup OBJECT-GROUP
   OBJECTS { --modemEthernetCountersEntryIndex, 
             modemEthTxPacketCounter,
             modemEthRxPacketCounter,
             modemEthRxCrcErrors,
             modemEthCountersControl,
             modemEthRxTruncatedFrames,
             modemEthRxLongEvents,
             modemEthRxVlanTagsDetected,
             modemEthRxUnsupportedOpCodes,
             modemEthRxpauseFrames,
             modemEthRxControlFrames,
             modemEthRxDribbleNibbles,
             modemEthRxBroadCasts,
             modemEthRxMultiCasts,
             modemEthRxOutOfRangeErrors,
             modemEthRxLengthCheckErrors,
             modemEthRxCodeErrors,
             modemEthRxFalseCarrierErrors,
             modemEthRxDvEvent,     
             modemEthRxPreviousPacketDropped,
             modemEthRxByteCounterLow,
             modemEthRxByteCounterHigh,
             modemEthRxBitRate,     
             modemEthTxVlanTags,    
             modemEthTxBackPressuresEvents,
             modemEthTxPauseFrames,
             modemEthTxControlFrames,
             modemEthTxWireByteCounterLow,
             modemEthTxWireByteCounterHigh,
             modemEthTxUnderRuns,   
             modemEthTxGiants,      
             modemEthTxLateCollisions,
             modemEthTxMaxCollisions,
             modemEthTxExcessiveDefers,
             modemEthTxNonExcessiveDefers,
             modemEthTxBroadCasts,  
             modemEthTxMulticasts,  
             modemEthTxReserved,    
             modemEthTxLengthCheckErrors,
             modemEthTxCrcErrors,   
             modemEthTxCollisions,  
             modemEthTxByteCounterLow,
             modemEthTxByteCounterHigh,
             modemEthTxBitRate,     
             modemEthCommulativeTime,
             modemEthRateTime,        
             modemEthRxBitRateHigh, 
             modemEthTxBitRateHigh,
             modemEthRxShortEvents}
   STATUS        current
   DESCRIPTION
           "A collection of objects providing the modem ethernet counters information."
   ::= { ptpMibConfGroups 5 }

   ptpNotificationObjectsGroup NOTIFICATION-GROUP
   NOTIFICATIONS { ptpModemFailureChange,              
             ptpmodemStatLinkStatusChange,       
             ptpRemoteModemStatLinkStatusChange, 
             ptpXpicModeAlarm,                   
             ptpmodemAlarmThreshStatusAlarm,
             ptpModemTxPHYModulationChange,
             ptpModemRxPHYModulationChange,
             ptpNeptuneYellowAlarm,
             ptpNeptuneRedAlarm,
             ptpModemPhymodLicenseFailure,
             ptpAtpcMaxTxPowerLicenseFail,
             ptpAtpcMinTxPowerLicenseFail,
             ptpAirEncryptionFailure,
             ptpModemTestNotification,
             ptpModemRemoteXPICStatusChange
             }
   STATUS        current
   DESCRIPTION
           "The collection of notifications related to ptp modems"
   ::= { ptpMibConfGroups 6 }

   modemVersionGroup OBJECT-GROUP
   OBJECTS { --modemVersionEntryIndex, 
             modemVersionStr, 
             fpgaVersion,
             slave1FpgaVersion}
   STATUS        current
   DESCRIPTION
           "A collection of objects providing the modem Versions information."
   ::= { ptpMibConfGroups 7 }

   modemRemoteStatusGroup OBJECT-GROUP
   OBJECTS { --modemRemoteStatusEntryIndex, 
             remoteModemLinkStatus,
             remoteModemIpAddress,
             remoteModemSlot,
             remoteModemLinkId,
             remoteModemLinkRebootMode}
   STATUS        current
   DESCRIPTION
           "A collection of objects providing the remote modem Status information."
   ::= { ptpMibConfGroups 8 }

   modemAdaptiveConfGroup OBJECT-GROUP
   OBJECTS { --modemAdaptiveConfEntryIndex,
             modemPowerMode,
             modemOptimumRSSI,      
             modemMaxAutoPHYmod,     
             modemMinAutoPHYmod,     
             modemAdaptiveConfDownLoadValues,
             modemMaxATPCTxPower,
             modemMinATPCTxPower,
             modemAutoMaxPowerMode
           }
   STATUS        current
   DESCRIPTION
           "A collection of objects providing the adaptive modem configuration information."
   ::= { ptpMibConfGroups 9 }

   xpicModemStatusCountersGroup OBJECT-GROUP
   OBJECTS { --xpicModemStatusCountersIndex,
             xpdStatusCounter, 
             xpicsweepStatus,
             xpdCalibration,
             xpicModemStatusRAITxMuted }
   STATUS        current
   DESCRIPTION
           "A collection of objects providing the cross polarization
                     interference cancellation modem status 
                     information."
   ::= { ptpMibConfGroups 10 }


   acquireModemCountersGroup OBJECT-GROUP
   OBJECTS { --acquireModemCountersIndex,
             numOfLolEvents,
             acquireModemCounterReset}
   STATUS        current
   DESCRIPTION
           "A collection of objects providing the acquire counters information"
   ::= { ptpMibConfGroups 11 }

   fecCountersGroup OBJECT-GROUP
   OBJECTS { --fecCountersIndex,
             fecBlockCounter,
             fecUncorBlockCounter,
             fecCountersReset }
   STATUS        current
   DESCRIPTION
           "A collection of objects providing the forward error correction information."
   ::= { ptpMibConfGroups 12 }

   modemXpicGroupConfGroup OBJECT-GROUP
   OBJECTS { --modemXpicConfIndex,  
             modemXpicConfEnabled,
             modemXpicConfPreambleType}
   STATUS        current
   DESCRIPTION
           "A collection of objects providing the configuration settings regarding Xpic modem functionality"
   ::= { ptpMibConfGroups 13 }

   modemThreshAlarmConfGroup OBJECT-GROUP
   OBJECTS { --modemThreshAlarmConfEntryIndex,  
              modemRxNormalizedMSEThresh,
              modemRxLdpcDecodersStressThresh,
	      muteRxModulationChangeTrap ,
	      muteTxModulationChangeTrap }
   STATUS        current
   DESCRIPTION
           "A collection of objects providing the modem threshhold Alarm Configuration information."
   ::= { ptpMibConfGroups 14 }

   g826CountersGroup OBJECT-GROUP
   OBJECTS { --g826CounterIndex,
             errorBlockCounter,
             backGroundBlockErrorsCounter,
             errorSecondsCounter,
             severelyErroredSecondsCounter,
             availlableSecCounter,
             unavailableSecondsCounter,
             g826CounterControl}
   STATUS        current
   DESCRIPTION
           "A collection of objects providing the G.826 performance 
            measurements on radio link."
   ::= { ptpMibConfGroups 15 }

ptpFlexModemMHSGroup OBJECT-GROUP
   OBJECTS { --ptpFlexModemMHSIndex ,        
               ptpFlexModemMHSSupprState,    
               ptpFlexModemMHSAging,         
               ptpFlexModemMHSRobustness,    
               ptpFlexModemMHSAutoResetTimer}
   STATUS        current
   DESCRIPTION
           "A collection of objects providing the MHS header suppresion."
   ::= { ptpMibConfGroups 16 }

   oduConfigGroup OBJECT-GROUP
   OBJECTS { --oduConfigEntryIndex,
             oduBandSelection,        
             oduSetTxFrequency,
             oduSetTxPower,  
             oduMute,
             oduLoop,
             oduRestart,
             oduConfigDownLoadValues,
             oduConfigPower,
             oduAutoUpdate, 
             oduUpdateNow,
             oduTestType,    
             oduTestTimeout, 
             oduTestTimer,
             oduCfgDuplexSpacing,
             oduCfgAntennaAlignMode}
   STATUS        current
   DESCRIPTION
           "A collection of objects providing the ODU Configuration general parameters information."
   ::= { ptpMibConfGroups 17 }


   oduCapabilitiesGroup OBJECT-GROUP
   OBJECTS {  --oduCapabilitiesEntryIndex,
              oduBand,
              oduSpectrumInversion,
              oduLoopBackSI,
              oduFirstFreq,  
              oduLastFreq,   
              oduFreqStep,   
              oduMaxTxPower,    
              oduMinTxPower,
              oduDuplexSpacing}
   STATUS        current
   DESCRIPTION
           "A collection of objects providing the ODU Capabilities information."
   ::= { ptpMibConfGroups 18 }

   oduStatusGroup OBJECT-GROUP
   OBJECTS { --oduStatusEntryIndex, 
             oduOperStatus,
             oduCurrentTxFrequency,
             oduCurrentTxPower,
             oduRadioAlarms,
             oduThresAlarms,
             oduPower,
             oduCurrentRxFrequency,
             oduStatusMute,
             oduUpdateStatus,
             oduGenConfigAlarm,
             oduStatusAntennaAlignMode,
             oduSlowFadingStatus,
             oduFastFadingStatus,
             oduCoChannelInterfereDetectStatus,
             oduStrongAdjChannelPresenceStatus,
             oduStatusBRAL,
             oduINRStatus,
             oduInterferenceDegrStatus,
             oduStatusDuplexerState}
   STATUS        current
   DESCRIPTION
           "A collection of objects providing the ODU Status information."
   ::= { ptpMibConfGroups 19 }

   oduAnalogueMonitorGroup OBJECT-GROUP
   OBJECTS { --oduAnalogueMonitorEntryIndex, 
             oduTemperature,
             oduRSSI,         
             oduPif,              
             oduPoutVdet,         
             oduMonitorPlus5V,    
             oduMonitorPlus7V,    
             oduMonitorMinus5V,   
             oduMonitorPlus6point5V,  
             oduMonitorMinus48V }
   STATUS        current
   DESCRIPTION
           "A collection of objects providing the ODU Analogue Monitor information."
   ::= { ptpMibConfGroups 20 }


   oduVersionGroup OBJECT-GROUP
   OBJECTS { --oduVersionEntryIndex, 
             oduModelType,
             oduSerialNumber,
             oduID,  
             oduVersion,
             oduSysSWver,
             oduProductCode,
             oduModelSubType,
             oduBootLoaderVersion,
             oduRadioModel,
             oduStringBootLoaderVersion}
   STATUS        current
   DESCRIPTION
           "A collection of objects providing the ODU Version information."
   ::= { ptpMibConfGroups 21 }


   oduAlarmConfigurationGroup OBJECT-GROUP
   OBJECTS { --oduAlarmConfigurationEntryIndex,
             oduPinRSSIThres,      
             oduTempThres,      
             oduAlarmConfDownLoadValues,
             oduAlarmConfTempLoThresh,
             oduAlarmConfLinkQualityAdminState,
             oduAlarmConfSupprState }
   STATUS        current
   DESCRIPTION
           "A collection of objects providing the ODU Alarm Configuration information"
   ::= { ptpMibConfGroups 22 }

   oduNotificationObjectsGroup NOTIFICATION-GROUP
   NOTIFICATIONS { oduOperationStatusFail,
             oduRadioAlarmsNotification,
             oduThresAlarmsNotification,
             oduUpdateStatAlarmsNotification,
             oduGenConfigAlarmNotification,
             oduTestNotification,
             oduTxPowerLicenseFailure,
             oduSlowFadingDetection,
             oduFastFadingDetection,
             oduCoChannelInterfereDetection,
             oduStrongAdjChannelPresence
              }
   STATUS        current
   DESCRIPTION
           "The collection of notifications related to ODUs"
   ::= { ptpMibConfGroups 23 }

   oduRFUConfTypeGroup OBJECT-GROUP
   OBJECTS { --oduCfgTypeIndex,
             oduConfigType,  
             oduActualType
            }
   STATUS  current
   DESCRIPTION
         "A collection of objects providing the ODU RFU Type Configuratuion information"
      ::= { ptpMibConfGroups 24 }

   oduRFUersionGroup OBJECT-GROUP
   OBJECTS  { --oduRFUVersionIndex,     
             oduRFUModelType,
             oduRFUModelNumber,
             oduRFUSerialNumber,
             oduRFUOEM,         
             oduRFUCLIE,  --It is not used      
             oduSWVersion, 
             oduUpdateSWVersion,
             oduRfuProductCode
            }
   STATUS  current
   DESCRIPTION
         "A collection of objects providing the ODU RFU Version information"
      ::= { ptpMibConfGroups 25 }

  oduServChanStatGroup OBJECT-GROUP
   OBJECTS  {--oduServChanStatIndex,      
             oduCrcErrors,            
             oduTotalCrcErrors,       
             iduCrcErrors,            
             oduDisconnects,          
             oduResetCmds,            
             oduCountCtrl,
             oduSfdAlarmsCounter,
             oduFfdAlarmsCounter,
             oduLinkQualityMonUpTime,
             oduCoChannelInterfereDetectAlarmsCounter,
             oduStrongAdjChannelPresenceAlarmsCounter}
   STATUS  current
   DESCRIPTION
         "A collection of objects providing the ODU 
          service channels counters "
      ::= { ptpMibConfGroups 26 }

modemClockSourceGroup OBJECT-GROUP
   OBJECTS { --modemClockSourceIndex,
               modemClockSource }
   STATUS        current
   DESCRIPTION
           "A collection of objects providing modem clock source."
   ::= { ptpMibConfGroups 27 }

strnAntennaGenConfigGroup OBJECT-GROUP
   OBJECTS { strnAntennaAlignConf,
             strnAntennaAzimuthRefPos
           }
   STATUS        current
   DESCRIPTION
           "A collection of objects providing Antenna general configuration."
   ::= { ptpMibConfGroups 28 }

strnAntennaAutoConfigGroup  OBJECT-GROUP
   OBJECTS { strnAntennaVerificationScan,
             strnAntennaSavedPeakDegrThresh,
             strnAntennaSavedPeakTestTimeout        
           }
   STATUS        current
   DESCRIPTION
           "A collection of objects providing Antenna Auto configuration."
   ::= { ptpMibConfGroups 29 }

strnAntennaAutoFineConfigGroup  OBJECT-GROUP
   OBJECTS { strnAntennaAutoFineTune,
             strnAntennaMaxFineTunes,
             strnAntennaAutoFineTuneDegrThresh,
             strnAntennaAutoFineTuneTimeout
           }
   STATUS        current
   DESCRIPTION
           "A collection of objects providing Antenna Auto Fine Tuning configuration."
   ::= { ptpMibConfGroups 30 }

strnAntennaManualConfigGroup  OBJECT-GROUP
   OBJECTS { strnAntennaCfgAzimuth,
             strnAntennaCfgElevation
           }
   STATUS        current
   DESCRIPTION
           "A collection of objects providing Antenna Manual configuration."
   ::= { ptpMibConfGroups 31 }

strnAntennaCurrentStatusGroup  OBJECT-GROUP
   OBJECTS { strnAntennaCurrentStatusAzimuth,
             strnAntennaCurrentStatusElevation,
             strnAntennaCurrentStatusRSSI,
             strnAntennaCurrentStatusSNR,
             strnAntennaCurrentStatusModemLock,
             strnAntennaCurrentStatusAlignmentState,
             strnAntennaCurrentStatusNumMeasurementElements,
             strnAntennaCurrentStatusNumPeakElements,
             strnAntennaCurrentAntennaFailureAlarmStatus,
             strnAntennaCurrentAntennaPolarization
           }
   STATUS        current
   DESCRIPTION
           "A collection of objects providing Antenna Alignment Current Status configuration."
   ::= { ptpMibConfGroups 32 }

strnAntennaMeasurementGroup  OBJECT-GROUP
   OBJECTS { strnAntennaMeasurementAzimuth,
             strnAntennaMeasurementElevation,
             strnAntennaMeasurementRssi,                                                  
             strnAntennaMeasurementSnr,
             strnAntennaMeasurementModemLock
           }
   STATUS        current
   DESCRIPTION
           "A collection of objects providing Antenna Measurement information."
   ::= { ptpMibConfGroups 33 }

strnAntennaPeakGroup   OBJECT-GROUP
   OBJECTS { strnAntennaPeakAzimuth,
             strnAntennaPeakElevation,
             strnAntennaPeakRssi,        
             strnAntennaPeakSnr,
             strnAntennaStartAction
           }
   STATUS        current
   DESCRIPTION
           "A collection of objects providing Antenna peak information."
   ::= { ptpMibConfGroups 34 }

strnAntennaNotificationObjectsGroup NOTIFICATION-GROUP
   NOTIFICATIONS { strnAntennaFailureAlarm
                 }
   STATUS        current
   DESCRIPTION
           "The collection of notifications related to STRN Antenna"
   ::= { ptpMibConfGroups 35 }


oduInterferenceScanConfigGroup  OBJECT-GROUP
   OBJECTS { oduInterferenceScanStep        
           }
   STATUS        current
   DESCRIPTION
           "A collection of objects providing ODU Interference Scan Configuration."
   ::= { ptpMibConfGroups 36 }

oduInterferenceScanStatusGroup  OBJECT-GROUP
   OBJECTS {oduInterferenceScanStatus,
            oduInterferenceScanStatusDateTime,
            oduInterferenceScanStatusAzimuth,
            oduInterferenceScanStatusElevation,
            oduInterferenceScanStatusLastStep,
            oduInterferenceScanStatusLastNoOfFreqs,
            oduInterferenceScanStatusMode,
            oduInterferenceScanStatusStartFreq,
            oduInterferenceScanStatusEndFreq,
            oduInterferenceScanStatusTotalNoOfFreqs
   }

   STATUS        current
   DESCRIPTION
           "A collection of objects providing ODU Interference Scan Status."
   ::= { ptpMibConfGroups 37 }

oduInterferenceScanMeasureGroup  OBJECT-GROUP
   OBJECTS {oduInterferenceScanMeasureCenterFreq,
            oduInterferenceScanMeasureRSSI,
            oduInterferenceScanAction                                                   		   
    }  

   STATUS        current
   DESCRIPTION
           "A collection of objects providing ODU Interference Scan Measurements."
   ::= { ptpMibConfGroups 38 }

oduInventoryInfoGroup  OBJECT-GROUP
   OBJECTS {oduZCode,
            oduZSerial,
            oduIfYCode,
            oduIfYSerial,
            oduTxRxYCode,
            oduTxRxYSerial
    }

   STATUS        current
   DESCRIPTION
           "A collection of objects providing SODU ODU version information."
   ::= { ptpMibConfGroups 39 }

modemSuppCapabilitiesGroup OBJECT-GROUP
   OBJECTS { --modemSuppCapabilitiesIndex,
             modemSuppCapModemType,
             modemSuppCapBitMap,
             modemSuppCapChannelBW,
             modemSuppCapPHYProfile,
             modemSuppCapPHYprofileVersion,
             modemSuppPhymodeBitMap,
             modemSuppTDDTxRatioBitMap
   }
   STATUS        current
   DESCRIPTION
           "A collection of objects providing the Supported Modem Capabilities."
   ::= { ptpMibConfGroups 40 }  

modemSuppCapPhymodCapacityGroup OBJECT-GROUP
   OBJECTS { --modemSuppCapabilitiesIndex,
             --modemSuppCapPhymodIndex,
             modemSuppCapPhymodName,
             modemSuppCapPhymodAirCapacity,
             modemSuppCapPhymodCfgId
   }
   STATUS        current
   DESCRIPTION
           "A collection of objects providing the Supported Capacities per PHYmode and Supported
            capabilities combination."
   ::= { ptpMibConfGroups 41 }
 
modemRemoteAddressGroup OBJECT-GROUP
   OBJECTS { --modemRemoteStatusEntryIndex,
             --modemRemoteAddressAddrType,
             --modemRemoteAddressAddr,      
             modemRemoteAddressRowStatus
   }
   STATUS        current
   DESCRIPTION
           "A collection of objects providing the Remote Modem IP address allocation information."
   ::= { ptpMibConfGroups 42 }

modemEthernetHcCountersGroup OBJECT-GROUP
   OBJECTS { --modemEthernetHcCountersEntryIndex, 
             modemEthHcTxPacketCounter,
             modemEthHcRxPacketCounter}
   STATUS        current
   DESCRIPTION
           "A collection of objects providing modem ethernet high capacity counters information."
   ::= { ptpMibConfGroups 43 }

modemTestGroup OBJECT-GROUP
   OBJECTS { --ModemTestEntryIndex,
             modemTestType,
             modemTestTimeout,
             modemTestTimer}
   STATUS        current
   DESCRIPTION
           "A collection of objects providing the Modem Test general parameters information."
   ::= { ptpMibConfGroups 44 }

oduChannelTxFreqGroup OBJECT-GROUP
   OBJECTS { oduMinTxFrequency,
             oduMaxTxFrequency}
   STATUS        current
   DESCRIPTION
           "A collection of objects providing the Min/Max Tx frequencies for a specific
           channel bandwidth."
   ::= { ptpMibConfGroups 45 }   

ptpFlexModemPHCGroup OBJECT-GROUP
   OBJECTS { --ptpFlexModemPHCIndex,
             ptpFlexModemPHCState,
             ptpFlexModemPHCAging,
             ptpFlexModemPHCRobustness,
             ptpFlexModemPHCMode,
             ptpFlexModemPHCAutoResetTimer
             }
   STATUS        current
   DESCRIPTION
           "A collection of objects providing the Modem PHC functionality."
   ::= { ptpMibConfGroups 46 }

   --================================================================
   --================================================================

   END
