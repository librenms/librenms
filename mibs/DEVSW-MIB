DEVSW-MIB DEFINITIONS ::= BEGIN

	IMPORTS
		OBJECT-TYPE, Integer32, MODULE-IDENTITY
			FROM SNMPv2-SMI
		DisplayString
			FROM SNMPv2-TC
		device
			FROM ANIROOT-MIB;


-- the aniDevSoftware group

aniDevSoftware  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	"This group provides information specific to the software image 
	 loaded on to the device and the configuration file downloaded.

	 Most of the objects are applicable to both the BSU and SU. 
	 However, a few parameters may be device specific, that is, 
	 applicable to only BSU or only SU. 
	 For eg. aniDevWSSOperatingSoftware is only valid for BSU and
	 not SU.
	"
	::= { device 2 }

aniDevSwConfigFile OBJECT-TYPE
	SYNTAX      DisplayString (SIZE (0..80))
	MAX-ACCESS  read-only
	STATUS      current
	DESCRIPTION
	   "The name of the device configuration file read from the 
	    TFTP server.
	   "
	--DEFAULT next-function-async     std_next_async
	::= { aniDevSoftware 1 }

aniDevSwSystemSoftwareFile  OBJECT-TYPE
	SYNTAX      DisplayString (SIZE(0..80))
	MAX-ACCESS  read-only
	STATUS      current
	DESCRIPTION
	   "The system software file name."
	--DEFAULT next-function-async     std_next_async
	::= { aniDevSoftware 2 }

aniDevSwWssSoftwareFile  OBJECT-TYPE
	SYNTAX      DisplayString (SIZE (0..80)) 
	MAX-ACCESS  read-only
	STATUS      current
	DESCRIPTION
	   "The WSS software file name for the BSU.

	    This parameter is applicable only for the BSU. 
	    When an SNMP Get request is sent on this parameter on a SU, 
	    an empty string is returned since it is not supported.
	    Similarly, when BSU is in point to point mode, this parameter
	    is not valid and returns an empty string. Also, for  
	    PacketWave 750, this parameter is not valid and displays 
	    an empty string."
	--DEFAULT next-function-async     std_next_async
	::= { aniDevSoftware 3 }

aniDevSwVersion OBJECT-TYPE
	SYNTAX      DisplayString (SIZE (0..16))
	MAX-ACCESS  read-only
	STATUS      current
	DESCRIPTION
	   "The Software Version.
	   "
	--DEFAULT next-function-async     std_next_async
	::= { aniDevSoftware 4 }

aniDevSwBuild OBJECT-TYPE
	SYNTAX      Integer32
	MAX-ACCESS  read-only
	STATUS      current
	DESCRIPTION
	   "The Software Build number.
	   "
	--DEFAULT next-function-async     std_next_async
	::= { aniDevSoftware 5 }

aniDevSwBuildDate OBJECT-TYPE
	SYNTAX      DisplayString (SIZE (0..22))
	MAX-ACCESS  read-only
	STATUS      current
	DESCRIPTION
	   "The Date of the Software Build.
	   "
	--DEFAULT next-function-async     std_next_async
	::= { aniDevSoftware 6 }

END
