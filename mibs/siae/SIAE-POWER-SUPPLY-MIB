-- ----------------------------------------------------------------------------
--
--  SIAE MICROELETTRONICA s.p.a.
--                 
--  Via Michelangelo Buonarroti, 21
--  20093 - Cologno Monzese
--  Milano 
--  ITALY
--
-- ----------------------------------------------------------------------------
-- ----------------------------------------------------------------------------

SIAE-POWER-SUPPLY-MIB
        DEFINITIONS ::= BEGIN

        IMPORTS
             MODULE-IDENTITY, OBJECT-TYPE,
             Integer32
        FROM SNMPv2-SMI
             DisplayString, RowStatus
        FROM SNMPv2-TC
             siaeMib
        FROM SIAE-TREE-MIB
             AlarmStatus, AlarmSeverityCode
        FROM SIAE-ALARM-MIB;

    pwrSupply MODULE-IDENTITY
        LAST-UPDATED "201410140000Z"
        ORGANIZATION "SIAE MICROELETTRONICA spa"
        CONTACT-INFO
            "SIAE MICROELETTONICA s.p.a.
             Via Michelangelo Buonarroti, 21
             20093 - Cologno Monzese
             Milano - ITALY
             Phone :  +39-02-27325-1
             E-mail: tbd@siaemic.com
            "
        DESCRIPTION
            "SIAE's Power Supply MIB.
            "
        REVISION "201410140000Z"
        DESCRIPTION 
            "Initial version 01.00.00
            "
      ::= { siaeMib 89 }

--------------------------------------------------------------------------------
--  POWER SUPPLY 
--------------------------------------------------------------------------------
--
-- This group is used to manage SIAE's power supply.
--
--------------------------------------------------------------------------------

------ Beginning --------------------------------------------------------------

    pwrSupplyMibVersion  OBJECT-TYPE
        SYNTAX      INTEGER
        MAX-ACCESS  read-only
        STATUS      current
        DESCRIPTION
            "Numerical version of this module.
             The string version of this MIB have the following format:
                XX.YY.ZZ
             so, for example, the value 1 should be interpreted as 00.00.01
             and the value 10001 should be interpreted as 01.00.01."
        DEFVAL {1}
    ::= {pwrSupply 1}

------  Begin of pwrSupplyTable
--

    pwrSupplyTable  OBJECT-TYPE
        SYNTAX      SEQUENCE OF PwrSupplyEntry
        MAX-ACCESS  not-accessible
        STATUS      current
        DESCRIPTION
            "Table with SIAE's Power Supply Entries."
    ::= {pwrSupply 2}

    pwrSupplyTableEntry  OBJECT-TYPE
        SYNTAX      PwrSupplyEntry
        MAX-ACCESS  not-accessible
        STATUS      current
        DESCRIPTION
            "SIAE's Power Supply entris. There is an entry for each power
             supply unit in the device."
        INDEX {pwrSupplyIndex}
    ::= {pwrSupplyTable 1}

    PwrSupplyEntry  ::=
        SEQUENCE {
            pwrSupplyIndex       Integer32,
            pwrSupplyRowStatus   RowStatus,
            pwrSupplyLabel       DisplayString,
            pwrSupplyAdminStatus INTEGER,
            pwrSupplyAlarm       AlarmStatus
         }

    pwrSupplyIndex  OBJECT-TYPE
        SYNTAX      Integer32
        MAX-ACCESS  not-accessible
        STATUS      current
        DESCRIPTION
            "A unique value, greater than zero, for each power supply unit."
    ::= {pwrSupplyTableEntry 1}

    pwrSupplyRowStatus  OBJECT-TYPE 
        SYNTAX      RowStatus
        MAX-ACCESS  read-create
        STATUS      current
        DESCRIPTION
            "Status of this row of pwrSupplyTable. A manager should not set
             this object. It is used by the agent to create relevant
             rows, depending on the HW configuration."
    ::= {pwrSupplyTableEntry 2}

    pwrSupplyLabel  OBJECT-TYPE
        SYNTAX      DisplayString (SIZE(0..63))
        MAX-ACCESS  read-only
        STATUS      current
        DESCRIPTION
            "A textual string containing information about the power supply
             unit."
    ::= {pwrSupplyTableEntry 3}

    pwrSupplyAdminStatus  OBJECT-TYPE
        SYNTAX      INTEGER {
                              disable (1),
                              enable  (2)
                    }
        MAX-ACCESS  read-create
        STATUS      current
        DESCRIPTION
            "The desired state of the Power supply.

             Only devices that allow the shutdown of a power supply accept
             the value disable(1).

             This object can be set only when the pwrSupplyRowStatus is active.
             
             Default value alfoplus2, alfo80hdx: disable
             Default value other equipment: enable
            "
    ::= {pwrSupplyTableEntry 4}

    pwrSupplyAlarm  OBJECT-TYPE
        SYNTAX      AlarmStatus
        MAX-ACCESS  read-only
        STATUS      current
        DESCRIPTION
            "The power supply has failed."
    ::= {pwrSupplyTableEntry 5}

--
------  End of pwrSupplyTable

    pwrSupplyAlarmSeverityCode  OBJECT-TYPE
        SYNTAX      AlarmSeverityCode
        MAX-ACCESS  read-write
        STATUS      current
        DESCRIPTION
            "Defines the severity associated to the pwrSupplyAlarm
             and enables/disables the trap generation on status change event."
        DEFVAL {majorTrapEnable}
    ::= {pwrSupply 3}

END
