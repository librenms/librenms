--
-- SamsungHost.mib
-- MIB generated by MG-SOFT Visual MIB Builder Version 3.0 Build 253
-- Thursday, April 05, 2007 at 11:01:52
--

	SAMSUNG-HOST-RESOURCES-EXT-MIB DEFINITIONS ::= BEGIN
 
		IMPORTS
			hrDeviceIndex
				FROM HOST-RESOURCES-MIB			
			samsungCommonMIB			
				FROM SAMSUNG-COMMON-MIB			
			OBJECT-GROUP			
				FROM SNMPv2-CONF			
			Integer32, Counter32, OBJECT-TYPE, MODULE-IDENTITY			
				FROM SNMPv2-SMI			
			TEXTUAL-CONVENTION			
				FROM SNMPv2-TC;
	
	
		scmHrMIB MODULE-IDENTITY 
			LAST-UPDATED "190407170000Z"		-- July 17, 1904 at 00:00 GMT
			ORGANIZATION 
				"Samsung Corporation - SCMI Working Group"
			CONTACT-INFO 
				"           SCMI Editors
				Email:      coherence@crt.samsung.com
				
				--
				--
				"
			DESCRIPTION 
				"Version:    1.00
				
				The MIB module for extended configuration and management of
				various host resources for network accessible host systems.
				This module augments and extends the original IETF Host
				Resources MIB (RFC 2790).
				
				Usage:  This MIB module introduces support for the 'realization'
				of both 'physical' and 'logical' devices, consistent with the
				Document Printing Application (DPA), ISO/IEC 10175, as reflected
				in the object 'scmHrDevInfoRealization'.
				
				Note:   Conforming implementations SHALL NOT 'bubble up' status
				from 'physical' devices to associated 'logical' devices.  All
				
				
				devices SHALL report their own status ONLY.
				
				See:    Section 9 'Supplement' in SCMI Extensions to IETF Host
				Resources TC, for implementation guidance for this MIB module.
				
				Copyright (C) 1995-2002 Samsung Corporation. All Rights Reserved."
			::= { samsungCommonMIB 53 }
		
	
--
-- Textual conventions
--
	
--  TEXTUAL-CONVENTIONs for this MIB module
-- 
-- Samsung Common MIB Count Info TEXTUAL-CONVENTIONs
-- 
		ScmHrDevCountJobTypeTC ::= TEXTUAL-CONVENTION
			STATUS current
			DESCRIPTION 
				"The type of count job."
			SYNTAX INTEGER
				{
				print(1),
				copy(2),
				faxIn(3),
				faxOut(4),
				scan(5),
				report(6),
				digitalSend(11),
				digitalRecieve(12),
				localStorage(21)				
				}
			
		ScmHrDevCountMediaSizeTC ::= TEXTUAL-CONVENTION
			STATUS current
			DESCRIPTION 
				"The size of media."
			SYNTAX INTEGER
				{
				small(1),
				large(2),
				letter(3),
				legal(4),
				a4(5),
				executive(6),
				jisB5(7),
				isoB5(8),
				com10(9),
				monarch(10),
				dl(11),
				c5(12),
				postA6(13),
				c6(14),
				folio(15),
				a5(16),
				statement(17),
				a6(18),
				ledger(19),
				a3(20),
				jisB4(21),
				jpost(22),
				jpostd(23),
				custom(24),
				letterP(25),
				a4P(26),
				jisB5P(27),
				a5P(28),
				executiveP(29),
				statementP(30),
				a3Over(31),
				b5Envelope(32)
				}
			
		ScmHrDevCountUnitTC ::= TEXTUAL-CONVENTION
			STATUS current
			DESCRIPTION 
				"The count unit of job count."
			SYNTAX INTEGER
				{
				other(1),
				unknown(2),
				tenThousandthsOfInches(3),
				micrometers(4),
				impressions(7),
				sheets(8),
				hours(11),
				thousandthsOfOunces(12),
				tenthsOfGrams(13),
				hundrethsOfFluidOunces(14),
				tenthsOfMilliliters(15),
				feet(16),
				meters(17),
				items(18),
				percent(19)
				}
			
		ScmHrDevCountDuplexTC ::= TEXTUAL-CONVENTION
			STATUS current
			DESCRIPTION 
				"The duplex type of job"
			SYNTAX INTEGER
				{
				simplex(1),
				duplex(2),
				duplexSingle(3)
				}
			
		ScmHrDevCountColorTC ::= TEXTUAL-CONVENTION
			STATUS current
			DESCRIPTION 
				"The color type of job"
			SYNTAX INTEGER
				{
				fullColor(1),
				singleColor(2),
				monoColor(3)
				}
			
	
--
-- Node definitions
--
	
		-- 1.3.6.1.4.1.236.11.5.11.53.2
		scmHrMIBConformance OBJECT IDENTIFIER ::= { scmHrMIB 2 }
		
		-- 1.3.6.1.4.1.236.11.5.11.53.2.2
		scmHrMIBGroups OBJECT IDENTIFIER ::= { scmHrMIBConformance 2 }
		
		-- 1.3.6.1.4.1.236.11.5.11.53.2.2.3
		scmHrDevInfoGroup OBJECT-GROUP
			OBJECTS { scmHrDevCountIndex, scmHrDevCountJobType, scmHrDevCountMediaSize, scmHrDevCountUnit, scmHrDevCountDuplex, 
				scmHrDevCountColor, scmHrDevCountValue }
			STATUS current
			DESCRIPTION 
				"The Host Resources Extensions MIB Device Info Group"
			::= { scmHrMIBGroups 3 }
		
		-- 1.3.6.1.4.1.236.11.5.11.53.11
		scmHrDevCount OBJECT IDENTIFIER ::= { scmHrMIB 11 }
		
		-- 1.3.6.1.4.1.236.11.5.11.53.11.1
		scmHrDevCountSimple OBJECT IDENTIFIER ::= { scmHrDevCount 1 }
		
		-- 1.3.6.1.4.1.236.11.5.11.53.11.2
		scmHrDevCountTable OBJECT-TYPE
			SYNTAX SEQUENCE OF ScmHrDevCountEntry
			MAX-ACCESS not-accessible
			STATUS current
			DESCRIPTION
				"Samsung Common Mib Host Resource Count MIB
				"
			::= { scmHrDevCount 2 }
		
		-- 1.3.6.1.4.1.236.11.5.11.53.11.2.1
		scmHrDevCountEntry OBJECT-TYPE
			SYNTAX ScmHrDevCountEntry
			MAX-ACCESS not-accessible
			STATUS current
			DESCRIPTION
				"An entry for a device alert which has been generated and
				recorded on this host system."
			REFERENCE
				"See:   'prtAlertEntry' in the Printer MIB."
			INDEX { hrDeviceIndex, scmHrDevCountIndex }
			::= { scmHrDevCountTable 1 }
		
		ScmHrDevCountEntry ::=
			SEQUENCE { 
				scmHrDevCountIndex
					Integer32,
				scmHrDevCountJobType
					ScmHrDevCountJobTypeTC,
				scmHrDevCountMediaSize
					ScmHrDevCountMediaSizeTC,
				scmHrDevCountUnit
					ScmHrDevCountUnitTC,
				scmHrDevCountDuplex
					ScmHrDevCountDuplexTC,
				scmHrDevCountColor
					ScmHrDevCountColorTC,
				scmHrDevCountValue
					Counter32
			 }

--  
-- Device Count Info
-- 
		-- 1.3.6.1.4.1.236.11.5.11.53.11.2.1.1
		scmHrDevCountIndex OBJECT-TYPE
			SYNTAX Integer32 (1..32767)
			MAX-ACCESS read-only
			STATUS current
			DESCRIPTION
				"A unique value used by the host to identify this Count item.
				This value indicate index of usage count value.
				If host device supports three count value (total page
				count, total color print count, total mono print count),
				this device has three count value and index."
			::= { scmHrDevCountEntry 1 }
		
		-- 1.3.6.1.4.1.236.11.5.11.53.11.2.1.2
		scmHrDevCountJobType OBJECT-TYPE
			SYNTAX ScmHrDevCountJobTypeTC
			MAX-ACCESS read-only
			STATUS current
			DESCRIPTION
				"scmHrDevCount defines items that are outside of the normal numeric range:  other(-1), unknown(-2).
				scm defines many a job type. but current samsung device supports counts of 
				print, fax, copy and scan job. Thus, the other items is not used. 
				"
			REFERENCE
				"
				"
			::= { scmHrDevCountEntry 2 }
		
		-- 1.3.6.1.4.1.236.11.5.11.53.11.2.1.3
		scmHrDevCountMediaSize OBJECT-TYPE
			SYNTAX ScmHrDevCountMediaSizeTC
			MAX-ACCESS read-only
			STATUS current
			DESCRIPTION
				"smcHrDevCount defines items that are outside of the normal numeric range:  other(-1), unknown(-2).
				
				scm defines many a size of media. But,
				We use 'small' or 'large' as media size so that application simply manage.
				"
			::= { scmHrDevCountEntry 3 }
		
		-- 1.3.6.1.4.1.236.11.5.11.53.11.2.1.4
		scmHrDevCountUnit OBJECT-TYPE
			SYNTAX ScmHrDevCountUnitTC
			MAX-ACCESS read-only
			STATUS current
			DESCRIPTION
				"smcHrDevCount define items that are outside of the normal numeric range:  other(-1), unknown(-2).
				PWG define count unit in printer mib(RFC1759, RFC3805).
				Default value is sheet(8), 
				but specifically use impression (for example OEM Model)."
			::= { scmHrDevCountEntry 4 }
		
		-- 1.3.6.1.4.1.236.11.5.11.53.11.2.1.5
		scmHrDevCountDuplex OBJECT-TYPE
			SYNTAX ScmHrDevCountDuplexTC
			MAX-ACCESS read-only
			STATUS current
			DESCRIPTION
				"smcHrDevCount define items that are outside of the normal numeric range:  
				other(-1), unknown(-2).
				samsung device suppor three duplex job type, simple, duplex, duplex(single).
				"
			::= { scmHrDevCountEntry 5 }
		
		-- 1.3.6.1.4.1.236.11.5.11.53.11.2.1.6
		scmHrDevCountColor OBJECT-TYPE
			SYNTAX ScmHrDevCountColorTC
			MAX-ACCESS read-only
			STATUS current
			DESCRIPTION
				"smcHrDevCount define items that are outside of the normal numeric range:  other(-1), unknown(-2).
				single-color is defined for extension of color job count."
			REFERENCE
				"smcHrDevCount define items that are outside of the normal numeric range:  other(-1), unknown(-2)."
			::= { scmHrDevCountEntry 6 }
		
		-- 1.3.6.1.4.1.236.11.5.11.53.11.2.1.7
		scmHrDevCountValue OBJECT-TYPE
			SYNTAX Counter32
			MAX-ACCESS read-only
			STATUS current
			DESCRIPTION
				"Value of usage count."
			::= { scmHrDevCountEntry 7 }
		
	
	END

--
-- SamsungHost.mib
--
