--  =============================================================================
--  Copyright (c) 2004-2019 New H3C Tech. Co., Ltd. All rights reserved.
--
--  Description: This MIB module contains managed object definitions for
--               Multiprotocol Extensions for BGP (MBGP or MP-BGP).
--  Reference: draft-ietf-idr-bgp4-mibv2-15
--  Version: V1.0
--  History:
--    V1.0 2019-07-04 Initial version Created by Gubin
--  =============================================================================
HH3C-BGP4V2-MIB DEFINITIONS ::= BEGIN

    IMPORTS
        OBJECT-TYPE, MODULE-IDENTITY, NOTIFICATION-TYPE
            FROM SNMPv2-SMI
        OBJECT-GROUP, MODULE-COMPLIANCE, NOTIFICATION-GROUP
            FROM SNMPv2-CONF
        InetAddressIPv6
            FROM INET-ADDRESS-MIB
        hh3cCommon
            FROM HH3C-OID-MIB;

--  =============================================================================
--  module identity part
--  =============================================================================
hh3cBgp4v2 MODULE-IDENTITY
    LAST-UPDATED "201907040000Z"        -- July 04, 2019 at 00:00 GMT
    ORGANIZATION
        "New H3C Technologies Co., Ltd."
    CONTACT-INFO
        "Platform Team New H3C Technologies Co., Ltd.
        Hai-Dian District Beijing P.R. China
        http://www.h3c.com
        Zip:100085"
    DESCRIPTION
        "The MIB module for the BGP4+ protocol."
    REVISION "201907040000Z"            -- July 04, 2019 at 00:00 GMT
    DESCRIPTION
        "This MIB updates the BGP MIB defined in
        RFC 4273."
    ::= { hh3cCommon 183 }

--  =============================================================================
--  hh3cBgp4v2Objects definition begin
--  =============================================================================
hh3cBgp4v2Objects OBJECT IDENTIFIER ::= { hh3cBgp4v2 1 }

hh3cBgp4v2PeerTable OBJECT-TYPE
    SYNTAX SEQUENCE OF Hh3cBgp4v2PeerEntry
    MAX-ACCESS not-accessible
    STATUS current
    DESCRIPTION
        "BGP peer table.  This table contains, one entry
        per BGP peer, information about the connections
        with BGP peers."
    ::= { hh3cBgp4v2Objects 1 }

hh3cBgp4v2PeerEntry OBJECT-TYPE
    SYNTAX Hh3cBgp4v2PeerEntry
    MAX-ACCESS not-accessible
    STATUS current
    DESCRIPTION
        "Entry containing information about the connection
        with a BGP peer."
    INDEX { hh3cBgp4v2PeerRemoteAddr }
    ::= { hh3cBgp4v2PeerTable 1 }

Hh3cBgp4v2PeerEntry ::=
    SEQUENCE {
        hh3cBgp4v2PeerRemoteAddr
            InetAddressIPv6,
        hh3cBgp4v2PeerLastError
            OCTET STRING,
        hh3cBgp4v2PeerState
            INTEGER
     }

hh3cBgp4v2PeerRemoteAddr OBJECT-TYPE
    SYNTAX InetAddressIPv6
    MAX-ACCESS accessible-for-notify
    STATUS current
    DESCRIPTION
        "The remote IPv6 address of this entry's BGP
        peer."
    ::= { hh3cBgp4v2PeerEntry 1 }

hh3cBgp4v2PeerLastError OBJECT-TYPE
    SYNTAX OCTET STRING (SIZE (2))
    MAX-ACCESS read-only
    STATUS current
    DESCRIPTION
        "The last error code and subcode seen by this
        peer on this connection.  If no error has
        occurred, this field is zero.  Otherwise, the
        first byte of this two byte OCTET STRING
        contains the error code, and the second byte
        contains the subcode."
    REFERENCE
        "RFC 4271, Section 4.5."
    ::= { hh3cBgp4v2PeerEntry 2 }

hh3cBgp4v2PeerState OBJECT-TYPE
    SYNTAX INTEGER
        {
        idle(1),
        connect(2),
        active(3),
        opensent(4),
        openconfirm(5),
        established(6)
        }
    MAX-ACCESS read-only
    STATUS current
    DESCRIPTION
        "The BGP peer connection state."
    REFERENCE
        "RFC 4271, Section 8.2.2."
    ::= { hh3cBgp4v2PeerEntry 3 }
--  ============================================================================
--  End of hh3cBgp4v2Objects Definition
--  ============================================================================

--  ============================================================================
--  Conformance Information
--  ============================================================================
hh3cBgp4v2Conformance OBJECT IDENTIFIER ::= { hh3cBgp4v2 2 }
hh3cBgp4v2Compliances OBJECT IDENTIFIER ::= { hh3cBgp4v2Conformance 1 }
hh3cBgp4v2Groups OBJECT IDENTIFIER ::= { hh3cBgp4v2Conformance 2 }

hh3cBgp4v2Compliance MODULE-COMPLIANCE
    STATUS current
    DESCRIPTION
        "The compliance statement for entities which implement the BGP4+
        mib."
    MODULE -- this module
        MANDATORY-GROUPS { hh3cBgp4v2ErrorsGroup, hh3cBgp4v2PeerGroup }
    GROUP hh3cBgp4v2NotificationGroup
    DESCRIPTION
        "Implementation of BGP Notifications are completely optional
        in this MIB."
    ::= { hh3cBgp4v2Compliances 1 }

hh3cBgp4v2ErrorsGroup OBJECT-GROUP
    OBJECTS { hh3cBgp4v2PeerLastError }
    STATUS current
    DESCRIPTION
        "Errors received on BGP peering sessions."
    ::= { hh3cBgp4v2Groups 1 }


hh3cBgp4v2PeerGroup OBJECT-GROUP
    OBJECTS { hh3cBgp4v2PeerState, hh3cBgp4v2PeerRemoteAddr }
    STATUS current
    DESCRIPTION
        "Core object types on BGP peering sessions."
    ::= { hh3cBgp4v2Groups 2 }


hh3cBgp4v2NotificationGroup NOTIFICATION-GROUP
    NOTIFICATIONS { hh3cBgp4v2Established, hh3cBgp4v2BackwardTransition }
    STATUS current
    DESCRIPTION
        "Notifications in this modules are completely optional."
    ::= { hh3cBgp4v2Groups 3 }

--  =============================================================================
--  End of Conformance Definition
--  =============================================================================

--  =============================================================================
--  Notifications Definition
--  =============================================================================
hh3cBgp4v2Notification OBJECT IDENTIFIER ::= { hh3cBgp4v2 0 }

hh3cBgp4v2Established NOTIFICATION-TYPE
    OBJECTS { hh3cBgp4v2PeerRemoteAddr, hh3cBgp4v2PeerLastError, hh3cBgp4v2PeerState }
    STATUS current
    DESCRIPTION
        "The hh3cBgp4v2Established event is generated when the BGP4+
        FSM enters the ESTABLISHED state."
    ::= { hh3cBgp4v2Notification 1 }

hh3cBgp4v2BackwardTransition NOTIFICATION-TYPE
    OBJECTS { hh3cBgp4v2PeerRemoteAddr, hh3cBgp4v2PeerLastError, hh3cBgp4v2PeerState }
    STATUS current
    DESCRIPTION
        "The hh3cBgp4v2BackwardTransition event is generated when
        the BGP4+ FSM moves from a higher numbered state to a lower
        numbered state.

        Due to the nature of the BGP state machine, an
        implementation MAY rate limit the generation of this event.
        An implementation MAY also generate this notification ONLY

        when the state machine moves out of the established state.
        An implementation should document its specific behavior."
    ::= { hh3cBgp4v2Notification 2 }
--  =============================================================================
--  End of Notifications Definition
--  =============================================================================

--  End of HH3C-BGP4V2-MIB
END
