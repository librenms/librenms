-- File Name : HORIZON-QUANTUM-MIB.mib
-- Version   : 1.2.5
-- Date      : Mar 19 2013
-- Author    : DragonWave Inc.

DRAGONWAVE-HORIZON-QUANTUM-MIB DEFINITIONS ::= BEGIN

IMPORTS
	MODULE-IDENTITY, NOTIFICATION-TYPE, OBJECT-TYPE,
	Counter32, TimeTicks, Counter64, IpAddress, Integer32
		FROM SNMPv2-SMI
	DisplayString
		FROM SNMPv2-TC
	ifIndex
		FROM RFC1213-MIB
	horizon
		FROM HORIZON-MIB;

hzQtmModIdentity MODULE-IDENTITY
	LAST-UPDATED "201003090930Z"
	ORGANIZATION
		"Dragonwave Inc."
	CONTACT-INFO
		"http://www.dragonwaveinc.com
		600-411 Legget Drive
		Ottawa, Ontario
		Canada, K2K 3C9

		Tel : 613-599-9991
		Fax: 613-599-4265
		Support: 613-271-7010"
	DESCRIPTION
		""
::= { horizonQuantum 1000 }


-- Important!! For HP OpenView, the following OID definition for ISO must be commented out,
-- otherwise it won't compile. HP openView has already defined ISO.
--      iso   OBJECT IDENTIFIER  ::=  { 1 }

horizonQuantum       OBJECT IDENTIFIER ::= { horizon 4 }

--
-- Node definitions
--

hzQtmSystem          OBJECT IDENTIFIER ::= { horizonQuantum 1 }

-- -------------
--   hzQtmSystem
-- -------------

hzQtmSysGeneral      OBJECT IDENTIFIER ::= { hzQtmSystem 1 }
hzQtmSysUpgradeSpeed  OBJECT IDENTIFIER ::= { hzQtmSystem 2 }
hzQtmSysDowngradeSpeed  OBJECT IDENTIFIER ::= { hzQtmSystem 3 }
hzQtmSysSpeed        OBJECT IDENTIFIER ::= { hzQtmSystem 4 }
hzQtmInventory       OBJECT IDENTIFIER ::= { hzQtmSystem 5 }

-- ----------------------------
--   hzQtmInventory
-- ----------------------------

hzQtmHwInventory     OBJECT IDENTIFIER ::= { hzQtmInventory 1 }
hzQtmSwInventory     OBJECT IDENTIFIER ::= { hzQtmInventory 2 }
hzQtmAtpc            OBJECT IDENTIFIER ::= { hzQtmSystem 6 }
hzQtmHitlessAam      OBJECT IDENTIFIER ::= { hzQtmSystem 7 }
hzQtmHitlessAamDiagnostics  OBJECT IDENTIFIER ::= { hzQtmHitlessAam 4 }
hzQtmPeerSysInfo     OBJECT IDENTIFIER ::= { hzQtmSystem 8 }
hzQtmBac             OBJECT IDENTIFIER ::= { hzQtmSystem 9 }
hzQtmSysDiagnostics  OBJECT IDENTIFIER ::= { hzQtmSystem 10 }
hzQtmSysLicensedFeatureGroups  OBJECT IDENTIFIER ::= { hzQtmSystem 11 }
hzQtmXpic            OBJECT IDENTIFIER ::= { hzQtmSystem 12 }
hzQtmPlcm            OBJECT IDENTIFIER ::= { hzQtmSystem 13 }
hzQtmBandwidthDoubling  OBJECT IDENTIFIER ::= { hzQtmSystem 14 }
hzQtmSyncE  OBJECT IDENTIFIER ::= { hzQtmSystem 15 }

hzQtmAuthentication  OBJECT IDENTIFIER ::= { horizonQuantum 2 }
hzQtmNetworkManagement  OBJECT IDENTIFIER ::= { horizonQuantum 3 }
hzQtmNetworkManagementInterface  OBJECT IDENTIFIER ::= { hzQtmNetworkManagement 8 }
hzQtmNetworkInterface  OBJECT IDENTIFIER ::= { horizonQuantum 4 }
hzQtmEnetPort        OBJECT IDENTIFIER ::= { hzQtmNetworkInterface 1 }
hzQtmAggregatedEnetPort  OBJECT IDENTIFIER ::= { hzQtmNetworkInterface 2 }
hzQtmAggregatedEnetPortConfig  OBJECT IDENTIFIER ::= { hzQtmAggregatedEnetPort 1 }
hzQtmAggregatedEnetPortStats  OBJECT IDENTIFIER ::= { hzQtmAggregatedEnetPort 2 }
hzQtmWirelessInterface  OBJECT IDENTIFIER ::= { horizonQuantum 5 }

-- ----------------------------
--   hzQtmWirelessInterface
-- ----------------------------

hzQtmWirelessInterfaceNames  OBJECT IDENTIFIER ::= { hzQtmWirelessInterface 1 }
hzQtmWirelessInterfaceModems  OBJECT IDENTIFIER ::= { hzQtmWirelessInterface 2 }
hzQtmWirelessInterfaceIF  OBJECT IDENTIFIER ::= { hzQtmWirelessInterface 3 }
hzQtmWirelessInterfaceRadios  OBJECT IDENTIFIER ::= { hzQtmWirelessInterface 4 }
hzQtmWirelessInterfaceRadioFrequencies  OBJECT IDENTIFIER ::= { hzQtmWirelessInterface 5 }

-- --------------------------------------
-- hzQtmWirelessInterfaceRadioFrequencies
-- --------------------------------------

hzQtmWirelessInterfaceRadio1Frequencies  OBJECT IDENTIFIER ::= { hzQtmWirelessInterfaceRadioFrequencies 1 }
hzQtmRadio1ProgrammedFrequency  OBJECT IDENTIFIER ::= { hzQtmWirelessInterfaceRadio1Frequencies 5 }
hzQtmWirelessInterfaceRadio2Frequencies  OBJECT IDENTIFIER ::= { hzQtmWirelessInterfaceRadioFrequencies 2 }
hzQtmRadio2ProgrammedFrequency  OBJECT IDENTIFIER ::= { hzQtmWirelessInterfaceRadio2Frequencies 5 }
hzQtmWirelessInterfaceAntenna  OBJECT IDENTIFIER ::= { hzQtmWirelessInterface 6 }
hzQtmWirelessInterfaceRedundancy  OBJECT IDENTIFIER ::= { hzQtmWirelessInterface 7 }
hzQtmWirelessInterfaceRedundancyDiagnostics  OBJECT IDENTIFIER ::= { hzQtmWirelessInterfaceRedundancy 6 }
hzQtmWirelessInterfaceRedundancyRadioSwitch  OBJECT IDENTIFIER ::= { hzQtmWirelessInterfaceRedundancy 7 }
hzQtmCalendar        OBJECT IDENTIFIER ::= { horizonQuantum 6 }
hzQtmAlarms          OBJECT IDENTIFIER ::= { horizonQuantum 7 }
hzQtmSystemAlarms    OBJECT IDENTIFIER ::= { hzQtmAlarms 2 }
hzQtmNetworkInterfaceAlarms  OBJECT IDENTIFIER ::= { hzQtmAlarms 3 }
hzQtmWirelessInterfaceAlarms  OBJECT IDENTIFIER ::= { hzQtmAlarms 4 }
hzQtmModemAlarms     OBJECT IDENTIFIER ::= { hzQtmWirelessInterfaceAlarms 1 }
hzQtmRadioAlarms     OBJECT IDENTIFIER ::= { hzQtmWirelessInterfaceAlarms 2 }
hzQtmIFAlarms        OBJECT IDENTIFIER ::= { hzQtmWirelessInterfaceAlarms 3 }
hzQtmTrapConfig      OBJECT IDENTIFIER ::= { horizonQuantum 8 }

-- ----------------------------
-- TRAP ENABLE
-- ----------------------------

hzQtmTrapEnable      OBJECT IDENTIFIER ::= { hzQtmTrapConfig 3 }
hzQtmSnmp            OBJECT IDENTIFIER ::= { horizonQuantum 9 }
hzQtmManagementSessions  OBJECT IDENTIFIER ::= { horizonQuantum 10 }
hzQtmHttp            OBJECT IDENTIFIER ::= { horizonQuantum 11 }
hzQtmHttpSecure      OBJECT IDENTIFIER ::= { hzQtmHttp 2 }
hzQtmQos             OBJECT IDENTIFIER ::= { horizonQuantum 12 }
hzQtmRapidLinkShutdown  OBJECT IDENTIFIER ::= { horizonQuantum 13 }

--
-- rlsStatus
--

hzQtmRlsStatus       OBJECT IDENTIFIER ::= { hzQtmRapidLinkShutdown 12 }
hzQtmRlsPortGroup    OBJECT IDENTIFIER ::= { hzQtmRapidLinkShutdown 13 }
hzQtmSntp            OBJECT IDENTIFIER ::= { horizonQuantum 14 }
hzQtmLogs            OBJECT IDENTIFIER ::= { horizonQuantum 15 }
hzQtmSysLog          OBJECT IDENTIFIER ::= { hzQtmLogs 4 }
hzQtmRadius          OBJECT IDENTIFIER ::= { horizonQuantum 16 }
hzQtmSnmpNotifications  OBJECT IDENTIFIER ::= { horizonQuantum 21 }

-- This node is reserved.

hzQtmReserved        OBJECT IDENTIFIER ::= { horizonQuantum 999 }

-- ----------------------------
--   hzQtmGeneral
-- ----------------------------

hzQtmResetSystem  OBJECT-TYPE
	SYNTAX     INTEGER {
		reset (1)
	}
	MAX-ACCESS read-write
	STATUS     current
	DESCRIPTION
		"Writing '1' to this object resets the NIC, Modem, and radio."
	::= { hzQtmSysGeneral 1 }

hzQtmSaveMIB  OBJECT-TYPE
	SYNTAX     INTEGER {
		save (1)
	}
	MAX-ACCESS read-write
	STATUS     current
	DESCRIPTION
		"Writing '1' or 'save' to this object save all MIB values."
	::= { hzQtmSysGeneral 2 }

hzQtmOperStatus  OBJECT-TYPE
	SYNTAX     INTEGER {
		up (1),
		down (2),
		testing (3)
	}
	MAX-ACCESS read-only
	STATUS     current
	DESCRIPTION
		"The current operational state of the system.
		Testing indicates that no operational packets can be passed."
	::= { hzQtmSysGeneral 3 }

hzQtmAirInterfaceEncryption  OBJECT-TYPE
	SYNTAX     INTEGER {
		disabled (1),
		enabled (2)
	}
	MAX-ACCESS read-only
	STATUS     current
	DESCRIPTION
		"OBSOLETE. This enables encryption on the air interface. "
	::= { hzQtmSysGeneral 4 }

hzQtmSystemCapacityOption  OBJECT-TYPE
	SYNTAX     INTEGER {
		singleModem-singleRadio (1),
		multiModem-singleRadio (2),
		multiModem-multiRadio (3),
		singleModem-redundancy (4),
		multiCarrierXpic (5)
	}
	MAX-ACCESS read-write
	STATUS     current
	DESCRIPTION
		"Sets the system capacity options. There are four options:
		Select 'singleModem-singleRadio' for a 400Mbps system.
		Select 'multiModem-singleRadio' for 800Mbps when the system is equipped with an internal or external IF Coupler.
		Select 'multiModem-multiRadio' for 800Mbps when the system is equipped with two radios connected to a Dual Polarization Radio Mount (DPRM).
		Select 'singleModem-redundancy' to provide a redundant 400Mbps link using a Redundant Dual Radio Mount (RDRM).
		Select 'multiCarrierXpic' when two systems are connected together to provide a four channels XPIC link.

		Notes:
		Setting the system capacity to 'singleModem-redundancy will fail if the primary path has not been set to either wireless_port1 or wireless_port2.
		Setting the system capacity to 'multiModem-multiRadio' will set the transmit power of wireless_port2 to the same transmite power as wireless_port1.
		Changing system capacity requires a reset in order to be activated."
	DEFVAL  { singleModem-singleRadio }
	::= { hzQtmSysGeneral 5 }

hzQtmSystemLedStatus  OBJECT-TYPE
	SYNTAX     DisplayString
	MAX-ACCESS read-only
	STATUS     current
	DESCRIPTION
		"Indicates the current LED status and colour."
	::= { hzQtmSysGeneral 6 }

hzQtmSaveL2SwConfig  OBJECT-TYPE
	SYNTAX     INTEGER {
		save (1)
	}
	MAX-ACCESS read-write
	STATUS     current
	DESCRIPTION
		"Writing '1' or 'save' to this object will save all L2 Switch config values."
	::= { hzQtmSysGeneral 7 }

hzQtmIduTemperature  OBJECT-TYPE
	SYNTAX     Integer32
	MAX-ACCESS read-only
	STATUS     current
	DESCRIPTION
		"The IDU temperature in degree Celsius. The actual temperature is determined by dividing the number by 100. e.g. 2825 is actually 28.25 degrees Celsius."
	::= { hzQtmSysGeneral 8 }

-- ----------------------------
--   hzQtmSysUpgradeSpeed
-- ----------------------------

hzQtmLicensedSpeedUpgradeSpeedAndKey  OBJECT-TYPE
	SYNTAX     DisplayString
	MAX-ACCESS read-write
	STATUS     current
	DESCRIPTION
		"Enter your key here along with the maximum speed for that key to upgrade the system.

		Format: [speed] [key]
		Example: 800 abc123"
	::= { hzQtmSysUpgradeSpeed 1 }

hzQtmLicensedSpeedCount  OBJECT-TYPE
	SYNTAX     Integer32
	MAX-ACCESS read-only
	STATUS     current
	DESCRIPTION
		"This object indicates the number of times the licensed speed has been changed successfully. It is used when generating new license keys for your system."
	::= { hzQtmSysUpgradeSpeed 2 }

-- ----------------------------
--   hzQtmSysDowngradeSpeed
-- ----------------------------

hzQtmLicensedSpeedDowngradeSpeed  OBJECT-TYPE
	SYNTAX     Integer32
	MAX-ACCESS read-write
	STATUS     current
	DESCRIPTION
		"Reduce your licensed speed by entering a speed to this write-only object and take note of the generated key in hzQtmDowngradeLicensedSpeedKey.

		Format: [speed]
		Example: 200"
	::= { hzQtmSysDowngradeSpeed 1 }

hzQtmLicensedSpeedCountUsedForKey  OBJECT-TYPE
	SYNTAX     Integer32
	MAX-ACCESS read-only
	STATUS     current
	DESCRIPTION
		"This object indicates the number of times the licensed speed has been changed successfully. It is used when generating new license keys for your system."
	::= { hzQtmSysDowngradeSpeed 2 }

hzQtmLicensedSpeedConfirmationKey  OBJECT-TYPE
	SYNTAX     DisplayString
	MAX-ACCESS read-only
	STATUS     current
	DESCRIPTION
		"This read-only object will show a 'key' after successfully downgrading the license speed."
	::= { hzQtmSysDowngradeSpeed 3 }

hzQtmSysDowngradeSpeedDecrement  OBJECT-TYPE
	SYNTAX     Integer32
	MAX-ACCESS read-only
	STATUS     current
	DESCRIPTION
		""
	::= { hzQtmSysDowngradeSpeed 4 }

-- ----------------------------
--   hzQtmSysSpeed
-- ----------------------------

hzQtmSystemCurrentSpeed  OBJECT-TYPE
	SYNTAX     Integer32 (0..2000)
	MAX-ACCESS read-write
	STATUS     current
	DESCRIPTION
		"Changes the working speed of the horizon. Writes are only valid if system is a FLEX. Due to backwards compatibility issue, 0 value should be treated as 0 Mbps."
	::= { hzQtmSysSpeed 1 }

hzQtmSystemLicensedSpeed  OBJECT-TYPE
	SYNTAX     Integer32 (0..2000)
	MAX-ACCESS read-only
	STATUS     current
	DESCRIPTION
		"Indicates the maximum speed that this system can operate at. Due to backwards compatibility issue, 0 value should be treated as 0 Mbps."
	::= { hzQtmSysSpeed 2 }

hzQtmSystemModeTable  OBJECT-TYPE
	SYNTAX SEQUENCE OF HzQtmSystemModeEntry
	MAX-ACCESS not-accessible
	STATUS     current
	DESCRIPTION
		"A table of system mode settings"
	::= { hzQtmSysSpeed 3 }

hzQtmSystemModeEntry  OBJECT-TYPE
	SYNTAX 	HzQtmSystemModeEntry
	MAX-ACCESS not-accessible
	STATUS     current
	DESCRIPTION
		"A system mode entry containing all the system mode values"
	INDEX { hzQtmSystemModeIndex }
	::= { hzQtmSystemModeTable 1 }

HzQtmSystemModeEntry ::= SEQUENCE {
	hzQtmSystemModeIndex
		Integer32,
	hzQtmSystemModeId
		Integer32,
	hzQtmSystemModeName
		DisplayString,
	hzQtmSystemModeProgrammed
		INTEGER
}

hzQtmSystemModeIndex  OBJECT-TYPE
	SYNTAX     Integer32
	MAX-ACCESS read-only
	STATUS     current
	DESCRIPTION
		"A unique value for each system mode. "
	::= { hzQtmSystemModeEntry 1 }

hzQtmSystemModeId  OBJECT-TYPE
	SYNTAX     Integer32
	MAX-ACCESS read-only
	STATUS     current
	DESCRIPTION
		"System mode Id. "
	::= { hzQtmSystemModeEntry 2 }

hzQtmSystemModeName  OBJECT-TYPE
	SYNTAX     DisplayString
	MAX-ACCESS read-only
	STATUS     current
	DESCRIPTION
		"The system mode name."
	::= { hzQtmSystemModeEntry 3 }

hzQtmSystemModeProgrammed  OBJECT-TYPE
	SYNTAX     INTEGER {
		active (1),
		notActive (2)
	}
	MAX-ACCESS read-write
	STATUS     current
	DESCRIPTION
		"Specifies the operating system mode for the modem.

		Notes:
		Only 1 index may be selected.
		Changing this option requires a system reset."
	DEFVAL  { notActive }
	::= { hzQtmSystemModeEntry 4 }

-- ----------------------------
--   hzQtmHwInventory
-- ----------------------------

hzQtmFrequencyFilePartNumber  OBJECT-TYPE
	SYNTAX     DisplayString
	MAX-ACCESS read-only
	STATUS     current
	DESCRIPTION
		"A textual string containing Part Number of the Frequency File"
	::= { hzQtmHwInventory 1 }

hzQtmUnitSerialNo  OBJECT-TYPE
	SYNTAX     DisplayString
	MAX-ACCESS read-only
	STATUS     current
	DESCRIPTION
		"A textual string containing Serial Number of the Unit."
	::= { hzQtmHwInventory 2 }

hzQtmUnitAssemblylNo  OBJECT-TYPE
	SYNTAX     DisplayString
	MAX-ACCESS read-only
	STATUS     current
	DESCRIPTION
		"A textual string containing the Assembly Number of the Unit."
	::= { hzQtmHwInventory 3 }

hzQtmCcaSerialNo  OBJECT-TYPE
	SYNTAX     DisplayString
	MAX-ACCESS read-only
	STATUS     current
	DESCRIPTION
		"A textual string containing Serial no of the NCC."
	::= { hzQtmHwInventory 4 }

hzQtmCcaPartNo  OBJECT-TYPE
	SYNTAX     DisplayString
	MAX-ACCESS read-only
	STATUS     current
	DESCRIPTION
		"A textual string containing assembly no of the NCC."
	::= { hzQtmHwInventory 5 }

hzQtmRadio1SerialNo  OBJECT-TYPE
	SYNTAX     DisplayString
	MAX-ACCESS read-only
	STATUS     current
	DESCRIPTION
		"A textual string containing the serial number of radio 1"
	::= { hzQtmHwInventory 6 }

hzQtmRadio2SerialNo  OBJECT-TYPE
	SYNTAX     DisplayString
	MAX-ACCESS read-only
	STATUS     current
	DESCRIPTION
		"A textual string containing the serial number of radio 2 if configured"
	::= { hzQtmHwInventory 7 }

hzQtmRadio1HardwareId  OBJECT-TYPE
	SYNTAX     DisplayString
	MAX-ACCESS read-only
	STATUS     current
	DESCRIPTION
		"A textual string containing the hardware id of radio 1"
	::= { hzQtmHwInventory 8 }

hzQtmRadio2HardwareId  OBJECT-TYPE
	SYNTAX     DisplayString
	MAX-ACCESS read-only
	STATUS     current
	DESCRIPTION
		"A textual string containing the hardware id of radio 2 if configured"
	::= { hzQtmHwInventory 9 }

hzQtmRadio1HardwareType  OBJECT-TYPE
	SYNTAX     DisplayString
	MAX-ACCESS read-only
	STATUS     current
	DESCRIPTION
		"A textual string containing the hardware type for radio 1"
	::= { hzQtmHwInventory 10 }

hzQtmRadio2HardwareType  OBJECT-TYPE
	SYNTAX     DisplayString
	MAX-ACCESS read-only
	STATUS     current
	DESCRIPTION
		"A textual string containing the hardware type for radio 2"
	::= { hzQtmHwInventory 11 }

-- ----------------------------
--   hzQtmSwInventory
-- ----------------------------

hzQtmSwInvAppOmniVersionNo  OBJECT-TYPE
	SYNTAX     DisplayString
	MAX-ACCESS read-only
	STATUS     current
	DESCRIPTION
		"The version number of the Omni."
	::= { hzQtmSwInventory 1 }

hzQtmSwInvAppFirmwareVersionNo  OBJECT-TYPE
	SYNTAX     DisplayString
	MAX-ACCESS read-only
	STATUS     current
	DESCRIPTION
		"The version number of the FPGA."
	::= { hzQtmSwInventory 2 }

hzQtmSwInvFrequencyFileVersionNo  OBJECT-TYPE
	SYNTAX     DisplayString
	MAX-ACCESS read-only
	STATUS     current
	DESCRIPTION
		"The version number of the FrequencyFile."
	::= { hzQtmSwInventory 3 }

hzQtmSwInvMibVersionNo  OBJECT-TYPE
	SYNTAX     DisplayString
	MAX-ACCESS read-only
	STATUS     current
	DESCRIPTION
		"The version number of the MIB."
	::= { hzQtmSwInventory 4 }

hzQtmSwInvRadioFirmware1VersionNo  OBJECT-TYPE
	SYNTAX     DisplayString
	MAX-ACCESS read-only
	STATUS     current
	DESCRIPTION
		"The radio firmware1 version."
	::= { hzQtmSwInventory 5 }

hzQtmSwInvRadioFirmware2VersionNo  OBJECT-TYPE
	SYNTAX     DisplayString
	MAX-ACCESS read-only
	STATUS     current
	DESCRIPTION
		"The radio firmware2 version."
	::= { hzQtmSwInventory 6 }

hzQtmSwInvAppSoftwareVersionNo  OBJECT-TYPE
	SYNTAX     DisplayString
	MAX-ACCESS read-only
	STATUS     current
	DESCRIPTION
		"The version number of the application software."
	::= { hzQtmSwInventory 7 }

hzQtmSwInvBootloaderVersionNo  OBJECT-TYPE
	SYNTAX     DisplayString
	MAX-ACCESS read-only
	STATUS     current
	DESCRIPTION
		"The bootloader version number."
	::= { hzQtmSwInventory 8 }

hzQtmSwInvSupportingAppVersionNo  OBJECT-TYPE
	SYNTAX     DisplayString
	MAX-ACCESS read-only
	STATUS     current
	DESCRIPTION
		"The version number for the third party applications such as ECFM etc..."
	::= { hzQtmSwInventory 9 }

hzQtmSwInvOperatingSystemVersionNo  OBJECT-TYPE
	SYNTAX     DisplayString
	MAX-ACCESS read-only
	STATUS     current
	DESCRIPTION
		"The version number of the running operating system."
	::= { hzQtmSwInventory 10 }

hzQtmSwInvRadio1CurrentFirmwareVersionNo  OBJECT-TYPE
	SYNTAX     DisplayString
	MAX-ACCESS read-only
	STATUS     current
	DESCRIPTION
		"The current running firmware version for Radio1."
	::= { hzQtmSwInventory 11 }

hzQtmSwInvRadio2CurrentFirmwareVersionNo  OBJECT-TYPE
	SYNTAX     DisplayString
	MAX-ACCESS read-only
	STATUS     current
	DESCRIPTION
		"The current running firmware version for Radio2."
	::= { hzQtmSwInventory 12 }

-- ----------------------------
--   hzQtmAtpc
-- ----------------------------

hzQtmAtpcEnable  OBJECT-TYPE
	SYNTAX     INTEGER {
		off (1),
		on (2)
	}
	MAX-ACCESS read-write
	STATUS     current
	DESCRIPTION
		"Indicates whether Automatic Transmit Power Control (ATPC) is enabled."
	DEFVAL  { off }
	::= { hzQtmAtpc 1 }

hzQtmAtpcStatus  OBJECT-TYPE
	SYNTAX     DisplayString
	MAX-ACCESS read-only
	STATUS     current
	DESCRIPTION
		"Indicates the actual condition of ATPC:
		Enabled – if config is on and no issues

		Auto-Disabled – when ATPC coordinated power alarm present

		Disabled-manual – if config set to off"
	::= { hzQtmAtpc 2 }

hzQtmAtpcCoordinatedPower  OBJECT-TYPE
	SYNTAX     DisplayString
	MAX-ACCESS read-write
	STATUS     current
	DESCRIPTION
		"
		The Coordinated Power can be enabled by specifying the coordinated power status and coordinated power offset in a string with the following format (without the single quotes):

		'<on [offset] | off>'

		The offset can optionally be specified after the 'on' string and after a single space and can be be between 0.0 and 10.0 inclusive.  The 'offset' is represented in dBm and indicates the offset below TxPower.  The accuracy is limited to tenths of dBm so an offset of 9.99 is recognized as 9.9 dBm.

		Examples: 'on 5.5' or 'off'"
	::= { hzQtmAtpc 3 }

-- ----------------------------
--   hzQtmHam
-- ----------------------------

hzQtmHitlessAamStatus  OBJECT-TYPE
	SYNTAX     INTEGER {
		off (1),
		on (2)
	}
	MAX-ACCESS read-write
	STATUS     current
	DESCRIPTION
		"Read or set the Hitless Automatic Adaptive Modulation (HAAM) as 'on' or 'off'.
		 HAAM feature is only available when system peer link compatibility mode is Quantum."
	DEFVAL  { off }
	::= { hzQtmHitlessAam 1 }

hzQtmHitlessAamManualMode  OBJECT-TYPE
	SYNTAX     INTEGER {
		off (1),
		on (2)
	}
	MAX-ACCESS read-write
	STATUS     current
	DESCRIPTION
		"Read or set the Hitless Automatic Adaptive Modulation (HAAM) Manual Mode as 'on' or 'off'."
	::= { hzQtmHitlessAam 2 }

-- ----------------
-- hzQtmHitlessAamTable
-- ----------------

hzQtmHitlessAamTable  OBJECT-TYPE
	SYNTAX SEQUENCE OF HzQtmHitlessAamEntry
	MAX-ACCESS not-accessible
	STATUS     current
	DESCRIPTION
		"A table of Hitless Aam."
	::= { hzQtmHitlessAam 3 }

hzQtmHitlessAamEntry  OBJECT-TYPE
	SYNTAX 	HzQtmHitlessAamEntry
	MAX-ACCESS not-accessible
	STATUS     current
	DESCRIPTION
		"Hitless Aam Status and Configurations."
	INDEX { hzQtmHitlessAamIndex }
	::= { hzQtmHitlessAamTable 1 }

HzQtmHitlessAamEntry ::= SEQUENCE {
	hzQtmHitlessAamIndex
		INTEGER,
	hzQtmHitlessAamCurrentMode
		DisplayString
}

hzQtmHitlessAamIndex  OBJECT-TYPE
	SYNTAX     INTEGER {
		wireless-port-1 (1),
		wireless-port-2 (2)
	}
	MAX-ACCESS read-only
	STATUS     current
	DESCRIPTION
		"A unique value for each interface. "
	::= { hzQtmHitlessAamEntry 1 }

hzQtmHitlessAamCurrentMode  OBJECT-TYPE
	SYNTAX     DisplayString (SIZE(0..24))
	MAX-ACCESS read-only
	STATUS     current
	DESCRIPTION
		"A read-only string specifing the currently running Hitless AAM Mode."
	::= { hzQtmHitlessAamEntry 2 }

-- ----------------------------
--   hzQtmAamDiagnostics
-- ----------------------------

hzQtmHitlessAamModem1Diagnose  OBJECT-TYPE
	SYNTAX     INTEGER {
		up (1),
		down (2)
	}
	MAX-ACCESS read-write
	STATUS     current
	DESCRIPTION
		"This service effecting write-only object accepts either 'up' or 'down' to diagnose whether the modulation speed can be increased or decreased respectively for modem1. Poll the hzQtmAamModem1DiagnosticResult object to determine the results."
	::= { hzQtmHitlessAamDiagnostics 1 }

hzQtmHitlessAamModem1DiagnosticResult  OBJECT-TYPE
	SYNTAX     DisplayString
	MAX-ACCESS read-only
	STATUS     current
	DESCRIPTION
		"The result from Hitless AAM Diagnostic for modem1 is read from this object."
	::= { hzQtmHitlessAamDiagnostics 2 }

hzQtmHitlessAamModem2Diagnose  OBJECT-TYPE
	SYNTAX     INTEGER {
		up (1),
		down (2)
	}
	MAX-ACCESS read-write
	STATUS     current
	DESCRIPTION
		"This service effecting write-only object accepts either 'up' or 'down' to diagnose whether the modulation speed can be increased or decreased respectively for modem2. Poll the hzQtmAamModem2DiagnosticResult object to determine the results."
	::= { hzQtmHitlessAamDiagnostics 3 }

hzQtmHitlessAamModem2DiagnosticResult  OBJECT-TYPE
	SYNTAX     DisplayString
	MAX-ACCESS read-only
	STATUS     current
	DESCRIPTION
		"The result from Hitless AAM Diagnostic for modem2 is read from this object."
	::= { hzQtmHitlessAamDiagnostics 4 }

-- ----------------
-- End of hzQtmHitlessAamDiagnostics
-- ----------------

hzQtmHitlessAamMaxMode  OBJECT-TYPE
	SYNTAX     DisplayString
	MAX-ACCESS read-write
	STATUS     current
	DESCRIPTION
		"Enter a string indicating the highest allowed system mode to be used for Hitless AAM. Example: hz50_364_256qam"
	::= { hzQtmHitlessAam 5 }

hzQtmHitlessAamMinMode  OBJECT-TYPE
	SYNTAX     DisplayString
	MAX-ACCESS read-write
	STATUS     current
	DESCRIPTION
		"Enter a string indicating the lowest allowed system mode to be used for Hitless AAM. Example: hz50_67_qpsk"
	::= { hzQtmHitlessAam 6 }

-- ----------------------
--  hzQtmPeerSysInfo
-- ---------------------

hzQtmPeerMacAddress  OBJECT-TYPE
	SYNTAX     DisplayString
	MAX-ACCESS read-only
	STATUS     current
	DESCRIPTION
		"The MAC Address of the peer network interface card."
	::= { hzQtmPeerSysInfo 1 }

hzQtmPeerIpAddress  OBJECT-TYPE
	SYNTAX     IpAddress
	MAX-ACCESS read-only
	STATUS     current
	DESCRIPTION
		"The IP Address of the peer network interface card."
	::= { hzQtmPeerSysInfo 2 }

hzQtmPeerSubnetMask  OBJECT-TYPE
	SYNTAX     IpAddress
	MAX-ACCESS read-only
	STATUS     current
	DESCRIPTION
		"The subnet mask for the peer network interface card."
	::= { hzQtmPeerSysInfo 3 }

hzQtmBacTable  OBJECT-TYPE
	SYNTAX SEQUENCE OF HzQtmBacEntry
	MAX-ACCESS not-accessible
	STATUS     current
	DESCRIPTION
		""
	::= { hzQtmBac 1 }

hzQtmBacEntry  OBJECT-TYPE
	SYNTAX 	HzQtmBacEntry
	MAX-ACCESS not-accessible
	STATUS     current
	DESCRIPTION
		""
	INDEX { hzQtmBacQIndex }
	::= { hzQtmBacTable 1 }

HzQtmBacEntry ::= SEQUENCE {
	hzQtmBacQIndex
		INTEGER,
	hzQtmBacQEnable
		INTEGER,
	hzQtmBacQBlockSize
		Integer32
}

hzQtmBacQIndex  OBJECT-TYPE
	SYNTAX     INTEGER {
		queue1 (1),
		queue2 (2),
		queue3 (3),
		queue4 (4)
	}
	MAX-ACCESS read-only
	STATUS     current
	DESCRIPTION
		"A unique value for each of the 4 Queues."
	::= { hzQtmBacEntry 1 }

hzQtmBacQEnable  OBJECT-TYPE
	SYNTAX     INTEGER {
		disabled (1),
		enabled (2)
	}
	MAX-ACCESS read-write
	STATUS     current
	DESCRIPTION
		"Configure Queue Compression state to disable/enable.
		 BAC feature is only available when system peer link compatibility mode is Quantum."
	::= { hzQtmBacEntry 2 }

hzQtmBacQBlockSize  OBJECT-TYPE
	SYNTAX     Integer32 (128..8000)
	MAX-ACCESS read-write
	STATUS     current
	DESCRIPTION
		"Configure Queue Compression block size (128...8000). Block size has to be in increments of 64 bytes. Otherwise it will be rounded off to nearest 64 bytes.
		Valid block sizes are <256 512 1024 4032 8000>
		"
	::= { hzQtmBacEntry 3 }

-- ----------------------
--  hzQtmLoopback
-- ---------------------

hzQtmIFPath1LoopbackAndTimeout  OBJECT-TYPE
	SYNTAX     DisplayString
	MAX-ACCESS read-write
	STATUS     current
	DESCRIPTION
		"To enable or disable IF path1 loopback. If timeout is not specified it's defaulted to 30 sec and if it's set to 0, infinite loopback is intended.

		Enter loopback on | off along with the timeout value.

		Format: [on | off] [timeout in sec]
		Example: on 40

		Enabling loopback is service disruptive."
	::= { hzQtmSysDiagnostics 1 }

hzQtmIFPath2LoopbackAndTimeout  OBJECT-TYPE
	SYNTAX     DisplayString
	MAX-ACCESS read-write
	STATUS     current
	DESCRIPTION
		"To enable or disable IF path2 loopback. If timeout is not specified it's defaulted to 30 sec and if it's set to 0, infinite loopback is intended.

		Enter loopback on | off along with the timeout value.

		Format: [on | off] [timeout in sec]
		Example: on 40

		Enabling loopback is service disruptive."
	::= { hzQtmSysDiagnostics 2 }

hzQtmRadio1LoopbackAndTimeout  OBJECT-TYPE
	SYNTAX     DisplayString
	MAX-ACCESS read-write
	STATUS     current
	DESCRIPTION
		"To enable or disable radio1 loopback. This feature is only supported when 1002+ radio is connected.

		If timeout is not specified it's defaulted to 30 sec and if it's set to 0, infinite loopback is intended.
		Enter loopback on | off along with the timeout value.

		Format: [on | off] [timeout in sec]
		Example: on 40

		Enabling loopback is service disruptive."
	::= { hzQtmSysDiagnostics 3 }

hzQtmRadio2LoopbackAndTimeout  OBJECT-TYPE
	SYNTAX     DisplayString
	MAX-ACCESS read-write
	STATUS     current
	DESCRIPTION
		"To enable or disable radio2 loopback. This feature is only supported when 1002+ radio is connected.

		If timeout is not specified it's defaulted to 30 sec and if it's set to 0, infinite loopback is intended.
		Enter loopback on | off along with the timeout value.

		Format: [on | off] [timeout in sec]
		Example: on 40

		Enabling loopback is service disruptive."
	::= { hzQtmSysDiagnostics 4 }

hzQtmSysUpgradeFeatureGroupsTable  OBJECT-TYPE
	SYNTAX SEQUENCE OF HzQtmSysUpgradeFeatureGroupsEntry
	MAX-ACCESS not-accessible
	STATUS     current
	DESCRIPTION
		"A table of system upgrade feature groups."
	::= { hzQtmSysLicensedFeatureGroups 1 }

hzQtmSysUpgradeFeatureGroupsEntry  OBJECT-TYPE
	SYNTAX 	HzQtmSysUpgradeFeatureGroupsEntry
	MAX-ACCESS not-accessible
	STATUS     current
	DESCRIPTION
		"A system upgrade feature group entry containing all licensed feature groups."
	INDEX { hzQtmUpgradeLicensedFeatureIndex }
	::= { hzQtmSysUpgradeFeatureGroupsTable 1 }

HzQtmSysUpgradeFeatureGroupsEntry ::= SEQUENCE {
	hzQtmUpgradeLicensedFeatureIndex
		INTEGER,
	hzQtmUpgradeLicensedFeatureKey
		DisplayString,
	hzQtmUpgradeLicensedFeatureCount
		Integer32
}

hzQtmUpgradeLicensedFeatureIndex  OBJECT-TYPE
	SYNTAX     INTEGER {
		xpic (1),
		bac (2),
		rlsEcfm (3),
		hitlessAam (4),
		dualWirelessPorts (5),
		l2switch (6)
	}
	MAX-ACCESS read-only
	STATUS     current
	DESCRIPTION
		"A unique value for each licensed group. Please note XPIC, HAAM and
		BAC feature is only available when system peer link compatibility mode is Quantum."
	::= { hzQtmSysUpgradeFeatureGroupsEntry 1 }

hzQtmUpgradeLicensedFeatureKey  OBJECT-TYPE
	SYNTAX     DisplayString
	MAX-ACCESS read-write
	STATUS     current
	DESCRIPTION
		"The key required for upgrading a feature."
	::= { hzQtmSysUpgradeFeatureGroupsEntry 2 }

hzQtmUpgradeLicensedFeatureCount  OBJECT-TYPE
	SYNTAX     Integer32
	MAX-ACCESS read-only
	STATUS     current
	DESCRIPTION
		"This object indicates the number of times the licensed feature has been changed successfully."
	::= { hzQtmSysUpgradeFeatureGroupsEntry 3 }

hzQtmSysDowngradeFeatureGroupsTable  OBJECT-TYPE
	SYNTAX SEQUENCE OF HzQtmSysDowngradeFeatureGroupsEntry
	MAX-ACCESS not-accessible
	STATUS     current
	DESCRIPTION
		"A table of system downgrade system groups."
	::= { hzQtmSysLicensedFeatureGroups 2 }

hzQtmSysDowngradeFeatureGroupsEntry  OBJECT-TYPE
	SYNTAX 	HzQtmSysDowngradeFeatureGroupsEntry
	MAX-ACCESS not-accessible
	STATUS     current
	DESCRIPTION
		"A system downgrade feature group entry containing all licensed feature groups."
	INDEX { hzQtmDowngradeLicensedFeatureIndex }
	::= { hzQtmSysDowngradeFeatureGroupsTable 1 }

HzQtmSysDowngradeFeatureGroupsEntry ::= SEQUENCE {
	hzQtmDowngradeLicensedFeatureIndex
		INTEGER,
	hzQtmDowngradeLicensedFeature
		INTEGER,
	hzQtmDowngradeLicensedFeatureCount
		Integer32,
	hzQtmDowngradeLicensedFeatureKey
		DisplayString
}

hzQtmDowngradeLicensedFeatureIndex  OBJECT-TYPE
	SYNTAX     INTEGER {
		xpic (1),
		bac (2),
		rlsEcfm (3),
		hitlessAam (4),
		dualWirelessPorts (5),
		l2switch (6)
	}
	MAX-ACCESS read-only
	STATUS     current
	DESCRIPTION
		"A unique value for each licensed group. "
	::= { hzQtmSysDowngradeFeatureGroupsEntry 1 }

hzQtmDowngradeLicensedFeature  OBJECT-TYPE
	SYNTAX     INTEGER {
		downgrade (1)
	}
	MAX-ACCESS read-write
	STATUS     current
	DESCRIPTION
		"Downgrading a licensed feature."
	::= { hzQtmSysDowngradeFeatureGroupsEntry 2 }

hzQtmDowngradeLicensedFeatureCount  OBJECT-TYPE
	SYNTAX     Integer32
	MAX-ACCESS read-only
	STATUS     current
	DESCRIPTION
		"This object indicates the number of times the licensed feature has been downgraded."
	::= { hzQtmSysDowngradeFeatureGroupsEntry 3 }

hzQtmDowngradeLicensedFeatureKey  OBJECT-TYPE
	SYNTAX     DisplayString
	MAX-ACCESS read-only
	STATUS     current
	DESCRIPTION
		"The key generated after downgrading a licensed feature."
	::= { hzQtmSysDowngradeFeatureGroupsEntry 4 }

hzQtmSysLicensedFeatureGroupsTable  OBJECT-TYPE
	SYNTAX SEQUENCE OF HzQtmSysLicensedFeatureGroupsEntry
	MAX-ACCESS not-accessible
	STATUS     current
	DESCRIPTION
		""
	::= { hzQtmSysLicensedFeatureGroups 3 }

hzQtmSysLicensedFeatureGroupsEntry  OBJECT-TYPE
	SYNTAX 	HzQtmSysLicensedFeatureGroupsEntry
	MAX-ACCESS not-accessible
	STATUS     current
	DESCRIPTION
		""
	INDEX { hzQtmSysLicensedFeatureGroupIndex }
	::= { hzQtmSysLicensedFeatureGroupsTable 1 }

HzQtmSysLicensedFeatureGroupsEntry ::= SEQUENCE {
	hzQtmSysLicensedFeatureGroupIndex
		INTEGER,
	hzQtmSysLicensedFeatureGroup
		DisplayString,
	hzQtmSysLicensedFeatureGroupStatus
		INTEGER
}

hzQtmSysLicensedFeatureGroupIndex  OBJECT-TYPE
	SYNTAX     INTEGER {
		xpic (1),
		bac (2),
		rlsEcfm (3),
		hitlessAam (4),
		dualWirelessPorts (5),
		l2switch (6)
	}
	MAX-ACCESS read-only
	STATUS     current
	DESCRIPTION
		"A unique value for each licensed group. "
	::= { hzQtmSysLicensedFeatureGroupsEntry 1 }

hzQtmSysLicensedFeatureGroup  OBJECT-TYPE
	SYNTAX     DisplayString
	MAX-ACCESS read-only
	STATUS     current
	DESCRIPTION
		"The name of the licensed feature group."
	::= { hzQtmSysLicensedFeatureGroupsEntry 2 }

hzQtmSysLicensedFeatureGroupStatus  OBJECT-TYPE
	SYNTAX     INTEGER {
		unlicensed (1),
		licensed (2)
	}
	MAX-ACCESS read-only
	STATUS     current
	DESCRIPTION
		"Specifies whether the feature group is unlicensed or licensed."
	::= { hzQtmSysLicensedFeatureGroupsEntry 3 }

-- ----------------------------
--   hzQtmXpic
-- ----------------------------

hzQtmXpicStatus  OBJECT-TYPE
	SYNTAX     INTEGER {
		off (1),
		on (2)
	}
	MAX-ACCESS read-write
	STATUS     current
	DESCRIPTION
		"Read or set the XPIC as 'on' or 'off'.
		 XPIC feature is only available when system peer link compatibility mode is Quantum."
	DEFVAL  { off }
	::= { hzQtmXpic 1 }

hzQtmXpicActualStatus  OBJECT-TYPE
	SYNTAX     INTEGER {
		off (1),
		on (2)
	}
	MAX-ACCESS read-only
	STATUS     current
	DESCRIPTION
		"Read the actual XPIC status as 'on' or 'off'.
		XPIC feature is only available when system peer link compatibility mode is Quantum."
	::= { hzQtmXpic 2 }

hzQtmXpicMode  OBJECT-TYPE
	SYNTAX     INTEGER {
		master (1),
		slave (2)
	}
	MAX-ACCESS read-write
	STATUS     current
	DESCRIPTION
		"Read or set the XPIC mode.
		The XPIC mode defines which system is controlling the radio (master) in a Multi Carrier XPIC configuration."
	::= { hzQtmXpic 3 }

-- ----------------------------
--   hzQtmPlcm
-- ----------------------------

hzQtmPlcmMode  OBJECT-TYPE
	SYNTAX     INTEGER {
		qtm (1),
		duo (2)
	}
	MAX-ACCESS read-only
	STATUS     current
	DESCRIPTION
		"Decides if the peer in the link is a Quantum or a Duo."
	::= { hzQtmPlcm 1 }

hzQtmPlcmConfigQtmAsDuo  OBJECT-TYPE
	SYNTAX     INTEGER {
		disabled (1),
		enabled (2)
	}
	MAX-ACCESS read-write
	STATUS     current
	DESCRIPTION
		"When enabled, a DUO compatible configuration is used when PLCM is configured as QTM."
	::= { hzQtmPlcm 2 }

hzQtmPlcmPeerOmniVersionTable  OBJECT-TYPE
	SYNTAX SEQUENCE OF HzQtmPlcmPeerOmniVersionEntry
	MAX-ACCESS not-accessible
	STATUS     current
	DESCRIPTION
		"A table of omni version of the peer when PLCM mode is configured as Duo"
	::= { hzQtmPlcm 3 }

hzQtmPlcmPeerOmniVersionEntry  OBJECT-TYPE
	SYNTAX 	HzQtmPlcmPeerOmniVersionEntry
	MAX-ACCESS not-accessible
	STATUS     current
	DESCRIPTION
		"A omni version of the peer when PLCM mode is configured as Duo entry containing all the omni version"
	INDEX { hzQtmPlcmPeerOmniVersionIndex }
	::= { hzQtmPlcmPeerOmniVersionTable 1 }

HzQtmPlcmPeerOmniVersionEntry ::= SEQUENCE {
	hzQtmPlcmPeerOmniVersionIndex
		Integer32,
	hzQtmPlcmPeerOmniVersionName
		DisplayString,
	hzQtmPlcmPeerOmniVersionProgrammed
		INTEGER
}

hzQtmPlcmPeerOmniVersionIndex  OBJECT-TYPE
	SYNTAX     Integer32
	MAX-ACCESS read-only
	STATUS     current
	DESCRIPTION
		"A unique value for each peer omni name. "
	::= { hzQtmPlcmPeerOmniVersionEntry 1 }

hzQtmPlcmPeerOmniVersionName  OBJECT-TYPE
	SYNTAX     DisplayString
	MAX-ACCESS read-only
	STATUS     current
	DESCRIPTION
		"The peer omni name."
	::= { hzQtmPlcmPeerOmniVersionEntry 2 }

hzQtmPlcmPeerOmniVersionProgrammed  OBJECT-TYPE
	SYNTAX     INTEGER {
		active (1),
		notActive (2)
	}
	MAX-ACCESS read-write
	STATUS     current
	DESCRIPTION
		"omni version of the peer when PLCM mode is configured as Duo.

		Notes:
		Only 1 index may be selected."
	DEFVAL  { notActive }
	::= { hzQtmPlcmPeerOmniVersionEntry 3 }

hzQtmPlcmMgtInterface  OBJECT-TYPE
	SYNTAX     INTEGER {
		inBand (1),
		outOfBand (2),
		port2extened (3)
	}
	MAX-ACCESS read-write
	STATUS     current
	DESCRIPTION
		"Decide the peer link management interface when PLCM mode is configured as a Duo."
	::= { hzQtmPlcm 4 }

hzQtmPlcmDataPort  OBJECT-TYPE
	SYNTAX     INTEGER {
		p1 (1),
		p2 (2),
		p3 (3),
		p4 (4),
		p5 (5),
		p6 (6),
		p7 (7),
		p8 (8)
	}
	MAX-ACCESS read-write
	STATUS     current
	DESCRIPTION
		"Describes the Ethernet traffic Port when PLCM mode is configured as a Duo.
		 Data port and management port have to be same when configured as 'inband'
		 management and data port and management port cannot be same for 'outOfBand'
		 and 'port2 extended' configuration."
	::= { hzQtmPlcm 5 }

hzQtmPlcmDataVlanTag  OBJECT-TYPE
	SYNTAX     Integer32 (1..4095)
	MAX-ACCESS read-write
	STATUS     current
	DESCRIPTION
		"Indicates the Vlan Tag Id (1...4095)for Ethernet data when PLCM mode is configured as a Duo."
	::= { hzQtmPlcm 6 }

hzQtmPlcmMgmtPort  OBJECT-TYPE
	SYNTAX     INTEGER {
		p1 (1),
		p2 (2),
		p3 (3),
		p4 (4),
		p5 (5),
		p6 (6),
		p7 (7),
		p8 (8)
	}
	MAX-ACCESS read-write
	STATUS     current
	DESCRIPTION
		"Describes the network management traffic port when PLCM mode is configured as a Duo.
		Data port and management port have to be same when configured as 'inband'
		 management and data port and management port cannot be same for 'outOfBand'
		 and 'port2 extended' configuration."
	::= { hzQtmPlcm 7 }

hzQtmPlcmMgmtVlanTagging  OBJECT-TYPE
	SYNTAX     INTEGER {
		disabled (1),
		enabled (2)
	}
	MAX-ACCESS read-write
	STATUS     current
	DESCRIPTION
		"Describes the network management traffic on has VLAN tagging on or not when PLCM mode is configured as a Duo."
	::= { hzQtmPlcm 8 }

hzQtmPlcmMgmtVlanTag  OBJECT-TYPE
	SYNTAX     Integer32 (1..4095)
	MAX-ACCESS read-write
	STATUS     current
	DESCRIPTION
		"Indicates the Vlan Tag Id (1...4095)for management data when PLCM mode is configured as a Duo."
	::= { hzQtmPlcm 9 }

hzQtmPlcmMgmtTagPriority  OBJECT-TYPE
	SYNTAX     Integer32 (0..7)
	MAX-ACCESS read-write
	STATUS     current
	DESCRIPTION
		"The priority for vlan tagging (0...7)for management data when PLCM mode is configured as a Duo."
	::= { hzQtmPlcm 10 }

hzQtmPlcmApplySaveResetSystem  OBJECT-TYPE
	SYNTAX     INTEGER {
		applySaveReset (1)
	}
	MAX-ACCESS read-write
	STATUS     current
	DESCRIPTION
		"Writing '1' to this object apply peer link compatibility mib changes,
		save the mib and resets the NIC, Modem, and radio."
	::= { hzQtmPlcm 20 }

-- ----------------------------
--   hzQtmXpic
-- ----------------------------

hzQtmBandwidthDoublingMode  OBJECT-TYPE
	SYNTAX     INTEGER {
		off (1),
		primary (2),
		secondary (3)
	}
	MAX-ACCESS read-write
	STATUS     current
	DESCRIPTION
		"Read or set bandwidth doubling mode."
	DEFVAL  { off }
	::= { hzQtmBandwidthDoubling 1 }

hzQtmBandwidthDoublingActualMode  OBJECT-TYPE
	SYNTAX     INTEGER {
		off (1),
		primary (2),
		secondary (3)
	}
	MAX-ACCESS read-only
	STATUS     current
	DESCRIPTION
		"Read the actual bandwidth doubling mode."
	::= { hzQtmBandwidthDoubling 2 }

hzQtmBandwidthDoublingPort  OBJECT-TYPE
	SYNTAX     INTEGER {
		enet-port-none (1),
		enet-port-1 (2),
		enet-port-2 (3),
		enet-port-3 (4),
		enet-port-4 (5),
		enet-port-5 (6),
		enet-port-6 (7),
		enet-port-7 (8),
		enet-port-8 (9)
	}
	MAX-ACCESS read-write
	STATUS     current
	DESCRIPTION
		"Read or set the bandwidth doubling data port interconnected between two systems."
	::= { hzQtmBandwidthDoubling 3 }

hzQtmBandwidthDoublingActualPort  OBJECT-TYPE
	SYNTAX     INTEGER {
		enet-port-none (1),
		enet-port-1 (2),
		enet-port-2 (3),
		enet-port-3 (4),
		enet-port-4 (5),
		enet-port-5 (6),
		enet-port-6 (7),
		enet-port-7 (8),
		enet-port-8 (9)
	}
	MAX-ACCESS read-only
	STATUS     current
	DESCRIPTION
		"Read the actual bandwidth doubling data port interconnected between two systems."
	::= { hzQtmBandwidthDoubling 4 }

-- - ----------------------------
--   hzQtmSyncE
-- ----------------------------

hzQtmSyncEMode  OBJECT-TYPE
	SYNTAX     INTEGER {
		off (1),
		manual (2),
		auto (3),
		esmc (4)
	}
	MAX-ACCESS read-write
	STATUS     current
	DESCRIPTION
		"Synchronous Ethernet support. When synchE is enabled, it can take clock from the following sources: free-run, Ethernet port3 to port8, wireless port1 or wireless port2.
		off: disables synchE support.
		manual: user specifies which port's incoming clock is to be used as clock source. If the specified port has no incoming clock, free-run will be used.
		auto: using user configured clock source prority, Quantum selects the best available clock as source.
		esmc: Quantum works in Ethernet Synchronization Messaging Channel mode. It supports Synchronous Status Message."
	DEFVAL  { off }
	::= { hzQtmSyncE 1 }

hzQtmSyncEPrimarySource  OBJECT-TYPE
	SYNTAX     INTEGER {
		p3 (1),
		p4 (2),
		p5 (3),
		p6 (4),
        p7 (5),
        p8 (6),
		wp1 (7),
        wp2 (8),
		free-run (9)
	}
	MAX-ACCESS read-write
	STATUS     current
	DESCRIPTION
		"Selects which port to be used as syncE primary clock source."
	::= { hzQtmSyncE 2 }

hzQtmSyncESecondarySource  OBJECT-TYPE
	SYNTAX     INTEGER {
		p3 (1),
		p4 (2),
		p5 (3),
		p6 (4),
        p7 (5),
        p8 (6),
		wp1 (7),
        wp2 (8),
		free-run (9)
	}
	MAX-ACCESS read-write
	STATUS     current
	DESCRIPTION
		"Selects which port to be used as syncE secondary when the master syncE is not available."
	::= { hzQtmSyncE 3 }

hzQtmSyncEMemberPorts  OBJECT-TYPE
	SYNTAX     DisplayString
	MAX-ACCESS read-write
	STATUS     current
	DESCRIPTION
		"Enter a string indicating all SyncE member ports.
		Example: p3 wp1
		Port options: p3 p4 p5 p6 p7 p8 wp1 wp2"
	::= { hzQtmSyncE 4 }

hzQtmSyncEForcedHoldover  OBJECT-TYPE
	SYNTAX     DisplayString
	MAX-ACCESS read-write
	STATUS     current
	DESCRIPTION
		"This forces SyncE into holdover mode. After the configurable timeout value, the forced holdover will be over. The forced timeout can be 0 to 300sec, 0 means infinite and default is 30sec."
	::= { hzQtmSyncE 5 }

hzQtmSyncERevertive  OBJECT-TYPE
	SYNTAX     DisplayString
	MAX-ACCESS read-write
	STATUS     current
	DESCRIPTION
		"In revertive mode, if the current source is secondary and the primary is Ok for configured amount of time, the primary will be used. The default revertive time is 10sec. "
	::= { hzQtmSyncE 6 }

hzQtmSyncEClockSource  OBJECT-TYPE
	SYNTAX     INTEGER {
		p3 (1),
		p4 (2),
		p5 (3),
		p6 (4),
        p7 (5),
        p8 (6),
		wp1 (7),
        wp2 (8),
		free-run (9)
	}
	MAX-ACCESS read-only
	STATUS     current
	DESCRIPTION
		"Retrieves Synce clock source."
	::= { hzQtmSyncE 7 }

hzQtmSyncEAcquisitionStatus  OBJECT-TYPE
	SYNTAX     DisplayString
	MAX-ACCESS read-only
	STATUS     current
	DESCRIPTION
		"Retrieves Synce acquisition status."
	::= { hzQtmSyncE 8 }

hzQtmSyncEWanderFilter  OBJECT-TYPE
	SYNTAX     INTEGER {
		option1 (1),
		option2 (2)
	}
	MAX-ACCESS read-write
	STATUS     current
	DESCRIPTION
		"ITU G.8262 specifies different wander filter requirements for networks based on the 2.048 kbit/s hiearchy , option1, vs those based on the 1.544kbit/s hiearchy, option2.  Option 2 specifies a low pass filter bandwidth of 0.1Hz, while option1 specifies a badwidth between 1 and10 Hz.  "
	::= { hzQtmSyncE 9 }






-- - ----------------------------
--   hzQtmAuthentication
-- ----------------------------

hzQtmUniquePeerAuthenticationKey  OBJECT-TYPE
	SYNTAX     DisplayString (SIZE(0..34))
	MAX-ACCESS read-write
	STATUS     current
	DESCRIPTION
		"The serial number of the peer node that this node will communicate with.
		 This is only used when authentication mode is set to unique."
	::= { hzQtmAuthentication 1 }

hzQtmPeerDetectedSerialNumber  OBJECT-TYPE
	SYNTAX     DisplayString
	MAX-ACCESS read-only
	STATUS     current
	DESCRIPTION
		"The serial number of the peer node that the system is presently communicating
		     with. This is only used when authentication is set to unique."
	::= { hzQtmAuthentication 2 }

hzQtmAuthenticationMode  OBJECT-TYPE
	SYNTAX     INTEGER {
		none (1),
		unique (2),
		group (3)
	}
	MAX-ACCESS read-write
	STATUS     current
	DESCRIPTION
		"This sets the authentication mode for the system.If configured for unique
		     authentication, an horizon node only exchanges user traffic with one other
		     horizon node. The serial number is used in this case.

		     If configured for group authentication, an horizon node exchanges user
		     traffic with another horizon node of the same group and uses the
		     authentication keys.

		     Note: Changing this option requires a system reset."
	DEFVAL  { none }
	::= { hzQtmAuthentication 3 }

hzQtmAuthenticationFailureAction  OBJECT-TYPE
	SYNTAX     INTEGER {
		blockTraffic (1),
		passTraffic (2)
	}
	MAX-ACCESS read-write
	STATUS     current
	DESCRIPTION
		"This sets the authentication failure action for the system.

		 Block traffic will block all user traffic including remote
		 management access.  Pass traffic will allow all user traffic
		 to be sent and recieved

		 Note: Changing this option requires a system reset."
	DEFVAL  { blockTraffic }
	::= { hzQtmAuthentication 4 }

hzQtmPeerAuthenticationStatus  OBJECT-TYPE
	SYNTAX     INTEGER {
		notAuthenticated (1),
		authenticated (2),
		explicitAuthenticationFailure (3)
	}
	MAX-ACCESS read-only
	STATUS     current
	DESCRIPTION
		"Specifies the current authentication status of the system.

		 Authenticated means authentication is on and the system
		 has been authenticated, notAuthenticated means authentication
		 is off or the system has not communicated yet with the other node,
		 explicit authentication failure means authentication is on and
		 authentication has failed"
	::= { hzQtmAuthentication 5 }

hzQtmGroupAuthenticationKey  OBJECT-TYPE
	SYNTAX     DisplayString (SIZE(0..34))
	MAX-ACCESS read-write
	STATUS     current
	DESCRIPTION
		"The serial number of the group that this node will communicate within.
		This is only used when authentication mode is set to group."
	::= { hzQtmAuthentication 6 }

--
-- NetworkManagement
--

hzQtmMacAddress  OBJECT-TYPE
	SYNTAX     DisplayString
	MAX-ACCESS read-only
	STATUS     current
	DESCRIPTION
		"The MAC Address of the network interface card."
	::= { hzQtmNetworkManagement 1 }

hzQtmIpAddress  OBJECT-TYPE
	SYNTAX     IpAddress
	MAX-ACCESS read-only
	STATUS     current
	DESCRIPTION
		"The IP Address of the network interface card.
		 Note: Changing IP Address requires a system reset."
	::= { hzQtmNetworkManagement 2 }

hzQtmSubnetMask  OBJECT-TYPE
	SYNTAX     IpAddress
	MAX-ACCESS read-only
	STATUS     current
	DESCRIPTION
		"The subnet mask for the network interface card.
		 Note: Changing Subnet Mask requires a system reset."
	::= { hzQtmNetworkManagement 3 }

hzQtmDefaultGateway  OBJECT-TYPE
	SYNTAX     IpAddress
	MAX-ACCESS read-only
	STATUS     current
	DESCRIPTION
		"The default gateway for the network interface card.
		 Note: Changing Default Gateway requires a system reset."
	::= { hzQtmNetworkManagement 4 }

hzQtmTelnetAccessMode  OBJECT-TYPE
	SYNTAX     INTEGER {
		disabled (1),
		enabled (2)
	}
	MAX-ACCESS read-write
	STATUS     current
	DESCRIPTION
		"Indicates whether Telnet access is allowed."
	DEFVAL  { enabled }
	::= { hzQtmNetworkManagement 5 }

hzQtmSshAccessMode  OBJECT-TYPE
	SYNTAX     INTEGER {
		disabled (1),
		enabled (2)
	}
	MAX-ACCESS read-write
	STATUS     current
	DESCRIPTION
		"Indicates whether ssh access is allowed."
	DEFVAL  { enabled }
	::= { hzQtmNetworkManagement 6 }

hzQtmNetMgmtPortList  OBJECT-TYPE
	SYNTAX     DisplayString
	MAX-ACCESS read-write
	STATUS     current
	DESCRIPTION
		"Describes the network management interface connection options. Enter a string indicating all management ports.

		Example: p1 p4 p6 dp3
		Switch Port options: p1 p2 p3 p4 p5 p6 p7 p8 dp1 dp2 dp3 dp4

		Note: Changing this option requires a system reset."
	::= { hzQtmNetworkManagementInterface 1 }

hzQtmNetMgmtVlanTagId  OBJECT-TYPE
	SYNTAX     Integer32 (1..4095)
	MAX-ACCESS read-write
	STATUS     current
	DESCRIPTION
		"Indicates the Vlan Tag Id (1...4095).

		Note: Changing this option requires a system reset."
	::= { hzQtmNetworkManagementInterface 2 }

hzQtmNetMgmtVlanTagPriority  OBJECT-TYPE
	SYNTAX     Integer32 (0..7)
	MAX-ACCESS read-write
	STATUS     current
	DESCRIPTION
		"The priority for vlan tagging (0...7)

		Note: Changing this option requires a system reset."
	::= { hzQtmNetworkManagementInterface 3 }

hzQtmEnetPortConfigTable  OBJECT-TYPE
	SYNTAX SEQUENCE OF HzQtmEnetPortConfigEntry
	MAX-ACCESS not-accessible
	STATUS     current
	DESCRIPTION
		""
	::= { hzQtmEnetPort 1 }

hzQtmEnetPortConfigEntry  OBJECT-TYPE
	SYNTAX 	HzQtmEnetPortConfigEntry
	MAX-ACCESS not-accessible
	STATUS     current
	DESCRIPTION
		""
	INDEX { hzQtmEnetPortIndex }
	::= { hzQtmEnetPortConfigTable 1 }

HzQtmEnetPortConfigEntry ::= SEQUENCE {
	hzQtmEnetPortIndex
		INTEGER,
	hzQtmEnetPortName
		DisplayString,
	hzQtmEnetPortAutoNegotiation
		INTEGER,
	hzQtmEnetPortSpeed
		INTEGER,
	hzQtmEnetPortDuplex
		INTEGER,
	hzQtmEnetPortMedia
		INTEGER,
	hzQtmEnetPortAdminState
		INTEGER,
	hzQtmEnetPortPauseFrame
		INTEGER,
	hzQtmEnetPortMaxFrameSize
		Integer32
}

hzQtmEnetPortIndex  OBJECT-TYPE
	SYNTAX     INTEGER {
		enet-port-1 (1),
		enet-port-2 (2),
		enet-port-3 (3),
		enet-port-4 (4),
		enet-port-5 (5),
		enet-port-6 (6),
		enet-port-7 (7),
		enet-port-8 (8)
	}
	MAX-ACCESS read-only
	STATUS     current
	DESCRIPTION
		""
	::= { hzQtmEnetPortConfigEntry 1 }

--
-- PORT CONFIG
--

hzQtmEnetPortName  OBJECT-TYPE
	SYNTAX     DisplayString
	MAX-ACCESS read-only
	STATUS     current
	DESCRIPTION
		"Describes the port interface name"
	::= { hzQtmEnetPortConfigEntry 2 }

hzQtmEnetPortAutoNegotiation  OBJECT-TYPE
	SYNTAX     INTEGER {
		on (1),
		off (2)
	}
	MAX-ACCESS read-write
	STATUS     current
	DESCRIPTION
		"Turns auto-negotiation on or off for Ethernet Port. Turning off results in the interface defaulting to 100BaseT, Full Duplex. "
	::= { hzQtmEnetPortConfigEntry 3 }

hzQtmEnetPortSpeed  OBJECT-TYPE
	SYNTAX     INTEGER {
		x10M (1),
		x100M (2),
		x1000M (3),
		auto (4)
	}
	MAX-ACCESS read-write
	STATUS     current
	DESCRIPTION
		"Configure the port interface speed ."
	::= { hzQtmEnetPortConfigEntry 4 }

hzQtmEnetPortDuplex  OBJECT-TYPE
	SYNTAX     INTEGER {
		full (1),
		half (2),
		auto (3)
	}
	MAX-ACCESS read-write
	STATUS     current
	DESCRIPTION
		"Configure the port interface duplex."
	::= { hzQtmEnetPortConfigEntry 5 }

hzQtmEnetPortMedia  OBJECT-TYPE
	SYNTAX     INTEGER {
		copper (1),
		sfp (2),
		auto (3)
	}
	MAX-ACCESS read-only
	STATUS     current
	DESCRIPTION
		"Configure the port interface media."
	::= { hzQtmEnetPortConfigEntry 6 }

hzQtmEnetPortAdminState  OBJECT-TYPE
	SYNTAX     INTEGER {
		on (1),
		off (2)
	}
	MAX-ACCESS read-write
	STATUS     current
	DESCRIPTION
		"Enable or disable the admin status of the port."
	::= { hzQtmEnetPortConfigEntry 7 }

hzQtmEnetPortPauseFrame  OBJECT-TYPE
	SYNTAX     INTEGER {
		disabled (1),
		enableRx (2),
		enableTx (3),
		enableBoth (4)
	}
	MAX-ACCESS read-write
	STATUS     current
	DESCRIPTION
		"When PAUSE is enabled, port pause frames can be generated by the system and the pause frames will flow toward the link partner on the network.  Pause frams can be enabled for Rx, Tx or both.
		When PAUSE is not enabled, no pause frames will be generated by the system. "
	DEFVAL  { disabled }
	::= { hzQtmEnetPortConfigEntry 8 }

hzQtmEnetPortMaxFrameSize  OBJECT-TYPE
	SYNTAX     Integer32 (1600..9600)
	MAX-ACCESS read-write
	STATUS     current
	DESCRIPTION
		"The default maximum frame size is 1600 bytes.
		 The settable lowest maximum frame size is 1600, and the settable
		                                         highest maximum frame size is 9600. If the chosen maximum
		                                         frame size is out of this range, the default maximum frame
		                                         size of 1600 is used. "
	DEFVAL  { 1600 }
	::= { hzQtmEnetPortConfigEntry 9 }

hzQtmEnetPortStatusTable  OBJECT-TYPE
	SYNTAX SEQUENCE OF HzQtmEnetPortStatusEntry
	MAX-ACCESS not-accessible
	STATUS     current
	DESCRIPTION
		""
	::= { hzQtmEnetPort 2 }

hzQtmEnetPortStatusEntry  OBJECT-TYPE
	SYNTAX 	HzQtmEnetPortStatusEntry
	MAX-ACCESS not-accessible
	STATUS     current
	DESCRIPTION
		""
	INDEX { hzQtmEnetPortStatusIndex }
	::= { hzQtmEnetPortStatusTable 1 }

HzQtmEnetPortStatusEntry ::= SEQUENCE {
	hzQtmEnetPortStatusIndex
		INTEGER,
	hzQtmEnetPortLinkStatus
		INTEGER,
	hzQtmEnetPortAutoNegotiationStatus
		INTEGER,
	hzQtmEnetPortSpeedStatus
		INTEGER,
	hzQtmEnetPortDuplexStatus
		INTEGER,
	hzQtmEnetPortMediaStatus
		INTEGER
}

hzQtmEnetPortStatusIndex  OBJECT-TYPE
	SYNTAX     INTEGER {
		enet-port-1 (1),
		enet-port-2 (2),
		enet-port-3 (3),
		enet-port-4 (4),
		enet-port-5 (5),
		enet-port-6 (6),
		enet-port-7 (7),
		enet-port-8 (8)
	}
	MAX-ACCESS read-only
	STATUS     current
	DESCRIPTION
		""
	::= { hzQtmEnetPortStatusEntry 1 }

--
-- PORT STATUS
--

hzQtmEnetPortLinkStatus  OBJECT-TYPE
	SYNTAX     INTEGER {
		down (1),
		up (2),
		invalid (3)
	}
	MAX-ACCESS read-only
	STATUS     current
	DESCRIPTION
		"Indicates the port link status."
	::= { hzQtmEnetPortStatusEntry 2 }

hzQtmEnetPortAutoNegotiationStatus  OBJECT-TYPE
	SYNTAX     INTEGER {
		on (1),
		off (2),
		invalid (3)
	}
	MAX-ACCESS read-only
	STATUS     current
	DESCRIPTION
		"Indicates the port AutoNegotiation status."
	::= { hzQtmEnetPortStatusEntry 3 }

hzQtmEnetPortSpeedStatus  OBJECT-TYPE
	SYNTAX     INTEGER {
		x10M (1),
		x100M (2),
		x1000M (3),
		auto (4),
		invalid (5)
	}
	MAX-ACCESS read-only
	STATUS     current
	DESCRIPTION
		"Indicates the port interface speed status."
	::= { hzQtmEnetPortStatusEntry 4 }

hzQtmEnetPortDuplexStatus  OBJECT-TYPE
	SYNTAX     INTEGER {
		full (1),
		half (2),
		auto (3),
		invalid (4)
	}
	MAX-ACCESS read-only
	STATUS     current
	DESCRIPTION
		"Indicates the port interface duplex status."
	::= { hzQtmEnetPortStatusEntry 5 }

hzQtmEnetPortMediaStatus  OBJECT-TYPE
	SYNTAX     INTEGER {
		copper (1),
		fiber (2),
		auto (3),
		invalid (4)
	}
	MAX-ACCESS read-only
	STATUS     current
	DESCRIPTION
		"Indicates the port interface media status."
	::= { hzQtmEnetPortStatusEntry 6 }

hzQtmEnetPortStatsTable  OBJECT-TYPE
	SYNTAX SEQUENCE OF HzQtmEnetPortStatsEntry
	MAX-ACCESS not-accessible
	STATUS     current
	DESCRIPTION
		""
	::= { hzQtmEnetPort 3 }

hzQtmEnetPortStatsEntry  OBJECT-TYPE
	SYNTAX 	HzQtmEnetPortStatsEntry
	MAX-ACCESS not-accessible
	STATUS     current
	DESCRIPTION
		""
	INDEX { hzQtmEnetPortStatsIndex }
	::= { hzQtmEnetPortStatsTable 1 }

HzQtmEnetPortStatsEntry ::= SEQUENCE {
	hzQtmEnetPortStatsIndex
		INTEGER,
	hzQtmEnetPortRxBytes
		Counter64,
	hzQtmEnetPortRxUcastPkts
		Counter64,
	hzQtmEnetPortRxNUcastPkts
		Counter64,
	hzQtmEnetPortRxDiscards
		Counter64,
	hzQtmEnetPortRxErrors
		Counter64,
	hzQtmEnetPortRxUnknownProtos
		Counter64,
	hzQtmEnetPortTxBytes
		Counter64,
	hzQtmEnetPortTxUcastPkts
		Counter64,
	hzQtmEnetPortTxNUcastPkts
		Counter64,
	hzQtmEnetPortTxDiscards
		Counter64,
	hzQtmEnetPortTxErrors
		Counter64
}

hzQtmEnetPortStatsIndex  OBJECT-TYPE
	SYNTAX     INTEGER {
		enet-port-1 (1),
		enet-port-2 (2),
		enet-port-3 (3),
		enet-port-4 (4),
		enet-port-5 (5),
		enet-port-6 (6),
		enet-port-7 (7),
		enet-port-8 (8)
	}
	MAX-ACCESS read-only
	STATUS     current
	DESCRIPTION
		""
	::= { hzQtmEnetPortStatsEntry 1 }

hzQtmEnetPortRxBytes  OBJECT-TYPE
	SYNTAX     Counter64
	MAX-ACCESS read-only
	STATUS     current
	DESCRIPTION
		"The total number of bytes received on the
		              interface, including framing characters."
	::= { hzQtmEnetPortStatsEntry 2 }

hzQtmEnetPortRxUcastPkts  OBJECT-TYPE
	SYNTAX     Counter64
	MAX-ACCESS read-only
	STATUS     current
	DESCRIPTION
		"The number of subnetwork-unicast packets delivered to a higher-layer protocol."
	::= { hzQtmEnetPortStatsEntry 3 }

hzQtmEnetPortRxNUcastPkts  OBJECT-TYPE
	SYNTAX     Counter64
	MAX-ACCESS read-only
	STATUS     current
	DESCRIPTION
		"The number of non-unicast (i.e., subnetwork-broadcast or subnetwork-multicast) packets
		delivered to a higher-layer protocol."
	::= { hzQtmEnetPortStatsEntry 4 }

hzQtmEnetPortRxDiscards  OBJECT-TYPE
	SYNTAX     Counter64
	MAX-ACCESS read-only
	STATUS     current
	DESCRIPTION
		"The number of inbound packets which were chosen
		  to be discarded even though no errors had been
		  detected to prevent their being deliverable to a
		  higher-layer protocol.  One possible reason for
		  discarding such a packet could be to free up buffer space."
	::= { hzQtmEnetPortStatsEntry 5 }

hzQtmEnetPortRxErrors  OBJECT-TYPE
	SYNTAX     Counter64
	MAX-ACCESS read-only
	STATUS     current
	DESCRIPTION
		"The number of inbound packets that contained
		  errors preventing them from being deliverable to a
		  higher-layer protocol."
	::= { hzQtmEnetPortStatsEntry 6 }

hzQtmEnetPortRxUnknownProtos  OBJECT-TYPE
	SYNTAX     Counter64
	MAX-ACCESS read-only
	STATUS     current
	DESCRIPTION
		"The number of packets received via the interface
		  which were discarded because of an unknown or
		  unsupported protocol."
	::= { hzQtmEnetPortStatsEntry 7 }

hzQtmEnetPortTxBytes  OBJECT-TYPE
	SYNTAX     Counter64
	MAX-ACCESS read-only
	STATUS     current
	DESCRIPTION
		"The total number of bytes transmitted out of the
		  interface, including framing characters."
	::= { hzQtmEnetPortStatsEntry 8 }

hzQtmEnetPortTxUcastPkts  OBJECT-TYPE
	SYNTAX     Counter64
	MAX-ACCESS read-only
	STATUS     current
	DESCRIPTION
		"The total number of packets that higher-level
		  protocols requested be transmitted to a
		  subnetwork-unicast address, including those that
		  were discarded or not sent."
	::= { hzQtmEnetPortStatsEntry 9 }

hzQtmEnetPortTxNUcastPkts  OBJECT-TYPE
	SYNTAX     Counter64
	MAX-ACCESS read-only
	STATUS     current
	DESCRIPTION
		"The total number of packets that higher-level
		  protocols requested be transmitted to a non-
		  unicast (i.e., a subnetwork-broadcast or
		  subnetwork-multicast) address, including those
		  that were discarded or not sent."
	::= { hzQtmEnetPortStatsEntry 10 }

hzQtmEnetPortTxDiscards  OBJECT-TYPE
	SYNTAX     Counter64
	MAX-ACCESS read-only
	STATUS     current
	DESCRIPTION
		"The number of outbound packets which were chosen
		  to be discarded even though no errors had been
		  detected to prevent their being transmitted.  One
		   possible reason for discarding such a packet could
		   be to free up buffer space."
	::= { hzQtmEnetPortStatsEntry 11 }

hzQtmEnetPortTxErrors  OBJECT-TYPE
	SYNTAX     Counter64
	MAX-ACCESS read-only
	STATUS     current
	DESCRIPTION
		"The number of outbound packets that could not be
		  transmitted because of errors."
	::= { hzQtmEnetPortStatsEntry 12 }

hzQtmEnetPortDroppedEnetFramesThresholdParameters  OBJECT-TYPE
	SYNTAX     DisplayString (SIZE(0..24))
	MAX-ACCESS read-write
	STATUS     current
	DESCRIPTION
		"A read-write string: The threshold, in percent, and the number of seconds that it must exceed this threshold are programmed by the user. An example of the format of the string is as follows: '70 10'. The first parameter is the percentage of frames that are dropped, the second is the time in seconds that the threshold must be exceeded. The single quote marks i.e. ' ' are not used in the command."
	::= { hzQtmAggregatedEnetPortConfig 1 }

hzQtmEnetPortBWUtilizationThresholdParameters  OBJECT-TYPE
	SYNTAX     DisplayString (SIZE(0..24))
	MAX-ACCESS read-write
	STATUS     current
	DESCRIPTION
		"A read-write string: The percentage of available bandwidth threshold and the number of seconds that it must exceed this threshold are programmed by the user. An example of the format of the string is as follows: '70 10'. The first parameter is the threshold point in percent, the number of seconds that the threshold must be exceeded. The single quote marks i.e. ' ' are not used in the command."
	::= { hzQtmAggregatedEnetPortConfig 2 }

hzQtmAggPortTxFrames  OBJECT-TYPE
	SYNTAX     Counter64
	MAX-ACCESS read-only
	STATUS     current
	DESCRIPTION
		"The current count of aggregated port egress frames."
	::= { hzQtmAggregatedEnetPortStats 1 }

hzQtmAggPortTxBytes  OBJECT-TYPE
	SYNTAX     Counter64
	MAX-ACCESS read-only
	STATUS     current
	DESCRIPTION
		"The current count of aggregated port egress bytes."
	::= { hzQtmAggregatedEnetPortStats 2 }

hzQtmAggPortRxFramesOK  OBJECT-TYPE
	SYNTAX     Counter64
	MAX-ACCESS read-only
	STATUS     current
	DESCRIPTION
		"The current count of aggregated port ingress frames."
	::= { hzQtmAggregatedEnetPortStats 3 }

hzQtmAggPortRxBytesOK  OBJECT-TYPE
	SYNTAX     Counter64
	MAX-ACCESS read-only
	STATUS     current
	DESCRIPTION
		"The current count of aggregated port ingress bytes."
	::= { hzQtmAggregatedEnetPortStats 4 }

hzQtmAggPortRxFramesError  OBJECT-TYPE
	SYNTAX     Counter64
	MAX-ACCESS read-only
	STATUS     current
	DESCRIPTION
		"The current count of aggregated port ingress errors."
	::= { hzQtmAggregatedEnetPortStats 5 }

hzQtmAggPortBWUtilization  OBJECT-TYPE
	SYNTAX     Integer32
	MAX-ACCESS read-only
	STATUS     current
	DESCRIPTION
		"The carried load over link capacity for port."
	::= { hzQtmAggregatedEnetPortStats 6 }

hzQtmAggPortIngressDataRate  OBJECT-TYPE
	SYNTAX     Integer32
	MAX-ACCESS read-only
	STATUS     current
	DESCRIPTION
		"The data rate coming into the ethernet for port.
		 The data rate you see is multiplied by 100. e.g. A display
		 of 1530 is actually 15.30 Mpbs"
	::= { hzQtmAggregatedEnetPortStats 7 }

hzQtmAggPortEgressDataRate  OBJECT-TYPE
	SYNTAX     Integer32
	MAX-ACCESS read-only
	STATUS     current
	DESCRIPTION
		"The data rate going out of the ethernet for port.
		 The data rate you see is multiplied by 100. e.g. A display
		 of 1530 is actually 15.30 Mpbs."
	::= { hzQtmAggregatedEnetPortStats 8 }

hzQtmAggPortFramesInQueue1  OBJECT-TYPE
	SYNTAX     Counter64
	MAX-ACCESS read-only
	STATUS     current
	DESCRIPTION
		"The current count of frames passed through queue 1."
	::= { hzQtmAggregatedEnetPortStats 9 }

hzQtmAggPortFramesInQueue2  OBJECT-TYPE
	SYNTAX     Counter64
	MAX-ACCESS read-only
	STATUS     current
	DESCRIPTION
		"The current count of frames passed through queue 2."
	::= { hzQtmAggregatedEnetPortStats 10 }

hzQtmAggPortFramesInQueue3  OBJECT-TYPE
	SYNTAX     Counter64
	MAX-ACCESS read-only
	STATUS     current
	DESCRIPTION
		"The current count of frames passed through queue 3."
	::= { hzQtmAggregatedEnetPortStats 11 }

hzQtmAggPortFramesInQueue4  OBJECT-TYPE
	SYNTAX     Counter64
	MAX-ACCESS read-only
	STATUS     current
	DESCRIPTION
		"The current count of frames passed through queue 4."
	::= { hzQtmAggregatedEnetPortStats 12 }

hzQtmAggPortFramesInQueue1Discarded  OBJECT-TYPE
	SYNTAX     Counter64
	MAX-ACCESS read-only
	STATUS     current
	DESCRIPTION
		"The current count of frames received in queue 1 that  were discarded due to an error.
		 One possible reason is lack of buffer space."
	::= { hzQtmAggregatedEnetPortStats 13 }

hzQtmAggPortFramesInQueue2Discarded  OBJECT-TYPE
	SYNTAX     Counter64
	MAX-ACCESS read-only
	STATUS     current
	DESCRIPTION
		"The current count of frames received in queue 2 that were discarded due to an error.
		 One possible reason is lack of buffer space."
	::= { hzQtmAggregatedEnetPortStats 14 }

hzQtmAggPortFramesInQueue3Discarded  OBJECT-TYPE
	SYNTAX     Counter64
	MAX-ACCESS read-only
	STATUS     current
	DESCRIPTION
		"The current count of frames received in queue 3 that were discarded due to an error.
		 One possible reason is lack of buffer space."
	::= { hzQtmAggregatedEnetPortStats 15 }

hzQtmAggPortFramesInQueue4Discarded  OBJECT-TYPE
	SYNTAX     Counter64
	MAX-ACCESS read-only
	STATUS     current
	DESCRIPTION
		"The current count of frames received in queue 4 that were discarded due to an error.
		 One possible reason is lack of buffer space."
	::= { hzQtmAggregatedEnetPortStats 16 }

hzQtmAggPortFramesInQueueC  OBJECT-TYPE
	SYNTAX     Counter64
	MAX-ACCESS read-only
	STATUS     current
	DESCRIPTION
		"The current count of frames passed through queue C."
	::= { hzQtmAggregatedEnetPortStats 17 }

hzQtmAggPortFramesInQueueCDiscarded  OBJECT-TYPE
	SYNTAX     Counter64
	MAX-ACCESS read-only
	STATUS     current
	DESCRIPTION
		"The current count of frames received in queue C that were discarded due to an error.
		 One possible reason is lack of buffer space."
	::= { hzQtmAggregatedEnetPortStats 18 }

-- -----------------------------
--   hzQtmWirelessInterfaceNames
-- -----------------------------

hzQtmWirelessInterfaceNameTable  OBJECT-TYPE
	SYNTAX SEQUENCE OF HzQtmWirelessInterfaceNameEntry
	MAX-ACCESS not-accessible
	STATUS     current
	DESCRIPTION
		"A table of Wireless Interface Modems"
	::= { hzQtmWirelessInterfaceNames 1 }

hzQtmWirelessInterfaceNameEntry  OBJECT-TYPE
	SYNTAX 	HzQtmWirelessInterfaceNameEntry
	MAX-ACCESS not-accessible
	STATUS     current
	DESCRIPTION
		"A Wireless Interface Modem"
	INDEX { hzQtmWirelessInterfaceNameIndex }
	::= { hzQtmWirelessInterfaceNameTable 1 }

HzQtmWirelessInterfaceNameEntry ::= SEQUENCE {
	hzQtmWirelessInterfaceNameIndex
		INTEGER,
	hzQtmWirelessInterfaceName
		DisplayString
}

hzQtmWirelessInterfaceNameIndex  OBJECT-TYPE
	SYNTAX     INTEGER {
		wireless-port-1 (1),
		wireless-port-2 (2)
	}
	MAX-ACCESS read-only
	STATUS     current
	DESCRIPTION
		"A unique value for each interface. "
	::= { hzQtmWirelessInterfaceNameEntry 1 }

hzQtmWirelessInterfaceName  OBJECT-TYPE
	SYNTAX     DisplayString
	MAX-ACCESS read-only
	STATUS     current
	DESCRIPTION
		"Describes the functionality of the Wireless Interface"
	::= { hzQtmWirelessInterfaceNameEntry 2 }

-- ----------------
-- hzQtmModemTable
-- ----------------

hzQtmModemTable  OBJECT-TYPE
	SYNTAX SEQUENCE OF HzQtmModemEntry
	MAX-ACCESS not-accessible
	STATUS     current
	DESCRIPTION
		"A table of Wireless Interface Modems"
	::= { hzQtmWirelessInterfaceModems 1 }

hzQtmModemEntry  OBJECT-TYPE
	SYNTAX 	HzQtmModemEntry
	MAX-ACCESS not-accessible
	STATUS     current
	DESCRIPTION
		"A Wireless Interface Modem"
	INDEX { hzQtmModemIndex }
	::= { hzQtmModemTable 1 }

HzQtmModemEntry ::= SEQUENCE {
	hzQtmModemIndex
		INTEGER,
	hzQtmModemOperStatus
		INTEGER,
	hzQtmModemChannelizedRSL
		Integer32,
	hzQtmModemChannelizedRSLUnsignedInt
		Integer32,
	hzQtmModemModulationType
		INTEGER,
	hzQtmModemRxSpeed
		Integer32,
	hzQtmModemTxSpeed
		Integer32,
	hzQtmModemSNR
		Integer32,
	hzQtmModemEbToNoiseRatio
		Integer32,
	hzQtmModemEqualizerStress
		Integer32,
	hzQtmModemSNRThresholdParameters
		DisplayString,
	hzQtmModemChannelizedRslBelowThresholdParameters
		DisplayString,
	hzQtmModemXpicEqualizerStress
		Integer32,
	hzQtmModemXPI
		Integer32
}

hzQtmModemIndex  OBJECT-TYPE
	SYNTAX     INTEGER {
		wireless-port-1 (1),
		wireless-port-2 (2)
	}
	MAX-ACCESS read-only
	STATUS     current
	DESCRIPTION
		"A unique value for each interface. "
	::= { hzQtmModemEntry 1 }

hzQtmModemOperStatus  OBJECT-TYPE
	SYNTAX     INTEGER {
		up (1),
		down (2),
		testing (3)
	}
	MAX-ACCESS read-only
	STATUS     current
	DESCRIPTION
		"The current operational state of the interface. Testing indicates that no operational packets can be passed."
	::= { hzQtmModemEntry 2 }

hzQtmModemChannelizedRSL  OBJECT-TYPE
	SYNTAX     Integer32
	MAX-ACCESS read-only
	STATUS     current
	DESCRIPTION
		"An estimate of the modem's channelized RSL. Divide the value by 10 to get the actual RSL value. Once this number is divided by 10 the units are dBm.  For example -352 is actually -35.2dBm"
	::= { hzQtmModemEntry 3 }

hzQtmModemChannelizedRSLUnsignedInt  OBJECT-TYPE
	SYNTAX     Integer32
	MAX-ACCESS read-only
	STATUS     current
	DESCRIPTION
		"The absolute value of the estimate of the modem's channelized RSL. Divide the value by 10 to get the actual RSL value. Once this number is divided by 10 the units are dBm.  For example -352 is actually 35.2dBm"
	::= { hzQtmModemEntry 4 }

hzQtmModemModulationType  OBJECT-TYPE
	SYNTAX     INTEGER {
		qpsk (1),
		qam (2),
		qam16 (3),
		qam32 (4),
		qam64 (5),
		qam128 (6),
		qam256 (7),
		x8psk (8)
	}
	MAX-ACCESS read-only
	STATUS     current
	DESCRIPTION
		"The modulation type of the modem, distinguished according
		 to the physical/link protocol."
	::= { hzQtmModemEntry 5 }

hzQtmModemRxSpeed  OBJECT-TYPE
	SYNTAX     Integer32
	MAX-ACCESS read-only
	STATUS     current
	DESCRIPTION
		"An estimate of the modem's current Rx bandwidth in bits per
		 second. Divide the value by 10000 to get the actual data rate in Mbps"
	::= { hzQtmModemEntry 6 }

hzQtmModemTxSpeed  OBJECT-TYPE
	SYNTAX     Integer32
	MAX-ACCESS read-only
	STATUS     current
	DESCRIPTION
		"An estimate of the modem's current Tx bandwidth in bits per
		 second. Divide the value by 10000 to get the actual data rate in Mbps"
	::= { hzQtmModemEntry 7 }

hzQtmModemSNR  OBJECT-TYPE
	SYNTAX     Integer32
	MAX-ACCESS read-only
	STATUS     current
	DESCRIPTION
		"SNR value in dB. Divide the value by 10 to get the actual SNR."
	::= { hzQtmModemEntry 8 }

hzQtmModemEbToNoiseRatio  OBJECT-TYPE
	SYNTAX     Integer32
	MAX-ACCESS read-only
	STATUS     current
	DESCRIPTION
		"The ratio of the modem Estimated Energy per information bit to Noise power spectral density.
		                                        Divide the value by 10 to get the actual EbToNoiseRatio"
	::= { hzQtmModemEntry 9 }

hzQtmModemEqualizerStress  OBJECT-TYPE
	SYNTAX     Integer32
	MAX-ACCESS read-only
	STATUS     current
	DESCRIPTION
		"Indicates the average magnitude of all the equalizer taps to provide a measure of how hard the equalizer is working."
	::= { hzQtmModemEntry 10 }

hzQtmModemSNRThresholdParameters  OBJECT-TYPE
	SYNTAX     DisplayString (SIZE(0..24))
	MAX-ACCESS read-write
	STATUS     current
	DESCRIPTION
		"A read-write string specifing the modem SNR threshold."
	::= { hzQtmModemEntry 11 }

hzQtmModemChannelizedRslBelowThresholdParameters  OBJECT-TYPE
	SYNTAX     DisplayString (SIZE(0..24))
	MAX-ACCESS read-write
	STATUS     current
	DESCRIPTION
		"A read-write string: The threshold in dBm  and the number of seconds threshold are programmed by the user. An example of the format of the string is as follows: '-75 10'. The first parameter power level in dBm, the second is the time in seconds that the threshold must be exceeded. In this example the threshold -75 dBm and the time is set to 10 seconds. The single quote marks i.e. ' ' are not used in the command."
	::= { hzQtmModemEntry 12 }

hzQtmModemXpicEqualizerStress  OBJECT-TYPE
	SYNTAX     Integer32
	MAX-ACCESS read-only
	STATUS     current
	DESCRIPTION
		"Indicates the average magnitude of all the XPIC equalizer taps to provide a measure of how hard the XPIC equalizer is working."
	::= { hzQtmModemEntry 13 }

hzQtmModemXPI  OBJECT-TYPE
	SYNTAX     Integer32
	MAX-ACCESS read-only
	STATUS     current
	DESCRIPTION
		"The XPI is a measure of the cross-polarization distortion (interference) (named XPD or XPI) with reference to the main received signal level.
		XPI is calculated as a ratio of XPIC_equalizer_stress to (Main_equalizer_stress + 512). This value is converted to dB by using the
		formula 20*log( XPIC_equalizer_stress / (Main_equalizer_stress + 512)) . Divide the value by 100 to get the actual RSL value. "
	::= { hzQtmModemEntry 14 }

-- ----------------------------
-- hzQtmWirelessInterfaceModems
-- ----------------------------

hzQtmModemStatsTable  OBJECT-TYPE
	SYNTAX SEQUENCE OF HzQtmModemStatsEntry
	MAX-ACCESS not-accessible
	STATUS     current
	DESCRIPTION
		"A table of Wireless Interface Modem Statistics"
	::= { hzQtmWirelessInterfaceModems 2 }

hzQtmModemStatsEntry  OBJECT-TYPE
	SYNTAX 	HzQtmModemStatsEntry
	MAX-ACCESS not-accessible
	STATUS     current
	DESCRIPTION
		"Statistics for a Wireless Interface Modem"
	INDEX { hzQtmModemStatsIndex }
	::= { hzQtmModemStatsTable 1 }

HzQtmModemStatsEntry ::= SEQUENCE {
	hzQtmModemStatsIndex
		INTEGER,
	hzQtmModemTxBlocks
		Counter64,
	hzQtmModemRxBlocksOKs
		Counter64,
	hzQtmModemRxBlocksErrors
		Counter64
}

hzQtmModemStatsIndex  OBJECT-TYPE
	SYNTAX     INTEGER {
		wireless-port-1 (1),
		wireless-port-2 (2),
		secondary-wireless-ports (3)
	}
	MAX-ACCESS read-only
	STATUS     current
	DESCRIPTION
		"A unique value for each interface. "
	::= { hzQtmModemStatsEntry 1 }

hzQtmModemTxBlocks  OBJECT-TYPE
	SYNTAX     Counter64
	MAX-ACCESS read-only
	STATUS     current
	DESCRIPTION
		"The current count of Modem blocks transmitted."
	::= { hzQtmModemStatsEntry 2 }

hzQtmModemRxBlocksOKs  OBJECT-TYPE
	SYNTAX     Counter64
	MAX-ACCESS read-only
	STATUS     current
	DESCRIPTION
		"The current count of Modem blocks received."
	::= { hzQtmModemStatsEntry 3 }

hzQtmModemRxBlocksErrors  OBJECT-TYPE
	SYNTAX     Counter64
	MAX-ACCESS read-only
	STATUS     current
	DESCRIPTION
		"The current count of Modem blocks received in error."
	::= { hzQtmModemStatsEntry 4 }

hzQtmWirelessEnetPortStatsTable  OBJECT-TYPE
	SYNTAX SEQUENCE OF HzQtmWirelessEnetPortStatsEntry
	MAX-ACCESS not-accessible
	STATUS     current
	DESCRIPTION
		""
	::= { hzQtmWirelessInterfaceModems 3 }

hzQtmWirelessEnetPortStatsEntry  OBJECT-TYPE
	SYNTAX 	HzQtmWirelessEnetPortStatsEntry
	MAX-ACCESS not-accessible
	STATUS     current
	DESCRIPTION
		""
	INDEX { hzQtmWirelessEnetPortIndex }
	::= { hzQtmWirelessEnetPortStatsTable 1 }

HzQtmWirelessEnetPortStatsEntry ::= SEQUENCE {
	hzQtmWirelessEnetPortIndex
		INTEGER,
	hzQtmWirelessEnetPortTxFrames
		Counter64,
	hzQtmWirelessEnetPortRxFramesOK
		Counter64,
	hzQtmWirelessEnetPortRxFramesErrors
		Counter64,
	hzQtmWirelessEnetPortRxFramesQueueDiscards
		Counter64
}

hzQtmWirelessEnetPortIndex  OBJECT-TYPE
	SYNTAX     INTEGER {
		wireless-enetport-1 (1),
		wireless-enetport-2 (2)
	}
	MAX-ACCESS read-only
	STATUS     current
	DESCRIPTION
		"A unique value for each interface. "
	::= { hzQtmWirelessEnetPortStatsEntry 1 }

hzQtmWirelessEnetPortTxFrames  OBJECT-TYPE
	SYNTAX     Counter64
	MAX-ACCESS read-only
	STATUS     current
	DESCRIPTION
		"The current count of Ethernet Combiner frames sent."
	::= { hzQtmWirelessEnetPortStatsEntry 2 }

hzQtmWirelessEnetPortRxFramesOK  OBJECT-TYPE
	SYNTAX     Counter64
	MAX-ACCESS read-only
	STATUS     current
	DESCRIPTION
		"The current count of good Ethernet Combiner frames received."
	::= { hzQtmWirelessEnetPortStatsEntry 3 }

hzQtmWirelessEnetPortRxFramesErrors  OBJECT-TYPE
	SYNTAX     Counter64
	MAX-ACCESS read-only
	STATUS     current
	DESCRIPTION
		"The current count of Ethernet Combiner frames received in error."
	::= { hzQtmWirelessEnetPortStatsEntry 4 }

hzQtmWirelessEnetPortRxFramesQueueDiscards  OBJECT-TYPE
	SYNTAX     Counter64
	MAX-ACCESS read-only
	STATUS     current
	DESCRIPTION
		"The current count of Ethernet Combiner frames in the queue that were discarded."
	::= { hzQtmWirelessEnetPortStatsEntry 5 }

-- -----------------------------
--   hzQtmWirelessInterfaceIF
-- -----------------------------

hzQtmIntermediateFrequencyTable  OBJECT-TYPE
	SYNTAX SEQUENCE OF HzQtmIntermediateFrequencyEntry
	MAX-ACCESS not-accessible
	STATUS     current
	DESCRIPTION
		"A table of Intermediate Frequency pat(pliu)"
	::= { hzQtmWirelessInterfaceIF 1 }

hzQtmIntermediateFrequencyEntry  OBJECT-TYPE
	SYNTAX 	HzQtmIntermediateFrequencyEntry
	MAX-ACCESS not-accessible
	STATUS     current
	DESCRIPTION
		"Intermediate Frequency Card (pliu)"
	INDEX { hzQtmIFPathIndex }
	::= { hzQtmIntermediateFrequencyTable 1 }

HzQtmIntermediateFrequencyEntry ::= SEQUENCE {
	hzQtmIFPathIndex
		INTEGER,
	hzQtmIFPathTxLockStatus
		INTEGER,
	hzQtmIFPathRxLockStatus
		INTEGER,
	hzQtmIFPathLoopbackLockStatus
		INTEGER
}

hzQtmIFPathIndex  OBJECT-TYPE
	SYNTAX     INTEGER {
		wireless-port-1 (1),
		wireless-port-2 (2)
	}
	MAX-ACCESS read-only
	STATUS     current
	DESCRIPTION
		"A unique value for each path. "
	::= { hzQtmIntermediateFrequencyEntry 1 }

hzQtmIFPathTxLockStatus  OBJECT-TYPE
	SYNTAX     INTEGER {
		unlocked (1),
		locked (2)
	}
	MAX-ACCESS read-only
	STATUS     current
	DESCRIPTION
		"Indicates if the IF transmit synthesizer is locked."
	::= { hzQtmIntermediateFrequencyEntry 2 }

hzQtmIFPathRxLockStatus  OBJECT-TYPE
	SYNTAX     INTEGER {
		unlocked (1),
		locked (2)
	}
	MAX-ACCESS read-only
	STATUS     current
	DESCRIPTION
		"Indicates if the IF receive synthesizer is locked."
	::= { hzQtmIntermediateFrequencyEntry 3 }

hzQtmIFPathLoopbackLockStatus  OBJECT-TYPE
	SYNTAX     INTEGER {
		unlocked (1),
		locked (2)
	}
	MAX-ACCESS read-only
	STATUS     current
	DESCRIPTION
		"Indicates if the IF loopback synthesizer is locked.
		The loopback synthesize is used only when the IF loopback is enabled."
	::= { hzQtmIntermediateFrequencyEntry 4 }

--
-- RADIO INFORMATION
--

hzQtmRadioTable  OBJECT-TYPE
	SYNTAX SEQUENCE OF HzQtmRadioEntry
	MAX-ACCESS not-accessible
	STATUS     current
	DESCRIPTION
		"A table of Wireless Interface Radios"
	::= { hzQtmWirelessInterfaceRadios 1 }

hzQtmRadioEntry  OBJECT-TYPE
	SYNTAX 	HzQtmRadioEntry
	MAX-ACCESS not-accessible
	STATUS     current
	DESCRIPTION
		"A Wireless Interface Radio"
	INDEX { hzQtmRadioIndex }
	::= { hzQtmRadioTable 1 }

HzQtmRadioEntry ::= SEQUENCE {
	hzQtmRadioIndex
		INTEGER,
	hzQtmRadioDescription
		DisplayString,
	hzQtmRadioOperStatus
		INTEGER,
	hzQtmRadioLastChanged
		TimeTicks,
	hzQtmRadioReceiveSignalLevel
		Integer32,
	hzQtmRadioReceiveSignalLevelUnsigned
		Integer32,
	hzQtmRadioTxGain
		Integer32,
	hzQtmRadioRxGain
		Integer32,
	hzQtmRadioReset
		Integer32,
	hzQtmRadioTransmitPowerdBm
		Integer32,
	hzQtmRadioPowerOption
		INTEGER,
	hzQtmRadioTxState
		INTEGER,
	hzQtmRadioActualTxState
		INTEGER,
	hzQtmRadioTemperature
		Integer32,
	hzQtmRadioRxCableLoss
		DisplayString,
	hzQtmRadioTxCableLoss
		DisplayString,
	hzQtmRadioTxCableLossChange
		DisplayString,
	hzQtmRadioMaxTransmitPowerdBm
		Integer32,
	hzQtmRadioActualTransmitPowerdBm
		Integer32
}

hzQtmRadioIndex  OBJECT-TYPE
	SYNTAX     INTEGER {
		wireless-port-1 (1),
		wireless-port-2 (2)
	}
	MAX-ACCESS read-only
	STATUS     current
	DESCRIPTION
		"A unique value for each interface. "
	::= { hzQtmRadioEntry 1 }

hzQtmRadioDescription  OBJECT-TYPE
	SYNTAX     DisplayString
	MAX-ACCESS read-only
	STATUS     current
	DESCRIPTION
		"A textual string containing information about the radio. Includes the
		manufacturer, product name, software version,  serial number, and hardware
		version of the radio."
	::= { hzQtmRadioEntry 2 }

hzQtmRadioOperStatus  OBJECT-TYPE
	SYNTAX     INTEGER {
		up (1),
		down (2),
		testing (3)
	}
	MAX-ACCESS read-only
	STATUS     current
	DESCRIPTION
		"The current operational state of the interface. Testing
		 indicates that no operational packets can be passed. Testing
		 also indicates that a firmware upgrade may be in progress"
	::= { hzQtmRadioEntry 3 }

hzQtmRadioLastChanged  OBJECT-TYPE
	SYNTAX     TimeTicks
	MAX-ACCESS read-only
	STATUS     current
	DESCRIPTION
		"The value of sysUpTime at the time the radio entered its current
		operational state. If the current state was entered prior to the
		last re-initialization of the local  network management subsystem,
		then this object contains  a zero value."
	::= { hzQtmRadioEntry 4 }

hzQtmRadioReceiveSignalLevel  OBJECT-TYPE
	SYNTAX     Integer32
	MAX-ACCESS read-only
	STATUS     current
	DESCRIPTION
		"The Received Signal Level indicates the power of the receive level
		in dBm. The number is divided by 10 to get the actual dBm. For example,
		-432 is actually -43.2dBm."
	::= { hzQtmRadioEntry 5 }

hzQtmRadioReceiveSignalLevelUnsigned  OBJECT-TYPE
	SYNTAX     Integer32
	MAX-ACCESS read-only
	STATUS     current
	DESCRIPTION
		"The Received Signal Level indicates the power of the receive level in dBm.
		The number is divided by -10. e.g. 432 is actually -43.2dBm. Object provided
		to accomodate plotting of negative RSL values which is not supported
		in some EMS (i.e.: CastleRock).  Please use 'hzQtmRadioReceiveSignalLevel'
		object if your EMS supports plotting of negative integers."
	::= { hzQtmRadioEntry 6 }

hzQtmRadioTxGain  OBJECT-TYPE
	SYNTAX     Integer32
	MAX-ACCESS read-only
	STATUS     current
	DESCRIPTION
		"The gain of the radio in the transmit chain. Indicates the gain in dB."
	::= { hzQtmRadioEntry 7 }

hzQtmRadioRxGain  OBJECT-TYPE
	SYNTAX     Integer32
	MAX-ACCESS read-only
	STATUS     current
	DESCRIPTION
		"The gain of the radio in the receive chain. Indicates the gain in dB."
	::= { hzQtmRadioEntry 8 }

hzQtmRadioReset  OBJECT-TYPE
	SYNTAX     Integer32
	MAX-ACCESS read-write
	STATUS     current
	DESCRIPTION
		"Writing 1 to this object causes the radio to be reset. All other values
		are not recognized. This variable  always reads back as 0. radioOperStatus
		should be polled  by the user after this object is written to, to verify
		that the radio card has been reset."
	::= { hzQtmRadioEntry 9 }

hzQtmRadioTransmitPowerdBm  OBJECT-TYPE
	SYNTAX     Integer32
	MAX-ACCESS read-write
	STATUS     current
	DESCRIPTION
		"This defines the programmed transmit level of the radio.
		The power you see is divided by 10. e.g. A display of 133 is actually 13.3 dBm.
		Notes:
		- Programmed and Actual transmit power may differ - see hzQtmRadioActualTransmitPower."
	DEFVAL  { 0 }
	::= { hzQtmRadioEntry 10 }

hzQtmRadioPowerOption  OBJECT-TYPE
	SYNTAX     INTEGER {
		normal (1),
		highPower (2)
	}
	MAX-ACCESS read-only
	STATUS     current
	DESCRIPTION
		"This indicates the power option of the radio: normal or high power."
	::= { hzQtmRadioEntry 11 }

hzQtmRadioTxState  OBJECT-TYPE
	SYNTAX     INTEGER {
		off (1),
		on (2)
	}
	MAX-ACCESS read-write
	STATUS     current
	DESCRIPTION
		"This indicates the power option of the radio: normal or high power."
	::= { hzQtmRadioEntry 12 }

hzQtmRadioActualTxState  OBJECT-TYPE
	SYNTAX     INTEGER {
		off (1),
		on (2)
	}
	MAX-ACCESS read-only
	STATUS     current
	DESCRIPTION
		"This defines the actual transmit state of the radio."
	::= { hzQtmRadioEntry 13 }

hzQtmRadioTemperature  OBJECT-TYPE
	SYNTAX     Integer32
	MAX-ACCESS read-only
	STATUS     current
	DESCRIPTION
		"The Radio temperature in degree Celsius. The actual temperature is determined by dividing the number by 10. e.g. 202 is actually 20.2 degrees Celsius."
	::= { hzQtmRadioEntry 14 }

hzQtmRadioRxCableLoss  OBJECT-TYPE
	SYNTAX     DisplayString
	MAX-ACCESS read-only
	STATUS     current
	DESCRIPTION
		"The Rx Cable Loss in dB."
	::= { hzQtmRadioEntry 15 }

hzQtmRadioTxCableLoss  OBJECT-TYPE
	SYNTAX     DisplayString
	MAX-ACCESS read-only
	STATUS     current
	DESCRIPTION
		"The Tx Cable Loss in dB."
	::= { hzQtmRadioEntry 16 }

hzQtmRadioTxCableLossChange  OBJECT-TYPE
	SYNTAX     DisplayString
	MAX-ACCESS read-only
	STATUS     current
	DESCRIPTION
		"The Tx Cable Loss Change is the difference between the configured TxPower and the measured TxPower measured in dB."
	::= { hzQtmRadioEntry 17 }

hzQtmRadioMaxTransmitPowerdBm  OBJECT-TYPE
	SYNTAX     Integer32
	MAX-ACCESS read-only
	STATUS     current
	DESCRIPTION
		"The maximum Transmit Power allowed."
	::= { hzQtmRadioEntry 18 }

hzQtmRadioActualTransmitPowerdBm  OBJECT-TYPE
	SYNTAX     Integer32
	MAX-ACCESS read-only
	STATUS     current
	DESCRIPTION
		"This defines the actual transmit level of the radio.
		The power you see is divided by 10. e.g. A display of 133 is actually 13.3 dBm.
		This value will be undefined:
		- If the radio is operational and muted.
		- If the radio is not operational.
		- If the radio does not have transmit calibration tables programmed into its EEPROM, this transmit power level cannot be used as it is not possible to accurately calculate the actual transmit level. In this case this object will return -99."
	::= { hzQtmRadioEntry 19 }

hzQtmRadio1FreqGroupSelected  OBJECT-TYPE
	SYNTAX     INTEGER {
		txLow (1),
		txHigh (2),
		none (3)
	}
	MAX-ACCESS read-write
	STATUS     current
	DESCRIPTION
		"The frequency group selected for Radio 1.

		The frequency subbands are divided into frequency groups txHigh and txLow.  An horizon system must have one node configured to txLow and the other node configure to txHigh"
	::= { hzQtmWirelessInterfaceRadio1Frequencies 1 }

hzQtmRadio1BandTable  OBJECT-TYPE
	SYNTAX SEQUENCE OF HzQtmRadio1BandEntry
	MAX-ACCESS not-accessible
	STATUS     current
	DESCRIPTION
		"A table of radio bands for Radio 1. Frequency bands are divided into sub bands.

		i.e. FCC 23 Ghz Band is comprised of fcc23a, fcc23b, fcc23c and
		fcc23d which make up the entire FCC23 band"
	::= { hzQtmWirelessInterfaceRadio1Frequencies 2 }

hzQtmRadio1BandEntry  OBJECT-TYPE
	SYNTAX 	HzQtmRadio1BandEntry
	MAX-ACCESS not-accessible
	STATUS     current
	DESCRIPTION
		"A radio band entry containing all the radio band values"
	INDEX { hzQtmRadio1BandIndex }
	::= { hzQtmRadio1BandTable 1 }

HzQtmRadio1BandEntry ::= SEQUENCE {
	hzQtmRadio1BandIndex
		Integer32,
	hzQtmRadio1BandId
		Integer32,
	hzQtmRadio1BandName
		DisplayString,
	hzQtmRadio1BandProgrammed
		INTEGER
}

hzQtmRadio1BandIndex  OBJECT-TYPE
	SYNTAX     Integer32
	MAX-ACCESS read-only
	STATUS     current
	DESCRIPTION
		"A unique value for each radio band. "
	::= { hzQtmRadio1BandEntry 1 }

hzQtmRadio1BandId  OBJECT-TYPE
	SYNTAX     Integer32
	MAX-ACCESS read-only
	STATUS     current
	DESCRIPTION
		"radio band ID.
		 Note: Changing radio band ID requires a system reset."
	::= { hzQtmRadio1BandEntry 2 }

hzQtmRadio1BandName  OBJECT-TYPE
	SYNTAX     DisplayString
	MAX-ACCESS read-only
	STATUS     current
	DESCRIPTION
		"The radio band name."
	::= { hzQtmRadio1BandEntry 3 }

hzQtmRadio1BandProgrammed  OBJECT-TYPE
	SYNTAX     INTEGER {
		active (1),
		notActive (2)
	}
	MAX-ACCESS read-write
	STATUS     current
	DESCRIPTION
		"Specifies the operating radio band for the modem.
         
		***Only 1 index may be selected in a 1 modem system."
	DEFVAL  { notActive }
	::= { hzQtmRadio1BandEntry 4 }

hzQtmRadio1TxHighFreqTable  OBJECT-TYPE
	SYNTAX SEQUENCE OF HzQtmRadio1TxHighFreqEntry
	MAX-ACCESS not-accessible
	STATUS     current
	DESCRIPTION
		"A table of txHigh frequency settings for Radio 1"
	::= { hzQtmWirelessInterfaceRadio1Frequencies 3 }

hzQtmRadio1TxHighFreqEntry  OBJECT-TYPE
	SYNTAX 	HzQtmRadio1TxHighFreqEntry
	MAX-ACCESS not-accessible
	STATUS     current
	DESCRIPTION
		"A txHighFrequency entry containing all the frequency values"
	INDEX { hzQtmRadio1TxHighFreqIndex }
	::= { hzQtmRadio1TxHighFreqTable 1 }

HzQtmRadio1TxHighFreqEntry ::= SEQUENCE {
	hzQtmRadio1TxHighFreqIndex
		Integer32,
	hzQtmRadio1TxHighFreqChannelIndex
		DisplayString,
	hzQtmRadio1TxHighFreqTransmitRfFrequency
		Integer32,
	hzQtmRadio1TxHighFreqReceiveRfFrequency
		Integer32,
	hzQtmRadio1TxHighFreqProgrammed
		INTEGER
}

hzQtmRadio1TxHighFreqIndex  OBJECT-TYPE
	SYNTAX     Integer32
	MAX-ACCESS read-only
	STATUS     current
	DESCRIPTION
		"A unique value for each frequency channel. "
	::= { hzQtmRadio1TxHighFreqEntry 1 }

hzQtmRadio1TxHighFreqChannelIndex  OBJECT-TYPE
	SYNTAX     DisplayString
	MAX-ACCESS read-only
	STATUS     current
	DESCRIPTION
		"The channel index for the frequency."
	::= { hzQtmRadio1TxHighFreqEntry 2 }

hzQtmRadio1TxHighFreqTransmitRfFrequency  OBJECT-TYPE
	SYNTAX     Integer32
	MAX-ACCESS read-only
	STATUS     current
	DESCRIPTION
		"The RF TX frequency in KHz."
	::= { hzQtmRadio1TxHighFreqEntry 3 }

hzQtmRadio1TxHighFreqReceiveRfFrequency  OBJECT-TYPE
	SYNTAX     Integer32
	MAX-ACCESS read-only
	STATUS     current
	DESCRIPTION
		"The RF RX frequency in KHz."
	::= { hzQtmRadio1TxHighFreqEntry 4 }

hzQtmRadio1TxHighFreqProgrammed  OBJECT-TYPE
	SYNTAX     INTEGER {
		active (1),
		notActive (2)
	}
	MAX-ACCESS read-write
	STATUS     current
	DESCRIPTION
		"Specifies the operating frequency channel for the modem.
         Note : For Multi Carrier XPIC configuration it specifies the frequency channel of the Master unit.
		***Only 1 index may be selected in a 1 modem system."
	DEFVAL  { notActive }
	::= { hzQtmRadio1TxHighFreqEntry 5 }

hzQtmRadio1TxLowFreqTable  OBJECT-TYPE
	SYNTAX SEQUENCE OF HzQtmRadio1TxLowFreqEntry
	MAX-ACCESS not-accessible
	STATUS     current
	DESCRIPTION
		"A table of txLow frequency settings for Radio 1"
	::= { hzQtmWirelessInterfaceRadio1Frequencies 4 }

hzQtmRadio1TxLowFreqEntry  OBJECT-TYPE
	SYNTAX 	HzQtmRadio1TxLowFreqEntry
	MAX-ACCESS not-accessible
	STATUS     current
	DESCRIPTION
		"A hzQtmTxLowFrequeny entry containing the frequency values for a specific index"
	INDEX { hzQtmRadio1TxLowFreqIndex }
	::= { hzQtmRadio1TxLowFreqTable 1 }

HzQtmRadio1TxLowFreqEntry ::= SEQUENCE {
	hzQtmRadio1TxLowFreqIndex
		Integer32,
	hzQtmRadio1TxLowFreqChannelIndex
		DisplayString,
	hzQtmRadio1TxLowFreqTransmitRfFrequency
		Integer32,
	hzQtmRadio1TxLowFreqReceiveRfFrequency
		Integer32,
	hzQtmRadio1TxLowFreqProgrammed
		INTEGER
}

hzQtmRadio1TxLowFreqIndex  OBJECT-TYPE
	SYNTAX     Integer32
	MAX-ACCESS read-only
	STATUS     current
	DESCRIPTION
		"A unique value for each frequency channel. "
	::= { hzQtmRadio1TxLowFreqEntry 1 }

hzQtmRadio1TxLowFreqChannelIndex  OBJECT-TYPE
	SYNTAX     DisplayString
	MAX-ACCESS read-only
	STATUS     current
	DESCRIPTION
		"The channel index for the frequency. "
	::= { hzQtmRadio1TxLowFreqEntry 2 }

hzQtmRadio1TxLowFreqTransmitRfFrequency  OBJECT-TYPE
	SYNTAX     Integer32
	MAX-ACCESS read-only
	STATUS     current
	DESCRIPTION
		"The RF TX frequency in KHz."
	::= { hzQtmRadio1TxLowFreqEntry 3 }

hzQtmRadio1TxLowFreqReceiveRfFrequency  OBJECT-TYPE
	SYNTAX     Integer32
	MAX-ACCESS read-only
	STATUS     current
	DESCRIPTION
		"The RF RX frequency in KHz."
	::= { hzQtmRadio1TxLowFreqEntry 4 }

hzQtmRadio1TxLowFreqProgrammed  OBJECT-TYPE
	SYNTAX     INTEGER {
		active (1),
		notActive (2)
	}
	MAX-ACCESS read-write
	STATUS     current
	DESCRIPTION
		"Specifies the operating frequency channel for the modem.
         Note : For Multi Carrier XPIC configuration it specifies the frequency channel of the Master unit.
		Notes:
		Only 1 index may be selected in a 1 modem system.
		Changing Programmed Frequency requires a system reset."
	DEFVAL  { notActive }
	::= { hzQtmRadio1TxLowFreqEntry 5 }

hzQtmRadio1ProgrammedFrequencyChannel  OBJECT-TYPE
	SYNTAX     DisplayString
	MAX-ACCESS read-only
	STATUS     current
	DESCRIPTION
		"The channel that has been programmed for Radio 1."
	::= { hzQtmRadio1ProgrammedFrequency 1 }

hzQtmRadio1ProgrammedFrequencyTxRf  OBJECT-TYPE
	SYNTAX     Integer32
	MAX-ACCESS read-only
	STATUS     current
	DESCRIPTION
		"The programmed RF TX frequency in KHz."
	::= { hzQtmRadio1ProgrammedFrequency 2 }

hzQtmRadio1ProgrammedFrequencyRxRf  OBJECT-TYPE
	SYNTAX     Integer32
	MAX-ACCESS read-only
	STATUS     current
	DESCRIPTION
		"The RF RX frequency in KHz."
	::= { hzQtmRadio1ProgrammedFrequency 3 }

hzQtmRadio2FreqGroupSelected  OBJECT-TYPE
	SYNTAX     INTEGER {
		txLow (1),
		txHigh (2),
		none (3)
	}
	MAX-ACCESS read-only
	STATUS     current
	DESCRIPTION
		"The frequency group selected for Radio 2.

		The frequency subbands are divided into frequency groups txHigh and txLow.  An horizon system must have one node configured to txLow and the other node configure to txHigh"
	::= { hzQtmWirelessInterfaceRadio2Frequencies 1 }

-- ----------------------------

hzQtmRadio2BandTable  OBJECT-TYPE
	SYNTAX SEQUENCE OF HzQtmRadio2BandEntry
	MAX-ACCESS not-accessible
	STATUS     current
	DESCRIPTION
		"A table of Radio Bands for Radio 2"
	::= { hzQtmWirelessInterfaceRadio2Frequencies 2 }

hzQtmRadio2BandEntry  OBJECT-TYPE
	SYNTAX 	HzQtmRadio2BandEntry
	MAX-ACCESS not-accessible
	STATUS     current
	DESCRIPTION
		"A table of radio bands for Radio 2. Frequency bands are divided into sub bands.

		i.e. FCC 23 Ghz Band is comprised of fcc23a, fcc23b, fcc23c and
		fcc23d which make up the entire FCC23 band"
	INDEX { hzQtmRadio2BandIndex }
	::= { hzQtmRadio2BandTable 1 }

HzQtmRadio2BandEntry ::= SEQUENCE {
	hzQtmRadio2BandIndex
		Integer32,
	hzQtmRadio2BandId
		Integer32,
	hzQtmRadio2BandName
		DisplayString,
	hzQtmRadio2BandProgrammed
		INTEGER
}

hzQtmRadio2BandIndex  OBJECT-TYPE
	SYNTAX     Integer32
	MAX-ACCESS read-only
	STATUS     current
	DESCRIPTION
		"A unique value for each radio band. "
	::= { hzQtmRadio2BandEntry 1 }

hzQtmRadio2BandId  OBJECT-TYPE
	SYNTAX     Integer32
	MAX-ACCESS read-only
	STATUS     current
	DESCRIPTION
		"Radio band ID.
		 Note: Changing radio band ID requires a system reset."
	::= { hzQtmRadio2BandEntry 2 }

hzQtmRadio2BandName  OBJECT-TYPE
	SYNTAX     DisplayString
	MAX-ACCESS read-only
	STATUS     current
	DESCRIPTION
		"The radio band name."
	::= { hzQtmRadio2BandEntry 3 }

hzQtmRadio2BandProgrammed  OBJECT-TYPE
	SYNTAX     INTEGER {
		active (1),
		notActive (2)
	}
	MAX-ACCESS read-only
	STATUS     current
	DESCRIPTION
		"Specifies the operating radio band for the modem.

		***Only 1 index may be selected in a 1 modem system."
	::= { hzQtmRadio2BandEntry 4 }

hzQtmRadio2TxHighFreqTable  OBJECT-TYPE
	SYNTAX SEQUENCE OF HzQtmRadio2TxHighFreqEntry
	MAX-ACCESS not-accessible
	STATUS     current
	DESCRIPTION
		"A table of txHigh frequency settings for Radio 2"
	::= { hzQtmWirelessInterfaceRadio2Frequencies 3 }

hzQtmRadio2TxHighFreqEntry  OBJECT-TYPE
	SYNTAX 	HzQtmRadio2TxHighFreqEntry
	MAX-ACCESS not-accessible
	STATUS     current
	DESCRIPTION
		"A txHighFrequency entry containing all the frequency values"
	INDEX { hzQtmRadio2TxHighFreqIndex }
	::= { hzQtmRadio2TxHighFreqTable 1 }

HzQtmRadio2TxHighFreqEntry ::= SEQUENCE {
	hzQtmRadio2TxHighFreqIndex
		Integer32,
	hzQtmRadio2TxHighFreqChannelIndex
		DisplayString,
	hzQtmRadio2TxHighFreqTransmitRfFrequency
		Integer32,
	hzQtmRadio2TxHighFreqReceiveRfFrequency
		Integer32,
	hzQtmRadio2TxHighFreqProgrammed
		INTEGER
}

hzQtmRadio2TxHighFreqIndex  OBJECT-TYPE
	SYNTAX     Integer32
	MAX-ACCESS read-only
	STATUS     current
	DESCRIPTION
		"A unique value for each frequency channel. "
	::= { hzQtmRadio2TxHighFreqEntry 1 }

hzQtmRadio2TxHighFreqChannelIndex  OBJECT-TYPE
	SYNTAX     DisplayString
	MAX-ACCESS read-only
	STATUS     current
	DESCRIPTION
		"The channel index for the frequency."
	::= { hzQtmRadio2TxHighFreqEntry 2 }

hzQtmRadio2TxHighFreqTransmitRfFrequency  OBJECT-TYPE
	SYNTAX     Integer32
	MAX-ACCESS read-only
	STATUS     current
	DESCRIPTION
		"The RF TX frequency in KHz."
	::= { hzQtmRadio2TxHighFreqEntry 3 }

hzQtmRadio2TxHighFreqReceiveRfFrequency  OBJECT-TYPE
	SYNTAX     Integer32
	MAX-ACCESS read-only
	STATUS     current
	DESCRIPTION
		"The RF RX frequency in KHz."
	::= { hzQtmRadio2TxHighFreqEntry 4 }

hzQtmRadio2TxHighFreqProgrammed  OBJECT-TYPE
	SYNTAX     INTEGER {
		active (1),
		notActive (2)
	}
	MAX-ACCESS read-write
	STATUS     current
	DESCRIPTION
		"Specifies the operating frequency channel for the modem.
         Note : For Multi Carrier XPIC configuration it specifies the frequency channel of the Slave unit.
		 Notes:
		 Only 1 index may be selected in a 1 modem system.
		 Changing Programmed Frequency requires a system reset."
	DEFVAL  { notActive }
	::= { hzQtmRadio2TxHighFreqEntry 5 }

hzQtmRadio2TxLowFreqTable  OBJECT-TYPE
	SYNTAX SEQUENCE OF HzQtmRadio2TxLowFreqEntry
	MAX-ACCESS not-accessible
	STATUS     current
	DESCRIPTION
		"A table of txLow frequency settings for Radio 2"
	::= { hzQtmWirelessInterfaceRadio2Frequencies 4 }

hzQtmRadio2TxLowFreqEntry  OBJECT-TYPE
	SYNTAX 	HzQtmRadio2TxLowFreqEntry
	MAX-ACCESS not-accessible
	STATUS     current
	DESCRIPTION
		"A hzQtmTxLowFrequeny entry containing the frequency values for a specific index"
	INDEX { hzQtmRadio2TxLowFreqIndex }
	::= { hzQtmRadio2TxLowFreqTable 1 }

HzQtmRadio2TxLowFreqEntry ::= SEQUENCE {
	hzQtmRadio2TxLowFreqIndex
		Integer32,
	hzQtmRadio2TxLowFreqChannelIndex
		DisplayString,
	hzQtmRadio2TxLowFreqTransmitRfFrequency
		Integer32,
	hzQtmRadio2TxLowFreqReceiveRfFrequency
		Integer32,
	hzQtmRadio2TxLowFreqProgrammed
		INTEGER
}

hzQtmRadio2TxLowFreqIndex  OBJECT-TYPE
	SYNTAX     Integer32
	MAX-ACCESS read-only
	STATUS     current
	DESCRIPTION
		"A unique value for each frequency channel. "
	::= { hzQtmRadio2TxLowFreqEntry 1 }

hzQtmRadio2TxLowFreqChannelIndex  OBJECT-TYPE
	SYNTAX     DisplayString
	MAX-ACCESS read-only
	STATUS     current
	DESCRIPTION
		"The channel index for the frequency. "
	::= { hzQtmRadio2TxLowFreqEntry 2 }

hzQtmRadio2TxLowFreqTransmitRfFrequency  OBJECT-TYPE
	SYNTAX     Integer32
	MAX-ACCESS read-only
	STATUS     current
	DESCRIPTION
		"The RF TX frequency in KHz."
	::= { hzQtmRadio2TxLowFreqEntry 3 }

hzQtmRadio2TxLowFreqReceiveRfFrequency  OBJECT-TYPE
	SYNTAX     Integer32
	MAX-ACCESS read-only
	STATUS     current
	DESCRIPTION
		"The RF RX frequency in KHz."
	::= { hzQtmRadio2TxLowFreqEntry 4 }

hzQtmRadio2TxLowFreqProgrammed  OBJECT-TYPE
	SYNTAX     INTEGER {
		active (1),
		notActive (2)
	}
	MAX-ACCESS read-write
	STATUS     current
	DESCRIPTION
		"Specifies the operating frequency channel for the modem.
         Note : For Multi Carrier XPIC configuration it specifies the frequency channel of the Slave unit.
		 Notes:
		 Only 1 index may be selected in a 1 modem system.
		 Changing Programmed Frequency requires a system reset."
	DEFVAL  { notActive }
	::= { hzQtmRadio2TxLowFreqEntry 5 }

hzQtmRadio2ProgrammedFrequencyChannel  OBJECT-TYPE
	SYNTAX     DisplayString
	MAX-ACCESS read-only
	STATUS     current
	DESCRIPTION
		"The channel that has been programmed for Radio 2."
	::= { hzQtmRadio2ProgrammedFrequency 1 }

hzQtmRadio2ProgrammedFrequencyTxRf  OBJECT-TYPE
	SYNTAX     Integer32
	MAX-ACCESS read-only
	STATUS     current
	DESCRIPTION
		"The programmed RF TX frequency in KHz."
	::= { hzQtmRadio2ProgrammedFrequency 2 }

hzQtmRadio2ProgrammedFrequencyRxRf  OBJECT-TYPE
	SYNTAX     Integer32
	MAX-ACCESS read-only
	STATUS     current
	DESCRIPTION
		"The RF RX frequency in KHz."
	::= { hzQtmRadio2ProgrammedFrequency 3 }

-- hzQtmWirelessInterfaceAntenna
-- ----------------------------

hzQtmAntennaDiameter  OBJECT-TYPE
	SYNTAX     INTEGER {
		antenna12 (1),
		antenna24 (2),
		antenna36 (3),
		antenna48 (4),
		antenna72 (5)
	}
	MAX-ACCESS read-only
	STATUS     current
	DESCRIPTION
		"This defines the diameter of the antenna represented in inches."
	::= { hzQtmWirelessInterfaceAntenna 1 }

hzQtmAntenna1Tilt  OBJECT-TYPE
	SYNTAX     INTEGER {
		unknown (1),
		vertical (2),
		horizontal (3),
		flat (4)
	}
	MAX-ACCESS read-only
	STATUS     current
	DESCRIPTION
		"This defines the position of the antenna for radio 1."
	::= { hzQtmWirelessInterfaceAntenna 2 }

hzQtmAntenna2Tilt  OBJECT-TYPE
	SYNTAX     INTEGER {
		unknown (1),
		vertical (2),
		horizontal (3),
		flat (4)
	}
	MAX-ACCESS read-only
	STATUS     current
	DESCRIPTION
		"This defines the position of the antenna for radio 2."
	::= { hzQtmWirelessInterfaceAntenna 3 }

-- --------------------------------
-- hzQtmWirelessInterfaceRedundancy
-- --------------------------------

hzQtmWirelessInterfaceRedundancyActiveWirelessPort  OBJECT-TYPE
	SYNTAX     INTEGER {
		wireless-port-1 (1),
		wireless-port-2 (2),
		none (3)
	}
	MAX-ACCESS read-only
	STATUS     current
	DESCRIPTION
		"This attribute indicates the active wireless port and is only applicable when the system capacity has been configured to singleCarrier-redundancy."
	::= { hzQtmWirelessInterfaceRedundancy 1 }

hzQtmWirelessInterfaceRedundancyPrimaryWirelessPort  OBJECT-TYPE
	SYNTAX     INTEGER {
		wireless-port-1 (1),
		wireless-port-2 (2),
		none (3)
	}
	MAX-ACCESS read-write
	STATUS     current
	DESCRIPTION
		"This attribute indicates the primary wireless port and is only applicable when the system capacity has been configured to singleCarrier-redundancy. The primary wireless port indicates which wireless port is connected to the 'primary' port on the RDRM coupler."
	::= { hzQtmWirelessInterfaceRedundancy 2 }

hzQtmWirelessInterfaceRedundancySwitchingAlgorithm  OBJECT-TYPE
	SYNTAX     INTEGER {
		manual (1),
		algorithm-based (2)
	}
	MAX-ACCESS read-write
	STATUS     current
	DESCRIPTION
		"This attribute selects the rule that will determine when a redundant path switch will take place. There are two options: manual and algorithm-based. The 'Manual' option turns off the automatic path switching feature. Only an operator can switch the active path."
	::= { hzQtmWirelessInterfaceRedundancy 3 }

hzQtmWirelessInterfaceRedundancySwitchCause  OBJECT-TYPE
	SYNTAX     DisplayString
	MAX-ACCESS read-only
	STATUS     current
	DESCRIPTION
		"This string indicates the reason that a redundancy switch has occurred.  If the active port is the primary port then this string is empty."
	::= { hzQtmWirelessInterfaceRedundancy 4 }

hzQtmWirelessInterfaceRedundancyRemoveFaulty  OBJECT-TYPE
	SYNTAX     INTEGER {
		wireless-port-1 (1),
		wireless-port-2 (2)
	}
	MAX-ACCESS read-write
	STATUS     current
	DESCRIPTION
		"This object removes the specified port from the faulty port list."
	::= { hzQtmWirelessInterfaceRedundancy 5 }

-- ---------------------------------------------
--   hzQtmWirelessInterfaceRedundancyDiagnostics
-- ---------------------------------------------

hzQtmWirelessInterfaceRedundancyDiagnose  OBJECT-TYPE
	SYNTAX     INTEGER {
		diagnose (1)
	}
	MAX-ACCESS read-write
	STATUS     current
	DESCRIPTION
		"This write-only object will diagnose problems with switching paths. Write diagnose (1) to this object and check results in hzQtmWirelessInterfaceRedundancyDiagnosticResult object"
	::= { hzQtmWirelessInterfaceRedundancyDiagnostics 1 }

hzQtmWirelessInterfaceRedundancyDiagnosticResult  OBJECT-TYPE
	SYNTAX     DisplayString
	MAX-ACCESS read-only
	STATUS     current
	DESCRIPTION
		"The result from Redundancy Diagnostic is read from this object. Note that the diagnostic result presented in this object is private to SNMP initiated diagnostics.  If a diagnostic is initiated from the CLI or WEB, this result will remain unchanged."
	::= { hzQtmWirelessInterfaceRedundancyDiagnostics 2 }

hzQtmWirelessInterfaceRedundancySwitchRadio  OBJECT-TYPE
	SYNTAX     INTEGER {
		switch (1)
	}
	MAX-ACCESS read-write
	STATUS     current
	DESCRIPTION
		"This write-only object will switch radio redunancy. Write switch (1) to this object and check results in hzQtmWirelessInterfaceRedundancySwitchRadioResult object."
	::= { hzQtmWirelessInterfaceRedundancyRadioSwitch 1 }

hzQtmWirelessInterfaceRedundancySwitchRadioResult  OBJECT-TYPE
	SYNTAX     DisplayString
	MAX-ACCESS read-only
	STATUS     current
	DESCRIPTION
		"The Switch Radio result is presented in this object. "
	::= { hzQtmWirelessInterfaceRedundancyRadioSwitch 2 }

--
-- hzQtmCalendar
--

hzQtmDate  OBJECT-TYPE
	SYNTAX     DisplayString
	MAX-ACCESS read-write
	STATUS     current
	DESCRIPTION
		"A string in the format as follows:
		                                                XX/YY/ZZ
		                                                Where XX = day of month (range 01 to  31)
		                                                YY = month of year(range 01 to 12)
		                                                ZZ = year (range 01 - 99)"
	::= { hzQtmCalendar 1 }

hzQtmTime  OBJECT-TYPE
	SYNTAX     DisplayString
	MAX-ACCESS read-write
	STATUS     current
	DESCRIPTION
		"A string in the format as follows:
		                                                 aa:bb:cc.ddd
		                                                 Where aa = hour of day ( range 00 to 23 )
		                                                       bb = minute of hour ( range 00 to 59 )
		                                                       cc = second of minute( range 00 to 59 )
		                                                       ddd = thousandths of second (range 000 to 999)"
	::= { hzQtmCalendar 2 }

--
-- ALARM FOLDER
--

hzQtmClearAlarmCounters  OBJECT-TYPE
	SYNTAX     INTEGER {
		nicCounters (1),
		modemCounters (2),
		radioCounters (3),
		allCounters (4),
		otherCounters (5)
	}
	MAX-ACCESS read-write
	STATUS     current
	DESCRIPTION
		"Clears the alarm counters for the specified group"
	::= { hzQtmAlarms 1 }

--
-- System Alarms
--

hzQtmExplicitAuthenticationFailureAlarm  OBJECT-TYPE
	SYNTAX     INTEGER {
		off (1),
		on (2)
	}
	MAX-ACCESS read-only
	STATUS     current
	DESCRIPTION
		"Authentication of the peer horizon node has failed. The severity is critical, the probable cause is an incorrect authentication configuration on horizon faulty cable between the modem and radio, and recommended course of action is to check both ends of the link."
	::= { hzQtmSystemAlarms 1 }

hzQtmExplicitAuthenticationFailureCounts  OBJECT-TYPE
	SYNTAX     Counter32
	MAX-ACCESS read-only
	STATUS     current
	DESCRIPTION
		"Indicates the number of times explicit authentication has failed."
	::= { hzQtmSystemAlarms 2 }

hzQtmHitlessAamConfigMismatchAlarm  OBJECT-TYPE
	SYNTAX     INTEGER {
		off (1),
		on (2)
	}
	MAX-ACCESS read-only
	STATUS     current
	DESCRIPTION
		"In the near end Hitless Automatic Adaptive Modulation (HAAM) feature set to on and in peer it is set to off"
	::= { hzQtmSystemAlarms 3 }

hzQtmHitlessAamConfigMismatchCounts  OBJECT-TYPE
	SYNTAX     Counter32
	MAX-ACCESS read-only
	STATUS     current
	DESCRIPTION
		"Indicates the approximate number of seconds Hitless AAM Configuration Mismatch alarm has been active."
	::= { hzQtmSystemAlarms 4 }

hzQtmHitlessAamActiveAlarm  OBJECT-TYPE
	SYNTAX     INTEGER {
		off (1),
		on (2)
	}
	MAX-ACCESS read-only
	STATUS     current
	DESCRIPTION
		"Indicates Hitless AAM is active and system running on lower modulation"
	::= { hzQtmSystemAlarms 5 }

hzQtmHitlessAamActiveCounts  OBJECT-TYPE
	SYNTAX     Counter32
	MAX-ACCESS read-only
	STATUS     current
	DESCRIPTION
		"Indicates the approximate number of seconds Hitless AAM Active alarm has been active."
	::= { hzQtmSystemAlarms 6 }

hzQtmSntpServerUnreachableAlarm  OBJECT-TYPE
	SYNTAX     INTEGER {
		off (1),
		on (2)
	}
	MAX-ACCESS read-only
	STATUS     current
	DESCRIPTION
		"All of the SNTP servers are not available. "
	::= { hzQtmSystemAlarms 7 }

hzQtmSntpServerUnreachableCounts  OBJECT-TYPE
	SYNTAX     Counter32
	MAX-ACCESS read-only
	STATUS     current
	DESCRIPTION
		"Indicates how long in seconds all of the SNTP servers are not available."
	::= { hzQtmSystemAlarms 8 }

hzQtmFrequencyFileInvalidAlarm  OBJECT-TYPE
	SYNTAX     INTEGER {
		off (1),
		on (2)
	}
	MAX-ACCESS read-only
	STATUS     current
	DESCRIPTION
		"Executing frequency file is invalid."
	::= { hzQtmSystemAlarms 9 }

hzQtmFrequencyFileInvalidCounts  OBJECT-TYPE
	SYNTAX     Counter32
	MAX-ACCESS read-only
	STATUS     current
	DESCRIPTION
		"Indicates the time (in secs) since this alarm exist."
	::= { hzQtmSystemAlarms 10 }

hzQtmFanFailureAlarm  OBJECT-TYPE
	SYNTAX     INTEGER {
		off (1),
		on (2)
	}
	MAX-ACCESS read-only
	STATUS     current
	DESCRIPTION
		"Indicates whether any of the two Fans have failed."
	::= { hzQtmSystemAlarms 11 }

hzQtmFanFailureCounts  OBJECT-TYPE
	SYNTAX     Counter32
	MAX-ACCESS read-only
	STATUS     current
	DESCRIPTION
		"Indicates the number of seconds that the fan has failed for."
	::= { hzQtmSystemAlarms 12 }

hzQtmRedundancyPrimaryPortNotSetAlarm  OBJECT-TYPE
	SYNTAX     INTEGER {
		off (1),
		on (2)
	}
	MAX-ACCESS read-only
	STATUS     current
	DESCRIPTION
		"The redundancy primary port used for redundancy has not been set."
	::= { hzQtmSystemAlarms 13 }

hzQtmRedundancyPrimaryPortNotSetCounts  OBJECT-TYPE
	SYNTAX     Counter32
	MAX-ACCESS read-only
	STATUS     current
	DESCRIPTION
		"Indicates the approximate number of seconds that this alarm has been active."
	::= { hzQtmSystemAlarms 14 }

hzQtmRedundancySecondaryPortActiveAlarm  OBJECT-TYPE
	SYNTAX     INTEGER {
		off (1),
		on (2)
	}
	MAX-ACCESS read-only
	STATUS     current
	DESCRIPTION
		"The active wireless port has switched to the secondary wireless port."
	::= { hzQtmSystemAlarms 15 }

hzQtmRedundancySecondaryPortActiveCounts  OBJECT-TYPE
	SYNTAX     Counter32
	MAX-ACCESS read-only
	STATUS     current
	DESCRIPTION
		"Indicates the approximate number of seconds that this alarm has been active."
	::= { hzQtmSystemAlarms 16 }

hzQtmRedundancyPrimaryPortFaultyAlarm  OBJECT-TYPE
	SYNTAX     INTEGER {
		off (1),
		on (2)
	}
	MAX-ACCESS read-only
	STATUS     current
	DESCRIPTION
		"The redundancy primary wireless port is faulty."
	::= { hzQtmSystemAlarms 17 }

hzQtmRedundancyPrimaryPortFaultyCounts  OBJECT-TYPE
	SYNTAX     Counter32
	MAX-ACCESS read-only
	STATUS     current
	DESCRIPTION
		"Indicates the approximate number of seconds that this alarm has been active."
	::= { hzQtmSystemAlarms 18 }

hzQtmRedundancySecondaryPortFaultyAlarm  OBJECT-TYPE
	SYNTAX     INTEGER {
		off (1),
		on (2)
	}
	MAX-ACCESS read-only
	STATUS     current
	DESCRIPTION
		"The redundancy secondary wireless port is faulty."
	::= { hzQtmSystemAlarms 19 }

hzQtmRedundancySecondaryPortFaultyCounts  OBJECT-TYPE
	SYNTAX     Counter32
	MAX-ACCESS read-only
	STATUS     current
	DESCRIPTION
		"Indicates the approximate number of seconds that this alarm has been active."
	::= { hzQtmSystemAlarms 20 }

hzQtmAtpcConfigMismatchAlarm  OBJECT-TYPE
	SYNTAX     INTEGER {
		off (1),
		on (2)
	}
	MAX-ACCESS read-only
	STATUS     current
	DESCRIPTION
		"In the near end ATPC feature is set to on and in peer it is set to off."
	::= { hzQtmSystemAlarms 21 }

hzQtmAtpcConfigMismatchCounts  OBJECT-TYPE
	SYNTAX     Counter32
	MAX-ACCESS read-only
	STATUS     current
	DESCRIPTION
		"Indicates the approximate number of seconds AtpcConfigMismatch alarm has been active."
	::= { hzQtmSystemAlarms 22 }

--
-- NETWORK INTERFACE PORT ALARMS
--

hzQtmDroppedEnetFramesThresholdAlarm  OBJECT-TYPE
	SYNTAX     INTEGER {
		off (1),
		on (2)
	}
	MAX-ACCESS read-only
	STATUS     current
	DESCRIPTION
		"The threshold for number of frames dropped has been exceeded. The threshold and the number of seconds that it must exceed this threshold are programmed by the user."
	::= { hzQtmSystemAlarms 23 }

hzQtmDroppedEnetFramesThresholdCounts  OBJECT-TYPE
	SYNTAX     Counter32
	MAX-ACCESS read-only
	STATUS     current
	DESCRIPTION
		"Indicates the approximate time, in seconds, that this alarm has been in the active state"
	::= { hzQtmSystemAlarms 24 }

hzQtmBandwidthUtilizationThresholdAlarm  OBJECT-TYPE
	SYNTAX     INTEGER {
		off (1),
		on (2)
	}
	MAX-ACCESS read-only
	STATUS     current
	DESCRIPTION
		"The threshold for the percentage of available bandwidth has been exceeded. The threshold and the number of seconds that it must exceed this threshold are programmed by the user."
	::= { hzQtmSystemAlarms 25 }

hzQtmBandwidthUtilizationThresholdCounts  OBJECT-TYPE
	SYNTAX     Counter32
	MAX-ACCESS read-only
	STATUS     current
	DESCRIPTION
		"Indicates the approximate time, in seconds, that this alarm has been in the active state"
	::= { hzQtmSystemAlarms 26 }

hzQtmRlsMismatchAlarm  OBJECT-TYPE
	SYNTAX     INTEGER {
		off (1),
		on (2)
	}
	MAX-ACCESS read-only
	STATUS     current
	DESCRIPTION
		"RLS configurations on the pair of systems are mismatched."
	::= { hzQtmSystemAlarms 27 }

hzQtmRlsMismatchCounts  OBJECT-TYPE
	SYNTAX     Counter32
	MAX-ACCESS read-only
	STATUS     current
	DESCRIPTION
		"Indicates the approximate time, in seconds, that this alarm has been in the active state"
	::= { hzQtmSystemAlarms 28 }

hzQtmRLSQueueBasedShutdownActivatedAlarm  OBJECT-TYPE
	SYNTAX     INTEGER {
		off (1),
		on (2)
	}
	MAX-ACCESS read-only
	STATUS     current
	DESCRIPTION
		"RLS Queue-Based shutdown is activated."
	::= { hzQtmSystemAlarms 29 }

hzQtmRLSQueueBasedShutdownActivatedCounts  OBJECT-TYPE
	SYNTAX     Counter32
	MAX-ACCESS read-only
	STATUS     current
	DESCRIPTION
		"Indicates the approximate time, in seconds, that this alarm has been in the active state"
	::= { hzQtmSystemAlarms 30 }

hzQtmFpgaProgrammingErrorAlarm  OBJECT-TYPE
	SYNTAX     INTEGER {
		off (1),
		on (2)
	}
	MAX-ACCESS read-only
	STATUS     current
	DESCRIPTION
		"Encountered some problem while programming the modem."
	::= { hzQtmSystemAlarms 31 }

hzQtmFpgaProgrammingErrorCounts  OBJECT-TYPE
	SYNTAX     Counter32
	MAX-ACCESS read-only
	STATUS     current
	DESCRIPTION
		"Indicates the approximate number of seconds that this alarm has been active."
	::= { hzQtmSystemAlarms 32 }

hzQtmMibChangeNotSavedAlarm  OBJECT-TYPE
	SYNTAX     INTEGER {
		off (1),
		on (2)
	}
	MAX-ACCESS read-only
	STATUS     current
	DESCRIPTION
		"The system has automatically re-programmed the mib. It requires a save mib action to save the changes to flash, otherwise the changes will be lost on reset.
		View the logs to see what was modified in the mib."
	::= { hzQtmSystemAlarms 33 }

hzQtmMibChangeNotSavedCounts  OBJECT-TYPE
	SYNTAX     Counter32
	MAX-ACCESS read-only
	STATUS     current
	DESCRIPTION
		"Indicates the approximate number of seconds that this alarm has been active."
	::= { hzQtmSystemAlarms 34 }

hzQtmBadSystemConfigurationAlarm  OBJECT-TYPE
	SYNTAX     INTEGER {
		off (1),
		on (2)
	}
	MAX-ACCESS read-only
	STATUS     current
	DESCRIPTION
		"The system has been configured incorrectly. Check the logs or use the CLI get alarms to isolate the cause."
	::= { hzQtmSystemAlarms 35 }

hzQtmBadSystemConfigurationCounts  OBJECT-TYPE
	SYNTAX     Counter32
	MAX-ACCESS read-only
	STATUS     current
	DESCRIPTION
		"Indicates the approximate number of seconds that this alarm has been active."
	::= { hzQtmSystemAlarms 36 }

hzQtmPartnerNodeAlarm  OBJECT-TYPE
	SYNTAX     INTEGER {
		off (1),
		on (2)
	}
	MAX-ACCESS read-only
	STATUS     current
	DESCRIPTION
		"Failed to establish communication or configuration mismatch with the partner node. Check the logs or use the CLI get alarms to isolate the cause.s"
	::= { hzQtmSystemAlarms 37 }

hzQtmPartnerNodeAlarmCounts  OBJECT-TYPE
	SYNTAX     Counter32
	MAX-ACCESS read-only
	STATUS     current
	DESCRIPTION
		"Indicates the approximate number of seconds that this alarm has been active."
	::= { hzQtmSystemAlarms 38 }

hzQtmBandwidthDoublingInvalidLinkConfigAlarm  OBJECT-TYPE
	SYNTAX     INTEGER {
		off (1),
		on (2)
	}
	MAX-ACCESS read-only
	STATUS     current
	DESCRIPTION
		"Bandwidth doubling link is configured wong. i.e., Primary is synchronized with remote primary, and secondary is sychronized with remote secondary."
	::= { hzQtmSystemAlarms 39 }

hzQtmBandwidthDoublingInvalidLinkConfigCounts  OBJECT-TYPE
	SYNTAX     Counter32
	MAX-ACCESS read-only
	STATUS     current
	DESCRIPTION
		"Indicates the approximate number of seconds that this alarm has been active."
	::= { hzQtmSystemAlarms 40 }

hzQtmBandwidthDoublingWrongPortConnectedAlarm  OBJECT-TYPE
	SYNTAX     INTEGER {
		off (1),
		on (2)
	}
	MAX-ACCESS read-only
	STATUS     current
	DESCRIPTION
		"Bandwidth doubling wrong port is connected to local partner."
	::= { hzQtmSystemAlarms 41 }

hzQtmBandwidthDoublingWrongPortConnectedCount  OBJECT-TYPE
	SYNTAX     Counter32
	MAX-ACCESS read-only
	STATUS     current
	DESCRIPTION
		"Indicates the approximate number of seconds that this alarm has been active."
	::= { hzQtmSystemAlarms 42 }

hzQtmSynceLostLockAlarm  OBJECT-TYPE
	SYNTAX     INTEGER {
		off (1),
		on (2)
	}
	MAX-ACCESS read-only
	STATUS     current
	DESCRIPTION
		"SyncE feature is currently out of lock."
	::= { hzQtmSystemAlarms 43 }

hzQtmSynceLostLockCount  OBJECT-TYPE
	SYNTAX     Counter32
	MAX-ACCESS read-only
	STATUS     current
	DESCRIPTION
		"Indicates the approximate number of seconds that this alarm has been active."
	::= { hzQtmSystemAlarms 44 }

hzQtmSynceSecondarySourceInUseAlarm  OBJECT-TYPE
	SYNTAX     INTEGER {
		off (1),
		on (2)
	}
	MAX-ACCESS read-only
	STATUS     current
	DESCRIPTION
		"SyncE feature is synchronized to secondary clock source."
	::= { hzQtmSystemAlarms 45 }

hzQtmSynceSecondarySourceInUseCount  OBJECT-TYPE
	SYNTAX     Counter32
	MAX-ACCESS read-only
	STATUS     current
	DESCRIPTION
		"Indicates the approximate number of seconds that this alarm has been active."
	::= { hzQtmSystemAlarms 46 }

hzQtmEnetPortAlarmsTable  OBJECT-TYPE
	SYNTAX SEQUENCE OF HzQtmEnetPortAlarmsEntry
	MAX-ACCESS not-accessible
	STATUS     current
	DESCRIPTION
		""
	::= { hzQtmNetworkInterfaceAlarms 1 }

hzQtmEnetPortAlarmsEntry  OBJECT-TYPE
	SYNTAX 	HzQtmEnetPortAlarmsEntry
	MAX-ACCESS not-accessible
	STATUS     current
	DESCRIPTION
		""
	INDEX { hzQtmEnetPortAlarmsIndex }
	::= { hzQtmEnetPortAlarmsTable 1 }

HzQtmEnetPortAlarmsEntry ::= SEQUENCE {
	hzQtmEnetPortAlarmsIndex
		INTEGER,
	hzQtmEnetPortEthernetLinkDownAlarm
		INTEGER,
	hzQtmEnetPortEthernetLinkDownCounts
		Counter32
}

hzQtmEnetPortAlarmsIndex  OBJECT-TYPE
	SYNTAX     INTEGER {
		enet-port-1 (1),
		enet-port-2 (2),
		enet-port-3 (3),
		enet-port-4 (4),
		enet-port-5 (5),
		enet-port-6 (6),
		enet-port-7 (7),
		enet-port-8 (8)
	}
	MAX-ACCESS read-only
	STATUS     current
	DESCRIPTION
		""
	::= { hzQtmEnetPortAlarmsEntry 1 }

hzQtmEnetPortEthernetLinkDownAlarm  OBJECT-TYPE
	SYNTAX     INTEGER {
		off (1),
		on (2)
	}
	MAX-ACCESS read-only
	STATUS     current
	DESCRIPTION
		"Indicates whether the Ethernet link is down or not. The severity is major, the probable cause is an incorrect configuration of the switch or router connected to horizon. The recommended course of action is to check the connection."
	::= { hzQtmEnetPortAlarmsEntry 2 }

hzQtmEnetPortEthernetLinkDownCounts  OBJECT-TYPE
	SYNTAX     Counter32
	MAX-ACCESS read-only
	STATUS     current
	DESCRIPTION
		"Indicates the approximate time, in seconds, that this alarm has been in the active state"
	::= { hzQtmEnetPortAlarmsEntry 3 }

--
-- MODEM ALARMS
--

hzQtmModemAlarmsTable  OBJECT-TYPE
	SYNTAX SEQUENCE OF HzQtmModemAlarmsEntry
	MAX-ACCESS not-accessible
	STATUS     current
	DESCRIPTION
		"A table of Modem Alarms."
	::= { hzQtmModemAlarms 1 }

hzQtmModemAlarmsEntry  OBJECT-TYPE
	SYNTAX 	HzQtmModemAlarmsEntry
	MAX-ACCESS not-accessible
	STATUS     current
	DESCRIPTION
		"Modem Alarms"
	INDEX { hzQtmModemAlarmsIndex }
	::= { hzQtmModemAlarmsTable 1 }

HzQtmModemAlarmsEntry ::= SEQUENCE {
	hzQtmModemAlarmsIndex
		INTEGER,
	hzQtmModemRxLossOfSignalAlarm
		INTEGER,
	hzQtmModemRxLossOfSignalCounts
		Counter32,
	hzQtmModemTxLossOfSyncAlarm
		INTEGER,
	hzQtmModemTxLossOfSyncCounts
		Counter32,
	hzQtmModemSnrBelowThresholdAlarm
		INTEGER,
	hzQtmModemSnrBelowThresholdCounts
		Counter32,
	hzQtmModemEqualizerStressExceedThresholdAlarm
		INTEGER,
	hzQtmModemEquilizerStressExceedThresholdCounts
		Counter32,
	hzQtmModemRLSShutdownActivatedAlarm
		INTEGER,
	hzQtmModemRLSShutdownActivatedCounts
		Counter32,
	hzQtmModemXPICEquStressExceedThresholdAlarm
		INTEGER,
	hzQtmModemXPICEquStressExceedThresholdCounts
		Counter32
}

hzQtmModemAlarmsIndex  OBJECT-TYPE
	SYNTAX     INTEGER {
		wireless-port-1 (1),
		wireless-port-2 (2)
	}
	MAX-ACCESS read-only
	STATUS     current
	DESCRIPTION
		"A unique value for each interface. "
	::= { hzQtmModemAlarmsEntry 1 }

hzQtmModemRxLossOfSignalAlarm  OBJECT-TYPE
	SYNTAX     INTEGER {
		off (1),
		on (2)
	}
	MAX-ACCESS read-only
	STATUS     current
	DESCRIPTION
		"Loss of signal lock from the demodulator. The severity is critical, the probable cause is lost synchronization with the far end, and recommended course of action is to check the operational state of both ends of the link."
	::= { hzQtmModemAlarmsEntry 2 }

hzQtmModemRxLossOfSignalCounts  OBJECT-TYPE
	SYNTAX     Counter32
	MAX-ACCESS read-only
	STATUS     current
	DESCRIPTION
		"Indicates the approximate number of seconds that this alarm has been active."
	::= { hzQtmModemAlarmsEntry 3 }

hzQtmModemTxLossOfSyncAlarm  OBJECT-TYPE
	SYNTAX     INTEGER {
		off (1),
		on (2)
	}
	MAX-ACCESS read-only
	STATUS     current
	DESCRIPTION
		"Loss of sync bytes at the input of the modulator. The severity is critical, the probable cause is physical interference in the air link, and recommended course of action is to check the line of site between the horizon nodes."
	::= { hzQtmModemAlarmsEntry 4 }

hzQtmModemTxLossOfSyncCounts  OBJECT-TYPE
	SYNTAX     Counter32
	MAX-ACCESS read-only
	STATUS     current
	DESCRIPTION
		"Indicates the approximate number of seconds that this alarm has been active."
	::= { hzQtmModemAlarmsEntry 5 }

hzQtmModemSnrBelowThresholdAlarm  OBJECT-TYPE
	SYNTAX     INTEGER {
		off (1),
		on (2)
	}
	MAX-ACCESS read-only
	STATUS     current
	DESCRIPTION
		"The demodulator SNR performance worse than programmed levels. The severity is major, the probable cause is physical interference in the air link path or misalignment of the radios or severe weather conditions, and recommended course of action is to check the line of site between the horizon nodes."
	::= { hzQtmModemAlarmsEntry 6 }

hzQtmModemSnrBelowThresholdCounts  OBJECT-TYPE
	SYNTAX     Counter32
	MAX-ACCESS read-only
	STATUS     current
	DESCRIPTION
		"Indicates the approximate number of seconds that this alarm has been active."
	::= { hzQtmModemAlarmsEntry 7 }

hzQtmModemEqualizerStressExceedThresholdAlarm  OBJECT-TYPE
	SYNTAX     INTEGER {
		off (1),
		on (2)
	}
	MAX-ACCESS read-only
	STATUS     current
	DESCRIPTION
		"Equalizer Stress measured within the demodulator exceeds the threshold value."
	::= { hzQtmModemAlarmsEntry 8 }

hzQtmModemEquilizerStressExceedThresholdCounts  OBJECT-TYPE
	SYNTAX     Counter32
	MAX-ACCESS read-only
	STATUS     current
	DESCRIPTION
		"Indicates the approximate number of seconds that this alarm has been active."
	::= { hzQtmModemAlarmsEntry 9 }

hzQtmModemRLSShutdownActivatedAlarm  OBJECT-TYPE
	SYNTAX     INTEGER {
		off (1),
		on (2)
	}
	MAX-ACCESS read-only
	STATUS     current
	DESCRIPTION
		"RLS shutdown is activated."
	::= { hzQtmModemAlarmsEntry 10 }

hzQtmModemRLSShutdownActivatedCounts  OBJECT-TYPE
	SYNTAX     Counter32
	MAX-ACCESS read-only
	STATUS     current
	DESCRIPTION
		"Indicates the approximate time, in seconds, that this alarm has been in the active state"
	::= { hzQtmModemAlarmsEntry 11 }

hzQtmModemXPICEquStressExceedThresholdAlarm  OBJECT-TYPE
	SYNTAX     INTEGER {
		off (1),
		on (2)
	}
	MAX-ACCESS read-only
	STATUS     current
	DESCRIPTION
		"XPIC Equalizer Stress measured within the demodulator exceeds the threshold value."
	::= { hzQtmModemAlarmsEntry 12 }

hzQtmModemXPICEquStressExceedThresholdCounts  OBJECT-TYPE
	SYNTAX     Counter32
	MAX-ACCESS read-only
	STATUS     current
	DESCRIPTION
		"Indicates the approximate number of seconds that this alarm has been active."
	::= { hzQtmModemAlarmsEntry 13 }

--
-- RADIO ALARMS
--

hzQtmRadioAlarmsTable  OBJECT-TYPE
	SYNTAX SEQUENCE OF HzQtmRadioAlarmsEntry
	MAX-ACCESS not-accessible
	STATUS     current
	DESCRIPTION
		"A table of Radio Alarms."
	::= { hzQtmRadioAlarms 1 }

hzQtmRadioAlarmsEntry  OBJECT-TYPE
	SYNTAX 	HzQtmRadioAlarmsEntry
	MAX-ACCESS not-accessible
	STATUS     current
	DESCRIPTION
		"Radio Alarms"
	INDEX { hzQtmRadioAlarmsIndex }
	::= { hzQtmRadioAlarmsTable 1 }

HzQtmRadioAlarmsEntry ::= SEQUENCE {
	hzQtmRadioAlarmsIndex
		INTEGER,
	hzQtmRadioSynthLostLockAlarm
		INTEGER,
	hzQtmRadioSynthLostLockCounts
		Counter32,
	hzQtmRadioLostCommunicationAlarm
		INTEGER,
	hzQtmRadioLostCommunicationCounts
		Counter32,
	hzQtmRadioMismatchAlarm
		INTEGER,
	hzQtmRadioMismatchCounts
		Counter32,
	hzQtmRadioPowerAmpAlarm
		INTEGER,
	hzQtmRadioPowerAmpCounts
		Counter32,
	hzQtmRadioExcessiveTxCableLossAlarm
		INTEGER,
	hzQtmRadioExcessiveTxCableLossCounts
		Counter32,
	hzQtmRadioRslBelowThresholdAlarm
		INTEGER,
	hzQtmRadioRslBelowThresholdCounts
		Counter32,
	hzQtmRadioHighPowerTxDetectorAlarm
		INTEGER,
	hzQtmRadioHighPowerTxDetectorCounts
		Counter32,
	hzQtmRadioRedundancySerialNumMismatchAlarm
		INTEGER,
	hzQtmRadioRedundancySerialNumMismatchCounts
		Counter32,
	hzQtmRadioExcessiveTxCableLossChangeAlarm
		INTEGER,
	hzQtmRadioExcessiveTxCableLossChangeCounts
		Counter32,
	hzQtmRadioExcessiveRxCableLossAlarm
		INTEGER,
	hzQtmRadioExcessiveRxCableLossCounts
		Counter32,
	hzQtmRadioAtpcTxAtMaxPowerAlarm
		INTEGER,
	hzQtmRadioAtpcTxAtMaxPowerCounts
		Counter32,
	hzQtmRadioSwDownloadFailedAlarm
		INTEGER,
	hzQtmRadioSwDownloadFailedCounts
		Counter32,
	hzQtmRadioDrainCurrentAlarm
		INTEGER,
	hzQtmRadioDrainCurrentCounts
		Counter32,
	hzQtmRadioPowerOffAlarm
		INTEGER,
	hzQtmRadioPowerOffCounts
		Counter32
}

hzQtmRadioAlarmsIndex  OBJECT-TYPE
	SYNTAX     INTEGER {
		wireless-port-1 (1),
		wireless-port-2 (2)
	}
	MAX-ACCESS read-only
	STATUS     current
	DESCRIPTION
		"A unique value for each radio interface. "
	::= { hzQtmRadioAlarmsEntry 1 }

hzQtmRadioSynthLostLockAlarm  OBJECT-TYPE
	SYNTAX     INTEGER {
		off (1),
		on (2)
	}
	MAX-ACCESS read-only
	STATUS     current
	DESCRIPTION
		"The radio synthesizer has lost lock. The severity is critical, the probable cause is a faulty radio and recommended course of action is to replace the radio unit."
	::= { hzQtmRadioAlarmsEntry 2 }

hzQtmRadioSynthLostLockCounts  OBJECT-TYPE
	SYNTAX     Counter32
	MAX-ACCESS read-only
	STATUS     current
	DESCRIPTION
		"Indicates the approximate number of seconds that this alarm has been active."
	::= { hzQtmRadioAlarmsEntry 3 }

hzQtmRadioLostCommunicationAlarm  OBJECT-TYPE
	SYNTAX     INTEGER {
		off (1),
		on (2)
	}
	MAX-ACCESS read-only
	STATUS     current
	DESCRIPTION
		"RS232 communication lost between IDU and the radio. The severity is critical, the probable cause is a faulty cable between the modem and radio, and recommended course of action is to check the connection."
	::= { hzQtmRadioAlarmsEntry 4 }

hzQtmRadioLostCommunicationCounts  OBJECT-TYPE
	SYNTAX     Counter32
	MAX-ACCESS read-only
	STATUS     current
	DESCRIPTION
		"Indicates the approximate number of seconds that this alarm has been active."
	::= { hzQtmRadioAlarmsEntry 5 }

hzQtmRadioMismatchAlarm  OBJECT-TYPE
	SYNTAX     INTEGER {
		off (1),
		on (2)
	}
	MAX-ACCESS read-only
	STATUS     current
	DESCRIPTION
		"The radio connected to the IDU modem does not match the frequency programmed into the modem unit. The severity is major, the probable cause is an incorrectly programmed modem or an incorrect radio type connected to the modem, and recommended course of action is to check the modem frequency settings and radio hardware version number or serial number."
	::= { hzQtmRadioAlarmsEntry 6 }

hzQtmRadioMismatchCounts  OBJECT-TYPE
	SYNTAX     Counter32
	MAX-ACCESS read-only
	STATUS     current
	DESCRIPTION
		"Indicates the approximate number of seconds that this alarm has been active."
	::= { hzQtmRadioAlarmsEntry 7 }

hzQtmRadioPowerAmpAlarm  OBJECT-TYPE
	SYNTAX     INTEGER {
		off (1),
		on (2)
	}
	MAX-ACCESS read-only
	STATUS     current
	DESCRIPTION
		"The power amplifier on the radio is not operating within normal operating specifications. The severity is critical, the probable cause a faulty radio unit, and recommended course of action is to replace the radio unit."
	::= { hzQtmRadioAlarmsEntry 8 }

hzQtmRadioPowerAmpCounts  OBJECT-TYPE
	SYNTAX     Counter32
	MAX-ACCESS read-only
	STATUS     current
	DESCRIPTION
		"Indicates the approximate number of seconds that this alarm has been active."
	::= { hzQtmRadioAlarmsEntry 9 }

hzQtmRadioExcessiveTxCableLossAlarm  OBJECT-TYPE
	SYNTAX     INTEGER {
		off (1),
		on (2)
	}
	MAX-ACCESS read-only
	STATUS     current
	DESCRIPTION
		""
	::= { hzQtmRadioAlarmsEntry 10 }

hzQtmRadioExcessiveTxCableLossCounts  OBJECT-TYPE
	SYNTAX     Counter32
	MAX-ACCESS read-only
	STATUS     current
	DESCRIPTION
		"Indicates the approximate number of seconds that this alarm has been active."
	::= { hzQtmRadioAlarmsEntry 11 }

hzQtmRadioRslBelowThresholdAlarm  OBJECT-TYPE
	SYNTAX     INTEGER {
		off (1),
		on (2)
	}
	MAX-ACCESS read-only
	STATUS     current
	DESCRIPTION
		"The minimum radio receive signal level threshold has been crossed. The severity is major, the probable cause is physical interference in the air link path or misalignment of the radios or severe weather conditions, and recommended course of action is to check the line of site between the air pair nodes."
	::= { hzQtmRadioAlarmsEntry 12 }

hzQtmRadioRslBelowThresholdCounts  OBJECT-TYPE
	SYNTAX     Counter32
	MAX-ACCESS read-only
	STATUS     current
	DESCRIPTION
		"Indicates the approximate number of seconds that this alarm has been active."
	::= { hzQtmRadioAlarmsEntry 13 }

hzQtmRadioHighPowerTxDetectorAlarm  OBJECT-TYPE
	SYNTAX     INTEGER {
		off (1),
		on (2)
	}
	MAX-ACCESS read-only
	STATUS     current
	DESCRIPTION
		"This applies to High Power Radios only. Indicates minimum power threshold has not been surpassed."
	::= { hzQtmRadioAlarmsEntry 14 }

hzQtmRadioHighPowerTxDetectorCounts  OBJECT-TYPE
	SYNTAX     Counter32
	MAX-ACCESS read-only
	STATUS     current
	DESCRIPTION
		"Indicates the approximate number of seconds that this alarm has been active."
	::= { hzQtmRadioAlarmsEntry 15 }

hzQtmRadioRedundancySerialNumMismatchAlarm  OBJECT-TYPE
	SYNTAX     INTEGER {
		off (1),
		on (2)
	}
	MAX-ACCESS read-only
	STATUS     current
	DESCRIPTION
		"The radio serial number programmed in flash and radio do not match."
	::= { hzQtmRadioAlarmsEntry 16 }

hzQtmRadioRedundancySerialNumMismatchCounts  OBJECT-TYPE
	SYNTAX     Counter32
	MAX-ACCESS read-only
	STATUS     current
	DESCRIPTION
		"Indicates the approximate number of seconds that this alarm has been active."
	::= { hzQtmRadioAlarmsEntry 17 }

hzQtmRadioExcessiveTxCableLossChangeAlarm  OBJECT-TYPE
	SYNTAX     INTEGER {
		off (1),
		on (2)
	}
	MAX-ACCESS read-only
	STATUS     current
	DESCRIPTION
		"Cable loss change exceeds the threshold."
	::= { hzQtmRadioAlarmsEntry 18 }

hzQtmRadioExcessiveTxCableLossChangeCounts  OBJECT-TYPE
	SYNTAX     Counter32
	MAX-ACCESS read-only
	STATUS     current
	DESCRIPTION
		"Indicates the approximate number of seconds that this alarm has been active."
	::= { hzQtmRadioAlarmsEntry 19 }

hzQtmRadioExcessiveRxCableLossAlarm  OBJECT-TYPE
	SYNTAX     INTEGER {
		off (1),
		on (2)
	}
	MAX-ACCESS read-only
	STATUS     current
	DESCRIPTION
		"Rx gain can not be adjusted to desired value."
	::= { hzQtmRadioAlarmsEntry 20 }

hzQtmRadioExcessiveRxCableLossCounts  OBJECT-TYPE
	SYNTAX     Counter32
	MAX-ACCESS read-only
	STATUS     current
	DESCRIPTION
		"Indicates the approximate number of seconds that this alarm has been active."
	::= { hzQtmRadioAlarmsEntry 21 }

hzQtmRadioAtpcTxAtMaxPowerAlarm  OBJECT-TYPE
	SYNTAX     INTEGER {
		off (1),
		on (2)
	}
	MAX-ACCESS read-only
	STATUS     current
	DESCRIPTION
		"ATPC auto-disabled (transmitting at coordinated power)."
	::= { hzQtmRadioAlarmsEntry 22 }

hzQtmRadioAtpcTxAtMaxPowerCounts  OBJECT-TYPE
	SYNTAX     Counter32
	MAX-ACCESS read-only
	STATUS     current
	DESCRIPTION
		"Indicates the approximate number of seconds that this alarm has been active."
	::= { hzQtmRadioAlarmsEntry 23 }

hzQtmRadioSwDownloadFailedAlarm  OBJECT-TYPE
	SYNTAX     INTEGER {
		off (1),
		on (2)
	}
	MAX-ACCESS read-only
	STATUS     current
	DESCRIPTION
		"Radio is failing to download the software on startup."
	::= { hzQtmRadioAlarmsEntry 24 }

hzQtmRadioSwDownloadFailedCounts  OBJECT-TYPE
	SYNTAX     Counter32
	MAX-ACCESS read-only
	STATUS     current
	DESCRIPTION
		"Indicates the approximate number of seconds that this alarm has been active."
	::= { hzQtmRadioAlarmsEntry 25 }

hzQtmRadioDrainCurrentAlarm  OBJECT-TYPE
	SYNTAX     INTEGER {
		off (1),
		on (2)
	}
	MAX-ACCESS read-only
	STATUS     current
	DESCRIPTION
		"The drain current on the radio is not operating within normal operating specifications. The severity is critical, the probable cause a faulty radio unit, and recommended course of action is to replace the radio unit."
	::= { hzQtmRadioAlarmsEntry 26 }

hzQtmRadioDrainCurrentCounts  OBJECT-TYPE
	SYNTAX     Counter32
	MAX-ACCESS read-only
	STATUS     current
	DESCRIPTION
		""
	::= { hzQtmRadioAlarmsEntry 27 }

hzQtmRadioPowerOffAlarm  OBJECT-TYPE
	SYNTAX     INTEGER {
		off (1),
		on (2)
	}
	MAX-ACCESS read-only
	STATUS     current
	DESCRIPTION
		"Radio power is off (potential IF cable short detection). "
	::= { hzQtmRadioAlarmsEntry 28 }

hzQtmRadioPowerOffCounts  OBJECT-TYPE
	SYNTAX     Counter32
	MAX-ACCESS read-only
	STATUS     current
	DESCRIPTION
		"Indicates the approximate number of seconds that this alarm has been active."
	::= { hzQtmRadioAlarmsEntry 29 }

--
-- IF ALARMS
--

hzQtmIFAlarmsTable  OBJECT-TYPE
	SYNTAX SEQUENCE OF HzQtmIFAlarmsEntry
	MAX-ACCESS not-accessible
	STATUS     current
	DESCRIPTION
		"A table of IF Alarms."
	::= { hzQtmIFAlarms 1 }

hzQtmIFAlarmsEntry  OBJECT-TYPE
	SYNTAX 	HzQtmIFAlarmsEntry
	MAX-ACCESS not-accessible
	STATUS     current
	DESCRIPTION
		"IF Alarms"
	INDEX { hzQtmIFAlarmsIndex }
	::= { hzQtmIFAlarmsTable 1 }

HzQtmIFAlarmsEntry ::= SEQUENCE {
	hzQtmIFAlarmsIndex
		INTEGER,
	hzQtmIFLostLockAlarm
		INTEGER,
	hzQtmIFLostLockCounts
		Counter32
}

hzQtmIFAlarmsIndex  OBJECT-TYPE
	SYNTAX     INTEGER {
		wireless-path-1 (1),
		wireless-path-2 (2)
	}
	MAX-ACCESS read-only
	STATUS     current
	DESCRIPTION
		"A unique value for each IF path. "
	::= { hzQtmIFAlarmsEntry 1 }

hzQtmIFLostLockAlarm  OBJECT-TYPE
	SYNTAX     INTEGER {
		off (1),
		on (2)
	}
	MAX-ACCESS read-only
	STATUS     current
	DESCRIPTION
		"The IF synthesizer has lost lock."
	::= { hzQtmIFAlarmsEntry 2 }

hzQtmIFLostLockCounts  OBJECT-TYPE
	SYNTAX     Counter32
	MAX-ACCESS read-only
	STATUS     current
	DESCRIPTION
		"Indicates the approximate number of seconds that this alarm has been active."
	::= { hzQtmIFAlarmsEntry 3 }

--
-- TRAP INFORMATION HOSTS, ENABLE/DISABLE
--

hzQtmSnmpTrapHostTable  OBJECT-TYPE
	SYNTAX SEQUENCE OF HzQtmSnmpTrapHostEntry
	MAX-ACCESS not-accessible
	STATUS     current
	DESCRIPTION
		"Table containing SNMP trap host entries."
	::= { hzQtmTrapConfig 1 }

hzQtmSnmpTrapHostEntry  OBJECT-TYPE
	SYNTAX 	HzQtmSnmpTrapHostEntry
	MAX-ACCESS not-accessible
	STATUS     current
	DESCRIPTION
		"The snmp trap host entry containing all the trap host information"
	INDEX { hzQtmSnmpTrapHostIndex }
	::= { hzQtmSnmpTrapHostTable 1 }

HzQtmSnmpTrapHostEntry ::= SEQUENCE {
	hzQtmSnmpTrapHostIndex
		Integer32,
	hzQtmSnmpTrapHostMode
		INTEGER,
	hzQtmSnmpTrapHostIpAddress
		IpAddress,
	hzQtmSnmpTrapHostCommunityName
		DisplayString,
	hzQtmSnmpTrapHostActivated
		INTEGER
}

hzQtmSnmpTrapHostIndex  OBJECT-TYPE
	SYNTAX     Integer32
	MAX-ACCESS read-only
	STATUS     current
	DESCRIPTION
		"A unique value for each trap host. "
	::= { hzQtmSnmpTrapHostEntry 1 }

hzQtmSnmpTrapHostMode  OBJECT-TYPE
	SYNTAX     INTEGER {
		static (1),
		dns (2)
	}
	MAX-ACCESS read-only
	STATUS     current
	DESCRIPTION
		"Indicates how the snmp trap host is obtained for the system."
	::= { hzQtmSnmpTrapHostEntry 2 }

hzQtmSnmpTrapHostIpAddress  OBJECT-TYPE
	SYNTAX     IpAddress
	MAX-ACCESS read-only
	STATUS     current
	DESCRIPTION
		"Indicates snmp trap host IP address. "
	::= { hzQtmSnmpTrapHostEntry 3 }

hzQtmSnmpTrapHostCommunityName  OBJECT-TYPE
	SYNTAX     DisplayString (SIZE(0..24))
	MAX-ACCESS read-only
	STATUS     current
	DESCRIPTION
		"The community string name used in Traps."
	::= { hzQtmSnmpTrapHostEntry 4 }

hzQtmSnmpTrapHostActivated  OBJECT-TYPE
	SYNTAX     INTEGER {
		notActive (1),
		active (2)
	}
	MAX-ACCESS read-only
	STATUS     current
	DESCRIPTION
		"Specifies whether traps are to be sent to this specific host or not"
	::= { hzQtmSnmpTrapHostEntry 5 }

--
-- SNMP V3 TRAP HOST TABLE
--

hzQtmSnmpV3TrapHostsTable  OBJECT-TYPE
	SYNTAX SEQUENCE OF HzQtmSnmpV3TrapHostsEntry
	MAX-ACCESS not-accessible
	STATUS     current
	DESCRIPTION
		"Table containing snmp V3 trap host entries"
	::= { hzQtmTrapConfig 2 }

hzQtmSnmpV3TrapHostsEntry  OBJECT-TYPE
	SYNTAX 	HzQtmSnmpV3TrapHostsEntry
	MAX-ACCESS not-accessible
	STATUS     current
	DESCRIPTION
		"Contains the snmp v3 trap host information"
	INDEX { hzQtmSnmpV3TrapHostsIndex }
	::= { hzQtmSnmpV3TrapHostsTable 1 }

HzQtmSnmpV3TrapHostsEntry ::= SEQUENCE {
	hzQtmSnmpV3TrapHostsIndex
		Integer32,
	snmpV3TrapHostIpAddress
		IpAddress,
	snmpV3TrapHostUserName
		DisplayString,
	snmpV3TrapHostAuthProtocol
		INTEGER,
	snmpV3TrapHostAuthPassword
		DisplayString,
	snmpV3TrapHostPrivProtocol
		INTEGER,
	snmpV3TrapHostPrivPassword
		DisplayString,
	snmpV3TrapHostActivated
		INTEGER
}

hzQtmSnmpV3TrapHostsIndex  OBJECT-TYPE
	SYNTAX     Integer32 (0..4)
	MAX-ACCESS read-only
	STATUS     current
	DESCRIPTION
		"A unique value for each v3 trap host."
	::= { hzQtmSnmpV3TrapHostsEntry 1 }

snmpV3TrapHostIpAddress  OBJECT-TYPE
	SYNTAX     IpAddress
	MAX-ACCESS read-only
	STATUS     current
	DESCRIPTION
		"Indicates snmp trap host IP address. "
	::= { hzQtmSnmpV3TrapHostsEntry 2 }

snmpV3TrapHostUserName  OBJECT-TYPE
	SYNTAX     DisplayString (SIZE(0..24))
	MAX-ACCESS read-only
	STATUS     current
	DESCRIPTION
		"The user name of the v3 trap host."
	::= { hzQtmSnmpV3TrapHostsEntry 3 }

snmpV3TrapHostAuthProtocol  OBJECT-TYPE
	SYNTAX     INTEGER {
		noAuth (1),
		md5 (2),
		sha (3)
	}
	MAX-ACCESS read-only
	STATUS     current
	DESCRIPTION
		"The authentication alogorithm used by the v3 trap host."
	::= { hzQtmSnmpV3TrapHostsEntry 4 }

snmpV3TrapHostAuthPassword  OBJECT-TYPE
	SYNTAX     DisplayString (SIZE(0..24))
	MAX-ACCESS read-only
	STATUS     current
	DESCRIPTION
		"The authentication password of the v3 trap host."
	::= { hzQtmSnmpV3TrapHostsEntry 5 }

snmpV3TrapHostPrivProtocol  OBJECT-TYPE
	SYNTAX     INTEGER {
		noPriv (1),
		des (2)
	}
	MAX-ACCESS read-only
	STATUS     current
	DESCRIPTION
		"The privacy encryption alogorithm used by the v3 trap host."
	::= { hzQtmSnmpV3TrapHostsEntry 6 }

snmpV3TrapHostPrivPassword  OBJECT-TYPE
	SYNTAX     DisplayString (SIZE(0..24))
	MAX-ACCESS read-only
	STATUS     current
	DESCRIPTION
		"The privacy password of the v3 trap host."
	::= { hzQtmSnmpV3TrapHostsEntry 7 }

snmpV3TrapHostActivated  OBJECT-TYPE
	SYNTAX     INTEGER {
		notActive (1),
		active (2)
	}
	MAX-ACCESS read-only
	STATUS     current
	DESCRIPTION
		"Specifies whether a specific v3 trap host is allowed to access the system"
	::= { hzQtmSnmpV3TrapHostsEntry 8 }

hzQtmColdStartTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 1 }

hzQtmLinkDownTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 2 }

hzQtmLinkUpTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 3 }

hzQtmExplicitAuthenticationFailureTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 4 }

hzQtmHitlessAamConfigMismatchTrap  OBJECT-TYPE
	SYNTAX     INTEGER {
		disabled (1),
		enabled (2)
	}
	MAX-ACCESS read-write
	STATUS     current
	DESCRIPTION
		"Enables or disables the Hitless Aam ConfigMismatch trap. "
	DEFVAL  { disabled }
	::= { hzQtmTrapEnable 5 }

hzQtmHitlessAamActiveTrap  OBJECT-TYPE
	SYNTAX     INTEGER {
		disabled (1),
		enabled (2)
	}
	MAX-ACCESS read-write
	STATUS     current
	DESCRIPTION
		"Enables or disables the Hitless AAM Active trap. "
	DEFVAL  { disabled }
	::= { hzQtmTrapEnable 6 }

hzQtmAtpcConfigMismatchTrap  OBJECT-TYPE
	SYNTAX     INTEGER {
		disabled (1),
		enabled (2)
	}
	MAX-ACCESS read-write
	STATUS     current
	DESCRIPTION
		"Enables or disables the trap. "
	DEFVAL  { disabled }
	::= { hzQtmTrapEnable 7 }

hzQtmSntpServersUnreachableTrap  OBJECT-TYPE
	SYNTAX     INTEGER {
		disabled (1),
		enabled (2)
	}
	MAX-ACCESS read-write
	STATUS     current
	DESCRIPTION
		"Enables or disables the trap. "
	DEFVAL  { disabled }
	::= { hzQtmTrapEnable 8 }

hzQtmFrequencyFileInvalidTrap  OBJECT-TYPE
	SYNTAX     INTEGER {
		disabled (1),
		enabled (2)
	}
	MAX-ACCESS read-write
	STATUS     current
	DESCRIPTION
		"Enables or disables the trap. "
	DEFVAL  { disabled }
	::= { hzQtmTrapEnable 9 }

hzQtmEnetPortDroppedFramesThresholdExceedTrap  OBJECT-TYPE
	SYNTAX     INTEGER {
		disabled (1),
		enabled (2)
	}
	MAX-ACCESS read-write
	STATUS     current
	DESCRIPTION
		"Enables or disables the trap."
	DEFVAL  { disabled }
	::= { hzQtmTrapEnable 10 }

hzQtmEnetPortBandwidthUtilizationThresholdExceedTrap  OBJECT-TYPE
	SYNTAX     INTEGER {
		disabled (1),
		enabled (2)
	}
	MAX-ACCESS read-write
	STATUS     current
	DESCRIPTION
		"Enables or disables the trap."
	DEFVAL  { disabled }
	::= { hzQtmTrapEnable 11 }

hzQtmEnetPortRlsMismatchTrap  OBJECT-TYPE
	SYNTAX     INTEGER {
		disabled (1),
		enabled (2)
	}
	MAX-ACCESS read-write
	STATUS     current
	DESCRIPTION
		"Enables or disables the trap. "
	DEFVAL  { disabled }
	::= { hzQtmTrapEnable 12 }

hzQtmRLSQueueBasedShutdownActivatedTrap  OBJECT-TYPE
	SYNTAX     INTEGER {
		disabled (1),
		enabled (2)
	}
	MAX-ACCESS read-write
	STATUS     current
	DESCRIPTION
		"Enables or disables the Queue-Based RLS Shutdown trap. "
	DEFVAL  { disabled }
	::= { hzQtmTrapEnable 13 }

hzQtmModemRxLossOfSignalLockTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 14 }

hzQtmModemTxLossOfSyncTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 15 }

hzQtmModemSnrBelowThresholdTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 16 }

hzQtmModemEqualizerStressExceedThresholdTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 17 }

hzQtmModemChannelizedRslBelowThresholdTrap  OBJECT-TYPE
	SYNTAX     INTEGER {
		disabled (1),
		enabled (2)
	}
	MAX-ACCESS read-write
	STATUS     current
	DESCRIPTION
		"Enables or disables the trap."
	DEFVAL  { disabled }
	::= { hzQtmTrapEnable 18 }

hzQtmFpgaProgrammingErrorTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 19 }

hzQtmUserManagementSessionCommencedTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 20 }

hzQtmUserManagementSessionTerminatedTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 21 }

hzQtmAtpcTxAtMaxPwrTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 22 }

hzQtmRadioSynthLostLockTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 23 }

hzQtmRadioLostCommunicationTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 24 }

hzQtmRadioMismatchTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 25 }

hzQtmRadioPowerAmpTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 26 }

hzQtmRadioExcessiveTxCableLossTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 27 }

hzQtmHiPowerRadioTxDetectorTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 28 }

hzQtmSecondaryRadioIsActiveTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 29 }

hzQtmRedundancySerialNumberMisMatchTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 30 }

hzQtmRadioFirmwareMismatchTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 31 }

hzQtmSecondaryRadioNotdetectedTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 32 }

hzQtmPrimaryRadioNotdetectedTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 33 }

hzQtmFaultyPrimaryRadioTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 34 }

hzQtmRadioExcessiveTxCableLossChangeTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 35 }

hzQtmRadioExcessiveRxCableLossTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 36 }

hzQtmRedundancyPrimaryPortNotSetTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 37 }

hzQtmRedundancySecondaryPortIsActiveTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 38 }

hzQtmRedundancyPrimaryPortFaultyTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 39 }

hzQtmRedundancySecondaryPortFaultyTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 40 }

hzQtmFanFailedTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 41 }

hzQtmModemRlsShutdownActivatedTrap  OBJECT-TYPE
	SYNTAX     INTEGER {
		disabled (1),
		enabled (2)
	}
	MAX-ACCESS read-write
	STATUS     current
	DESCRIPTION
		"Enables or disables the RLS Shutdown trap. "
	DEFVAL  { disabled }
	::= { hzQtmTrapEnable 42 }

hzQtmRadioUnitHwChangedTrap  OBJECT-TYPE
	SYNTAX     INTEGER {
		disabled (1),
		enabled (2)
	}
	MAX-ACCESS read-write
	STATUS     current
	DESCRIPTION
		"Enables or disables the Radio Unit Hardware changed trap. "
	DEFVAL  { disabled }
	::= { hzQtmTrapEnable 43 }

hzQtmRadioSwDownloadFailedTrap  OBJECT-TYPE
	SYNTAX     INTEGER {
		disabled (1),
		enabled (2)
	}
	MAX-ACCESS read-write
	STATUS     current
	DESCRIPTION
		"Enables or disables the Radio software download failure trap. "
	DEFVAL  { disabled }
	::= { hzQtmTrapEnable 44 }

hzQtmRadioRestartedOKTrap  OBJECT-TYPE
	SYNTAX     INTEGER {
		disabled (1),
		enabled (2)
	}
	MAX-ACCESS read-write
	STATUS     current
	DESCRIPTION
		"Enables or disables the Radio restarted OK trap. "
	DEFVAL  { disabled }
	::= { hzQtmTrapEnable 45 }

hzQtmMibChangeNotSavedTrap  OBJECT-TYPE
	SYNTAX     INTEGER {
		disabled (1),
		enabled (2)
	}
	MAX-ACCESS read-write
	STATUS     current
	DESCRIPTION
		"Enables or disables the 'Mib changed not saved' trap. "
	DEFVAL  { disabled }
	::= { hzQtmTrapEnable 46 }

hzQtmRadioDrainCurrentTrap  OBJECT-TYPE
	SYNTAX     INTEGER {
		disabled (1),
		enabled (2)
	}
	MAX-ACCESS read-write
	STATUS     current
	DESCRIPTION
		"Enables or disables the Radio Drain Current trap. "
	DEFVAL  { disabled }
	::= { hzQtmTrapEnable 47 }

hzQtmIFLostLockTrap  OBJECT-TYPE
	SYNTAX     INTEGER {
		disabled (1),
		enabled (2)
	}
	MAX-ACCESS read-write
	STATUS     current
	DESCRIPTION
		"Enables or disables the 'IF Synthesizer Lost Lock' trap. "
	DEFVAL  { disabled }
	::= { hzQtmTrapEnable 48 }

hzQtmInvalidSystemConfigurationTrap  OBJECT-TYPE
	SYNTAX     INTEGER {
		disabled (1),
		enabled (2)
	}
	MAX-ACCESS read-write
	STATUS     current
	DESCRIPTION
		"Enables or disables the Invalid System Configuration trap. "
	::= { hzQtmTrapEnable 49 }

hzQtmHitlessAamEventTrap  OBJECT-TYPE
	SYNTAX     INTEGER {
		disabled (1),
		enabled (2)
	}
	MAX-ACCESS read-write
	STATUS     current
	DESCRIPTION
		"Enables or disables the Hitless AAM Event trap. "
	::= { hzQtmTrapEnable 50 }

hzQtmModemXPICEqualizerStressExceedThresholdTrap  OBJECT-TYPE
	SYNTAX     INTEGER {
		disabled (1),
		enabled (2)
	}
	MAX-ACCESS read-write
	STATUS     current
	DESCRIPTION
		"Specifies whether this trap is to be sent or not. "
	::= { hzQtmTrapEnable 51 }

hzQtmPartnerNodeAlarmTrap  OBJECT-TYPE
	SYNTAX     INTEGER {
		disabled (1),
		enabled (2)
	}
	MAX-ACCESS read-write
	STATUS     current
	DESCRIPTION
		"Enables or disables the Partner node trap. "
	::= { hzQtmTrapEnable 52 }

hzQtmBandwidthDoublingInvalidLinkConfigTrap  OBJECT-TYPE
	SYNTAX     INTEGER {
		disabled (1),
		enabled (2)
	}
	MAX-ACCESS read-write
	STATUS     current
	DESCRIPTION
		"Enables or disables the bandwidth doubling invalid link configuration trap"
	::= { hzQtmTrapEnable 53 }

hzQtmBandwidthDoublingWrongPortConnectedTrap  OBJECT-TYPE
	SYNTAX     INTEGER {
		disabled (1),
		enabled (2)
	}
	MAX-ACCESS read-write
	STATUS     current
	DESCRIPTION
		"Enables or disables the bandwidth doubling wrong link connected trap"
	::= { hzQtmTrapEnable 54 }

hzQtmRadioPowerOffTrap  OBJECT-TYPE
	SYNTAX     INTEGER {
		disabled (1),
		enabled (2)
	}
	MAX-ACCESS read-write
	STATUS     current
	DESCRIPTION
		"Specifies whether this trap is to be sent or not. "
	DEFVAL  { disabled }
	::= { hzQtmTrapEnable 55 }

hzQtmSynceLostLockTrap  OBJECT-TYPE
	SYNTAX     INTEGER {
		disabled (1),
		enabled (2)
	}
	MAX-ACCESS read-write
	STATUS     current
	DESCRIPTION
		"Enables or disables this trap."
	::= { hzQtmTrapEnable 56 }

hzQtmSynceSecondarySourceInUseTrap  OBJECT-TYPE
	SYNTAX     INTEGER {
		disabled (1),
		enabled (2)
	}
	MAX-ACCESS read-write
	STATUS     current
	DESCRIPTION
		"Enables or disables this trap."
	::= { hzQtmTrapEnable 57 }


--
-- SNMP MANAGERS
--

hzQtmSnmpUserAccess  OBJECT-TYPE
	SYNTAX     INTEGER {
		explicitManagers (1),
		any (2)
	}
	MAX-ACCESS read-only
	STATUS     current
	DESCRIPTION
		"Specifies the user access to the system. If access is set to 'explicitManagers' then only managers with ip addresses set in snmpManagersTable will be able to gain SNMP access to the system.  If access is set to 'any' then any manager will be able to gain SNMP access to the system"
	::= { hzQtmSnmp 1 }

hzQtmSnmpManagerAnyCommunityName  OBJECT-TYPE
	SYNTAX     DisplayString (SIZE(0..24))
	MAX-ACCESS read-only
	STATUS     current
	DESCRIPTION
		"The community string name used by the 'any' manager."
	::= { hzQtmSnmp 2 }

hzQtmSnmpSetRequests  OBJECT-TYPE
	SYNTAX     INTEGER {
		disabled (1),
		enabled (2)
	}
	MAX-ACCESS read-only
	STATUS     current
	DESCRIPTION
		"Indicates whether SNMP SET requests are allowed."
	::= { hzQtmSnmp 3 }

hzQtmSnmpManagersTable  OBJECT-TYPE
	SYNTAX SEQUENCE OF HzQtmSnmpManagersEntry
	MAX-ACCESS not-accessible
	STATUS     current
	DESCRIPTION
		"Table containing snmp manager entries"
	::= { hzQtmSnmp 4 }

hzQtmSnmpManagersEntry  OBJECT-TYPE
	SYNTAX 	HzQtmSnmpManagersEntry
	MAX-ACCESS not-accessible
	STATUS     current
	DESCRIPTION
		"Contains the snmp manager information"
	INDEX { hzQtmSnmpManagersIndex }
	::= { hzQtmSnmpManagersTable 1 }

HzQtmSnmpManagersEntry ::= SEQUENCE {
	hzQtmSnmpManagersIndex
		Integer32,
	hzQtmSnmpManagerIpAddress
		IpAddress,
	hzQtmSnmpManagerCommunityName
		DisplayString,
	hzQtmSnmpManagerActivated
		INTEGER
}

hzQtmSnmpManagersIndex  OBJECT-TYPE
	SYNTAX     Integer32
	MAX-ACCESS read-only
	STATUS     current
	DESCRIPTION
		"A unique value for each manager."
	::= { hzQtmSnmpManagersEntry 1 }

hzQtmSnmpManagerIpAddress  OBJECT-TYPE
	SYNTAX     IpAddress
	MAX-ACCESS read-only
	STATUS     current
	DESCRIPTION
		"The IP address of the Manager."
	::= { hzQtmSnmpManagersEntry 2 }

hzQtmSnmpManagerCommunityName  OBJECT-TYPE
	SYNTAX     DisplayString (SIZE(0..24))
	MAX-ACCESS read-only
	STATUS     current
	DESCRIPTION
		"The community string name used by the manager."
	::= { hzQtmSnmpManagersEntry 3 }

hzQtmSnmpManagerActivated  OBJECT-TYPE
	SYNTAX     INTEGER {
		notActive (1),
		active (2)
	}
	MAX-ACCESS read-only
	STATUS     current
	DESCRIPTION
		"Specifies whether a specific manager is allowed to access the system"
	::= { hzQtmSnmpManagersEntry 4 }

hzQtmSnmpV3ManagersTable  OBJECT-TYPE
	SYNTAX SEQUENCE OF HzQtmSnmpV3ManagersEntry
	MAX-ACCESS not-accessible
	STATUS     current
	DESCRIPTION
		"Table containing snmp V3 manager entries"
	::= { hzQtmSnmp 5 }

hzQtmSnmpV3ManagersEntry  OBJECT-TYPE
	SYNTAX 	HzQtmSnmpV3ManagersEntry
	MAX-ACCESS not-accessible
	STATUS     current
	DESCRIPTION
		"Contains the snmp v3 manager information"
	INDEX { hzQtmSnmpV3ManagersIndex }
	::= { hzQtmSnmpV3ManagersTable 1 }

HzQtmSnmpV3ManagersEntry ::= SEQUENCE {
	hzQtmSnmpV3ManagersIndex
		Integer32,
	hzQtmSnmpV3ManagerUserName
		DisplayString,
	hzQtmSnmpV3ManagerAuthProtocol
		INTEGER,
	hzQtmSnmpV3ManagerAuthPassword
		DisplayString,
	hzQtmSnmpV3ManagerPrivProtocol
		INTEGER,
	hzQtmSnmpV3ManagerPrivPassword
		DisplayString,
	hzQtmSnmpV3ManagerActivated
		INTEGER
}

hzQtmSnmpV3ManagersIndex  OBJECT-TYPE
	SYNTAX     Integer32
	MAX-ACCESS read-only
	STATUS     current
	DESCRIPTION
		"A unique value for each v3 manager."
	::= { hzQtmSnmpV3ManagersEntry 1 }

hzQtmSnmpV3ManagerUserName  OBJECT-TYPE
	SYNTAX     DisplayString (SIZE(0..24))
	MAX-ACCESS read-only
	STATUS     current
	DESCRIPTION
		"The user name of the v3 Manager."
	::= { hzQtmSnmpV3ManagersEntry 2 }

hzQtmSnmpV3ManagerAuthProtocol  OBJECT-TYPE
	SYNTAX     INTEGER {
		noAuth (1),
		md5 (2),
		sha (3)
	}
	MAX-ACCESS read-only
	STATUS     current
	DESCRIPTION
		"The authentication alogorithm used by the v3 manager."
	::= { hzQtmSnmpV3ManagersEntry 3 }

hzQtmSnmpV3ManagerAuthPassword  OBJECT-TYPE
	SYNTAX     DisplayString (SIZE(0..24))
	MAX-ACCESS read-only
	STATUS     current
	DESCRIPTION
		"The authentication password of the v3 Manager."
	::= { hzQtmSnmpV3ManagersEntry 4 }

hzQtmSnmpV3ManagerPrivProtocol  OBJECT-TYPE
	SYNTAX     INTEGER {
		noPriv (1),
		des (2)
	}
	MAX-ACCESS read-only
	STATUS     current
	DESCRIPTION
		"The privacy encryption alogorithm used by the v3 manager."
	::= { hzQtmSnmpV3ManagersEntry 5 }

hzQtmSnmpV3ManagerPrivPassword  OBJECT-TYPE
	SYNTAX     DisplayString (SIZE(0..24))
	MAX-ACCESS read-only
	STATUS     current
	DESCRIPTION
		"The privacy password of the v3 Manager."
	::= { hzQtmSnmpV3ManagersEntry 6 }

hzQtmSnmpV3ManagerActivated  OBJECT-TYPE
	SYNTAX     INTEGER {
		notActive (1),
		active (2)
	}
	MAX-ACCESS read-only
	STATUS     current
	DESCRIPTION
		"Specifies whether a specific v3 manager is allowed to access the system"
	::= { hzQtmSnmpV3ManagersEntry 7 }

-- ------------------------------
-- hzQtmManagementSessions
-- ------------------------------

hzQtmUserSessionUserTable  OBJECT-TYPE
	SYNTAX SEQUENCE OF HzQtmUserSessionUserEntry
	MAX-ACCESS not-accessible
	STATUS     current
	DESCRIPTION
		"A table of Wireless Interface Radios"
	::= { hzQtmManagementSessions 1 }

hzQtmUserSessionUserEntry  OBJECT-TYPE
	SYNTAX 	HzQtmUserSessionUserEntry
	MAX-ACCESS not-accessible
	STATUS     current
	DESCRIPTION
		"A Wireless Interface Radio"
	INDEX { hzQtmUserSessionUserIndex }
	::= { hzQtmUserSessionUserTable 1 }

HzQtmUserSessionUserEntry ::= SEQUENCE {
	hzQtmUserSessionUserIndex
		INTEGER,
	hzQtmUserSessionUserName
		DisplayString,
	hzQtmUserSessionUserConnectionType
		DisplayString,
	hzQtmUserSessionUserState
		INTEGER
}

hzQtmUserSessionUserIndex  OBJECT-TYPE
	SYNTAX     INTEGER {
		user1 (1),
		user2 (2),
		user3 (3),
		user4 (4),
		user5 (5),
		user6 (6),
		user7 (7),
		user8 (8),
		user9 (9),
		user10 (10),
		user11 (11),
		user12 (12),
		user13 (13),
		user14 (14),
		user15 (15),
		user16 (16),
		user17 (17),
		user18 (18),
		user19 (19),
		user20 (20)
	}
	MAX-ACCESS read-only
	STATUS     current
	DESCRIPTION
		"A unique value for each user."
	::= { hzQtmUserSessionUserEntry 1 }

hzQtmUserSessionUserName  OBJECT-TYPE
	SYNTAX     DisplayString (SIZE(0..32))
	MAX-ACCESS read-only
	STATUS     current
	DESCRIPTION
		"The username of a management session using Telnet or HTTP. The session state variable must be checked to determine if the management session is currently in progress."
	::= { hzQtmUserSessionUserEntry 2 }

hzQtmUserSessionUserConnectionType  OBJECT-TYPE
	SYNTAX     DisplayString
	MAX-ACCESS read-only
	STATUS     current
	DESCRIPTION
		"Either serial port connection or ethernet connection. Ethernet connection may be through any physical port(s) dedicated to management of the equipment."
	::= { hzQtmUserSessionUserEntry 3 }

hzQtmUserSessionUserState  OBJECT-TYPE
	SYNTAX     INTEGER {
		informationNotAvailable (1),
		sessionTerminated (2),
		sessionInProgress (3)
	}
	MAX-ACCESS read-only
	STATUS     current
	DESCRIPTION
		"The state of the session. The session is inProgress if the user is currently logged into the system. The session is terminated if the user has logged out of the system."
	::= { hzQtmUserSessionUserEntry 4 }

--
-- HTTPS group
--

hzQtmHttpEnable  OBJECT-TYPE
	SYNTAX     INTEGER {
		disabled (1),
		enabled (2)
	}
	MAX-ACCESS read-write
	STATUS     current
	DESCRIPTION
		"Indicates whether HTTP is enabled."
	DEFVAL  { disabled }
	::= { hzQtmHttp 1 }

hzQtmHttpSecureCertificateStatus  OBJECT-TYPE
	SYNTAX     DisplayString (SIZE(0..100))
	MAX-ACCESS read-only
	STATUS     current
	DESCRIPTION
		"Returns the HTTPS certificate status"
	::= { hzQtmHttpSecure 1 }

hzQtmHttpSecureAccessForAdminUsers  OBJECT-TYPE
	SYNTAX     INTEGER {
		off (1),
		on (2)
	}
	MAX-ACCESS read-write
	STATUS     current
	DESCRIPTION
		"the HTTPS access requirement for Admin user group."
	::= { hzQtmHttpSecure 2 }

hzQtmHttpSecureAccessForNocUsers  OBJECT-TYPE
	SYNTAX     INTEGER {
		off (1),
		on (2)
	}
	MAX-ACCESS read-write
	STATUS     current
	DESCRIPTION
		"the HTTPS access requirement for Noc user group."
	::= { hzQtmHttpSecure 3 }

hzQtmHttpSecureAccessForSuperUsers  OBJECT-TYPE
	SYNTAX     INTEGER {
		off (1),
		on (2)
	}
	MAX-ACCESS read-write
	STATUS     current
	DESCRIPTION
		"the HTTPS access requirement for Super user group."
	::= { hzQtmHttpSecure 4 }

--
-- Giga Ethernet Qos
--

hzQtmQosEnable  OBJECT-TYPE
	SYNTAX     INTEGER {
		disabled (1),
		enabled (2)
	}
	MAX-ACCESS read-write
	STATUS     current
	DESCRIPTION
		"Indicates whether QOS is enabled. If disabled is selected and cos flow mapping is active on Q1, Q2 or Q3, then cos flow mapping will be disabled."
	DEFVAL  { disabled }
	::= { hzQtmQos 1 }

hzQtmCosType  OBJECT-TYPE
	SYNTAX     INTEGER {
		cosVlan (1),
		cosQinQiTag (2),
		cosQinQoTag (3),
		cosDscp (4),
		cosMplsExp (5)
	}
	MAX-ACCESS read-write
	STATUS     current
	DESCRIPTION
		"Indicates the class of service tag type.  Based on the setting Horizon will use the CoS value in the VLAN tag, or Q-in-Q inner VLAN tag, or Q-in-Q outer VLAN tag."
	DEFVAL  { cosVlan }
	::= { hzQtmQos 2 }

--
-- 802.1p priorities assignment.
--

hzQtmCosQinQiTag  OBJECT-TYPE
	SYNTAX     DisplayString
	MAX-ACCESS read-write
	STATUS     current
	DESCRIPTION
		"Sets the value of the Q-in-Q inner tag. This tag is also used to classify the non-Q-in-Q VLAN. Default value is 0x8100."
	::= { hzQtmQos 3 }

hzQtmCosQinQoTag  OBJECT-TYPE
	SYNTAX     DisplayString
	MAX-ACCESS read-write
	STATUS     current
	DESCRIPTION
		"Sets the value of the Q-in-Q outer VLAN tag.  Default value is 0x8100."
	::= { hzQtmQos 4 }

hzQtmCosQueueMapping  OBJECT-TYPE
	SYNTAX     DisplayString (SIZE(15..32))
	MAX-ACCESS read-write
	STATUS     current
	DESCRIPTION
		"User queue assignments for CoS values 0 to 7.
		                                         There are 4 coS queues. Their corresponding
		                                         queue numbers are 1,2, 3, where 1 is the lowest priority queue and
		                                         4 is the highest priority queue.
		                                         CoS to queue mapping example: 1 1 2 2 3 3 4 4."
	::= { hzQtmQos 5 }

--
-- Queue operation mode
--

hzQtmCosExpediteQueue  OBJECT-TYPE
	SYNTAX     INTEGER {
		disabled (1),
		enabled (2)
	}
	MAX-ACCESS read-write
	STATUS     current
	DESCRIPTION
		"This sets the user queue operation mode. (a) In expedite mode,
		                                        any Queue can be assigned 100% of CIR. Queue 4 is serviced first
		                                        and queue 1 is servcied last.(b) In non expedite mode, the sum of all CIRs
		                                        must be equal to 100%. In this mode higher priority queues
		                                        will be serviced first until that queue is emptied or
		                                        the defined CIR is reached."
	DEFVAL  { disabled }
	::= { hzQtmQos 6 }

--
-- user queues configuration.
--

hzQtmCosQueueCIR  OBJECT-TYPE
	SYNTAX     DisplayString (SIZE(0..32))
	MAX-ACCESS read-write
	STATUS     current
	DESCRIPTION
		"Committed Information Rate (CIR) assignments for CoS queues
		                                         1 to 4. CIR is assigned as the percentage of system current speed.
		                                         When expedite queue is enabled any queue can be assigned 100% bandwidth.
		                                         When expedite queue is disabled the sum of CIR of all queues should be 100."
	::= { hzQtmQos 7 }

hzQtmCosQueueCBS  OBJECT-TYPE
	SYNTAX     DisplayString (SIZE(0..32))
	MAX-ACCESS read-write
	STATUS     current
	DESCRIPTION
		"Comitted Burst Size (CBS) for CoS queues 1 to 4 and queue C. CBS is the percentage
		                                         of total packet buffer size. The sum of CBS's of all 5
		                                         queues must be equal to 100. Minimum CBS assignable to any queue
		                                         is 1."
	::= { hzQtmQos 8 }

hzQtmCosDefaultValue  OBJECT-TYPE
	SYNTAX     Integer32 (0..7)
	MAX-ACCESS read-write
	STATUS     current
	DESCRIPTION
		"Default CoS value assigned to the ethernet
		                                         frames that don't have VLAN or Q-in-Q tag."
	DEFVAL  { 0 }
	::= { hzQtmQos 9 }

--
-- hzQtmCosWfq
--

hzQtmQosPolicy  OBJECT-TYPE
	SYNTAX     INTEGER {
		strict-priority (1),
		wfq (2)
	}
	MAX-ACCESS read-write
	STATUS     current
	DESCRIPTION
		"Sets the Qos policy."
	::= { hzQtmQos 10 }

hzQtmCosWfqWeight  OBJECT-TYPE
	SYNTAX     DisplayString (SIZE(0..32))
	MAX-ACCESS read-write
	STATUS     current
	DESCRIPTION
		"The weight assigned to each of the 4 cos queue.  The wireless bandwidth is distributed amongst the
		queues proportional to their weight.
		                                        The weights have values from 0-15, where 0 is the lowest weight and
		                                        15 is the highest weight.
		                                        Setting the Cos weight example: 1 2 3 4."
	::= { hzQtmQos 11 }

hzQtmCutThroughProcessing  OBJECT-TYPE
	SYNTAX     INTEGER {
		disabled (1),
		enabled (2)
	}
	MAX-ACCESS read-write
	STATUS     current
	DESCRIPTION
		"This value enables or disables the cut through feature in Quantum hardware."
	DEFVAL  { disabled }
	::= { hzQtmQos 12 }

hzQtmCosEcfmFlowMapping  OBJECT-TYPE
	SYNTAX     INTEGER {
		disabled (1),
		q1 (2),
		q2 (3),
		q3 (4),
		q4 (5),
		qC (6)
	}
	MAX-ACCESS read-write
	STATUS     current
	DESCRIPTION
		"Select a queue to route ECFM frames. The mapping is only active when ECFM is disabled. If QoS is disabled then Q1, Q2 and Q3 cannot be selected."
	DEFVAL  { disabled }
	::= { hzQtmQos 13 }

hzQtmCosControlFlowMapping  OBJECT-TYPE
	SYNTAX     INTEGER {
		disabled (1),
		q1 (2),
		q2 (3),
		q3 (4),
		q4 (5),
		qC (6)
	}
	MAX-ACCESS read-write
	STATUS     current
	DESCRIPTION
		"Select a queue to route slow protocol frames (with destination mac address 0x180C200xxxx). If QoS is disabled then Q1, Q2 and Q3 cannot be selected."
	DEFVAL  { disabled }
	::= { hzQtmQos 14 }

--
-- hzQtmRapidLinkShutdown
--

hzQtmRlsEnable  OBJECT-TYPE
	SYNTAX     INTEGER {
		disabled (1),
		enabled (2)
	}
	MAX-ACCESS read-write
	STATUS     current
	DESCRIPTION
		"The Rapid Link Shutdown feature: enabled or disabled.

		  Note: Changing this option requires a system reset."
	DEFVAL  { disabled }
	::= { hzQtmRapidLinkShutdown 1 }

hzQtmRlsHardFaultMonitor  OBJECT-TYPE
	SYNTAX     INTEGER {
		off (1),
		on (2)
	}
	MAX-ACCESS read-write
	STATUS     current
	DESCRIPTION
		"Enable the rlsHardFaultMonitor for rapid detection of severely degrade link. When disabled
		                                         only the RLS Link Degrade Monitor is used.

		 Note: Changing this option requires a system reset."
	DEFVAL  { off }
	::= { hzQtmRapidLinkShutdown 2 }

hzQtmRlsWirelessPortOption  OBJECT-TYPE
	SYNTAX     INTEGER {
		anyport (1),
		bothports (2)
	}
	MAX-ACCESS read-write
	STATUS     current
	DESCRIPTION
		"anyport - If the IDU is operating with two wireless ports and any one of the wireless ports goes down disables the ethernet port.
		                         bothports - In the above condition, this feature disables the ehternet traffic through the faulty wireless link but continuously send
		                         ethernet traffic through the other good wireless port. If the remaining wireless port also exceeds the error thereshold, ethernet port
		                         will be disabled

		 Note: Changing this option requires a system reset."
	DEFVAL  { anyport }
	::= { hzQtmRapidLinkShutdown 3 }

hzQtmRlsAutomaticLinkReestablish  OBJECT-TYPE
	SYNTAX     INTEGER {
		disabled (1),
		enabled (2)
	}
	MAX-ACCESS read-write
	STATUS     current
	DESCRIPTION
		"If this feature is enabled, the link will be automatically reestablished
		                                         If this feature is disabled, the user must explicitly use the manualReestablish object
		                                         to bring the link back up"
	DEFVAL  { disabled }
	::= { hzQtmRapidLinkShutdown 4 }

hzQtmRlsManualLinkReestablish  OBJECT-TYPE
	SYNTAX     INTEGER {
		disabled (1),
		enabled (2)
	}
	MAX-ACCESS read-write
	STATUS     current
	DESCRIPTION
		"This object is writeable ONLY if automaticLinkReestablish is set to disabled.
		                                         The user explicitly brings the link back up by setting this object to enabled.
		                                         The user explicitly brings the link down by setting this object to disabled.
		                                         to bring the link back up"
	DEFVAL  { disabled }
	::= { hzQtmRapidLinkShutdown 5 }

hzQtmWriteRlsMonitorParametersToSystem  OBJECT-TYPE
	SYNTAX     INTEGER {
		enabled (1)
	}
	MAX-ACCESS read-write
	STATUS     current
	DESCRIPTION
		"This writes RLS soft and hard fault monitor parameters to RAM
		                                         Reading this object returns '1'."
	DEFVAL  { enabled }
	::= { hzQtmRapidLinkShutdown 6 }

hzQtmRlsDroppedFramesThresholdOverride  OBJECT-TYPE
	SYNTAX     INTEGER {
		enabled (1)
	}
	MAX-ACCESS read-write
	STATUS     current
	DESCRIPTION
		"If the Ethernet is down due to Queue-Based Rls shutdown, this will bring the ethernet back and obey the queue settings.
		         Reading this object returns '1'."
	DEFVAL  { enabled }
	::= { hzQtmRapidLinkShutdown 7 }

hzQtmRlsDroppedFramesThresholdTable  OBJECT-TYPE
	SYNTAX SEQUENCE OF HzQtmRlsDroppedFramesThresholdEntry
	MAX-ACCESS not-accessible
	STATUS     current
	DESCRIPTION
		"A table of RLS Queue Monitor Parameters"
	::= { hzQtmRapidLinkShutdown 8 }

hzQtmRlsDroppedFramesThresholdEntry  OBJECT-TYPE
	SYNTAX 	HzQtmRlsDroppedFramesThresholdEntry
	MAX-ACCESS not-accessible
	STATUS     current
	DESCRIPTION
		"RLS Queue Parameters "
	INDEX { hzQtmRlsDroppedFramesThresholdIndex }
	::= { hzQtmRlsDroppedFramesThresholdTable 1 }

HzQtmRlsDroppedFramesThresholdEntry ::= SEQUENCE {
	hzQtmRlsDroppedFramesThresholdIndex
		INTEGER,
	hzQtmRlsAllowedDroppedFrameRateValue
		DisplayString,
	hzQtmRlsDroppedFrameMonitorPeriod
		Integer32
}

hzQtmRlsDroppedFramesThresholdIndex  OBJECT-TYPE
	SYNTAX     INTEGER {
		queue-1 (1),
		queue-2 (2),
		queue-3 (3),
		queue-4 (4)
	}
	MAX-ACCESS read-only
	STATUS     current
	DESCRIPTION
		"A unique value for each interface. "
	::= { hzQtmRlsDroppedFramesThresholdEntry 1 }

hzQtmRlsAllowedDroppedFrameRateValue  OBJECT-TYPE
	SYNTAX     DisplayString
	MAX-ACCESS read-write
	STATUS     current
	DESCRIPTION
		"Maximum allowed ethernet frame drop rate. If the average drop rate exceeds this threshold in any of the 4 queues, the Ethernet port will be shut down.
		This feture is availabe only with bothports option"
	::= { hzQtmRlsDroppedFramesThresholdEntry 2 }

hzQtmRlsDroppedFrameMonitorPeriod  OBJECT-TYPE
	SYNTAX     Integer32
	MAX-ACCESS read-write
	STATUS     current
	DESCRIPTION
		"The monitoring period in seconds. "
	::= { hzQtmRlsDroppedFramesThresholdEntry 3 }

hzQtmRlsSoftFaultMonitorTable  OBJECT-TYPE
	SYNTAX SEQUENCE OF HzQtmRlsSoftFaultMonitorEntry
	MAX-ACCESS not-accessible
	STATUS     current
	DESCRIPTION
		"A table of RLS Soft Fault Monitor Parameters"
	::= { hzQtmRapidLinkShutdown 9 }

hzQtmRlsSoftFaultMonitorEntry  OBJECT-TYPE
	SYNTAX 	HzQtmRlsSoftFaultMonitorEntry
	MAX-ACCESS not-accessible
	STATUS     current
	DESCRIPTION
		"RLS Parameters for Soft Fault Monitoring"
	INDEX { hzQtmRlsSoftFaultMonitorIndex }
	::= { hzQtmRlsSoftFaultMonitorTable 1 }

HzQtmRlsSoftFaultMonitorEntry ::= SEQUENCE {
	hzQtmRlsSoftFaultMonitorIndex
		INTEGER,
	hzQtmRlsEstablishErredFrameThreshold
		Integer32,
	hzQtmRlsShutdownErredFrameThreshold
		Integer32,
	hzQtmRlsEstablishNumberOfSamples
		Integer32,
	hzQtmRlsShutdownNumberOfSamples
		Integer32,
	hzQtmRlsEstablishSamplePeriod
		Integer32,
	hzQtmRlsShutdownSamplePeriod
		Integer32,
	hzQtmRlsQuickShutdownSamplePeriod
		Integer32
}

hzQtmRlsSoftFaultMonitorIndex  OBJECT-TYPE
	SYNTAX     INTEGER {
		wireless-port-1 (1),
		wireless-port-2 (2)
	}
	MAX-ACCESS read-only
	STATUS     current
	DESCRIPTION
		"A unique value for each interface. "
	::= { hzQtmRlsSoftFaultMonitorEntry 1 }

hzQtmRlsEstablishErredFrameThreshold  OBJECT-TYPE
	SYNTAX     Integer32
	MAX-ACCESS read-write
	STATUS     current
	DESCRIPTION
		"Maximum erred blocks, per sample, allowed for link establishment."
	::= { hzQtmRlsSoftFaultMonitorEntry 2 }

hzQtmRlsShutdownErredFrameThreshold  OBJECT-TYPE
	SYNTAX     Integer32
	MAX-ACCESS read-write
	STATUS     current
	DESCRIPTION
		"Minimum erred blocks, per sample, allowed before link shutdown."
	::= { hzQtmRlsSoftFaultMonitorEntry 3 }

hzQtmRlsEstablishNumberOfSamples  OBJECT-TYPE
	SYNTAX     Integer32
	MAX-ACCESS read-write
	STATUS     current
	DESCRIPTION
		"Minimum number of consecutive good samples required before link is established."
	::= { hzQtmRlsSoftFaultMonitorEntry 4 }

hzQtmRlsShutdownNumberOfSamples  OBJECT-TYPE
	SYNTAX     Integer32
	MAX-ACCESS read-write
	STATUS     current
	DESCRIPTION
		"Minimum number of consecutive erred samples before link is shutdown."
	::= { hzQtmRlsSoftFaultMonitorEntry 5 }

hzQtmRlsEstablishSamplePeriod  OBJECT-TYPE
	SYNTAX     Integer32
	MAX-ACCESS read-write
	STATUS     current
	DESCRIPTION
		"Period of Time, in milliseconds, for monitoring Establish Erred Frame Threshold."
	::= { hzQtmRlsSoftFaultMonitorEntry 6 }

hzQtmRlsShutdownSamplePeriod  OBJECT-TYPE
	SYNTAX     Integer32
	MAX-ACCESS read-write
	STATUS     current
	DESCRIPTION
		"Period of Time, in milliseconds, for monitoring Shutdown Erred Frame Threshold."
	::= { hzQtmRlsSoftFaultMonitorEntry 7 }

hzQtmRlsQuickShutdownSamplePeriod  OBJECT-TYPE
	SYNTAX     Integer32
	MAX-ACCESS read-write
	STATUS     current
	DESCRIPTION
		"Minimum number of milliseconds required to classify samples as erred."
	::= { hzQtmRlsSoftFaultMonitorEntry 8 }

hzQtmHardFaultMonitorTable  OBJECT-TYPE
	SYNTAX SEQUENCE OF HzQtmHardFaultMonitorEntry
	MAX-ACCESS not-accessible
	STATUS     current
	DESCRIPTION
		"A table of RLS Hard Fault Monitor Parameters"
	::= { hzQtmRapidLinkShutdown 10 }

hzQtmHardFaultMonitorEntry  OBJECT-TYPE
	SYNTAX 	HzQtmHardFaultMonitorEntry
	MAX-ACCESS not-accessible
	STATUS     current
	DESCRIPTION
		"RLS Parameters for Hard Fault Monitoring"
	INDEX { hzQtmHardFaultMonitorIndex }
	::= { hzQtmHardFaultMonitorTable 1 }

HzQtmHardFaultMonitorEntry ::= SEQUENCE {
	hzQtmHardFaultMonitorIndex
		INTEGER,
	hzQtmRlsHardFaultSamplePeriod
		Integer32,
	hzQtmRlsHardFaultThreshold
		Integer32
}

hzQtmHardFaultMonitorIndex  OBJECT-TYPE
	SYNTAX     INTEGER {
		wireless-port-1 (1),
		wireless-port-2 (2)
	}
	MAX-ACCESS read-only
	STATUS     current
	DESCRIPTION
		"A unique value for each interface. "
	::= { hzQtmHardFaultMonitorEntry 1 }

hzQtmRlsHardFaultSamplePeriod  OBJECT-TYPE
	SYNTAX     Integer32
	MAX-ACCESS read-write
	STATUS     current
	DESCRIPTION
		"The period of time, in milliseconds, for which the
		                                         rlsFaultThreshold is applied."
	::= { hzQtmHardFaultMonitorEntry 2 }

hzQtmRlsHardFaultThreshold  OBJECT-TYPE
	SYNTAX     Integer32
	MAX-ACCESS read-write
	STATUS     current
	DESCRIPTION
		"Acceptalbe errored block rate in percent"
	::= { hzQtmHardFaultMonitorEntry 3 }

hzQtmRlsReceiveSignalLevelMonitorTable  OBJECT-TYPE
	SYNTAX SEQUENCE OF HzQtmRlsReceiveSignalLevelMonitorEntry
	MAX-ACCESS not-accessible
	STATUS     current
	DESCRIPTION
		"A table of RLS RSL Monitor Parameters"
	::= { hzQtmRapidLinkShutdown 11 }

hzQtmRlsReceiveSignalLevelMonitorEntry  OBJECT-TYPE
	SYNTAX 	HzQtmRlsReceiveSignalLevelMonitorEntry
	MAX-ACCESS not-accessible
	STATUS     current
	DESCRIPTION
		"RLS RSL Monitor Parameters"
	INDEX { hzQtmRlsReceiveSignalLevelMonitorIndex }
	::= { hzQtmRlsReceiveSignalLevelMonitorTable 1 }

HzQtmRlsReceiveSignalLevelMonitorEntry ::= SEQUENCE {
	hzQtmRlsReceiveSignalLevelMonitorIndex
		INTEGER,
	hzQtmRlsMakeRslMonitorRslValue
		DisplayString,
	hzQtmRlsMakeRslMonitorPeriod
		Integer32
}

hzQtmRlsReceiveSignalLevelMonitorIndex  OBJECT-TYPE
	SYNTAX     INTEGER {
		wireless-port-1 (1),
		wireless-port-2 (2)
	}
	MAX-ACCESS read-only
	STATUS     current
	DESCRIPTION
		"A unique value for each interface. "
	::= { hzQtmRlsReceiveSignalLevelMonitorEntry 1 }

hzQtmRlsMakeRslMonitorRslValue  OBJECT-TYPE
	SYNTAX     DisplayString (SIZE(0..24))
	MAX-ACCESS read-write
	STATUS     current
	DESCRIPTION
		"The RSL threshold, in dBm. When Link is inactive and if RSL
		is higher than this threshold for a desired
		period, the link will become active."
	::= { hzQtmRlsReceiveSignalLevelMonitorEntry 2 }

hzQtmRlsMakeRslMonitorPeriod  OBJECT-TYPE
	SYNTAX     Integer32
	MAX-ACCESS read-write
	STATUS     current
	DESCRIPTION
		"The desired period, in seconds. When Link is inactive and if RSL
		is higher than the desiredthreshold for this
		period, the link will become active."
	::= { hzQtmRlsReceiveSignalLevelMonitorEntry 3 }

hzQtmRlsCurrentDroppedFramesTable  OBJECT-TYPE
	SYNTAX SEQUENCE OF HzQtmRlsCurrentDroppedFramesEntry
	MAX-ACCESS not-accessible
	STATUS     current
	DESCRIPTION
		"A table of RLS Currently Observed Queue Monitor Parameters"
	::= { hzQtmRlsStatus 1 }

hzQtmRlsCurrentDroppedFramesEntry  OBJECT-TYPE
	SYNTAX 	HzQtmRlsCurrentDroppedFramesEntry
	MAX-ACCESS not-accessible
	STATUS     current
	DESCRIPTION
		"RLS Currently Observed Queue Monitor Parameters"
	INDEX { hzQtmRlsCurrentDroppedFramesIndex }
	::= { hzQtmRlsCurrentDroppedFramesTable 1 }

HzQtmRlsCurrentDroppedFramesEntry ::= SEQUENCE {
	hzQtmRlsCurrentDroppedFramesIndex
		INTEGER,
	hzQtmRlsCurrentDroppedFramesRateValue
		DisplayString,
	hzQtmRlsCurrentDroppedFrameMonitorPeriod
		Integer32,
	hzQtmRlsCurrentQueueStatus
		DisplayString
}

hzQtmRlsCurrentDroppedFramesIndex  OBJECT-TYPE
	SYNTAX     INTEGER {
		queue-1 (1),
		queue-2 (2),
		queue-3 (3),
		queue-4 (4)
	}
	MAX-ACCESS read-only
	STATUS     current
	DESCRIPTION
		"A unique value for each interface. "
	::= { hzQtmRlsCurrentDroppedFramesEntry 1 }

hzQtmRlsCurrentDroppedFramesRateValue  OBJECT-TYPE
	SYNTAX     DisplayString
	MAX-ACCESS read-only
	STATUS     current
	DESCRIPTION
		"RLS Current Ethernet Frame drop rate"
	::= { hzQtmRlsCurrentDroppedFramesEntry 2 }

hzQtmRlsCurrentDroppedFrameMonitorPeriod  OBJECT-TYPE
	SYNTAX     Integer32
	MAX-ACCESS read-only
	STATUS     current
	DESCRIPTION
		"Queue Monitoring time"
	::= { hzQtmRlsCurrentDroppedFramesEntry 3 }

hzQtmRlsCurrentQueueStatus  OBJECT-TYPE
	SYNTAX     DisplayString
	MAX-ACCESS read-only
	STATUS     current
	DESCRIPTION
		"Queue Status - OK: drop rate is within the threshold, Activated: Exceeded the drop threshold"
	::= { hzQtmRlsCurrentDroppedFramesEntry 4 }

hzQtmRlsStatusTable  OBJECT-TYPE
	SYNTAX SEQUENCE OF HzQtmRlsStatusEntry
	MAX-ACCESS not-accessible
	STATUS     current
	DESCRIPTION
		"A table of RLS Parameters and states"
	::= { hzQtmRlsStatus 2 }

hzQtmRlsStatusEntry  OBJECT-TYPE
	SYNTAX 	HzQtmRlsStatusEntry
	MAX-ACCESS not-accessible
	STATUS     current
	DESCRIPTION
		"RLS Parameters and states"
	INDEX { hzQtmRlsStatusIndex }
	::= { hzQtmRlsStatusTable 1 }

HzQtmRlsStatusEntry ::= SEQUENCE {
	hzQtmRlsStatusIndex
		INTEGER,
	hzQtmRlsOption
		DisplayString,
	hzQtmRlsState
		DisplayString,
	hzQtmRlsMismatchState
		DisplayString,
	hzQtmDegradeMonitorState
		DisplayString,
	hzQtmHardFaultMonitorState
		DisplayString,
	hzQtmMakeRslThresholdState
		DisplayString,
	hzQtmPeerRlsState
		DisplayString,
	hzQtmRadioInterfaceState
		DisplayString,
	hzQtmNetworkInterfaceState
		DisplayString,
	hzQtmUserConfiguredEstablishFer
		DisplayString,
	hzQtmMinimumAchievableEstablishFer
		DisplayString,
	hzQtmUserConfiguredShutdownFer
		DisplayString,
	hzQtmMinimumAchievableShutdownFer
		DisplayString,
	hzQtmUserConfiguredEstablishMonitorTime
		Integer32,
	hzQtmActualEstablishMonitorTime
		Integer32,
	hzQtmUserConfiguredShutdownMonitorTime
		Integer32,
	hzQtmActualShutdownMonitorTime
		Integer32
}

hzQtmRlsStatusIndex  OBJECT-TYPE
	SYNTAX     INTEGER {
		wireless-port-1 (1),
		wireless-port-2 (2)
	}
	MAX-ACCESS read-only
	STATUS     current
	DESCRIPTION
		"A unique value for each interface. "
	::= { hzQtmRlsStatusEntry 1 }

hzQtmRlsOption  OBJECT-TYPE
	SYNTAX     DisplayString
	MAX-ACCESS read-only
	STATUS     current
	DESCRIPTION
		"RLS Option. On Basic: RLS enabled with base degrade monitoring;
		 On Advanced: RLS enabled with hard fault monitoring;
		 On Anyport: If any one of the wireless links exceeds the threshold Ehternet Port will be shut down
		 On Bothports: Both wireless links should exceed the threshold to bring the Ethernet Port down
		 Off: Entire RLS feature disabled."
	::= { hzQtmRlsStatusEntry 2 }

hzQtmRlsState  OBJECT-TYPE
	SYNTAX     DisplayString
	MAX-ACCESS read-only
	STATUS     current
	DESCRIPTION
		"Rapid Link Shutdown State. If the state is activated, that means
		The wireless link is down for Ethernet traffic; If the state is inactivated, that means that
		wireless link is up for Ethernet traffic."
	::= { hzQtmRlsStatusEntry 3 }

hzQtmRlsMismatchState  OBJECT-TYPE
	SYNTAX     DisplayString
	MAX-ACCESS read-only
	STATUS     current
	DESCRIPTION
		"RLS Mismatch State. If the state is activated, that means RLS
		configuration is mismatched with peer. If the state is OK,
		that means RLS configuration is matched with peer."
	::= { hzQtmRlsStatusEntry 4 }

hzQtmDegradeMonitorState  OBJECT-TYPE
	SYNTAX     DisplayString
	MAX-ACCESS read-only
	STATUS     current
	DESCRIPTION
		"Degrade Monitor State. If the state is activated, that means
		the RLS Degrade Monitor is asserting the link down. If the
		state is OK, that means the RLS Degrade Monitor is asserting
		the link up."
	::= { hzQtmRlsStatusEntry 5 }

hzQtmHardFaultMonitorState  OBJECT-TYPE
	SYNTAX     DisplayString
	MAX-ACCESS read-only
	STATUS     current
	DESCRIPTION
		"Hard Fault Monitor State. If the state is activated, that means
		the Hard Fault Monitor is asserting the link down. If the state
		is OK, that means the RLS Hard Fault Monitor is asserting the
		link up."
	::= { hzQtmRlsStatusEntry 6 }

hzQtmMakeRslThresholdState  OBJECT-TYPE
	SYNTAX     DisplayString
	MAX-ACCESS read-only
	STATUS     current
	DESCRIPTION
		"Make RSL Threshold State. If the state is not met, that means the
		RLS signal level is below the threshold value. If the state is OK,
		that means the RLS signal level is above the threshold value."
	::= { hzQtmRlsStatusEntry 7 }

hzQtmPeerRlsState  OBJECT-TYPE
	SYNTAX     DisplayString
	MAX-ACCESS read-only
	STATUS     current
	DESCRIPTION
		"Peer RLS State. If the state is activated, that means the peer has
		activated RLS. If the state is OK, that means the Peer hasn't
		activated RLS."
	::= { hzQtmRlsStatusEntry 8 }

hzQtmRadioInterfaceState  OBJECT-TYPE
	SYNTAX     DisplayString
	MAX-ACCESS read-only
	STATUS     current
	DESCRIPTION
		"Radio Interface State. If the state is down, that means The radio
		interface is not operational(muted,disconnected, not configured).
		If the state is up, that means the radio interface is operational."
	::= { hzQtmRlsStatusEntry 9 }

hzQtmNetworkInterfaceState  OBJECT-TYPE
	SYNTAX     DisplayString
	MAX-ACCESS read-only
	STATUS     current
	DESCRIPTION
		"Network Interface State. If the state is down, that means the network
		interface (Ethernet/PHY) is not operational(disconnected, not
		configured). If the state is up, that means the network interface
		(Ethernet/PHY) is operational."
	::= { hzQtmRlsStatusEntry 10 }

hzQtmUserConfiguredEstablishFer  OBJECT-TYPE
	SYNTAX     DisplayString
	MAX-ACCESS read-only
	STATUS     current
	DESCRIPTION
		"User Configured Establish Frame Error Ratio required for the
		link to be restored to service, set by the user. An example
		value being '1.0E-7'."
	::= { hzQtmRlsStatusEntry 11 }

hzQtmMinimumAchievableEstablishFer  OBJECT-TYPE
	SYNTAX     DisplayString
	MAX-ACCESS read-only
	STATUS     current
	DESCRIPTION
		"Minimum achievable Frame Error Ratio required for the link to be
		restored to service. An example value being '1.0E-7'."
	::= { hzQtmRlsStatusEntry 12 }

hzQtmUserConfiguredShutdownFer  OBJECT-TYPE
	SYNTAX     DisplayString
	MAX-ACCESS read-only
	STATUS     current
	DESCRIPTION
		"User Configured Shutdown Frame Error Ratio required for the
		link to remain in-service, set by the user. An example value
		being '1.0E-7'."
	::= { hzQtmRlsStatusEntry 13 }

hzQtmMinimumAchievableShutdownFer  OBJECT-TYPE
	SYNTAX     DisplayString
	MAX-ACCESS read-only
	STATUS     current
	DESCRIPTION
		"Minimum achievable Frame Error Ratio required for the link to
		remain in-service. An example value being '1.0E-7'."
	::= { hzQtmRlsStatusEntry 14 }

hzQtmUserConfiguredEstablishMonitorTime  OBJECT-TYPE
	SYNTAX     Integer32
	MAX-ACCESS read-only
	STATUS     current
	DESCRIPTION
		"User Configured Establish Monitor Time, in milliseconds, for
		which the 'User Configured Establish FER' must be achieved
		to bring link into service, set by user"
	::= { hzQtmRlsStatusEntry 15 }

hzQtmActualEstablishMonitorTime  OBJECT-TYPE
	SYNTAX     Integer32
	MAX-ACCESS read-only
	STATUS     current
	DESCRIPTION
		"Actual Establish Monitor Time, in milliseconds, for which the
		'User Configured Establish FER'must be achieved to bring
		link into service, it's a multiple of the establish sample
		period required to observe the FER"
	::= { hzQtmRlsStatusEntry 16 }

hzQtmUserConfiguredShutdownMonitorTime  OBJECT-TYPE
	SYNTAX     Integer32
	MAX-ACCESS read-only
	STATUS     current
	DESCRIPTION
		"User Configured Shutdown Monitor Time, in milliseconds, for which
		the 'User Configured Shutdown FER' must be met for the link to
		remain in-service, set by user."
	::= { hzQtmRlsStatusEntry 17 }

hzQtmActualShutdownMonitorTime  OBJECT-TYPE
	SYNTAX     Integer32
	MAX-ACCESS read-only
	STATUS     current
	DESCRIPTION
		"Actual Shutdown Monitor Time, in milliseconds, for which the 'User
		Configured Shutdown FER' must be met for the link to remain
		in-service, it's a multiple of the shutdown sample period required
		to  observe the FER"
	::= { hzQtmRlsStatusEntry 18 }

hzQtmRlsPort1  OBJECT-TYPE
	SYNTAX     INTEGER {
		exclude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 1 }

hzQtmRlsPort2  OBJECT-TYPE
	SYNTAX     INTEGER {
		exlcude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 2 }

hzQtmRlsPort3  OBJECT-TYPE
	SYNTAX     INTEGER {
		exclude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 3 }

hzQtmRlsPort4  OBJECT-TYPE
	SYNTAX     INTEGER {
		exlcude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 4 }

hzQtmRlsPort5  OBJECT-TYPE
	SYNTAX     INTEGER {
		exclude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 5 }

hzQtmRlsPort6  OBJECT-TYPE
	SYNTAX     INTEGER {
		exclude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 6 }

hzQtmRlsPort7  OBJECT-TYPE
	SYNTAX     INTEGER {
		exclude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 7 }

hzQtmRlsPort8  OBJECT-TYPE
	SYNTAX     INTEGER {
		exclude (0),
		gr-A (1),
		gr-B (2),
		gr-C (3)
	}
	MAX-ACCESS read-write
	STATUS     current
	DESCRIPTION
		"This is an important configuration!!!!

		There are three groups GR-A (OR-A), GR-B (OR-B) and GR-C (AND). Any Ethernet port can belong to any one of these three groups.These port groups are mutually exclusive. That means, one port cannot belongs to two or more groups

		Example:
		  OR-A = {Port1, Port2}, OR-B = {Port3,Port5} and AND = {Port4}
		  RLS will not trigger due to local Ethernet port state if
		  1. Either Port1 or Port2 is up AND
		  2. Either Port2 or Port5 is up AND
		  3. Port4 is up
		  For any reason if RLS triggers, Port1, Port2, Port3, Port4 and Port5 all be shutdown.
		"
	::= { hzQtmRlsPortGroup 8 }

hzQtmRlsPauseEnable  OBJECT-TYPE
	SYNTAX     INTEGER {
		disabled (1),
		enabled (2)
	}
	MAX-ACCESS read-write
	STATUS     current
	DESCRIPTION
		""
	::= { hzQtmRapidLinkShutdown 14 }

--
-- hzQtmSntp
--

hzQtmSntpEnable  OBJECT-TYPE
	SYNTAX     INTEGER {
		disabled (1),
		enabled (2)
	}
	MAX-ACCESS read-write
	STATUS     current
	DESCRIPTION
		"Indicates whether SNTP feature is enabled."
	DEFVAL  { enabled }
	::= { hzQtmSntp 1 }

hzQtmSntpOffset  OBJECT-TYPE
	SYNTAX     Integer32 (-140..140)
	MAX-ACCESS read-write
	STATUS     current
	DESCRIPTION
		"System time offset from GMT in tenths of hours. For example, an offset of 10 indicates 10 tenths, or 1 hour.  An offset of 5 indicates half an hour."
	DEFVAL  { -40 }
	::= { hzQtmSntp 2 }

-- This value is shown in 10ths of hours

hzQtmSntpServerTable  OBJECT-TYPE
	SYNTAX SEQUENCE OF HzQtmSntpServerEntry
	MAX-ACCESS not-accessible
	STATUS     current
	DESCRIPTION
		"Table containing sntp server entries"
	::= { hzQtmSntp 3 }

hzQtmSntpServerEntry  OBJECT-TYPE
	SYNTAX 	HzQtmSntpServerEntry
	MAX-ACCESS not-accessible
	STATUS     current
	DESCRIPTION
		"Contains the sntp server information"
	INDEX { hzQtmSntpServerIndex }
	::= { hzQtmSntpServerTable 1 }

HzQtmSntpServerEntry ::= SEQUENCE {
	hzQtmSntpServerIndex
		Integer32,
	hzQtmSntpServerIpAddress
		IpAddress,
	hzQtmSntpServerStatus
		INTEGER,
	hzQtmSntpServerStratum
		Integer32
}

hzQtmSntpServerIndex  OBJECT-TYPE
	SYNTAX     Integer32
	MAX-ACCESS read-only
	STATUS     current
	DESCRIPTION
		"A unique value for each server."
	::= { hzQtmSntpServerEntry 1 }

hzQtmSntpServerIpAddress  OBJECT-TYPE
	SYNTAX     IpAddress
	MAX-ACCESS read-write
	STATUS     current
	DESCRIPTION
		"The IP address of the server."
	::= { hzQtmSntpServerEntry 2 }

hzQtmSntpServerStatus  OBJECT-TYPE
	SYNTAX     INTEGER {
		good (1),
		failed (2)
	}
	MAX-ACCESS read-only
	STATUS     current
	DESCRIPTION
		"The status of the sntp server."
	::= { hzQtmSntpServerEntry 3 }

hzQtmSntpServerStratum  OBJECT-TYPE
	SYNTAX     Integer32
	MAX-ACCESS read-only
	STATUS     current
	DESCRIPTION
		"Specifies the stratum of a server, 0 for failed server"
	::= { hzQtmSntpServerEntry 4 }

hzQtmSntpRestoreDefault  OBJECT-TYPE
	SYNTAX     INTEGER {
		restore (1)
	}
	MAX-ACCESS read-write
	STATUS     current
	DESCRIPTION
		"Restores SNTP servers to default Addresses."
	::= { hzQtmSntp 4 }

--
-- hzQtmLogs
--

hzQtmEventLogEnable  OBJECT-TYPE
	SYNTAX     INTEGER {
		disabled (1),
		enabled (2)
	}
	MAX-ACCESS read-write
	STATUS     current
	DESCRIPTION
		"Indicates whether event log is enabled."
	DEFVAL  { enabled }
	::= { hzQtmLogs 1 }

hzQtmPerfmLogEnable  OBJECT-TYPE
	SYNTAX     INTEGER {
		disabled (1),
		enabled (2)
	}
	MAX-ACCESS read-write
	STATUS     current
	DESCRIPTION
		"Indicates whether performance log is enabled."
	DEFVAL  { enabled }
	::= { hzQtmLogs 2 }

hzQtmPerfmLogInterval  OBJECT-TYPE
	SYNTAX     DisplayString (SIZE(0..10))
	MAX-ACCESS read-write
	STATUS     current
	DESCRIPTION
		"Performance statistics are logged periodically by this interval. The interval can be up to 24:00:00 (24 hours) and as short as 00:00:1 (1 seconds)."
	::= { hzQtmLogs 3 }

hzQtmSysLogEnable  OBJECT-TYPE
	SYNTAX     INTEGER {
		disabled (1),
		enabled (2)
	}
	MAX-ACCESS read-write
	STATUS     current
	DESCRIPTION
		""
	::= { hzQtmSysLog 1 }

hzQtmSysLogIpAddress  OBJECT-TYPE
	SYNTAX     IpAddress
	MAX-ACCESS read-write
	STATUS     current
	DESCRIPTION
		""
	::= { hzQtmSysLog 2 }

--
-- hzQtmRadius
--

hzQtmRadiusSuperUserAuthentication  OBJECT-TYPE
	SYNTAX     INTEGER {
		off (1),
		on (2)
	}
	MAX-ACCESS read-write
	STATUS     current
	DESCRIPTION
		" The set strict mode on or off"
	DEFVAL  { off }
	::= { hzQtmRadius 1 }

hzQtmRadiusServerTimeOut  OBJECT-TYPE
	SYNTAX     Integer32
	MAX-ACCESS read-only
	STATUS     current
	DESCRIPTION
		" Timeout period for authentication requests"
	::= { hzQtmRadius 2 }

hzQtmRadiusServerDeadTime  OBJECT-TYPE
	SYNTAX     Integer32
	MAX-ACCESS read-only
	STATUS     current
	DESCRIPTION
		" Time to declare an unresponsive server 'dead'"
	::= { hzQtmRadius 3 }

hzQtmRadiusServerReTransmit  OBJECT-TYPE
	SYNTAX     Integer32
	MAX-ACCESS read-only
	STATUS     current
	DESCRIPTION
		"Maximum number of retransmits to an unresponsive server"
	::= { hzQtmRadius 4 }

hzQtmRadiusServerTable  OBJECT-TYPE
	SYNTAX SEQUENCE OF HzQtmRadiusServerEntry
	MAX-ACCESS not-accessible
	STATUS     current
	DESCRIPTION
		"Table containing radius server entries"
	::= { hzQtmRadius 5 }

hzQtmRadiusServerEntry  OBJECT-TYPE
	SYNTAX 	HzQtmRadiusServerEntry
	MAX-ACCESS not-accessible
	STATUS     current
	DESCRIPTION
		"Contains the sntp server information"
	INDEX { hzQtmRadiusServerIndex }
	::= { hzQtmRadiusServerTable 1 }

HzQtmRadiusServerEntry ::= SEQUENCE {
	hzQtmRadiusServerIndex
		Integer32,
	hzQtmRadiusCfgdHostIpAddress
		IpAddress,
	hzQtmRadiusActiveHostIpAddress
		IpAddress
}

hzQtmRadiusServerIndex  OBJECT-TYPE
	SYNTAX     Integer32
	MAX-ACCESS read-only
	STATUS     current
	DESCRIPTION
		"A unique value for each server."
	::= { hzQtmRadiusServerEntry 1 }

hzQtmRadiusCfgdHostIpAddress  OBJECT-TYPE
	SYNTAX     IpAddress
	MAX-ACCESS read-write
	STATUS     current
	DESCRIPTION
		"The IP address of the configured radius server.

		Note: Changing this option requires a system reset. "
	::= { hzQtmRadiusServerEntry 2 }

hzQtmRadiusActiveHostIpAddress  OBJECT-TYPE
	SYNTAX     IpAddress
	MAX-ACCESS read-only
	STATUS     current
	DESCRIPTION
		"The IP address of the active radius server."
	::= { hzQtmRadiusServerEntry 3 }

-- NOTIFICATION_TYPE
-- for generic traps real trap value of linkDown is 2.

hzQtmLinkDown  NOTIFICATION-TYPE
	OBJECTS { ifIndex }
	STATUS     current
	DESCRIPTION
		"A linkDown trap signifies that the sending protocol entity recognizes a failure in one of the communication links represented in the agent's configuration."
	::= { hzQtmSnmpNotifications 1 }

-- for generic traps real trap value of linkup is 3.

hzQtmLinkUp  NOTIFICATION-TYPE
	OBJECTS { ifIndex }
	STATUS     current
	DESCRIPTION
		"A linkUp trap signifies that the sending protocol entity recognizes that one of the communication links represented in the agent's configuration has come up."
	::= { hzQtmSnmpNotifications 2 }

hzQtmExplicitAuthenticationFailure  NOTIFICATION-TYPE
	STATUS     current
	DESCRIPTION
		"Authentication of the peer horizon node has failed. The severity is critical, the probable cause is an incorrect authentication configuration on horizon faulty
		 cable between the modem and radio, and recommended course of action is to check both ends of the link."
	::= { hzQtmSnmpNotifications 3 }

hzQtmExplicitAuthenticationFailureCleared  NOTIFICATION-TYPE
	STATUS     current
	DESCRIPTION
		"The condition has cleared. The peer node is now authenticated."
	::= { hzQtmSnmpNotifications 4 }

hzQtmHitlessAamConfigMisMatch  NOTIFICATION-TYPE
	OBJECTS { hzQtmModemAlarmsIndex }
	STATUS     current
	DESCRIPTION
		"Hitless Automatic Adaptive modulation configuration mismatch"
	::= { hzQtmSnmpNotifications 5 }

hzQtmHitlessAamConfigMisMatchCleared  NOTIFICATION-TYPE
	OBJECTS { hzQtmModemAlarmsIndex }
	STATUS     current
	DESCRIPTION
		"Hitless Automatic Adaptive modulation configuration mismatch cleared"
	::= { hzQtmSnmpNotifications 6 }

hzQtmHitlessAamActive  NOTIFICATION-TYPE
	OBJECTS { hzQtmModemAlarmsIndex }
	STATUS     current
	DESCRIPTION
		"Hitless Automatic Adaptive modulation on and system running on lower modulation"
	::= { hzQtmSnmpNotifications 7 }

hzQtmHitlessAamActiveCleared  NOTIFICATION-TYPE
	OBJECTS { hzQtmModemAlarmsIndex }
	STATUS     current
	DESCRIPTION
		"Hitless Automatic Adaptive modulation on  system running on higher modulation"
	::= { hzQtmSnmpNotifications 8 }

hzQtmAtpcConfigMismatch  NOTIFICATION-TYPE
	STATUS     current
	DESCRIPTION
		"ATPC configuration mismatch in the Horizon systems. ATPC is enabled at one system, but ATPC is not enabled at the other system."
	::= { hzQtmSnmpNotifications 9 }

hzQtmAtpcConfigMismatchCleared  NOTIFICATION-TYPE
	STATUS     current
	DESCRIPTION
		"ATPC configuration mismatch in the Horizon systems is cleared. Both systems enabled ATPC."
	::= { hzQtmSnmpNotifications 10 }

hzQtmSntpServersUnreachable  NOTIFICATION-TYPE
	STATUS     current
	DESCRIPTION
		"Can't reach any of the sntp servers"
	::= { hzQtmSnmpNotifications 11 }

hzQtmSntpServersUnreachableCleared  NOTIFICATION-TYPE
	STATUS     current
	DESCRIPTION
		"At least one of SNTP servers is reachable"
	::= { hzQtmSnmpNotifications 12 }

hzQtmFrequencyFileInvalid  NOTIFICATION-TYPE
	STATUS     current
	DESCRIPTION
		"When the executing frequency file is invalid,
		this trap is generated."
	::= { hzQtmSnmpNotifications 13 }

hzQtmDroppedFramesThresholdExceeded  NOTIFICATION-TYPE
	STATUS     current
	DESCRIPTION
		"The ethernet dropped frames threshold has been detected above its threshold value."
	::= { hzQtmSnmpNotifications 14 }

hzQtmDroppedFramesThresholdExceededCleared  NOTIFICATION-TYPE
	STATUS     current
	DESCRIPTION
		"The condition has cleared.The ethernet dropped frames threshold is now below its threshold value."
	::= { hzQtmSnmpNotifications 15 }

hzQtmBwUtilizationThresholdExceeded  NOTIFICATION-TYPE
	STATUS     current
	DESCRIPTION
		"The ethernet bandwidth threshold has been detected above its threshold value."
	::= { hzQtmSnmpNotifications 16 }

hzQtmBwUtilizationThresholdExceededCleared  NOTIFICATION-TYPE
	STATUS     current
	DESCRIPTION
		"The condition has cleared. The ethernet bandwidth threshold is now below its threshold value."
	::= { hzQtmSnmpNotifications 17 }

hzQtmRlsMismatch  NOTIFICATION-TYPE
	STATUS     current
	DESCRIPTION
		"RLS mismatch"
	::= { hzQtmSnmpNotifications 18 }

hzQtmRlsMismatchCleared  NOTIFICATION-TYPE
	STATUS     current
	DESCRIPTION
		"RLS mismatch cleared"
	::= { hzQtmSnmpNotifications 19 }

hzQtmRlsQueueBasedShutdownActivated  NOTIFICATION-TYPE
	STATUS     current
	DESCRIPTION
		"RLS Queue-Based shutdown is activated"
	::= { hzQtmSnmpNotifications 20 }

hzQtmRlsQueueBasedShutdownActivatedCleared  NOTIFICATION-TYPE
	STATUS     current
	DESCRIPTION
		"RLS Queue-Based shutdown is not activated"
	::= { hzQtmSnmpNotifications 21 }

hzQtmModemRxLossOfSignalLock  NOTIFICATION-TYPE
	OBJECTS { hzQtmModemAlarmsIndex }
	STATUS     current
	DESCRIPTION
		"Loss of signal lock from the demodulator. The severity is critical, the probable cause is lost synchronization with the far end,
		 and recommended course of action is to check the operational state of both ends of the link."
	::= { hzQtmSnmpNotifications 22 }

hzQtmModemRxLossOfSignalLockCleared  NOTIFICATION-TYPE
	OBJECTS { hzQtmModemAlarmsIndex }
	STATUS     current
	DESCRIPTION
		"Loss of signal lock from demodulator cleared."
	::= { hzQtmSnmpNotifications 23 }

hzQtmModemTxLossOfSync  NOTIFICATION-TYPE
	OBJECTS { hzQtmModemAlarmsIndex }
	STATUS     current
	DESCRIPTION
		"Loss of sync bytes at the input of the modulator. The severity is critical, the probable cause is physical
		       interference in the air link, and recommended course of action is to check the line of site between the horizon nodes."
	::= { hzQtmSnmpNotifications 24 }

hzQtmModemTxLossOfSyncCleared  NOTIFICATION-TYPE
	OBJECTS { hzQtmModemAlarmsIndex }
	STATUS     current
	DESCRIPTION
		"Tx Loss of sync bytes cleared."
	::= { hzQtmSnmpNotifications 25 }

hzQtmModemSnrBelowThreshold  NOTIFICATION-TYPE
	OBJECTS { hzQtmModemAlarmsIndex }
	STATUS     current
	DESCRIPTION
		"The demodulator SNR performance worse than programmed levels. The severity is major, the probable cause
		       is physical interference in the air link path or misalignment of the radios or severe weather conditions,
		       and recommended course of action is to check the line of site between the horizon nodes."
	::= { hzQtmSnmpNotifications 26 }

hzQtmModemSnrBelowThresholdCleared  NOTIFICATION-TYPE
	OBJECTS { hzQtmModemAlarmsIndex }
	STATUS     current
	DESCRIPTION
		"SNR performance back to normal."
	::= { hzQtmSnmpNotifications 27 }

hzQtmModemEqualizerStressExceedThreshold  NOTIFICATION-TYPE
	OBJECTS { hzQtmModemAlarmsIndex }
	STATUS     current
	DESCRIPTION
		"Equalizer Stress measured within the demodulator exceeds the threshold value."
	::= { hzQtmSnmpNotifications 28 }

hzQtmModemEqualizerStressExceedThresholdCleared  NOTIFICATION-TYPE
	OBJECTS { hzQtmModemAlarmsIndex }
	STATUS     current
	DESCRIPTION
		"Equalizer Stress measured within the demodulator is within the threshold value."
	::= { hzQtmSnmpNotifications 29 }

hzQtmModemChannelizedRslBelowThreshold  NOTIFICATION-TYPE
	OBJECTS { hzQtmModemAlarmsIndex }
	STATUS     current
	DESCRIPTION
		"The RSL has been detected below its minimum threshold."
	::= { hzQtmSnmpNotifications 30 }

hzQtmModemChannelizedRslBelowThresholdCleared  NOTIFICATION-TYPE
	OBJECTS { hzQtmModemAlarmsIndex }
	STATUS     current
	DESCRIPTION
		"The condition has cleared. RSL is now above its minimum threshold."
	::= { hzQtmSnmpNotifications 31 }

hzQtmFpgaProgrammingError  NOTIFICATION-TYPE
	STATUS     current
	DESCRIPTION
		"Encountered problem while programming modem."
	::= { hzQtmSnmpNotifications 32 }

hzQtmFpgaProgrammingErrorCleared  NOTIFICATION-TYPE
	STATUS     current
	DESCRIPTION
		"Problem encountered while programming modem is gone."
	::= { hzQtmSnmpNotifications 33 }

hzQtmUserSessionCommenced  NOTIFICATION-TYPE
	OBJECTS { hzQtmUserSessionUserName,
		hzQtmUserSessionUserConnectionType }
	STATUS     current
	DESCRIPTION
		"A person has successfully gained access to the ascii management port (telnet, local management port, or HTTP).
		 The username is included in the Trap."
	::= { hzQtmSnmpNotifications 34 }

hzQtmUserSessionTerminated  NOTIFICATION-TYPE
	OBJECTS { hzQtmUserSessionUserName,
		hzQtmUserSessionUserConnectionType }
	STATUS     current
	DESCRIPTION
		"A person has logged out of an ascii management port (telnet, local management port, or HTTP). The username is included in the Trap."
	::= { hzQtmSnmpNotifications 35 }

hzQtmAtpcTxAtMaxPwr  NOTIFICATION-TYPE
	OBJECTS { hzQtmRadioAlarmsIndex }
	STATUS     current
	DESCRIPTION
		"ATPC auto-disabled (transmitting at coordinated power)."
	::= { hzQtmSnmpNotifications 36 }

hzQtmAtpcTxAtMaxPwrCleared  NOTIFICATION-TYPE
	OBJECTS { hzQtmRadioAlarmsIndex }
	STATUS     current
	DESCRIPTION
		"ATPC has been disabled."
	::= { hzQtmSnmpNotifications 37 }

hzQtmRadioSynthLostLock  NOTIFICATION-TYPE
	OBJECTS { hzQtmRadioAlarmsIndex }
	STATUS     current
	DESCRIPTION
		"The radio synthesizer has lost lock. The severity is critical, the probable cause is a faulty radio,
		 and recommended course of action is to replace the radio unit"
	::= { hzQtmSnmpNotifications 38 }

hzQtmRadioSynthLostLockCleared  NOTIFICATION-TYPE
	OBJECTS { hzQtmRadioAlarmsIndex }
	STATUS     current
	DESCRIPTION
		"The radio synthesizer lost lock condition has cleared."
	::= { hzQtmSnmpNotifications 39 }

hzQtmRadioLostCommunication  NOTIFICATION-TYPE
	OBJECTS { hzQtmRadioAlarmsIndex }
	STATUS     current
	DESCRIPTION
		"RS232 communication lost between IDU and the radio. The severity is critical, the probable cause is a faulty cable
		 between the modem and radio, and recommended course of action is to check the connection."
	::= { hzQtmSnmpNotifications 40 }

hzQtmRadioLostCommunicationCleared  NOTIFICATION-TYPE
	OBJECTS { hzQtmRadioAlarmsIndex }
	STATUS     current
	DESCRIPTION
		"RS232 communication has been re-establisted between IDU and the radio."
	::= { hzQtmSnmpNotifications 41 }

hzQtmRadioMismatch  NOTIFICATION-TYPE
	OBJECTS { hzQtmRadioAlarmsIndex }
	STATUS     current
	DESCRIPTION
		"The radio connected to the IDU modem does not match the frequency programmed into the modem unit. The severity is major,
		 the probable cause is an incorrectly programmed modem or an incorrect radio type connected to the modem,
		 and recommended course of action is to check the modem frequency settings and radio hardware version number or serial number."
	::= { hzQtmSnmpNotifications 42 }

hzQtmRadioMismatchCleared  NOTIFICATION-TYPE
	OBJECTS { hzQtmRadioAlarmsIndex }
	STATUS     current
	DESCRIPTION
		"The condition has cleared. The radio matches the programmed parameters in the modem."
	::= { hzQtmSnmpNotifications 43 }

hzQtmRadioPowerAmp  NOTIFICATION-TYPE
	OBJECTS { hzQtmRadioAlarmsIndex }
	STATUS     current
	DESCRIPTION
		"The power amplifier on the radio is not operating within normal operating specifications. The severity is critical,
		 the probable cause a faulty radio unit, and recommended course of action is to replace the radio unit."
	::= { hzQtmSnmpNotifications 44 }

hzQtmRadioPowerAmpCleared  NOTIFICATION-TYPE
	OBJECTS { hzQtmRadioAlarmsIndex }
	STATUS     current
	DESCRIPTION
		"The power amplifier on the radio is now operating within normal specifications"
	::= { hzQtmSnmpNotifications 45 }

hzQtmRadioExcessiveTxCableLoss  NOTIFICATION-TYPE
	OBJECTS { hzQtmRadioAlarmsIndex }
	STATUS     current
	DESCRIPTION
		"The radio cannot compensate for the calculated amount of Tx Cable Loss."
	::= { hzQtmSnmpNotifications 46 }

hzQtmRadioExcessiveTxCableLossCleared  NOTIFICATION-TYPE
	OBJECTS { hzQtmRadioAlarmsIndex }
	STATUS     current
	DESCRIPTION
		"Radio Excessive Tx Cable Loss cleared."
	::= { hzQtmSnmpNotifications 47 }

hzQtmHiPowerRadioTxDetector  NOTIFICATION-TYPE
	OBJECTS { hzQtmRadioAlarmsIndex }
	STATUS     current
	DESCRIPTION
		"This applies to High Power Radios only. Indicates minimum power threshold has not been surpassed."
	::= { hzQtmSnmpNotifications 48 }

hzQtmHiPowerRadioTxDetectorCleared  NOTIFICATION-TYPE
	OBJECTS { hzQtmRadioAlarmsIndex }
	STATUS     current
	DESCRIPTION
		"This applies to High Power Radios only. Indicates minimum power threshold alarm has cleared."
	::= { hzQtmSnmpNotifications 49 }

hzQtmSecondaryRadioIsActive  NOTIFICATION-TYPE
	OBJECTS { hzQtmRadioAlarmsIndex }
	STATUS     current
	DESCRIPTION
		"Radio redundancy on, secondary radio is active."
	::= { hzQtmSnmpNotifications 50 }

hzQtmSecondaryRadioIsActiveCleared  NOTIFICATION-TYPE
	OBJECTS { hzQtmRadioAlarmsIndex }
	STATUS     current
	DESCRIPTION
		"Radio redundancy, secondary radio is no longer active."
	::= { hzQtmSnmpNotifications 51 }

hzQtmRedundancySerialNumberMisMatch  NOTIFICATION-TYPE
	OBJECTS { hzQtmRadioAlarmsIndex }
	STATUS     current
	DESCRIPTION
		"The radio serial number programmed in flash and radio do not match."
	::= { hzQtmSnmpNotifications 52 }

hzQtmRedundancySerialNumberMisMatchCleared  NOTIFICATION-TYPE
	OBJECTS { hzQtmRadioAlarmsIndex }
	STATUS     current
	DESCRIPTION
		"The radio serial number mismatch has cleared."
	::= { hzQtmSnmpNotifications 53 }

hzQtmRadioFirmwareMismatch  NOTIFICATION-TYPE
	OBJECTS { hzQtmRadioAlarmsIndex }
	STATUS     current
	DESCRIPTION
		"The radio connected to the IDU modem does not match the radio band or frequency bank specified by the user.
		 As a result, the system will not work."
	::= { hzQtmSnmpNotifications 54 }

hzQtmRadioFirmwareMismatchCleared  NOTIFICATION-TYPE
	OBJECTS { hzQtmRadioAlarmsIndex }
	STATUS     current
	DESCRIPTION
		"Radio Firmnware mismatch cleared."
	::= { hzQtmSnmpNotifications 55 }

hzQtmSecondaryRadioNotdetected  NOTIFICATION-TYPE
	OBJECTS { hzQtmRadioAlarmsIndex }
	STATUS     current
	DESCRIPTION
		"Secondary radio not detected."
	::= { hzQtmSnmpNotifications 56 }

hzQtmSecondaryRadioNotdetectedCleared  NOTIFICATION-TYPE
	OBJECTS { hzQtmRadioAlarmsIndex }
	STATUS     current
	DESCRIPTION
		"secondary Radio not detected alarm cleared."
	::= { hzQtmSnmpNotifications 57 }

hzQtmPrimaryRadioNotdetected  NOTIFICATION-TYPE
	OBJECTS { hzQtmRadioAlarmsIndex }
	STATUS     current
	DESCRIPTION
		"Primary Radio not detected."
	::= { hzQtmSnmpNotifications 58 }

hzQtmPrimaryRadioNotdetectedCleared  NOTIFICATION-TYPE
	OBJECTS { hzQtmRadioAlarmsIndex }
	STATUS     current
	DESCRIPTION
		"Primary Radio not detected alarm cleared."
	::= { hzQtmSnmpNotifications 59 }

hzQtmFaultyPrimaryRadio  NOTIFICATION-TYPE
	OBJECTS { hzQtmRadioAlarmsIndex }
	STATUS     current
	DESCRIPTION
		"Faulty Primary Radio."
	::= { hzQtmSnmpNotifications 60 }

hzQtmFaultyPrimaryRadioCleared  NOTIFICATION-TYPE
	OBJECTS { hzQtmRadioAlarmsIndex }
	STATUS     current
	DESCRIPTION
		"Faulty Primary Radio alarm cleared."
	::= { hzQtmSnmpNotifications 61 }

hzQtmRadioExcessiveTxCableLossChange  NOTIFICATION-TYPE
	OBJECTS { hzQtmRadioAlarmsIndex }
	STATUS     current
	DESCRIPTION
		"Excessive IF cable loss change detected."
	::= { hzQtmSnmpNotifications 62 }

hzQtmRadioExcessiveTxCableLossChangeCleared  NOTIFICATION-TYPE
	OBJECTS { hzQtmRadioAlarmsIndex }
	STATUS     current
	DESCRIPTION
		"Excessive IF cable loss change cleared."
	::= { hzQtmSnmpNotifications 63 }

hzQtmExcessiveRxCableLoss  NOTIFICATION-TYPE
	OBJECTS { hzQtmRadioAlarmsIndex }
	STATUS     current
	DESCRIPTION
		"Radio - Excessive receive cable loss detected."
	::= { hzQtmSnmpNotifications 64 }

hzQtmExcessiveRxCableLossCleared  NOTIFICATION-TYPE
	OBJECTS { hzQtmRadioAlarmsIndex }
	STATUS     current
	DESCRIPTION
		"Radio - Excessive receive cable loss cleared."
	::= { hzQtmSnmpNotifications 65 }

hzQtmRedundancyPrimaryPortNotSet  NOTIFICATION-TYPE
	STATUS     current
	DESCRIPTION
		"Radio Redundancy: Primary Port not set."
	::= { hzQtmSnmpNotifications 66 }

hzQtmRedundancyPrimaryPortNotSetCleared  NOTIFICATION-TYPE
	STATUS     current
	DESCRIPTION
		"Radio Redundancy: Primary Port not set - cleared."
	::= { hzQtmSnmpNotifications 67 }

hzQtmRedundancySecondaryPortIsActive  NOTIFICATION-TYPE
	STATUS     current
	DESCRIPTION
		"Radio Redundancy: Secondary Port is Active."
	::= { hzQtmSnmpNotifications 68 }

hzQtmRedundancySecondaryPortIsActiveCleared  NOTIFICATION-TYPE
	STATUS     current
	DESCRIPTION
		"Radio Redundancy: Secondary Port is no longer Active"
	::= { hzQtmSnmpNotifications 69 }

hzQtmRedundancyPrimaryPortFaulty  NOTIFICATION-TYPE
	STATUS     current
	DESCRIPTION
		"Radio Redundancy: Primary Port is Faulty."
	::= { hzQtmSnmpNotifications 70 }

hzQtmRedundancyPrimaryPortFaultyCleared  NOTIFICATION-TYPE
	STATUS     current
	DESCRIPTION
		"Radio Redundancy: Primary Port is no longer Faulty."
	::= { hzQtmSnmpNotifications 71 }

hzQtmRedundancySecondaryPortFaulty  NOTIFICATION-TYPE
	STATUS     current
	DESCRIPTION
		"Radio Redundancy: Secondary Port is Faulty."
	::= { hzQtmSnmpNotifications 72 }

hzQtmRedundancySecondaryPortFaultyCleared  NOTIFICATION-TYPE
	STATUS     current
	DESCRIPTION
		"Radio Redundancy: secondary Port is no longer Faulty."
	::= { hzQtmSnmpNotifications 73 }

hzQtmFanFailed  NOTIFICATION-TYPE
	STATUS     current
	DESCRIPTION
		"Fan 1 has failed"
	::= { hzQtmSnmpNotifications 74 }

hzQtmFanFailureCleared  NOTIFICATION-TYPE
	STATUS     current
	DESCRIPTION
		"The Fan 1 Failure has Cleared"
	::= { hzQtmSnmpNotifications 75 }

hzQtmModemRlsShutdownActivated  NOTIFICATION-TYPE
	OBJECTS { hzQtmModemAlarmsIndex }
	STATUS     current
	DESCRIPTION
		"RLS shutdown is activated"
	::= { hzQtmSnmpNotifications 76 }

hzQtmModemRlsShutdownActivatedCleared  NOTIFICATION-TYPE
	OBJECTS { hzQtmModemAlarmsIndex }
	STATUS     current
	DESCRIPTION
		"RLS shutdown is not activated"
	::= { hzQtmSnmpNotifications 77 }

hzQtmRadioUnitHwChanged  NOTIFICATION-TYPE
	OBJECTS { hzQtmRadioAlarmsIndex }
	STATUS     current
	DESCRIPTION
		"Indication that the Radio Unit hardware has changed."
	::= { hzQtmSnmpNotifications 78 }

hzQtmRadioSwDownloadFailed  NOTIFICATION-TYPE
	OBJECTS { hzQtmRadioAlarmsIndex }
	STATUS     current
	DESCRIPTION
		"The IDU failed to upload the radio firmware during the radio boot cycle."
	::= { hzQtmSnmpNotifications 79 }

hzQtmRadioSwDownloadFailedCleared  NOTIFICATION-TYPE
	OBJECTS { hzQtmRadioAlarmsIndex }
	STATUS     current
	DESCRIPTION
		"The IDU successfully uploaded the radio firmware after an initial upload failure."
	::= { hzQtmSnmpNotifications 80 }

hzQtmRadioRestartedOK  NOTIFICATION-TYPE
	OBJECTS { hzQtmRadioAlarmsIndex }
	STATUS     current
	DESCRIPTION
		"Radio unit has successfully restarted after a failure was found during a previous boot cycle."
	::= { hzQtmSnmpNotifications 81 }

hzQtmMibChangeNotSaved  NOTIFICATION-TYPE
	STATUS     current
	DESCRIPTION
		"The system has automatically re-programmed the mib but it has not been saved to flash.
		              The system event logs will indicate what has changed in the mib.
		              The user must invoke the 'save mib' command to save the mib to flash."
	::= { hzQtmSnmpNotifications 82 }

hzQtmMibChangeNotSavedCleared  NOTIFICATION-TYPE
	STATUS     current
	DESCRIPTION
		"The mib has been saved to flash since the system has automatically re-programmed the mib"
	::= { hzQtmSnmpNotifications 83 }

hzQtmRadioDrainCurrent  NOTIFICATION-TYPE
	OBJECTS { hzQtmRadioAlarmsIndex }
	STATUS     current
	DESCRIPTION
		"The radio has a drain current alarm. View the system logs for more information."
	::= { hzQtmSnmpNotifications 84 }

hzQtmRadioDrainCurrentCleared  NOTIFICATION-TYPE
	OBJECTS { hzQtmRadioAlarmsIndex }
	STATUS     current
	DESCRIPTION
		"The radio drain current alarm is cleared."
	::= { hzQtmSnmpNotifications 85 }

hzQtmIFSynthLostLock  NOTIFICATION-TYPE
	OBJECTS { hzQtmIFPathIndex }
	STATUS     current
	DESCRIPTION
		"The Synthesizer has Lost Lock on the IF Path. View the system logs for more information."
	::= { hzQtmSnmpNotifications 86 }

hzQtmIFSynthLostLockCleared  NOTIFICATION-TYPE
	OBJECTS { hzQtmIFPathIndex }
	STATUS     current
	DESCRIPTION
		"The IF Synthesizer Lost Lock alarm is cleared."
	::= { hzQtmSnmpNotifications 87 }

hzQtmInvalidSystemConfig  NOTIFICATION-TYPE
	STATUS     current
	DESCRIPTION
		"The system has been configured incorrectly. Check the logs or use the CLI get alarms
		to isolate the cause."
	::= { hzQtmSnmpNotifications 88 }

hzQtmInvalidSystemConfigCleared  NOTIFICATION-TYPE
	STATUS     current
	DESCRIPTION
		"The invalid system configuration alarm has been cleared."
	::= { hzQtmSnmpNotifications 89 }

hzQtmHitlessAamEvent  NOTIFICATION-TYPE
	OBJECTS { hzQtmModemAlarmsIndex }
	STATUS     current
	DESCRIPTION
		"Hitless Automatic Adaptive modulation switch triggered."
	::= { hzQtmSnmpNotifications 90 }

hzQtmModemXPICEquStressExceedThreshold  NOTIFICATION-TYPE
	OBJECTS { hzQtmModemAlarmsIndex }
	STATUS     current
	DESCRIPTION
		"XPIC Equalizer Stress measured within the demodulator exceeds the threshold value."
	::= { hzQtmSnmpNotifications 91 }

hzQtmModemXPICEquStressExceedThresholdCleared  NOTIFICATION-TYPE
	OBJECTS { hzQtmModemAlarmsIndex }
	STATUS     current
	DESCRIPTION
		"XPIC Equalizer Stress measured within the demodulator is within the threshold value."
	::= { hzQtmSnmpNotifications 92 }

hzQtmPartnerNodeAlarmIndication  NOTIFICATION-TYPE
	STATUS     current
	DESCRIPTION
		"The configuration in the partner node does not match this system."
	::= { hzQtmSnmpNotifications 93 }

hzQtmPartnerNodeAlarmIndicationCleared  NOTIFICATION-TYPE
	STATUS     current
	DESCRIPTION
		"Partner node alarm is cleared."
	::= { hzQtmSnmpNotifications 94 }

hzQtmBandwidthDoublingInvalidLinkConfig  NOTIFICATION-TYPE
	STATUS     current
	DESCRIPTION
		"The bandwidth doubling has invalid link configuration. i.e., Primary is synchronized with remote primary, and secondary is synchronized with remote secondary "
	::= { hzQtmSnmpNotifications 95 }

hzQtmBandwidthDoublingInvalidLinkConfigCleared  NOTIFICATION-TYPE
	STATUS     current
	DESCRIPTION
		"Bandwidth doubling invalid link configuration alarm is cleared."
	::= { hzQtmSnmpNotifications 96 }

hzQtmBandwidthDoublingWrongPortConnected  NOTIFICATION-TYPE
	STATUS     current
	DESCRIPTION
		"Wrong port is connected to the loacal partner."
	::= { hzQtmSnmpNotifications 97 }

hzQtmBandwidthDoublingWrongPortConnectedCleared  NOTIFICATION-TYPE
	STATUS     current
	DESCRIPTION
		"Bandwidth doubling wrong port connected alarm is cleared."
	::= { hzQtmSnmpNotifications 98 }

hzQtmRadioPowerOff  NOTIFICATION-TYPE
	STATUS     current
	DESCRIPTION
		"Radio power is off (potential IF cable short detection)."
	::= { hzQtmSnmpNotifications 99 }

hzQtmRadioPowerOffCleared  NOTIFICATION-TYPE
	OBJECTS { hzQtmRadioAlarmsIndex }
	STATUS     current
	DESCRIPTION
		"Radio power off alarm is cleared."
	::= { hzQtmSnmpNotifications 100 }

hzQtmSynceLostLock  NOTIFICATION-TYPE
	STATUS     current
	DESCRIPTION
		"SyncE Lost Lock alarm."
	::= { hzQtmSnmpNotifications 101 }

hzQtmSynceLostLockCleared  NOTIFICATION-TYPE
	STATUS     current
	DESCRIPTION
		"SyncE Lost Lock alarm cleared."
	::= { hzQtmSnmpNotifications 102 }

hzQtmSynceSecondarySourceInUse  NOTIFICATION-TYPE
	STATUS     current
	DESCRIPTION
		"SyncE Secondary Source in use alarm."
	::= { hzQtmSnmpNotifications 103 }

hzQtmSynceSecondarySourceInUseCleared  NOTIFICATION-TYPE
	STATUS     current
	DESCRIPTION
		"SyncE Secondary Source in use alarm cleared."
	::= { hzQtmSnmpNotifications 104 }

END


-- This MIB was created using NuDesign Team's Visual MIBuilder (Ver 4.7).
