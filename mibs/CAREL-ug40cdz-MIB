--
-- CAREL-ug40cdz.MIB
-- MIB generated by CAREL
-- Tuesday, 11 April 2006
--

    CAREL-ug40cdz-MIB DEFINITIONS ::= BEGIN
 
		IMPORTS
			OBJECT-GROUP		FROM SNMPv2-CONF			
			sysContact, sysName,
			sysLocation		FROM SNMPv2-MIB
			enterprises, MODULE-IDENTITY,
			OBJECT-TYPE, Integer32	FROM SNMPv2-SMI
			DisplayString		FROM RFC1213-MIB;		
		
        ug40cdzMIB MODULE-IDENTITY
      		LAST-UPDATED  "200604111645Z"		-- April 11, 2006 at 16:45 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the UG40 Close Control Uniflair device."
		REVISION   "200604111645Z"		-- April 11, 2006 at 16:45 GMT
		DESCRIPTION
		"This is the original version of the MIB"
			::= { instruments 1 }
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }

		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.1
        -- ug40cdzMIB OBJECT IDENTIFIER ::= { instruments 1 }

	-- 1.3.6.1.4.1.9839.2.1.1
	digitalObjects OBJECT IDENTIFIER ::= { ug40cdzMIB 1 }

        -- 1.3.6.1.4.1.9839.2.1.1.1
        systemOn OBJECT-TYPE
                    SYNTAX Integer32 (0..1)
                    UNITS "N/A"
                    MAX-ACCESS read-only
                    STATUS current
                    DESCRIPTION "System On (Fan)"
                    ::= { digitalObjects 1 }

        -- 1.3.6.1.4.1.9839.2.1.1.2
        compressore1 OBJECT-TYPE
                    SYNTAX Integer32 (0..1)
                    UNITS "N/A"
                    MAX-ACCESS read-only
                    STATUS current
                    DESCRIPTION "Compressor 1"
                    ::= { digitalObjects 2 }

        -- 1.3.6.1.4.1.9839.2.1.1.3
        compressore2 OBJECT-TYPE
                    SYNTAX Integer32 (0..1)
                    UNITS "N/A"
                    MAX-ACCESS read-only
                    STATUS current
                    DESCRIPTION "Compressor 2"
                    ::= { digitalObjects 3 }

        -- 1.3.6.1.4.1.9839.2.1.1.4
        compressore3 OBJECT-TYPE
                    SYNTAX Integer32 (0..1)
                    UNITS "N/A"
                    MAX-ACCESS read-only
                    STATUS current
                    DESCRIPTION "Compressor 3"
                    ::= { digitalObjects 4 }

        -- 1.3.6.1.4.1.9839.2.1.1.5
        compressore4 OBJECT-TYPE
                    SYNTAX Integer32 (0..1)
                    UNITS "N/A"
                    MAX-ACCESS read-only
                    STATUS current
                    DESCRIPTION "Compressor 4"
                    ::= { digitalObjects 5 }

        -- 1.3.6.1.4.1.9839.2.1.1.6
        heating1 OBJECT-TYPE
                    SYNTAX Integer32 (0..1)
                    UNITS "N/A"
                    MAX-ACCESS read-only
                    STATUS current
                    DESCRIPTION "Heating 1"
                    ::= { digitalObjects 6 }

        -- 1.3.6.1.4.1.9839.2.1.1.7
        heating2 OBJECT-TYPE
                    SYNTAX Integer32 (0..1)
                    UNITS "N/A"
                    MAX-ACCESS read-only
                    STATUS current
                    DESCRIPTION "Heating 2"
                    ::= { digitalObjects 7 }

        -- 1.3.6.1.4.1.9839.2.1.1.9
        hotGasCoil OBJECT-TYPE
                    SYNTAX Integer32 (0..1)
                    UNITS "N/A"
                    MAX-ACCESS read-only
                    STATUS current
                    DESCRIPTION "Hot Gas Coil"
                    ::= { digitalObjects 9 }

        -- 1.3.6.1.4.1.9839.2.1.1.10
        dehumidification OBJECT-TYPE
                    SYNTAX Integer32 (0..1)
                    UNITS "N/A"
                    MAX-ACCESS read-only
                    STATUS current
                    DESCRIPTION "Dehumidification"
                    ::= { digitalObjects 10 }

        -- 1.3.6.1.4.1.9839.2.1.1.11
        humidification OBJECT-TYPE
                    SYNTAX Integer32 (0..1)
                    UNITS "N/A"
                    MAX-ACCESS read-only
                    STATUS current
                    DESCRIPTION "Humidification"
                    ::= { digitalObjects 11 }

        -- 1.3.6.1.4.1.9839.2.1.1.12
        emerg OBJECT-TYPE
                    SYNTAX Integer32 (0..1)
                    UNITS "N/A"
                    MAX-ACCESS read-only
                    STATUS current
                    DESCRIPTION "Main Power Loss"
                    ::= { digitalObjects 12 }
  
        -- 1.3.6.1.4.1.9839.2.1.1.20
        alarmAccess OBJECT-TYPE
                    SYNTAX Integer32 (0..1)
                    UNITS "N/A"
                    MAX-ACCESS read-only
                    STATUS current
                    DESCRIPTION "Tampering Alarm"
                    ::= { digitalObjects 20 }

        -- 1.3.6.1.4.1.9839.2.1.1.21
        alarmRoomHT OBJECT-TYPE
                    SYNTAX Integer32 (0..1)
                    UNITS "N/A"
                    MAX-ACCESS read-only
                    STATUS current
                    DESCRIPTION "Alarm: Room High Temperature"
                    ::= { digitalObjects 21 }

        -- 1.3.6.1.4.1.9839.2.1.1.22
        alarmRoomLT OBJECT-TYPE
                    SYNTAX Integer32 (0..1)
                    UNITS "N/A"
                    MAX-ACCESS read-only
                    STATUS current
                    DESCRIPTION "Alarm: Room Low Temperature"
                    ::= { digitalObjects 22 }

        -- 1.3.6.1.4.1.9839.2.1.1.23
        alarmRoomHH OBJECT-TYPE
                    SYNTAX Integer32 (0..1)
                    UNITS "N/A"
                    MAX-ACCESS read-only
                    STATUS current
                    DESCRIPTION "Alarm: Room High Humidity"
                    ::= { digitalObjects 23 }

        -- 1.3.6.1.4.1.9839.2.1.1.24
        alarmRoomLH OBJECT-TYPE
                    SYNTAX Integer32 (0..1)
                    UNITS "N/A"
                    MAX-ACCESS read-only
                    STATUS current
                    DESCRIPTION "Alarm: Room Low Humidity"
                    ::= { digitalObjects 24 }

        -- 1.3.6.1.4.1.9839.2.1.1.25
        alarmRoomEAP OBJECT-TYPE
                    SYNTAX Integer32 (0..1)
                    UNITS "N/A"
                    MAX-ACCESS read-only
                    STATUS current
                    DESCRIPTION "Room T+H Limits by External Sensors"
                    ::= { digitalObjects 25 }

        -- 1.3.6.1.4.1.9839.2.1.1.26
        alarmFilter OBJECT-TYPE
                    SYNTAX Integer32 (0..1)
                    UNITS "N/A"
                    MAX-ACCESS read-only
                    STATUS current
                    DESCRIPTION "Alarm: Clogged Filter"
                    ::= { digitalObjects 26 }

        -- 1.3.6.1.4.1.9839.2.1.1.27
        alarmFlood OBJECT-TYPE
                    SYNTAX Integer32 (0..1)
                    UNITS "N/A"
                    MAX-ACCESS read-only
                    STATUS current
                    DESCRIPTION "Alarm: Water Leakage Detected"
                    ::= { digitalObjects 27 }

        -- 1.3.6.1.4.1.9839.2.1.1.28
        alarmAirFlow OBJECT-TYPE
                    SYNTAX Integer32 (0..1)
                    UNITS "N/A"
                    MAX-ACCESS read-only
                    STATUS current
                    DESCRIPTION "Alarm: Loss of Air Flow"
                    ::= { digitalObjects 28 }

        -- 1.3.6.1.4.1.9839.2.1.1.29
        alarmHeater OBJECT-TYPE
                    SYNTAX Integer32 (0..1)
                    UNITS "N/A"
                    MAX-ACCESS read-only
                    STATUS current
                    DESCRIPTION "Alarm: Heater Overheating"
                    ::= { digitalObjects 29 }

        -- 1.3.6.1.4.1.9839.2.1.1.30
        alarmHP1 OBJECT-TYPE
                    SYNTAX Integer32 (0..1)
                    UNITS "N/A"
                    MAX-ACCESS read-only
                    STATUS current
                    DESCRIPTION "Alarm: Circuit 1 High Pressure"
                    ::= { digitalObjects 30 }

        -- 1.3.6.1.4.1.9839.2.1.1.31
        alarmHP2 OBJECT-TYPE
                    SYNTAX Integer32 (0..1)
                    UNITS "N/A"
                    MAX-ACCESS read-only
                    STATUS current
                    DESCRIPTION "Alarm: Circuit 1 High Pressure"
                    ::= { digitalObjects 31 }

        -- 1.3.6.1.4.1.9839.2.1.1.32
        alarmLP1 OBJECT-TYPE
                    SYNTAX Integer32 (0..1)
                    UNITS "N/A"
                    MAX-ACCESS read-only
                    STATUS current
                    DESCRIPTION "Alarm: Circuit 1 Low Pressure"
                    ::= { digitalObjects 32 }

        -- 1.3.6.1.4.1.9839.2.1.1.33
        alarmLP2 OBJECT-TYPE
                    SYNTAX Integer32 (0..1)
                    UNITS "N/A"
                    MAX-ACCESS read-only
                    STATUS current
                    DESCRIPTION "Alarm: Circuit 2 Low Pressure"
                    ::= { digitalObjects 33 }

        -- 1.3.6.1.4.1.9839.2.1.1.34
        alarmEXV1 OBJECT-TYPE
                    SYNTAX Integer32 (0..1)
                    UNITS "N/A"
                    MAX-ACCESS read-only
                    STATUS current
                    DESCRIPTION "Alarm: Circuit 1 Electronic Valve Failure"
                    ::= { digitalObjects 34 }

        -- 1.3.6.1.4.1.9839.2.1.1.35
        alarmEXV2 OBJECT-TYPE
                    SYNTAX Integer32 (0..1)
                    UNITS "N/A"
                    MAX-ACCESS read-only
                    STATUS current
                    DESCRIPTION "Alarm: Circuit 2 Electronic Valve Failure"
                    ::= { digitalObjects 35 }

        -- 1.3.6.1.4.1.9839.2.1.1.36
        alarmPSE OBJECT-TYPE
                    SYNTAX Integer32 (0..1)
                    UNITS "N/A"
                    MAX-ACCESS read-only
                    STATUS current
                    DESCRIPTION "Alarm: Wrong Phase Sequence"
                    ::= { digitalObjects 36 }

        -- 1.3.6.1.4.1.9839.2.1.1.37
        alarmSmokeFire OBJECT-TYPE
                    SYNTAX Integer32 (0..1)
                    UNITS "N/A"
                    MAX-ACCESS read-only
                    STATUS current
                    DESCRIPTION "Alarm: SMOKE-FIRE DETECTED"
                    ::= { digitalObjects 37 }

        -- 1.3.6.1.4.1.9839.2.1.1.38
        alarmLAN OBJECT-TYPE
                    SYNTAX Integer32 (0..1)
                    UNITS "N/A"
                    MAX-ACCESS read-only
                    STATUS current
                    DESCRIPTION "Interrupted LAN Alarm"
                    ::= { digitalObjects 38 }

        -- 1.3.6.1.4.1.9839.2.1.1.39
        alarmHUHC OBJECT-TYPE
                    SYNTAX Integer32 (0..1)
                    UNITS "N/A"
                    MAX-ACCESS read-only
                    STATUS current
                    DESCRIPTION "Alarm: Humidifier High Current"
                    ::= { digitalObjects 39 }

        -- 1.3.6.1.4.1.9839.2.1.1.40
        alarmHUPL OBJECT-TYPE
                    SYNTAX Integer32 (0..1)
                    UNITS "N/A"
                    MAX-ACCESS read-only
                    STATUS current
                    DESCRIPTION "Alarm: Humidifier Power Loss"
                    ::= { digitalObjects 40 }

        -- 1.3.6.1.4.1.9839.2.1.1.41
        alarmHUWL OBJECT-TYPE
                    SYNTAX Integer32 (0..1)
                    UNITS "N/A"
                    MAX-ACCESS read-only
                    STATUS current
                    DESCRIPTION "Alarm: Humidifier Water Loss"
                    ::= { digitalObjects 41 }

        -- 1.3.6.1.4.1.9839.2.1.1.42
        alarmCWDHT OBJECT-TYPE
                    SYNTAX Integer32 (0..1)
                    UNITS "N/A"
                    MAX-ACCESS read-only
                    STATUS current
                    DESCRIPTION "Alarm: CW Temperature too High for Dehumidification"
                    ::= { digitalObjects 42 }

        -- 1.3.6.1.4.1.9839.2.1.1.43
        alarmCWF OBJECT-TYPE
                    SYNTAX Integer32 (0..1)
                    UNITS "N/A"
                    MAX-ACCESS read-only
                    STATUS current
                    DESCRIPTION "Alarm: CW Valve Failure or Water Flow too Low"
                    ::= { digitalObjects 43 }

        -- 1.3.6.1.4.1.9839.2.1.1.44
        alarmCWFF OBJECT-TYPE
                    SYNTAX Integer32 (0..1)
                    UNITS "N/A"
                    MAX-ACCESS read-only
                    STATUS current
                    DESCRIPTION "Alarm: Loss of Water Flow"
                    ::= { digitalObjects 44 }

        -- 1.3.6.1.4.1.9839.2.1.1.45
        alarmCWHT OBJECT-TYPE
                    SYNTAX Integer32 (0..1)
                    UNITS "N/A"
                    MAX-ACCESS read-only
                    STATUS current
                    DESCRIPTION "Alarm: High Chilled Water Temperature"
                    ::= { digitalObjects 45 }

        -- 1.3.6.1.4.1.9839.2.1.1.46
        alarmRTS OBJECT-TYPE
                    SYNTAX Integer32 (0..1)
                    UNITS "N/A"
                    MAX-ACCESS read-only
                    STATUS current
                    DESCRIPTION "Alarm: Room Temp. Sensor Failed/Disconnected"
                    ::= { digitalObjects 46 }

        -- 1.3.6.1.4.1.9839.2.1.1.47
        alarmHWS OBJECT-TYPE
                    SYNTAX Integer32 (0..1)
                    UNITS "N/A"
                    MAX-ACCESS read-only
                    STATUS current
                    DESCRIPTION "Alarm: Hot Water Temp. Sensor Failed/Disconnected"
                    ::= { digitalObjects 47 }

        -- 1.3.6.1.4.1.9839.2.1.1.48
        alarmCWS OBJECT-TYPE
                    SYNTAX Integer32 (0..1)
                    UNITS "N/A"
                    MAX-ACCESS read-only
                    STATUS current
                    DESCRIPTION "Alarm: Chilled Water Temp. Sensor Failed/Disconnected"
                    ::= { digitalObjects 48 }

        -- 1.3.6.1.4.1.9839.2.1.1.49
        alarmOTS OBJECT-TYPE
                    SYNTAX Integer32 (0..1)
                    UNITS "N/A"
                    MAX-ACCESS read-only
                    STATUS current
                    DESCRIPTION "Alarm: Outdoor Temperature Sensor Failed/Disconnected"
                    ::= { digitalObjects 49 }

        -- 1.3.6.1.4.1.9839.2.1.1.50
        alarmDTS OBJECT-TYPE
                    SYNTAX Integer32 (0..1)
                    UNITS "N/A"
                    MAX-ACCESS read-only
                    STATUS current
                    DESCRIPTION "Alarm: Delivery Air Temp. Sensor Failed/Disconnected"
                    ::= { digitalObjects 50 }

        -- 1.3.6.1.4.1.9839.2.1.1.51
        alarmRHS OBJECT-TYPE
                    SYNTAX Integer32 (0..1)
                    UNITS "N/A"
                    MAX-ACCESS read-only
                    STATUS current
                    DESCRIPTION "Alarm: Room Humidity Sensor Failed/Disconnected"
                    ::= { digitalObjects 51 }

        -- 1.3.6.1.4.1.9839.2.1.1.52
        alarmCWOTS OBJECT-TYPE
                    SYNTAX Integer32 (0..1)
                    UNITS "N/A"
                    MAX-ACCESS read-only
                    STATUS current
                    DESCRIPTION "Alarm: Chilled Water Outlet T. Sensor Failed/Disconnected"
                    ::= { digitalObjects 52 }

        -- 1.3.6.1.4.1.9839.2.1.1.53
        alarmC1Hours OBJECT-TYPE
                    SYNTAX Integer32 (0..1)
                    UNITS "N/A"
                    MAX-ACCESS read-only
                    STATUS current
                    DESCRIPTION "ServiceAlarm: Compressor 1 hour counter threshold"
                    ::= { digitalObjects 53 }

        -- 1.3.6.1.4.1.9839.2.1.1.54
        alarmC2Hours OBJECT-TYPE
                    SYNTAX Integer32 (0..1)
                    UNITS "N/A"
                    MAX-ACCESS read-only
                    STATUS current
                    DESCRIPTION "ServiceAlarm: Compressor 2 hour counter threshold"
                    ::= { digitalObjects 54 }

        -- 1.3.6.1.4.1.9839.2.1.1.55
        alarmC3Hours OBJECT-TYPE
                    SYNTAX Integer32 (0..1)
                    UNITS "N/A"
                    MAX-ACCESS read-only
                    STATUS current
                    DESCRIPTION "ServiceAlarm: Compressor 3 hour counter threshold"
                    ::= { digitalObjects 55 }

        -- 1.3.6.1.4.1.9839.2.1.1.56
        alarmC4Hours OBJECT-TYPE
                    SYNTAX Integer32 (0..1)
                    UNITS "N/A"
                    MAX-ACCESS read-only
                    STATUS current
                    DESCRIPTION "ServiceAlarm: Compressor 4 hour counter threshold"
                    ::= { digitalObjects 56 }

        -- 1.3.6.1.4.1.9839.2.1.1.57
        alarmFilterHours OBJECT-TYPE
                    SYNTAX Integer32 (0..1)
                    UNITS "N/A"
                    MAX-ACCESS read-only
                    STATUS current
                    DESCRIPTION "ServiceAlarm: Air Filter hour counter threshold"
                    ::= { digitalObjects 57 }

        -- 1.3.6.1.4.1.9839.2.1.1.58
        alarmHeat1Hours OBJECT-TYPE
                    SYNTAX Integer32 (0..1)
                    UNITS "N/A"
                    MAX-ACCESS read-only
                    STATUS current
                    DESCRIPTION "ServiceAlarm: Heater 1 hour counter threshold"
                    ::= { digitalObjects 58 }

        -- 1.3.6.1.4.1.9839.2.1.1.59
        alarmHeat2Hours OBJECT-TYPE
                    SYNTAX Integer32 (0..1)
                    UNITS "N/A"
                    MAX-ACCESS read-only
                    STATUS current
                    DESCRIPTION "ServiceAlarm: Heater 1 hour counter threshold"
                    ::= { digitalObjects 59 }

        -- 1.3.6.1.4.1.9839.2.1.1.60
        alarmHumHours OBJECT-TYPE
                    SYNTAX Integer32 (0..1)
                    UNITS "N/A"
                    MAX-ACCESS read-only
                    STATUS current
                    DESCRIPTION "ServiceAlarm: Humidifier hour counter threshold"
                    ::= { digitalObjects 60 }

        -- 1.3.6.1.4.1.9839.2.1.1.61
        alarmUnitHours OBJECT-TYPE
                    SYNTAX Integer32 (0..1)
                    UNITS "N/A"
                    MAX-ACCESS read-only
                    STATUS current
                    DESCRIPTION "ServiceAlarm: Unit hour counter threshold"
                    ::= { digitalObjects 61 }

        -- 1.3.6.1.4.1.9839.2.1.1.62
        alarmDI2 OBJECT-TYPE
                    SYNTAX Integer32 (0..1)
                    UNITS "N/A"
                    MAX-ACCESS read-only
                    STATUS current
                    DESCRIPTION "Alarm by Digital Input 2"
                    ::= { digitalObjects 62 }

        -- 1.3.6.1.4.1.9839.2.1.1.63
        alarmDI4 OBJECT-TYPE
                    SYNTAX Integer32 (0..1)
                    UNITS "N/A"
                    MAX-ACCESS read-only
                    STATUS current
                    DESCRIPTION "Alarm by Digital Input 4"
                    ::= { digitalObjects 63 }

        -- 1.3.6.1.4.1.9839.2.1.1.64
        alarmDI6 OBJECT-TYPE
                    SYNTAX Integer32 (0..1)
                    UNITS "N/A"
                    MAX-ACCESS read-only
                    STATUS current
                    DESCRIPTION "Alarm by Digital Input 6"
                    ::= { digitalObjects 64 }

        -- 1.3.6.1.4.1.9839.2.1.1.65
        alarmHum OBJECT-TYPE
                    SYNTAX Integer32 (0..1)
                    UNITS "N/A"
                    MAX-ACCESS read-only
                    STATUS current
                    DESCRIPTION "Humidifier General Alarm"
                    ::= { digitalObjects 65 }

        -- 1.3.6.1.4.1.9839.2.1.1.66
        alarmGeneral OBJECT-TYPE
                    SYNTAX Integer32 (0..1)
                    UNITS "N/A"
                    MAX-ACCESS read-only
                    STATUS current
                    DESCRIPTION "General Alarm"
                    ::= { digitalObjects 66 }

        -- 1.3.6.1.4.1.9839.2.1.1.67
        alarm2ndLevel OBJECT-TYPE
                    SYNTAX Integer32 (0..1)
                    UNITS "N/A"
                    MAX-ACCESS read-only
                    STATUS current
                    DESCRIPTION "Standby Unit Switchover Alarm"
                    ::= { digitalObjects 67 }

        -- 1.3.6.1.4.1.9839.2.1.1.68
        alarmA OBJECT-TYPE
                    SYNTAX Integer32 (0..1)
                    UNITS "N/A"
                    MAX-ACCESS read-only
                    STATUS current
                    DESCRIPTION "Type A Alarm"
                    ::= { digitalObjects 68 }

        -- 1.3.6.1.4.1.9839.2.1.1.69
        alarmB OBJECT-TYPE
                    SYNTAX Integer32 (0..1)
                    UNITS "N/A"
                    MAX-ACCESS read-only
                    STATUS current
                    DESCRIPTION "Type B Alarm"
                    ::= { digitalObjects 69 }

        -- 1.3.6.1.4.1.9839.2.1.1.70
        alarmC OBJECT-TYPE
                    SYNTAX Integer32 (0..1)
                    UNITS "N/A"
                    MAX-ACCESS read-only
                    STATUS current
                    DESCRIPTION "Type C Alarm"
                    ::= { digitalObjects 70 }

        -- 1.3.6.1.4.1.9839.2.1.1.71
        selDXCW OBJECT-TYPE
                    SYNTAX Integer32 (0..1)
                    UNITS "N/A"
                    MAX-ACCESS read-write
                    STATUS current
                    DESCRIPTION "DX/CW Switch on TC Units"
                    ::= { digitalObjects 71 }

        -- 1.3.6.1.4.1.9839.2.1.1.72
        selSW OBJECT-TYPE
                    SYNTAX Integer32 (0..1)
                    UNITS "N/A"
                    MAX-ACCESS read-write
                    STATUS current
                    DESCRIPTION "Summer/Winter Switchover"
                    ::= { digitalObjects 72 }

        -- 1.3.6.1.4.1.9839.2.1.1.75
        systemOnOff OBJECT-TYPE
                    SYNTAX Integer32 (0..1)
                    UNITS "N/A"
                    MAX-ACCESS read-write
                    STATUS current
                    DESCRIPTION "System On-Off"
                    ::= { digitalObjects 75 }

        -- 1.3.6.1.4.1.9839.2.1.1.76
        resetAlarm OBJECT-TYPE
                    SYNTAX Integer32 (0..1)
                    UNITS "N/A"
                    MAX-ACCESS read-write
                    STATUS current
                    DESCRIPTION "Alarm Reset"
                    ::= { digitalObjects 76 }

        -- 1.3.6.1.4.1.9839.2.1.1.77
        resetHrsFilt OBJECT-TYPE
                    SYNTAX Integer32 (0..1)
                    UNITS "N/A"
                    MAX-ACCESS read-write
                    STATUS current
                    DESCRIPTION "Filter Run Hours Reset"
                    ::= { digitalObjects 77 }

        -- 1.3.6.1.4.1.9839.2.1.1.78
        resetHrC1 OBJECT-TYPE
                    SYNTAX Integer32 (0..1)
                    UNITS "N/A"
                    MAX-ACCESS read-write
                    STATUS current
                    DESCRIPTION "Compressor 1 Run Hours Reset"
                    ::= { digitalObjects 78 }

        -- 1.3.6.1.4.1.9839.2.1.1.79
        resetHrC2 OBJECT-TYPE
                    SYNTAX Integer32 (0..1)
                    UNITS "N/A"
                    MAX-ACCESS read-write
                    STATUS current
                    DESCRIPTION "Compressor 2 Run Hours Reset"
                    ::= { digitalObjects 79 }

        -- 1.3.6.1.4.1.9839.2.1.1.80
        resetHrC3 OBJECT-TYPE
                    SYNTAX Integer32 (0..1)
                    UNITS "N/A"
                    MAX-ACCESS read-write
                    STATUS current
                    DESCRIPTION "Compressor 3 Run Hours Reset"
                    ::= { digitalObjects 80 }

        -- 1.3.6.1.4.1.9839.2.1.1.81
        resetHrC4 OBJECT-TYPE
                    SYNTAX Integer32 (0..1)
                    UNITS "N/A"
                    MAX-ACCESS read-write
                    STATUS current
                    DESCRIPTION "Compressor 4 Run Hours Reset"
                    ::= { digitalObjects 81 }

        -- 1.3.6.1.4.1.9839.2.1.1.82
        resetStC1 OBJECT-TYPE
                    SYNTAX Integer32 (0..1)
                    UNITS "N/A"
                    MAX-ACCESS read-write
                    STATUS current
                    DESCRIPTION "Compressor 1 Starting Counter Reset "
                    ::= { digitalObjects 82 }

        -- 1.3.6.1.4.1.9839.2.1.1.83
        resetStC2 OBJECT-TYPE
                    SYNTAX Integer32 (0..1)
                    UNITS "N/A"
                    MAX-ACCESS read-write
                    STATUS current
                    DESCRIPTION "Compressor 2 Starting Counter Reset "
                    ::= { digitalObjects 83 }

        -- 1.3.6.1.4.1.9839.2.1.1.84
        resetStC3 OBJECT-TYPE
                    SYNTAX Integer32 (0..1)
                    UNITS "N/A"
                    MAX-ACCESS read-write
                    STATUS current
                    DESCRIPTION "Compressor 3 Starting Counter Reset "
                    ::= { digitalObjects 84 }

        -- 1.3.6.1.4.1.9839.2.1.1.85
        resetStC4 OBJECT-TYPE
                    SYNTAX Integer32 (0..1)
                    UNITS "N/A"
                    MAX-ACCESS read-write
                    STATUS current
                    DESCRIPTION "Compressor 4 Starting Counter Reset "
                    ::= { digitalObjects 85 }

        -- 1.3.6.1.4.1.9839.2.1.1.86
        resetHrH1 OBJECT-TYPE
                    SYNTAX Integer32 (0..1)
                    UNITS "N/A"
                    MAX-ACCESS read-write
                    STATUS current
                    DESCRIPTION "Heater 1 Run Hours Reset"
                    ::= { digitalObjects 86 }


        -- 1.3.6.1.4.1.9839.2.1.1.87
        resetHrH2 OBJECT-TYPE
                    SYNTAX Integer32 (0..1)
                    UNITS "N/A"
                    MAX-ACCESS read-write
                    STATUS current
                    DESCRIPTION "Heater 2 Run Hours Reset"
                    ::= { digitalObjects 87 }

        -- 1.3.6.1.4.1.9839.2.1.1.88
        resetStH1 OBJECT-TYPE
                    SYNTAX Integer32 (0..1)
                    UNITS "N/A"
                    MAX-ACCESS read-write
                    STATUS current
                    DESCRIPTION "Heater 1 Starting Counter Reset"
                    ::= { digitalObjects 88 }

        -- 1.3.6.1.4.1.9839.2.1.1.89
        resetStH2 OBJECT-TYPE
                    SYNTAX Integer32 (0..1)
                    UNITS "N/A"
                    MAX-ACCESS read-write
                    STATUS current
                    DESCRIPTION "Heater 2 Starting Counter Reset"
                    ::= { digitalObjects 89 }

        -- 1.3.6.1.4.1.9839.2.1.1.90
        resetHrHU OBJECT-TYPE
                    SYNTAX Integer32 (0..1)
                    UNITS "N/A"
                    MAX-ACCESS read-write
                    STATUS current
                    DESCRIPTION "Humidifier Run Hours Reset"
                    ::= { digitalObjects 90 }

        -- 1.3.6.1.4.1.9839.2.1.1.91
        resetStHU OBJECT-TYPE
                    SYNTAX Integer32 (0..1)
                    UNITS "N/A"
                    MAX-ACCESS read-write
                    STATUS current
                    DESCRIPTION "Humidifier Starting Counter Reset"
                    ::= { digitalObjects 91 }

        -- 1.3.6.1.4.1.9839.2.1.1.92
        resetHrACU OBJECT-TYPE
                    SYNTAX Integer32 (0..1)
                    UNITS "N/A"
                    MAX-ACCESS read-write
                    STATUS current
                    DESCRIPTION "Unit Run Hours Reset"
                    ::= { digitalObjects 92 }

        -- 1.3.6.1.4.1.9839.2.1.1.95
        sleepmode OBJECT-TYPE
                    SYNTAX Integer32 (0..1)
                    UNITS "N/A"
                    MAX-ACCESS read-write
                    STATUS current
                    DESCRIPTION "Setback Mode (Sleep Mode)"
                    ::= { digitalObjects 95 }

        -- 1.3.6.1.4.1.9839.2.1.1.96
        smtest OBJECT-TYPE
                    SYNTAX Integer32 (0..1)
                    UNITS "N/A"
                    MAX-ACCESS read-write
                    STATUS current
                    DESCRIPTION "Sleep Mode Test"
                    ::= { digitalObjects 96 }

        -- 1.3.6.1.4.1.9839.2.1.1.97
        enablemeanT OBJECT-TYPE
                    SYNTAX Integer32 (0..1)
                    UNITS "N/A"
                    MAX-ACCESS read-write
                    STATUS current
                    DESCRIPTION "Local/Mean Usage of Values"
                    ::= { digitalObjects 97 }

 
        -- 1.3.6.1.4.1.9839.2.1.2
        analogObjects OBJECT IDENTIFIER ::= { ug40cdzMIB 2 }

        -- 1.3.6.1.4.1.9839.2.1.2.1
        roomTemp OBJECT-TYPE
                    SYNTAX Integer32 (-32767..32767)
                    UNITS "degrees C"
                    MAX-ACCESS read-only
                    STATUS current
                    DESCRIPTION "Room Temperature"
                    ::= { analogObjects 1 }

        -- 1.3.6.1.4.1.9839.2.1.2.2
        outdoorTemp OBJECT-TYPE
                    SYNTAX Integer32 (-32767..32767)
                    UNITS "degrees C"
                    MAX-ACCESS read-only
                    STATUS current
                    DESCRIPTION "Ambient Temperature"
                    ::= { analogObjects 2 }

        -- 1.3.6.1.4.1.9839.2.1.2.3
        deliveryTemp OBJECT-TYPE
                    SYNTAX Integer32 (-32767..32767)
                    UNITS "degrees C"
                    MAX-ACCESS read-write
                    STATUS current
                    DESCRIPTION "Delivery Air Temperature"
                    ::= { analogObjects 3 }

        -- 1.3.6.1.4.1.9839.2.1.2.4
        cwTemp OBJECT-TYPE
                    SYNTAX Integer32 (-32767..32767)
                    UNITS "degrees C"
                    MAX-ACCESS read-only
                    STATUS current
                    DESCRIPTION "Chilled Water Temperature"
                    ::= { analogObjects 4 }

        -- 1.3.6.1.4.1.9839.2.1.2.5
        hwTemp OBJECT-TYPE
                    SYNTAX Integer32 (-32767..32767)
                    UNITS "degrees C"
                    MAX-ACCESS read-only
                    STATUS current
                    DESCRIPTION "Hot Water Temperature"
                    ::= { analogObjects 5 }

        -- 1.3.6.1.4.1.9839.2.1.2.6
        roomRH OBJECT-TYPE
                    SYNTAX Integer32 (-32767..32767)
                    UNITS "rH%"
                    MAX-ACCESS read-only
                    STATUS current
                    DESCRIPTION "Room Relative Humidity"
                    ::= { analogObjects 6 }

        -- 1.3.6.1.4.1.9839.2.1.2.7
        cwoTemp OBJECT-TYPE
                    SYNTAX Integer32 (-32767..32767)
                    UNITS "degrees C"
                    MAX-ACCESS read-only
                    STATUS current
                    DESCRIPTION "Chilled Water Outlet Temperature"
                    ::= { analogObjects 7 }

        -- 1.3.6.1.4.1.9839.2.1.2.8
        evapPress1 OBJECT-TYPE
                    SYNTAX Integer32 (-32767..32767)
                    UNITS "bar"
                    MAX-ACCESS read-write
                    STATUS current
                    DESCRIPTION "Circuit 1 Evaporating Pressure"
                    ::= { analogObjects 8 }

        -- 1.3.6.1.4.1.9839.2.1.2.9
        evapPress2 OBJECT-TYPE
                    SYNTAX Integer32 (-32767..32767)
                    UNITS "bar"
                    MAX-ACCESS read-write
                    STATUS current
                    DESCRIPTION "Circuit 2 Evaporating Pressure"
                    ::= { analogObjects 9 }

        -- 1.3.6.1.4.1.9839.2.1.2.10
        suctTemp1 OBJECT-TYPE
                    SYNTAX Integer32 (-32767..32767)
                    UNITS "degrees C"
                    MAX-ACCESS read-only
                    STATUS current
                    DESCRIPTION "Circuit 1 Suction Temperature"
                    ::= { analogObjects 10 }

        -- 1.3.6.1.4.1.9839.2.1.2.11
        suctTemp2 OBJECT-TYPE
                    SYNTAX Integer32 (-32767..32767)
                    UNITS "degrees C"
                    MAX-ACCESS read-only
                    STATUS current
                    DESCRIPTION "Circuit 2 Suction Temperature"
                    ::= { analogObjects 11 }

        -- 1.3.6.1.4.1.9839.2.1.2.12
        evapTemp1 OBJECT-TYPE
                    SYNTAX Integer32 (-32767..32767)
                    UNITS "degrees C"
                    MAX-ACCESS read-only
                    STATUS current
                    DESCRIPTION "Circuit 1 Evap.Temperature"
                    ::= { analogObjects 12 }

        -- 1.3.6.1.4.1.9839.2.1.2.13
        evapTemp2 OBJECT-TYPE
                    SYNTAX Integer32 (-32767..32767)
                    UNITS "degrees C"
                    MAX-ACCESS read-only
                    STATUS current
                    DESCRIPTION "Circuit 2 Evap.Temperature"
                    ::= { analogObjects 13 }

        -- 1.3.6.1.4.1.9839.2.1.2.14
        ssh1 OBJECT-TYPE
                    SYNTAX Integer32 (-32767..32767)
                    UNITS "degrees C"
                    MAX-ACCESS read-only
                    STATUS current
                    DESCRIPTION "Circuit 1 Superheat"
                    ::= { analogObjects 14 }

        -- 1.3.6.1.4.1.9839.2.1.2.15
        ssh2 OBJECT-TYPE
                    SYNTAX Integer32 (-32767..32767)
                    UNITS "degrees C"
                    MAX-ACCESS read-only
                    STATUS current
                    DESCRIPTION "Circuit 2 Superheat"
                    ::= { analogObjects 15 }

        -- 1.3.6.1.4.1.9839.2.1.2.16
        coolRamp OBJECT-TYPE
                    SYNTAX Integer32 (-32767..32767)
                    UNITS "%"
                    MAX-ACCESS read-only
                    STATUS current
                    DESCRIPTION "Cooling Valve Ramp"
                    ::= { analogObjects 16 }

        -- 1.3.6.1.4.1.9839.2.1.2.17
        heatRamp OBJECT-TYPE
                    SYNTAX Integer32 (-32767..32767)
                    UNITS "%"
                    MAX-ACCESS read-only
                    STATUS current
                    DESCRIPTION "Heating Valve Ramp"
                    ::= { analogObjects 17 }

        -- 1.3.6.1.4.1.9839.2.1.2.18
        fanSpeed OBJECT-TYPE
                    SYNTAX Integer32 (-32767..32767)
                    UNITS "%"
                    MAX-ACCESS read-only
                    STATUS current
                    DESCRIPTION "Evapor. Fan Speed"
                    ::= { analogObjects 18 }

        -- 1.3.6.1.4.1.9839.2.1.2.20
        coolSetP OBJECT-TYPE
                    SYNTAX Integer32 (-32767..32767)
                    UNITS "degrees C"
                    MAX-ACCESS read-write
                    STATUS current
                    DESCRIPTION "Cooling Set Point"
                    ::= { analogObjects 20 }

        -- 1.3.6.1.4.1.9839.2.1.2.21
        coolDiff OBJECT-TYPE
                    SYNTAX Integer32 (-32767..32767)
                    UNITS "degrees C"
                    MAX-ACCESS read-write
                    STATUS current
                    DESCRIPTION "Cooling Prop.Band"
                    ::= { analogObjects 21 }

        -- 1.3.6.1.4.1.9839.2.1.2.22
        cool2SetP OBJECT-TYPE
                    SYNTAX Integer32 (-32767..32767)
                    UNITS "degrees C"
                    MAX-ACCESS read-write
                    STATUS current
                    DESCRIPTION "Cooling 2nd Set Point"
                    ::= { analogObjects 22 }

        -- 1.3.6.1.4.1.9839.2.1.2.23
        heatSetP OBJECT-TYPE
                    SYNTAX Integer32 (-32767..32767)
                    UNITS "degrees C"
                    MAX-ACCESS read-write
                    STATUS current
                    DESCRIPTION "Heating Set point"
                    ::= { analogObjects 23 }

        -- 1.3.6.1.4.1.9839.2.1.2.24
        heat2SetP OBJECT-TYPE
                    SYNTAX Integer32 (-32767..32767)
                    UNITS "degrees C"
                    MAX-ACCESS read-write
                    STATUS current
                    DESCRIPTION "Heating 2nd Set point"
                    ::= { analogObjects 24 }

        -- 1.3.6.1.4.1.9839.2.1.2.25
        heatDiff OBJECT-TYPE
                    SYNTAX Integer32 (-32767..32767)
                    UNITS "degrees C"
                    MAX-ACCESS read-write
                    STATUS current
                    DESCRIPTION "Heating Prop.Band"
                    ::= { analogObjects 25 }

        -- 1.3.6.1.4.1.9839.2.1.2.26
        thrsHT OBJECT-TYPE
                    SYNTAX Integer32 (-32767..32767)
                    UNITS "degrees C x10"
                    MAX-ACCESS read-write
                    STATUS current
                    DESCRIPTION "High Room Temperature Alarm Threshold"
                    ::= { analogObjects 26 }

        -- 1.3.6.1.4.1.9839.2.1.2.27
        thrsLT OBJECT-TYPE
                    SYNTAX Integer32 (-32767..32767)
                    UNITS "degrees C x10"
                    MAX-ACCESS read-write
                    STATUS current
                    DESCRIPTION "Low Room Temperature Alarm Threshold"
                    ::= { analogObjects 27 }

        -- 1.3.6.1.4.1.9839.2.1.2.28
        smCoolSetp OBJECT-TYPE
                    SYNTAX Integer32 (-32767..32767)
                    UNITS "degrees C"
                    MAX-ACCESS read-write
                    STATUS current
                    DESCRIPTION "Setback Mode: Cooling Setpoint"
                    ::= { analogObjects 28 }

        -- 1.3.6.1.4.1.9839.2.1.2.29
        smHeatSetp OBJECT-TYPE
                    SYNTAX Integer32 (-32767..32767)
                    UNITS "degrees C"
                    MAX-ACCESS read-write
                    STATUS current
                    DESCRIPTION "Setback Mode: Heating Setpoint"
                    ::= { analogObjects 29 }

        -- 1.3.6.1.4.1.9839.2.1.2.30
        cwDehumSetp OBJECT-TYPE
                    SYNTAX Integer32 (-32767..32767)
                    UNITS "degrees C"
                    MAX-ACCESS read-write
                    STATUS current
                    DESCRIPTION "CW Setpoint to Start Dehumidification"
                    ::= { analogObjects 30 }

        -- 1.3.6.1.4.1.9839.2.1.2.31
        cwHtThrsh OBJECT-TYPE
                    SYNTAX Integer32 (-32767..32767)
                    UNITS "degrees C"
                    MAX-ACCESS read-write
                    STATUS current
                    DESCRIPTION "CW High Temperature Alarm Threshold"
                    ::= { analogObjects 31 }

        -- 1.3.6.1.4.1.9839.2.1.2.32
        cwModeSetp OBJECT-TYPE
                    SYNTAX Integer32 (-32767..32767)
                    UNITS "degrees C"
                    MAX-ACCESS read-write
                    STATUS current
                    DESCRIPTION "CW Setpoint to start CW Operating Mode (Only TC Units)"
                    ::= { analogObjects 32 }

        -- 1.3.6.1.4.1.9839.2.1.2.33
        radcoolSpES OBJECT-TYPE
                    SYNTAX Integer32 (-32767..32767)
                    UNITS "degrees C"
                    MAX-ACCESS read-write
                    STATUS current
                    DESCRIPTION "Radcooler Setpoint in Energy Saving Mode"
                    ::= { analogObjects 33 }

        -- 1.3.6.1.4.1.9839.2.1.2.34
        radcoolSpDX OBJECT-TYPE
                    SYNTAX Integer32 (-32767..32767)
                    UNITS "degrees C"
                    MAX-ACCESS read-write
                    STATUS current
                    DESCRIPTION "Radcooler Setpoint in DX Mode"
                    ::= { analogObjects 34 }

        -- 1.3.6.1.4.1.9839.2.1.2.35
        delTempLimit OBJECT-TYPE
                    SYNTAX Integer32 (-32767..32767)
                    UNITS "degrees C x10"
                    MAX-ACCESS read-write
                    STATUS current
                    DESCRIPTION "Delivery Temperature Low Limit Setpoint"
                    ::= { analogObjects 35 }

        -- 1.3.6.1.4.1.9839.2.1.2.36
        dtAutChgMLT OBJECT-TYPE
                    SYNTAX Integer32 (-32767..32767)
                    UNITS "degrees C"
                    MAX-ACCESS read-write
                    STATUS current
                    DESCRIPTION "Delta Temperature for Automatic Mean/Local Changeover"
                    ::= { analogObjects 36 }


        -- 1.3.6.1.4.1.9839.2.1.3
        integerObjects OBJECT IDENTIFIER ::= { ug40cdzMIB 3 }

        -- 1.3.6.1.4.1.9839.2.1.3.1
        filterWorkH OBJECT-TYPE
                    SYNTAX Integer32 (-32767..32767)
                    UNITS "h"
                    MAX-ACCESS read-only
                    STATUS current
                    DESCRIPTION "Air Filter Working Houres"
                    ::= { integerObjects 1 }

        -- 1.3.6.1.4.1.9839.2.1.3.2
        unitWorkH OBJECT-TYPE
                    SYNTAX Integer32 (-32767..32767)
                    UNITS "h"
                    MAX-ACCESS read-only
                    STATUS current
                    DESCRIPTION "Unit Working Houres"
                    ::= { integerObjects 2 }

        -- 1.3.6.1.4.1.9839.2.1.3.3
        compr1WorkH OBJECT-TYPE
                    SYNTAX Integer32 (-32767..32767)
                    UNITS "h"
                    MAX-ACCESS read-only
                    STATUS current
                    DESCRIPTION "Compressor 1 Run Hours"
                    ::= { integerObjects 3 }

        -- 1.3.6.1.4.1.9839.2.1.3.4
        compr2WorkH OBJECT-TYPE
                    SYNTAX Integer32 (-32767..32767)
                    UNITS "h"
                    MAX-ACCESS read-only
                    STATUS current
                    DESCRIPTION "Compressor 2 Run Hours"
                    ::= { integerObjects 4 }

        -- 1.3.6.1.4.1.9839.2.1.3.5
        compr3WorkH OBJECT-TYPE
                    SYNTAX Integer32 (-32767..32767)
                    UNITS "h"
                    MAX-ACCESS read-only
                    STATUS current
                    DESCRIPTION "Compressor 3 Run Hours"
                    ::= { integerObjects 5 }

        -- 1.3.6.1.4.1.9839.2.1.3.6
        compr4WorkH OBJECT-TYPE
                    SYNTAX Integer32 (-32767..32767)
                    UNITS "h"
                    MAX-ACCESS read-only
                    STATUS current
                    DESCRIPTION "Compressor 4 Run Hours"
                    ::= { integerObjects 6 }

        -- 1.3.6.1.4.1.9839.2.1.3.7
        heat1WorkH OBJECT-TYPE
                    SYNTAX Integer32 (-32767..32767)
                    UNITS "h"
                    MAX-ACCESS read-only
                    STATUS current
                    DESCRIPTION "Heater 1 Run Hours"
                    ::= { integerObjects 7 }

        -- 1.3.6.1.4.1.9839.2.1.3.8
        heat2WorkH OBJECT-TYPE
                    SYNTAX Integer32 (-32767..32767)
                    UNITS "h"
                    MAX-ACCESS read-only
                    STATUS current
                    DESCRIPTION "Heater 2 Run Hours"
                    ::= { integerObjects 8 }

        -- 1.3.6.1.4.1.9839.2.1.3.9
        humiWorkH OBJECT-TYPE
                    SYNTAX Integer32 (-32767..32767)
                    UNITS "h"
                    MAX-ACCESS read-only
                    STATUS current
                    DESCRIPTION "Humidifier Run Hours"
                    ::= { integerObjects 9 }

        -- 1.3.6.1.4.1.9839.2.1.3.12
        dehumPband OBJECT-TYPE
                    SYNTAX Integer32 (-32767..32767)
                    UNITS "rH%"
                    MAX-ACCESS read-write
                    STATUS current
                    DESCRIPTION "Dehumidification Prop.Band"
                    ::= { integerObjects 12 }

        -- 1.3.6.1.4.1.9839.2.1.3.13
        humidPband OBJECT-TYPE
                    SYNTAX Integer32 (-32767..32767)
                    UNITS "rH%"
                    MAX-ACCESS read-write
                    STATUS current
                    DESCRIPTION "Humidification Prop.Band"
                    ::= { integerObjects 13 }

        -- 1.3.6.1.4.1.9839.2.1.3.14
        hhAlarmThrsh OBJECT-TYPE
                    SYNTAX Integer32 (-32767..32767)
                    UNITS "rH%"
                    MAX-ACCESS read-write
                    STATUS current
                    DESCRIPTION "High Humidity Alarm Threshold"
                    ::= { integerObjects 14 }

        -- 1.3.6.1.4.1.9839.2.1.3.15
        lhAlarmThrsh OBJECT-TYPE
                    SYNTAX Integer32 (-32767..32767)
                    UNITS "rH%"
                    MAX-ACCESS read-write
                    STATUS current
                    DESCRIPTION "Low Humidity Alarm Threshold"
                    ::= { integerObjects 15 }

        -- 1.3.6.1.4.1.9839.2.1.3.16
        dehumSetp OBJECT-TYPE
                    SYNTAX Integer32 (-32767..32767)
                    UNITS "rH%"
                    MAX-ACCESS read-write
                    STATUS current
                    DESCRIPTION "Dehumidification Setpoint"
                    ::= { integerObjects 16 }

        -- 1.3.6.1.4.1.9839.2.1.3.17
        smDehumSetp OBJECT-TYPE
                    SYNTAX Integer32 (-32767..32767)
                    UNITS "rH%"
                    MAX-ACCESS read-write
                    STATUS current
                    DESCRIPTION "Setback  Mode: Dehumidification Setpoint"
                    ::= { integerObjects 17 }

        -- 1.3.6.1.4.1.9839.2.1.3.18
        humidSetp OBJECT-TYPE
                    SYNTAX Integer32 (-32767..32767)
                    UNITS "rH%"
                    MAX-ACCESS read-write
                    STATUS current
                    DESCRIPTION "Humidification Setpoint"
                    ::= { integerObjects 18 }

        -- 1.3.6.1.4.1.9839.2.1.3.19
        smHumidSetp OBJECT-TYPE
                    SYNTAX Integer32 (-32767..32767)
                    UNITS "rH%"
                    MAX-ACCESS read-write
                    STATUS current
                    DESCRIPTION "Setback  Mode: Humidification Setpoint"
                    ::= { integerObjects 19 }

        -- 1.3.6.1.4.1.9839.2.1.3.20
        pwOnDelay OBJECT-TYPE
                    SYNTAX Integer32 (-32767..32767)
                    UNITS "s"
                    MAX-ACCESS read-write
                    STATUS current
                    DESCRIPTION "Restart Delay"
                    ::= { integerObjects 20 }

        -- 1.3.6.1.4.1.9839.2.1.3.21
        regulDelay OBJECT-TYPE
                    SYNTAX Integer32 (-32767..32767)
                    UNITS "s"
                    MAX-ACCESS read-write
                    STATUS current
                    DESCRIPTION "Regulation Start Transitory"
                    ::= { integerObjects 21 }

        -- 1.3.6.1.4.1.9839.2.1.3.22
        lowPdelay OBJECT-TYPE
                    SYNTAX Integer32 (-32767..32767)
                    UNITS "s"
                    MAX-ACCESS read-write
                    STATUS current
                    DESCRIPTION "Low Pressure Delay"
                    ::= { integerObjects 22 }

        -- 1.3.6.1.4.1.9839.2.1.3.23
        thAlarmdelay OBJECT-TYPE
                    SYNTAX Integer32 (-32767..32767)
                    UNITS "min"
                    MAX-ACCESS read-write
                    STATUS current
                    DESCRIPTION "Temp./Humid.Limits Alarm Delay"
                    ::= { integerObjects 23 }

        -- 1.3.6.1.4.1.9839.2.1.3.24
        regExcTime OBJECT-TYPE
                    SYNTAX Integer32 (-32767..32767)
                    UNITS "min"
                    MAX-ACCESS read-write
                    STATUS current
                    DESCRIPTION "Anti-Hunting Constant"
                    ::= { integerObjects 24 }

        -- 1.3.6.1.4.1.9839.2.1.3.25
        stdbyTime OBJECT-TYPE
                    SYNTAX Integer32 (-32767..32767)
                    UNITS "h"
                    MAX-ACCESS read-write
                    STATUS current
                    DESCRIPTION "Stand-by Cycle Base Time"
                    ::= { integerObjects 25 }

        -- 1.3.6.1.4.1.9839.2.1.3.27
        lanUnit OBJECT-TYPE
                    SYNTAX Integer32 (-32767..32767)
                    UNITS "n"
                    MAX-ACCESS read-write
                    STATUS current
                    DESCRIPTION "Number of LAN Units"
                    ::= { integerObjects 27 }

        -- 1.3.6.1.4.1.9839.2.1.3.28
        smCycleTime OBJECT-TYPE
                    SYNTAX Integer32 (-32767..32767)
                    UNITS "min"
                    MAX-ACCESS read-write
                    STATUS current
                    DESCRIPTION "Sleep Mode Testing Cycle Time"
                    ::= { integerObjects 28 }

        -- 1.3.6.1.4.1.9839.2.1.3.29
        exv1steps OBJECT-TYPE
                    SYNTAX Integer32 (-32767..32767)
                    UNITS "n"
                    MAX-ACCESS read-only
                    STATUS current
                    DESCRIPTION "Circuit 1 EXV Valve Position"
                    ::= { integerObjects 29 }

        -- 1.3.6.1.4.1.9839.2.1.3.30
        exv2steps OBJECT-TYPE
                    SYNTAX Integer32 (-32767..32767)
                    UNITS "n"
                    MAX-ACCESS read-only
                    STATUS current
                    DESCRIPTION "Circuit 2 EXV Valve Position"
                    ::= { integerObjects 30 }


	
	END

--
-- CAREL-ug40cdz.MIB
--
