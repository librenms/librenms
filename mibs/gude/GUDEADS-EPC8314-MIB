GUDEADS-EPC8314-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "202409261531Z"	-- Sep 26, 2024, 3:31:00 PM
	ORGANIZATION "GUDE Systems GmbH"
	CONTACT-INFO
		"Von-der-Wettern-Str. 23
		51149 Cologne
		Germany
		https://www.gude-systems.com"
	DESCRIPTION
		"Expert Power Control 8314 MIB"
	-- 1.3.6.1.4.1.28507
	::= { enterprises 28507 }


epc8314DeviceInfo OBJECT IDENTIFIER 
	-- 1.3.6.1.4.1.28507.97.1.1.2
	::= { epc8314CommonConfig 2 }

epc8314ProdName OBJECT-TYPE
	SYNTAX  OCTET STRING
	MAX-ACCESS read-only
	STATUS  current
	DESCRIPTION
		"The Product Name of the device."
	-- 1.3.6.1.4.1.28507.97.1.1.2.1
	::= { epc8314DeviceInfo 1 }


epc8314FWVersion OBJECT-TYPE
	SYNTAX  OCTET STRING
	MAX-ACCESS read-only
	STATUS  current
	DESCRIPTION
		"Firmware Version of the device."
	-- 1.3.6.1.4.1.28507.97.1.1.2.2
	::= { epc8314DeviceInfo 2 }


epc8314HostName OBJECT-TYPE
	SYNTAX  OCTET STRING
	MAX-ACCESS read-only
	STATUS  current
	DESCRIPTION
		"The configured Host Name."
	-- 1.3.6.1.4.1.28507.97.1.1.2.3
	::= { epc8314DeviceInfo 3 }


epc8314PhysAddress OBJECT-TYPE
	SYNTAX  OCTET STRING
	MAX-ACCESS read-only
	STATUS  current
	DESCRIPTION
		"The MAC address of the device."
	-- 1.3.6.1.4.1.28507.97.1.1.2.4
	::= { epc8314DeviceInfo 4 }


epc8314SerialNumber OBJECT-TYPE
	SYNTAX  Unsigned32
	MAX-ACCESS read-only
	STATUS  current
	DESCRIPTION
		"The Serial Number of the device. Not available for all devices. Production start 2026."
	-- 1.3.6.1.4.1.28507.97.1.1.2.5
	::= { epc8314DeviceInfo 5 }


epc8314ExtInputToggleCount OBJECT-TYPE
	SYNTAX  Unsigned32
	MAX-ACCESS read-only
	STATUS  current
	DESCRIPTION
		"Number of times the Input has changed its state."
	-- 1.3.6.1.4.1.28507.97.1.6.2.2.1.3
	::= { epc8314ExtInputEntry 3 }


epc8314ExtInputs OBJECT IDENTIFIER 
	-- 1.3.6.1.4.1.28507.97.1.6.2
	::= { epc8314ExtSensors 2 }

epc8314ExtInputEntry OBJECT-TYPE
	SYNTAX  Epc8314ExtInputEntry
	MAX-ACCESS not-accessible
	STATUS  current
	DESCRIPTION ""
	INDEX {
		epc8314ExtInputIndex }
	-- 1.3.6.1.4.1.28507.97.1.6.2.2.1
	::= { epc8314ExtInputTable 1 }


Epc8314ExtInputEntry ::= SEQUENCE {

	epc8314ExtInputIndex       Unsigned32,
	epc8314ExtInput            INTEGER,
	epc8314ExtInputToggleCount Unsigned32,
	epc8314ExtInputName        OCTET STRING,
	epc8314ExtInputPortNum     Integer32,
	epc8314ExtInputBlockIndex  Integer32 }


epc8314ExtInput OBJECT-TYPE
	SYNTAX  INTEGER {
			lo(0),
			hi(1) }
	MAX-ACCESS read-only
	STATUS  current
	DESCRIPTION
		"Input state of device"
	-- 1.3.6.1.4.1.28507.97.1.6.2.2.1.2
	::= { epc8314ExtInputEntry 2 }


epc8314ExtActiveInputs OBJECT-TYPE
	SYNTAX  Unsigned32 (1..12)
	MAX-ACCESS read-only
	STATUS  current
	DESCRIPTION
		"Number of suppported Input Channels."
	-- 1.3.6.1.4.1.28507.97.1.6.2.1
	::= { epc8314ExtInputs 1 }


epc8314ExtInputTable OBJECT-TYPE
	SYNTAX  SEQUENCE OF Epc8314ExtInputEntry
	MAX-ACCESS not-accessible
	STATUS  current
	DESCRIPTION ""
	-- 1.3.6.1.4.1.28507.97.1.6.2.2
	::= { epc8314ExtInputs 2 }


epc8314ExtInputIndex OBJECT-TYPE
	SYNTAX  Unsigned32
	MAX-ACCESS read-only
	STATUS  current
	DESCRIPTION ""
	-- 1.3.6.1.4.1.28507.97.1.6.2.2.1.1
	::= { epc8314ExtInputEntry 1 }


epc8314ExtInputName OBJECT-TYPE
	SYNTAX  OCTET STRING (SIZE (0..32))
	MAX-ACCESS read-write
	STATUS  current
	DESCRIPTION
		"A textual string containing name of
		the Input"
	-- 1.3.6.1.4.1.28507.97.1.6.2.2.1.32
	::= { epc8314ExtInputEntry 32 }


epc8314ExtInputPortNum OBJECT-TYPE
	SYNTAX  Integer32
	MAX-ACCESS read-only
	STATUS  current
	DESCRIPTION
		"Number of external Sensor Port when value greater zero, else device built-in Input."
	-- 1.3.6.1.4.1.28507.97.1.6.2.2.1.33
	::= { epc8314ExtInputEntry 33 }


epc8314ExtInputBlockIndex OBJECT-TYPE
	SYNTAX  Integer32
	MAX-ACCESS read-only
	STATUS  current
	DESCRIPTION
		"Either index of device built-in Input, or index of Input in external sensor."
	-- 1.3.6.1.4.1.28507.97.1.6.2.2.1.34
	::= { epc8314ExtInputEntry 34 }


epc8314NTPClient OBJECT IDENTIFIER 
	-- 1.3.6.1.4.1.28507.97.1.5.15
	::= { epc8314IntSensors 15 }

epc8314NTPUnixTime OBJECT-TYPE
	SYNTAX  Unsigned32
	UNITS	"s"
	MAX-ACCESS read-only
	STATUS  current
	DESCRIPTION
		"show received NTP time as unixtime (secs since 1 January 1970)"
	-- 1.3.6.1.4.1.28507.97.1.5.15.2
	::= { epc8314NTPClient 2 }


epc8314NTPLastValidTimestamp OBJECT-TYPE
	SYNTAX  Unsigned32
	UNITS	"s"
	MAX-ACCESS read-only
	STATUS  current
	DESCRIPTION
		"show seconds since last valid NTP timestamp received"
	-- 1.3.6.1.4.1.28507.97.1.5.15.3
	::= { epc8314NTPClient 3 }


epc8314NTPTimeValid OBJECT-TYPE
	SYNTAX  INTEGER {
			notime(0),
			valid(1) }
	MAX-ACCESS read-only
	STATUS  current
	DESCRIPTION
		"Show if valid Time is received"
	-- 1.3.6.1.4.1.28507.97.1.5.15.1
	::= { epc8314NTPClient 1 }


epc8314PortResetDuration OBJECT-TYPE
	SYNTAX  Integer32 (0..65535)
	UNITS	"seconds"
	MAX-ACCESS read-write
	STATUS  current
	DESCRIPTION
		"Delay in sec for turning Port on again after Reset action"
	DEFVAL { 0 }
	-- 1.3.6.1.4.1.28507.97.1.3.1.2.1.8
	::= { epc8314portEntry 8 }


epc8314LineSensorName OBJECT-TYPE
	SYNTAX  OCTET STRING (SIZE (0..32))
	MAX-ACCESS read-write
	STATUS  current
	DESCRIPTION
		"A textual string containing name of a
		Line Sensor"
	-- 1.3.6.1.4.1.28507.97.1.5.1.2.1.100
	::= { epc8314PowerEntry 100 }


epc8314ExtSensorName OBJECT-TYPE
	SYNTAX  OCTET STRING (SIZE (0..32))
	MAX-ACCESS read-write
	STATUS  current
	DESCRIPTION
		"A textual string containing name of a
		external Sensor"
	-- 1.3.6.1.4.1.28507.97.1.6.1.1.32
	::= { epc8314SensorEntry 32 }


epc8314TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.97.1.1.1.1
	::= { epc8314SNMPaccess 1 }


gadsEPC8314 OBJECT IDENTIFIER 
	-- 1.3.6.1.4.1.28507.97
	::= { gudeads 97 }

-- Notification Types
--

events OBJECT IDENTIFIER 
	-- 1.3.6.1.4.1.28507.97.3
	::= { gadsEPC8314 3 }

-- Scalars and Tables
--

epc8314Objects OBJECT IDENTIFIER 
	-- 1.3.6.1.4.1.28507.97.1
	::= { gadsEPC8314 1 }

epc8314CommonConfig OBJECT IDENTIFIER 
	-- 1.3.6.1.4.1.28507.97.1.1
	::= { epc8314Objects 1 }

epc8314SNMPaccess OBJECT IDENTIFIER 
	-- 1.3.6.1.4.1.28507.97.1.1.1
	::= { epc8314CommonConfig 1 }

epc8314TrapIPTable OBJECT-TYPE
	SYNTAX  SEQUENCE OF Epc8314TrapIPEntry
	MAX-ACCESS not-accessible
	STATUS  current
	DESCRIPTION
		"list of all Trap receiver"
	-- 1.3.6.1.4.1.28507.97.1.1.1.2
	::= { epc8314SNMPaccess 2 }


epc8314TrapIPEntry OBJECT-TYPE
	SYNTAX  Epc8314TrapIPEntry
	MAX-ACCESS not-accessible
	STATUS  current
	DESCRIPTION
		"an entry containing management
		informations regarding the list of trap
		receivers"
	INDEX {
		epc8314TrapIPIndex }
	-- 1.3.6.1.4.1.28507.97.1.1.1.2.1
	::= { epc8314TrapIPTable 1 }


Epc8314TrapIPEntry ::= SEQUENCE {

	epc8314TrapIPIndex Integer32,
	epc8314TrapAddr    OCTET STRING }


epc8314TrapIPIndex OBJECT-TYPE
	SYNTAX  Integer32 (1..8)
	MAX-ACCESS read-only
	STATUS  current
	DESCRIPTION
		"A unique value, greater than zero, for each receiver slot."
	-- 1.3.6.1.4.1.28507.97.1.1.1.2.1.1
	::= { epc8314TrapIPEntry 1 }


epc8314TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.97.1.1.1.2.1.2
	::= { epc8314TrapIPEntry 2 }


epc8314DeviceConfig OBJECT IDENTIFIER 
	-- 1.3.6.1.4.1.28507.97.1.2
	::= { epc8314Objects 2 }

epc8314IntActors OBJECT IDENTIFIER 
	-- 1.3.6.1.4.1.28507.97.1.3
	::= { epc8314Objects 3 }

epc8314relayports OBJECT IDENTIFIER 
	-- 1.3.6.1.4.1.28507.97.1.3.1
	::= { epc8314IntActors 1 }

epc8314portNumber OBJECT-TYPE
	SYNTAX  Integer32 (1..12)
	MAX-ACCESS read-only
	STATUS  current
	DESCRIPTION
		"The number of Relay Ports"
	-- 1.3.6.1.4.1.28507.97.1.3.1.1
	::= { epc8314relayports 1 }


-- the Interfaces table
-- The Interfaces table contains information on the entity's
-- interfaces.  Each sub-layer below the internetwork-layer
-- of a network interface is considered to be an interface.

epc8314portTable OBJECT-TYPE
	SYNTAX  SEQUENCE OF Epc8314portEntry
	MAX-ACCESS not-accessible
	STATUS  current
	DESCRIPTION
		"list of all EPC Relay Ports"
	-- 1.3.6.1.4.1.28507.97.1.3.1.2
	::= { epc8314relayports 2 }


epc8314portEntry OBJECT-TYPE
	SYNTAX  Epc8314portEntry
	MAX-ACCESS not-accessible
	STATUS  current
	DESCRIPTION
		"An entry containing management information applicable to a
		particular relay port."
	INDEX {
		epc8314PortIndex }
	-- 1.3.6.1.4.1.28507.97.1.3.1.2.1
	::= { epc8314portTable 1 }


Epc8314portEntry ::= SEQUENCE {

	epc8314PortIndex         Integer32,
	epc8314PortName          OCTET STRING,
	epc8314PortState         INTEGER,
	epc8314PortSwitchCount   Integer32,
	epc8314PortStartupMode   INTEGER,
	epc8314PortStartupDelay  Integer32,
	epc8314PortRepowerTime   Integer32,
	epc8314PortResetDuration Integer32 }


epc8314PortIndex OBJECT-TYPE
	SYNTAX  Integer32 (1..8)
	MAX-ACCESS read-only
	STATUS  current
	DESCRIPTION
		"A unique value, greater than zero, for each Relay Port."
	-- 1.3.6.1.4.1.28507.97.1.3.1.2.1.1
	::= { epc8314portEntry 1 }


epc8314PortName OBJECT-TYPE
	SYNTAX  OCTET STRING (SIZE (0..15))
	MAX-ACCESS read-write
	STATUS  current
	DESCRIPTION
		"A textual string containing name of a Relay Port."
	-- 1.3.6.1.4.1.28507.97.1.3.1.2.1.2
	::= { epc8314portEntry 2 }


epc8314PortState OBJECT-TYPE
	SYNTAX  INTEGER {
			off(0),
			on(1) }
	MAX-ACCESS read-write
	STATUS  current
	DESCRIPTION
		"current state a Relay Port"
	-- 1.3.6.1.4.1.28507.97.1.3.1.2.1.3
	::= { epc8314portEntry 3 }


epc8314PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.97.1.3.1.2.1.4
	::= { epc8314portEntry 4 }


epc8314PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.97.1.3.1.2.1.5
	::= { epc8314portEntry 5 }


epc8314PortStartupDelay OBJECT-TYPE
	SYNTAX  Integer32
	UNITS	"seconds"
	MAX-ACCESS read-write
	STATUS  current
	DESCRIPTION
		"Delay in sec for startup action"
	DEFVAL { 0 }
	-- 1.3.6.1.4.1.28507.97.1.3.1.2.1.6
	::= { epc8314portEntry 6 }


epc8314PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.97.1.3.1.2.1.7
	::= { epc8314portEntry 7 }


epc8314ExtActors OBJECT IDENTIFIER 
	-- 1.3.6.1.4.1.28507.97.1.4
	::= { epc8314Objects 4 }

epc8314IntSensors OBJECT IDENTIFIER 
	-- 1.3.6.1.4.1.28507.97.1.5
	::= { epc8314Objects 5 }

epc8314PowerChan OBJECT IDENTIFIER 
	-- 1.3.6.1.4.1.28507.97.1.5.1
	::= { epc8314IntSensors 1 }

epc8314ActivePowerChan OBJECT-TYPE
	SYNTAX  Unsigned32 (1)
	MAX-ACCESS read-only
	STATUS  current
	DESCRIPTION
		"Number of suppported Power Channels."
	-- 1.3.6.1.4.1.28507.97.1.5.1.1
	::= { epc8314PowerChan 1 }


epc8314PowerTable OBJECT-TYPE
	SYNTAX  SEQUENCE OF Epc8314PowerEntry
	MAX-ACCESS not-accessible
	STATUS  current
	DESCRIPTION
		"All available Channel Interfaces."
	-- 1.3.6.1.4.1.28507.97.1.5.1.2
	::= { epc8314PowerChan 2 }


epc8314PowerEntry OBJECT-TYPE
	SYNTAX  Epc8314PowerEntry
	MAX-ACCESS not-accessible
	STATUS  current
	DESCRIPTION
		"An entry containing management information
		applicable to a particular Power Channel."
	INDEX {
		epc8314PowerIndex }
	-- 1.3.6.1.4.1.28507.97.1.5.1.2.1
	::= { epc8314PowerTable 1 }


Epc8314PowerEntry ::= SEQUENCE {

	epc8314PowerIndex                   Integer32,
	epc8314ChanStatus                   Integer32,
	epc8314AbsEnergyActive              Unsigned32,
	epc8314PowerActive                  Integer32,
	epc8314Current                      Unsigned32,
	epc8314Voltage                      Unsigned32,
	epc8314Frequency                    Unsigned32,
	epc8314PowerFactor                  Integer32,
	epc8314Pangle                       Integer32,
	epc8314PowerApparent                Integer32,
	epc8314PowerReactive                Integer32,
	epc8314AbsEnergyReactive            Unsigned32,
	epc8314AbsEnergyActiveResettable    Unsigned32,
	epc8314AbsEnergyReactiveResettable  Unsigned32,
	epc8314ResetTime                    Unsigned32,
	epc8314ForwEnergyActive             Unsigned32,
	epc8314ForwEnergyReactive           Unsigned32,
	epc8314ForwEnergyActiveResettable   Unsigned32,
	epc8314ForwEnergyReactiveResettable Unsigned32,
	epc8314RevEnergyActive              Unsigned32,
	epc8314RevEnergyReactive            Unsigned32,
	epc8314RevEnergyActiveResettable    Unsigned32,
	epc8314RevEnergyReactiveResettable  Unsigned32,
	epc8314LineSensorName               OCTET STRING }


epc8314PowerIndex OBJECT-TYPE
	SYNTAX  Integer32 (1)
	MAX-ACCESS read-only
	STATUS  current
	DESCRIPTION
		"Index of Power Channel entries"
	-- 1.3.6.1.4.1.28507.97.1.5.1.2.1.1
	::= { epc8314PowerEntry 1 }


epc8314ChanStatus OBJECT-TYPE
	SYNTAX  Integer32 (0..1)
	MAX-ACCESS read-only
	STATUS  current
	DESCRIPTION
		"0 = data not active, 1 = data valid"
	-- 1.3.6.1.4.1.28507.97.1.5.1.2.1.2
	::= { epc8314PowerEntry 2 }


epc8314AbsEnergyActive OBJECT-TYPE
	SYNTAX  Unsigned32
	UNITS	"Wh"
	MAX-ACCESS read-only
	STATUS  current
	DESCRIPTION
		"Absolute Active Energy counter."
	-- 1.3.6.1.4.1.28507.97.1.5.1.2.1.3
	::= { epc8314PowerEntry 3 }


epc8314PowerActive OBJECT-TYPE
	SYNTAX  Integer32
	UNITS	"W"
	MAX-ACCESS read-only
	STATUS  current
	DESCRIPTION
		"Active Power"
	-- 1.3.6.1.4.1.28507.97.1.5.1.2.1.4
	::= { epc8314PowerEntry 4 }


epc8314Current OBJECT-TYPE
	SYNTAX  Unsigned32
	UNITS	"mA"
	MAX-ACCESS read-only
	STATUS  current
	DESCRIPTION
		"Actual Curent on Power Channel."
	-- 1.3.6.1.4.1.28507.97.1.5.1.2.1.5
	::= { epc8314PowerEntry 5 }


epc8314Voltage OBJECT-TYPE
	SYNTAX  Unsigned32
	UNITS	"V"
	MAX-ACCESS read-only
	STATUS  current
	DESCRIPTION
		"Actual Voltage on Power Channel"
	-- 1.3.6.1.4.1.28507.97.1.5.1.2.1.6
	::= { epc8314PowerEntry 6 }


epc8314Frequency OBJECT-TYPE
	SYNTAX  Unsigned32
	UNITS	"0.01 hz"
	MAX-ACCESS read-only
	STATUS  current
	DESCRIPTION
		"Frequency of Power Channel"
	-- 1.3.6.1.4.1.28507.97.1.5.1.2.1.7
	::= { epc8314PowerEntry 7 }


epc8314PowerFactor OBJECT-TYPE
	SYNTAX  Integer32
	UNITS	"0.001"
	MAX-ACCESS read-only
	STATUS  current
	DESCRIPTION
		"Power Factor of Channel between
		-1.0 and 1.00"
	-- 1.3.6.1.4.1.28507.97.1.5.1.2.1.8
	::= { epc8314PowerEntry 8 }


epc8314Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.97.1.5.1.2.1.9
	::= { epc8314PowerEntry 9 }


epc8314PowerApparent OBJECT-TYPE
	SYNTAX  Integer32
	UNITS	"VA"
	MAX-ACCESS read-only
	STATUS  current
	DESCRIPTION
		"L Line Mean Apparent Power"
	-- 1.3.6.1.4.1.28507.97.1.5.1.2.1.10
	::= { epc8314PowerEntry 10 }


epc8314PowerReactive OBJECT-TYPE
	SYNTAX  Integer32
	UNITS	"VAR"
	MAX-ACCESS read-only
	STATUS  current
	DESCRIPTION
		"L Line Mean Reactive Power"
	-- 1.3.6.1.4.1.28507.97.1.5.1.2.1.11
	::= { epc8314PowerEntry 11 }


epc8314AbsEnergyReactive OBJECT-TYPE
	SYNTAX  Unsigned32
	UNITS	"VARh"
	MAX-ACCESS read-only
	STATUS  current
	DESCRIPTION
		"Absolute Reactive Energy counter."
	-- 1.3.6.1.4.1.28507.97.1.5.1.2.1.12
	::= { epc8314PowerEntry 12 }


epc8314AbsEnergyActiveResettable OBJECT-TYPE
	SYNTAX  Unsigned32
	UNITS	"Wh"
	MAX-ACCESS read-write
	STATUS  current
	DESCRIPTION
		"Resettable Absolute Active Energy counter.
		Writing '0' resets all resettable counter."
	-- 1.3.6.1.4.1.28507.97.1.5.1.2.1.13
	::= { epc8314PowerEntry 13 }


epc8314AbsEnergyReactiveResettable OBJECT-TYPE
	SYNTAX  Unsigned32
	UNITS	"VARh"
	MAX-ACCESS read-only
	STATUS  current
	DESCRIPTION
		"Resettable Absolute Reactive Energy counter."
	-- 1.3.6.1.4.1.28507.97.1.5.1.2.1.14
	::= { epc8314PowerEntry 14 }


epc8314ResetTime OBJECT-TYPE
	SYNTAX  Unsigned32
	UNITS	"s"
	MAX-ACCESS read-only
	STATUS  current
	DESCRIPTION
		"Time in seconds since last Energy
		Counter reset."
	-- 1.3.6.1.4.1.28507.97.1.5.1.2.1.15
	::= { epc8314PowerEntry 15 }


epc8314ForwEnergyActive OBJECT-TYPE
	SYNTAX  Unsigned32
	UNITS	"Wh"
	MAX-ACCESS read-only
	STATUS  current
	DESCRIPTION
		"Forward Active Energy counter."
	-- 1.3.6.1.4.1.28507.97.1.5.1.2.1.16
	::= { epc8314PowerEntry 16 }


epc8314ForwEnergyReactive OBJECT-TYPE
	SYNTAX  Unsigned32
	UNITS	"VARh"
	MAX-ACCESS read-only
	STATUS  current
	DESCRIPTION
		"Forward Reactive Energy counter."
	-- 1.3.6.1.4.1.28507.97.1.5.1.2.1.17
	::= { epc8314PowerEntry 17 }


epc8314ForwEnergyActiveResettable OBJECT-TYPE
	SYNTAX  Unsigned32
	UNITS	"Wh"
	MAX-ACCESS read-only
	STATUS  current
	DESCRIPTION
		"Resettable Forward Active Energy counter."
	-- 1.3.6.1.4.1.28507.97.1.5.1.2.1.18
	::= { epc8314PowerEntry 18 }


epc8314ForwEnergyReactiveResettable OBJECT-TYPE
	SYNTAX  Unsigned32
	UNITS	"VARh"
	MAX-ACCESS read-only
	STATUS  current
	DESCRIPTION
		"Resettable Forward Reactive Energy counter."
	-- 1.3.6.1.4.1.28507.97.1.5.1.2.1.19
	::= { epc8314PowerEntry 19 }


epc8314RevEnergyActive OBJECT-TYPE
	SYNTAX  Unsigned32
	UNITS	"Wh"
	MAX-ACCESS read-only
	STATUS  current
	DESCRIPTION
		"Reverse Active Energy counter."
	-- 1.3.6.1.4.1.28507.97.1.5.1.2.1.20
	::= { epc8314PowerEntry 20 }


epc8314RevEnergyReactive OBJECT-TYPE
	SYNTAX  Unsigned32
	UNITS	"VARh"
	MAX-ACCESS read-only
	STATUS  current
	DESCRIPTION
		"Reverse Reactive Energy counter."
	-- 1.3.6.1.4.1.28507.97.1.5.1.2.1.21
	::= { epc8314PowerEntry 21 }


epc8314RevEnergyActiveResettable OBJECT-TYPE
	SYNTAX  Unsigned32
	UNITS	"Wh"
	MAX-ACCESS read-only
	STATUS  current
	DESCRIPTION
		"Resettable Reverse Active Energy counter."
	-- 1.3.6.1.4.1.28507.97.1.5.1.2.1.22
	::= { epc8314PowerEntry 22 }


epc8314RevEnergyReactiveResettable OBJECT-TYPE
	SYNTAX  Unsigned32
	UNITS	"VARh"
	MAX-ACCESS read-only
	STATUS  current
	DESCRIPTION
		"Resettable Reverse Reactive Energy counter."
	-- 1.3.6.1.4.1.28507.97.1.5.1.2.1.23
	::= { epc8314PowerEntry 23 }


epc8314ExtSensors OBJECT IDENTIFIER 
	-- 1.3.6.1.4.1.28507.97.1.6
	::= { epc8314Objects 6 }

epc8314SensorTable OBJECT-TYPE
	SYNTAX  SEQUENCE OF Epc8314SensorEntry
	MAX-ACCESS not-accessible
	STATUS  current
	DESCRIPTION ""
	-- 1.3.6.1.4.1.28507.97.1.6.1
	::= { epc8314ExtSensors 1 }


epc8314SensorEntry OBJECT-TYPE
	SYNTAX  Epc8314SensorEntry
	MAX-ACCESS not-accessible
	STATUS  current
	DESCRIPTION ""
	INDEX {
		epc8314SensorIndex }
	-- 1.3.6.1.4.1.28507.97.1.6.1.1
	::= { epc8314SensorTable 1 }


Epc8314SensorEntry ::= SEQUENCE {

	epc8314SensorIndex   Integer32,
	epc8314TempSensor    Integer32,
	epc8314HygroSensor   Integer32,
	epc8314InputSensor   INTEGER,
	epc8314AirPressure   Integer32,
	epc8314DewPoint      Integer32,
	epc8314DewPointDiff  Integer32,
	epc8314ExtSensorName OCTET STRING }


epc8314SensorIndex OBJECT-TYPE
	SYNTAX  Integer32 (1..2)
	MAX-ACCESS read-only
	STATUS  current
	DESCRIPTION ""
	-- 1.3.6.1.4.1.28507.97.1.6.1.1.1
	::= { epc8314SensorEntry 1 }


epc8314TempSensor OBJECT-TYPE
	SYNTAX  Integer32
	MAX-ACCESS read-only
	STATUS  current
	DESCRIPTION
		"actual temperature"
	-- 1.3.6.1.4.1.28507.97.1.6.1.1.2
	::= { epc8314SensorEntry 2 }


epc8314HygroSensor OBJECT-TYPE
	SYNTAX  Integer32
	UNITS	"0.1 percent humidity"
	MAX-ACCESS read-only
	STATUS  current
	DESCRIPTION
		"actual humidity"
	-- 1.3.6.1.4.1.28507.97.1.6.1.1.3
	::= { epc8314SensorEntry 3 }


epc8314InputSensor OBJECT-TYPE
	SYNTAX  INTEGER {
			off(0),
			on(1) }
	MAX-ACCESS read-only
	STATUS  current
	DESCRIPTION
		"logical state of input sensor"
	-- 1.3.6.1.4.1.28507.97.1.6.1.1.4
	::= { epc8314SensorEntry 4 }


-- Conformance
--

epc8314Conf OBJECT IDENTIFIER 
	-- 1.3.6.1.4.1.28507.97.2
	::= { gadsEPC8314 2 }

-- Groups
--

epc8314Groups OBJECT IDENTIFIER 
	-- 1.3.6.1.4.1.28507.97.2.1
	::= { epc8314Conf 1 }

-- Compliance
--

epc8314Compls OBJECT IDENTIFIER 
	-- 1.3.6.1.4.1.28507.97.2.2
	::= { epc8314Conf 2 }

epc8314BasicGroup OBJECT-GROUP
	OBJECTS {
		epc8314TrapCtrl,
		epc8314TrapIPIndex,
		epc8314TrapAddr,
		epc8314portNumber,
		epc8314PortIndex,
		epc8314PortName,
		epc8314PortState,
		epc8314PortSwitchCount,
		epc8314PortStartupMode,
		epc8314PortStartupDelay,
		epc8314PortRepowerTime,
		epc8314ActivePowerChan,
		epc8314PowerIndex,
		epc8314ChanStatus,
		epc8314AbsEnergyActive,
		epc8314PowerActive,
		epc8314Current,
		epc8314Voltage,
		epc8314Frequency,
		epc8314PowerFactor,
		epc8314Pangle,
		epc8314PowerApparent,
		epc8314PowerReactive,
		epc8314AbsEnergyReactive,
		epc8314AbsEnergyActiveResettable,
		epc8314AbsEnergyReactiveResettable,
		epc8314ResetTime,
		epc8314ForwEnergyActive,
		epc8314ForwEnergyReactive,
		epc8314ForwEnergyActiveResettable,
		epc8314ForwEnergyReactiveResettable,
		epc8314RevEnergyActive,
		epc8314RevEnergyReactive,
		epc8314RevEnergyActiveResettable,
		epc8314RevEnergyReactiveResettable,
		epc8314SensorIndex,
		epc8314TempSensor,
		epc8314HygroSensor,
		epc8314InputSensor,
		epc8314AirPressure,
		epc8314DewPoint,
		epc8314DewPointDiff,
		epc8314LineSensorName,
		epc8314ExtSensorName,
		epc8314PortResetDuration,
		epc8314NTPTimeValid,
		epc8314NTPUnixTime,
		epc8314NTPLastValidTimestamp,
		epc8314ExtActiveInputs,
		epc8314ExtInputIndex,
		epc8314ExtInput,
		epc8314ExtInputName,
		epc8314ExtInputPortNum,
		epc8314ExtInputBlockIndex,
		epc8314ExtInputToggleCount,
		epc8314ProdName,
		epc8314FWVersion,
		epc8314HostName,
		epc8314PhysAddress,
		epc8314SerialNumber }
	STATUS  current
	DESCRIPTION
		"Basic objects."
	-- 1.3.6.1.4.1.28507.97.2.1.1
	::= { epc8314Groups 1 }

epc8314NotificationGroup NOTIFICATION-GROUP
	NOTIFICATIONS {
		epc8314SwitchEvtPort,
		epc8314TempEvtSen,
		epc8314HygroEvtSen,
		epc8314InputEvtSen,
		epc8314AirPressureEvtSen,
		epc8314DewPtDiffEvtSen,
		epc8314LineAmperageEvt,
		epc8314ExtInputEvt,
		epc8314LineVoltageEvt,
		epc8314LinePowerEvt }
	STATUS  current
	DESCRIPTION ""
	-- 1.3.6.1.4.1.28507.97.2.1.2
	::= { epc8314Groups 2 }

epc8314AirPressure OBJECT-TYPE
	SYNTAX  Integer32
	MAX-ACCESS read-only
	STATUS  current
	DESCRIPTION
		"actual air pressure"
	-- 1.3.6.1.4.1.28507.97.1.6.1.1.5
	::= { epc8314SensorEntry 5 }


epc8314DewPoint OBJECT-TYPE
	SYNTAX  Integer32
	MAX-ACCESS read-only
	STATUS  current
	DESCRIPTION
		"dew point for actual temperature and humidity"
	-- 1.3.6.1.4.1.28507.97.1.6.1.1.6
	::= { epc8314SensorEntry 6 }


epc8314DewPointDiff OBJECT-TYPE
	SYNTAX  Integer32
	MAX-ACCESS read-only
	STATUS  current
	DESCRIPTION
		"difference between dew point and actual
		temperature (Temp - DewPoint)"
	-- 1.3.6.1.4.1.28507.97.1.6.1.1.7
	::= { epc8314SensorEntry 7 }



epc8314SwitchEvtPort NOTIFICATION-TYPE
	OBJECTS {
		epc8314PortIndex,
		epc8314PortName,
		epc8314PortState,
		epc8314PortSwitchCount}
	STATUS  current
	DESCRIPTION
		"Event is triggered when a port is switched"
	-- 1.3.6.1.4.1.28507.97.3.1
	::= { events 1 }


epc8314TempEvtSen NOTIFICATION-TYPE
	OBJECTS {
		epc8314SensorIndex,
		epc8314TempSensor}
	STATUS  current
	DESCRIPTION
		"temperature limits exceeded"
	-- 1.3.6.1.4.1.28507.97.3.2
	::= { events 2 }


epc8314HygroEvtSen NOTIFICATION-TYPE
	OBJECTS {
		epc8314SensorIndex,
		epc8314HygroSensor}
	STATUS  current
	DESCRIPTION
		"hygro limits exceeded"
	-- 1.3.6.1.4.1.28507.97.3.3
	::= { events 3 }


epc8314InputEvtSen NOTIFICATION-TYPE
	OBJECTS {
		epc8314SensorIndex,
		epc8314InputSensor}
	STATUS  current
	DESCRIPTION
		"change of logical input sensor state"
	-- 1.3.6.1.4.1.28507.97.3.4
	::= { events 4 }


epc8314AirPressureEvtSen NOTIFICATION-TYPE
	OBJECTS {
		epc8314SensorIndex,
		epc8314AirPressure}
	STATUS  current
	DESCRIPTION
		"Air Pressure limits exceeded

		"
	-- 1.3.6.1.4.1.28507.97.3.5
	::= { events 5 }


epc8314DewPtDiffEvtSen NOTIFICATION-TYPE
	OBJECTS {
		epc8314SensorIndex,
		epc8314DewPointDiff}
	STATUS  current
	DESCRIPTION
		"Dew Point Difference limits exceeded"
	-- 1.3.6.1.4.1.28507.97.3.6
	::= { events 6 }


epc8314LineAmperageEvt NOTIFICATION-TYPE
	OBJECTS {
		epc8314PowerIndex,
		epc8314PowerActive,
		epc8314Current,
		epc8314Voltage,
		epc8314Frequency,
		epc8314PowerApparent,
		epc8314PowerReactive}
	STATUS  current
	DESCRIPTION
		"Event is triggered when a measured
		current is crossing the entered limits"
	-- 1.3.6.1.4.1.28507.97.3.7
	::= { events 7 }


epc8314ExtInputEvt NOTIFICATION-TYPE
	OBJECTS {
		epc8314ExtInputIndex,
		epc8314ExtInput,
		epc8314ExtInputName,
		epc8314ExtInputPortNum,
		epc8314ExtInputBlockIndex}
	STATUS  current
	DESCRIPTION
		"Change of external sensor input."
	-- 1.3.6.1.4.1.28507.97.3.8
	-- 1.3.6.1.4.1.28507.97.3.25
::= { events 25 }


epc8314LineVoltageEvt NOTIFICATION-TYPE
	OBJECTS {
		epc8314PowerIndex,
		epc8314PowerActive,
		epc8314Current,
		epc8314Voltage,
		epc8314Frequency,
		epc8314PowerApparent,
		epc8314PowerReactive}
	STATUS  current
	DESCRIPTION
		"Event is triggered when a measured
		voltage is crossing the entered limits"
	-- 1.3.6.1.4.1.28507.97.3.26
	::= { events 26 }


epc8314LinePowerEvt NOTIFICATION-TYPE
	OBJECTS {
		epc8314PowerIndex,
		epc8314PowerActive,
		epc8314Current,
		epc8314Voltage,
		epc8314Frequency,
		epc8314PowerApparent,
		epc8314PowerReactive}
	STATUS  current
	DESCRIPTION
		"Event is triggered when a measured
		power is crossing the entered limits"
	-- 1.3.6.1.4.1.28507.97.3.27
	::= { events 27 }

END
