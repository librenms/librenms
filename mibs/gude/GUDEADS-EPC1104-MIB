GUDEADS-EPC1104-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "202409250745Z"	-- Sep 25, 2024, 7:45:00 AM
	ORGANIZATION "GUDE Systems GmbH"
	CONTACT-INFO
		"Von-der-Wettern-Str. 23
		51149 Cologne
		Germany
		https://www.gude-systems.com"
	DESCRIPTION
		"Expert Power Control 1104 MIB"
	-- 1.3.6.1.4.1.28507
	::= { enterprises 28507 }


epc1104DeviceInfo OBJECT IDENTIFIER 
	-- 1.3.6.1.4.1.28507.68.1.1.2
	::= { epc1104CommonConfig 2 }

epc1104ProdName OBJECT-TYPE
	SYNTAX  OCTET STRING
	MAX-ACCESS read-only
	STATUS  current
	DESCRIPTION
		"The Product Name of the device."
	-- 1.3.6.1.4.1.28507.68.1.1.2.1
	::= { epc1104DeviceInfo 1 }


epc1104FWVersion OBJECT-TYPE
	SYNTAX  OCTET STRING
	MAX-ACCESS read-only
	STATUS  current
	DESCRIPTION
		"Firmware Version of the device."
	-- 1.3.6.1.4.1.28507.68.1.1.2.2
	::= { epc1104DeviceInfo 2 }


epc1104HostName OBJECT-TYPE
	SYNTAX  OCTET STRING
	MAX-ACCESS read-only
	STATUS  current
	DESCRIPTION
		"The configured Host Name."
	-- 1.3.6.1.4.1.28507.68.1.1.2.3
	::= { epc1104DeviceInfo 3 }


epc1104PhysAddress OBJECT-TYPE
	SYNTAX  OCTET STRING
	MAX-ACCESS read-only
	STATUS  current
	DESCRIPTION
		"The MAC address of the device."
	-- 1.3.6.1.4.1.28507.68.1.1.2.4
	::= { epc1104DeviceInfo 4 }


epc1104SerialNumber OBJECT-TYPE
	SYNTAX  Unsigned32
	MAX-ACCESS read-only
	STATUS  current
	DESCRIPTION
		"The Serial Number of the device. Not available for all devices. Production start 2026."
	-- 1.3.6.1.4.1.28507.68.1.1.2.5
	::= { epc1104DeviceInfo 5 }


epc1104ExtInputToggleCount OBJECT-TYPE
	SYNTAX  Unsigned32
	MAX-ACCESS read-only
	STATUS  current
	DESCRIPTION
		"Number of times the Input has changed its state."
	-- 1.3.6.1.4.1.28507.68.1.6.2.2.1.3
	::= { epc1104ExtInputEntry 3 }


epc1104ExtInputs OBJECT IDENTIFIER 
	-- 1.3.6.1.4.1.28507.68.1.6.2
	::= { epc1104ExtSensors 2 }

epc1104ExtInputEntry OBJECT-TYPE
	SYNTAX  Epc1104ExtInputEntry
	MAX-ACCESS not-accessible
	STATUS  current
	DESCRIPTION ""
	INDEX {
		epc1104ExtInputIndex }
	-- 1.3.6.1.4.1.28507.68.1.6.2.2.1
	::= { epc1104ExtInputTable 1 }


Epc1104ExtInputEntry ::= SEQUENCE {

	epc1104ExtInputIndex       Unsigned32,
	epc1104ExtInput            INTEGER,
	epc1104ExtInputToggleCount Unsigned32,
	epc1104ExtInputName        OCTET STRING,
	epc1104ExtInputPortNum     Integer32,
	epc1104ExtInputBlockIndex  Integer32 }


epc1104ExtInput OBJECT-TYPE
	SYNTAX  INTEGER {
			lo(0),
			hi(1) }
	MAX-ACCESS read-only
	STATUS  current
	DESCRIPTION
		"Input state of device"
	-- 1.3.6.1.4.1.28507.68.1.6.2.2.1.2
	::= { epc1104ExtInputEntry 2 }


epc1104ExtActiveInputs OBJECT-TYPE
	SYNTAX  Unsigned32 (1..12)
	MAX-ACCESS read-only
	STATUS  current
	DESCRIPTION
		"Number of suppported Input Channels."
	-- 1.3.6.1.4.1.28507.68.1.6.2.1
	::= { epc1104ExtInputs 1 }


epc1104ExtInputTable OBJECT-TYPE
	SYNTAX  SEQUENCE OF Epc1104ExtInputEntry
	MAX-ACCESS not-accessible
	STATUS  current
	DESCRIPTION ""
	-- 1.3.6.1.4.1.28507.68.1.6.2.2
	::= { epc1104ExtInputs 2 }


epc1104ExtInputIndex OBJECT-TYPE
	SYNTAX  Unsigned32
	MAX-ACCESS read-only
	STATUS  current
	DESCRIPTION ""
	-- 1.3.6.1.4.1.28507.68.1.6.2.2.1.1
	::= { epc1104ExtInputEntry 1 }


epc1104ExtInputName OBJECT-TYPE
	SYNTAX  OCTET STRING (SIZE (0..32))
	MAX-ACCESS read-write
	STATUS  current
	DESCRIPTION
		"A textual string containing name of
		the Input"
	-- 1.3.6.1.4.1.28507.68.1.6.2.2.1.32
	::= { epc1104ExtInputEntry 32 }


epc1104ExtInputPortNum OBJECT-TYPE
	SYNTAX  Integer32
	MAX-ACCESS read-only
	STATUS  current
	DESCRIPTION
		"Number of external Sensor Port when value greater zero, else device built-in Input."
	-- 1.3.6.1.4.1.28507.68.1.6.2.2.1.33
	::= { epc1104ExtInputEntry 33 }


epc1104ExtInputBlockIndex OBJECT-TYPE
	SYNTAX  Integer32
	MAX-ACCESS read-only
	STATUS  current
	DESCRIPTION
		"Either index of device built-in Input, or index of Input in external sensor."
	-- 1.3.6.1.4.1.28507.68.1.6.2.2.1.34
	::= { epc1104ExtInputEntry 34 }


epc1104NTPClient OBJECT IDENTIFIER 
	-- 1.3.6.1.4.1.28507.68.1.5.15
	::= { epc1104IntSensors 15 }

epc1104NTPUnixTime OBJECT-TYPE
	SYNTAX  Unsigned32
	UNITS	"s"
	MAX-ACCESS read-only
	STATUS  current
	DESCRIPTION
		"show received NTP time as unixtime (secs since 1 January 1970)"
	-- 1.3.6.1.4.1.28507.68.1.5.15.2
	::= { epc1104NTPClient 2 }


epc1104NTPLastValidTimestamp OBJECT-TYPE
	SYNTAX  Unsigned32
	UNITS	"s"
	MAX-ACCESS read-only
	STATUS  current
	DESCRIPTION
		"show seconds since last valid NTP timestamp received"
	-- 1.3.6.1.4.1.28507.68.1.5.15.3
	::= { epc1104NTPClient 3 }


epc1104NTPTimeValid OBJECT-TYPE
	SYNTAX  INTEGER {
			notime(0),
			valid(1) }
	MAX-ACCESS read-only
	STATUS  current
	DESCRIPTION
		"Show if valid Time is received"
	-- 1.3.6.1.4.1.28507.68.1.5.15.1
	::= { epc1104NTPClient 1 }


epc1104PortResetDuration OBJECT-TYPE
	SYNTAX  Integer32 (0..65535)
	UNITS	"seconds"
	MAX-ACCESS read-write
	STATUS  current
	DESCRIPTION
		"Delay in sec for turning Port on again after Reset action"
	DEFVAL { 0 }
	-- 1.3.6.1.4.1.28507.68.1.3.1.2.1.8
	::= { epc1104portEntry 8 }


epc1104ExtSensorName OBJECT-TYPE
	SYNTAX  OCTET STRING (SIZE (0..32))
	MAX-ACCESS read-write
	STATUS  current
	DESCRIPTION
		"A textual string containing name of a
		external Sensor"
	-- 1.3.6.1.4.1.28507.68.1.6.1.1.32
	::= { epc1104SensorEntry 32 }


gadsEPC1104 OBJECT IDENTIFIER 
	-- 1.3.6.1.4.1.28507.68
	::= { gudeads 68 }

-- Scalars and Tables
--

epc1104Objects OBJECT IDENTIFIER 
	-- 1.3.6.1.4.1.28507.68.1
	::= { gadsEPC1104 1 }

epc1104CommonConfig OBJECT IDENTIFIER 
	-- 1.3.6.1.4.1.28507.68.1.1
	::= { epc1104Objects 1 }

epc1104SNMPaccess OBJECT IDENTIFIER 
	-- 1.3.6.1.4.1.28507.68.1.1.1
	::= { epc1104CommonConfig 1 }

epc1104TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.68.1.1.1.1
	::= { epc1104SNMPaccess 1 }


epc1104TrapIPTable OBJECT-TYPE
	SYNTAX  SEQUENCE OF Epc8TrapIPEntry
	MAX-ACCESS not-accessible
	STATUS  current
	DESCRIPTION
		"list of all Trap receiver"
	-- 1.3.6.1.4.1.28507.68.1.1.1.2
	::= { epc1104SNMPaccess 2 }


epc1104TrapIPEntry OBJECT-TYPE
	SYNTAX  Epc8TrapIPEntry
	MAX-ACCESS not-accessible
	STATUS  current
	DESCRIPTION
		"an entry containing management
		informations regarding the list of trap
		receivers"
	INDEX {
		epc1104TrapIPIndex }
	-- 1.3.6.1.4.1.28507.68.1.1.1.2.1
	::= { epc1104TrapIPTable 1 }


Epc8TrapIPEntry ::= SEQUENCE {

	epc1104TrapIPIndex Integer32,
	epc1104TrapAddr    OCTET STRING }


epc1104TrapIPIndex OBJECT-TYPE
	SYNTAX  Integer32 (1..8)
	MAX-ACCESS read-only
	STATUS  current
	DESCRIPTION
		"A unique value, greater than zero, for each receiver slot."
	-- 1.3.6.1.4.1.28507.68.1.1.1.2.1.1
	::= { epc1104TrapIPEntry 1 }


epc1104TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.68.1.1.1.2.1.2
	::= { epc1104TrapIPEntry 2 }


epc1104DeviceConfig OBJECT IDENTIFIER 
	-- 1.3.6.1.4.1.28507.68.1.2
	::= { epc1104Objects 2 }

epc1104IntActors OBJECT IDENTIFIER 
	-- 1.3.6.1.4.1.28507.68.1.3
	::= { epc1104Objects 3 }

epc1104relayports OBJECT IDENTIFIER 
	-- 1.3.6.1.4.1.28507.68.1.3.1
	::= { epc1104IntActors 1 }

epc1104portNumber OBJECT-TYPE
	SYNTAX  Integer32 (1)
	MAX-ACCESS read-only
	STATUS  current
	DESCRIPTION
		"The number of Relay Ports"
	-- 1.3.6.1.4.1.28507.68.1.3.1.1
	::= { epc1104relayports 1 }


-- the Interfaces table
-- The Interfaces table contains information on the entity's
-- interfaces.  Each sub-layer below the internetwork-layer
-- of a network interface is considered to be an interface.

epc1104portTable OBJECT-TYPE
	SYNTAX  SEQUENCE OF Epc1104portEntry
	MAX-ACCESS not-accessible
	STATUS  current
	DESCRIPTION
		"list of all EPC Relay Ports"
	-- 1.3.6.1.4.1.28507.68.1.3.1.2
	::= { epc1104relayports 2 }


epc1104portEntry OBJECT-TYPE
	SYNTAX  Epc1104portEntry
	MAX-ACCESS not-accessible
	STATUS  current
	DESCRIPTION
		"An entry containing management information applicable to a
		particular relay port."
	INDEX {
		epc1104PortIndex }
	-- 1.3.6.1.4.1.28507.68.1.3.1.2.1
	::= { epc1104portTable 1 }


Epc1104portEntry ::= SEQUENCE {

	epc1104PortIndex         Integer32,
	epc1104PortName          OCTET STRING,
	epc1104PortState         INTEGER,
	epc1104PortSwitchCount   Integer32,
	epc1104PortStartupMode   INTEGER,
	epc1104PortStartupDelay  Integer32,
	epc1104PortRepowerTime   Integer32,
	epc1104PortResetDuration Integer32 }


epc1104PortIndex OBJECT-TYPE
	SYNTAX  Integer32 (1)
	MAX-ACCESS read-only
	STATUS  current
	DESCRIPTION
		"A unique value, greater than zero, for each Relay Port."
	-- 1.3.6.1.4.1.28507.68.1.3.1.2.1.1
	::= { epc1104portEntry 1 }


epc1104PortName OBJECT-TYPE
	SYNTAX  OCTET STRING (SIZE (0..15))
	MAX-ACCESS read-write
	STATUS  current
	DESCRIPTION
		"A textual string containing name of a Relay Port."
	-- 1.3.6.1.4.1.28507.68.1.3.1.2.1.2
	::= { epc1104portEntry 2 }


epc1104PortState OBJECT-TYPE
	SYNTAX  INTEGER {
			off(0),
			on(1) }
	MAX-ACCESS read-write
	STATUS  current
	DESCRIPTION
		"current state a Relay Port"
	-- 1.3.6.1.4.1.28507.68.1.3.1.2.1.3
	::= { epc1104portEntry 3 }


epc1104PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.68.1.3.1.2.1.4
	::= { epc1104portEntry 4 }


epc1104PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.68.1.3.1.2.1.5
	::= { epc1104portEntry 5 }


epc1104PortStartupDelay OBJECT-TYPE
	SYNTAX  Integer32
	UNITS	"seconds"
	MAX-ACCESS read-write
	STATUS  current
	DESCRIPTION
		"Delay in sec for startup action"
	DEFVAL { 0 }
	-- 1.3.6.1.4.1.28507.68.1.3.1.2.1.6
	::= { epc1104portEntry 6 }


epc1104PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.68.1.3.1.2.1.7
	::= { epc1104portEntry 7 }


epc1104ExtActors OBJECT IDENTIFIER 
	-- 1.3.6.1.4.1.28507.68.1.4
	::= { epc1104Objects 4 }

epc1104IntSensors OBJECT IDENTIFIER 
	-- 1.3.6.1.4.1.28507.68.1.5
	::= { epc1104Objects 5 }

epc1104ExtSensors OBJECT IDENTIFIER 
	-- 1.3.6.1.4.1.28507.68.1.6
	::= { epc1104Objects 6 }

-- Conformance
--

epc1104Conf OBJECT IDENTIFIER 
	-- 1.3.6.1.4.1.28507.68.2
	::= { gadsEPC1104 2 }

-- Groups
--

epc1104Groups OBJECT IDENTIFIER 
	-- 1.3.6.1.4.1.28507.68.2.1
	::= { epc1104Conf 1 }

-- Compliance
--

epc1104Compls OBJECT IDENTIFIER 
	-- 1.3.6.1.4.1.28507.68.2.2
	::= { epc1104Conf 2 }

epc1104BasicGroup OBJECT-GROUP
	OBJECTS {
		epc1104TrapCtrl,
		epc1104TrapIPIndex,
		epc1104TrapAddr,
		epc1104portNumber,
		epc1104PortIndex,
		epc1104PortName,
		epc1104PortState,
		epc1104PortSwitchCount,
		epc1104PortStartupMode,
		epc1104PortStartupDelay,
		epc1104PortRepowerTime,
		epc1104SensorIndex,
		epc1104TempSensor,
		epc1104HygroSensor,
		epc1104InputSensor,
		epc1104AirPressure,
		epc1104DewPoint,
		epc1104DewPointDiff,
		epc1104ExtSensorName,
		epc1104PortResetDuration,
		epc1104NTPTimeValid,
		epc1104NTPUnixTime,
		epc1104NTPLastValidTimestamp,
		epc1104ExtActiveInputs,
		epc1104ExtInputIndex,
		epc1104ExtInput,
		epc1104ExtInputName,
		epc1104ExtInputPortNum,
		epc1104ExtInputBlockIndex,
		epc1104ExtInputToggleCount,
		epc1104ProdName,
		epc1104FWVersion,
		epc1104HostName,
		epc1104PhysAddress,
		epc1104SerialNumber }
	STATUS  current
	DESCRIPTION
		"Basic objects."
	-- 1.3.6.1.4.1.28507.68.2.1.1
	::= { epc1104Groups 1 }

epc1104NotificationGroup NOTIFICATION-GROUP
	NOTIFICATIONS {
		epc1104SwitchEvtPort,
		epc1104TempEvtSen,
		epc1104HygroEvtSen,
		epc1104InputEvtSen,
		epc1104AirPressureEvtSen,
		epc1104DewPtDiffEvtSen,
		epc1104ExtInputEvt }
	STATUS  current
	DESCRIPTION ""
	-- 1.3.6.1.4.1.28507.68.2.1.2
	::= { epc1104Groups 2 }

-- Notification Types
--

events OBJECT IDENTIFIER 
	-- 1.3.6.1.4.1.28507.68.3
	::= { gadsEPC1104 3 }

epc1104SensorTable OBJECT-TYPE
	SYNTAX  SEQUENCE OF Epc1104SensorEntry
	MAX-ACCESS not-accessible
	STATUS  current
	DESCRIPTION ""
	-- 1.3.6.1.4.1.28507.68.1.6.1
	::= { epc1104ExtSensors 1 }


epc1104SensorEntry OBJECT-TYPE
	SYNTAX  Epc1104SensorEntry
	MAX-ACCESS not-accessible
	STATUS  current
	DESCRIPTION ""
	INDEX {
		epc1104SensorIndex }
	-- 1.3.6.1.4.1.28507.68.1.6.1.1
	::= { epc1104SensorTable 1 }


Epc1104SensorEntry ::= SEQUENCE {

	epc1104SensorIndex   Integer32,
	epc1104TempSensor    Integer32,
	epc1104HygroSensor   Integer32,
	epc1104InputSensor   INTEGER,
	epc1104AirPressure   Integer32,
	epc1104DewPoint      Integer32,
	epc1104DewPointDiff  Integer32,
	epc1104ExtSensorName OCTET STRING }


epc1104SensorIndex OBJECT-TYPE
	SYNTAX  Integer32 (1)
	MAX-ACCESS read-only
	STATUS  current
	DESCRIPTION ""
	-- 1.3.6.1.4.1.28507.68.1.6.1.1.1
	::= { epc1104SensorEntry 1 }


epc1104TempSensor OBJECT-TYPE
	SYNTAX  Integer32
	MAX-ACCESS read-only
	STATUS  current
	DESCRIPTION
		"actual temperature"
	-- 1.3.6.1.4.1.28507.68.1.6.1.1.2
	::= { epc1104SensorEntry 2 }


epc1104HygroSensor OBJECT-TYPE
	SYNTAX  Integer32
	UNITS	"0.1 percent humidity"
	MAX-ACCESS read-only
	STATUS  current
	DESCRIPTION
		"actual humidity"
	-- 1.3.6.1.4.1.28507.68.1.6.1.1.3
	::= { epc1104SensorEntry 3 }


epc1104InputSensor OBJECT-TYPE
	SYNTAX  INTEGER {
			off(0),
			on(1) }
	MAX-ACCESS read-only
	STATUS  current
	DESCRIPTION
		"logical state of input sensor"
	-- 1.3.6.1.4.1.28507.68.1.6.1.1.4
	::= { epc1104SensorEntry 4 }



epc1104SwitchEvtPort NOTIFICATION-TYPE
	OBJECTS {
		epc1104PortIndex,
		epc1104PortName,
		epc1104PortState,
		epc1104PortSwitchCount}
	STATUS  current
	DESCRIPTION
		"Event is triggered when a port is switched"
	-- 1.3.6.1.4.1.28507.68.3.1
	::= { events 1 }


epc1104TempEvtSen NOTIFICATION-TYPE
	OBJECTS {
		epc1104SensorIndex,
		epc1104TempSensor}
	STATUS  current
	DESCRIPTION
		"temperature limits exceeded"
	-- 1.3.6.1.4.1.28507.68.3.2
	::= { events 2 }


epc1104InputEvtSen NOTIFICATION-TYPE
	OBJECTS {
		epc1104SensorIndex,
		epc1104InputSensor}
	STATUS  current
	DESCRIPTION
		"change of logical input sensor state"
	-- 1.3.6.1.4.1.28507.68.3.4
	::= { events 4 }


epc1104AirPressureEvtSen NOTIFICATION-TYPE
	OBJECTS {
		epc1104SensorIndex,
		epc1104AirPressure}
	STATUS  current
	DESCRIPTION
		"Air Pressure limits exceeded"
	-- 1.3.6.1.4.1.28507.68.3.5
	::= { events 5 }


epc1104DewPtDiffEvtSen NOTIFICATION-TYPE
	OBJECTS {
		epc1104SensorIndex,
		epc1104DewPointDiff}
	STATUS  current
	DESCRIPTION
		"Dew Point Difference limits exceeded"
	-- 1.3.6.1.4.1.28507.68.3.6
	::= { events 6 }

epc1104AirPressure OBJECT-TYPE
	SYNTAX  Integer32
	MAX-ACCESS read-only
	STATUS  current
	DESCRIPTION
		"actual air pressure"
	-- 1.3.6.1.4.1.28507.68.1.6.1.1.5
	::= { epc1104SensorEntry 5 }


epc1104DewPoint OBJECT-TYPE
	SYNTAX  Integer32
	MAX-ACCESS read-only
	STATUS  current
	DESCRIPTION
		"dew point for actual temperature and humidity"
	-- 1.3.6.1.4.1.28507.68.1.6.1.1.6
	::= { epc1104SensorEntry 6 }


epc1104DewPointDiff OBJECT-TYPE
	SYNTAX  Integer32
	MAX-ACCESS read-only
	STATUS  current
	DESCRIPTION
		"difference between dew point and actual
		temperature (Temp - DewPoint)"
	-- 1.3.6.1.4.1.28507.68.1.6.1.1.7
	::= { epc1104SensorEntry 7 }



epc1104HygroEvtSen NOTIFICATION-TYPE
	OBJECTS {
		epc1104SensorIndex,
		epc1104HygroSensor}
	STATUS  current
	DESCRIPTION
		"hygro limits exceeded"
	-- 1.3.6.1.4.1.28507.43.3.4
	-- 1.3.6.1.4.1.28507.68.3.3
::= { events 3 }


epc1104ExtInputEvt NOTIFICATION-TYPE
	OBJECTS {
		epc1104ExtInputIndex,
		epc1104ExtInput,
		epc1104ExtInputToggleCount,
		epc1104ExtInputName,
		epc1104ExtInputPortNum,
		epc1104ExtInputBlockIndex}
	STATUS  current
	DESCRIPTION
		"Change of external sensor input."
	-- 1.3.6.1.4.1.28507.68.3.25
	::= { events 25 }

END
