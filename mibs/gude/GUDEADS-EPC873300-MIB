GUDEADS-EPC873300-MIB DEFINITIONS ::= BEGIN

IMPORTS
	enterprises,
	MODULE-IDENTITY,
	OBJECT-TYPE,
	NOTIFICATION-TYPE,
	Gauge32,
	Integer32,
	Unsigned32
		FROM SNMPv2-SMI
	OBJECT-GROUP,
	NOTIFICATION-GROUP
		FROM SNMPv2-CONF;

gudeads MODULE-IDENTITY
	LAST-UPDATED "202409261416Z"	-- Sep 26, 2024, 2:16:00 PM
	ORGANIZATION "GUDE Systems GmbH"
	CONTACT-INFO
		"Von-der-Wettern-Str. 23
		51149 Cologne
		Germany
		https://www.gude-systems.com"
	DESCRIPTION
		"Expert Power Control 873300 MIB"
	-- 1.3.6.1.4.1.28507
	::= { enterprises 28507 }


epc873300DeviceInfo OBJECT IDENTIFIER 
	-- 1.3.6.1.4.1.28507.111.1.1.2
	::= { epc873300CommonConfig 2 }

epc873300ProdName OBJECT-TYPE
	SYNTAX  OCTET STRING
	MAX-ACCESS read-only
	STATUS  current
	DESCRIPTION
		"The Product Name of the device."
	-- 1.3.6.1.4.1.28507.111.1.1.2.1
	::= { epc873300DeviceInfo 1 }


epc873300FWVersion OBJECT-TYPE
	SYNTAX  OCTET STRING
	MAX-ACCESS read-only
	STATUS  current
	DESCRIPTION
		"Firmware Version of the device."
	-- 1.3.6.1.4.1.28507.111.1.1.2.2
	::= { epc873300DeviceInfo 2 }


epc873300HostName OBJECT-TYPE
	SYNTAX  OCTET STRING
	MAX-ACCESS read-only
	STATUS  current
	DESCRIPTION
		"The configured Host Name."
	-- 1.3.6.1.4.1.28507.111.1.1.2.3
	::= { epc873300DeviceInfo 3 }


epc873300PhysAddress OBJECT-TYPE
	SYNTAX  OCTET STRING
	MAX-ACCESS read-only
	STATUS  current
	DESCRIPTION
		"The MAC address of the device."
	-- 1.3.6.1.4.1.28507.111.1.1.2.4
	::= { epc873300DeviceInfo 4 }


epc873300SerialNumber OBJECT-TYPE
	SYNTAX  Unsigned32
	MAX-ACCESS read-only
	STATUS  current
	DESCRIPTION
		"The Serial Number of the device. Not available for all devices. Production start 2026."
	-- 1.3.6.1.4.1.28507.111.1.1.2.5
	::= { epc873300DeviceInfo 5 }



epc873300PwrSupplyChangeEvt NOTIFICATION-TYPE
	OBJECTS {
		epc873300PwrSupplyIndex,
		epc873300PwrSupplyStatus}
	STATUS  current
	DESCRIPTION
		"Event is triggered when Power Supply state
		changes"
	-- 1.3.6.1.4.1.28507.111.3.17
	::= { events 17 }

epc873300PwrSupplyTable OBJECT-TYPE
	SYNTAX  SEQUENCE OF Epc873300PwrSupplyEntry
	MAX-ACCESS not-accessible
	STATUS  current
	DESCRIPTION
		"Overvoltage Protection Table
		This table may not be present
		on devices without OVP feature"
	-- 1.3.6.1.4.1.28507.111.1.5.13
	::= { epc873300IntSensors 13 }


epc873300PwrSupplyEntry OBJECT-TYPE
	SYNTAX  Epc873300PwrSupplyEntry
	MAX-ACCESS not-accessible
	STATUS  current
	DESCRIPTION ""
	INDEX {
		epc873300PwrSupplyIndex }
	-- 1.3.6.1.4.1.28507.111.1.5.13.1
	::= { epc873300PwrSupplyTable 1 }


Epc873300PwrSupplyEntry ::= SEQUENCE {

	epc873300PwrSupplyIndex  Integer32,
	epc873300PwrSupplyStatus INTEGER }


epc873300PwrSupplyIndex OBJECT-TYPE
	SYNTAX  Integer32 (1..2)
	MAX-ACCESS read-only
	STATUS  current
	DESCRIPTION
		"Index of Power Supply entries"
	-- 1.3.6.1.4.1.28507.111.1.5.13.1.1
	::= { epc873300PwrSupplyEntry 1 }


epc873300PwrSupplyStatus OBJECT-TYPE
	SYNTAX  INTEGER {
			up(1),
			down(0) }
	MAX-ACCESS read-only
	STATUS  current
	DESCRIPTION
		"shows the status of the
		Power Supply"
	-- 1.3.6.1.4.1.28507.111.1.5.13.1.2
	::= { epc873300PwrSupplyEntry 2 }



epc873300LineVoltageEvt NOTIFICATION-TYPE
	OBJECTS {
		epc873300PowerIndex,
		epc873300PowerActive,
		epc873300Current,
		epc873300Voltage,
		epc873300Frequency,
		epc873300PowerApparent,
		epc873300PowerReactive}
	STATUS  current
	DESCRIPTION
		"Event is triggered when a measured
		voltage is crossing the entered limits"
	-- 1.3.6.1.4.1.28507.111.3.26
	::= { events 26 }


epc873300LinePowerEvt NOTIFICATION-TYPE
	OBJECTS {
		epc873300PowerIndex,
		epc873300PowerActive,
		epc873300Current,
		epc873300Voltage,
		epc873300Frequency,
		epc873300PowerApparent,
		epc873300PowerReactive}
	STATUS  current
	DESCRIPTION
		"Event is triggered when a measured
		power is crossing the entered limits"
	-- 1.3.6.1.4.1.28507.111.3.27
	::= { events 27 }

epc873300NeutralCurrent OBJECT-TYPE
	SYNTAX  Unsigned32
	UNITS	"mA"
	MAX-ACCESS read-only
	STATUS  current
	DESCRIPTION
		"Actual Neutral Current"
	-- 1.3.6.1.4.1.28507.111.1.5.3.2.1.2
	::= { epc873300TotalEntry 2 }


epc873300TotalChan OBJECT IDENTIFIER 
	-- 1.3.6.1.4.1.28507.111.1.5.3
	::= { epc873300IntSensors 3 }

epc873300ActiveTotalChan OBJECT-TYPE
	SYNTAX  Unsigned32 (1)
	MAX-ACCESS read-only
	STATUS  current
	DESCRIPTION
		"Number of suppported Power Channels."
	-- 1.3.6.1.4.1.28507.111.1.5.3.1
	::= { epc873300TotalChan 1 }


epc873300TotalTable OBJECT-TYPE
	SYNTAX  SEQUENCE OF Epc873300TotalEntry
	MAX-ACCESS not-accessible
	STATUS  current
	DESCRIPTION
		"All available Channel Interfaces."
	-- 1.3.6.1.4.1.28507.111.1.5.3.2
	::= { epc873300TotalChan 2 }


epc873300TotalIndex OBJECT-TYPE
	SYNTAX  Integer32 (1..2)
	MAX-ACCESS read-only
	STATUS  current
	DESCRIPTION
		"Index of Power Channel entries"
	-- 1.3.6.1.4.1.28507.111.1.5.3.2.1.1
	::= { epc873300TotalEntry 1 }


epc873300TotalEntry OBJECT-TYPE
	SYNTAX  Epc873300TotalEntry
	MAX-ACCESS not-accessible
	STATUS  current
	DESCRIPTION
		"An entry containing management information
		applicable to a particular Total Channel."
	INDEX {
		epc873300TotalIndex }
	-- 1.3.6.1.4.1.28507.111.1.5.3.2.1
	::= { epc873300TotalTable 1 }


Epc873300TotalEntry ::= SEQUENCE {

	epc873300TotalIndex     Integer32,
	epc873300NeutralCurrent Unsigned32 }


epc873300ExtInputs OBJECT IDENTIFIER 
	-- 1.3.6.1.4.1.28507.111.1.6.2
	::= { epc873300ExtSensors 2 }

epc873300ExtInputEntry OBJECT-TYPE
	SYNTAX  Epc873300ExtInputEntry
	MAX-ACCESS not-accessible
	STATUS  current
	DESCRIPTION ""
	INDEX {
		epc873300ExtInputIndex }
	-- 1.3.6.1.4.1.28507.111.1.6.2.2.1
	::= { epc873300ExtInputTable 1 }


Epc873300ExtInputEntry ::= SEQUENCE {

	epc873300ExtInputIndex       Unsigned32,
	epc873300ExtInput            INTEGER,
	epc873300ExtInputToggleCount Integer32,
	epc873300ExtInputName        OCTET STRING,
	epc873300ExtInputPortNum     Integer32,
	epc873300ExtInputBlockIndex  Integer32 }


epc873300ExtInput OBJECT-TYPE
	SYNTAX  INTEGER {
			lo(0),
			hi(1) }
	MAX-ACCESS read-only
	STATUS  current
	DESCRIPTION
		"Input state of device"
	-- 1.3.6.1.4.1.28507.111.1.6.2.2.1.2
	::= { epc873300ExtInputEntry 2 }


epc873300ExtInputTable OBJECT-TYPE
	SYNTAX  SEQUENCE OF Epc873300ExtInputEntry
	MAX-ACCESS not-accessible
	STATUS  current
	DESCRIPTION ""
	-- 1.3.6.1.4.1.28507.111.1.6.2.2
	::= { epc873300ExtInputs 2 }


epc873300ExtInputIndex OBJECT-TYPE
	SYNTAX  Unsigned32
	MAX-ACCESS read-only
	STATUS  current
	DESCRIPTION ""
	-- 1.3.6.1.4.1.28507.111.1.6.2.2.1.1
	::= { epc873300ExtInputEntry 1 }



epc873300ExtInputEvt NOTIFICATION-TYPE
	OBJECTS {
		epc873300ExtInputIndex,
		epc873300ExtInput,
		epc873300ExtInputToggleCount,
		epc873300ExtInputName,
		epc873300ExtInputPortNum,
		epc873300ExtInputBlockIndex}
	STATUS  current
	DESCRIPTION
		"Change of external sensor input."
	-- 1.3.6.1.4.1.28507.111.3.25
	::= { events 25 }

epc873300ExtInputName OBJECT-TYPE
	SYNTAX  OCTET STRING (SIZE (0..32))
	MAX-ACCESS read-write
	STATUS  current
	DESCRIPTION
		"A textual string containing name of
		the Input"
	-- 1.3.6.1.4.1.28507.111.1.6.2.2.1.32
	::= { epc873300ExtInputEntry 32 }


epc873300ExtInputPortNum OBJECT-TYPE
	SYNTAX  Integer32
	MAX-ACCESS read-only
	STATUS  current
	DESCRIPTION
		"Number of external Sensor Port when value greater zero, else device built-in Input."
	-- 1.3.6.1.4.1.28507.111.1.6.2.2.1.33
	::= { epc873300ExtInputEntry 33 }


epc873300ExtInputBlockIndex OBJECT-TYPE
	SYNTAX  Integer32
	MAX-ACCESS read-only
	STATUS  current
	DESCRIPTION
		"Either index of device built-in Input, or index of Input in external sensor."
	-- 1.3.6.1.4.1.28507.111.1.6.2.2.1.34
	::= { epc873300ExtInputEntry 34 }


epc873300CPUSensors OBJECT IDENTIFIER 
	-- 1.3.6.1.4.1.28507.111.1.5.14
	::= { epc873300IntSensors 14 }

epc873300NTPClient OBJECT IDENTIFIER 
	-- 1.3.6.1.4.1.28507.111.1.5.15
	::= { epc873300IntSensors 15 }

epc873300NTPUnixTime OBJECT-TYPE
	SYNTAX  Unsigned32
	UNITS	"s"
	MAX-ACCESS read-only
	STATUS  current
	DESCRIPTION
		"show received NTP time as unixtime (secs since 1 January 1970)"
	-- 1.3.6.1.4.1.28507.111.1.5.15.2
	::= { epc873300NTPClient 2 }


epc873300NTPLastValidTimestamp OBJECT-TYPE
	SYNTAX  Unsigned32
	UNITS	"s"
	MAX-ACCESS read-only
	STATUS  current
	DESCRIPTION
		"show seconds since last valid NTP timestamp received"
	-- 1.3.6.1.4.1.28507.111.1.5.15.3
	::= { epc873300NTPClient 3 }


epc873300NTPTimeValid OBJECT-TYPE
	SYNTAX  INTEGER {
			notime(0),
			valid(1) }
	MAX-ACCESS read-only
	STATUS  current
	DESCRIPTION
		"Show if valid Time is received"
	-- 1.3.6.1.4.1.28507.111.1.5.15.1
	::= { epc873300NTPClient 1 }


epc873300CPUSensorVsystem OBJECT-TYPE
	SYNTAX  Gauge32
	UNITS	"0.01 V"
	MAX-ACCESS read-only
	STATUS  current
	DESCRIPTION
		"System Voltage on CPU Board"
	-- 1.3.6.1.4.1.28507.111.1.5.14.1
	::= { epc873300CPUSensors 1 }


epc873300CPUSensorVaux OBJECT-TYPE
	SYNTAX  Gauge32
	UNITS	"0.01 V"
	MAX-ACCESS read-only
	STATUS  current
	DESCRIPTION
		"Auxiliary Voltage on CPU Board"
	-- 1.3.6.1.4.1.28507.111.1.5.14.2
	::= { epc873300CPUSensors 2 }


epc873300CPUSensorVmain OBJECT-TYPE
	SYNTAX  Gauge32
	UNITS	"0.01 V"
	MAX-ACCESS read-only
	STATUS  current
	DESCRIPTION
		"Main Voltage on CPU Board"
	-- 1.3.6.1.4.1.28507.111.1.5.14.3
	::= { epc873300CPUSensors 3 }


epc873300CPUSensorTcpu OBJECT-TYPE
	SYNTAX  Integer32
	MAX-ACCESS read-only
	STATUS  current
	DESCRIPTION
		"Temperature on CPU Board"
	-- 1.3.6.1.4.1.28507.111.1.5.14.4
	::= { epc873300CPUSensors 4 }


-- Notification Types
--

events OBJECT IDENTIFIER 
	-- 1.3.6.1.4.1.28507.111.3
	::= { gadsEPC873300 3 }


epc873300SwitchEvtPort NOTIFICATION-TYPE
	OBJECTS {
		epc873300PortIndex,
		epc873300PortName,
		epc873300PortState,
		epc873300PortSwitchCount}
	STATUS  current
	DESCRIPTION
		"Event is triggered when a port is switched"
	-- 1.3.6.1.4.1.28507.111.3.1
	::= { events 1 }


epc873300TempEvtSen NOTIFICATION-TYPE
	OBJECTS {
		epc873300SensorIndex,
		epc873300TempSensor}
	STATUS  current
	DESCRIPTION
		"temperature limits exceeded"
	-- 1.3.6.1.4.1.28507.111.3.2
	::= { events 2 }


epc873300AirPressureEvtSen NOTIFICATION-TYPE
	OBJECTS {
		epc873300SensorIndex,
		epc873300AirPressure}
	STATUS  current
	DESCRIPTION
		"Air Pressure limits exceeded

		"
	-- 1.3.6.1.4.1.28507.111.3.4
	::= { events 4 }


epc873300DewPtDiffEvtSen NOTIFICATION-TYPE
	OBJECTS {
		epc873300SensorIndex,
		epc873300DewPointDiff}
	STATUS  current
	DESCRIPTION
		"Dew Point Difference limits exceeded"
	-- 1.3.6.1.4.1.28507.111.3.5
	::= { events 5 }


epc873300LineAmperageEvt NOTIFICATION-TYPE
	OBJECTS {
		epc873300PowerIndex,
		epc873300PowerActive,
		epc873300Current,
		epc873300Voltage,
		epc873300Frequency,
		epc873300PowerApparent,
		epc873300PowerReactive}
	STATUS  current
	DESCRIPTION
		"Event is triggered when a measured
		current is crossing the entered limits"
	-- 1.3.6.1.4.1.28507.111.3.7
	::= { events 7 }

epc873300Voltage OBJECT-TYPE
	SYNTAX  Gauge32
	UNITS	"V"
	MAX-ACCESS read-only
	STATUS  current
	DESCRIPTION
		"Actual Voltage on Power Channel"
	-- 1.3.6.1.4.1.28507.111.1.5.1.2.1.6
	::= { epc873300PowerEntry 6 }


epc873300Frequency OBJECT-TYPE
	SYNTAX  Gauge32
	UNITS	"0.01 hz"
	MAX-ACCESS read-only
	STATUS  current
	DESCRIPTION
		"Frequency of Power Channel"
	-- 1.3.6.1.4.1.28507.111.1.5.1.2.1.7
	::= { epc873300PowerEntry 7 }


epc873300AbsEnergyReactive OBJECT-TYPE
	SYNTAX  Gauge32
	UNITS	"VARh"
	MAX-ACCESS read-only
	STATUS  current
	DESCRIPTION
		"Absolute Reactive Energy counter."
	-- 1.3.6.1.4.1.28507.111.1.5.1.2.1.12
	::= { epc873300PowerEntry 12 }


epc873300AbsEnergyActiveResettable OBJECT-TYPE
	SYNTAX  Gauge32
	UNITS	"Wh"
	MAX-ACCESS read-write
	STATUS  current
	DESCRIPTION
		"Resettable Absolute Active Energy counter.
		Writing '0' resets all resettable counter."
	-- 1.3.6.1.4.1.28507.111.1.5.1.2.1.13
	::= { epc873300PowerEntry 13 }


epc873300AbsEnergyReactiveResettable OBJECT-TYPE
	SYNTAX  Gauge32
	UNITS	"VARh"
	MAX-ACCESS read-only
	STATUS  current
	DESCRIPTION
		"Resettable Absolute Reactive Energy counter."
	-- 1.3.6.1.4.1.28507.111.1.5.1.2.1.14
	::= { epc873300PowerEntry 14 }


epc873300ResetTime OBJECT-TYPE
	SYNTAX  Gauge32
	UNITS	"s"
	MAX-ACCESS read-only
	STATUS  current
	DESCRIPTION
		"Time in seconds since last Energy
		Counter reset."
	-- 1.3.6.1.4.1.28507.111.1.5.1.2.1.15
	::= { epc873300PowerEntry 15 }


epc873300ForwEnergyActive OBJECT-TYPE
	SYNTAX  Gauge32
	UNITS	"Wh"
	MAX-ACCESS read-only
	STATUS  current
	DESCRIPTION
		"Forward Active Energy counter."
	-- 1.3.6.1.4.1.28507.111.1.5.1.2.1.16
	::= { epc873300PowerEntry 16 }


epc873300ForwEnergyReactive OBJECT-TYPE
	SYNTAX  Gauge32
	UNITS	"VARh"
	MAX-ACCESS read-only
	STATUS  current
	DESCRIPTION
		"Forward Reactive Energy counter."
	-- 1.3.6.1.4.1.28507.111.1.5.1.2.1.17
	::= { epc873300PowerEntry 17 }


epc873300ForwEnergyActiveResettable OBJECT-TYPE
	SYNTAX  Gauge32
	UNITS	"Wh"
	MAX-ACCESS read-only
	STATUS  current
	DESCRIPTION
		"Resettable Forward Active Energy counter."
	-- 1.3.6.1.4.1.28507.111.1.5.1.2.1.18
	::= { epc873300PowerEntry 18 }


epc873300ForwEnergyReactiveResettable OBJECT-TYPE
	SYNTAX  Gauge32
	UNITS	"VARh"
	MAX-ACCESS read-only
	STATUS  current
	DESCRIPTION
		"Resettable Forward Reactive Energy counter."
	-- 1.3.6.1.4.1.28507.111.1.5.1.2.1.19
	::= { epc873300PowerEntry 19 }


epc873300RevEnergyActive OBJECT-TYPE
	SYNTAX  Gauge32
	UNITS	"Wh"
	MAX-ACCESS read-only
	STATUS  current
	DESCRIPTION
		"Reverse Active Energy counter."
	-- 1.3.6.1.4.1.28507.111.1.5.1.2.1.20
	::= { epc873300PowerEntry 20 }


epc873300RevEnergyReactive OBJECT-TYPE
	SYNTAX  Gauge32
	UNITS	"VARh"
	MAX-ACCESS read-only
	STATUS  current
	DESCRIPTION
		"Reverse Reactive Energy counter."
	-- 1.3.6.1.4.1.28507.111.1.5.1.2.1.21
	::= { epc873300PowerEntry 21 }


epc873300RevEnergyActiveResettable OBJECT-TYPE
	SYNTAX  Gauge32
	UNITS	"Wh"
	MAX-ACCESS read-only
	STATUS  current
	DESCRIPTION
		"Resettable Reverse Active Energy counter."
	-- 1.3.6.1.4.1.28507.111.1.5.1.2.1.22
	::= { epc873300PowerEntry 22 }


epc873300RevEnergyReactiveResettable OBJECT-TYPE
	SYNTAX  Gauge32
	UNITS	"VARh"
	MAX-ACCESS read-only
	STATUS  current
	DESCRIPTION
		"Resettable Reverse Reactive Energy counter."
	-- 1.3.6.1.4.1.28507.111.1.5.1.2.1.23
	::= { epc873300PowerEntry 23 }


epc873300AbsEnergyActive OBJECT-TYPE
	SYNTAX  Gauge32
	UNITS	"Wh"
	MAX-ACCESS read-only
	STATUS  current
	DESCRIPTION
		"Absolute Active Energy counter."
	-- 1.3.6.1.4.1.28507.111.1.5.1.2.1.3
	::= { epc873300PowerEntry 3 }


-- Scalars and Tables
--

epc873300Objects OBJECT IDENTIFIER 
	-- 1.3.6.1.4.1.28507.111.1
	::= { gadsEPC873300 1 }

epc873300CommonConfig OBJECT IDENTIFIER 
	-- 1.3.6.1.4.1.28507.111.1.1
	::= { epc873300Objects 1 }

epc873300SNMPaccess OBJECT IDENTIFIER 
	-- 1.3.6.1.4.1.28507.111.1.1.1
	::= { epc873300CommonConfig 1 }

epc873300TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.111.1.1.1.1
	::= { epc873300SNMPaccess 1 }


epc873300TrapIPTable OBJECT-TYPE
	SYNTAX  SEQUENCE OF Epc873300TrapIPEntry
	MAX-ACCESS not-accessible
	STATUS  current
	DESCRIPTION
		"list of all Trap receiver"
	-- 1.3.6.1.4.1.28507.111.1.1.1.2
	::= { epc873300SNMPaccess 2 }


epc873300TrapIPEntry OBJECT-TYPE
	SYNTAX  Epc873300TrapIPEntry
	MAX-ACCESS not-accessible
	STATUS  current
	DESCRIPTION
		"an entry containing management
		informations regarding the list of trap
		receivers"
	INDEX {
		epc873300TrapIPIndex }
	-- 1.3.6.1.4.1.28507.111.1.1.1.2.1
	::= { epc873300TrapIPTable 1 }


Epc873300TrapIPEntry ::= SEQUENCE {

	epc873300TrapIPIndex Integer32,
	epc873300TrapAddr    OCTET STRING }


epc873300TrapIPIndex OBJECT-TYPE
	SYNTAX  Integer32 (1..8)
	MAX-ACCESS read-only
	STATUS  current
	DESCRIPTION
		"A unique value, greater than zero, for each receiver slot."
	-- 1.3.6.1.4.1.28507.111.1.1.1.2.1.1
	::= { epc873300TrapIPEntry 1 }


epc873300TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.111.1.1.1.2.1.2
	::= { epc873300TrapIPEntry 2 }


epc873300DeviceConfig OBJECT IDENTIFIER 
	-- 1.3.6.1.4.1.28507.111.1.2
	::= { epc873300Objects 2 }

epc873300IntActors OBJECT IDENTIFIER 
	-- 1.3.6.1.4.1.28507.111.1.3
	::= { epc873300Objects 3 }

epc873300relayports OBJECT IDENTIFIER 
	-- 1.3.6.1.4.1.28507.111.1.3.1
	::= { epc873300IntActors 1 }

-- the Interfaces table
-- The Interfaces table contains information on the entity's
-- interfaces.  Each sub-layer below the internetwork-layer
-- of a network interface is considered to be an interface.

epc873300portTable OBJECT-TYPE
	SYNTAX  SEQUENCE OF Epc873300portEntry
	MAX-ACCESS not-accessible
	STATUS  current
	DESCRIPTION
		"list of all EPC Relay Ports"
	-- 1.3.6.1.4.1.28507.111.1.3.1.2
	::= { epc873300relayports 2 }


epc873300portEntry OBJECT-TYPE
	SYNTAX  Epc873300portEntry
	MAX-ACCESS not-accessible
	STATUS  current
	DESCRIPTION
		"An entry containing management information applicable to a
		particular relay port."
	INDEX {
		epc873300PortIndex }
	-- 1.3.6.1.4.1.28507.111.1.3.1.2.1
	::= { epc873300portTable 1 }


Epc873300portEntry ::= SEQUENCE {

	epc873300PortIndex         Integer32,
	epc873300PortName          OCTET STRING,
	epc873300PortState         INTEGER,
	epc873300PortSwitchCount   Integer32,
	epc873300PortStartupMode   INTEGER,
	epc873300PortStartupDelay  Integer32,
	epc873300PortRepowerTime   Integer32,
	epc873300PortResetDuration Integer32 }


epc873300PortName OBJECT-TYPE
	SYNTAX  OCTET STRING (SIZE (0..15))
	MAX-ACCESS read-write
	STATUS  current
	DESCRIPTION
		"A textual string containing name of a Relay Port."
	-- 1.3.6.1.4.1.28507.111.1.3.1.2.1.2
	::= { epc873300portEntry 2 }


epc873300PortState OBJECT-TYPE
	SYNTAX  INTEGER {
			off(0),
			on(1) }
	MAX-ACCESS read-write
	STATUS  current
	DESCRIPTION
		"current state of a Relay Port"
	-- 1.3.6.1.4.1.28507.111.1.3.1.2.1.3
	::= { epc873300portEntry 3 }


epc873300PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.111.1.3.1.2.1.4
	::= { epc873300portEntry 4 }


epc873300PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.111.1.3.1.2.1.5
	::= { epc873300portEntry 5 }


epc873300PortStartupDelay OBJECT-TYPE
	SYNTAX  Integer32
	UNITS	"seconds"
	MAX-ACCESS read-write
	STATUS  current
	DESCRIPTION
		"Delay in sec for startup action"
	DEFVAL { 0 }
	-- 1.3.6.1.4.1.28507.111.1.3.1.2.1.6
	::= { epc873300portEntry 6 }


epc873300PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.111.1.3.1.2.1.7
	::= { epc873300portEntry 7 }


epc873300Buzzer OBJECT-TYPE
	SYNTAX  Integer32 (0..1)
	UNITS	"0 = Off, 1 = On"
	MAX-ACCESS read-write
	STATUS  current
	DESCRIPTION
		"turn Buzzer on and off"
	-- 1.3.6.1.4.1.28507.111.1.3.10
	::= { epc873300IntActors 10 }


epc873300ExtActors OBJECT IDENTIFIER 
	-- 1.3.6.1.4.1.28507.111.1.4
	::= { epc873300Objects 4 }

epc873300IntSensors OBJECT IDENTIFIER 
	-- 1.3.6.1.4.1.28507.111.1.5
	::= { epc873300Objects 5 }

epc873300PowerChan OBJECT IDENTIFIER 
	-- 1.3.6.1.4.1.28507.111.1.5.1
	::= { epc873300IntSensors 1 }

epc873300ActivePowerChan OBJECT-TYPE
	SYNTAX  Unsigned32 (1)
	MAX-ACCESS read-only
	STATUS  current
	DESCRIPTION
		"Number of suppported Power Channels."
	-- 1.3.6.1.4.1.28507.111.1.5.1.1
	::= { epc873300PowerChan 1 }


epc873300PowerTable OBJECT-TYPE
	SYNTAX  SEQUENCE OF Epc873300PowerEntry
	MAX-ACCESS not-accessible
	STATUS  current
	DESCRIPTION
		"All available Channel Interfaces."
	-- 1.3.6.1.4.1.28507.111.1.5.1.2
	::= { epc873300PowerChan 2 }


epc873300PowerEntry OBJECT-TYPE
	SYNTAX  Epc873300PowerEntry
	MAX-ACCESS not-accessible
	STATUS  current
	DESCRIPTION
		"An entry containing management information
		applicable to a particular Power Channel."
	INDEX {
		epc873300PowerIndex }
	-- 1.3.6.1.4.1.28507.111.1.5.1.2.1
	::= { epc873300PowerTable 1 }


Epc873300PowerEntry ::= SEQUENCE {

	epc873300PowerIndex                   Integer32,
	epc873300ChanStatus                   Integer32,
	epc873300AbsEnergyActive              Gauge32,
	epc873300PowerActive                  Integer32,
	epc873300Current                      Gauge32,
	epc873300Voltage                      Gauge32,
	epc873300Frequency                    Gauge32,
	epc873300PowerFactor                  Integer32,
	epc873300Pangle                       Integer32,
	epc873300PowerApparent                Integer32,
	epc873300PowerReactive                Integer32,
	epc873300AbsEnergyReactive            Gauge32,
	epc873300AbsEnergyActiveResettable    Gauge32,
	epc873300AbsEnergyReactiveResettable  Gauge32,
	epc873300ResetTime                    Gauge32,
	epc873300ForwEnergyActive             Gauge32,
	epc873300ForwEnergyReactive           Gauge32,
	epc873300ForwEnergyActiveResettable   Gauge32,
	epc873300ForwEnergyReactiveResettable Gauge32,
	epc873300RevEnergyActive              Gauge32,
	epc873300RevEnergyReactive            Gauge32,
	epc873300RevEnergyActiveResettable    Gauge32,
	epc873300RevEnergyReactiveResettable  Gauge32,
	epc873300LineSensorName               OCTET STRING }


epc873300ChanStatus OBJECT-TYPE
	SYNTAX  Integer32 (0..1)
	MAX-ACCESS read-only
	STATUS  current
	DESCRIPTION
		"0 = data not active, 1 = data valid"
	-- 1.3.6.1.4.1.28507.111.1.5.1.2.1.2
	::= { epc873300PowerEntry 2 }


epc873300PowerActive OBJECT-TYPE
	SYNTAX  Integer32
	UNITS	"W"
	MAX-ACCESS read-only
	STATUS  current
	DESCRIPTION
		"Active Power"
	-- 1.3.6.1.4.1.28507.111.1.5.1.2.1.4
	::= { epc873300PowerEntry 4 }


epc873300Current OBJECT-TYPE
	SYNTAX  Gauge32
	UNITS	"mA"
	MAX-ACCESS read-only
	STATUS  current
	DESCRIPTION
		"Actual Curent on Power Channel."
	-- 1.3.6.1.4.1.28507.111.1.5.1.2.1.5
	::= { epc873300PowerEntry 5 }


epc873300PowerFactor OBJECT-TYPE
	SYNTAX  Integer32
	UNITS	"0.001"
	MAX-ACCESS read-only
	STATUS  current
	DESCRIPTION
		"Power Factor of Channel between
		-1.0 and 1.00"
	-- 1.3.6.1.4.1.28507.111.1.5.1.2.1.8
	::= { epc873300PowerEntry 8 }


epc873300Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.111.1.5.1.2.1.9
	::= { epc873300PowerEntry 9 }


epc873300PowerApparent OBJECT-TYPE
	SYNTAX  Integer32
	UNITS	"VA"
	MAX-ACCESS read-only
	STATUS  current
	DESCRIPTION
		"L Line Mean Apparent Power"
	-- 1.3.6.1.4.1.28507.111.1.5.1.2.1.10
	::= { epc873300PowerEntry 10 }


epc873300PowerReactive OBJECT-TYPE
	SYNTAX  Integer32
	UNITS	"VAR"
	MAX-ACCESS read-only
	STATUS  current
	DESCRIPTION
		"L Line Mean Reactive Power"
	-- 1.3.6.1.4.1.28507.111.1.5.1.2.1.11
	::= { epc873300PowerEntry 11 }


epc873300ExtSensors OBJECT IDENTIFIER 
	-- 1.3.6.1.4.1.28507.111.1.6
	::= { epc873300Objects 6 }

epc873300SensorTable OBJECT-TYPE
	SYNTAX  SEQUENCE OF Epc873300SensorEntry
	MAX-ACCESS not-accessible
	STATUS  current
	DESCRIPTION ""
	-- 1.3.6.1.4.1.28507.111.1.6.1
	::= { epc873300ExtSensors 1 }


epc873300SensorEntry OBJECT-TYPE
	SYNTAX  Epc873300SensorEntry
	MAX-ACCESS not-accessible
	STATUS  current
	DESCRIPTION ""
	INDEX {
		epc873300SensorIndex }
	-- 1.3.6.1.4.1.28507.111.1.6.1.1
	::= { epc873300SensorTable 1 }


Epc873300SensorEntry ::= SEQUENCE {

	epc873300SensorIndex   Integer32,
	epc873300TempSensor    Integer32,
	epc873300HygroSensor   Integer32,
	epc873300AirPressure   Integer32,
	epc873300DewPoint      Integer32,
	epc873300DewPointDiff  Integer32,
	epc873300ExtSensorName OCTET STRING }


epc873300SensorIndex OBJECT-TYPE
	SYNTAX  Integer32 (1..2)
	MAX-ACCESS read-only
	STATUS  current
	DESCRIPTION ""
	-- 1.3.6.1.4.1.28507.111.1.6.1.1.1
	::= { epc873300SensorEntry 1 }


epc873300TempSensor OBJECT-TYPE
	SYNTAX  Integer32
	MAX-ACCESS read-only
	STATUS  current
	DESCRIPTION
		"actual temperature"
	-- 1.3.6.1.4.1.28507.111.1.6.1.1.2
	::= { epc873300SensorEntry 2 }


epc873300AirPressure OBJECT-TYPE
	SYNTAX  Integer32
	MAX-ACCESS read-only
	STATUS  current
	DESCRIPTION
		"actual air pressure"
	-- 1.3.6.1.4.1.28507.111.1.6.1.1.5
	::= { epc873300SensorEntry 5 }


epc873300DewPoint OBJECT-TYPE
	SYNTAX  Integer32
	MAX-ACCESS read-only
	STATUS  current
	DESCRIPTION
		"dew point for actual temperature and humidity"
	-- 1.3.6.1.4.1.28507.111.1.6.1.1.6
	::= { epc873300SensorEntry 6 }


epc873300DewPointDiff OBJECT-TYPE
	SYNTAX  Integer32
	MAX-ACCESS read-only
	STATUS  current
	DESCRIPTION
		"difference between dew point and actual
		temperature (Temp - DewPoint)"
	-- 1.3.6.1.4.1.28507.111.1.6.1.1.7
	::= { epc873300SensorEntry 7 }


epc873300HygroSensor OBJECT-TYPE
	SYNTAX  Integer32
	UNITS	"0.1 percent humidity"
	MAX-ACCESS read-only
	STATUS  current
	DESCRIPTION
		"actual humidity"
	-- 1.3.6.1.4.1.28507.111.1.6.1.1.3
	::= { epc873300SensorEntry 3 }


-- Conformance
--

epc873300Conf OBJECT IDENTIFIER 
	-- 1.3.6.1.4.1.28507.111.2
	::= { gadsEPC873300 2 }

-- Groups
--

epc873300Groups OBJECT IDENTIFIER 
	-- 1.3.6.1.4.1.28507.111.2.1
	::= { epc873300Conf 1 }

-- Compliance
--

epc873300Compls OBJECT IDENTIFIER 
	-- 1.3.6.1.4.1.28507.111.2.2
	::= { epc873300Conf 2 }

epc873300BasicGroup OBJECT-GROUP
	OBJECTS {
		epc873300TrapCtrl,
		epc873300TrapIPIndex,
		epc873300TrapAddr,
		epc873300portNumber,
		epc873300PortIndex,
		epc873300PortName,
		epc873300PortState,
		epc873300PortSwitchCount,
		epc873300PortStartupMode,
		epc873300PortStartupDelay,
		epc873300PortRepowerTime,
		epc873300Buzzer,
		epc873300ActivePowerChan,
		epc873300PowerIndex,
		epc873300ChanStatus,
		epc873300AbsEnergyActive,
		epc873300PowerActive,
		epc873300Current,
		epc873300Voltage,
		epc873300Frequency,
		epc873300PowerFactor,
		epc873300Pangle,
		epc873300PowerApparent,
		epc873300PowerReactive,
		epc873300AbsEnergyReactive,
		epc873300AbsEnergyActiveResettable,
		epc873300AbsEnergyReactiveResettable,
		epc873300ResetTime,
		epc873300ForwEnergyActive,
		epc873300ForwEnergyReactive,
		epc873300ForwEnergyActiveResettable,
		epc873300ForwEnergyReactiveResettable,
		epc873300RevEnergyActive,
		epc873300RevEnergyReactive,
		epc873300RevEnergyActiveResettable,
		epc873300RevEnergyReactiveResettable,
		epc873300SensorIndex,
		epc873300TempSensor,
		epc873300HygroSensor,
		epc873300AirPressure,
		epc873300DewPoint,
		epc873300DewPointDiff,
		epc873300LineSensorName,
		epc873300ExtSensorName,
		epc873300CPUSensorVsystem,
		epc873300CPUSensorVaux,
		epc873300CPUSensorVmain,
		epc873300CPUSensorTcpu,
		epc873300NTPTimeValid,
		epc873300NTPUnixTime,
		epc873300NTPLastValidTimestamp,
		epc873300PortResetDuration,
		epc873300ExtActiveInputs,
		epc873300ExtInputIndex,
		epc873300ExtInput,
		epc873300ExtInputName,
		epc873300ExtInputPortNum,
		epc873300ExtInputBlockIndex,
		epc873300ActiveTotalChan,
		epc873300TotalIndex,
		epc873300NeutralCurrent,
		epc873300ExtInputToggleCount,
		epc873300PwrSupplyIndex,
		epc873300PwrSupplyStatus,
		epc873300ProdName,
		epc873300FWVersion,
		epc873300HostName,
		epc873300PhysAddress,
		epc873300SerialNumber }
	STATUS  current
	DESCRIPTION
		"Basic objects."
	-- 1.3.6.1.4.1.28507.111.2.1.1
	::= { epc873300Groups 1 }

epc873300NotificationGroup NOTIFICATION-GROUP
	NOTIFICATIONS {
		epc873300SwitchEvtPort,
		epc873300TempEvtSen,
		epc873300HygroEvtSen,
		epc873300AirPressureEvtSen,
		epc873300DewPtDiffEvtSen,
		epc873300LineAmperageEvt,
		epc873300ExtInputEvt,
		epc873300LineVoltageEvt,
		epc873300LinePowerEvt,
		epc873300PwrSupplyChangeEvt }
	STATUS  current
	DESCRIPTION ""
	-- 1.3.6.1.4.1.28507.111.2.1.2
	::= { epc873300Groups 2 }


epc873300HygroEvtSen NOTIFICATION-TYPE
	OBJECTS {
		epc873300SensorIndex,
		epc873300HygroSensor}
	STATUS  current
	DESCRIPTION
		"hygro limits exceeded"
	-- 1.3.6.1.4.1.28507.111.3.3
	::= { events 3 }

epc873300LineSensorName OBJECT-TYPE
	SYNTAX  OCTET STRING (SIZE (0..32))
	MAX-ACCESS read-write
	STATUS  current
	DESCRIPTION
		"A textual string containing name of a
		Line Sensor"
	-- 1.3.6.1.4.1.28507.111.1.5.1.2.1.100
	::= { epc873300PowerEntry 100 }


epc873300ExtSensorName OBJECT-TYPE
	SYNTAX  OCTET STRING (SIZE (0..32))
	MAX-ACCESS read-write
	STATUS  current
	DESCRIPTION
		"A textual string containing name of a
		external Sensor"
	-- 1.3.6.1.4.1.28507.111.1.6.1.1.32
	::= { epc873300SensorEntry 32 }


epc873300PortIndex OBJECT-TYPE
	SYNTAX  Integer32 (1..30)
	MAX-ACCESS read-only
	STATUS  current
	DESCRIPTION
		"A unique value, greater than zero, for each Relay Port."
	-- 1.3.6.1.4.1.28507.111.1.3.1.2.1.1
	::= { epc873300portEntry 1 }


epc873300PowerIndex OBJECT-TYPE
	SYNTAX  Integer32 (1..3)
	MAX-ACCESS read-only
	STATUS  current
	DESCRIPTION
		"Index of Power Channel entries"
	-- 1.3.6.1.4.1.28507.111.1.5.1.2.1.1
	::= { epc873300PowerEntry 1 }


gadsEPC873300 OBJECT IDENTIFIER 
	-- 1.3.6.1.4.1.28507.111
	::= { gudeads 111 }

epc873300PortResetDuration OBJECT-TYPE
	SYNTAX  Integer32 (0..65535)
	UNITS	"seconds"
	MAX-ACCESS read-write
	STATUS  current
	DESCRIPTION
		"Delay in sec for turning Port on again after Reset action"
	DEFVAL { 0 }
	-- 1.3.6.1.4.1.28507.111.1.3.1.2.1.8
	::= { epc873300portEntry 8 }


epc873300portNumber OBJECT-TYPE
	SYNTAX  Integer32 (1..30)
	MAX-ACCESS read-only
	STATUS  current
	DESCRIPTION
		"The number of Relay Ports"
	-- 1.3.6.1.4.1.28507.111.1.3.1.1
	::= { epc873300relayports 1 }


epc873300ExtInputToggleCount OBJECT-TYPE
	SYNTAX  Integer32
	MAX-ACCESS read-only
	STATUS  current
	DESCRIPTION
		"Number of times the Input has changed its state."
	-- 1.3.6.1.4.1.28507.111.1.6.2.2.1.3
	::= { epc873300ExtInputEntry 3 }


epc873300ExtActiveInputs OBJECT-TYPE
	SYNTAX  Unsigned32
	MAX-ACCESS read-only
	STATUS  current
	DESCRIPTION
		"Number of suppported Input Channels."
	-- 1.3.6.1.4.1.28507.111.1.6.2.1
	::= { epc873300ExtInputs 1 }


END
