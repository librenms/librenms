--
-- genCardResources.mib
-- MIB generated by MG-SOFT Visual MIB Builder Version 3.0 Build 285
-- Wednesday, November 02, 2011 at 14:49:06
--

	ZHONE-CARD-RESOURCES-MIB DEFINITIONS ::= BEGIN
 
		IMPORTS
			OBJECT-GROUP, NOTIFICATION-GROUP			
				FROM SNMPv2-CONF			
			TimeTicks, Integer32, Unsigned32, OBJECT-TYPE, MODULE-IDENTITY, 
			OBJECT-IDENTITY, NOTIFICATION-TYPE			
				FROM SNMPv2-SMI			
			TEXTUAL-CONVENTION			
				FROM SNMPv2-TC			
			zhoneCard, zhoneShelfIndex, zhoneSlotIndex, zhoneModules, zhoneShelfIndex, 
			zhoneSlotIndex			
				FROM Zhone			
			ZhoneAdminString, ZhoneDiagAction, ZhoneCardType			
				FROM Zhone-TC;
	
	
-- 	
-- The Zhone CardResource MIB defines management variables for managing card on Zhone systems.
-- 
-- /vob/zhonetools/bin/pahrser.pl [-css] rfc2514.mib rfc1907.mib iftype.mib 
-- rfc2233.mib rfc2571.mib Zhone.mib Zhone-TC.mib genCardResources.mib
-- 
-- /vob/EPILOGUE/binaries/emissary/solaris/mibcomp rfc2514.mib rfc1907.mib 
-- iftype.mib rfc2233.mib rfc2571.mib Zhone.mib Zhone-TC.mib -stub 
-- -o cardHdlrs.o genCardResources.mib
-- 
--  
-- 
-- 
		-- 1.3.6.1.4.1.5504.6.4
		zhoneCardResourcesModule MODULE-IDENTITY 
			LAST-UPDATED "201110241558Z"		-- October 24, 2011 at 15:58 GMT
			ORGANIZATION 
				"Zhone Technologies"
			CONTACT-INFO 
				"  Postal: 
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"Contains the resources utilized on a per CPU basis. Note
				that in a single cpu system, this data represents the
				entire system."
			REVISION "201110241447Z"		-- October 24, 2011 at 14:47 GMT
			DESCRIPTION 
				"add zhoneExternalRelayNormalState field"
			REVISION "201110121244Z"		-- October 12, 2011 at 12:44 GMT
			DESCRIPTION 
				"Add more objects to cardResourcesEntry"
			REVISION "201108241533Z"		-- August 24, 2011 at 15:33 GMT
			DESCRIPTION 
				"Add zhoneMxkAlarmInputTrap"
			REVISION "201007131041Z"		-- July 13, 2010 at 10:41 GMT
			DESCRIPTION 
				"Added zhoneTrapProcessorUsage"
			REVISION "200905120758Z"		-- May 12, 2009 at 07:58 GMT
			DESCRIPTION 
				"Replaced cardResourceTable.cardPweTrafficMode
				with cardResourceTable.cardPweTimingMode, also
				modifying allowed values, defaulted to none."
			REVISION "200904240851Z"		-- April 24, 2009 at 08:51 GMT
			DESCRIPTION 
				"Added cardResourceTable.cardPweTrafficMode to support
				timing modes which may require rtp headers in packets."
			REVISION "200810220311Z"		-- October 22, 2008 at 03:11 GMT
			DESCRIPTION 
				"Changing MTAC names to TAC."
			REVISION "200708151730Z"		-- August 15, 2007 at 17:30 GMT
			DESCRIPTION 
				"Add znidResources."
			REVISION "200610171503Z"		-- October 17, 2006 at 15:03 GMT
			DESCRIPTION 
				"Deprecate cardLineVoltage and cardVpiVciRange
				(moved to zhoneSysCardSoftwareConfig)"
			REVISION "200609281142Z"		-- September 28, 2006 at 11:42 GMT
			DESCRIPTION 
				"Add field vpiVciRange to card profile"
			REVISION "200510111647Z"		-- October 11, 2005 at 16:47 GMT
			DESCRIPTION 
				"V01.05.24 - Replaced cardAtmAvailableBandwidthPercentage
				             (read-only OID 17, not used) with cardLineVoltage"
			REVISION "200510051116Z"		-- October 05, 2005 at 11:16 GMT
			DESCRIPTION 
				"V01.05.23 - Added new services to ZhoneServiceIDs."
			REVISION "200505231422Z"		-- May 23, 2005 at 14:22 GMT
			DESCRIPTION 
				"V01.05.21 -- Change zrgBatteryRelayStatus from notify to read-only"
			REVISION "200404151327Z"		-- April 15, 2004 at 13:27 GMT
			DESCRIPTION 
				"V01.05.20 - Change cardProcessorIdle
				and cardProcessorUsage from TimeTicks
				to Integer32 since they are percentage
				values."
			REVISION "200312221214Z"		-- December 22, 2003 at 12:14 GMT
			DESCRIPTION 
				"V01.05.19 - Added ZRG power trap to monitor the state of power supply for the ZRG boards"
			REVISION "200311211518Z"		-- November 21, 2003 at 15:18 GMT
			DESCRIPTION 
				"V01.05.18 - Added zhoneExternalRelayName to zhoneExternalAlarmTrap OBJECTs"
			REVISION "200210291530Z"		-- October 29, 2002 at 15:30 GMT
			DESCRIPTION 
				"V01.05.17 - change cardInterfaceType to use ZhoneCardType from Zhone-TC.mib"
			REVISION "200210241724Z"		-- October 24, 2002 at 17:24 GMT
			DESCRIPTION 
				"V01.05.16 - import zhonecardtype from zhone-tc.mib"
			REVISION "200207091127Z"		-- July 09, 2002 at 11:27 GMT
			DESCRIPTION 
				"V01.05.15 - Add memory state notification"
			REVISION "200206071738Z"		-- June 07, 2002 at 17:38 GMT
			DESCRIPTION 
				"V01.05.14 - Added malcT1E1Tdm, malcAdslAc6, malcAdslAc6Post, malcAdslAc6Splt, malcAdslAc6AnxB and malcAdslAc6AnxBSplt. Changed malcAdslAc5B to malcAdslAc5AnxB."
			REVISION "200205241258Z"		-- May 24, 2002 at 12:58 GMT
			DESCRIPTION 
				"V01.05.13 - added malcAdslAc5B card type"
			REVISION "200203221455Z"		-- March 22, 2002 at 14:55 GMT
			DESCRIPTION 
				"V01.05.12 - added malcOc3 card type"
			REVISION "200111161811Z"		-- November 16, 2001 at 18:11 GMT
			DESCRIPTION 
				"V01.05.11 - added malcAdslAc5(5010) card type"
			REVISION "200110231110Z"		-- October 23, 2001 at 11:10 GMT
			DESCRIPTION 
				"V01.05.10 - added tdmT1e1 card type."
			REVISION "200110091000Z"		-- October 09, 2001 at 10:00 GMT
			DESCRIPTION 
				"V01.05.09 - added malcDs3 card type."
			REVISION "200110081336Z"		-- October 08, 2001 at 13:36 GMT
			DESCRIPTION 
				"V01.05.08 - added malcPots900 card type."
			REVISION "200110041226Z"		-- October 04, 2001 at 12:26 GMT
			DESCRIPTION 
				"V01.05.07 - moved card-atm-configuration to genSystem.mib"
			REVISION "200109171650Z"		-- September 17, 2001 at 16:50 GMT
			DESCRIPTION 
				"V01.05.06 - Added s300 ST1 CSU type"
			REVISION "200109071640Z"		-- September 07, 2001 at 16:40 GMT
			DESCRIPTION 
				"V01.05.05 - Added ATM configuration support"
			REVISION "200109061603Z"		-- September 06, 2001 at 16:03 GMT
			DESCRIPTION 
				"V01.05.04 - Added two new values for cardSwStatus."
			REVISION "200109052038Z"		-- September 05, 2001 at 20:38 GMT
			DESCRIPTION 
				"V01.05.03 - moved card-line-type to genSystem and added missing card types."
			REVISION "200108291123Z"		-- August 29, 2001 at 11:23 GMT
			DESCRIPTION 
				"V01.05.02 Add sechtor300 card types"
			REVISION "200108091043Z"		-- August 09, 2001 at 10:43 GMT
			DESCRIPTION 
				"V01.05.01 Add Card Line Type"
			REVISION "200107261047Z"		-- July 26, 2001 at 10:47 GMT
			DESCRIPTION 
				"V01.05.00 -- added cardServices"
			REVISION "200107201320Z"		-- July 20, 2001 at 13:20 GMT
			DESCRIPTION 
				"V01.04.00 - Add zhoneExternalRelay Objects"
			REVISION "200009121059Z"		-- September 12, 2000 at 10:59 GMT
			DESCRIPTION 
				"V01.00.00 - Initial Release"
			REVISION "200009201100Z"		-- September 20, 2000 at 11:00 GMT
			DESCRIPTION 
				"V01.00.01 - ZOI 1560"
			REVISION "200011111059Z"		-- November 11, 2000 at 10:59 GMT
			DESCRIPTION 
				"V01.01.00 - Add wireless card type"
			REVISION "200011211831Z"		-- November 21, 2000 at 18:31 GMT
			DESCRIPTION 
				"V01.02.00 - Redo sw card load/upgrade"
			REVISION "200012011218Z"		-- December 01, 2000 at 12:18 GMT
			DESCRIPTION 
				"V01.02.01 - Change markup to reflect latest MIB
				layout."
			REVISION "200012181911Z"		-- December 18, 2000 at 19:11 GMT
			DESCRIPTION 
				"V01.02.02 - added back enum value upgradeOnReset to cardSwAdmin"
			REVISION "200101221456Z"		-- January 22, 2001 at 14:56 GMT
			DESCRIPTION 
				"V01.02.03 - Add MALC card types."
			REVISION "200103271029Z"		-- March 27, 2001 at 10:29 GMT
			DESCRIPTION 
				"V01.02.04 - Added Default Values 
				for cardAdminStatus, cardAdminStatsEnable, and cardSwAdmin."
			REVISION "200104061425Z"		-- April 06, 2001 at 14:25 GMT
			DESCRIPTION 
				"V01.03.00 - Add Services Table
				Add card subtype
				Remove ts3atm card type
				as oc3Atm covers both ds3
				and ds3. cardInterfaceType further refines this."
			REVISION "200104271149Z"		-- April 27, 2001 at 11:49 GMT
			DESCRIPTION 
				"V01.03.01 - add atmTrnkCr under cardZhoneType,
				cardInterfaceType"
			REVISION "200105241315Z"		-- May 24, 2001 at 13:15 GMT
			DESCRIPTION 
				"V01.03.02 - Add card subtype oc3AtmMm
				Substitude oc3Atm card type as oc3AtmSm."
			::= { zhoneModules 4 }

		
	
--
-- Textual conventions
--
	
		Kbytes ::= TEXTUAL-CONVENTION
			STATUS current
			DESCRIPTION 
				"Memory size expressed in kilobytes (1024 bytes)"
			SYNTAX Integer32 (1..2147483647)

		ZhoneServiceId ::= TEXTUAL-CONVENTION
			STATUS current
			DESCRIPTION 
				"Identifer of a Zhone service. The following services are allowed:
				
				dspResource(1)               DSP Resources
				numberService(2)             Service to provide unique numbers to the 
				                             system. NOT ADDED BY A USER BUT 
				                             AUTOMATICALLY STARTED.
				tadService(3)                Time and Date Service
				aal2Resource(4)              ATM AAL2 Resource Manager
				ctrpCallResource(5)          Call Termination Resource Provider
				callControlResource(6)       Call Control Services
				mprrResource(7)              Voice Media Provider 
				mamaResource(8               IP Port Mapping service
				raFtdResource(9)             IP forwarding engine
				voiceCall(10)                Voice Call Processing Manager
				shelfControllerService(11)   Shelf Controller
				snmpMasterAgent(12)          SNMP Master Agent
				trapService(13)              Trap Server
				informationServices(14)      Persistent Information Storage Manager
				lineResource(15)             Line Resource Registry
				ifCfgMgrResource(16)         Interface Configuration Manager
				logServer(17)                Logging Services=
				cardServer(18)               Card Redundancy Manager 
				dhcpServer(19)               DHCP Server
				filterUpdate(20)             IP Filtering 
				ringGenerator(21)            Ring Generator Service
				zhoneRouteTableService(22)   ZAP Route Table Service
				pppResourceProvider(23)      PPP Manager
				rootDirectoryService(24)     Root Directory Services
				cssService(25)               Config Sync Service
				sipResource(26)              Session Interface Protocol Resource
				mgcpResource(27)             Media Gateway Control Protocol Resource
				npRedundantServer(28)        Network Processor Redundant Server"
			SYNTAX INTEGER
				{
				dspResource(1),
				numberService(2),
				tadService(3),
				aal2Resource(4),
				ctrpCallResource(5),
				callControlResource(6),
				mprrResource(7),
				mamaResource(8),
				raFtdResource(9),
				voiceCall(10),
				shelfControllerService(11),
				snmpMasterAgent(12),
				trapService(13),
				informationServices(14),
				lineResource(15),
				ifCfgMgrResource(16),
				logServer(17),
				cardServer(18),
				dhcpServer(19),
				filterUpdate(20),
				ringGenerator(21),
				zhoneRouteTableService(22),
				pppResourceProvider(23),
				rootDirectoryService(24),
				cssService(25),
				sipResource(26),
				mgcpResource(27),
				npRedundantServer(28)
				}

	
--
-- Node definitions
--
	
		-- 1.3.6.1.4.1.5504.3.3.1
		cardResourceTable OBJECT-TYPE
			SYNTAX SEQUENCE OF CardResourceEntry
			MAX-ACCESS not-accessible
			STATUS current
			DESCRIPTION
				"A table of unit/card status and functions for each 
				card in A BAN system. Functions include software
				download management.
				
				The maximum cards in a BAN is 255 shelves x 17 cards
				per shelf, a typical configuration will consist of
				several hundred cards.
				
				A single card system will use shelf/slot index of 1,1
				and will not be identifiable as a single card system 
				based on the shelf, slot indices."
			::= { zhoneCard 1 }

		
		-- 1.3.6.1.4.1.5504.3.3.1.1
		cardResourceEntry OBJECT-TYPE
			SYNTAX CardResourceEntry
			MAX-ACCESS not-accessible
			STATUS current
			DESCRIPTION
				"An entry per card or a singe row for a single CPU/card
				system."
			INDEX { zhoneShelfIndex, zhoneSlotIndex }
			::= { cardResourceTable 1 }

		
		CardResourceEntry ::=
			SEQUENCE { 
				cardIdentification
					ZhoneAdminString,
				cardZhoneType
					ZhoneCardType,
				cardMfgSerialNumber
					ZhoneAdminString,
				cardMfgCLEICode
					ZhoneAdminString,
				cardMfgRevisionCode
					ZhoneAdminString,
				cardMfgBootRevision
					ZhoneAdminString,
				cardPostResults
					ZhoneAdminString,
				cardAdminStatus
					INTEGER,
				cardOperStatus
					INTEGER,
				cardAdminStatsEnable
					INTEGER,
				cardUpTime
					TimeTicks,
				cardProcessorType
					ZhoneAdminString,
				cardPortStatus
					OCTET STRING,
				cardInterfaceType
					ZhoneCardType,
				cardAtmManualAal2bw
					Integer32,
				cardAtmManualAal2h
					Integer32,
				cardLineVoltage
					INTEGER,
				cardVpiVciRange
					INTEGER,
				cardPweTimingMode
					INTEGER
			 }

-- 
--  
-- 
-- 
		-- 1.3.6.1.4.1.5504.3.3.1.1.1
		cardIdentification OBJECT-TYPE
			SYNTAX ZhoneAdminString
			MAX-ACCESS read-only
			STATUS current
			DESCRIPTION
				"Textual description of the unit/card or access device
				type."
			::= { cardResourceEntry 1 }

		
-- 
-- 
-- 
-- 
		-- 1.3.6.1.4.1.5504.3.3.1.1.2
		cardZhoneType OBJECT-TYPE
			SYNTAX ZhoneCardType
			MAX-ACCESS read-only
			STATUS current
			DESCRIPTION
				"The numerical representation of what unit/card type
				is present."
			::= { cardResourceEntry 2 }

		
-- 
-- 
-- 
		-- 1.3.6.1.4.1.5504.3.3.1.1.3
		cardMfgSerialNumber OBJECT-TYPE
			SYNTAX ZhoneAdminString
			MAX-ACCESS read-only
			STATUS current
			DESCRIPTION
				"The manufacturing serial number for this unit/card."
			::= { cardResourceEntry 3 }

		
-- 
-- 
-- 
		-- 1.3.6.1.4.1.5504.3.3.1.1.4
		cardMfgCLEICode OBJECT-TYPE
			SYNTAX ZhoneAdminString
			MAX-ACCESS read-only
			STATUS current
			DESCRIPTION
				"CLEI code for the unit/card if defined, otherwise the
				value will be set to zero (0) by the card."
			::= { cardResourceEntry 4 }

		
-- 
-- 
-- 
-- 
		-- 1.3.6.1.4.1.5504.3.3.1.1.5
		cardMfgRevisionCode OBJECT-TYPE
			SYNTAX ZhoneAdminString
			MAX-ACCESS read-only
			STATUS current
			DESCRIPTION
				"Manufacturing hardware revision code for the unit/card."
			::= { cardResourceEntry 5 }

		
-- 
-- 
-- 
-- 
		-- 1.3.6.1.4.1.5504.3.3.1.1.6
		cardMfgBootRevision OBJECT-TYPE
			SYNTAX ZhoneAdminString
			MAX-ACCESS read-only
			STATUS current
			DESCRIPTION
				"Revision level of any permenant (PROM) or semi-
				permenant (flash) code on the unit/card.  This code
				is generally used as a bootstrap loader."
			::= { cardResourceEntry 6 }

		
-- 
-- 
-- 
-- 
		-- 1.3.6.1.4.1.5504.3.3.1.1.7
		cardPostResults OBJECT-TYPE
			SYNTAX ZhoneAdminString
			MAX-ACCESS read-only
			STATUS current
			DESCRIPTION
				"Results string generated by unit/card that displays
				the results of the POST (power-on-self-test).  The
				first item in the text string indicates the overall
				results of the test.  'Pass' or 'Fail'.  The 
				reminder of the string enumerates the results of
				each test which will vary by unit/card type or may
				only enumerate failed tests."
			::= { cardResourceEntry 7 }

		
-- 
--  
-- 
-- 
		-- 1.3.6.1.4.1.5504.3.3.1.1.8
		cardAdminStatus OBJECT-TYPE
			SYNTAX INTEGER
				{
				operational(1),
				disable(2),
				maintenance(3),
				warmreset(4),
				reset(5)
				}
			MAX-ACCESS read-write
			STATUS current
			DESCRIPTION
				"Specifies the adminstrative status of the unit/card 
				as follows:
				
				operational: the unit/card enters the operational
				state if able.  In the operational state the 
				unit/card is able to accept requests from other 
				elements in the BAN or if a standalone device is 
				processing requests from the WAN or local interfaces.
				
				disable: the unit/card ceases to accept requests 
				from other elements.  If the unit/card is
				operational and recieves this command it will 
				complete processing of open requests if able.
				
				maintenance: enter a special maintenance state if
				available - if not available enter the disabled
				state and set adminStatus to disabled.
				
				warmreset - perform a warm reset of system software
				that does not reinitialize or reset hardware 
				resources.
				
				reset - perform an immediate full reset, following a 
				successful reset the unit/card should enter the 
				operational state."
			DEFVAL { operational }
			::= { cardResourceEntry 8 }

		
-- 
-- 
-- 
		-- 1.3.6.1.4.1.5504.3.3.1.1.9
		cardOperStatus OBJECT-TYPE
			SYNTAX INTEGER
				{
				unknown(1),
				operating(2),
				nonoperating(3),
				maintenance(4)
				}
			MAX-ACCESS read-only
			STATUS current
			DESCRIPTION
				"Indicates the operational status of the unit/card as
				follows:
				
				unknown: the card is in an unknown or error state
				
				operating: software has been loaded and is operating, 
				the unit/card is accepting requests from other system
				elements or if a standalone unit it is processing 
				requests form the WAN or local interfaces.
				
				non-operating: unit/card is not operating due to 
				internal errors or it has been disabled by the 
				management system.
				
				maintenance: the unit/card is in the maintenance 
				state."
			::= { cardResourceEntry 9 }

		
-- 
-- 
-- 
		-- 1.3.6.1.4.1.5504.3.3.1.1.10
		cardAdminStatsEnable OBJECT-TYPE
			SYNTAX INTEGER
				{
				enable(1),
				disable(2)
				}
			MAX-ACCESS read-write
			STATUS current
			DESCRIPTION
				"Enable the collection and forwarding of historical
				statistics on the unit/card.  The default value is
				disabled.
				
				Note this value should be logically 'anded' with the
				the system statistics enbale to determine if the 
				collection and forwarding of statistics should 
				actually be enabled.
				
				Default value is 'disabled'."
			DEFVAL { enable }
			::= { cardResourceEntry 10 }

		
-- 
-- 
-- 
-- 
		-- 1.3.6.1.4.1.5504.3.3.1.1.11
		cardUpTime OBJECT-TYPE
			SYNTAX TimeTicks
			MAX-ACCESS read-only
			STATUS current
			DESCRIPTION
				"The amount of time since this unit/card was last
				initialized (warm or full reset).  The units are in
				100ths of a second."
			::= { cardResourceEntry 11 }

		
-- 
-- 
-- 
-- 
		-- 1.3.6.1.4.1.5504.3.3.1.1.12
		cardProcessorType OBJECT-TYPE
			SYNTAX ZhoneAdminString
			MAX-ACCESS read-only
			STATUS current
			DESCRIPTION
				"A string is returned that describes the processor type
				used on the unit/card."
			::= { cardResourceEntry 12 }

		
-- 
-- 
-- 
		-- 1.3.6.1.4.1.5504.3.3.1.1.13
		cardPortStatus OBJECT-TYPE
			SYNTAX OCTET STRING
			MAX-ACCESS read-only
			STATUS current
			DESCRIPTION
				"Summary of the status of all physical ports on the
				unit/card.  Each port is identified by it's ifTable
				index and the status is indicated as up|down|unknown."
			::= { cardResourceEntry 13 }

		
		-- 1.3.6.1.4.1.5504.3.3.1.1.14
		cardInterfaceType OBJECT-TYPE
			SYNTAX ZhoneCardType
			MAX-ACCESS read-only
			STATUS current
			DESCRIPTION
				"This field is used to identify which interface types are s
				upported for a  given card. In the  case  where a card has 
				exactly one possible interface (such as the ethernet card) 
				this field is exactly the same as the cardResourceCardType 
				field. For polymorphic trunk cards this field reflects the
				interface card type which is installed."
			::= { cardResourceEntry 14 }

		
		-- 1.3.6.1.4.1.5504.3.3.1.1.15
		cardAtmManualAal2bw OBJECT-TYPE
			SYNTAX Integer32 (0..100)
			MAX-ACCESS read-write
			STATUS current
			DESCRIPTION
				"This field is used to configure the resources for AAL2
				for both high and low priority interfaces as the 
				percentage of total available resources. Remainder 
				of the resources would be used for AAL5.This field 
				will be used if cardAtmConfiguration is entered 
				as manual. 
				This variable is not supported in this release.
				"
			DEFVAL { '0'b }
			::= { cardResourceEntry 15 }

		
		-- 1.3.6.1.4.1.5504.3.3.1.1.16
		cardAtmManualAal2h OBJECT-TYPE
			SYNTAX Integer32 (0..100)
			MAX-ACCESS read-write
			STATUS current
			DESCRIPTION
				"This field is used to configure the resources for 
				high priorty AAL2 interface as the percentage of total 
				bandwidth allocated for AAL2. This field will be used if
				cardAtmConfiguration is entered as manual.
				This variable is not supported in this release.
				"
			DEFVAL { '0'b }
			::= { cardResourceEntry 16 }

		
		-- 1.3.6.1.4.1.5504.3.3.1.1.17
		cardLineVoltage OBJECT-TYPE
			SYNTAX INTEGER
				{
				line-voltage-not-used(1),
				line-voltage-60-volts(2),
				line-voltage-68-volts(3),
				line-voltage-95-volts(4),
				line-voltage-100-volts(5),
				line-voltage-110-volts(6)
				}
			MAX-ACCESS read-write
			STATUS deprecated
			DESCRIPTION
				"DEPRECATED - use zhoneSysCardLineVoltage
				
				Specifies the voltage supplied to all lines(ports) of 
				this card.
				Used on ISDN line cards."
			DEFVAL { line-voltage-not-used }
			::= { cardResourceEntry 17 }

		
		-- 1.3.6.1.4.1.5504.3.3.1.1.18
		cardVpiVciRange OBJECT-TYPE
			SYNTAX INTEGER
				{
				vpivci-range-not-applicable(1),
				vpivci-range-vpi-15-vci-63(2),
				vpivci-range-vpi-7-vci-127(3)
				}
			MAX-ACCESS read-write
			STATUS deprecated
			DESCRIPTION
				"DEPRECATED - use zhoneSysCardVpiVciRange.
				
				The maximum vpi and vci values that may be used for this card."
			::= { cardResourceEntry 18 }

		
		-- 1.3.6.1.4.1.5504.3.3.1.1.19
		cardPweTimingMode OBJECT-TYPE
			SYNTAX INTEGER
				{
				none(1),
				source-differential(2),
				source-adaptive(3),
				remote-differential(4),
				remote-adaptive(5)
				}
			MAX-ACCESS read-write
			STATUS current
			DESCRIPTION
				"Describes PWE timing origin and mode of timing recovery:
				
				none    - no reference clock required, or PWE not
				          supported.
				
				source-differential - the local Provider Edge (PE) device
				          supplies the reference signal for differential
				          recovery.
				
				source-adaptive - the local PE device participates in
				          the adaptive clock recovery scheme.
				
				remote-differential - the remote PE device supplies
				          the reference signal for differential
				          recovery.
				
				remote-adaptive - the local PE device participates in
				          the adaptive clock recovery scheme."
			DEFVAL { none }
			::= { cardResourceEntry 19 }

		
		-- 1.3.6.1.4.1.5504.3.3.2
		cardSoftwareTable OBJECT-TYPE
			SYNTAX SEQUENCE OF CardSoftwareEntry
			MAX-ACCESS not-accessible
			STATUS current
			DESCRIPTION
				"Information about the software running on this
				unit(system) or card."
			::= { zhoneCard 2 }

		
		-- 1.3.6.1.4.1.5504.3.3.2.1
		cardSoftwareEntry OBJECT-TYPE
			SYNTAX CardSoftwareEntry
			MAX-ACCESS not-accessible
			STATUS current
			DESCRIPTION
				"A augmented table of the unit resource table specific 
				for software information."
			AUGMENTS { cardResourceEntry }
			::= { cardSoftwareTable 1 }

		
		CardSoftwareEntry ::=
			SEQUENCE { 
				cardSwRunningVers
					ZhoneAdminString,
				cardSwUpgradeVers
					ZhoneAdminString,
				cardSwAdmin
					INTEGER,
				cardSwStatus
					INTEGER
			 }

-- 
-- 
--  
-- 
		-- 1.3.6.1.4.1.5504.3.3.2.1.1
		cardSwRunningVers OBJECT-TYPE
			SYNTAX ZhoneAdminString
			MAX-ACCESS read-only
			STATUS current
			DESCRIPTION
				"The software version that is currently running on
				this card. This object complies to the
				Zhone software revision syntax."
			::= { cardSoftwareEntry 1 }

		
-- 
-- 
-- 
-- 
		-- 1.3.6.1.4.1.5504.3.3.2.1.2
		cardSwUpgradeVers OBJECT-TYPE
			SYNTAX ZhoneAdminString
			MAX-ACCESS read-only
			STATUS current
			DESCRIPTION
				"If warm upgrade is supported, this is the version of 
				software that is loaded on the card that will be
				switched to with a warm upgrade. 
				
				This value is set by the card sw after a loadUpgradeSoftware
				command is completed successfully.
				"
			::= { cardSoftwareEntry 2 }

		
-- 
--  
--  
-- 
		-- 1.3.6.1.4.1.5504.3.3.2.1.3
		cardSwAdmin OBJECT-TYPE
			SYNTAX INTEGER
				{
				loadUpgradeSw(1),
				upgradeNow(2),
				upgradeOnReset(3),
				reloadCurrRev(4)
				}
			MAX-ACCESS read-write
			STATUS current
			DESCRIPTION
				"
				Some items are only valid if warm upgrade is supported.
				
				loadUpgradeSoftware: the unit/card should request a 
				load of the upgrade software from the previously
				downloaded on to the system. If an 
				upgrade version of software is not available or the 
				server(s) is unable to respond to the load request 
				the card will set the cardSwStaus to 
				upgradeloadFailed (warm upgrade only - this is
				ignored if warm upgrade is not supported).
				
				upgradeNow: the unit/card should upgrade to the 
				already loaded upgrade software if warm upgrade is 
				supported or reboot and load the upgrade software
				if warm upgrade is not supported.  If the upgrade 
				software has not been loaded or there is no grade
				software load available, the unit/card will set 
				the cardSwStatus to upgradeFailed. When this value is
				set, the zhoneSysCardSwUpgradeEnable field is set to
				true in the genSystem mib associated with this card.
				
				upgradeOnReset:  the unit/card will upgrade to the
				already loaded software the next time it is 
				initialized.  If the upgrade software is not loaded 
				the card will set the cardSwStatus to upgradeFailed 
				following reset.
				
				reloadCurrVers: the will re-initialize and load the 
				previous version of code prior to the upgrade (which is
				either the 'specific' version or default version
				of software depending upon what has been provisioned) 
				See the genSystem mib for details.
				
				When this value is set, the zhoneSysCardSwUpgradeEnable
				field is set to false.
				
				"
			DEFVAL { reloadCurrRev }
			::= { cardSoftwareEntry 3 }

		
-- 
-- 
-- 
-- 
		-- 1.3.6.1.4.1.5504.3.3.2.1.4
		cardSwStatus OBJECT-TYPE
			SYNTAX INTEGER
				{
				upgradeLoadSuccessful(1),
				loadingSw(2),
				upgrading(3),
				upgradeLoadFailed(4),
				upgradeFailed(5),
				upgradeImageNotAvail(6),
				pendingUpgradeOnReset(7),
				upgradeNotRequested(8)
				}
			MAX-ACCESS read-only
			STATUS current
			DESCRIPTION
				"The upgrade status is indicated as follows:
				
				upgradeLoadSuccessful: following the setting of 
				cardSwAdmin to loadUpgradeSw this status indicates
				the load to memory or storage was successful. 
				
				loadingSw: the unit/card is loading upgrade software 
				from the internal software load service (warm upgrade 
				only).
				
				upgrading: the unit/card is in the process of 
				switching to the upgrade software (warm upgrade only).
				
				upgradeLoadFailed: the upgrade version software load
				was not able to complete due to an error or the unit
				has determined the downloaded software to be invalid.
				
				upgradeFailed: the upgrade was not able to complete
				due a load error, invalid version loaded or upgrade
				software was loaded and unable to initialize.  The 
				unit/card has reverted to the 'current' version of
				software.
				
				upgradeImageNotAvail  - The upgrade image is not
				available on this system. 
				
				pendingUpgradeOnReset :  The unit/card needs a reboot 
				to upgrade to the already loaded software .
				
				upgradeNotRequested : The upgrade image is available
				on the system but the cardSwAdmin is not set to perform
				upgrade.
				"
			::= { cardSoftwareEntry 4 }

		
		-- 1.3.6.1.4.1.5504.3.3.3
		cardRuntimeTable OBJECT-TYPE
			SYNTAX SEQUENCE OF CardRuntimeEntry
			MAX-ACCESS not-accessible
			STATUS current
			DESCRIPTION
				"Augment table of the unit/card resource but specific
				to the runtime status information."
			::= { zhoneCard 3 }

		
		-- 1.3.6.1.4.1.5504.3.3.3.1
		cardRuntimeEntry OBJECT-TYPE
			SYNTAX CardRuntimeEntry
			MAX-ACCESS not-accessible
			STATUS current
			DESCRIPTION
				"A row definition for the runtime software state/status."
			AUGMENTS { cardResourceEntry }
			::= { cardRuntimeTable 1 }

		
		CardRuntimeEntry ::=
			SEQUENCE { 
				cardPeakMemUsage
					Kbytes,
				cardAvailMem
					Kbytes,
				cardTotalMem
					Kbytes,
				cardProcessorIdle
					Integer32,
				cardProcessorUsage
					Integer32,
				cardMemStatus
					INTEGER,
				cardProcessorHighUsage
					Integer32,
				cardProcessorServicesUsage
					Integer32,
				cardProcessorFrameworkUsage
					Integer32,
				cardProcessorLowUsage
					Integer32
			 }

-- 
-- 
-- 
-- 
		-- 1.3.6.1.4.1.5504.3.3.3.1.1
		cardPeakMemUsage OBJECT-TYPE
			SYNTAX Kbytes
			MAX-ACCESS read-only
			STATUS current
			DESCRIPTION
				"The maximum physical memory that has been allocated
				at any time by the unit/card."
			::= { cardRuntimeEntry 1 }

		
-- 
-- 
-- 
-- 
		-- 1.3.6.1.4.1.5504.3.3.3.1.2
		cardAvailMem OBJECT-TYPE
			SYNTAX Kbytes
			MAX-ACCESS read-only
			STATUS current
			DESCRIPTION
				"The amount of physical memory that is unallocated
				and not in use by the unit/card."
			::= { cardRuntimeEntry 2 }

		
-- 
--  
--  
		-- 1.3.6.1.4.1.5504.3.3.3.1.3
		cardTotalMem OBJECT-TYPE
			SYNTAX Kbytes
			MAX-ACCESS read-only
			STATUS current
			DESCRIPTION
				"The amount of physical memory contained by the
				unit/card."
			::= { cardRuntimeEntry 3 }

		
-- 
-- 
-- 
-- 
		-- 1.3.6.1.4.1.5504.3.3.3.1.4
		cardProcessorIdle OBJECT-TYPE
			SYNTAX Integer32
			MAX-ACCESS read-only
			STATUS current
			DESCRIPTION
				"Percentage of time the CPU has spent executing tasks with priority
				of 200 or less.  Tasks with priority of 200 or less (the higher the
				number, the lower the priority) are considered idle tasks."
			::= { cardRuntimeEntry 4 }

		
-- 
-- 
-- 
		-- 1.3.6.1.4.1.5504.3.3.3.1.5
		cardProcessorUsage OBJECT-TYPE
			SYNTAX Integer32
			MAX-ACCESS read-only
			STATUS current
			DESCRIPTION
				"Percentage of time the CPU has spent executing tasks with priority
				of 199 or higher."
			::= { cardRuntimeEntry 5 }

		
-- 
		-- 1.3.6.1.4.1.5504.3.3.3.1.6
		cardMemStatus OBJECT-TYPE
			SYNTAX INTEGER
				{
				ramMemOK(1),
				ramMemLow(2),
				flashMemOK(3),
				flashMemLow(4),
				flashMemOut(5)
				}
			MAX-ACCESS read-only
			STATUS current
			DESCRIPTION
				"Memory status of the card sent with memory trap. 
				A trap is sent when each condition occurs.
				
				1 - ramMemOK          less then 90% of ram is used
				2 - ramMemLow         more then 90% of ram is used
				3 - flashMemOK        enough flash for maximum database
				4 - flashMemLow       not enough flash for maximum database
				5 - flashMemOut       no more flash memory, data no longer persistent
				"
			::= { cardRuntimeEntry 6 }

		
-- 
-- 
-- 
		-- 1.3.6.1.4.1.5504.3.3.3.1.7
		cardProcessorHighUsage OBJECT-TYPE
			SYNTAX Integer32 (0..100)
			MAX-ACCESS read-only
			STATUS current
			DESCRIPTION
				"Percentage of time the CPU has spent executing tasks with priority
				of 001 to 099."
			::= { cardRuntimeEntry 7 }

		
-- 
-- 
-- 
		-- 1.3.6.1.4.1.5504.3.3.3.1.8
		cardProcessorServicesUsage OBJECT-TYPE
			SYNTAX Integer32 (0..100)
			MAX-ACCESS read-only
			STATUS current
			DESCRIPTION
				"Percentage of time the CPU has spent executing tasks with priority
				of 100 to 179."
			::= { cardRuntimeEntry 8 }

		
-- 
-- 
-- 
		-- 1.3.6.1.4.1.5504.3.3.3.1.9
		cardProcessorFrameworkUsage OBJECT-TYPE
			SYNTAX Integer32 (0..100)
			MAX-ACCESS read-only
			STATUS current
			DESCRIPTION
				"Percentage of time the CPU has spent executing tasks with priority
				of 180 to 199."
			::= { cardRuntimeEntry 9 }

		
-- 
-- 
-- 
		-- 1.3.6.1.4.1.5504.3.3.3.1.10
		cardProcessorLowUsage OBJECT-TYPE
			SYNTAX Integer32 (0..100)
			MAX-ACCESS read-only
			STATUS current
			DESCRIPTION
				"Percentage of time the CPU has spent executing tasks with priority
				of 200 to 250."
			::= { cardRuntimeEntry 10 }

		
		-- 1.3.6.1.4.1.5504.3.3.4
		zhoneCardServices OBJECT IDENTIFIER ::= { zhoneCard 4 }

		
		-- 1.3.6.1.4.1.5504.3.3.4.1
		cardServicesTable OBJECT-TYPE
			SYNTAX SEQUENCE OF CardServicesEntry
			MAX-ACCESS not-accessible
			STATUS current
			DESCRIPTION
				"This contains the table of services configured to be running 
				on this card. The card runs services that are either
				customer visible (can be configured by the user) or those
				that the customer can select which card to be run on.
				This table lists all services running on this 
				card but only those services customer viewable can be 
				modified. 
				
				This table is only supported on multi-card systems (i.e. BAN)."
			::= { zhoneCardServices 1 }

		
		-- 1.3.6.1.4.1.5504.3.3.4.1.1
		cardServicesEntry OBJECT-TYPE
			SYNTAX CardServicesEntry
			MAX-ACCESS not-accessible
			STATUS current
			DESCRIPTION
				"A row in this table represents a redundant service that is running on
				this card."
			INDEX { zhoneShelfIndex, zhoneSlotIndex, cardServiceId, cardServiceInstance }
			::= { cardServicesTable 1 }

		
		CardServicesEntry ::=
			SEQUENCE { 
				cardServiceId
					ZhoneServiceId,
				cardServiceInstance
					Unsigned32,
				cardServiceChangeTime
					TimeTicks,
				cardServiceStatus
					INTEGER
			 }

		-- 1.3.6.1.4.1.5504.3.3.4.1.1.1
		cardServiceId OBJECT-TYPE
			SYNTAX ZhoneServiceId
			MAX-ACCESS accessible-for-notify
			STATUS current
			DESCRIPTION
				"Identifies the service.  The Servide ID, together with a Service 
				Instance, uniquely identify a service running on a particular card.
				"
			::= { cardServicesEntry 1 }

		
		-- 1.3.6.1.4.1.5504.3.3.4.1.1.2
		cardServiceInstance OBJECT-TYPE
			SYNTAX Unsigned32
			MAX-ACCESS accessible-for-notify
			STATUS current
			DESCRIPTION
				"The instance of this service that is running on the card. For 
				example, if multiple versions of a service is running, this
				will be the differentiator. In the case of routing domains, this
				would be the rdIndex. In most cases this value is 0 which is 
				allowed even though this field is used as an INDEX."
			::= { cardServicesEntry 2 }

		
		-- 1.3.6.1.4.1.5504.3.3.4.1.1.3
		cardServiceChangeTime OBJECT-TYPE
			SYNTAX TimeTicks
			MAX-ACCESS read-only
			STATUS current
			DESCRIPTION
				"Represents the time that service entered the current cardServiceStatus.
				Value is in system ticks."
			::= { cardServicesEntry 3 }

		
		-- 1.3.6.1.4.1.5504.3.3.4.1.1.4
		cardServiceStatus OBJECT-TYPE
			SYNTAX INTEGER
				{
				unAvailable(1),
				inActive(2),
				standBy(3),
				active(4)
				}
			MAX-ACCESS read-only
			STATUS current
			DESCRIPTION
				"The status for this particular service instance. The possible values 
				are:
				
				unAvailable (1) - The service is unavailable for unknown reasons.
				                 This is an error situation. This value may not be
				                 supported by the device.
				inActive (2) -   This service instance is waiting in line to 
				                 become standby. There may be 0 or more 
				                 services of this type in this state.
				standBy (3) -    Next in line to become active if the current
				                 active service should fail. If there's more than
				                 one service instance running, there will be one
				                 instance in standby mode.
				active (4) -     The current active service performing this 
				                 function."
			::= { cardServicesEntry 4 }

		
		-- 1.3.6.1.4.1.5504.3.3.4.2
		activeServicesTable OBJECT-TYPE
			SYNTAX SEQUENCE OF ActiveServicesEntry
			MAX-ACCESS not-accessible
			STATUS current
			DESCRIPTION
				"The table of active services running on the system"
			::= { zhoneCardServices 2 }

		
		-- 1.3.6.1.4.1.5504.3.3.4.2.1
		activeServicesEntry OBJECT-TYPE
			SYNTAX ActiveServicesEntry
			MAX-ACCESS not-accessible
			STATUS current
			DESCRIPTION
				"A row in this table represents an active service running on a card."
			INDEX { cardServiceId, cardServiceInstance }
			::= { activeServicesTable 1 }

		
		ActiveServicesEntry ::=
			SEQUENCE { 
				activeServiceShelf
					Integer32,
				activeServiceSlot
					Integer32,
				activeServiceChangeTime
					TimeTicks
			 }

		-- 1.3.6.1.4.1.5504.3.3.4.2.1.1
		activeServiceShelf OBJECT-TYPE
			SYNTAX Integer32
			MAX-ACCESS read-only
			STATUS current
			DESCRIPTION
				"Identifies the shelf where the active service is running."
			::= { activeServicesEntry 1 }

		
		-- 1.3.6.1.4.1.5504.3.3.4.2.1.2
		activeServiceSlot OBJECT-TYPE
			SYNTAX Integer32
			MAX-ACCESS read-only
			STATUS current
			DESCRIPTION
				"Identifies the slot where the active service is running."
			::= { activeServicesEntry 2 }

		
		-- 1.3.6.1.4.1.5504.3.3.4.2.1.3
		activeServiceChangeTime OBJECT-TYPE
			SYNTAX TimeTicks
			MAX-ACCESS read-only
			STATUS current
			DESCRIPTION
				"Represents the time that service became Active.
				Value is in system ticks."
			::= { activeServicesEntry 3 }

		
		-- 1.3.6.1.4.1.5504.3.3.4.3
		standbyServicesTable OBJECT-TYPE
			SYNTAX SEQUENCE OF StandbyServicesEntry
			MAX-ACCESS not-accessible
			STATUS current
			DESCRIPTION
				"The table of standby services running on the system"
			::= { zhoneCardServices 3 }

		
		-- 1.3.6.1.4.1.5504.3.3.4.3.1
		standbyServicesEntry OBJECT-TYPE
			SYNTAX StandbyServicesEntry
			MAX-ACCESS not-accessible
			STATUS current
			DESCRIPTION
				"A row in this table represents a standby service running on a card.."
			INDEX { cardServiceId, cardServiceInstance }
			::= { standbyServicesTable 1 }

		
		StandbyServicesEntry ::=
			SEQUENCE { 
				standbyServiceShelf
					Integer32,
				standbyServiceSlot
					Integer32,
				standbyServiceChangeTime
					TimeTicks
			 }

		-- 1.3.6.1.4.1.5504.3.3.4.3.1.1
		standbyServiceShelf OBJECT-TYPE
			SYNTAX Integer32
			MAX-ACCESS read-only
			STATUS current
			DESCRIPTION
				"Identifies the shelf where the standby service is running."
			::= { standbyServicesEntry 1 }

		
		-- 1.3.6.1.4.1.5504.3.3.4.3.1.2
		standbyServiceSlot OBJECT-TYPE
			SYNTAX Integer32
			MAX-ACCESS read-only
			STATUS current
			DESCRIPTION
				"Identifies the slot where the standby service is running."
			::= { standbyServicesEntry 2 }

		
		-- 1.3.6.1.4.1.5504.3.3.4.3.1.3
		standbyServiceChangeTime OBJECT-TYPE
			SYNTAX TimeTicks
			MAX-ACCESS read-only
			STATUS current
			DESCRIPTION
				"Represents the time that service became Standby.
				Value is in system ticks.
				"
			::= { standbyServicesEntry 3 }

		
		-- 1.3.6.1.4.1.5504.3.3.4.4
		zhoneTrapCardServices OBJECT-IDENTITY
			STATUS current
			DESCRIPTION 
				"Traps related to Card Services"
			::= { zhoneCardServices 4 }

		
		-- 1.3.6.1.4.1.5504.3.3.4.4.0
		zhoneTrapCardServicesV2Traps OBJECT-IDENTITY
			STATUS current
			DESCRIPTION 
				"This object identity adds a zero(0) for the next to last
				sub-identifier which should be used for new SNMPv2 Traps."
			::= { zhoneTrapCardServices 0 }

		
		-- 1.3.6.1.4.1.5504.3.3.4.4.0.1
		zhoneCardServicesStatusChange NOTIFICATION-TYPE
			OBJECTS { cardServiceStatus }
			STATUS current
			DESCRIPTION 
				"This trap is generated whenever a redundancy state change occurs."
			::= { zhoneTrapCardServicesV2Traps 1 }

		
		-- 1.3.6.1.4.1.5504.3.3.4.4.0.2
		zhoneCardServicesStandbyReady NOTIFICATION-TYPE
			OBJECTS { standbyServiceShelf, standbyServiceSlot }
			STATUS current
			DESCRIPTION 
				"This trap indicates that all services on the standby card 
				are synchronized with their active couterparts, and that
				the card is fully ready as the standby."
			::= { zhoneTrapCardServicesV2Traps 2 }

		
		-- 1.3.6.1.4.1.5504.3.3.8
		zhoneExternalRelay OBJECT-IDENTITY
			STATUS current
			DESCRIPTION 
				"The following defines the information
				pertinent for external relays."
			::= { zhoneCard 8 }

		
		-- 1.3.6.1.4.1.5504.3.3.8.1
		zhoneExternalRelayTable OBJECT-TYPE
			SYNTAX SEQUENCE OF ZhoneExternalRelayEntry
			MAX-ACCESS not-accessible
			STATUS current
			DESCRIPTION
				"A Table of External Relay Interface status for handling relays  on a card and for the TAC card,this is 
				of 12 Rows."
			::= { zhoneExternalRelay 1 }

		
		-- 1.3.6.1.4.1.5504.3.3.8.1.1
		zhoneExternalRelayEntry OBJECT-TYPE
			SYNTAX ZhoneExternalRelayEntry
			MAX-ACCESS not-accessible
			STATUS current
			DESCRIPTION
				"One entry for each relay on a card."
			INDEX { zhoneShelfIndex, zhoneSlotIndex, zhoneExternalRelayId }
			::= { zhoneExternalRelayTable 1 }

		
		ZhoneExternalRelayEntry ::=
			SEQUENCE { 
				zhoneExternalRelayName
					ZhoneAdminString,
				zhoneExternalRelayState
					INTEGER,
				zhoneExternalRelayNormalState
					INTEGER
			 }

		-- 1.3.6.1.4.1.5504.3.3.8.1.1.1
		zhoneExternalRelayName OBJECT-TYPE
			SYNTAX ZhoneAdminString (SIZE (1..32))
			MAX-ACCESS read-write
			STATUS current
			DESCRIPTION
				"A provisionable name which may used in referring
				to an external relay.
				This  external relay name should be unique on the box.If not set ,
				it defaults to a unique value <relay x/y/z> where 
				x=shelf number, y=slot , and z=relayId.
				
				"
			::= { zhoneExternalRelayEntry 1 }

		
		-- 1.3.6.1.4.1.5504.3.3.8.1.1.2
		zhoneExternalRelayState OBJECT-TYPE
			SYNTAX INTEGER
				{
				relayStateOpen(1),
				relayStateClosed(2)
				}
			MAX-ACCESS read-only
			STATUS current
			DESCRIPTION
				"The object describes the state of the external relays.
				An external relay may have one of two states:
				relayStateOpen(1) indicates that the external relay
				is open or is not connected.
				relayStateClosed(2) indicates that the external relay
				is closed."
			::= { zhoneExternalRelayEntry 2 }

		
		-- 1.3.6.1.4.1.5504.3.3.8.1.1.3
		zhoneExternalRelayNormalState OBJECT-TYPE
			SYNTAX INTEGER
				{
				notSpecified(1),
				normallyOpen(2),
				normallyClosed(3)
				}
			MAX-ACCESS read-write
			STATUS current
			DESCRIPTION
				"Specifies whether relay is normally open or normally closed.
				The other state will then generate an alarm. 
				A value of not-specified is valid for MTAC and 1U cards,
				where alarms are not present in the central alarm manager.
				For the mxk i/o alarm board relays, a value should be 
				present for all relays that are in use."
			DEFVAL { notSpecified }
			::= { zhoneExternalRelayEntry 3 }

		
		-- 1.3.6.1.4.1.5504.3.3.8.2
		zhoneExternalRelayMappingTable OBJECT-TYPE
			SYNTAX SEQUENCE OF ZhoneExternalRelayMappingEntry
			MAX-ACCESS not-accessible
			STATUS current
			DESCRIPTION
				"This table is used to map an external relay name
				to the relay Id. This table contains all entries for relays
				defined in the system. For example, if 2 TAC cards are
				present there will be 24 entries in this table."
			::= { zhoneExternalRelay 2 }

		
		-- 1.3.6.1.4.1.5504.3.3.8.2.1
		zhoneExternalRelayMappingEntry OBJECT-TYPE
			SYNTAX ZhoneExternalRelayMappingEntry
			MAX-ACCESS not-accessible
			STATUS current
			DESCRIPTION
				"One row for each relay."
			INDEX { IMPLIED zhoneExternalRelayName }
			::= { zhoneExternalRelayMappingTable 1 }

		
		ZhoneExternalRelayMappingEntry ::=
			SEQUENCE { 
				zhoneExternalRelayId
					Integer32
			 }

		-- 1.3.6.1.4.1.5504.3.3.8.2.1.1
		zhoneExternalRelayId OBJECT-TYPE
			SYNTAX Integer32 (1..12)
			MAX-ACCESS read-only
			STATUS current
			DESCRIPTION
				"A numeric identifier which identifies the relay."
			::= { zhoneExternalRelayMappingEntry 1 }

		
		-- 1.3.6.1.4.1.5504.3.3.8.3
		zhoneTrapExternalRelay OBJECT-IDENTITY
			STATUS current
			DESCRIPTION 
				"Traps defined for the external relays."
			::= { zhoneExternalRelay 3 }

		
		-- 1.3.6.1.4.1.5504.3.3.8.3.0
		zhoneTrapExternalRelayV2Traps OBJECT-IDENTITY
			STATUS current
			DESCRIPTION 
				"In order to make this a v2 trap (0)."
			::= { zhoneTrapExternalRelay 0 }

		
		-- 1.3.6.1.4.1.5504.3.3.8.3.0.1
		zhoneExternalAlarmTrap NOTIFICATION-TYPE
			OBJECTS { zhoneExternalRelayName, zhoneExternalRelayState }
			STATUS current
			DESCRIPTION 
				"This trap is thrown when the state of an external TAC card
				relay changes."
			::= { zhoneTrapExternalRelayV2Traps 1 }

		
		-- 1.3.6.1.4.1.5504.3.3.8.3.0.2
		zhoneMxkAlarmInputTrap NOTIFICATION-TYPE
			OBJECTS { zhoneExternalRelayName, zhoneExternalRelayState, zhoneExternalRelayNormalState }
			STATUS current
			DESCRIPTION 
				"This trap is thrown when the state of an
				MXK I/O Alarm Card relay changes."
			::= { zhoneTrapExternalRelayV2Traps 2 }

		
		-- 1.3.6.1.4.1.5504.3.3.9
		zhoneCardCompliances OBJECT IDENTIFIER ::= { zhoneCard 9 }

		
		-- 1.3.6.1.4.1.5504.3.3.9.1
		zhoneCardGroups OBJECT IDENTIFIER ::= { zhoneCardCompliances 1 }

		
		-- 1.3.6.1.4.1.5504.3.3.9.1.1
		zhoneCardResourcesGroup OBJECT-GROUP
			OBJECTS { cardIdentification, cardZhoneType, cardMfgSerialNumber, cardMfgCLEICode, cardMfgRevisionCode, 
				cardMfgBootRevision, cardPostResults, cardAdminStatus, cardOperStatus, cardAdminStatsEnable, 
				cardUpTime, cardProcessorType, cardPortStatus, cardInterfaceType, cardSwRunningVers, 
				cardSwUpgradeVers, cardSwAdmin, cardSwStatus, cardPeakMemUsage, cardAvailMem, 
				cardTotalMem, cardProcessorIdle, cardProcessorUsage, cardProcessorServicesUsage, cardProcessorFrameworkUsage, 
				cardProcessorLowUsage, cardProcessorHighUsage, cardMemStatus, cardPweTimingMode }
			STATUS current
			DESCRIPTION 
				"Description."
			::= { zhoneCardGroups 1 }

		
		-- 1.3.6.1.4.1.5504.3.3.9.1.2
		zhoneExternalRelayGroup OBJECT-GROUP
			OBJECTS { zhoneExternalRelayName, zhoneExternalRelayState, zhoneExternalRelayId }
			STATUS current
			DESCRIPTION 
				"This group contains objects associated with the 
				zhone external relay interface."
			::= { zhoneCardGroups 2 }

		
		-- 1.3.6.1.4.1.5504.3.3.9.1.3
		zhoneExternalAlarmTrapGroup NOTIFICATION-GROUP
			NOTIFICATIONS { zhoneExternalAlarmTrap, zhoneMxkAlarmInputTrap }
			STATUS current
			DESCRIPTION 
				"This group contains trap definitions associated with
				the external relays."
			::= { zhoneCardGroups 3 }

		
		-- 1.3.6.1.4.1.5504.3.3.10
		zhoneTrapCardMemV2Traps OBJECT-IDENTITY
			STATUS current
			DESCRIPTION 
				"Memory Trap"
			::= { zhoneCard 10 }

		
		-- 1.3.6.1.4.1.5504.3.3.10.1
		zhoneTrapCardMemGroup NOTIFICATION-GROUP
			NOTIFICATIONS { zhoneTrapCardMemStatus, zhoneTrapProcessorUsage }
			STATUS current
			DESCRIPTION 
				"Memory trap"
			::= { zhoneTrapCardMemV2Traps 1 }

		
		-- 1.3.6.1.4.1.5504.3.3.10.2
		zhoneTrapCardMemStatus NOTIFICATION-TYPE
			OBJECTS { cardMemStatus }
			STATUS current
			DESCRIPTION 
				"Memory notification"
			::= { zhoneTrapCardMemV2Traps 2 }

		
		-- 1.3.6.1.4.1.5504.3.3.10.3
		zhoneTrapProcessorUsage NOTIFICATION-TYPE
			OBJECTS { cardProcessorUsage }
			STATUS current
			DESCRIPTION 
				"Notification sent when CPU Usage crosses a predetermined
				threshold value."
			::= { zhoneTrapCardMemV2Traps 3 }

		
		-- 1.3.6.1.4.1.5504.3.3.11
		zrgResources OBJECT-IDENTITY
			STATUS current
			DESCRIPTION 
				"Description.
				
				The following defines the information
				pertinent for ZRG boards."
			::= { zhoneCard 11 }

		
		-- 1.3.6.1.4.1.5504.3.3.11.1
		zrgBatteryRelayStatus OBJECT-TYPE
			SYNTAX BITS
				{
				normalMode(0),
				batteryON(1),
				batteryLOW(2),
				batteryBAD(3),
				batteryGone(4),
				noUPS(5)
				}
			MAX-ACCESS read-only
			STATUS current
			DESCRIPTION
				"Description.
				
				The object describes the state of the ZRG board power supply.
				The power may have one or two states from the following states:
				
				normalMode(0)  indicates that the load is receiving power from commercial power
				
				batteryON(1)   indicates that the load is receiving power from battery.
				
				batteryLOW(2)  indicates that the battery has been reduced to the point that
				roughly 20% of the available runtime is available.
				
				batteryBAD(3)  indicates that the battery has failed it's periodic test. The
				battery should be replaced as system availability has been compromised.
				
				batteryGone(4) indicates that the battery is disconnected. Load will not be
				supported if the commercial power fails.
				
				noUPS(5)      indicates that the UPS unit is disconnected. Load will not be
				supported if the commercial power fails. "
			::= { zrgResources 1 }

		
		-- 1.3.6.1.4.1.5504.3.3.11.2
		zrgTrapBatteryRelay OBJECT-IDENTITY
			STATUS current
			DESCRIPTION 
				"Traps defined for the ZRG power source/state."
			::= { zrgResources 2 }

		
		-- 1.3.6.1.4.1.5504.3.3.11.2.0
		zrgBatterRelayTrapV2 OBJECT-IDENTITY
			STATUS current
			DESCRIPTION 
				"In order to make this a v2 trap (0)."
			::= { zrgTrapBatteryRelay 0 }

		
		-- 1.3.6.1.4.1.5504.3.3.11.2.0.1
		zrgBatteryRelayNotification NOTIFICATION-TYPE
			OBJECTS { zrgBatteryRelayStatus }
			STATUS current
			DESCRIPTION 
				"Description."
			::= { zrgBatterRelayTrapV2 1 }

		
		-- 1.3.6.1.4.1.5504.3.3.14
		znidResources OBJECT-IDENTITY
			STATUS current
			DESCRIPTION 
				"ZNID Resources."
			::= { zhoneCard 14 }

		
		-- 1.3.6.1.4.1.5504.3.3.14.1
		znidBatteryStatus OBJECT-TYPE
			SYNTAX BITS
				{
				normal(0),
				onBatteryPower(1),
				batteryPowerLow(2),
				replaceBattery(3),
				batteryRemoved(4),
				noUPS(5)
				}
			MAX-ACCESS accessible-for-notify
			STATUS current
			DESCRIPTION
				"ZNID Battery Status object used for notification reporting."
			::= { znidResources 1 }

		
		-- 1.3.6.1.4.1.5504.3.3.14.2
		znidSerialNumber OBJECT-TYPE
			SYNTAX Unsigned32
			MAX-ACCESS accessible-for-notify
			STATUS current
			DESCRIPTION
				"ZNID Battery Status object used for notification reporting."
			::= { znidResources 2 }

		
		-- 1.3.6.1.4.1.5504.3.3.14.3
		znidNotificationObjects OBJECT-IDENTITY
			STATUS current
			DESCRIPTION 
				"ZNID notification objects."
			::= { znidResources 3 }

		
		-- 1.3.6.1.4.1.5504.3.3.14.3.0
		znidNotifications OBJECT-IDENTITY
			STATUS current
			DESCRIPTION 
				"ZNID notifications."
			::= { znidNotificationObjects 0 }

		
		-- 1.3.6.1.4.1.5504.3.3.14.3.0.1
		znidBatteryStatusNotification NOTIFICATION-TYPE
			OBJECTS { znidSerialNumber, znidBatteryStatus }
			STATUS current
			DESCRIPTION 
				"ZNID battery status notification."
			::= { znidNotifications 1 }

		
		-- 1.3.6.1.4.1.5504.3.3.14.3.1
		znidNotificationGroup NOTIFICATION-GROUP
			NOTIFICATIONS { znidBatteryStatusNotification }
			STATUS current
			DESCRIPTION 
				"ZNID notification group."
			::= { znidNotificationObjects 1 }

		
		-- 1.3.6.1.4.1.5504.3.3.14.3.2
		znidOjectGroup OBJECT-GROUP
			OBJECTS { znidBatteryStatus, znidSerialNumber }
			STATUS current
			DESCRIPTION 
				"ZNID object group."
			::= { znidNotificationObjects 2 }

		
	
	END

--
-- genCardResources.mib
--
