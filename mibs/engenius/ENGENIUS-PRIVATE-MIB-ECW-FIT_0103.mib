ENGENIUS-PRIVATE-MIB-ECW-SECRIAL-AP DEFINITIONS ::= BEGIN

IMPORTS
	MODULE-IDENTITY, OBJECT-TYPE, NOTIFICATION-TYPE, OBJECT-IDENTITY, 
	enterprises, snmpModules, IpAddress, Counter32, Gauge32, TimeTicks, Integer32,
	Counter64                                              
            	FROM SNMPv2-SMI
                                                   
	DisplayString, MacAddress, TruthValue, TimeStamp,
	TimeInterval, DateAndTime, RowStatus, TEXTUAL-CONVENTION
				FROM SNMPv2-TC

	MODULE-COMPLIANCE, OBJECT-GROUP, NOTIFICATION-GROUP
				FROM SNMPv2-CONF

	ifIndex
				FROM RFC1213-MIB
        
	InetAddressType, InetAddress 
				FROM INET-ADDRESS-MIB;    
		  
engeniusprivate MODULE-IDENTITY
    LAST-UPDATED "202212151007Z"
    ORGANIZATION "R&D Dept., S/W Division"
    CONTACT-INFO
       "
       "
   DESCRIPTION
       "
       "
    REVISION        "200906111100Z"
    DESCRIPTION	    "Added new parameter: modelname,rf power, macadd, rssi"
    REVISION        "200906101600Z"
    DESCRIPTION	    "Simplified version, remove unsupported item, added ipaddress type, added reboot cmd"
    REVISION        "200905141000Z"
    DESCRIPTION	    "First version of Engenius-Private-MIB"
    REVISION        "201111171030Z"
    DESCRIPTION	    "v1.0.8.2 of Engenius-Private-MIB"
    REVISION        "201112131030Z"
    DESCRIPTION	    "v1.0.9 of Engenius-Private-MIB"
    REVISION        "201312131642Z"
    DESCRIPTION	    "v2.0.0 of Engenius-Private-MIB"
   ::= { engenius 9 }

engenius				OBJECT IDENTIFIER ::= { enterprises 14125 }

sys			OBJECT IDENTIFIER ::= { engeniusprivate 1 }
    sys_info			        OBJECT IDENTIFIER ::= { sys 1 }
    --login                       OBJECT IDENTIFIER ::= { sys 2 }
    snmp                        OBJECT IDENTIFIER ::= { sys 3 }


net		OBJECT IDENTIFIER ::= { engeniusprivate 2 }
    ethernet				OBJECT IDENTIFIER ::= { net 1 }
        ipv4            OBJECT IDENTIFIER ::= { ethernet 2 }
        ipv6            OBJECT IDENTIFIER ::= { ethernet 3 }
    stp				OBJECT IDENTIFIER ::= { net 2 }

--ntp				OBJECT IDENTIFIER ::= { configuration 6 }

wifi		OBJECT IDENTIFIER ::= { engeniusprivate 3 }
    radio       OBJECT IDENTIFIER ::= { wifi 1 }
	    twoG	OBJECT IDENTIFIER ::= { radio 1 }
        fiveG              OBJECT IDENTIFIER ::= { radio 2 }
    ssid        OBJECT IDENTIFIER ::= { wifi 2 }
        wireless_security   OBJECT IDENTIFIER ::= { ssid 4 }
        schedule            OBJECT IDENTIFIER ::= { ssid 7 }
        

    client_info OBJECT IDENTIFIER ::= { wifi 3 }
        client_24g            OBJECT IDENTIFIER ::={ client_info 1 }
        client_5g              OBJECT IDENTIFIER ::={ client_info 2 }

snmpMIB                 OBJECT IDENTIFIER ::= { snmpModules 1 }
    snmpMIBObjects          OBJECT IDENTIFIER ::= { snmpMIB 1 }
        snmpTraps                OBJECT IDENTIFIER ::= { snmpMIBObjects 5 }


-- ==========================
-- Defination Begins
-- ==========================

-- =======| status > system | ===============

firmware_version OBJECT-TYPE
	  SYNTAX DisplayString (SIZE (0..256))
	  MAX-ACCESS read-only
	  STATUS current
	  DESCRIPTION
	  "Firmware model name"
     ::= { sys_info 1 }	


serial_number OBJECT-TYPE
	   SYNTAX DisplayString
	   MAX-ACCESS read-only
	   STATUS current
	   DESCRIPTION
	   ""
	   ::={ sys_info 2 }

uptime OBJECT-TYPE
	   SYNTAX DisplayString
	   MAX-ACCESS read-only
	   STATUS current
	   DESCRIPTION
	   ""
      ::={ sys_info 3 }	 

device_name OBJECT-TYPE
	SYNTAX DisplayString (SIZE (0..32))
  	MAX-ACCESS read-only
     	STATUS current
     	DESCRIPTION
	"The DUT's device name."
	DEFVAL { "EnGenius SERIAL AP" }
     ::= { sys_info 4 }

mac_address OBJECT-TYPE
	   SYNTAX DisplayString (SIZE(0..17))
	   MAX-ACCESS read-only
	   STATUS current
	   DESCRIPTION
	   "The wireless MAC address"
      ::={ sys_info 5 }

mac_24g_address OBJECT-TYPE
	   SYNTAX DisplayString (SIZE(0..17))
	   MAX-ACCESS read-only
	   STATUS current
	   DESCRIPTION
	   "The wireless 2_4G MAC address"
      ::={ sys_info 6 }

mac_5g_address OBJECT-TYPE
	   SYNTAX DisplayString (SIZE(0..17))
	   MAX-ACCESS read-only
	   STATUS current
	   DESCRIPTION
	   "The wireless 5G MAC address"
      ::={ sys_info 7 }
      
mac_6g_address OBJECT-TYPE
	   SYNTAX DisplayString (SIZE(0..17))
	   MAX-ACCESS read-only
	   STATUS current
	   DESCRIPTION
	   "The wireless 6G MAC address"
      ::={ sys_info 8 }

-- login is for post. need to comfirm.

cpu_loading OBJECT-TYPE
	   SYNTAX DisplayString
	   MAX-ACCESS read-only
	   STATUS current
	   DESCRIPTION
	   ""
	   ::={ sys_info 9 }

mem_usage OBJECT-TYPE
	   SYNTAX DisplayString
	   MAX-ACCESS read-only
	   STATUS current
	   DESCRIPTION
	   ""
	   ::={ sys_info 10 }

-- =======| configuration > ntp | ===============

timezone OBJECT-TYPE
	SYNTAX DisplayString (SIZE (0..128))
	MAX-ACCESS read-only
	STATUS current
	DESCRIPTION
	"To setting time zone in DUT:
		zone name (timezone)
		UTC-12:00 Kwajalein (UTC12), 
		UTC-11:00 Midway-Island, Samoa (UTC11),
		UTC-10:00 Hawaii (UTC10),
		UTC-09:00 Alaska (NAST9),
		UTC-08:00 Pacific-Time (PST8),
		UTC-07:00 Arizona (UTC7),  
		UTC-07:00 Mountain-Time (MST7),
		UTC-06:00 Mexico (UTC6),
		UTC-06:00 Central-Time (CST6),
		UTC-05:00 Colombia, Panama (UTC5),
		UTC-05:00 Eastern-Time (EST5),
		UTC-04:00 Bolivia, Venezuela (UTC4),
		UTC-04:00 Atlantic-Time (AST4),
		UTC-04:00 Brazil-West (BRWST4),
		UTC-03:30 Newfoundland (NST3:30),
		UTC-03:00 Greenland (WGST3),
		UTC-03:00 Brazil-East (BRST3),
		UTC-03:00 Guyana (UTC3),
		UTC-02:00 Mid-Atlantic (UTC2),
		UTC-01:00 Azores (STD1),
		UTC+00:00 Gambia, Liberia, Morocco (UTC0),
		UTC+00:00 England (GMT0),
		UTC+01:00 Tunisia (UTC-1),
		UTC+01:00 France, Germany, Italy (STD-1),
		UTC+02:00 South-Africa (UTC-2),
		UTC+02:00 Greece, Ukraine, Romania, Turkey (STD-2),
		UTC+03:00 Iraq, Jordan, Kuwait (UTC-3),
		UTC+03:00 Finland (EEST-3),
		UTC+04:00 Armenia (UTC-4),
		UTC+05:00 Pakistan, Russia (UTC-5),
		UTC+05:30 Bombay, Calcutta, Madras, New-Delhi (UTC-5:30),
		UTC+06:00 Bangladesh, Russia (UTC-6), 
		UTC+07:00 Thailand, Russia (UTC-7), 
		UTC+08:00 China, Hong-Kong, Western-Australia, Singapore, Taiwan, Russia (UTC-8),
		UTC+09:00 Japan, Korea (UTC-9),
		UTC+09:30 South-Australia (CST-9:30),
		UTC+10:00 Guam, Russia (UTC-10),
		UTC+10:00 Australia (STD-10),
		UTC+11:00 Solomon-Islands (UTC-11),
		UTC+12:00 Fiji (UTC-12),
		UTC+12:00 New-Zealand (NZST-12)"
	DEFVAL { "GMT0" }
     ::= { sys_info 11 }

-- ============== Time Zone END ===========================



-- =======| configuration > snmp | ===============

enable OBJECT-TYPE
	SYNTAX DisplayString
	MAX-ACCESS read-only
	STATUS current
	DESCRIPTION
	"Enable / Disable SNMP agent"
	DEFVAL { Enable }
	::= { snmp 1 }

community OBJECT-TYPE
	SYNTAX DisplayString (SIZE(0..33))
	MAX-ACCESS read-only
	STATUS current
	DESCRIPTION
	"The communication string for Read Only"
	DEFVAL { public }
	::= { snmp 2 }

-- ============== END ===========================

-- =======| net > ethernet | ===============

mode OBJECT-TYPE
	SYNTAX DisplayString
    MAX-ACCESS read-only
    STATUS current
    DESCRIPTION
    "IP Network Setting"
    DEFVAL { "DHCP" }
    ::= { ethernet 1 }

ip OBJECT-TYPE
	SYNTAX DisplayString
	MAX-ACCESS read-only
	STATUS current
	DESCRIPTION
	"To setting static LAN IP address in DUT"
	DEFVAL { "192.168.1.1" }
     ::= { ipv4 1 }

mask OBJECT-TYPE
	SYNTAX DisplayString
	MAX-ACCESS read-only
	STATUS current
	DESCRIPTION
	"To setting static Subnet Mask in DUT"
	DEFVAL { "255.255.255.0" }
     ::= { ipv4 2 }

gateway OBJECT-TYPE
	SYNTAX DisplayString
	MAX-ACCESS read-only
	STATUS current
	DESCRIPTION
	"To setting getway IP address in DUT"
	DEFVAL { "0.0.0.0" }
     ::= { ipv4 3 }

primary_dns OBJECT-TYPE
	SYNTAX DisplayString
	MAX-ACCESS read-only
	STATUS current
	DESCRIPTION
	"To setting Primary DNS IP address in DUT"
	DEFVAL { "0.0.0.0" }
     ::= { ipv4 4 }
	 
secondary_dns OBJECT-TYPE
	SYNTAX DisplayString
	MAX-ACCESS read-only
	STATUS current
	DESCRIPTION
	"To setting SecondaryDNS IP address in DUT"
	DEFVAL { "0.0.0.0" }
     ::= { ipv4 5 }

linkLocal OBJECT-TYPE
	SYNTAX DisplayString
	MAX-ACCESS read-only
	STATUS current
	DESCRIPTION
	""
	DEFVAL { "true" }
     ::= { ipv6 1 }

ip OBJECT-TYPE
	SYNTAX DisplayString
	MAX-ACCESS read-only
	STATUS current
	DESCRIPTION
	"To setting static Ipv6 address in DUT"
	--DEFVAL { "255.255.255.0" }
     ::= { ipv6 2 }

prefix OBJECT-TYPE
	SYNTAX DisplayString
	MAX-ACCESS read-only
	STATUS current
	DESCRIPTION
	"To setting IPv6 prefix in DUT"
	DEFVAL { "0" }
     ::= { ipv6 3 }

gateway OBJECT-TYPE
	SYNTAX DisplayString
	MAX-ACCESS read-only
	STATUS current
	DESCRIPTION
	"To setting IPv6 gateway IP address in DUT"
	--DEFVAL { "0.0.0.0" }
     ::= { ipv6 4 }
	 
primary_dns OBJECT-TYPE
	SYNTAX DisplayString
	MAX-ACCESS read-only
	STATUS current
	DESCRIPTION
	"To setting IPv6 Primary DNS IP address in DUT"
	-- DEFVAL { "0.0.0.0" }
     ::= { ipv6 5 }

secondary_dns OBJECT-TYPE
	SYNTAX DisplayString
	MAX-ACCESS read-only
	STATUS current
	DESCRIPTION
	"To setting IPv6 Secondary DNS IP address in DUT"
	-- DEFVAL { "0.0.0.0" }
     ::= { ipv6 6 }
	 
-- ============== END ================================

-- =======| net > stp | ===============

mgmt_vlanid OBJECT-TYPE
    SYNTAX DisplayString
    MAX-ACCESS read-only
    STATUS current
    DESCRIPTION
    "Dispaly Management VLAN ID"
    ::= { ethernet 4 }

mode OBJECT-TYPE
	SYNTAX DisplayString
	MAX-ACCESS read-only
	STATUS current
	DESCRIPTION
	"Enable / Disable Spanning Tree"
	DEFVAL { Disable }
	::= { stp 1 }

priority OBJECT-TYPE
	SYNTAX Integer32 (0..65535)
	MAX-ACCESS read-only
	STATUS current
	DESCRIPTION
	"The manageable component of the Port Identifier. IEEE 802.1D 17.13.10.
    Minimum: 0. Maximum: 65535."
	DEFVAL { 32768 }
	::= { stp 2 }

-- ============== END ===========================

-- =======| wifi > radio > 24g | ===============

enable OBJECT-TYPE
    SYNTAX DisplayString
    MAX-ACCESS read-only
    STATUS current
    DESCRIPTION
    "Enable/ Disable 2_4G wireless lan band"
    ::= { twoG 1 }

country OBJECT-TYPE
	SYNTAX DisplayString
	MAX-ACCESS read-only
	STATUS current
	DESCRIPTION
	"The country name. 
	The supported country ID as follows,
	FCC : {0,3,11,12,14,15,19,20,27,29,45,46,54,55,59,71,81,83}
	ETSI : {0,1,5,7,10,16,17,18,22,23,24,25,26,30,31,34,37,43,47,49,50,57,58,61,62,64,65,67,69,70,77,78,79}
	INT : all
        na (0),
		albania (1),
		algeria (2),
		argentina (3),
		australia (4),
		austria (5),
		bahrain (6),
		belgium (7),
		brazil (8),
		brunei (9),
		bulgaria (10),
		canada (11),
		chile (12),
		china (13),
		colombia (14),
		costa-Rica (15),
		croatia (16),
		czech-Republic (17),
		denmark (18),
		dominican-Republic (19),
		ecuador (20),
		egypt (21),
		estonia (22),
		finland (23),
		france (24),
		germany (25),
		greece (26),
		guatemala (27),
		honduras (28),
		hong-Kong (29),
		hungary (30),
		iceland (31),
		india (32),
		indonesia (33),
		ireland (34),
		iran (35),
		israel (36),
		italy (37),
		japan (38),
		jordan (39),
		south-Korea (40),
		kuwait (41),
		lebanon (42),
		luxembourg (43),
		macau (44),
		malaysia (45),
		mexico (46),
		monaco (47),
		nepal (48),
		netherlands (49),
		norway (50),
		new-Zealand (51),
		oman (52),
		pakistan (53),
		panama (54),
		peru (55),
		philippines (56),
		poland (57),
		portugal (58),
		puerto-Rico (59),
		qatar (60),
		romania (61),
		russia (62),
		saudi-Arabia (63),
		singapore (64),
		slovakia (65),
		slovenia (66),
		south-Africa (67),
		spain (68),
		sri-Lanka (69),
		sweden (70),
		switzerland (71),
		taiwan (72),
		thailand (73),
		tunisia (74),
		turkey (75),
		united-Arab-Emirates (76),
		ukraine (77),
		united-Kingdom (78),
		united-Kingdom-B (79),
		united-Kingdom-C (80),
		uruguay (81),
		usa (82),
		uzbekistan (83),
		venezuela (84),
		vietnam (85)"
	DEFVAL { na }
     ::= { twoG 2 }


hw_mode OBJECT-TYPE
	SYNTAX DisplayString
	MAX-ACCESS read-only
	STATUS current
	DESCRIPTION
	"The wireless lan operation mode. 
    {11b, 11g, 11bg, 11n, 11ng, 11axg}"
	DEFVAL { bgn_Mixed}
	::= { twoG 3 }

is_11ax_disable OBJECT-TYPE
    SYNTAX DisplayString
    MAX-ACCESS read-only
    STATUS current
    DESCRIPTION
    "Eblae / Disable 11ax mode"
    ::= { twoG 4 }

channel OBJECT-TYPE
	SYNTAX Integer32 (0..13)
	MAX-ACCESS read-only
	STATUS current
	DESCRIPTION
	"The wireless 2.4G channel frequency. Minimum: 0. Maximum: 14. 0 is auto"
     ::= { twoG 5 }


ht_mode OBJECT-TYPE
	SYNTAX DisplayString
	MAX-ACCESS read-only
	STATUS current
	DESCRIPTION
	"The WLAN narrow band
    {HT20, HT20_40, HT40}"
	::= { twoG 6 }


tx_power OBJECT-TYPE
	SYNTAX Integer32 (8..28)
	MAX-ACCESS read-only
	STATUS current
	DESCRIPTION
	"The WLAN transmission power. Minimum: 8. Maximum: 28. 0 is auto" 
        ::= { twoG 7 }

--clientlimit2point4GEnable OBJECT-TYPE
	--SYNTAX DisplayString
    --MAX-ACCESS read-only
    --STATUS current
    --DESCRIPTION
    --"Enable / Disable client limit function"
    --DEFVAL { Enable }
    --::= { clientLimit 1 }

client_limit OBJECT-TYPE
	SYNTAX DisplayString
	MAX-ACCESS read-only
	STATUS current
	DESCRIPTION
	"Max number of client"
    ::= { twoG 8 }

--clientlimit5GEnable OBJECT-TYPE
	--SYNTAX DisplayString
    --MAX-ACCESS read-only
    --STATUS current
    --DESCRIPTION
    --"Enable / Disable client limit function"
    --DEFVAL { Enable }
    --::= { clientLimit 3 }


min_bitrate OBJECT-TYPE
    SYNTAX DisplayString
    MAX-ACCESS read-only
    STATUS current
    DESCRIPTION
    "The WLAN minimum bit rate"
    ::= { twoG 9 }

opmode OBJECT-TYPE
	SYNTAX DisplayString
	MAX-ACCESS read-only
	STATUS current
	DESCRIPTION
	"The WLAN operation mode.
    {ap, wds_ap, wds_bridge, wds_sta, sta_ap, sta}"
	DEFVAL { ap }
	::= { twoG 10 }

legacy_hwmode_deny OBJECT-TYPE
    SYNTAX DisplayString
    MAX-ACCESS read-only
    STATUS current
    DESCRIPTION
    ""
    ::= { twoG 11 }

channel_list OBJECT-TYPE	
    SYNTAX DisplayString
   	MAX-ACCESS read-only
    STATUS current
    DESCRIPTION
	"Show channel list that control by CountryCode."
	::= { twoG 20 }


-- ============== wifi > radio > fiveG =============

enable OBJECT-TYPE
    SYNTAX DisplayString
    MAX-ACCESS read-only
    STATUS current
    DESCRIPTION
    "Enable/ Disable 5G wireless lan band"
    ::= { fiveG 1 }

country OBJECT-TYPE
    SYNTAX DisplayString
    MAX-ACCESS read-only
	STATUS current
	DESCRIPTION
	"The country name.Please enter the value from 0~84. 
	The supported country ID as follows,
	FCC : {0,3,11,12,14,15,19,20,27,29,45,46,54,55,59,71,81,83}
	ETSI : {0,1,5,7,10,16,17,18,22,23,24,25,26,30,31,34,37,43,47,49,50,57,58,61,62,64,65,67,69,70,77,78,79}
	INT : all
        na (0),
		albania (1),
		algeria (2),
		argentina (3),
		australia (4),
		austria (5),
		bahrain (6),
		belgium (7),
		brazil (8),
		brunei (9),
		bulgaria (10),
		canada (11),
		chile (12),
		china (13),
		colombia (14),
		costa-Rica (15),
		croatia (16),
		czech-Republic (17),
		denmark (18),
		dominican-Republic (19),
		ecuador (20),
		egypt (21),
		estonia (22),
		finland (23),
		france (24),
		germany (25),
		greece (26),
		guatemala (27),
		honduras (28),
		hong-Kong (29),
		hungary (30),
		iceland (31),
		india (32),
		indonesia (33),
		ireland (34),
		iran (35),
		israel (36),
		italy (37),
		japan (38),
		jordan (39),
		south-Korea (40),
		kuwait (41),
		lebanon (42),
		luxembourg (43),
		macau (44),
		malaysia (45),
		mexico (46),
		monaco (47),
		nepal (48),
		netherlands (49),
		norway (50),
		new-Zealand (51),
		oman (52),
		pakistan (53),
		panama (54),
		peru (55),
		philippines (56),
		poland (57),
		portugal (58),
		puerto-Rico (59),
		qatar (60),
		romania (61),
		russia (62),
		saudi-Arabia (63),
		singapore (64),
		slovakia (65),
		slovenia (66),
		south-Africa (67),
		spain (68),
		sri-Lanka (69),
		sweden (70),
		switzerland (71),
		taiwan (72),
		thailand (73),
		tunisia (74),
		turkey (75),
		united-Arab-Emirates (76),
		ukraine (77),
		united-Kingdom (78),
		united-Kingdom-B (79),
		united-Kingdom-C (80),
		uruguay (81),
		usa (82),
		uzbekistan (83),
		venezuela (84),
		vietnam (85)"
	DEFVAL { na }
     ::= { fiveG 2 }


hw_mode OBJECT-TYPE
	SYNTAX DisplayString
	MAX-ACCESS read-only
	STATUS current
	DESCRIPTION
	"The wireless lan operation mode.
    { 11a, 11n, 11na, 11ac, 11axa }"
	DEFVAL { "11axa" }
	::= { fiveG 3 }

is_11ax_disable OBJECT-TYPE
    SYNTAX DisplayString
    MAX-ACCESS read-only
    STATUS current
    DESCRIPTION
    "Eblae / Disable 11ax mode"
    ::= { fiveG 4 }

channel OBJECT-TYPE
	SYNTAX Integer32 (36..173)
	MAX-ACCESS read-only
	STATUS current
	DESCRIPTION
	"The wireless 5G channel frequency. Specific Value. 0 is auto"
     ::= { fiveG 5 }


ht_mode OBJECT-TYPE
	SYNTAX DisplayString
	MAX-ACCESS read-only
	STATUS current
	DESCRIPTION
	"The WLAN narrow band.
    {HT20, HT40, HT80}"
	DEFVAL { HT80}
	::= { fiveG 6 }

tx_power OBJECT-TYPE
	SYNTAX Integer32 (8..28)
	MAX-ACCESS read-only
	STATUS current
	DESCRIPTION
	"The WLAN transmission power. 
    Minimum: 8. Maximum: 28."     
	--DEFVAL { 20 }
    ::= { fiveG 7 }

client_limit OBJECT-TYPE
	SYNTAX Integer32
	MAX-ACCESS read-only
	STATUS current
	DESCRIPTION
	"Max number of client"
    ::= { fiveG 8 }	

min_bitrate OBJECT-TYPE
    SYNTAX DisplayString
    MAX-ACCESS read-only
    STATUS current
    DESCRIPTION
    "The WLAN minimum bit rate"
    ::= { fiveG 9 }

opmode OBJECT-TYPE
	SYNTAX DisplayString
	MAX-ACCESS read-only
	STATUS current
	DESCRIPTION
	"The WLAN operation mode.
    {ap, wds_ap, wds_bridge, wds_sta, sta_ap, sta}"
	DEFVAL { ap }
	::= { fiveG 10 }

auto_channel_exclude_dfs OBJECT-TYPE
    SYNTAX DisplayString
    MAX-ACCESS read-only
    STATUS current
    DESCRIPTION
    ""
    ::= { fiveG 11 }

legacy_hwmode_deny OBJECT-TYPE
    SYNTAX DisplayString
    MAX-ACCESS read-only
    STATUS current
    DESCRIPTION
    ""
    ::= { fiveG 12 }


channel_list OBJECT-TYPE	
    SYNTAX DisplayString
   	MAX-ACCESS read-only
    STATUS current
    DESCRIPTION
	"Show channel list that control by CountryCode."
	::= { fiveG 20 } 


-- ============== Wlan table ================

ssid_table OBJECT-TYPE
    SYNTAX SEQUENCE OF ssid_Entry
    MAX-ACCESS not-accessible
    STATUS current
    DESCRIPTION
    ""
    ::={ ssid 1 }


ssid_entry OBJECT-TYPE
    	SYNTAX ssid_Entry
		MAX-ACCESS not-accessible
    	STATUS current
    	DESCRIPTION
	"Represent the entry in the ssid table."
        INDEX { enable }
    ::= { ssid_table 1 }

ssid_Entry::=
    SEQUENCE 
    {
        enable          DisplayString,
        enable_bands    DisplayString,
        ssid_name       DisplayString,
        hidden_ssid     DisplayString,
        client_isolation DisplayString,
        vlan_isolation  DisplayString,
        vlan_id         DisplayString
    }

enable OBJECT-TYPE
    SYNTAX DisplayString
    MAX-ACCESS read-only
    STATUS current
    DESCRIPTION
	"SSID Enable / Disable"
    ::= { ssid_entry 1 }

enable_bands OBJECT-TYPE
    SYNTAX DisplayString
    MAX-ACCESS read-only
    STATUS current
    DESCRIPTION
    "WLAN Available bands.
    {2.4G, 5G, 6G}"
    ::={ ssid_entry 2 }

ssid_name OBJECT-TYPE
	SYNTAX DisplayString (SIZE(1..32))
	MAX-ACCESS read-only
    	STATUS current
    	DESCRIPTION
	"The WLAN SSID"
    ::= { ssid_entry 3 }

hidden_ssid OBJECT-TYPE
    SYNTAX DisplayString
    MAX-ACCESS read-only
    STATUS current
    DESCRIPTION
	"Enable / Disable broadcast SSID"
    ::= { ssid_entry 4 }

client_isolation OBJECT-TYPE
    SYNTAX DisplayString
    MAX-ACCESS read-only
    STATUS current
    DESCRIPTION
	"Enable / Disable broadcast SSID"
    ::= { ssid_entry 5 }


vlan_isolation OBJECT-TYPE
    SYNTAX DisplayString
    MAX-ACCESS read-only
    STATUS current
    DESCRIPTION
    "Enable / Disable vlan isolation"
    ::={ ssid_entry 6 }

vlan_id OBJECT-TYPE
    SYNTAX DisplayString
    MAX-ACCESS read-only
    STATUS current
    DESCRIPTION
	"The WLAN interface VLAN ID"
    ::= { ssid_entry 7 }

bandsteering_table OBJECT-TYPE
    	SYNTAX SEQUENCE OF BandEntry
		MAX-ACCESS not-accessible
    	STATUS current
    	DESCRIPTION
	"Represent the entry in the ssid table."
    ::= { ssid 2 }

bandsteering_entry OBJECT-TYPE
    SYNTAX BandEntry
    MAX-ACCESS not-accessible
    STATUS current
    DESCRIPTION
    "Represent the entry in the band_steering"
    INDEX { enable }
    ::= { bandsteering_table 1 }

BandEntry ::=
    SEQUENCE
    {     
        enable	DisplayString,
        steering_type          DisplayString,
	    fiveG_rssi_threshold 	DisplayString
    }

enable OBJECT-TYPE
    SYNTAX DisplayString
    MAX-ACCESS read-only
    STATUS current
    DESCRIPTION
        "Enable / Disable band steering function"
    DEFVAL { disable }
    ::= { bandsteering_entry 1 }

steering_type OBJECT-TYPE
    SYNTAX DisplayString
    MAX-ACCESS read-only
    STATUS current
    DESCRIPTION
    "BandSteering Type"
    ::= { bandsteering_entry 2 }

fiveG_rssi_threshold OBJECT-TYPE
    SYNTAX DisplayString
    MAX-ACCESS read-only
    STATUS current
    DESCRIPTION
        "Set 5GHz RSSI Threshold in -80~-60 dBm."
    ::= { bandsteering_entry 3 }

security_table OBJECT-TYPE
    SYNTAX SEQUENCE OF securityEntry
    MAX-ACCESS not-accessible
    STATUS current
    DESCRIPTION
    "The Table for Wireless Security."
    ::= { wireless_security 1 }

security_entry  OBJECT-TYPE
    SYNTAX securityEntry
    MAX-ACCESS not-accessible
    STATUS current
    DESCRIPTION
    "The entry for wiree securtiy table"
    INDEX { encryption }
    ::= { security_table 1 }

securityEntry ::=
SEQUENCE
{
    encryption      DisplayString,
    auth_type       DisplayString,
    suiteb_192bits  DisplayString,
    ieee80211w      DisplayString,
    key_interval    DisplayString,
    nasId_enable    DisplayString,
    nasId           DisplayString,
    nasIp_enable    DisplayString,
    nasIp           DisplayString,
    nasPort_enable  DisplayString,
    nasPort         DisplayString,
    fast_roaming    DisplayString
}


encryption OBJECT-TYPE
    SYNTAX DisplayString
    MAX-ACCESS read-only
    STATUS current
    DESCRIPTION
	"The WLAN encryption type.
    Disable,
    WPA2-PSK,
    WPA2-Enterprise,
    OWE,
    WPA3-SAE,
    WPA3-SAE-Mixed,
    WPA3-Enterprise,
    WPA3-Mixed-Enterprise."
	::= { security_entry 1 }

auth_type OBJECT-TYPE
    SYNTAX DisplayString
    MAX-ACCESS read-only
    STATUS current
    DESCRIPTION
    "The WLAN authentication type.
    { TKIP, AES, BOTH }"
    ::= { security_entry 2 }


suiteb_192bits OBJECT-TYPE
    SYNTAX DisplayString
    MAX-ACCESS read-only
    STATUS current
    DESCRIPTION
    ""
    ::= { security_entry 4 }

ieee80211w OBJECT-TYPE
    SYNTAX DisplayString
    MAX-ACCESS read-only
    STATUS current
    DESCRIPTION
    ""
    ::= { security_entry 5 }

key_interval OBJECT-TYPE
    SYNTAX DisplayString
    MAX-ACCESS read-only
    STATUS current
    DESCRIPTION
    ""
    ::= { security_entry 6 }

nasId_enable OBJECT-TYPE
    SYNTAX DisplayString
    MAX-ACCESS read-only
    STATUS current
    DESCRIPTION
    ""
    ::= { security_entry 7 }

nasId OBJECT-TYPE
    SYNTAX DisplayString
    MAX-ACCESS read-only
    STATUS current
    DESCRIPTION
    ""
    ::= { security_entry 8 }

nasIp_enable OBJECT-TYPE
    SYNTAX DisplayString
    MAX-ACCESS read-only
    STATUS current
    DESCRIPTION
    ""
    ::= { security_entry 9 }

nasIp OBJECT-TYPE
    SYNTAX DisplayString
    MAX-ACCESS read-only
    STATUS current
    DESCRIPTION
    ""
    ::= { security_entry 10 }

nasPort_enable OBJECT-TYPE
    SYNTAX DisplayString
    MAX-ACCESS read-only
    STATUS current
    DESCRIPTION
    ""
    ::= { security_entry 11 }

nasPort OBJECT-TYPE
    SYNTAX DisplayString
    MAX-ACCESS read-only
    STATUS current
    DESCRIPTION
    ""
    ::= { security_entry 12 }

wpa_table OBJECT-TYPE
    SYNTAX SEQUENCE OF WPAEntry
    MAX-ACCESS read-only
    STATUS current
    DESCRIPTION
    "The Table for WPA"
    ::= { wireless_security 2 }

wpa_entry OBJECT-TYPE
    SYNTAX WPAEntry
    MAX-ACCESS read-only
    STATUS current
    DESCRIPTION
    "The Entry of WPA table."
    INDEX { passpharse }
    ::= { wpa_table 1 }

WPAEntry ::=
SEQUENCE
{
    passpharse      DisplayString,
    radius_mac_auth DisplayString
}

passpharse OBJECT-TYPE
    SYNTAX DisplayString
    MAX-ACCESS read-only
    STATUS current
    DESCRIPTION
    "The WLAN WPA Key combination.
    Display ******** if no passpharse setted."
    ::= { wpa_entry 1 }

radius_mac_auth OBJECT-TYPE
    SYNTAX DisplayString
    MAX-ACCESS read-only
    STATUS current
    DESCRIPTION
    ""
    ::= { wpa_entry 2 }

fast_roaming OBJECT-TYPE
    SYNTAX DisplayString
    MAX-ACCESS read-only
    STATUS current
    DESCRIPTION
    ""
    ::= { security_entry 14 }

radius_server_table OBJECT-TYPE
    SYNTAX SEQUENCE OF radius_serverEntry
    MAX-ACCESS read-only
    STATUS current
    DESCRIPTION
    "The table for radius server"
    ::={ wireless_security 3 }

radius_server_entry OBJECT-TYPE
    SYNTAX radius_serverEntry
    MAX-ACCESS read-only
    STATUS current
    DESCRIPTION
    "The entry for the radius server"
    INDEX { server_type }
    ::= { radius_server_table 1 }

radius_serverEntry ::=
SEQUENCE
{
    server_type         DisplayString,
    auth_type           DisplayString,
    server1Ip           IpAddress,
    server1Port         Integer32,
    server1Secret       DisplayString,
    server2Ip           IpAddress,
    server2Port         Integer32,
    server2Secret       DisplayString,

}

server_type OBJECT-TYPE
    SYNTAX DisplayString
    MAX-ACCESS read-only
    STATUS current
    DESCRIPTION
	""
    ::= { radius_server_entry 1 }

auth_type OBJECT-TYPE
    SYNTAX DisplayString
    MAX-ACCESS read-only
    STATUS current
    DESCRIPTION
	"Authentication type for the radius server"
    ::= { radius_server_entry 2 }

server1Ip OBJECT-TYPE
    SYNTAX IpAddress
    MAX-ACCESS read-only
    STATUS current
    DESCRIPTION
	"The WLAN WPA-Enterprise remote radius server 1 IP"
    ::= { radius_server_entry 3 }

server1Port OBJECT-TYPE
    SYNTAX Integer32 (1..65535)
    MAX-ACCESS read-only
    STATUS current
    DESCRIPTION
	"The WLAN WPA-Enterprise remote radius server 1 port.
    Minimum: 1. Maximum: 65535."
    ::= { radius_server_entry 4 }

server1Secret OBJECT-TYPE
    SYNTAX DisplayString (SIZE(1..64))
    MAX-ACCESS read-only
    STATUS current
    DESCRIPTION
	"The WLAN WPA-Enterprise key combination.
    Display ******** if no passpharse setted."
    ::= { radius_server_entry 5 }

server2Ip OBJECT-TYPE
    SYNTAX IpAddress
    MAX-ACCESS read-only
    STATUS current
    DESCRIPTION
	"The WLAN WPA-Enterprise remote radius server 2 IP"
    ::= { radius_server_entry 6 }

server2Port OBJECT-TYPE
    SYNTAX Integer32 (1..65535)
    MAX-ACCESS read-only
    STATUS current
    DESCRIPTION
	"The WLAN WPA-Enterprise remote radius server 2 port.
    Minimum: 1. Maximum: 65535."
    ::= { radius_server_entry 7 }

server2Secret OBJECT-TYPE
    SYNTAX DisplayString (SIZE(1..64))
    MAX-ACCESS read-only
    STATUS current
    DESCRIPTION
	"The WLAN WPA-Enterprise key combination.
    Display ******** if no passpharse setted."
    ::= { radius_server_entry 8 }

accounting_server_table OBJECT-TYPE
    SYNTAX SEQUENCE OF account_serverEntry
    MAX-ACCESS read-only
    STATUS current
    DESCRIPTION
    "The table for radius server"
    ::={ wireless_security 4 }

accounting_server_entry OBJECT-TYPE
    SYNTAX account_serverEntry
    MAX-ACCESS read-only
    STATUS current
    DESCRIPTION
    "The entry for the radius server"
    INDEX { enable }
    ::= { accounting_server_table 1 }

account_serverEntry ::=
SEQUENCE
{
    enable              DisplayString,
    interval            DisplayString,
    server1Ip           IpAddress,
    server1Port         Integer32,
    server1Secret       DisplayString,
    server2Ip           IpAddress,
    server2Port         Integer32,
    server2Secret       DisplayString,

}

enable OBJECT-TYPE
    SYNTAX DisplayString
    MAX-ACCESS read-only
    STATUS current
    DESCRIPTION
	""
    ::= { accounting_server_entry 1 }

interval OBJECT-TYPE
    SYNTAX DisplayString
    MAX-ACCESS read-only
    STATUS current
    DESCRIPTION
	"Authentication type for the radius server"
    ::= { accounting_server_entry 2 }

server1Ip OBJECT-TYPE
    SYNTAX IpAddress
    MAX-ACCESS read-only
    STATUS current
    DESCRIPTION
	"The WLAN WPA-Enterprise remote radius server 1 IP"
    ::= { accounting_server_entry 3 }

server1Port OBJECT-TYPE
    SYNTAX Integer32 (1..65535)
    MAX-ACCESS read-only
    STATUS current
    DESCRIPTION
	"The WLAN WPA-Enterprise remote radius server 1 port.
    Minimum: 1. Maximum: 65535."
    ::= { accounting_server_entry 4 }

server1Secret OBJECT-TYPE
    SYNTAX DisplayString (SIZE(1..64))
    MAX-ACCESS read-only
    STATUS current
    DESCRIPTION
	"The WLAN WPA-Enterprise key combination.
    Display ******** if no passpharse setted."
    ::= { accounting_server_entry 5 }

server2Ip OBJECT-TYPE
    SYNTAX IpAddress
    MAX-ACCESS read-only
    STATUS current
    DESCRIPTION
	"The WLAN WPA-Enterprise remote radius server 2 IP"
    ::= { accounting_server_entry 6 }

server2Port OBJECT-TYPE
    SYNTAX Integer32 (1..65535)
    MAX-ACCESS read-only
    STATUS current
    DESCRIPTION
	"The WLAN WPA-Enterprise remote radius server 2 port.
    Minimum: 1. Maximum: 65535."
    ::= { accounting_server_entry 7 }

server2Secret OBJECT-TYPE
    SYNTAX DisplayString (SIZE(1..64))
    MAX-ACCESS read-only
    STATUS current
    DESCRIPTION
	"The WLAN WPA-Enterprise key combination.
    Display ******** if no passpharse setted."
    ::= { accounting_server_entry 8 }

-- =======| configuration > schedule | ==============
schedule_table OBJECT-TYPE
    SYNTAX SEQUENCE OF scheduleEntry
    MAX-ACCESS not-accessible
    STATUS current
    DESCRIPTION
    "The table for schedule"
    ::={ schedule 1 }

schedule_entry OBJECT-TYPE
    SYNTAX scheduleEntry
    MAX-ACCESS not-accessible
    STATUS current
    DESCRIPTION
    "The entry for the schedule"
    INDEX { enable }
    ::= { schedule_table 1 }
    
scheduleEntry::=
    SEQUENCE
    {
        enable  DisplayString
    }


enable OBJECT-TYPE
	SYNTAX DisplayString
	MAX-ACCESS read-only
	STATUS current
	DESCRIPTION
	"Enable / Disable WiFi schedule."
	::= { schedule_entry 1 }

daysEntry::=
    SEQUENCE
    {
        available            DisplayString,
        start                DisplayString,
        end                  DisplayString
    }

su_table OBJECT-TYPE
    	SYNTAX SEQUENCE OF daysEntry
    	MAX-ACCESS not-accessible
    	STATUS current
    	DESCRIPTION
	"This table display the schedule table." 
    ::= { schedule 2 }

su_entry OBJECT-TYPE
    	SYNTAX daysEntry
		MAX-ACCESS not-accessible
    	STATUS current
    	DESCRIPTION
	"Represent the entry in the schedule table."
    INDEX { available }
    ::= { su_table 1 }

available OBJECT-TYPE
    SYNTAX DisplayString
    MAX-ACCESS read-only
    STATUS current
    DESCRIPTION 
    "Schedule Status: Enable / Disable."
    ::= { su_entry 1 }

start OBJECT-TYPE
	SYNTAX DisplayString
	MAX-ACCESS read-only
	STATUS current
	DESCRIPTION
	"Schedule time : Start Time."
	::= { su_entry 2 }	
	
end OBJECT-TYPE
	SYNTAX DisplayString
	MAX-ACCESS read-only
	STATUS current
	DESCRIPTION
	"Schedule time : End Time."
	::= { su_entry 3 }	


mo_table OBJECT-TYPE
    	SYNTAX SEQUENCE OF daysEntry
    	MAX-ACCESS not-accessible
    	STATUS current
    	DESCRIPTION
	"This table display the schedule table." 
    ::= { schedule 3 }

mo_entry OBJECT-TYPE
    	SYNTAX daysEntry
		MAX-ACCESS not-accessible
    	STATUS current
    	DESCRIPTION
	"Represent the entry in the schedule table."
    INDEX { available }
    ::= { mo_table 1 }

available OBJECT-TYPE
    SYNTAX DisplayString
    MAX-ACCESS read-only
    STATUS current
    DESCRIPTION 
    "Schedule Status: Enable / Disable."
    ::= { mo_entry 1 }

start OBJECT-TYPE
	SYNTAX DisplayString
	MAX-ACCESS read-only
	STATUS current
	DESCRIPTION
	"Schedule time : Start Time."
	::= { mo_entry 2 }	
	
end OBJECT-TYPE
	SYNTAX DisplayString
	MAX-ACCESS read-only
	STATUS current
	DESCRIPTION
	"Schedule time : End Time."
	::= { mo_entry 3 }	


tu_table OBJECT-TYPE
    	SYNTAX SEQUENCE OF daysEntry
    	MAX-ACCESS not-accessible
    	STATUS current
    	DESCRIPTION
	"This table display the schedule table." 
    ::= { schedule 4 }

tu_entry OBJECT-TYPE
    	SYNTAX daysEntry
		MAX-ACCESS not-accessible
    	STATUS current
    	DESCRIPTION
	"Represent the entry in the schedule table."
    INDEX { available }
    ::= { tu_table 1 }

available OBJECT-TYPE
    SYNTAX DisplayString
    MAX-ACCESS read-only
    STATUS current
    DESCRIPTION 
    "Schedule Status: Enable / Disable."
    ::= { tu_entry 1 }

start OBJECT-TYPE
	SYNTAX DisplayString
	MAX-ACCESS read-only
	STATUS current
	DESCRIPTION
	"Schedule time : Start Time."
	::= { tu_entry 2 }	
	
end OBJECT-TYPE
	SYNTAX DisplayString
	MAX-ACCESS read-only
	STATUS current
	DESCRIPTION
	"Schedule time : End Time."
	::= { tu_entry 3 }	

we_table OBJECT-TYPE
    	SYNTAX SEQUENCE OF daysEntry
    	MAX-ACCESS not-accessible
    	STATUS current
    	DESCRIPTION
	"This table display the schedule table." 
    ::= { schedule 5 }

we_entry OBJECT-TYPE
    	SYNTAX daysEntry
		MAX-ACCESS not-accessible
    	STATUS current
    	DESCRIPTION
	"Represent the entry in the schedule table."
    INDEX { available }
    ::= { we_table 1 }

available OBJECT-TYPE
    SYNTAX DisplayString
    MAX-ACCESS read-only
    STATUS current
    DESCRIPTION 
    "Schedule Status: Enable / Disable."
    ::= { we_entry 1 }

start OBJECT-TYPE
	SYNTAX DisplayString
	MAX-ACCESS read-only
	STATUS current
	DESCRIPTION
	"Schedule time : Start Time."
	::= { we_entry 2 }	
	
end OBJECT-TYPE
	SYNTAX DisplayString
	MAX-ACCESS read-only
	STATUS current
	DESCRIPTION
	"Schedule time : End Time."
	::= { we_entry 3 }	

th_table OBJECT-TYPE
    	SYNTAX SEQUENCE OF daysEntry
    	MAX-ACCESS not-accessible
    	STATUS current
    	DESCRIPTION
	"This table display the schedule table." 
    ::= { schedule 6 }

th_entry OBJECT-TYPE
    	SYNTAX daysEntry
		MAX-ACCESS not-accessible
    	STATUS current
    	DESCRIPTION
	"Represent the entry in the schedule table."
    INDEX { available }
    ::= { th_table 1 }

available OBJECT-TYPE
    SYNTAX DisplayString
    MAX-ACCESS read-only
    STATUS current
    DESCRIPTION 
    "Schedule Status: Enable / Disable."
    ::= { th_entry 1 }

start OBJECT-TYPE
	SYNTAX DisplayString
	MAX-ACCESS read-only
	STATUS current
	DESCRIPTION
	"Schedule time : Start Time."
	::= { th_entry 2 }	
	
end OBJECT-TYPE
	SYNTAX DisplayString
	MAX-ACCESS read-only
	STATUS current
	DESCRIPTION
	"Schedule time : End Time."
	::= { th_entry 3 }	


fr_table OBJECT-TYPE
    	SYNTAX SEQUENCE OF daysEntry
    	MAX-ACCESS not-accessible
    	STATUS current
    	DESCRIPTION
	"This table display the schedule table." 
    ::= { schedule 7 }

fr_entry OBJECT-TYPE
    	SYNTAX daysEntry
		MAX-ACCESS not-accessible
    	STATUS current
    	DESCRIPTION
	"Represent the entry in the schedule table."
    INDEX { available }
    ::= { fr_table 1 }

available OBJECT-TYPE
    SYNTAX DisplayString
    MAX-ACCESS read-only
    STATUS current
    DESCRIPTION 
    "Schedule Status: Enable / Disable."
    ::= { fr_entry 1 }

start OBJECT-TYPE
	SYNTAX DisplayString
	MAX-ACCESS read-only
	STATUS current
	DESCRIPTION
	"Schedule time : Start Time."
	::= { fr_entry 2 }	
	
end OBJECT-TYPE
	SYNTAX DisplayString
	MAX-ACCESS read-only
	STATUS current
	DESCRIPTION
	"Schedule time : End Time."
	::= { fr_entry 3 }	

sa_table OBJECT-TYPE
    	SYNTAX SEQUENCE OF daysEntry
    	MAX-ACCESS not-accessible
    	STATUS current
    	DESCRIPTION
	"This table display the schedule table." 
    ::= { schedule 8 }

sa_entry OBJECT-TYPE
    	SYNTAX daysEntry
		MAX-ACCESS not-accessible
    	STATUS current
    	DESCRIPTION
	"Represent the entry in the schedule table."
    INDEX { available }
    ::= { sa_table 1 }

available OBJECT-TYPE
    SYNTAX DisplayString
    MAX-ACCESS read-only
    STATUS current
    DESCRIPTION 
    "Schedule Status: Enable / Disable."
    ::= { sa_entry 1 }

start OBJECT-TYPE
	SYNTAX DisplayString
	MAX-ACCESS read-only
	STATUS current
	DESCRIPTION
	"Schedule time : Start Time."
	::= { sa_entry 2 }	
	
end OBJECT-TYPE
	SYNTAX DisplayString
	MAX-ACCESS read-only
	STATUS current
	DESCRIPTION
	"Schedule time : End Time."
	::= { sa_entry 3 }	
	
		     
-- ============== END ===========================

bandwidth_limit_table OBJECT-TYPE
    SYNTAX SEQUENCE OF bandwidth_limitEntry
    MAX-ACCESS read-only
    STATUS current
    DESCRIPTION
    "The table for bandwidth limit"
    ::= { ssid 8 }

bandwidth_limit_entry   OBJECT-TYPE
    SYNTAX bandwidth_limitEntry
    MAX-ACCESS read-only
    STATUS current
    DESCRIPTION
    "The entry for the bandwidth limit"
    INDEX { enable }
    ::= { bandwidth_limit_table 1 }

bandwidth_limitEntry ::=
SEQUENCE
{
    enable                      DisplayString,
    ssid_download_limit         Integer32,
    ssid_upload_limit           Integer32,
    perclient_download_limit    Integer32,
    perclient_upload_limit      Integer32
}

enable OBJECT-TYPE
    SYNTAX DisplayString
    MAX-ACCESS read-only
    STATUS current
    DESCRIPTION
	"Traffic Shaping enabled status for each ssid"
    ::= { bandwidth_limit_entry 1 }

ssid_download_limit OBJECT-TYPE
    SYNTAX Integer32
    MAX-ACCESS read-only
    STATUS current
    DESCRIPTION
    "SSID max download limit"
    ::= { bandwidth_limit_entry 2 }

ssid_upload_limit OBJECT-TYPE
    SYNTAX Integer32
    MAX-ACCESS read-only
    STATUS current
    DESCRIPTION
    "SSID max upload limit"
    ::= { bandwidth_limit_entry 3 }

perclient_download_limit OBJECT-TYPE
    SYNTAX Integer32
    MAX-ACCESS read-only
    STATUS current
    DESCRIPTION
    "SSID per-client download limit"
    ::= { bandwidth_limit_entry 4 }

perclient_upload_limit OBJECT-TYPE
    SYNTAX Integer32
    MAX-ACCESS read-only
    STATUS current
    DESCRIPTION
    "SSID per-client upload limit"
    ::= { bandwidth_limit_entry 5 }

-- =======| wifi > client_info ================================

client_number OBJECT-TYPE
    SYNTAX Integer32 (0..65535)
    MAX-ACCESS read-only
    STATUS current
    DESCRIPTION
	"The number of connected clients"
    ::= { client_24g 1 }


client_list OBJECT-TYPE
	   SYNTAX DisplayString
	   MAX-ACCESS read-only
	   STATUS current
	   DESCRIPTION
	   "The 2.4G wireless client list."
      ::={ client_24g 2 }


client_info_24g_table OBJECT-TYPE
    	SYNTAX SEQUENCE OF LiveClientTableEntry
    	MAX-ACCESS not-accessible
    	STATUS current
    	DESCRIPTION
	"This table display the list of client that associated to the device." 
    ::= { client_24g 3 }

client_info_24g_entry OBJECT-TYPE
    	SYNTAX LiveClientTableEntry
   	MAX-ACCESS not-accessible
    	STATUS current
    	DESCRIPTION
	"Represent the entry in the Client table."
    INDEX { ip_address }
    ::= { client_info_24g_table 1 }

LiveClientTableEntry::=
    SEQUENCE
    {
	mac_address 			DisplayString, 
	ip_address			DisplayString,
	host_name			DisplayString,
	tx_byte			Integer32,
	rx_byte			Integer32,
	os				DisplayString,
	rssi				DisplayString
    }

mac_address OBJECT-TYPE
    SYNTAX DisplayString (SIZE(0..17))
    MAX-ACCESS read-only
    STATUS current
    DESCRIPTION
	"The mac address of the client"
    ::= { client_info_24g_entry 1 }

ip_address OBJECT-TYPE
    SYNTAX DisplayString 
    MAX-ACCESS read-only
    STATUS current
    DESCRIPTION
	"The IP address of the client"
    ::= { client_info_24g_entry 2 }

host_name OBJECT-TYPE
    SYNTAX DisplayString (SIZE(0..32))
    MAX-ACCESS read-only
    STATUS current
    DESCRIPTION
	"The hostname of the client"
    ::= { client_info_24g_entry 3 }

tx_byte OBJECT-TYPE
    SYNTAX Integer32 (0..65535)
    MAX-ACCESS read-only
    STATUS current
    DESCRIPTION
	"The transmitted data bytes of the client, in Bytes"
    ::= { client_info_24g_entry 4}

rx_byte OBJECT-TYPE
    SYNTAX Integer32 (0..65535)
    MAX-ACCESS read-only
    STATUS current
    DESCRIPTION
	"The received data bytes of the client, in Bytes"
    ::= { client_info_24g_entry 5 }
	
os OBJECT-TYPE
    SYNTAX DisplayString (SIZE(0..32))
    MAX-ACCESS read-only
    STATUS current
    DESCRIPTION
	"The OS of client"
    ::= { client_info_24g_entry 6 }
	
rssi OBJECT-TYPE
    SYNTAX DisplayString (SIZE(0..32))
    MAX-ACCESS read-only
    STATUS current
    DESCRIPTION
	"The connection RSSI of client"
    ::= { client_info_24g_entry 7 }
	 
-- ============== END ===========================
      
-- =======| config > client | ================================

client_number OBJECT-TYPE
    SYNTAX Integer32 (0..65535)
    MAX-ACCESS read-only
    STATUS current
    DESCRIPTION
	"The number of connected clients"
    ::= { client_5g 1 }


client_list OBJECT-TYPE
	   SYNTAX DisplayString
	   MAX-ACCESS read-only
	   STATUS current
	   DESCRIPTION
	   "The 5G wireless client list."
      ::={ client_5g 2 }


client_info_5g_table OBJECT-TYPE
    	SYNTAX SEQUENCE OF LiveClientTableEntry
    	MAX-ACCESS not-accessible
    	STATUS current
    	DESCRIPTION
	"This table display the list of client that associated to the device." 
    ::= { client_5g 3 }

client_info_5g_entry OBJECT-TYPE
    	SYNTAX LiveClientTableEntry
   	MAX-ACCESS not-accessible
    	STATUS current
    	DESCRIPTION
	"Represent the entry in the Client table."
    INDEX { ip_address }
    ::= { client_info_5g_table 1 }

mac_address OBJECT-TYPE
    SYNTAX DisplayString (SIZE(0..17))
    MAX-ACCESS read-only
    STATUS current
    DESCRIPTION
	"The mac address of the client"
    ::= { client_info_5g_entry 1 }

ip_address OBJECT-TYPE
    SYNTAX DisplayString 
    MAX-ACCESS read-only
    STATUS current
    DESCRIPTION
	"The IP address of the client"
    ::= { client_info_5g_entry 2 }

host_name OBJECT-TYPE
    SYNTAX DisplayString (SIZE(0..32))
    MAX-ACCESS read-only
    STATUS current
    DESCRIPTION
	"The hostname of the client"
    ::= { client_info_5g_entry 3 }

tx_byte OBJECT-TYPE
    SYNTAX Integer32 (0..65535)
    MAX-ACCESS read-only
    STATUS current
    DESCRIPTION
	"The transmitted data bytes of the client, in Bytes"
    ::= { client_info_5g_entry 4}

rx_byte OBJECT-TYPE
    SYNTAX Integer32 (0..65535)
    MAX-ACCESS read-only
    STATUS current
    DESCRIPTION
	"The received data bytes of the client, in Bytes"
    ::= { client_info_5g_entry 5 }
	
os OBJECT-TYPE
    SYNTAX DisplayString (SIZE(0..32))
    MAX-ACCESS read-only
    STATUS current
    DESCRIPTION
	"The OS of client"
    ::= { client_info_5g_entry 6 }
	
rssi OBJECT-TYPE
    SYNTAX DisplayString (SIZE(0..32))
    MAX-ACCESS read-only
    STATUS current
    DESCRIPTION
	"The connection RSSI of client"
    ::= { client_info_5g_entry 7 }
 
-- ============== END ===========================

-- ============== Public Traps ==================

   coldStart NOTIFICATION-TYPE
       STATUS  current
       DESCRIPTION
               "A coldStart trap signifies that the SNMP entity,
               supporting a notification originator application, is
               reinitializing itself and that its configuration may
               have been altered."
        ::=  { snmpTraps 1 }

    warmStart NOTIFICATION-TYPE
       STATUS  current
       DESCRIPTION
               "A warmStart trap signifies that the SNMP entity,
               supporting a notification originator application,
               is reinitializing itself such that its configuration
               is unaltered."
    ::=  { snmpTraps 2 } 

    linkDown NOTIFICATION-TYPE
        -- OBJECTS { ifIndex, ifAdminStatus, ifOperStatus }
        STATUS  current
        DESCRIPTION
            "A linkDown trap signifies that the SNMP entity, acting in
            an agent role, has detected that the ifOperStatus object for
            one of its communication links is about to enter the down
            state from some other state (but not from the notPresent
            state).  This other state is indicated by the included value
            of ifOperStatus."
    ::=  { snmpTraps 3 } 

    linkUp NOTIFICATION-TYPE
        -- OBJECTS { ifIndex, ifAdminStatus, ifOperStatus }
        STATUS  current
        DESCRIPTION
            "A linkUp trap signifies that the SNMP entity, acting in an
            agent role, has detected that the ifOperStatus object for
            one of its communication links left the down state and
            transitioned into some other state (but not into the
            notPresent state).  This other state is indicated by the
            included value of ifOperStatus."
    ::=  { snmpTraps 4 } 

    authenticationFailure NOTIFICATION-TYPE
       STATUS  current
       DESCRIPTION
               "An authenticationFailure trap signifies that the SNMP
                entity has received a protocol message that is not
                properly authenticated.  While all implementations
                of SNMP entities MAY be capable of generating this
                trap, the snmpEnableAuthenTraps object indicates
                whether this trap will be generated."
       ::=  { snmpTraps 5 } 

-- ============== END ===========================


END
