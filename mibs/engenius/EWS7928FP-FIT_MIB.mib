EWS7928FP-FIT-MIB DEFINITIONS ::= BEGIN

-- -------------------------------------------------------------
-- IMPORTS
-- -------------------------------------------------------------
IMPORTS
dot1xAuthOperControlledDirections,PaeControlledPortStatus FROM IEEE8021-PAE-MIB
ifType,ifIndex,ifEntry,InterfaceIndexOrZero,InterfaceIndex FROM IF-MIB
InetZoneIndex,InetScopeType,InetPortNumber,InetAddressType,InetAddressPrefixLength,InetAddress FROM INET-ADDRESS-MIB
lldpLocPortNum,lldpRemChassisId,lldpRemPortId,lldpRemSysName,lldpRemManAddrIfId,lldpLocPortId,lldpStatsRemTablesInserts,lldpStatsRemTablesAgeouts,lldpStatsRemTablesDeletes,lldpStatsRemTablesDrops,lldpLocManAddrEntry,LldpPortNumber FROM LLDP-MIB
LldpV2DestAddressTableIndex FROM LLDP-V2-TC-MIB
EnabledStatus FROM P-BRIDGE-MIB
VlanIndex,VlanIdOrNone,VlanId,PortList FROM Q-BRIDGE-MIB
etherStatsEntry FROM RMON-MIB
ZeroBasedCounter32,TimeFilter FROM RMON2-MIB
SnmpAdminString FROM SNMP-FRAMEWORK-MIB
SnmpTagValue FROM SNMP-TARGET-MIB
mib-2,enterprises,Unsigned32,TimeTicks,OBJECT-TYPE,NOTIFICATION-TYPE,MODULE-IDENTITY,IpAddress,Integer32,Gauge32,Counter64,Counter32 FROM SNMPv2-SMI
TruthValue,TimeStamp,TEXTUAL-CONVENTION,StorageType,RowStatus,MacAddress,DisplayString FROM SNMPv2-TC;

-- -------------------------------------------------------------
-- Module Identity
-- -------------------------------------------------------------
enGeniusNetworksInc MODULE-IDENTITY
      LAST-UPDATED "201209050000Z"
      ORGANIZATION "SENAO COMMUNICATIONS SOFTWARE"
      CONTACT-INFO "www.senao.com"
      DESCRIPTION "The MIB for EWS7928FP-FIT."
      REVISION "201209050000Z"
      DESCRIPTION "The MIB is contained
                     pm_radext.mib
                     pm_iss.mib
                     pm_msipvx.mib
                     pm_msvlan.mib
                     pm_qosxtd.mib
                     pm_ipv6.mib
                     pm_dns.mib
                     pm_cfa.mib
                     pm_eee.mib
                     pm_msbrg.mib
                     pm_mprst.mib
                     pm_mpmst.mib
                     pm_lbd.mib
                     pm_snp.mib
                     pm_la.mib
                     pm_lldp.mib
                     pm_mpvlan.mib
                     pm_mparp.mib
                     pm_pnac.mib
                     pm_issext.mib
                     pm_poe.mib
                     pm_usermgm.mib
                     pm_ssl.mib
                     pm_snmp3.mib
                     pm_rmon.mib
                     pm_sshmib.mib
                     pm_clkiwf.mib
                     pm_sntp.mib
                     pm_syslg.mib
                     pm_midhcsnp.mib
                     pm_cdp.mib
                     pm_cdp.mib
                     "
::= { enterprises 44194 }

no2Oid OBJECT IDENTIFIER ::={enGeniusNetworksInc 22 }
profileA OBJECT IDENTIFIER ::={no2Oid 1 }
swEWS7928FP-FIT OBJECT IDENTIFIER ::={profileA 85 }

-- -------------------------------------------------------------
-- Textual Conventions
-- -------------------------------------------------------------
Dscp ::= TEXTUAL-CONVENTION
    DISPLAY-HINT "d"
    STATUS   current
    DESCRIPTION
       "A Differentiated Services Code-Point that may be used for
       marking a traffic stream."
    REFERENCE
        "RFC 2474, RFC 2780"
    SYNTAX   Integer32 (0..63)

MeterColorMode ::= TEXTUAL-CONVENTION
        STATUS  current
        DESCRIPTION
        "Enums to indicate the color mode of the Meter
        colorAware      - the Meter will also consider the Pre-Color 
                          of the Packet
        colorBlind      - the Meter will ignore the Pre-Color of the Packet"
        SYNTAX   INTEGER {
                          colorAware(1),
                          colorBlind(2)
                         }

MeterType ::= TEXTUAL-CONVENTION
        STATUS  current
        DESCRIPTION
        "Enums to indicate the meter type :
        SimpleTokenBucket - Two Parameter Token Bucket Meter as described in 
                            the Informal Differentiated Services Model section 
                            5.2.3.
        AvgRate           - Average Rate Meter as described in the Informal 
                            Differentiated Services Model section 5.2.1.
        SrTCM             - Single Rate Three Color Marker Metering as defined 
                            by RFC 2697.
        TrTCM             - Two Rate Three Color Marker Metering as defined by 
                            RFC 2698.
        TswTCM            - Time Sliding Window Three Color Marker Metering as 
                            defined by RFC 2859.
        mefDecoupledMeter - Dual bucket meter as defined by RFC 4115.
        mefCoupledMeter   - Dual bucket meter as defined by RFC 2697 and 
                            MEF coupling Flag."
        SYNTAX   INTEGER {
                          simpleTokenBucket(1),
                          avgRate(2),
                          srTCM(3),         
                          trTCM(4), 
                          tswTCM(5),
                          mefDecoupledMeter(6),
                          mefCoupledMeter(7)
                         }

EnableStatus    ::= TEXTUAL-CONVENTION
    STATUS      current
    DESCRIPTION "A textual convention to Enable or Disable a MIB contruct."
    SYNTAX      INTEGER {
                    enable(1),
                    disable(2)
                }

SchedulerPriority    ::= TEXTUAL-CONVENTION
    DISPLAY-HINT "d"
    STATUS    current
    DESCRIPTION
        "Scheduler Priority which a flow should fall in."
    SYNTAX    Integer32 (0..15)

IndexInteger ::= TEXTUAL-CONVENTION
    DISPLAY-HINT "d"
    STATUS   current
    DESCRIPTION
       "An integer which may be used as a table index. If 0 then it is invalid"
    SYNTAX   Unsigned32 (0..65535)
InterfaceList ::= TEXTUAL-CONVENTION
    STATUS      current
    DESCRIPTION
        "Each octet within this value specifies a set of eight
        interfaces, with the first octet specifying router-ports 1 through
        8, the second octet specifying router-ports 9 through 16, etc.
        Within each octet, the most significant bit represents the lowest 
        numbered router-port or L3 interface, and the least significant bit
        represents the highest numbered port.  Thus, each L3 interface
        of the switch is represented by a single bit within the
        value of this object.  If that bit has a value of '1',
        then that L3 interface is included in the set of interfaces; the interface 
        is not included if its bit has a value of '0'."
    SYNTAX      OCTET STRING
BridgeId ::= TEXTUAL-CONVENTION
     STATUS  current
     DESCRIPTION
           "The Bridge-Identifier as used in the
           Spanning Tree
           Protocol to uniquely identify a bridge.  Its first two
           octets (in network byte order) contain a priority
           value and its last 6 octets contain the MAC address
           used to refer to a bridge in a unique fashion
           (typically, the numerically smallest MAC address
           of all ports on the bridge).
           Several objects in this MIB module represent values of
           timers used by the Spanning Tree Protocol.  In this
           MIB, these timers have values in units of hundreths of
           a second (i.e. 1/100 secs).
           These timers, when stored in a Spanning Tree Protocol's
           BPDU, are in units of 1/256 seconds.  Note, however,
           that 802.1D-1998 specifies a settable granularity of
           no more than 1 second for these timers.  To avoid
           ambiguity, a data type is defined here as a textual
           convention and all representation of these timers
           in this MIB module are defined using this data type.  An
           algorithm is also defined for converting between the
           different units, to ensure a timer's value is not                                  distorted by multiple conversions."
     SYNTAX          OCTET STRING (SIZE (8))

Timeout ::= TEXTUAL-CONVENTION
     DISPLAY-HINT "d"
     STATUS       current
     DESCRIPTION
          "A Spanning Tree Protocol (STP) timer in units of 1/100
           seconds.  Several objects in this MIB module represent
           values of timers used by the Spanning Tree Protocol.
           In this MIB, these timers have values in units of
           hundredths of a second (i.e., 1/100 secs).

           These timers, when stored in a Spanning Tree Protocol's
           BPDU, are in units of 1/256 seconds.  Note, however, that
           802.1D-1998 specifies a settable granularity of no more
           than one second for these timers.  To avoid ambiguity,
           a conversion algorithm is defined below for converting
           between the different units, which ensures a timer's
           value is not distorted by multiple conversions.

           To convert a Timeout value into a value in units of
           1/256 seconds, the following algorithm should be used:

               b = floor( (n * 256) / 100)

           where:
               floor   =  quotient [ignore remainder]
               n is the value in 1/100 second units
               b is the value in 1/256 second units

           To convert the value from 1/256 second units back to
           1/100 seconds, the following algorithm should be used:

               n = ceiling( (b * 100) / 256)

           where:
               ceiling = quotient [if remainder is 0], or
                         quotient + 1 [if remainder is nonzero]
               n is the value in 1/100 second units

               b is the value in 1/256 second units

           Note: it is important that the arithmetic operations are
           done in the order specified (i.e., multiply first,
           divide second)."

     SYNTAX       Integer32
InnerVlanIndex ::= TEXTUAL-CONVENTION
    DISPLAY-HINT "d"
    STATUS      current
    DESCRIPTION
        "A value used to represent the Inner VLAN that might be
         carried in a packet. 
         A value between 1 and 4094 inclusive, represents
         a valid vlan and is used only in cases where the
         switch understands and is capable of handling 
         double tagged packets.
         A value 0 is used in cases where the switch understands
         and is capable of handling only single tagged packets."
    SYNTAX      Unsigned32 (0..4094)
     PortLaMode ::= TEXTUAL-CONVENTION
         STATUS         current
         DESCRIPTION    
           "Defines how a Port Channel does channeling.
           lacp(1)      - place the port into passive 
                           negotiation state, in which the
                           port waits for its peer to 
                           initiate negotiation.
           manual(2)    - force the port to enable 
                           channeling.
           disable(3)   - channeling is disabled."
                     
     SYNTAX INTEGER {
                       lacp(1),
                       manual(2),
                       disable(3)
                    }

     LacpKey ::= TEXTUAL-CONVENTION
     DISPLAY-HINT "d"
         STATUS    current
         DESCRIPTION
                "The Actor or Partner Key value."
         SYNTAX Integer32 (0..65535)
 
    
   LacpState ::= TEXTUAL-CONVENTION
      STATUS current
      DESCRIPTION
         "The Actor and Partner State values from the LACPDU."
      SYNTAX BITS {
           lacpActivity(0),
           lacpTimeout(1),
           aggregation(2),
           synchronization(3),
           collecting(4),
           distributing(5),
           defaulted(6),
           expired(7)
          }
MacLearningStatus ::= TEXTUAL-CONVENTION
    STATUS      current
    DESCRIPTION
        "A simple MAC learning status value specific to VLAN."
    SYNTAX      INTEGER { enabled(1), disabled(2), default(3) }
       AuthenticMethod ::= TEXTUAL-CONVENTION 
          STATUS      current 
          DESCRIPTION 
             "The Authentication method is using Remote Authentication 
             Server or Local Authentication Server." 
          SYNTAX      INTEGER { 
                          remoteServer(1), 
                          localServer(2) 
                      } 
 
       RemoteAuthServerType ::= TEXTUAL-CONVENTION 
          STATUS      current 
          DESCRIPTION 
             "This indicates which Remote Server is to provide the 
              authentication. Currently supported servers are RADIUS
              Server and Terminal Access Controller Access-Control 
              System Plus (TACACS+) Server." 
          SYNTAX      INTEGER {                           
                          radiusServer(1), 
                          tacacsplusServer(2) 
                      } 

       PermissionType ::= TEXTUAL-CONVENTION 
          STATUS      current 
          DESCRIPTION 
             "The permission values." 
          SYNTAX       INTEGER { 
                           allow(1), 
                           deny(2) 
                       }
PmClkIwfTimeInterval ::= TEXTUAL-CONVENTION
    STATUS     current
    DESCRIPTION
            "The time interval field represents the values in scalednanoseconds.
             The scalednanoseconds member is the time interval expressed in
             units of nanoseconds and multiplied by 2^16.
             Positive or negative time intervals outside the maximum range of
             this data type shall be encoded as the largest positive and
             negative values of this data type, respectively. For example, 2.5 
             nanoseconds, will be expressed as 2.5 * 2^16 and the value
             converted to hexadecimal that will obviously evolve to
             0000 0000 0002 8000 base 16."
    SYNTAX   OCTET STRING (SIZE (8))
EnabledStatus ::= TEXTUAL-CONVENTION
    STATUS      current
    DESCRIPTION 
        "A simple status value for the object." 
    SYNTAX      INTEGER { enabled(1), disabled(2) }
EnabledStatus ::= TEXTUAL-CONVENTION
    STATUS      current
    DESCRIPTION 
        "A simple status value for the object." 
    SYNTAX      INTEGER { enabled(1), disabled(2) }

-- -------------------------------------------------------------
-- Title
-- -------------------------------------------------------------
systemFeatures OBJECT IDENTIFIER ::={ swEWS7928FP-FIT 2 }
port OBJECT IDENTIFIER ::={ swEWS7928FP-FIT 3 }
l2Features OBJECT IDENTIFIER ::={ swEWS7928FP-FIT 4 }
dhcp OBJECT IDENTIFIER ::={ swEWS7928FP-FIT 6 }
vlan OBJECT IDENTIFIER ::={ swEWS7928FP-FIT 7 }
l3Interface OBJECT IDENTIFIER ::={ swEWS7928FP-FIT 8 }
security OBJECT IDENTIFIER ::={ swEWS7928FP-FIT 13 }
management OBJECT IDENTIFIER ::={ swEWS7928FP-FIT 15 }
temporarily OBJECT IDENTIFIER ::={ swEWS7928FP-FIT 99 }
privateIpv6 OBJECT IDENTIFIER ::={ systemFeatures 9 }
privateDns OBJECT IDENTIFIER ::={ systemFeatures 21 }
privateCfa OBJECT IDENTIFIER ::={ port 1 }
privateEee OBJECT IDENTIFIER ::={ port 37 }
privateDot1dBridge OBJECT IDENTIFIER ::={ l2Features 17 }
privateMIRstMIB OBJECT IDENTIFIER ::={ l2Features 19 }
privateMIMstMIB OBJECT IDENTIFIER ::={ l2Features 21 }
privateLBD OBJECT IDENTIFIER ::={ l2Features 43 }
privateSnoop OBJECT IDENTIFIER ::={ l2Features 57 }
privateLa OBJECT IDENTIFIER ::={ l2Features 131 }
privateLldp OBJECT IDENTIFIER ::={ l2Features 139 }
privateCDP OBJECT IDENTIFIER ::={ l2Features 147 }
privateMIDhcpSnp OBJECT IDENTIFIER ::={ dhcp 17 }
privateMIVlanMIB OBJECT IDENTIFIER ::={ vlan 1 }
priavteMiArp OBJECT IDENTIFIER ::={ l3Interface 3 }
privatePnac OBJECT IDENTIFIER ::={ security 1 }
privateIssExt OBJECT IDENTIFIER ::={ security 31 }
privateRADIUSEXTMIB OBJECT IDENTIFIER ::={ security 59 }
privatePoe OBJECT IDENTIFIER ::={ management 1 }
privateUsrMgmt OBJECT IDENTIFIER ::={ management 13 }
privateSsl OBJECT IDENTIFIER ::={ management 19 }
privateSnmp3 OBJECT IDENTIFIER ::={ management 29 }
privateRmon OBJECT IDENTIFIER ::={ management 31 }
privateSsh OBJECT IDENTIFIER ::={ management 33 }
privateClkIwfMIB OBJECT IDENTIFIER ::={ management 87 }
privateSntpMIB OBJECT IDENTIFIER ::={ management 88 }
privateSyslog OBJECT IDENTIFIER ::={ management 103 }
privateIss OBJECT IDENTIFIER ::={ temporarily 1 }
privateQoSMib OBJECT IDENTIFIER ::={ temporarily 2 }
privateMIStdIp OBJECT IDENTIFIER ::={ temporarily 3 }
privateQBridgeMIB OBJECT IDENTIFIER ::={ temporarily 4 }

-- -------------------------------------------------------------
-- Body
-- -------------------------------------------------------------
    pmRadExtClient       OBJECT IDENTIFIER ::= { privateRADIUSEXTMIB 1 }

-- ---------------------------------------------------------- -- 
-- ---------------------------------------------------------- -- 
-- groups in the RADIUS EXTENDED MIB 
-- ---------------------------------------------------------- -- 
 
     pmRadExtServer        OBJECT IDENTIFIER ::= { pmRadExtClient 1 } 
     pmRadAuthClient       OBJECT IDENTIFIER ::= { pmRadExtClient 2 } 
     pmRadAccClient        OBJECT IDENTIFIER ::= { pmRadExtClient 3 } 
 
-- ---------------------------------------------------------- -- 

pmRadExtPrimaryServerAddressType OBJECT-TYPE
   SYNTAX      InetAddressType
   MAX-ACCESS  read-write 
   STATUS      current
   DESCRIPTION
   "The address type of active server.This can be Ipv4 or Ipv6."
      ::= { pmRadExtServer 3 }


pmRadExtPrimaryServer   OBJECT-TYPE
    SYNTAX      InetAddress (SIZE(16))
    MAX-ACCESS  read-write
    STATUS      current
    DESCRIPTION
      "A maximum of 5 RADIUS servers (IPv4 or IPv6) can be configured
      in pmRadExtServerEntry. This object indicates the primary server 
      among those 5 servers. The RADIUS client will first try to interact 
      with the server mentioned in this object. Other servers are 
      approached only if this server is not reachable. Setting this 
      object to zero disables the primary server concept."
      ::= { pmRadExtServer 4 }

pmRadExtServerTable OBJECT-TYPE
    SYNTAX SEQUENCE OF PmRadExtServerEntry
    MAX-ACCESS not-accessible
    STATUS current
    DESCRIPTION
        "The (conceptual) table that lists the RADIUS servers with
         which the client shares a secret."
    ::=  { pmRadExtServer 5 }

pmRadExtServerEntry OBJECT-TYPE
    SYNTAX PmRadExtServerEntry
    MAX-ACCESS not-accessible
    STATUS current
    DESCRIPTION
        "An entry (conceptual row) representing a RADIUS server
                 with which the client shares a secret."
    INDEX {pmRadExtServerIndex}
    ::=  { pmRadExtServerTable 1 }

PmRadExtServerEntry ::= SEQUENCE {
    pmRadExtServerIndex    Integer32,
    pmRadExtServerAddrType    InetAddressType,
    pmRadExtServerAddress   InetAddress,
    pmRadExtServerSharedSecret    DisplayString,
    pmRadExtServerResponseTime Integer32,
    pmRadExtServerMaximumRetransmission  Integer32,
    pmRadExtServerEntryStatus       RowStatus
   }


pmRadExtServerIndex OBJECT-TYPE
    SYNTAX Integer32 (1..5)
    MAX-ACCESS not-accessible
    STATUS current
    DESCRIPTION
        "This object enumerates the order in which the server should
         be contacted.Index 1 is contacted first if the primary server
         specified by pmRadExtPrimaryServer is not configured"
    ::=  { pmRadExtServerEntry 1 }
    
pmRadExtServerAddrType OBJECT-TYPE
    SYNTAX InetAddressType
    MAX-ACCESS read-create
    STATUS current
    DESCRIPTION
       "The type of IP address to be configured for the RADIUS server.
        While other types of addresses are defined in the InetAddressType
        textual convention, like DNS names, this object is limited to IPv4
        and IPv6 addresses."
    ::= { pmRadExtServerEntry 2 }


pmRadExtServerAddress OBJECT-TYPE
    SYNTAX InetAddress
    MAX-ACCESS read-write
    STATUS current
    DESCRIPTION
        "The IP address(Ipv4 or Ipv6) of the RADIUS server
         referred to in pmRadExtServerTable entry."
    ::=  { pmRadExtServerEntry 3 }


pmRadExtServerSharedSecret OBJECT-TYPE
    SYNTAX DisplayString
    MAX-ACCESS read-write
    STATUS current
    DESCRIPTION
        "The secret string which is shared between the Server and the 
        Client"
    ::=  { pmRadExtServerEntry 5 }


pmRadExtServerResponseTime OBJECT-TYPE
    SYNTAX Integer32  (1 ..120)
    MAX-ACCESS read-write
    STATUS current
    DESCRIPTION
        "The maximum time within which the server has to respond for a
         request from the client."
    ::=  { pmRadExtServerEntry 7 }

pmRadExtServerMaximumRetransmission OBJECT-TYPE
    SYNTAX Integer32  (1 ..254)
    MAX-ACCESS read-write
    STATUS current
    DESCRIPTION
        "The allowed maximum number of trials to be tried by a client to get
         the response from the server for a request"
    ::=  { pmRadExtServerEntry 8 }

pmRadExtServerEntryStatus   OBJECT-TYPE
   SYNTAX               RowStatus
   MAX-ACCESS           read-write
   STATUS           current
   DESCRIPTION
      "The status of the entry can be used as specified in the SNMP V2
      standard. "
  ::=  {   pmRadExtServerEntry 9  }
  
-- ---------------------------------------------------------- --
-- The Radius Authentication Group
-- ---------------------------------------------------------- --
-- The group for entities implementing the client
-- side of the Remote Access Dial in User Service (RADIUS)
-- authentication protocol.

pmRadExtAuthServerTable OBJECT-TYPE
      SYNTAX     SEQUENCE OF PmRadExtAuthServerEntry
      MAX-ACCESS not-accessible
      STATUS     current
      DESCRIPTION
            "The (conceptual) table taht lists the RADIUS authentication
             servers with which the client shares a secret."
      ::=  { pmRadAuthClient 3 }

pmRadExtAuthServerEntry OBJECT-TYPE
      SYNTAX     PmRadExtAuthServerEntry
      MAX-ACCESS not-accessible
      STATUS     current
      DESCRIPTION
            "An entry (conceptual row) that represents a RADIUS
             authentication server with which the client shares
             a secret."
      INDEX      { pmRadExtAuthServerIndex }
      ::= { pmRadExtAuthServerTable 1 }

PmRadExtAuthServerEntry ::= SEQUENCE {
      pmRadExtAuthServerIndex                           Integer32,
      pmRadExtAuthClientServerPortNumber                Integer32,
      pmRadExtAuthClientRoundTripTime                   TimeTicks,
      pmRadExtAuthClientAccessRequests                  Counter32,
      pmRadExtAuthClientAccessRetransmissions           Counter32,
      pmRadExtAuthClientAccessAccepts                   Counter32,
      pmRadExtAuthClientAccessRejects                   Counter32,
      pmRadExtAuthClientAccessChallenges                Counter32,
      pmRadExtAuthClientMalformedAccessResponses        Counter32,
      pmRadExtAuthClientBadAuthenticators               Counter32,
      pmRadExtAuthClientPendingRequests                   Gauge32,
      pmRadExtAuthClientTimeouts                        Counter32,
      pmRadExtAuthClientUnknownTypes                    Counter32
}

pmRadExtAuthServerIndex OBJECT-TYPE
      SYNTAX     Integer32 (1..2147483647)
      MAX-ACCESS not-accessible
      STATUS     current
      DESCRIPTION
             "A number that uniquely idenfifies each RADIUS
             Authentication server with which the client
             communicates."
      ::= { pmRadExtAuthServerEntry 1 }

pmRadExtAuthClientServerPortNumber  OBJECT-TYPE
      SYNTAX Integer32 (0..65535)
      MAX-ACCESS read-write
      STATUS current
      DESCRIPTION
            "The UDP port that the client uses to send requests to
             this server."
      ::= { pmRadExtAuthServerEntry 4 }

pmRadExtAuthClientRoundTripTime  OBJECT-TYPE
      SYNTAX TimeTicks
      MAX-ACCESS read-only
      STATUS current
      DESCRIPTION
            "The time interval (in hundredths of a second) between
             the most recent Access-Reply/Access-Challenge and the
             Access-Request that that matches with the 
             Access-Reply/Access-Challengeit from the RADIUS
             authentication server."
      ::= { pmRadExtAuthServerEntry 5 }
      
-- Request/Response statistics
--
-- TotalIncomingPackets = Accepts + Rejects + Challenges + UnknownTypes
--
-- TotalIncomingPackets - MalformedResponses - BadAuthenticators -
-- UnknownTypes - PacketsDropped = Successfully received
--
-- AccessRequests + PendingRequests + ClientTimeouts =
-- Successfully Received
--
--

pmRadExtAuthClientAccessRequests OBJECT-TYPE
      SYNTAX Counter32
      MAX-ACCESS read-only
      STATUS current
      DESCRIPTION
            "The number of RADIUS Access-Request packets sent
             to this server. This does not include retransmissions."
      ::= { pmRadExtAuthServerEntry 6 }

pmRadExtAuthClientAccessRetransmissions OBJECT-TYPE
      SYNTAX Counter32
      MAX-ACCESS read-only
      STATUS current
      DESCRIPTION
            "The number of RADIUS Access-Request packets
             retransmitted to this RADIUS authentication server."
      ::= { pmRadExtAuthServerEntry 7 }

pmRadExtAuthClientAccessAccepts OBJECT-TYPE
      SYNTAX Counter32
      MAX-ACCESS read-only
      STATUS current
      DESCRIPTION
            "The number of RADIUS Access-Accept packets
             (valid or invalid) received from this server."
      ::= { pmRadExtAuthServerEntry 8 }

pmRadExtAuthClientAccessRejects OBJECT-TYPE
      SYNTAX Counter32
      MAX-ACCESS read-only
      STATUS current
      DESCRIPTION
            "The number of RADIUS Access-Reject packets
             (valid or invalid) received from this server."
      ::= { pmRadExtAuthServerEntry  9 }

pmRadExtAuthClientAccessChallenges OBJECT-TYPE
      SYNTAX Counter32
      MAX-ACCESS read-only
      STATUS current
      DESCRIPTION
            "The number of RADIUS Access-Challenge packets
             (valid or invalid) received from this server."
      ::= { pmRadExtAuthServerEntry 10 }

-- "Access-Response" includes an Access-Accept, Access-Challenge
-- or Access-Reject

pmRadExtAuthClientMalformedAccessResponses OBJECT-TYPE
      SYNTAX Counter32
      MAX-ACCESS read-only
      STATUS current
      DESCRIPTION
            "The number of malformed RADIUS Access-Response
             packets received from this server.
             Malformed packets include packets with
             an invalid length. Bad authenticators or
             Signature attributes or unknown types are not
             included as malformed access responses."
      ::= { pmRadExtAuthServerEntry 11 }

pmRadExtAuthClientBadAuthenticators OBJECT-TYPE
      SYNTAX Counter32
      MAX-ACCESS read-only
      STATUS current
      DESCRIPTION
            "The number of RADIUS Access-Response packets
             containing invalid authenticators or Signature
             attributes received from this server."
      ::= { pmRadExtAuthServerEntry 12 }

pmRadExtAuthClientPendingRequests OBJECT-TYPE
      SYNTAX Gauge32
      MAX-ACCESS read-only
      STATUS current
      DESCRIPTION
            "The number of RADIUS Access-Request packets
             destined for this server, which have not yet timed out
             or received a response. This variable is incremented
             when an Access-Request is sent and is decremented due to
             receipt of an Access-Accept, Access-Reject or
             Access-Challenge, a timeout or retransmission."
      ::= { pmRadExtAuthServerEntry 13 }

pmRadExtAuthClientTimeouts OBJECT-TYPE
     SYNTAX Counter32
     MAX-ACCESS read-only
     STATUS current
     DESCRIPTION
            "The number of authentication timeouts to this server.
             After the entry timeout the client may retry to the same
             server, send to a different server, or
             give up. Retry to the same server is counted as a
             retransmit as well as a timeout. Send to a different
             server is counted as a Request as well as a timeout."
      ::= { pmRadExtAuthServerEntry  14 }

pmRadExtAuthClientUnknownTypes OBJECT-TYPE
      SYNTAX Counter32
      MAX-ACCESS read-only
      STATUS current
      DESCRIPTION
            "The number of RADIUS packets of unknown type, which
             were received from this server on the authentication port."
      ::= { pmRadExtAuthServerEntry  15 }
      
      
-- ---------------------------------------------------------- --
-- The Radius Accounting Group
-- ---------------------------------------------------------- --
-- The group for entities implementing the client side of
-- the Remote Access Dialin User Service (RADIUS) accounting
-- protocol.

pmRadExtAccServerTable OBJECT-TYPE
      SYNTAX SEQUENCE OF PmRadExtAccServerEntry
      MAX-ACCESS not-accessible
      STATUS     current
      DESCRIPTION
            "The (conceptual) table that lists the RADIUS accounting
             servers with which the client shares a secret."
      ::=  { pmRadAccClient 3 }

pmRadExtAccServerEntry OBJECT-TYPE
      SYNTAX     PmRadExtAccServerEntry
      MAX-ACCESS not-accessible
      STATUS     current
      DESCRIPTION
            "An entry (conceptual row) that represents a RADIUS
             accounting server with which the client shares a secret."
      INDEX      { pmRadExtAccServerIndex }
      ::= { pmRadExtAccServerTable 1 }

PmRadExtAccServerEntry ::= SEQUENCE {
      pmRadExtAccServerIndex                           Integer32,
      pmRadExtAccClientServerPortNumber                Integer32
}

pmRadExtAccServerIndex OBJECT-TYPE
      SYNTAX     Integer32 (1..2147483647)
      MAX-ACCESS not-accessible
      STATUS     current
      DESCRIPTION
            "A number uniquely identifying each RADIUS
             accounting server with which this client
             communicates."
      ::= { pmRadExtAccServerEntry 1 }

pmRadExtAccClientServerPortNumber  OBJECT-TYPE
      SYNTAX Integer32 (0..65535)
      MAX-ACCESS read-write
      STATUS current
      DESCRIPTION
            "The UDP port that the client is using to send requests to
             this server."
      ::= { pmRadExtAccServerEntry 4 }

-- ----------------------------------------------------------------- -- 
-- groups in the MIB  
-- ----------------------------------------------------------------- -- 

      issSystem                OBJECT IDENTIFIER ::= { privateIss 1 }
      issMirror                OBJECT IDENTIFIER ::= { privateIss 3 }
      issL2Filter              OBJECT IDENTIFIER ::= { privateIss 5 }
      issL3Filter              OBJECT IDENTIFIER ::= { privateIss 6 }
      issAclTrafficControl     OBJECT IDENTIFIER ::= { privateIss 15 }

-- ---------------------------------------------------------------- --

-- System Group 

-- System Information

issSwitchName OBJECT-TYPE 
   SYNTAX      DisplayString (SIZE(1..15))
   MAX-ACCESS  read-write 
   STATUS      current 
   DESCRIPTION 
      "System name used for identification of the device."
      DEFVAL { "ISS" }
   ::= { issSystem 1 }
issFirmwareVersion OBJECT-TYPE 
   SYNTAX      DisplayString (SIZE(1..15))
   MAX-ACCESS  read-only 
   STATUS      current 
   DESCRIPTION 
      "Version number of the Firmware."
      DEFVAL { "" }
   ::= { issSystem 3 }
issConfigSaveStatus OBJECT-TYPE
   SYNTAX     INTEGER {
              saveInProgress(1),
              saveSuccessful(2),
              saveFailed(3),
              notInitiated(4)
             }
   MAX-ACCESS  read-only
   STATUS      current
   DESCRIPTION
      "Status of configuration save operation."
   DEFVAL  { notInitiated }
   ::= { issSystem 14 }
issConfigRestoreStatus    OBJECT-TYPE
   SYNTAX      INTEGER {
               restoreInprogress(1),
               restoreSuccessful(2),
               restoreFailed(3),
               notInitiated(4)
              }
   MAX-ACCESS  read-only
   STATUS      current
   DESCRIPTION
      "The status of the switch configuration restore operation." 
   DEFVAL  { notInitiated }
   ::= { issSystem 19 }
-- Event logging related configuration / information

issLoggingOption OBJECT-TYPE
   SYNTAX      INTEGER {
               console(1),
               file(2),
               flash(3)
              }
   MAX-ACCESS  read-write
   STATUS      current
   DESCRIPTION
      "The Logging option specifying whether the logging is to be 
       done at console or to a file(system buffer) in the system.
       Flash specifies the logging of traces into a file."
       DEFVAL { console }
   ::= { issSystem 23 }

-- Remote save status

issRemoteSaveStatus OBJECT-TYPE
   SYNTAX     INTEGER {
              inprogress(1),
              successful(2),
              failed(3),
              notInitiated(4)
             }
   MAX-ACCESS  read-only
   STATUS      current
   DESCRIPTION
      "Status of remote save operation. 

       The remote save operation could be a
           a) configuration file save to remote system
           b) log file upload to remote system."
   DEFVAL  { notInitiated }
   ::= { issSystem 27 }

-- Login Authentication mechanism

issLoginAuthentication OBJECT-TYPE
   SYNTAX      INTEGER {
               local(1),
               remoteRadius(2),
               remoteTacacs(3),
               radiusFallbackToLocal(4),
               tacacsFallbackToLocal(5)

              }
   MAX-ACCESS  read-write
   STATUS      current
   DESCRIPTION
    "Configures the mechanism by which the user login has to be authenticated 
    for accessing the GUI to manage the switch. Authentication is done 
    either locally or in the remote side through a RADIUS Server or TACACS.
        If Authentication is configured as radiusLocal or tacacsLocal then
        Local authentication  provides a back door or a secondary option
        for authentication if the server fails."

   DEFVAL  { local } 
   ::= { issSystem 31 }

issSwitchBaseMacAddress OBJECT-TYPE 
   SYNTAX      MacAddress
   MAX-ACCESS  read-only 
   STATUS      current 
   DESCRIPTION 
      "Ethernet address (base address) of the Switch."
      
   DEFVAL  { '000102030405'h }
   ::= { issSystem 32 }


-- OOB Interface Existence

    issSwitchDate OBJECT-TYPE
    SYNTAX       DisplayString (SIZE(40))
    MAX-ACCESS   read-write
    STATUS       current
    DESCRIPTION

    " The date is configured in the switch in the format, 
    Hours:Minutes:Seconds Day Month Year
    e.g 19:10:31 11 08 2005

    01-12  Month - beginning from January to December
    The railway time  00 to 24 hours can be configured and 
    displayed. 
    The Display of the date is in the format ,
    WeekDay  Month  Day  Hours:Minutes:Seconds Year
    e.g 04 09 21 18:11:30 2005 

    01-07  WeekDay - beginning from Sunday to Saturday
    01-12  Month - beginning from January to December "

    ::= { issSystem 34 }


issHttpStatus  OBJECT-TYPE
   SYNTAX       INTEGER {
                enable(1),
                disable(2)
               }
   MAX-ACCESS  read-write
   STATUS      current
   DESCRIPTION
      "This object is for enabling or disabling HTTP in the system."

   DEFVAL  { enable }
   ::= { issSystem 38 }

issSwitchCurrentTemperature    OBJECT-TYPE
    SYNTAX          DisplayString 
    MAX-ACCESS      read-only
    STATUS          current
    DESCRIPTION
    "Indicates the current temperature of the switch in celsius."

     ::= {  issSystem 66 }

issMgmtInterfaceRouting OBJECT-TYPE
    SYNTAX      INTEGER {
                            enabled(1),
                            disabled(2)
                        }
    MAX-ACCESS  read-write
    STATUS      current
    DESCRIPTION
        " Enables / Disables Routing over the Management Interface.

        This object can be configured only if the Management Port
        is used for IP Access. "

    DEFVAL  { disabled }

    ::= { issSystem 90 }

issTelnetStatus  OBJECT-TYPE
    SYNTAX      INTEGER {
                    enable(1),
                    disable(2),
                    enableInProgress(3),
                    disableInProgress(4)
                }
    MAX-ACCESS  read-write
    STATUS      current
    DESCRIPTION
       "This object is for enabling or disabling the TELNET in the system.
       Set operation of enable will move this object to the enableInProgress
       first then to the enable on successfull transition. Otherwise it will
       move back to the old state. Same applies to the disable also.

       CAUTION: enableInProgress and disableInProgress are not admin
       configurable values"
    DEFVAL      { enable }
    ::= { issSystem 97 }

issSysDescription OBJECT-TYPE
    SYNTAX      DisplayString (SIZE(1..50))
    MAX-ACCESS  read-write
    STATUS      deprecated
    DESCRIPTION
            "The object which descript switch. The value is the zero-length string."
   ::= { issSystem 116 }


-- Mirror Group ------------------------------------------------------

issMirrorStatus OBJECT-TYPE 
   SYNTAX      INTEGER {
                  disabled      (1),
                  enabled       (2)
               }
   MAX-ACCESS  read-write 
   STATUS      current 
   DESCRIPTION 
       "This object is used to enable/disable mirroring
        feature in hardware.
        When set to 'disabled (1)', all mirroring configurations will be
        removed from hardware.
        When set to 'enabled (2)', all mirroring configurations
        present in software will be programmed in hardware."

   DEFVAL  { enabled }
   ::= { issMirror 1 }

-- Mirror Control Extension Table

issMirrorCtrlExtnTable OBJECT-TYPE
   SYNTAX      SEQUENCE OF IssMirrorCtrlExtnEntry
   MAX-ACCESS  not-accessible
   STATUS      current
   DESCRIPTION
      "This Table is used to configure advanced mirroring features like
       - Port Based Mirroring:
       - flow based mirroring
       - vlan based mirroring

            Following are the configuration details for Port based mirroring:
                To configure source ports in a session
               - issMirrorCtrlExtnMirrType - is set to portBased
               - issMirrorCtrlExtnSrcTable - should be used to configure list
                                             of source ports to be mirrored 
                                             in a session
               - issMirrorCtrlExtnSrcId  - represents the source port. 
                                           The port Id to be mirrored 
                                           should be given here.
               - issMirrorCtrlExtnSrcCfg - this object is used to 
                                           add/remove a port in the 
                                           source port list 

               Example
               To create a session 1 with source ports 5,6 following 
               sequence of configuration should be followed
               For table issMirrorCtrlExtnTable
               issMirrorCtrlExtnSessionIndex = 1 as index
               issMirrorCtrlExtnMirrType = portBased

               For table issMirrorCtrlExtnSrcTable
               issMirrorCtrlExtnSessionIndex = 1 as index
               issMirrorCtrlExtnSrcId  = 5 as index
               issMirrorCtrlExtnSrcCfg = add
               issMirrorCtrlExtnSessionIndex = 1 as index
               issMirrorCtrlExtnSrcId  = 6 as index
               issMirrorCtrlExtnSrcCfg = add
                    
               To configure destination ports in a session
                - issMirrorCtrlExtnDestinationTable - should be used to 
                                                      configure list of 
                                                      destination ports to be 
                                                      mirrored in a session
                    - issMirrorCtrlExtnDestination  - represents the 
                                                      destination port. The 
                                                      port Id to which packets 
                                                      should be mirrored should
                                                      be given here.
                    - issMirrorCtrlExtnDestCfg - this object is used to 
                                                 add/remove a port in the 
                                                 source port list. 
                    Example
                    To create a session 1 with destination port 10,11 following
                    sequence of configuration should be followed
                    For table issMirrorCtrlExtnTable
                    issMirrorCtrlExtnSessionIndex = 1 as index
                    issMirrorCtrlExtnMirrType = portBased

                    For table issMirrorCtrlExtnDestinationTable
                    issMirrorCtrlExtnSessionIndex = 1 as index
                    issMirrorCtrlExtnDestination  = 10 as index
                    issMirrorCtrlExtnDestCfg = add
                    issMirrorCtrlExtnSessionIndex = 1 as index
                    issMirrorCtrlExtnDestination  = 11 as index
                    issMirrorCtrlExtnDestCfg = add

               To Activate a session
                - issMirrorCtrlExtnStatus - should be used to 
                                            activate/deactivate mirroring for a
                                            session
                    Example
                    To enable mirroring for a session following sequence of 
                    configuration should be followed        
                    For table issMirrorCtrlExtnTable
                    issMirrorCtrlExtnSessionIndex = 1 as index
                    issMirrorCtrlExtnStatus = active

                Above configurations applies to flow based mirroring also, the 
                issMirrorCtrlExtnSrcId used above for configuratin ports 
                should be used to configure flow Id
                
               To enable remote monitoring of sources for a session
                - issMirrorCtrlExtnRSpanStatus - should be used to 
                                                 enable/disable remote 
                                                 monitoring for a session 
                                                 it can be used to set a 
                                                 session as source rspan 
                                                 session which implies source 
                                                 entities for this session are 
                                                 monitored remotely or can be 
                                                 used to set a session 
                                                 as destination rspan session 
                                                 which implies that mirrored 
                                                 data is received for this 
                                                 session should be forwarded to 
                                                 destination entities of this 
                                                 session
                - issMirrorCtrlExtnRSpanVlanId - it is the vlan id which is 
                                                 reserved in the network to 
                                                 carry Mirrored data,if the 
                                                 session is configured as 
                                                 source rspan session then data 
                                                 mirrored for the source 
                                                 entities will be forwarded on 
                                                 this vlan if the session is 
                                                 configured as destination 
                                                 rspan session then data 
                                                 received on this vlan will be 
                                                 forwarded to the destination 
                                                 entities of this session

            Following are the configuration details for configurating Vlan 
            based mirroring:
                To configure vlans as source for a session
               - issMirrorCtrlExtnMirrType - is set to vlanBased
               - issMirrorCtrlExtnSrcVlanTable - should be used to configure 
                                                 list of source vlans to be 
                                                 mirrored in a session
                 - issMirrorCtrlExtnSrcVlanId  - represents a source vlan. The 
                                                 vlan to be mirrored should be 
                                                 given here.
                 - issMirrorCtrlExtnSrcVlanCfg - this object is used to 
                                                 add/remove a vlan in the 
                                                 source vlan list 
                    Example
                    To create a session 1 with source list as vlan 5,6 
                    belonging to context 1 following sequence of configuration
                    should be followed
                    For table issMirrorCtrlExtnTable
                    issMirrorCtrlExtnSessionIndex = 1 as index
                    issMirrorCtrlExtnMirrType = vlanBased

                    For table issMirrorCtrlExtnSrcVlanTable
                    issMirrorCtrlExtnSrcVlanContext = 1 as index
                    issMirrorCtrlExtnSessionIndex = 1 as index
                    issMirrorCtrlExtnSrcVlanId  = 5 as index
                    issMirrorCtrlExtnSrcVlanCfg = add
                    issMirrorCtrlExtnSrcVlanContext = 1 as index
                    issMirrorCtrlExtnSessionIndex = 1 as index
                    issMirrorCtrlExtnSrcVlanId  = 6 as index
                    issMirrorCtrlExtnSrcVlanCfg = add
                    
       Entries for this table can be configured only when issMirrorStatus 
       is set to enabled.
       Configurations done through 'issMirrorCtrlTable' will change the 
       following for the first session on this table:
            - Mirroring type will be changed to port-based
            - Mode and Source entities will be overwritten 
              with the values configured through 'issMirrorCtrlTable'
            - Destination entities will be overwritten 
              with the value configured through 'issMirrorToPort' object "
   ::= { issMirror 6 } 

issMirrorCtrlExtnEntry OBJECT-TYPE
   SYNTAX      IssMirrorCtrlExtnEntry
   MAX-ACCESS  not-accessible
   STATUS      current
   DESCRIPTION
       "An entry appears in this table for each session
        in the system."
   INDEX { issMirrorCtrlExtnSessionIndex}
   ::= { issMirrorCtrlExtnTable 1 }

IssMirrorCtrlExtnEntry ::=
   SEQUENCE {
      issMirrorCtrlExtnSessionIndex
         Integer32,
      issMirrorCtrlExtnMirrType
         INTEGER,
      issMirrorCtrlExtnRSpanStatus
         INTEGER,
      issMirrorCtrlExtnRSpanVlanId
         Integer32,
      issMirrorCtrlExtnStatus
         RowStatus
  }

issMirrorCtrlExtnSessionIndex OBJECT-TYPE
   SYNTAX      Integer32 (1..20)
   MAX-ACCESS  not-accessible
   STATUS      current
   DESCRIPTION
      "The index of the mirroring session for which the configuration
      in this entry applies."
   ::= { issMirrorCtrlExtnEntry 1 }

issMirrorCtrlExtnMirrType OBJECT-TYPE
     SYNTAX       INTEGER{
                    portBased(1),
                    mac-flowBased(2),
                    vlanBased(3),
                    invalid(4),
                    ip-flowBased(5)
     }
     MAX-ACCESS   read-write
     STATUS       current
     DESCRIPTION
         "This object tells the type of mirroring this session supports.
          This object needs to be set before doing any configuration for 
          a mirroring session"
     DEFVAL       { invalid }
     ::= { issMirrorCtrlExtnEntry 2 }

issMirrorCtrlExtnRSpanStatus OBJECT-TYPE
     SYNTAX       INTEGER{
                    sourceRSpanVlan(1),
                    destinationRSpanVlan(2),
                    disabled(3)
     }
     MAX-ACCESS   read-write
     STATUS       current
     DESCRIPTION
         "This object indicates session is enabled or disabled for 
         Remote monitoring.
         If set as 'source-rspan-vlanid' indicates that the session is 
         enabled for Remote monitoring and the source entities for this 
         session will be remotely monitored.
         If set as 'destination-rspan-vlanid' indicates that the session 
         should monitor remote traffic mirrored with RSPAN VLAN ID tag.
         RSPAN VLAN ID should be configured through object 
         'issMirrorCtrlExtnRSpanVlanId'.
         If set as 'disabled' Remote monitoring is disabled for this
         mirroring session."

     DEFVAL       { disabled }
     ::= { issMirrorCtrlExtnEntry 3 }

issMirrorCtrlExtnRSpanVlanId OBJECT-TYPE
     SYNTAX       Integer32
     MAX-ACCESS   read-write
    STATUS       current
    DESCRIPTION
        "Vlan Id used for Remote monitoring for this session.
         If issMirrorCtrlExtnRSpanStatus is set to disabled, then 
         this object will have an invalid value (zero)"
     DEFVAL { 0 }
     ::= { issMirrorCtrlExtnEntry 4 }
     
issMirrorCtrlExtnStatus OBJECT-TYPE
   SYNTAX      RowStatus
   MAX-ACCESS  read-create
   STATUS      current
   DESCRIPTION
      "This object indicates the status of the entry. The entry can be 
       made active only if issMirrorCtrlExtnMirrType is configured and 
       source and destination entries for this sesion is also configured"
   ::= { issMirrorCtrlExtnEntry 6 }
  
issMirrorCtrlExtnSrcTable OBJECT-TYPE
   SYNTAX      SEQUENCE OF IssMirrorCtrlExtnSrcEntry
   MAX-ACCESS  not-accessible
   STATUS      current
   DESCRIPTION
      "A table to configure list of source entities for mirroring sessions"
   ::= { issMirror 7 }

issMirrorCtrlExtnSrcEntry OBJECT-TYPE
   SYNTAX      IssMirrorCtrlExtnSrcEntry
   MAX-ACCESS  not-accessible
   STATUS      current
   DESCRIPTION
       "An entry appears in this table for each mirroring session."
   INDEX { issMirrorCtrlExtnSessionIndex, issMirrorCtrlExtnSrcId }
   ::= { issMirrorCtrlExtnSrcTable 1 }

IssMirrorCtrlExtnSrcEntry ::=
   SEQUENCE {
      issMirrorCtrlExtnSrcId
         Integer32,
      issMirrorCtrlExtnSrcMode
         INTEGER
   }

issMirrorCtrlExtnSrcId OBJECT-TYPE
   SYNTAX      Integer32 (1..65535) 
   MAX-ACCESS  not-accessible
   STATUS      current
   DESCRIPTION
      "Specifies the source id which participates in a mirroring session.
        For Port based mirroring this object can be port IfIndex.
        To mirror Tunnel and Trunk ports the same Id can be used for 
        specifying Tunnel/Trunk Id.
        For Flow based mirroring this object can be Acl Ids."
   ::= { issMirrorCtrlExtnSrcEntry 1 }

issMirrorCtrlExtnSrcMode OBJECT-TYPE
   SYNTAX      INTEGER {
               ingress(1),
               egress(2),
               both(3),
               disable(4)
              }
   MAX-ACCESS  read-write
   STATUS      current
   DESCRIPTION
       "Provides control to set the mode of mirroring. 
        It can be ingress, egress, both or disable."
   DEFVAL  { both }
   ::= { issMirrorCtrlExtnSrcEntry 3 }

issMirrorCtrlExtnDestinationTable OBJECT-TYPE
   SYNTAX      SEQUENCE OF IssMirrorCtrlExtnDestinationEntry
   MAX-ACCESS  not-accessible
   STATUS      current
   DESCRIPTION
      "A table to configure list of destination entities"
   ::= { issMirror 9 }

issMirrorCtrlExtnDestinationEntry OBJECT-TYPE
   SYNTAX      IssMirrorCtrlExtnDestinationEntry
   MAX-ACCESS  not-accessible
   STATUS      current
   DESCRIPTION
       "An entry appears in this table for each destination entity
        in a mirroring session."
   INDEX { issMirrorCtrlExtnSessionIndex, issMirrorCtrlExtnDestination }
   ::= { issMirrorCtrlExtnDestinationTable 1 }

IssMirrorCtrlExtnDestinationEntry ::=
   SEQUENCE {
      issMirrorCtrlExtnDestination
         Integer32,
      issMirrorCtrlExtnDestAllowIng
         INTEGER
   }

issMirrorCtrlExtnDestination OBJECT-TYPE
   SYNTAX      Integer32 (1..65535) 
   MAX-ACCESS  not-accessible
   STATUS      current
   DESCRIPTION
       "Specifies the destination port id which participates in a mirroring 
        session."
   ::= { issMirrorCtrlExtnDestinationEntry 1 }

issMirrorCtrlExtnDestAllowIng OBJECT-TYPE
   SYNTAX      INTEGER{
                 disabled (1),
                enabled (2)
               }
   MAX-ACCESS  read-write
   STATUS      current
   DESCRIPTION
       "This object is used to enable/disable a destination ingress state for a session."
   ::= { issMirrorCtrlExtnDestinationEntry 3 }


-- ------------------------------------------------------------------ 
-- L2 Filter Group --------------------------------------------------

issL2FilterTable OBJECT-TYPE 

   SYNTAX      SEQUENCE OF IssL2FilterEntry
   MAX-ACCESS  not-accessible 
   STATUS      deprecated
   DESCRIPTION 
       "A table to configure L2 filter rules in the system.
       This object is deprecated and the corresponding functionality is
       met with issL2Filter objects in pmissext.mib."
   ::= { issL2Filter 1 }

issL2FilterEntry OBJECT-TYPE 
   SYNTAX      IssL2FilterEntry
   MAX-ACCESS  not-accessible 
   STATUS      deprecated
   DESCRIPTION 
       "Each entry in this table is a L2 filter rule.Index to the table
       is the L2 filter number.This object is deprecated and the 
       corresponding functionality is met with issL2Filter objects 
       in pmissext.mib."
   
   INDEX { issL2FilterNo}
   ::= { issL2FilterTable 1 }
   
IssL2FilterEntry ::= 
   SEQUENCE { 
      issL2FilterNo 
         Integer32, 
      issL2FilterPriority 
         Integer32, 
      issL2FilterEtherType
         Integer32, 
      issL2FilterProtocolType 
         Unsigned32, 
      issL2FilterDstMacAddr 
         MacAddress, 
      issL2FilterSrcMacAddr 
         MacAddress, 
      issL2FilterVlanId 
         Integer32,
      issL2FilterInPortList 
         PortList,
      issL2FilterAction 
         INTEGER,
      issL2FilterStatus
         RowStatus
  }

issL2FilterNo OBJECT-TYPE 
   SYNTAX      Integer32 (1..65535)
   MAX-ACCESS  not-accessible 
   STATUS      current 
   DESCRIPTION 
      "L2 Filter rule number.
      This object is deprecated and the corresponding functionality is
      met with issL2Filter objects in pmissext.mib."
   ::= { issL2FilterEntry 1 }
    
issL2FilterPriority OBJECT-TYPE 
   SYNTAX      Integer32 (1..255)
   MAX-ACCESS  read-write 
   STATUS      current 
   DESCRIPTION 
      "The priority of the L2 filter can be used to decide which filter rule
       is applicable when 
          --> the packet matches with more than one filter rules
          --> All the filter rules result in 'allow'ing the packet

      Higher value of 'filter priority' implies a higher priority.

      Usage of 'L2FilterPriority' is implementation dependant.
      This object is deprecated and the corresponding functionality is
      met with issL2Filter objects in pmissext.mib."
   DEFVAL  { 1 }
   ::= { issL2FilterEntry 2 }

issL2FilterEtherType OBJECT-TYPE 
   SYNTAX      Integer32 (0..65535)
   MAX-ACCESS  read-write 
   STATUS      deprecated
   DESCRIPTION 
      "The value in the Type/Len field of a frame that will
      be matched to trigger this filter. The default value of
      this object is '0'. When this object is SET with the default
      value, frames are not matched for the value in the Type/Len
      field with the value set for this object.
      This object is deprecated and the corresponding functionality is
      met with issL2Filter objects in pmissext.mib."
   DEFVAL  { 0 }
   ::= { issL2FilterEntry 3 }

   
issL2FilterProtocolType OBJECT-TYPE 
   SYNTAX      Unsigned32 (0..65535) 
   MAX-ACCESS  read-write 
   STATUS      deprecated
   DESCRIPTION 
      "Specifies the non IP protocol type to be filtered.
       aarp | amber | dec-spanning | decnet-iv | 
       diagnostic | dsm |etype-6000 | etype-8042 | 
       lat | lavc-sca | mop-console | mop-dump | 
       msdos | mumps | netbios | vines-echo |
       vines-ip | xns-idp: A non-IP protocol.

      A value of '0' means, the filter is applicable for all protocols.
      This object is deprecated and the corresponding functionality is
      met with issL2Filter objects in pmissext.mib."
   DEFVAL  { 0 }
   ::= { issL2FilterEntry 4 }

issL2FilterDstMacAddr OBJECT-TYPE 
   SYNTAX      MacAddress
   MAX-ACCESS  read-write 
   STATUS      deprecated
   DESCRIPTION 
      "Destination MAC address to be matched with the packet. By Default, the
       Destination Mac Address will be zero which means dont care condition ie)
       any Dst Mac Address .This object is deprecated and the corresponding 
       functionality is met with issL2Filter objects in pmissext.mib."
   ::= { issL2FilterEntry 5 }

issL2FilterSrcMacAddr OBJECT-TYPE 
   SYNTAX      MacAddress
   MAX-ACCESS  read-write 
   STATUS      deprecated
   DESCRIPTION 
      "Source MAC address to be matched with the packet. By Default, the Source 
       Mac Address will be zero which means dont care condition ie) any Src Mac 
       address This object is deprecated and the corresponding functionality is
       met with issL2Filter objects in pmissext.mib."
   ::= { issL2FilterEntry 6 }
    

issL2FilterVlanId OBJECT-TYPE 
   SYNTAX      Integer32 (0..4094)
   MAX-ACCESS  read-write 
   STATUS      deprecated
   DESCRIPTION 
      "Vlan Id to be filtered. In case of Provider bridges, This Vlan Id will
      be treated as customer Vlan Id. 
      A value of '0' means, this object is unused. Configuring this value is not
      allowed.
      This object is deprecated and the corresponding functionality is
      met with issL2Filter objects in pmissext.mib."
   DEFVAL  { 0 }
   ::= { issL2FilterEntry 7 }


issL2FilterInPortList OBJECT-TYPE 
   SYNTAX      PortList
   MAX-ACCESS  read-write 
   STATUS      deprecated
   DESCRIPTION 
      "Specifies the complete set of ports over which this filter is applied
       for packets ingress at ports in this list.
       If the In port list is '0', the filter rule is applicable for  the 
       incoming packets on all ports.
       Even though the issL2FilterInPortList is configured, It is applicable only
       if issL2FilterDirection is configured as 'in'.
       By default inport list is maintained as '0'.
       This object is deprecated and the corresponding functionality is
       met with issL2Filter objects in pmissext.mib."
   ::= { issL2FilterEntry 8 }

issL2FilterAction OBJECT-TYPE 
   SYNTAX      INTEGER {
                  allow (1),
                  drop  (2)
               }
   MAX-ACCESS  read-write 
   STATUS      deprecated
   DESCRIPTION 
      "Specifies the action to be taken on the packet if the filter
      rule matches.
      If the action is 'allow', the packet will be forwarded according
      to the forwarding rules.
      If the action is 'drop', the packet will be discarded.
      This object is deprecated and the corresponding functionality is
      met with issL2Filter objects in pmissext.mib."
   DEFVAL  { allow } 
   ::= { issL2FilterEntry 9 }

issL2FilterStatus OBJECT-TYPE 
   SYNTAX      RowStatus
   MAX-ACCESS  read-create 
   STATUS      deprecated
   DESCRIPTION 
        "This object indicates the status of this entry. An entry is
        created in this table when this object is SET to 'createAndWait'.
        The entry in this table is used when the status of this object 
        is SET 'active'. The entry in this table is not used when this 
        object is SET 'notInService'. An entry created in this table is
        be deleted when this object is SET 'destroy'.
        This object is deprecated and the corresponding functionality is
        met with issL2Filter objects in pmissext.mib."
   ::= { issL2FilterEntry 11 }

-- ------------------------------------------------------------------ 
-- L3 Filter Group --------------------------------------------------


issL3FilterTable OBJECT-TYPE 
   SYNTAX      SEQUENCE OF IssL3FilterEntry
   MAX-ACCESS  not-accessible 
   STATUS      deprecated
   DESCRIPTION 
       " A table to configure L3 filter rules in the system.
       This object is deprecated and the corresponding functionality is
       met with issL3Filter objects in pmissext.mib."
   ::= { issL3Filter 1 }

issL3FilterEntry OBJECT-TYPE 
   SYNTAX      IssL3FilterEntry
   MAX-ACCESS  not-accessible 
   STATUS      deprecated
   DESCRIPTION 
       " Each entry in this table is a L3 filter rule.
         Index to the table is L3 filter number.
         This object is deprecated and the corresponding functionality is
         met with issL3Filter objects in pmissext.mib."
   INDEX { issL3FilterNo}
   ::= { issL3FilterTable 1 }
   
IssL3FilterEntry ::= 
   SEQUENCE { 
      issL3FilterNo 
         Integer32, 
      issL3FilterPriority 
         Integer32, 
      issL3FilterProtocol  
         Integer32, 
      issL3FilterMessageType 
         Integer32, 
      issL3FilterMessageCode 
         Integer32, 
      issL3FilterDstIpAddr 
         IpAddress, 
      issL3FilterSrcIpAddr 
         IpAddress, 
      issL3FilterDstIpAddrMask 
         IpAddress, 
      issL3FilterSrcIpAddrMask 
         IpAddress,
      issL3FilterMinDstProtPort
         Unsigned32, 
      issL3FilterMaxDstProtPort
         Unsigned32, 
      issL3FilterMinSrcProtPort
         Unsigned32, 
      issL3FilterMaxSrcProtPort
         Unsigned32, 
      issL3FilterInPortList 
         PortList,
      issL3FilterOutPortList 
         PortList, 
      issL3FilterAckBit
         INTEGER,
      issL3FilterRstBit
         INTEGER,
      issL3FilterTos
         Integer32,
      issL3FilterDscp
         Integer32,
      issL3FilterAction 
         INTEGER,
      issL3FilterStatus
         RowStatus
  }

issL3FilterNo OBJECT-TYPE 
   SYNTAX      Integer32 (1..65535)
   MAX-ACCESS  not-accessible 
   STATUS      deprecated
   DESCRIPTION 
      "L3 Filter rule number.
      This object is deprecated and the corresponding functionality is
      met with issL3Filter objects in pmissext.mib."
   ::= { issL3FilterEntry 1 }
    
issL3FilterPriority OBJECT-TYPE 
   SYNTAX      Integer32 (1..255)
   MAX-ACCESS  read-write 
   STATUS      deprecated
   DESCRIPTION 
      "The priority of the filter can be used to decide which filter rule
       is applicable when 
          --> the packet matches with more than one filter rules
          --> All the filter rules result in 'allow'ing the packet
      Higher value of 'L3 filter priority' implies a higher priority.
      Usage of 'L3FilterPriority' is implementation dependant.
      This object is deprecated and the corresponding functionality is
      met with issL3Filter objects in pmissext.mib."
   DEFVAL  { 1 }
   ::= { issL3FilterEntry 2 }
   
issL3FilterProtocol OBJECT-TYPE 
   SYNTAX      Integer32 (0..255)
   MAX-ACCESS  read-write 
   STATUS      deprecated
   DESCRIPTION 
      " The type of protocol to be checked against the packet. The
      default value is 255. If the value is 255, it means that the
      protocol type can be anything and it will not be checked to 
      decide the action.
      This object is deprecated and the corresponding functionality is
      met with issL3Filter objects in pmissext.mib."
   DEFVAL   { 255 }
   ::= { issL3FilterEntry 3 }

issL3FilterMessageType OBJECT-TYPE 
   SYNTAX      Integer32 (0..65535)
   MAX-ACCESS  read-write 
   STATUS      deprecated
   DESCRIPTION 
     " The message type to be checked against the packet. If the
      message type matches with the packet, then the packet will be
      dropped / allowed based on the action set in issL3FilterAction.
      The default value is 255. It means that message type is not
      configured and need not be checked.
      Generally the value zero is given as default. But here
      zero can be an ICMP Type value. Hence 255 is given as the
      default value. 
      Some ICMP message types are: 
           echoReply(0),
           destinationUnreachable(3),
           sourceQuench(4),
           redirect(5),
           echoRequest(8),
           timeExceeded(11),
           parameterProblem(12),
           timestampRequest(13),
           timestampReply(14),
           informationRequest(15),
           informationReply(16),
           addressMaskRequest(17),
           addressMaskReply (18),
           noICMPType(255)
       This object is deprecated and the corresponding functionality is
       met with issL3Filter objects in pmissext.mib."
   DEFVAL  { 255 }
   ::= { issL3FilterEntry 4 }

issL3FilterMessageCode OBJECT-TYPE 
   SYNTAX      Integer32 (0..65535)
   MAX-ACCESS  read-write 
   STATUS      deprecated
   DESCRIPTION 
      " The message code to be checked against the packet. If the
      packet matches with the message code, then the packet will
      be dropped / allowed based on the action set in issL3FilterAction.
      The default value is 255. It means that message code is not 
      configured and need not be checked. Generally the value zero 
      will be given as default. But here, zero can be an ICMP Code 
      value. Hence 255 is given as the default value.
      Some ICMP message codes are :
           networkUnreachable(0),
           hostUnreachable(1),
           protocolUnreachable(2),
           portUnreachable(3),
           fragmentNeed(4),
           sourceRouteFail(5),
           destNetworkUnknown(6),
           destHostUnknown(7),
           srcHostIsolated(8),
           destNetworkAdminProhibited(9),
           destHostAdminProhibited(10),
           networkUnreachableTOS(11),
           hostUnreachableTOS(12),
           noICMPCode(255) 
      This object is deprecated and the corresponding functionality is
      met with issL3Filter objects in pmissext.mib."
   DEFVAL   { 255 }
   ::= { issL3FilterEntry 5 }     

issL3FilterDstIpAddr OBJECT-TYPE 
   SYNTAX      IpAddress
   MAX-ACCESS  read-write 
   STATUS      deprecated
   DESCRIPTION 
      "Destination IP address to be matched with the packet.
      This object is valid only if the 'issFilterType' is 'l3filter'.
      This object is deprecated and the corresponding functionality is
      met with issL3Filter objects in pmissext.mib."
   DEFVAL  { '00000000'h }
   ::= { issL3FilterEntry 6 }

issL3FilterSrcIpAddr OBJECT-TYPE 
   SYNTAX      IpAddress
   MAX-ACCESS  read-write 
   STATUS      deprecated
   DESCRIPTION 
      "Source IP address to be matched with the packet.
      This object is valid only if the 'issFilterType' is 'l3filter'
      This object is deprecated and the corresponding functionality is
      met with issL3Filter objects in pmissext.mib."
   DEFVAL  { '00000000'h }
   ::= { issL3FilterEntry 7 }

issL3FilterDstIpAddrMask OBJECT-TYPE 
   SYNTAX      IpAddress
   MAX-ACCESS  read-write 
   STATUS      deprecated
   DESCRIPTION 
      "The IP subnet mask for Destination IP address.
      This object is valid only if the 'issFilterType' is 'l3filter'
      This object is deprecated and the corresponding functionality is
      met with issL3Filter objects in pmissext.mib."
   DEFVAL  { 'FFFFFFFF'h }
   ::= { issL3FilterEntry 8 }

issL3FilterSrcIpAddrMask OBJECT-TYPE 
   SYNTAX      IpAddress
   MAX-ACCESS  read-write 
   STATUS      deprecated
   DESCRIPTION 
      "The IP subnet mask for Source IP address.
      This object is valid only if the 'issFilterType' is 'l3filter'.
      This object is deprecated and the corresponding functionality is
      met with issL3Filter objects in pmissext.mib."
   DEFVAL  { 'FFFFFFFF'h }
   ::= { issL3FilterEntry 9 }

issL3FilterMinDstProtPort OBJECT-TYPE
   SYNTAX      Unsigned32
   MAX-ACCESS  read-write
   STATUS      deprecated
   DESCRIPTION
      "The minimum port in the destination port range. Please note 
       these ports are the TCP / UDP ports.
       This object is deprecated and the corresponding functionality is
       met with issL3Filter objects in pmissext.mib."
   DEFVAL   { 0 }
   ::= { issL3FilterEntry 10 }

issL3FilterMaxDstProtPort OBJECT-TYPE
   SYNTAX      Unsigned32
   MAX-ACCESS  read-write
   STATUS      deprecated
   DESCRIPTION
      "The maximum port in the destination port range. Please note 
       these ports are the TCP / UDP ports.
       This object is deprecated and the corresponding functionality is
       met with issL3Filter objects in pmissext.mib."
   DEFVAL   { 65535 }
   ::= { issL3FilterEntry 11 }

issL3FilterMinSrcProtPort OBJECT-TYPE
   SYNTAX      Unsigned32
   MAX-ACCESS  read-write
   STATUS      deprecated
   DESCRIPTION
      "The minimum port in the source port range. Please note 
       these ports are the TCP / UDP ports.
       This object is deprecated and the corresponding functionality is
       met with issL3Filter objects in pmissext.mib."
   DEFVAL   { 0 }
   ::= { issL3FilterEntry 12 }

issL3FilterMaxSrcProtPort OBJECT-TYPE
   SYNTAX      Unsigned32
   MAX-ACCESS  read-write
   STATUS      deprecated
   DESCRIPTION
      "The maximum port in the source port range. Please note 
       these ports are the TCP / UDP ports.
       This object is deprecated and the corresponding functionality is
       met with issL3Filter objects in pmissext.mib."
   DEFVAL   { 65535 }
   ::= { issL3FilterEntry 13 }

issL3FilterInPortList OBJECT-TYPE 
   SYNTAX      PortList
   MAX-ACCESS  read-write 
   STATUS      deprecated
   DESCRIPTION 
      "Specifies the complete set of ports over which if the packet arrives
      this filter rule will be applicable.
      If the incoming port list is '0', the filter rule is applicable for all the 
      incoming ports.
      By default inport list is maintained as '0'.
      This object is deprecated and the corresponding functionality is
      met with issL3Filter objects in pmissext.mib."
   ::= { issL3FilterEntry 14 }

issL3FilterOutPortList OBJECT-TYPE 
   SYNTAX      PortList
   MAX-ACCESS  read-write 
   STATUS      deprecated
   DESCRIPTION 
      "Specifies the complete set of ports over which if the packet goes out, 
      this filter rule will be applicable.
      If the outgoing port list is '0',the filter rule is applicable for all the 
      outgoing packets in all ports.
      By default outport list is maintained as '0'
      This object is deprecated and the corresponding functionality is
      met with issL3Filter objects in pmissext.mib."
   ::= { issL3FilterEntry 15 }

issL3FilterAckBit       OBJECT-TYPE
    SYNTAX  INTEGER {
            establish(1),
                notEstablish(2),
                any(3)  
            }
    MAX-ACCESS  read-create
    STATUS      deprecated
    DESCRIPTION
        " The TCP ACK bit to be checked against the packet. The default 
        value is 'any'(3). It means that ACK bit will not be checked 
                to decide the action.
       This object is deprecated and the corresponding functionality is
       met with issL3Filter objects in pmissext.mib."
    DEFVAL  { any }
    ::= { issL3FilterEntry 16 }

issL3FilterRstBit    OBJECT-TYPE
    SYNTAX  INTEGER {
                  set(1),
              notSet(2),
              any(3)    
            }
    MAX-ACCESS  read-create
    STATUS      deprecated
    DESCRIPTION
        " The TCP RST bit to be checked against the packet. The default 
        value is 'any'(3). It means that RST bit will not be checked to 
        decide the action.
        This object is deprecated and the corresponding functionality is
       met with issL3Filter objects in pmissext.mib."
    DEFVAL  { any }
    ::= { issL3FilterEntry 17 }

issL3FilterTos      OBJECT-TYPE
    SYNTAX      Integer32 (-1..7)
    MAX-ACCESS  read-create
    STATUS      deprecated
    DESCRIPTION
        " The IP TOS bit to be checked against the packet. This is a 
        single byte integer of which the last three bits (least 
      significant bits) indicate Delay, Throughput and Reliability 
      i.e 'uuuuudtr', u-unused, d-delay, t-throughput, r-reliability.
        For example '6' indicates low delay and high throughput. 
                A value of '-1' means, the Tos Field becomes dont care
       This object is deprecated and the corresponding functionality is
       met with issL3Filter objects in pmissext.mib."
    DEFVAL  { -1 }
    ::= { issL3FilterEntry 18 }

issL3FilterDscp     OBJECT-TYPE
    SYNTAX      Integer32 (-1..63)
    MAX-ACCESS  read-create
    STATUS      deprecated
    DESCRIPTION
        " The IP Dscp value to be checked against the packet. 
        A value of '-1' means, the Dscp Field becomes dont care.
        This object is deprecated and the corresponding functionality is
        met with issL3Filter objects in pmissext.mib."
    DEFVAL  { -1 }
    ::= { issL3FilterEntry 19 }
   
issL3FilterAction OBJECT-TYPE 
   SYNTAX      INTEGER {
                  allow (1),
                  drop  (2)
               }
   MAX-ACCESS  read-write 
   STATUS      deprecated
   DESCRIPTION 
      "Specifies the action to be taken on the packet if the filter
      rule matches.
      If the action is 'allow', the packet will be sent to the
      ports in 'out port list'. If the out port list is '0', 
      the port over which the packet is to be switched will be decided
      based on further processing on the packet.
      If the action is 'drop', the packet will be discardedThis object is
      deprecated and the corresponding functionality is
      met with issL3Filter objects in pmissext.mib."
   DEFVAL  { allow } 
   ::= { issL3FilterEntry 21 }

issL3FilterStatus OBJECT-TYPE 
   SYNTAX      RowStatus
   MAX-ACCESS  read-create 
   STATUS      deprecated
   DESCRIPTION 
        "This object indicates the status of this entry. An entry is
        created in this table when this object is SET to 'createAndWait'.
        The entry in this table is used when the status of this object 
        is SET 'active'. The entry in this table is not used when this 
        object is SET 'notInService'. An entry created in this table is
        be deleted when this object is SET 'destroy.This object is 
        deprecated and the corresponding functionality is
        met with issL3Filter objects in pmissext.mib."
   ::= { issL3FilterEntry 23 }

-- Traffic Control Group ------------------------------------------ --

issAclTrafficSeperationCtrl OBJECT-TYPE 
   SYNTAX      INTEGER {
                  systemdefault (1), 
                  userconfig (2),
                  none(3)
               }
   MAX-ACCESS  read-write
   STATUS      current 
   DESCRIPTION 
      "This object provides control to administrator, to have system default or 
       user defined ACL/QoS rules to carry control traffic to CPU.

       system-default: ACL/QoS rules for all the control packets will be 
       automatically installed by the ISS software at system init time.Either a
       'switch-and-copy-to-cpu'filter (or) 'drop-and-copy-to-cpu' filter will be
       installed, as appropriate, for getting the control packets to CPU, for 
       processing. Each ACL rule will be associated with class-map, meter and 
       policy map with protocol ID, and CPU queue number

       user-config: The ACL/QoS rules for receiving all the control packets to 
       CPU for processing, will NOT be automatically installed by the the ISS 
       software.The administrator is expected to install required rules for the
       control packets as requried.

       none: ACL/QoS rules for all the control packets will be automatically
       installed by the ISS software at system init time.Either a 'switch-and-co
       py-to-cpu'filter (or) 'drop-and-copy-to-cpu' filter will be installed, 
       as appropriate, for getting the control packets to CPU, for processing.
       Default mode is none

       If the configuration is changed from 'systemdefault' to 'userconfig' 
       option, then all the default ACL/QoS rules for carrying protocol control
       packets to CPU are removed.Then user has to install the specific ACL/QoS
       rules, to carry the intended control packets to CPU for the processing.

       If the configuration is changed from 'userconfig' to 'systemdefault',
       all the default ACL/QoS rules are installed. Already existing(if any) 
       user configured ACL rules in the system are not removed.
       
       If the configuration is changed from 'none' to 'systemdefault' 
       option, then all the default ACL filters for carrying protocol control
       packets to CPU are removed and new set of filters will be installed. 
       Each filter will be associated with Qos rules.
       
       If the configuration is changed from 'none' to 'userconfig' 
       option, then all the default ACL filters for carrying protocol control
       packets to CPU are removed.Then user has to install the specific ACL/QoS
       rules, to carry the intended control packets to CPU for the processing.

       If the configuration is changed from 'userconfig' to 'none'
       all the default ACL filters are installed. Already existing(if any) 
       user configured ACL rules in the system are not removed.

       Above three options can be configured during system runtime."

   DEFVAL      { none }
   ::= { issAclTrafficControl 1 } 
--
-- Global configurations with MI support
--

pmMIStdIpGlobalTable OBJECT-TYPE
    SYNTAX SEQUENCE OF PmMIStdIpGlobalEntry
    MAX-ACCESS not-accessible
    STATUS     current
    DESCRIPTION
           "Table to store the IP configurations specific to a virtual router"
    ::= {privateMIStdIp 4 }

pmMIStdIpGlobalEntry OBJECT-TYPE
    SYNTAX     PmMIStdIpGlobalEntry
    MAX-ACCESS not-accessible
    STATUS     current
    DESCRIPTION
           "Each entry contains the IP configurations specific to a particular 
            virtual router specified the index."
    INDEX { pmMIStdIpContextId }
    ::= { pmMIStdIpGlobalTable 1 }

PmMIStdIpGlobalEntry ::= SEQUENCE {
        pmMIStdIpContextId                     Integer32,
        pmMIStdIpForwarding                    INTEGER,
        pmMIStdIpDefaultTTL                    Integer32,
        pmMIStdIpReasmTimeout                  Integer32,
        pmMIStdIpv6IpForwarding                INTEGER,
        pmMIStdIpv6IpDefaultHopLimit           Integer32,
        pmMIStdInetCidrRouteNumber             Gauge32,
        pmMIStdInetCidrRouteDiscards           Counter32
    }

pmMIStdIpContextId OBJECT-TYPE
    SYNTAX     Integer32 (0..256)
    MAX-ACCESS not-accessible
    STATUS     current
    DESCRIPTION
           "The index value that uniquely identifies the virtual router for which
            the configuration is applicable."
    ::= { pmMIStdIpGlobalEntry 1 }
pmQBridgeMIB OBJECT IDENTIFIER ::= { privateQBridgeMIB 7 }
pmQBridgeMIBObjects  OBJECT IDENTIFIER ::= { pmQBridgeMIB 1 }
-- -------------------------------------------------------------
-- groups in the Q-BRIDGE MIB
-- -------------------------------------------------------------

pmDot1qBase       OBJECT IDENTIFIER ::= { pmQBridgeMIBObjects 1 }
pmDot1qTp         OBJECT IDENTIFIER ::= { pmQBridgeMIBObjects 2 }
pmDot1qStatic     OBJECT IDENTIFIER ::= { pmQBridgeMIBObjects 3 }
pmDot1qVlan       OBJECT IDENTIFIER ::= { pmQBridgeMIBObjects 4 }

-- -------------------------------------------------------------
-- fsDot1qBase group
-- -------------------------------------------------------------

pmDot1qBaseTable OBJECT-TYPE
   SYNTAX        SEQUENCE OF PmDot1qBaseEntry
   MAX-ACCESS    not-accessible
   STATUS        current
   DESCRIPTION
      "List of pmDot1qBase objects that can be configured per 
      virtual context in the system."
   ::= { pmDot1qBase 1 }

pmDot1qBaseEntry OBJECT-TYPE
   SYNTAX        PmDot1qBaseEntry
   MAX-ACCESS    not-accessible
   STATUS        current
   DESCRIPTION
      "Virtual context pmDot1qBase objects."
   INDEX { pmDot1qVlanContextId }
   ::= { pmDot1qBaseTable 1 }

PmDot1qBaseEntry ::=
    SEQUENCE {
        pmDot1qVlanContextId
           Integer32,
        pmDot1qVlanVersionNumber
           INTEGER,
        pmDot1qMaxVlanId 
           VlanId,
        pmDot1qMaxSupportedVlans 
           Unsigned32,
        pmDot1qNumVlans 
           Unsigned32,
        pmDot1qGvrpStatus 
           EnabledStatus
}

pmDot1qVlanContextId OBJECT-TYPE
   SYNTAX       Integer32 (0..65535)
   MAX-ACCESS   not-accessible
   STATUS       current
   DESCRIPTION
      "Identifies a virtual context."
   ::= { pmDot1qBaseEntry 1 }
   
-- -------------------------------------------------------------
-- the pmDot1qTp group
-- -------------------------------------------------------------

pmDot1qFdbTable OBJECT-TYPE
    SYNTAX      SEQUENCE OF PmDot1qFdbEntry
    MAX-ACCESS  not-accessible
    STATUS      current
    DESCRIPTION
        "A table that contains configuration and control
        information for each Filtering Database currently
        operating on this device.  Entries in this table appear
        automatically when VLANs are assigned FDB IDs in the
        pmDot1qVlanCurrentTable. This table maintains context ID
        as one more index to support Multiple Instances."
    ::= { pmDot1qTp 1 }

pmDot1qFdbEntry OBJECT-TYPE
    SYNTAX      PmDot1qFdbEntry
    MAX-ACCESS  not-accessible
    STATUS      current
    DESCRIPTION
        "Information about a specific Filtering Database."
    INDEX   { pmDot1qVlanContextId, pmDot1qFdbId }
    ::= { pmDot1qFdbTable 1 }

PmDot1qFdbEntry ::=
    SEQUENCE {
        pmDot1qFdbId
            Unsigned32,
        pmDot1qFdbDynamicCount
            Counter32
    }

pmDot1qFdbId OBJECT-TYPE
    SYNTAX       Unsigned32
    MAX-ACCESS   not-accessible
    STATUS       current
    DESCRIPTION
        "The identity of this Filtering Database."
    ::= { pmDot1qFdbEntry 1 }

-- -------------------------------------------------------------
-- Multiple Forwarding Databases for 802.1Q Transparent devices
-- This table is an alternative to the fsDot1dTpFdbTable,
-- previously defined for 802.1D devices which only support a
-- single Forwarding Database.
-- -------------------------------------------------------------

pmDot1qTpFdbTable OBJECT-TYPE
    SYNTAX      SEQUENCE OF PmDot1qTpFdbEntry
    MAX-ACCESS  not-accessible
    STATUS      current
    DESCRIPTION
        "A table that contains information about unicast entries
        for which the device has forwarding and/or filtering
        information.  This information is used by the
        transparent bridging function in determining how to
        propagate a received frame. This table maintains context ID
        as one more index to support Multiple Instances."
    REFERENCE
        "IEEE 802.1Q/D11 Section 12.7.7"
    ::= { pmDot1qTp 2 }

pmDot1qTpFdbEntry OBJECT-TYPE
    SYNTAX      PmDot1qTpFdbEntry
    MAX-ACCESS  not-accessible
    STATUS      current
    DESCRIPTION
        "Information about a specific unicast MAC address for
        which the device has some forwarding and/or filtering
        information."
    INDEX   { pmDot1qVlanContextId, pmDot1qFdbId, pmDot1qTpFdbAddress }
    ::= { pmDot1qTpFdbTable 1 }

PmDot1qTpFdbEntry ::=
    SEQUENCE {
        pmDot1qTpFdbAddress
            MacAddress,
        pmDot1qTpFdbPort
            Integer32,
        pmDot1qTpFdbStatus
            INTEGER,
        pmDot1qTpFdbPw
            Unsigned32
    }

pmDot1qTpFdbAddress OBJECT-TYPE
    SYNTAX      MacAddress
    MAX-ACCESS  not-accessible
    STATUS      current
    DESCRIPTION
        "A unicast MAC address for which the device has
        forwarding and/or filtering information."
    ::= { pmDot1qTpFdbEntry 1 }

pmDot1qTpFdbPort OBJECT-TYPE
    SYNTAX      Integer32 (0..65535)
    MAX-ACCESS  read-only
    STATUS      current
    DESCRIPTION
        "Either the value '0', or the port number of the port on
        which a frame having a source address equal to the value
        of the corresponding instance of pmDot1qTpFdbAddress has
        been seen.  A value of '0' indicates that the port
        number has not been learned but that the device does
        have some forwarding/filtering information about this
        address (e.g. in the pmDot1qStaticUnicastTable).
        Implementors are encouraged to assign the port value to
        this object whenever it is learned even for addresses
        for which the corresponding value of pmDot1qTpFdbStatus is
        not learned(3)."
    ::= { pmDot1qTpFdbEntry 2 }

-- -------------------------------------------------------------
-- Dynamic Group Registration Table
-- -------------------------------------------------------------

pmDot1qTpGroupTable OBJECT-TYPE
    SYNTAX      SEQUENCE OF PmDot1qTpGroupEntry
    MAX-ACCESS  not-accessible
    STATUS      current
    DESCRIPTION
        "A table containing filtering information for VLANs
        configured into the bridge by (local or network)
        management, or learnt dynamically, specifying the set of
        ports to which frames received on a VLAN for this FDB
        and containing a specific Group destination address are
        allowed to be forwarded. This table maintains context ID 
	as one more index to support Multiple Instances."
    ::= { pmDot1qTp 3 }

pmDot1qTpGroupEntry OBJECT-TYPE
    SYNTAX      PmDot1qTpGroupEntry
    MAX-ACCESS  not-accessible
    STATUS      current
    DESCRIPTION
        "Filtering information configured into the bridge by
        management, or learnt dynamically, specifying the set of
        ports to which frames received on a VLAN and containing
        a specific Group destination address, are allowed to be
        forwarded.  The subset of these ports learnt dynamically
        is also provided."
    INDEX   { pmDot1qVlanContextId, 
              pmDot1qVlanIndex, pmDot1qTpGroupAddress, pmDot1qTpPort }
    ::= { pmDot1qTpGroupTable 1 }

PmDot1qTpGroupEntry ::=
    SEQUENCE {
        pmDot1qVlanIndex
	    VlanIndex,
        pmDot1qTpGroupAddress
            MacAddress,
	pmDot1qTpPort
	    Integer32,
        pmDot1qTpGroupIsLearnt
            TruthValue
    }

pmDot1qVlanIndex OBJECT-TYPE
    SYNTAX      VlanIndex
    MAX-ACCESS  not-accessible
    STATUS      current
    DESCRIPTION
        "The VLAN-ID or other identifier referring to this VLAN."
    ::= { pmDot1qTpGroupEntry 1 }

pmDot1qTpGroupAddress OBJECT-TYPE
    SYNTAX      MacAddress
    MAX-ACCESS  not-accessible
    STATUS      current
    DESCRIPTION
        "The destination Group MAC address in a frame to which
        this entry's filtering information applies."
    ::= { pmDot1qTpGroupEntry 2 }

pmDot1qTpPort OBJECT-TYPE 
    SYNTAX      Integer32 (1..65535) 
    MAX-ACCESS  not-accessible 
    STATUS      current 
    DESCRIPTION 
       "The port number of the port for which this entry applies." 
    ::= { pmDot1qTpGroupEntry 3 }

-- -------------------------------------------------------------
-- The Static (Destination-Address Filtering) Database
-- -------------------------------------------------------------

pmDot1qStaticUnicastTable OBJECT-TYPE
    SYNTAX      SEQUENCE OF PmDot1qStaticUnicastEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only. This table maintains context ID as 
	one more index to support Multiple Instances."
    REFERENCE
        "IEEE 802.1Q/D11 Section 12.7.7,
        ISO/IEC 15802-3 Section 7.9.1"
    ::= { pmDot1qStatic 1 }

pmDot1qStaticUnicastEntry OBJECT-TYPE
    SYNTAX      PmDot1qStaticUnicastEntry
    MAX-ACCESS  not-accessible
    STATUS      current
    DESCRIPTION
        "Filtering information configured into the device by
        (local or network) management specifying the set of
        ports to which frames received from a specific port and
        containing a specific unicast destination address are
        allowed to be forwarded."
    INDEX   {
        pmDot1qVlanContextId, 
	pmDot1qFdbId,
        pmDot1qStaticUnicastAddress,
        pmDot1qStaticUnicastReceivePort
    }
    ::= { pmDot1qStaticUnicastTable 1 }

PmDot1qStaticUnicastEntry ::=
    SEQUENCE {
        pmDot1qStaticUnicastAddress
            MacAddress,
        pmDot1qStaticUnicastReceivePort
            Integer32,
        pmDot1qStaticUnicastRowStatus
            RowStatus,
        pmDot1qStaticUnicastStatus
            INTEGER
    }

pmDot1qStaticUnicastAddress OBJECT-TYPE
    SYNTAX      MacAddress
    MAX-ACCESS  not-accessible
    STATUS      current
    DESCRIPTION
        "The destination MAC address in a frame to which this
        entry's filtering information applies.  This object must
        take the value of a unicast address."
    ::= { pmDot1qStaticUnicastEntry 1 }

pmDot1qStaticUnicastReceivePort OBJECT-TYPE
    SYNTAX      Integer32 (0..65535)
    MAX-ACCESS  not-accessible
    STATUS      current
    DESCRIPTION
        "Either the value '0', or the port number of the port
        from which a frame must be received in order for this
        entry's filtering information to apply.  A value of zero
        indicates that this entry applies on all ports of the
        device for which there is no other applicable entry."
    ::= { pmDot1qStaticUnicastEntry 2 }


-- -------------------------------------------------------------
-- The Static VLAN Database
-- -------------------------------------------------------------

pmDot1qVlanStaticTable OBJECT-TYPE
    SYNTAX      SEQUENCE OF PmDot1qVlanStaticEntry
    MAX-ACCESS  not-accessible
    STATUS      current
    DESCRIPTION
        "A table containing static configuration information for
        each VLAN configured into the device by (local or
        network) management.  All entries are permanent and will
        be restored after the device is reset. This table
        maintains context ID as one more index to support
        Multiple Instance."
    ::= { pmDot1qVlan 4 }

pmDot1qVlanStaticEntry OBJECT-TYPE
    SYNTAX      PmDot1qVlanStaticEntry
    MAX-ACCESS  not-accessible
    STATUS      current
    DESCRIPTION
        "Static information for a VLAN configured into the
        device by (local or network) management."
    INDEX   { pmDot1qVlanContextId, pmDot1qVlanIndex }
    ::= { pmDot1qVlanStaticTable 1 }

PmDot1qVlanStaticEntry ::=
    SEQUENCE {
        pmDot1qVlanStaticName
            SnmpAdminString,
        pmDot1qVlanStaticRowStatus
            RowStatus
    }

pmDot1qVlanStaticName OBJECT-TYPE
    SYNTAX      SnmpAdminString (SIZE (0..32))
    MAX-ACCESS  not-accessible
    STATUS      current
    DESCRIPTION
        "An administratively assigned string, which may be used
        to identify the VLAN."
    REFERENCE
        "IEEE 802.1Q/D11 Section 12.10.2.1"
    ::= { pmDot1qVlanStaticEntry 1 }

pmDot1qVlanStaticRowStatus OBJECT-TYPE
    SYNTAX      RowStatus
    MAX-ACCESS  not-accessible
    STATUS      current
    DESCRIPTION
        "This object is used to set/indicate the status of the
        static vlan entry. Setting the status as NOT_IN_SERVICE stops
        the data flow for this Vlan.

        This table will only create/delete a Vlan. To set the member ports
        for the Vlan configure the table - fsDot1qVlanStaticPortConfigTable.

        To create a new VLAN and assign member ports to it set the rowstatus
        object in this table as 'CREATE_AND_WAIT', set the appropriate port
        in the fsDot1qVlanStaticPortConfigTable and finally set the rowstatus
        in this table as 'ACTIVE'.

        To update the member ports of an existing Vlan
            - EITHER set the rowstatus object in this table as
              'NOT_IN_SERVICE', add/delete the appropriate ports in the
              fsDot1qVlanStaticPortConfigTable and finally 'apply' the
              changes by setting the rowstatus in this table as 'ACTIVE'.
            - OR directly add/delete the ports in the
              fsDot1qVlanStaticPortConfigTable on the fly without changing
              the Vlan status."
    ::= { pmDot1qVlanStaticEntry 2 }
-- ----------------------------------------------------------------- -- 
-- groups in the MIB  
-- ----------------------------------------------------------------- -- 

pmQoSMIBObjects     OBJECT IDENTIFIER ::= { privateQoSMib 1 }

-- System Object to support system specific scalars.
pmQoSSystem             OBJECT IDENTIFIER ::= { pmQoSMIBObjects 1 }

-- Class Table
pmQoSClass         OBJECT IDENTIFIER ::= { pmQoSMIBObjects 2 }

-- Policy Table : Meter and Action tables
pmQoSPolicy             OBJECT IDENTIFIER ::= { pmQoSMIBObjects 3 }

-- Traffic Management Tables for shaping , managing queues and scheduling them
pmQoSTrafficMgmt        OBJECT IDENTIFIER ::= { pmQoSMIBObjects 4 }

pmQoSSystemControl OBJECT-TYPE
    SYNTAX      INTEGER { shutdown(0), start(1) }
    MAX-ACCESS  read-write
    STATUS      current
    DESCRIPTION
               "Starts or shutdowns QoS Module in the system.
                When set as 'start',resources required by QoS module are
                allocated & QoS module starts running.
                When shutdown, all the pools used by QoS module will be 
                released to the system."
    ::= { pmQoSSystem  1 }

pmQoSStatus OBJECT-TYPE
    SYNTAX      INTEGER { disabled(0), enabled(1) }
    MAX-ACCESS  read-write
    STATUS      current
    DESCRIPTION
               "Enables or Disables QoS Module in the system.
                When set as 'enabled', QoS module programs the hardware
                and starts Protocol Operation.
                When set as 'disabled', it stops protocol operation by 
                deleting the hardware configuration.
                If any mib table supports global configurations (less-specific) 
                at runtime and H/W supports more-specific configurations,                  
                then appropriate behaviour may take effect in H/W only after next 
                status change of this object."
    DEFVAL { enabled }
    ::= { pmQoSSystem  2 }

pmQoSTrcFlag     OBJECT-TYPE
    SYNTAX      Unsigned32 (0..255)
    MAX-ACCESS  read-write
    STATUS      current
    DESCRIPTION 
             "This object is used to enable trace statements in QoS module. 
              A four byte integer is used for enabling the trace level.  
              Each bit in the four byte integer represents a particular  
              trace level.  
              The mapping between the bit positions & the trace level is  
              as follows:  
                      0 - Init and Shutdown traces 
                      1 - Management traces 
                      2 - Data Path traces 
                      3 - Control Plane traces 
                      5 - Traces related to all resources except buffers 
                      6 - Buffer allocation/release traces 
                      7 - All Failure traces 
                      None of the bit is set the Disable the Trace,value(0). 

              The remaining bits are unused. Combination of levels are  
              also allowed. 
 
              For example if the bits 0 and 1 are set, then the trace 
              statement related to Init-Shutdown and management  
              will be printed. 
 
              The user has to enter the corresponding integer value for the 
              bits set. For example if bits 0 and 1 are to be set ,then user
              has to give the value 3." 
    ::= { pmQoSSystem  3 }

pmQoSRateUnit OBJECT-TYPE
    SYNTAX   INTEGER 
             {
                 bps(1),
                 kbps(2),
                 mbps(3),
                 gbps(4)
             }
    MAX-ACCESS  read-only
    STATUS      current
    DESCRIPTION    "This Object indicates the unit for the 
                    Information Rate(CIR,EIR,PIR,PTR,CTR ...)values 
                    based on target platform.
                    This  Object  specifies the unit alone. Value corresponding 
                    to this unit should be taken from 'pmQoSRateGranularity' 
                    Ex 1:
                    'pmQoSRateUnit'        = kbps
                    'pmQoSRateGranularity' =  64 
                    then this target will accept the  Information 
                    Rate(CIR,EIR,TIR,PTR, CTR ...) values in multiples of 64
                    like 64 kbps, 128 kbps ...
                    Ex 2: 
                    'pmQoSRateUnit'        = mbps
                    'pmQoSRateGranularity' =  64 
                    then this target will accept the  Information 
                    Rate(CIR,EIR,TIR,PTR, CTR ...) values in multiples of 64
                    like 64 mbps, 128 mbps ..."

    ::= { pmQoSSystem  4 }

pmQoSRateGranularity OBJECT-TYPE
    SYNTAX          Unsigned32
    MAX-ACCESS      read-only
    STATUS          current
    DESCRIPTION     "This Object indicates the acceptable Granularity level
                    for configuring the Information Rate(CIR,EIR,PIR,PTR,
                    CTR ...)values for a target platform.
                    This  Object specifies the Integer Value for the 
                    granularity. Unit for 
                    this value should be taken from 'pmQoSRateUnit' 
                    Ex 1: 
                    'pmQoSRateUnit'        = kbps
                    'pmQoSRateGranularity' =  64 
                    then this target will accept the  Information 
                    Rate(CIR,EIR,TIR,PTR, CTR ...) values in multiples of 64
                    like 64 kbps, 128 kbps ...
                    Ex 2: 
                    'pmQoSRateUnit'        = mbps
                    'pmQoSRateGranularity' =  64 
                    then this target will accept the  Information 
                    Rate(CIR,EIR,TIR,PTR, CTR ...) values in multiples of 64
                    like 64 mbps, 128 mbps ..."
    ::= { pmQoSSystem  5 }

-- ------------------------------------------------------------------ 
-- Priority Map Table 
-- ------------------------------------------------------------------ 

pmQoSPriorityMapTable OBJECT-TYPE
    SYNTAX       SEQUENCE OF PmQoSPriorityMapEntry
    MAX-ACCESS   not-accessible
    STATUS       current
    DESCRIPTION
        "A table to map incoming priority to a regenerated priority. 
        This table is used to regenerate port/VLAN priorities for an 
        incoming packet. It can be used to directly program priority 
        tables in the hardware."
    ::= { pmQoSClass 1 }

pmQoSPriorityMapEntry OBJECT-TYPE
    SYNTAX      PmQoSPriorityMapEntry
    MAX-ACCESS  not-accessible
    STATUS      current
    DESCRIPTION
        "An entry to map an incoming priority, drop-precedence to a 
        regenerated priority value for an ingress PORT/VLAN. The PORT/VLAN 
        indices may take dont-care (0) values as required." 
    INDEX   { pmQoSPriorityMapID }
    ::= { pmQoSPriorityMapTable 1 }

PmQoSPriorityMapEntry ::=
    SEQUENCE {
        pmQoSPriorityMapID                   IndexInteger,
        pmQoSPriorityMapIfIndex              Unsigned32,
        pmQoSPriorityMapVlanId               Unsigned32, 
        pmQoSPriorityMapInPriority           Integer32,
        pmQoSPriorityMapInPriType            INTEGER,
        pmQoSPriorityMapRegenPriority        Unsigned32,
        pmQoSPriorityMapRegenInnerPriority   Unsigned32,
        pmQoSPriorityMapStatus               RowStatus
    }

pmQoSPriorityMapID OBJECT-TYPE
    SYNTAX      IndexInteger
    MAX-ACCESS  not-accessible 
    STATUS      current
    DESCRIPTION
        " The output priority map index for the incoming packet received over
          ingress PORT/VLAN with specified incoming priority. This is unique for
          each entry in the priority-map table."
    ::= { pmQoSPriorityMapEntry 1 }

 pmQoSPriorityMapIfIndex  OBJECT-TYPE
    SYNTAX      Unsigned32
    MAX-ACCESS  read-write 
    STATUS      current
    DESCRIPTION
        "Incoming Port Number. The PORT may take dont-care (0) values 
         as required."
   DEFVAL { 0 }
    ::= { pmQoSPriorityMapEntry 3 }

pmQoSPriorityMapVlanId OBJECT-TYPE
    SYNTAX      Unsigned32
    MAX-ACCESS  read-write 
    STATUS      current
    DESCRIPTION "Vlan Id for Priority regeneration.The VlanId may 
                 take dont-care (0) values as required."
   DEFVAL { 0 }
    ::= { pmQoSPriorityMapEntry 4 }

pmQoSPriorityMapInPriority OBJECT-TYPE
    SYNTAX      Integer32 (0..63)
    MAX-ACCESS  read-write
    STATUS      current
    DESCRIPTION
        "The incoming Priority value determined for the received frame.
        This value is equivalent to the priority( VLAN (4 bit)/DSCP( 6 bit)
        priority bits) indicated in the received frame, or one of the 
        evaluated priorities."
   DEFVAL { 0 } 
    ::= { pmQoSPriorityMapEntry 5 }

pmQoSPriorityMapInPriType OBJECT-TYPE
    SYNTAX      INTEGER { vlanPri(0),
                          ipTos(1),
                          ipDscp(2),
                          mplsExp(3),
                          vlanDEI(4)
                        }
 
    MAX-ACCESS  read-write 
    STATUS      current
    DESCRIPTION
        "The Incoming Priority Type is used to Identify the 
        'pmQoSPriorityMapInPriority' value is a VLAN PRI or IP TOS or IP DSCP
         or MPLS EXP. if the Type is vlanDEI the we can set 
         'pmQoSPriorityMapInPriority' and 'pmQoSPriorityMapRegenPriority' as
         0 or 1"
   DEFVAL { 0 } 
    ::= { pmQoSPriorityMapEntry 6 }
 
pmQoSPriorityMapRegenPriority OBJECT-TYPE
    SYNTAX      Unsigned32 (0..63)
    MAX-ACCESS  read-write
    STATUS      current
    DESCRIPTION
        "The Regenerated Priority value determined for the received frame."
   DEFVAL { 0 } 
    ::= { pmQoSPriorityMapEntry 7 }

pmQoSPriorityMapRegenInnerPriority OBJECT-TYPE
    SYNTAX      Unsigned32 (0..8)
    MAX-ACCESS  read-write
    STATUS      current
    DESCRIPTION
        "The Regenerated Inner-VLAN (CVLAN) Priority value determined
        for the received frame. It the Values is 8 then this object is not
        configured by user"
    ::= { pmQoSPriorityMapEntry 8 }

pmQoSPriorityMapStatus OBJECT-TYPE
    SYNTAX      RowStatus 
    MAX-ACCESS  read-create
    STATUS      current
    DESCRIPTION 
       "The status of this conceptual row. All writable objects in this
       row may be modified at any time. 
       It can be deleted 'destroy', only if it is not referenced 
       by other table; otherwise returns inconsistentValue error. 
       For any mib table that supports global configurations (less-specific) at runtime  
       and H/W supports more-specific configurations, if a more-specific entry is deleted 
       by configuration, then the next less-specific entry gets programmed to H/W"
    ::= { pmQoSPriorityMapEntry 10 }

-- -------------------------------------------------------------------------- 
-- ClassToPriority Table
-- -------------------------------------------------------------------------- 

pmQoSClassToPriorityTable OBJECT-TYPE
    SYNTAX       SEQUENCE OF PmQoSClassToPriorityEntry
    MAX-ACCESS   not-accessible
    STATUS       current
    DESCRIPTION
        "This table assigns local priority values for a input CLASS. This table
         is optional and can be configured as per user requirement. This table
         is provided for easy mapping of CLASS to priority values. 
         A set of non-contiguous CLASS values belong to a 
         unique Group ( identified by a group name)."
    ::= { pmQoSClass 3 }

pmQoSClassToPriorityEntry OBJECT-TYPE
    SYNTAX       PmQoSClassToPriorityEntry
    MAX-ACCESS   not-accessible
    STATUS   current
    DESCRIPTION
       "An entry to specify a regenerated priority value for a input CLASS."
    INDEX { pmQoSClassToPriorityCLASS }
    ::= { pmQoSClassToPriorityTable 1 }

-- This table maps a CLASS to a regenerated priority value.
PmQoSClassToPriorityEntry ::= SEQUENCE {
    pmQoSClassToPriorityCLASS            IndexInteger, 
    pmQoSClassToPriorityRegenPri         Unsigned32, 
    pmQoSClassToPriorityGroupName        DisplayString
}

pmQoSClassToPriorityCLASS OBJECT-TYPE
    SYNTAX      IndexInteger
    MAX-ACCESS  not-accessible 
    STATUS      current
    DESCRIPTION
        "This represents the Traffic CLASS to which an incoming frame pattern
         is classified. The administrator needs to define the traffic 
         class patterns that represent this CLASS. Multiple 
         ACL/priority-map entries can map to the same CLASS value."
    ::= { pmQoSClassToPriorityEntry 1 }

pmQoSClassToPriorityRegenPri OBJECT-TYPE
    SYNTAX      Unsigned32 (0..7)
    MAX-ACCESS  read-write
    STATUS      current
    DESCRIPTION
        "The Regenerated Priority value determined for the input CLASS."
    ::= { pmQoSClassToPriorityEntry 2 }

pmQoSClassToPriorityGroupName  OBJECT-TYPE
    SYNTAX         DisplayString (SIZE(1..31)) 
    MAX-ACCESS     read-write
    STATUS         current
    DESCRIPTION
        "This is for unique identification of the group to which a input
        CLASS belongs."
    ::= { pmQoSClassToPriorityEntry 3 }

-- ------------------------------------------------------------------ 
-- Meter Table
-- ------------------------------------------------------------------ 
-- The below is as per RFC 3289 ( std qos difpmerv mib). 

-- This MIB supports a variety of Meters.  It includes a specific
-- definition for Token Bucket Meter, which are but one type of
-- specification. 

-- Configuration of various meter parameters is as follows :
-- AvgRate meter 
-- Average Rate = CIR
-- Avg. Interval = Interval

-- srTCM meters (RFC 2697) can be specified using CIR, CBS and EBS.

-- trTCM meters (RFC 2698) can be specified using CIR, CBS, PIR, PBS where
-- PIR = EIR, 
-- PBS = EBS. 

-- tswTCM meters (RFC 2859) can be specified using CTR, PTR and Avg. Interval 
-- where
-- CTR = CIR,
-- PTR = EIR
-- Average Interval = Interval.

--  MEF based meter bandwidth attributes -
--  CIR, EIR , CBS, EBS where EBS should mean max burst size. 
--  single bucket parameters - CIR, CBS, EBS
--  dual bucket parameters - CIR, EIR, CBS and EBS where EIR - max rate
--

pmQoSMeterTable OBJECT-TYPE
    SYNTAX       SEQUENCE OF PmQoSMeterEntry
    MAX-ACCESS   not-accessible
    STATUS       current
    DESCRIPTION
       "This table enumerates specific meters that a system may use to
       police a stream of traffic. This may include all traffic on an
       interface."
    ::= { pmQoSPolicy 1 }

pmQoSMeterEntry OBJECT-TYPE
    SYNTAX       PmQoSMeterEntry
    MAX-ACCESS   not-accessible
    STATUS       current
    DESCRIPTION
       "An entry in the meter table describes a single conformance level
       of a meter."
    INDEX { pmQoSMeterId }
    ::= { pmQoSMeterTable 1 }

PmQoSMeterEntry ::= SEQUENCE  {
    pmQoSMeterId                                  IndexInteger,
    pmQoSMeterType                                MeterType,
    pmQoSMeterInterval                            Unsigned32,
    pmQoSMeterColorMode                           MeterColorMode,
    pmQoSMeterCIR                                 Unsigned32,
    pmQoSMeterCBS                                 Unsigned32,
    pmQoSMeterEIR                                 Unsigned32,
    pmQoSMeterEBS                                 Unsigned32,
    pmQoSMeterNext                                Unsigned32,
    pmQoSMeterStatus                              RowStatus
}

pmQoSMeterId OBJECT-TYPE
    SYNTAX       IndexInteger
    MAX-ACCESS   not-accessible
    STATUS       current
    DESCRIPTION
       "An index that enumerates the Meter entries." 
    ::= { pmQoSMeterEntry 1 }

pmQoSMeterType OBJECT-TYPE
    SYNTAX       MeterType 
    MAX-ACCESS   read-write
    STATUS       current
    DESCRIPTION
       "The Metering algorithm associated with the Token Bucket meter."
    ::= { pmQoSMeterEntry 3 }

pmQoSMeterInterval OBJECT-TYPE
    SYNTAX       Unsigned32 (0..10000)
    UNITS        "microseconds"
    MAX-ACCESS   read-write
    STATUS       current
    DESCRIPTION
       "The time interval used with the token bucket.  For:
       1. Average Rate Meter, the Informal Differentiated Services Model
          section 5.2.1, - Delta.
       2. Simple Token Bucket Meter, the Informal Differentiated
          Services Model section 5.1, - time interval t.
       3. RFC 2859 TSWTCM, - AVG_INTERVAL.
       4. RFC 2697 srTCM, RFC 2698 trTCM, - token bucket update time
          interval."
    DEFVAL { 0 }
    ::= { pmQoSMeterEntry 4 }

pmQoSMeterColorMode    OBJECT-TYPE
    SYNTAX      MeterColorMode
    MAX-ACCESS  read-write
    STATUS      current
    DESCRIPTION "The user defined Meter Color Mode."
    DEFVAL  { colorBlind }
    ::= { pmQoSMeterEntry 5 }

pmQoSMeterCIR OBJECT-TYPE 
    SYNTAX       Unsigned32 (0..65535)
    MAX-ACCESS  read-write
    STATUS      current 
    DESCRIPTION 
       "The committed information rate as per MEF. 
        Must be >= 0. CIR must be less than or equal to  EIR, if EIR > 0"
    ::= { pmQoSMeterEntry 6 }

pmQoSMeterCBS OBJECT-TYPE 
    SYNTAX      Unsigned32 (0..65535)
    UNITS       "Bytes"
    MAX-ACCESS  read-write
    STATUS      current 
    DESCRIPTION 
        "The committed burst size as per MEF. Must be > 0 if CIR > 0.
         Maximum allowable size will be jumbo frame size."
    ::= { pmQoSMeterEntry 7 }

pmQoSMeterEIR OBJECT-TYPE 
    SYNTAX       Unsigned32 (0..65535)
    MAX-ACCESS   read-write
    STATUS       current 
    DESCRIPTION 
       "The excess information rate as per MEF. 
        Must be >= 0. EIR must be greater than or equal to CIR,
        if EIR > 0.  This is not applicable when MeterType is srtcm."
    ::= { pmQoSMeterEntry 8 }

pmQoSMeterEBS OBJECT-TYPE 
    SYNTAX      Unsigned32 (0..65535)
    UNITS       "Bytes"
    MAX-ACCESS  read-write
    STATUS      current 
    DESCRIPTION "The excess burst size as per MEF. Must be > 0 if EIR > 0."
    ::= { pmQoSMeterEntry 9 }

pmQoSMeterNext OBJECT-TYPE
    SYNTAX       Unsigned32 (0..65535)
    MAX-ACCESS   read-write
    STATUS       current
    DESCRIPTION
       "This specifies the meter entry ID to be used for applying the 
       second/next level of conformance on the incoming packet. A valid 
       value of this object is not mandatory for the creation of an 
       entry in the conceptual row."
    DEFVAL { 0 } 
    ::= { pmQoSMeterEntry 10 }

pmQoSMeterStatus OBJECT-TYPE
    SYNTAX       RowStatus
    MAX-ACCESS   read-create
    STATUS       current
    DESCRIPTION
       "The status of this conceptual row. All writable objects in this
       row may be modified only of the Entry is not ACTIVE.
       It can be deleted 'destroy', only if it is not referenced 
       by other table; otherwise return inconsistentValue error."
    ::= { pmQoSMeterEntry 11 }


-- ------------------------------------------------------------------ 
-- Policy-Map Table ( ClassMap To PolicyMap Table ) 
-- ------------------------------------------------------------------ 

pmQoSPolicyMapTable OBJECT-TYPE
    SYNTAX       SEQUENCE OF PmQoSPolicyMapEntry
    MAX-ACCESS   not-accessible
    STATUS       current
    DESCRIPTION  "This table contains the class-map to policy-map details."
    ::= { pmQoSPolicy 2 }

pmQoSPolicyMapEntry OBJECT-TYPE
    SYNTAX       PmQoSPolicyMapEntry
    MAX-ACCESS   not-accessible
    STATUS       current
    DESCRIPTION
       "An entry to map a policy for a class-map." 
    INDEX { pmQoSPolicyMapId }
    ::= { pmQoSPolicyMapTable 1 }

PmQoSPolicyMapEntry ::= SEQUENCE  {
    pmQoSPolicyMapId                                  IndexInteger,
-- inputs
    pmQoSPolicyMapIfIndex                             PortList,
    pmQoSPolicyMapCLASS                               Unsigned32,
-- outputs  
    pmQoSPolicyMapPHBType                             INTEGER, 
    pmQoSPolicyMapDefaultPHB                          Unsigned32,    -- default outgoing priority
    pmQoSPolicyMapMeterTableId                        Unsigned32,  -- meter
-- actions
    pmQoSPolicyMapStatus                              RowStatus
}

pmQoSPolicyMapId OBJECT-TYPE
    SYNTAX       IndexInteger
    MAX-ACCESS   not-accessible
    STATUS       current
    DESCRIPTION "An index that enumerates the policy-map table entries."
    ::= { pmQoSPolicyMapEntry 1 }

pmQoSPolicyMapIfIndex OBJECT-TYPE
    SYNTAX       PortList
    MAX-ACCESS   read-write
    STATUS       current
    DESCRIPTION
       "This indicates the incoming interface identifier for which the policy
        map is applied. A Valid value of this object is not mandatory for the 
        creation of an entry in this table."
    ::= { pmQoSPolicyMapEntry 3 }

pmQoSPolicyMapCLASS OBJECT-TYPE
    SYNTAX       Unsigned32
    MAX-ACCESS   read-write 
    STATUS       current
    DESCRIPTION 
        "This indicates the Traffic CLASS for which the policy-map
         needs to be applied. A valid value is not necessary for 
         creation of an entry in this table. When this object is configured as
         dont-care(0), it is mandatory that the PolicyMapIfIndex is 
         configured. This implies that the policy is interface-specific 
         and not CLASS-specific." 
    DEFVAL { 0 }
    ::= { pmQoSPolicyMapEntry 4 }

pmQoSPolicyMapPHBType OBJECT-TYPE
    SYNTAX      INTEGER {
                        none(0),
                        vlanPri(1),
                        ipTos(2),
                        ipDscp(3),
                        mplsExp(4)
                        }
    MAX-ACCESS  read-write
    STATUS      current
    DESCRIPTION "It indicates the PHB type to be used for filling the Default PHB
                 for the policy-map entry."
    ::= { pmQoSPolicyMapEntry 5 }

pmQoSPolicyMapDefaultPHB  OBJECT-TYPE
    SYNTAX      Unsigned32 (0..63)
    MAX-ACCESS  read-write
    STATUS      current
    DESCRIPTION "It indicate the default out going PHB Values for the 
                 Policy-Map. It may be overriden by the Meter used for the policy-map. 
                 This value is interpreted by pmQoSPolicyMapPHBType."
    ::= { pmQoSPolicyMapEntry 6 }

pmQoSPolicyMapMeterTableId OBJECT-TYPE
    SYNTAX       Unsigned32
    MAX-ACCESS   read-write
    STATUS       current
    DESCRIPTION
       "The Object refers to a Meter table Id which is the index
        for the Meter  table. A Valid value of this object is
        not mandatory for the creation of an entry in this table."
    DEFVAL { 0 }
    ::= { pmQoSPolicyMapEntry 7 } 
    
pmQoSPolicyMapStatus OBJECT-TYPE
    SYNTAX       RowStatus
    MAX-ACCESS   read-create
    STATUS       current
    DESCRIPTION
       "The status of this conceptual row." 
    ::= { pmQoSPolicyMapEntry 37 } 

-- ------------------------------------------------------------------
-- Scheduler Table
-- ------------------------------------------------------------------

pmQoSSchedulerTable   OBJECT-TYPE
    SYNTAX       SEQUENCE OF PmQoSSchedulerEntry
    MAX-ACCESS   not-accessible
    STATUS       current
    DESCRIPTION  "Scheduler table " 
    ::= { pmQoSTrafficMgmt 6 }

pmQoSSchedulerEntry   OBJECT-TYPE
    SYNTAX       PmQoSSchedulerEntry
    MAX-ACCESS   not-accessible
    STATUS       current
    DESCRIPTION  "Scheduler table Entry."
    INDEX   { ifIndex, pmQoSSchedulerId } 
    ::= { pmQoSSchedulerTable 1 }

PmQoSSchedulerEntry ::=
    SEQUENCE {
       pmQoSSchedulerId             Unsigned32,
       pmQoSSchedulerSchedAlgorithm INTEGER,
       pmQoSSchedulerShapeId        Unsigned32,
       pmQoSSchedulerHierarchyLevel Unsigned32,
       pmQoSSchedulerGlobalId       Unsigned32,
       pmQoSSchedulerStatus         RowStatus,
       pmQoSSchedulerWeight         DisplayString
    }

pmQoSSchedulerId    OBJECT-TYPE
    SYNTAX        Unsigned32 (0..65535)
    MAX-ACCESS    not-accessible 
    STATUS        current
    DESCRIPTION
        "The Scheduler Identifier that uniquely identifies the 
        scheduler in the system/egress interface."
    ::= { pmQoSSchedulerEntry 1 }

pmQoSSchedulerSchedAlgorithm OBJECT-TYPE
    SYNTAX      INTEGER {
                strictPriority(1),
                roundRobin(2),
                weightedRoundRobin(3),
                weightedFairQueing(4),
                strictRoundRobin(5),
                strictWeightedRoundRobin(6),
                strictWeightedFairQueing(7),
                deficitRoundRobin(8)
    }
    MAX-ACCESS  read-write
    STATUS      current
    DESCRIPTION
        "Sets the packet scheduling algorithm for the port
        The default is strictPriority(1)."
    DEFVAL      { 1 }
    ::= { pmQoSSchedulerEntry 2 }

pmQoSSchedulerShapeId    OBJECT-TYPE
    SYNTAX        Unsigned32 (0..65535)
    MAX-ACCESS    read-write 
    STATUS        current
    DESCRIPTION
        "The shaper identifier that specifies the bandwidth requirements 
        for the scheduler. This object is not mandatory for the 
        creation of the conceptual row." 
    ::= { pmQoSSchedulerEntry 3 }

pmQoSSchedulerHierarchyLevel    OBJECT-TYPE
    SYNTAX        Unsigned32 (0..10)
    MAX-ACCESS    read-write 
    STATUS        current
    DESCRIPTION
        "This indicates the depth of the queue/scheduler hierarchy. 
        A value of 0 indicates that there is no hierarchy and that all 
        queues/schedulers are port-bound.
        0 - No hierarchy
    1 - S1 schedulers (attached to the egress port)
    2 - S2 schedulers (next level attached to the S1 schecdulers)
    3 - S3 schedulers (attached to the COS queues)"
    DEFVAL {0}
    ::= { pmQoSSchedulerEntry 4 }

pmQoSSchedulerGlobalId    OBJECT-TYPE
    SYNTAX        Unsigned32 (0..65535)
    MAX-ACCESS    read-write 
    STATUS        current
    DESCRIPTION
        "The Scheduler Identifier that uniquely identifies the 
        scheduler in the system/egress interface.This object is
        used only for creating Scheduler entry from the 
        standard QOS Scheduler table diffServSchedulerTable
        as defined in RFC 3289. The Id corresponds to the 
        diffServSchedulerId in RFC 3289. This is added purely
        for the purpose of Save/Restore"
    ::= { pmQoSSchedulerEntry 5 }

pmQoSSchedulerStatus   OBJECT-TYPE 
    SYNTAX      RowStatus
    MAX-ACCESS  read-create
    STATUS      current
    DESCRIPTION "Row Status to Create/Destroy the entry.
        It can be deleted 'destroy', only if it is not referenced 
        by other table; otherwise return inconsistentValue error."
    ::= { pmQoSSchedulerEntry 6 }
    
pmQoSSchedulerWeight OBJECT-TYPE
    SYNTAX      DisplayString
    MAX-ACCESS  read-write
    STATUS      current
    DESCRIPTION
            "WRR weight.
            String '10,30,45,15,6,100,74,56' means Queue1 weight 10.
            Queue2 weight 30. Queue3 weight 45, and so on"
    ::= { pmQoSSchedulerEntry 7 }


-- ------------------------------------------------------------------
-- Default User Priority Table : for Untagged Packets
-- and to specify preference for p-bit over dscp in case of tagged
-- packets                  
-- ------------------------------------------------------------------

pmQoSDefUserPriorityTable  OBJECT-TYPE
    SYNTAX      SEQUENCE OF PmQoSDefUserPriorityEntry
    MAX-ACCESS  not-accessible
    STATUS      current
    DESCRIPTION
        "A table that contains default user priority for an interfae." 
    ::= { pmQoSTrafficMgmt 8}

pmQoSDefUserPriorityEntry OBJECT-TYPE
    SYNTAX     PmQoSDefUserPriorityEntry 
    MAX-ACCESS  not-accessible
    STATUS      current
    DESCRIPTION
        "Table for configuring default user priority for each port. This is  
         used for assigning priority to the untagged packets received on the
         interface."
    INDEX { ifIndex }
    ::= { pmQoSDefUserPriorityTable 1 }

PmQoSDefUserPriorityEntry ::=
    SEQUENCE {
        pmQoSPortDefaultUserPriority Integer32
    }

pmQoSPortDefaultUserPriority OBJECT-TYPE
    SYNTAX      Integer32 (0..7)
    MAX-ACCESS  read-write
    STATUS      current
    DESCRIPTION
        "The default ingress user priority for this port. 
         It will be used to set priority for an untagged Packets."
    ::= { pmQoSDefUserPriorityEntry 1 }

-- ---------------------------------------------------------------- --
      pmipv6          OBJECT IDENTIFIER ::= { privateIpv6 1 }
      pmipv6Route     OBJECT IDENTIFIER ::= { privateIpv6 6 }
-- ---------------------------------------------------------------- --
-- the IPv6 general group
-- pmipv6 GROUP

pmipv6Tables  OBJECT IDENTIFIER ::= { pmipv6 2 }

-- pmipv6Tables BEGIN
         -- IPv6 Interface Table

         -- The IPv6 Interface table defines the logical interfaces on which
         -- IPv6 protocol is running. These include LAN interfaces, Point-to-
         -- Point interfaces, IPv6 over IPv4 Tunnel interfaces and NBMA
         -- interfaces.

         -- Entries of this table are created/deleted from SNMP.


         pmipv6IfTable OBJECT-TYPE
             SYNTAX      SEQUENCE OF Pmipv6IfEntry
             MAX-ACCESS      not-accessible
             STATUS      current
             DESCRIPTION
               "The IPv6 Interface table contains information on the 
               entity's internetwork-layer interfaces on which IPv6.
               protocol is enabled. An IPv6 interface constitutes a logical 
               network layer attachment to the layer immediately below
               IPv6. These include LAN interfaces, Point-to-Point interfaces, 
               NBMA interfaces and IPv6 over IPv4 Tunnel interfaces."
             ::= { pmipv6Tables 1 }


         pmipv6IfEntry OBJECT-TYPE
             SYNTAX     Pmipv6IfEntry
             MAX-ACCESS     not-accessible
             STATUS     current
             DESCRIPTION
               "An interface entry containing objects about a particular 
               IPv6 interface. The entry is created or deleted from SNMP."
             INDEX   { pmipv6IfIndex }
             ::= { pmipv6IfTable 1 }


         Pmipv6IfEntry ::= SEQUENCE {
                 pmipv6IfIndex
                     InterfaceIndex,
                 pmipv6IfType   
                     INTEGER,
                 pmipv6IfAdminStatus
                     INTEGER,
                 pmipv6IfOperStatus
                     INTEGER,
                 pmipv6IfDADRetries
                     Integer32
         }


         pmipv6IfIndex OBJECT-TYPE
             SYNTAX     InterfaceIndex
             MAX-ACCESS   not-accessible
             STATUS     current
             DESCRIPTION
               "A unique value identifying the particular IPv6 
               interface."
             ::= { pmipv6IfEntry 1 }


         pmipv6IfType OBJECT-TYPE
             SYNTAX     INTEGER {
                            ethernetcsmacd(6),
                            ppp(23),
                            framerelay(32),
                            tunnel(131),
                            l3ipvlan(136) 
                        }
             MAX-ACCESS     read-only
             STATUS     current
             DESCRIPTION
               "The type of interface immediately `below' the network layer 
               in the protocol stack."
             ::= { pmipv6IfEntry 2 }


         pmipv6IfAdminStatus OBJECT-TYPE
             SYNTAX     INTEGER {
                            up(1),
                            down(2)
                        }
             MAX-ACCESS     read-write
             STATUS     current
             DESCRIPTION
              "Indicates whether IPv6 is enabled/disabled on this interface.
               When lower layer indicates the creation of the interface, an
               entry will be create in IPv6 interfac table with
               pmipv6IfAdminStatus in down(2) state. Either on setting this
               object as up(1) or configuring any IPv6 address over this
               interface, will set the pmipv6IfAdminStatus to up(1) state.
               If this object is set to down(2), and if no IPv6 address is
               configured for this interface, pmipv6IfAdminStatus goes
               down(2). Else the Status remains up(1), as long as the
               IPv6 address are present. Once these addresses are removed,
               the status goes to down(2)."
             ::= { pmipv6IfEntry 6 }


         pmipv6IfOperStatus OBJECT-TYPE
             SYNTAX     INTEGER {
                            up(1),
                            down(2),
                            stale(3)
                        }
             MAX-ACCESS     read-only
             STATUS     current
             DESCRIPTION
               "The operational state of interface. It is up(1) if the
                pmipv6IfAdminStatus is 'up' and the layer below the network
                layer is also operational. Otherwise it is down(2)."
             ::= { pmipv6IfEntry 7 }

           pmipv6IfDADRetries OBJECT-TYPE
              SYNTAX   Integer32 (0..10)
              MAX-ACCESS   read-write
              STATUS   current
              DESCRIPTION
                  "The maximum number of neighbor solicitations sent for
                   the purpose of duplicate address detection on a tentative 
                   address."
             DEFVAL  { 1 }
             ::= { pmipv6IfEntry 18 }



-- IPv6 Address Table
          
-- The IPv6 address table contains this entity's IPv6
-- addressing information.

-- Entries are created/deleted from SNMP.


          pmipv6AddrTable   OBJECT-TYPE
              SYNTAX   SEQUENCE OF Pmipv6AddrEntry
              MAX-ACCESS   not-accessible
              STATUS   current
              DESCRIPTION
                 "The table containing entity's IPv6 addressing information."
              ::= { pmipv6Tables 4 }


          pmipv6AddrEntry   OBJECT-TYPE
              SYNTAX   Pmipv6AddrEntry
              MAX-ACCESS   not-accessible
              STATUS   current
              DESCRIPTION
                 "The entry in the IPv6 Address Table which defines a
                 unicast, anycast or link-local address on an IPv6 interface."
              INDEX  {pmipv6AddrIndex,
                      pmipv6AddrAddress,
                      pmipv6AddrPrefixLen
                     }
              ::= { pmipv6AddrTable 1 }


          Pmipv6AddrEntry  ::=
              SEQUENCE {
                 pmipv6AddrIndex
                     InterfaceIndex,
                 pmipv6AddrAddress
                     OCTET STRING,
                 pmipv6AddrPrefixLen
                     Integer32,
                 pmipv6AddrAdminStatus
                     RowStatus,
                 pmipv6AddrType
                     INTEGER,
                 pmipv6AddrOperStatus    
                     INTEGER
              }


          pmipv6AddrIndex OBJECT-TYPE
              SYNTAX   InterfaceIndex
              MAX-ACCESS  not-accessible
              STATUS   current
              DESCRIPTION
                 "The index value which uniquely identifies the IPv6
                 interface on which this IPv6 address entry exists.
                 The interface identified by a particular value of this 
                 index is the same interface as identified by the same 
                 value of pmipv6IfIndex."
              ::= { pmipv6AddrEntry 1 }


          pmipv6AddrAddress OBJECT-TYPE
              SYNTAX   OCTET STRING (SIZE (16))
              MAX-ACCESS   not-accessible
              STATUS   current
              DESCRIPTION
                 "The IPv6 address to which this entry's addressing
                  information pertains."
              ::= { pmipv6AddrEntry 2 }


          pmipv6AddrPrefixLen OBJECT-TYPE
              SYNTAX   Integer32 (0..128)
              MAX-ACCESS  not-accessible
              STATUS   current
              DESCRIPTION
                 "The length of the prefix (in bits) associated with
                 the IPv6 address of this entry. For a link-local address,
                 the prefix is always start with '0xfe80' and the prefix
                 length is 128 bits."
              ::= { pmipv6AddrEntry 3 }


          pmipv6AddrAdminStatus OBJECT-TYPE
              SYNTAX            RowStatus
              MAX-ACCESS   read-create
              STATUS   current
              DESCRIPTION
                "Indicates the desired status of the address. Also a creation
                 of an address can trigger IPv6 to be enabled over the
                 interface. Similarly deletion of all the address may trigger
                 IPv6 to be disabled on the interface. NotInService value is
                 not supported."
              ::= { pmipv6AddrEntry 4 }


          pmipv6AddrType OBJECT-TYPE
              SYNTAX   INTEGER {
                            unicast(1),
                            anycast(2),
                            linklocal(3)
                       }
              MAX-ACCESS   read-write
              STATUS   current
              DESCRIPTION
                "Indicates whether the address is a unicast, anycast or
                 link-local address. Syntactically there is no difference
                 between a unicast address and a anycast address while a
                 link-local address has the prefix '0xfe80'. This
                 object can be modified only if pmipv6AddrOperStatus is
                 down."
              ::= { pmipv6AddrEntry 5 }


          pmipv6AddrOperStatus OBJECT-TYPE
              SYNTAX   INTEGER {

                           tentative (1),    -- DAD resolution going
                                             -- on on the address

                           complete (2),     -- DAD completed on the address

                           down(3),          -- address is operationally
                                             -- down

                           failed(4)         -- DAD failed for the address

                       }
              MAX-ACCESS   read-only
              STATUS   current
              DESCRIPTION
                 "Indicates the operational status of the address. A
                 status of failed(4) indicates that a duplicate address has
                 been detected on this IPv6 interface. On interfaces on
                 which Duplicate Address Detection is not performed, this
                 object will take values only complete(2) and down(3)."
              ::= { pmipv6AddrEntry 7 }


-- IPv6 Routing Table

          -- The IPv6 routing table contains an entry for each
          -- valid IPv6 unicast routes that can be used for packet
          -- forwarding. There are no entries for Multicast and Link-Local
          -- addresses.

          -- This table contains static and dynamic routes as well as routes
          -- to directly connected networks which are derived from the
          -- configured address prefixes. Thus entries exist in this table
          -- even if RIPng protocol is not running.

          -- Entries created/deleted from SNMP, dynamically through RIPng
          -- protocol or derived from configured address prefixes.

	 pmipv6RouteTable   OBJECT-TYPE
              SYNTAX   SEQUENCE OF Pmipv6RouteEntry
              MAX-ACCESS   not-accessible
              STATUS   current
              DESCRIPTION
                 "This table contains dynamic routes that are learnt
                 through dynamic routing protocol as well as local routes
                 derived from configured address prefixes and statically
                 configured routes."
              ::= { pmipv6Route 1 }


         pmipv6RouteEntry   OBJECT-TYPE
              SYNTAX   Pmipv6RouteEntry
              MAX-ACCESS   not-accessible
              STATUS   current
              DESCRIPTION
                 "An entry in the IPv6 Routing Table. An entry can be created
                 by means of the routing protocol, derived from configured
                 address prefixes as well as statically configured. There
                 can be a static route as well as dynamic routes with the
                 same destination and prefix length."
              INDEX  { pmipv6RouteDest,
                       pmipv6RoutePfxLength,
                       pmipv6RouteProtocol,
                       pmipv6RouteNextHop
                     }
              ::= { pmipv6RouteTable 1 }


         Pmipv6RouteEntry  ::=
              SEQUENCE {
                 pmipv6RouteDest
                     OCTET STRING,
                 pmipv6RoutePfxLength
                     Integer32,
                 pmipv6RouteProtocol
                     INTEGER,
                 pmipv6RouteNextHop
                     OCTET STRING,
                 pmipv6RouteIfIndex
                     InterfaceIndex,
                 pmipv6RouteAdminStatus
                     RowStatus
              }


          pmipv6RouteDest  OBJECT-TYPE
              SYNTAX   OCTET STRING (SIZE (16))
              MAX-ACCESS  not-accessible
              STATUS   current
              DESCRIPTION
                 "The destination IPv6 address of this route.
                  This object will not take a Link-Local or Multicast address
                  value."
              ::= { pmipv6RouteEntry 1 }


          pmipv6RoutePfxLength OBJECT-TYPE
              SYNTAX   Integer32 (1..128)
              MAX-ACCESS   not-accessible
              STATUS   current
              DESCRIPTION
                 "Indicates the prefix length of the destination
                  address."
              ::= { pmipv6RouteEntry 2 }


          pmipv6RouteProtocol OBJECT-TYPE
              SYNTAX     INTEGER {
                            other(1),        -- none of the following


                            local(2),        -- non-protocol information,
                                             -- e.g., manually configured
                                             -- entries

                            netmgmt(3),      -- static route

                            ndisc(4),        -- e.g., Redirect
                                             -- the following are all
                                             -- dynamic routing protocols

                            rip(5),          -- RIPng

                            ospf(6),         -- Open Shortest Path First

                            bgp(7),          -- Border Gateway Protocol
                            idrp(8),         -- InterDomain Routing Protocol
                            igrp(9)          -- InterGateway Routing Protocol

                         }
              MAX-ACCESS    not-accessible
              STATUS   current
              DESCRIPTION
                 "The routing mechanism via which this route was
                 learned. If it has value local(2), it indicates this
                 route was derived from a configured address prefix."
              ::= { pmipv6RouteEntry 3 }


          pmipv6RouteNextHop  OBJECT-TYPE
              SYNTAX   OCTET STRING (SIZE (16))
              MAX-ACCESS   not-accessible
              STATUS   current
              DESCRIPTION
                 "Next hop IPv6 Address for this route. For direct routes
                 it has the value ::0."
              ::= { pmipv6RouteEntry 4 }


          pmipv6RouteIfIndex  OBJECT-TYPE
              SYNTAX   InterfaceIndex
              MAX-ACCESS   read-write
              STATUS   current
              DESCRIPTION
                 "The index value which uniquely identifies the interface
                  through which the next hop of this route should be reached.
                  The interface identified by a particular value of this index
                  is the same interface as identified by the same value of
                  pmipv6IfIndex."
              ::= { pmipv6RouteEntry 5 }

          pmipv6RouteAdminStatus  OBJECT-TYPE
              SYNTAX    RowStatus
              MAX-ACCESS   read-create
              STATUS   current
              DESCRIPTION
                "Administrative Status of the route. This object is used
                 to create or delete the route entry. The pmipv6RouteIfIndex
                 needs to be set, before the route entry is made active. 
                 CreateAndGo is not supported."
              ::= { pmipv6RouteEntry 10 }

--ipv6RouteTable END

-- *****************************************************************************
--              subtrees in the DNS Resolver MIB
-- *****************************************************************************
    pmDnsNameServer   OBJECT IDENTIFIER ::= { privateDns 2 }
  
-- pmDnsNameServerTable

-- This table is for configuring the Name Server List (SLIST)
 
       pmDnsNameServerTable OBJECT-TYPE
          SYNTAX      SEQUENCE OF PmDnsNameServerEntry
          MAX-ACCESS  not-accessible
          STATUS      current
          DESCRIPTION
             "A table containing the Name Server List (SLIST)"
         ::= { pmDnsNameServer 1}

       pmDnsNameServerEntry OBJECT-TYPE
         SYNTAX        PmDnsNameServerEntry
         MAX-ACCESS    not-accessible
         STATUS        current
         DESCRIPTION
             "Name Server List SLIST Entries "
         INDEX { pmDnsNameServerIndex }
         ::= { pmDnsNameServerTable 1 }

         PmDnsNameServerEntry ::=
          SEQUENCE {
                    pmDnsNameServerIndex Unsigned32,
                    pmDnsServerIPAddressType InetAddressType,
                    pmDnsServerIPAddress InetAddress,
                    pmDnsNameServerRowStatus RowStatus
                   }

       pmDnsNameServerIndex OBJECT-TYPE
         SYNTAX       Unsigned32
         MAX-ACCESS   not-accessible
         STATUS       current
         DESCRIPTION
            " An arbitrary integer value, greater than zero, 
              which uniquely identifies a Name Server"
         ::= { pmDnsNameServerEntry 1 }

       pmDnsServerIPAddressType OBJECT-TYPE
         SYNTAX      InetAddressType
         MAX-ACCESS  read-create
         STATUS      current
         DESCRIPTION
            "The type of object that represents the Name server's Ip address"
         ::= { pmDnsNameServerEntry 2 }

       pmDnsServerIPAddress OBJECT-TYPE      
         SYNTAX       InetAddress (SIZE(4..16))
         MAX-ACCESS   read-create   
         STATUS       current
         DESCRIPTION
           "The Object represents the Name server's Ip Address"
         ::= { pmDnsNameServerEntry 3 }

        pmDnsNameServerRowStatus OBJECT-TYPE
           SYNTAX        RowStatus
           MAX-ACCESS    read-create
           STATUS        current
           DESCRIPTION
             "Specifies the Row Status of the Name Server table"
          ::= { pmDnsNameServerEntry 4 }

-- the Cfa group------------------------------------------------------
-- ---------------------------------------------------------------- --
      if               OBJECT IDENTIFIER ::= { privateCfa 1 }
-- ---------------------------------------------------------------- --
-- Cfa If Group
-- ifMainTable
-- This table is used for the management of all the interfaces in the
-- system. 
         
      ifMainTable          OBJECT-TYPE
         SYNTAX            SEQUENCE OF IfMainEntry
         MAX-ACCESS        not-accessible
         STATUS            current
         DESCRIPTION
            "A list of all the interface entries in the system. 
            This table contains objects which are applicable to all
            types of interfaces in the system. This table is a 
            proprietary extension to the standard ifTable and 
            ifXTable. The index to this table has the semantics of
            the MIB-2 ifIndex."
         ::= { if 4 }

      ifMainEntry          OBJECT-TYPE
         SYNTAX            IfMainEntry
         MAX-ACCESS        not-accessible
         STATUS            current
         DESCRIPTION
            "An entry containing management information applicable
            to a particular interface."
         INDEX { ifMainIndex }
         ::= { ifMainTable 1 }

      IfMainEntry ::=
         SEQUENCE {
            ifMainIndex              InterfaceIndex,
            ifMainOperStatus         INTEGER,
            ifMainRowStatus          RowStatus,
            ifMainDesc               DisplayString
            }

      ifMainIndex          OBJECT-TYPE
         SYNTAX            InterfaceIndex
         MAX-ACCESS        not-accessible 
         STATUS            current
         DESCRIPTION
            "A unique value, greater than zero, for each
            interface. This object is identical to the ifIndex
            of the standard MIB-2 ifTable." 
         ::= { ifMainEntry 1 }


      ifMainOperStatus     OBJECT-TYPE
         SYNTAX            INTEGER  {
                              up(1),        -- ready to pass packets
                              down(2),
                              testing(3),   -- in some test mode
                              unknown(4),   -- status can not be
                                            -- determined for
                                            -- some reason.
                              dormant(5),
                              notPresent(6), -- some component is
                                             -- missing
                              lowerLayerDown(7) -- down due to state
                                                --  of lower-layer
                                                -- interface(s).
                              }
         MAX-ACCESS        read-only
         STATUS            current
         DESCRIPTION
            "The current operational state of the interface.
            The testing (3) state indicates that no operational
            packets can be passed - this state is not supported
            currently. 
            
            If ifMainAdminStatus is down (2)
            then ifMainOperStatus would be down (2). If
            ifMainAdminStatus is changed to up (1) then
            ifMainOperStatus should change to up (1) if the
            interface is ready to transmit and receive
            work traffic; it should change to dormant (5)
            the interface is waiting for external actions
            (such as a serial line waiting for an incoming
            connection); it should change to lowerLayerDown(7)
            state if it cannot be made up as the interface sub-layer
            below it is down; it should remain in the down (2) state
            if and only if there is a fault that prevents it
            from going to the up (1) state; it should remain in
            the notPresent (6) state if the interface has
            missing (typically, hardware) components.
            
            The status unknown(4) is shown when it is not possible
            to determine the exact status of the interface - e.g.
            the interface sub-layer is performing negotiations - 
            during this period the interface is not up but at the
            same time, it is not a fault condition and hence it
            cannot be shown as down - in such periods the status
            is shown as unknown.
            
            This object has the semantics of the ifOperStatus of the
            standard ifTable."
         ::= { ifMainEntry 5 }

      ifMainRowStatus      OBJECT-TYPE
         SYNTAX            RowStatus
         MAX-ACCESS        read-create
         STATUS            current
         DESCRIPTION
            "A RowStatus variable for addition, deletion and in-activation
            of the interfaces. Specification of the object is mandatory
            for all interfaces.
            
            When the status is active, the interface is created and
            ready to use in the respective protocol modules.
            
            When the status is notInService, the interface has not been
            registered with the respective protocol modules and as such
            those modules are not aware of the existence of the interface
            - creation is hence, incomplete. Setting an active interface
            to notInService results in de-registration/deletion of the
            interface from the respective protocol modules and all the
            configurations associated with that interface in those modules
            may be lost.
            
            Deletion of an interface, may affect the status of other
            interfaces which are layered above or below it in the Interface
            Stack (ifStackTable) and may result in other interfaces being
            made notReady or notInService."
         ::= { ifMainEntry 8 }

      ifMainDesc	OBJECT-TYPE
             SYNTAX		DisplayString
             MAX-ACCESS	read-write
             STATUS		current
             DESCRIPTION	
             "A textual string which contains the description about an interface."

             ::= { ifMainEntry 12 }

-- ifIpTable
-- This table is used for the management of the interfaces in the
-- system which are registered with IP. 
      
      ifIpTable            OBJECT-TYPE
         SYNTAX            SEQUENCE OF IfIpEntry
         MAX-ACCESS        not-accessible
         STATUS            current
         DESCRIPTION
            "A list of all the interface entries in the system which
            are registered with IP.
                  
            This table contains objects which are applicable for the
            management of IP over the network interfaces
            in the system. 
               
            This table is a extension to the ifMainTable. 
            The index to this table has the semantics of
            the ifMainIndex of the ifMainTable.
                  
            Entries are created automatically in this table for
            any interface sub-layer which is layer below IP using
            the ifStackTable. Similarly, entries are deleted from
            this table when the interface's layering below IP is
            removed."
         ::= { if 5 }

      ifIpEntry            OBJECT-TYPE
         SYNTAX            IfIpEntry
         MAX-ACCESS        not-accessible
         STATUS            current
         DESCRIPTION
            "An entry containing management information applicable
            to a particular interface over which IP is operating."
         INDEX { ifMainIndex }
         ::= { ifIpTable 1 }

      IfIpEntry ::=
         SEQUENCE {
            ifIpAddrAllocMethod  INTEGER,
            ifIpAddr             IpAddress,
            ifIpSubnetMask       IpAddress,
            ifIpBroadcastAddr    IpAddress
            }

      ifIpAddrAllocMethod  OBJECT-TYPE
         SYNTAX            INTEGER {
                              manual(1),  -- To be set by Manager
                              negotiation(2), -- obtained from peer
                              dynamic(3),
			      none(4)  -- none of the above
                              } -- Currently only
                                -- these method possible.
         MAX-ACCESS        read-write 
         STATUS            current
         DESCRIPTION
            "The mechanism to be used for allocation of IP
            address for this interface. 
            
            The value negotiation can be used only for PPP
            and MLPPP interfaces which support obtaining of
            IP addresses through negotiation.

            The dynamic(3) option takes an IP 
            address dynamically from the available 
            server (dhcp/bootp/rarp) according to the
            protocol specified in ifIpAddrAllocProtocol. 

            If the method specified is manual and the IP 
            address is not provided (then the interface   
            would be treated as a un-numbered interface."
         DEFVAL { none }
         ::= { ifIpEntry 1 }

      ifIpAddr             OBJECT-TYPE
         SYNTAX            IpAddress
         MAX-ACCESS        read-write 
         STATUS            current
         DESCRIPTION
            "Specifies the IP address given to this
            interface. The specification of this object is
            mandatory for all network interfaces (Ethernet,
            FR VC, IPoA interface, PPP link - not under MP,
            MP interface and X.25 VC). If the interface is
            not a network interface then the default value
            of 0.0.0.0 is assigned and the interface is
            treated as a un-numbered interface by IP."
         DEFVAL { '00000000'H } 
         ::= { ifIpEntry 2 }

      ifIpSubnetMask       OBJECT-TYPE
         SYNTAX            IpAddress
         MAX-ACCESS        read-write 
         STATUS            current
         DESCRIPTION
            "Specifies the IP Subnet Mask for this
            interface. The value should be specified only
            for network interfaces and any valid VLSM is
            accepted. 
            
            If not specified, this object takes the default
            subnet mask value based on the class of the IP
            address configured for the interface."
         ::= { ifIpEntry 3 }

      ifIpBroadcastAddr    OBJECT-TYPE
         SYNTAX            IpAddress
         MAX-ACCESS        read-write
         STATUS            current
         DESCRIPTION
            "Specifies the IP broadcast address for this
            interface. The value should be specified only
            for network interfaces and any valid broadcast
            address based on a valid VLSM is accepted. 
            
            If not specified, this object takes the default
            value based on the class of the IP
            address configured for the interface."
         ::= { ifIpEntry 4 }    
 
-- ----------------------------------------------------------------------------
-- ifMainExtTable
-- This table is used for the additional management of the interfaces in the
-- system. 
-- ----------------------------------------------------------------------------

ifMainExtTable OBJECT-TYPE
   SYNTAX      SEQUENCE OF IfMainExtEntry
   MAX-ACCESS  not-accessible
   STATUS      current
   DESCRIPTION
      "This table is an extension to the ifMainTable."
   ::= { if 12 }

ifMainExtEntry OBJECT-TYPE
   SYNTAX      IfMainExtEntry 
   MAX-ACCESS  not-accessible
   STATUS      current
   DESCRIPTION
      "An entry containing additional management information
       applicable to a particular interface."
  AUGMENTS    { ifMainEntry }
    ::= { ifMainExtTable 1 }

IfMainExtEntry ::=
   SEQUENCE {
      ifMainExtPortSecState         INTEGER
   }

      ifMainExtPortSecState OBJECT-TYPE
         SYNTAX        INTEGER {
                            untrusted (0),
                            trusted (1)
         }
         MAX-ACCESS  read-write
         STATUS      current
         DESCRIPTION
           "The interface port security state says whether the port is connected
           to trusted hosts or not. If a port is trusted, the packets coming
           on that ports will also be trusted. By default all the ports will be
           untrusted"

         DEFVAL { trusted }
         ::={ ifMainExtEntry 11 }

-- ifCableDiagTable
-- This table is used for the Cable Diagnostic
         
      ifCableDiagTable   	  OBJECT-TYPE
         SYNTAX               SEQUENCE OF IfCableDiagEntry
         MAX-ACCESS           not-accessible
         STATUS               current
         DESCRIPTION
            ""
         ::= { if 26 }

      ifCableDiagEntry   OBJECT-TYPE
         SYNTAX            IfCableDiagEntry
         MAX-ACCESS        not-accessible
         STATUS            current
         DESCRIPTION
            ""
         INDEX { ifCableDiagIndex }
         ::= { ifCableDiagTable 1 }
         
      IfCableDiagEntry ::=
	  	SEQUENCE {
	        ifCableDiagIndex       Integer32,
	        ifCableDiagStatus      DisplayString
	    	}

      ifCableDiagIndex OBJECT-TYPE
         SYNTAX        Integer32 (1..2147483647)
         MAX-ACCESS    not-accessible
         STATUS        current
         DESCRIPTION   ""
         ::= { ifCableDiagEntry 1 }

      ifCableDiagStatus    OBJECT-TYPE
         SYNTAX            DisplayString
         MAX-ACCESS        read-only
         STATUS            current
         DESCRIPTION
            "This object indicates the cable diagnostics result.
            [PairAStatus,PairBStatus,PairCStatus,PairDstatus,
            PairALength,PairBLength,PairCLength,PairDLength].
            Status 0:OK, 1:OPEN, 2:SHORT, 3:OPENSHORT, 4:CROSSTALK,
            5:UNKNOWN.
            "
         ::= { ifCableDiagEntry 2 }

-- ------------------------------------------------------------
-- groups in the MIB 
-- ------------------------------------------------------------

      pmEeeSystem       OBJECT IDENTIFIER ::= { privateEee 1 }

-- ------------------------------------------------------------------
-- The Eee System Group
-- ------------------------------------------------------------------

      pmPortEeeTable OBJECT-TYPE
          SYNTAX      SEQUENCE OF PmPortEeeEntry
          MAX-ACCESS  not-accessible
          STATUS      current
          DESCRIPTION
             "This table contains information associated port for which 
              Eee has to be applied."
          ::= { pmEeeSystem 1 }

      pmPortEeeEntry OBJECT-TYPE
          SYNTAX     PmPortEeeEntry 
          MAX-ACCESS  not-accessible
          STATUS      current
          DESCRIPTION
             "Eee status."
          INDEX {pmPortIndex}
          ::= { pmPortEeeTable 1 }

      PmPortEeeEntry ::= SEQUENCE {
            pmPortIndex
            Integer32,
            pmPortEeeStatus 
            INTEGER
          }

      pmPortIndex OBJECT-TYPE
          SYNTAX      Integer32 (1..2147483647)
          MAX-ACCESS  not-accessible
          STATUS      current
          DESCRIPTION
            "This variable uniquely identifies the power Ethernet
             port which the EEE is connected."
          ::= { pmPortEeeEntry 1 }

      pmPortEeeStatus OBJECT-TYPE
          SYNTAX INTEGER   {
            enalbe(1),
            disable(0)
          }
          MAX-ACCESS read-write
          STATUS current
          DESCRIPTION
            "enable(1) The type port will set EEE to enable.
            disable(0) The type port will set EEE to disable."
          ::= { pmPortEeeEntry 2}
      pmDot1dBase              OBJECT IDENTIFIER ::= { privateDot1dBridge 1 }
      pmDot1dStp               OBJECT IDENTIFIER ::= { privateDot1dBridge 2 }
      pmDot1dTp                OBJECT IDENTIFIER ::= { privateDot1dBridge 4 }

-- the pmDot1dBase group

-- Implementation of the pmDot1dBase group is current for all
-- bridges.
pmDot1dBaseTable OBJECT-TYPE
    SYNTAX SEQUENCE OF PmDot1dBaseEntry
    MAX-ACCESS    not-accessible
    STATUS        current
    DESCRIPTION
       "List of per Virtual Bridge Module Parameters."
    ::= { pmDot1dBase 1 }

pmDot1dBaseEntry OBJECT-TYPE
   SYNTAX       PmDot1dBaseEntry
   MAX-ACCESS   not-accessible
   STATUS       current
   DESCRIPTION
      "Virtual Bridge Rst Module Parameters."
   INDEX { pmDot1dBaseContextId}
   ::= { pmDot1dBaseTable 1 }

PmDot1dBaseEntry ::=
    SEQUENCE {
           pmDot1dBaseContextId
              Integer32,
           pmDot1dBaseBridgeAddress
              MacAddress, 
           pmDot1dBaseNumPorts
              Integer32,
           pmDot1dBaseType
              INTEGER
}

pmDot1dBaseContextId OBJECT-TYPE
   SYNTAX       Integer32 (0..65535)
   MAX-ACCESS   not-accessible
   STATUS       current
   DESCRIPTION
      "Virtual Bridge number"
   ::= { pmDot1dBaseEntry 1}
          -- the pmDot1dStp group

          -- Implementation of the pmDot1dStp group is optional.  It is
          -- implemented by those bridges that support the Spanning Tree
          -- Protocol.

pmDot1dStpTable OBJECT-TYPE
   SYNTAX       SEQUENCE OF PmDot1dStpEntry
   MAX-ACCESS   not-accessible
   STATUS       current
   DESCRIPTION
      "Table of StpScalars per virtual bridge"
   ::= { pmDot1dStp 1 }

pmDot1dStpEntry OBJECT-TYPE
   SYNTAX       PmDot1dStpEntry
   MAX-ACCESS   not-accessible
   STATUS       current
   DESCRIPTION
     "Per bridge StpScalars"
   INDEX { pmDot1dStpContextId }
   ::= { pmDot1dStpTable 1 }

PmDot1dStpEntry ::=
    SEQUENCE {
           pmDot1dStpContextId
              Integer32,
           pmDot1dStpPriority 
              INTEGER,
           pmDot1dStpTimeSinceTopologyChange
              TimeTicks,
           pmDot1dStpTopChanges
              Counter32,
           pmDot1dStpDesignatedRoot 
              BridgeId,
           pmDot1dStpRootCost
              Integer32,
           pmDot1dStpRootPort
              Integer32,
           pmDot1dStpMaxAge
              Timeout,
           pmDot1dStpHelloTime
              Timeout,
           pmDot1dStpHoldTime
              Integer32,
           pmDot1dStpForwardDelay
              Timeout,
           pmDot1dStpBridgeMaxAge
              Timeout,
           pmDot1dStpBridgeHelloTime
              Timeout,
           pmDot1dStpBridgeForwardDelay
              Timeout
}

pmDot1dStpContextId OBJECT-TYPE
   SYNTAX       Integer32 (0..65535)
   MAX-ACCESS   not-accessible
   STATUS       current
   DESCRIPTION
     "Virtual Bridge number"
   ::= { pmDot1dStpEntry 1}


pmDot1dStpPriority OBJECT-TYPE
   SYNTAX  INTEGER (0..65535)
   MAX-ACCESS  read-write
   STATUS  current
   DESCRIPTION
     "The value of the write-able portion of the Bridge
     ID, i.e., the first two octets of the (8 octet
     long) Bridge ID.  The other (last) 6 octets of the
     Bridge ID are given by the value of
     pmDot1dBaseBridgeAddress.
     On bridges supporting IEEE 802.1t or IEEE 802.1w,
     permissible values are 0-61440, in steps of 4096."
   REFERENCE
     "IEEE 802.1D-1998 clause 8.10.2, Table 8-4,
      IEEE 802.1t clause 8.10.2, Table 8-4, clause 14.3."

   ::= { pmDot1dStpEntry 3 }

pmDot1dStpTimeSinceTopologyChange OBJECT-TYPE
   SYNTAX  TimeTicks
   UNITS       "centi-seconds"
   MAX-ACCESS  read-only
   STATUS  current
   DESCRIPTION
     "The time (in hundredths of a second) since the
     last time a topology change was detected by the
     bridge entity.
     For RSTP, this reports the time since the tcWhile
     timer for any port on this Bridge was nonzero."
   REFERENCE
     "IEEE 802.1D-1998: Section 14.8.1.1
      IEEE 802.1w clause 14.8.1.1."
   ::= { pmDot1dStpEntry 4 }

pmDot1dStpTopChanges OBJECT-TYPE
   SYNTAX  Counter32
   MAX-ACCESS  read-only
   STATUS  current
   DESCRIPTION
     "The total number of topology changes detected by
     this bridge since the management entity was last
     reset or initialized."
   REFERENCE
     "IEEE 802.1D-1998: Section 14.8.1.1.3"
   ::= { pmDot1dStpEntry 5 }

pmDot1dStpDesignatedRoot OBJECT-TYPE
   SYNTAX  BridgeId
   MAX-ACCESS  read-only
   STATUS  current
   DESCRIPTION
     "The bridge identifier of the root of the spanning
     tree as determined by the Spanning Tree Protocol
     as executed by this node.  This value is used as
     the Root Identifier parameter in all Configuration
     Bridge PDUs originated by this node."
   REFERENCE
     "IEEE 802.1D-1998: Section 8.5.3.1"
   ::= { pmDot1dStpEntry 6 }

pmDot1dStpRootCost OBJECT-TYPE
   SYNTAX  Integer32
   MAX-ACCESS  read-only
   STATUS  current
   DESCRIPTION
     "The cost of the path to the root as seen from
     this bridge."
   REFERENCE
     "IEEE 802.1D-1998: Section 8.5.3.2"
   ::= { pmDot1dStpEntry 7 }

pmDot1dStpRootPort OBJECT-TYPE
   SYNTAX  Integer32
   MAX-ACCESS  read-only
   STATUS  current
   DESCRIPTION
     "The port number of the port which offers the
     lowest cost path from this bridge to the root
     bridge."
   REFERENCE
     "IEEE 802.1D-1998: Section 8.5.3.3"
   ::= { pmDot1dStpEntry 8 }

pmDot1dStpMaxAge OBJECT-TYPE
   SYNTAX  Timeout
   UNITS   "centi-seconds"
   MAX-ACCESS  read-only
   STATUS  current
   DESCRIPTION
     "The maximum age of Spanning Tree Protocol
     information learned from the network on any port
     before it is discarded, in units of hundredths of
     a second.  This is the actual value that this
     bridge is currently using."
   REFERENCE
     "IEEE 802.1D-1998: Section 8.5.3.4"
   ::= { pmDot1dStpEntry 9 }

pmDot1dStpHelloTime OBJECT-TYPE
   SYNTAX  Timeout
   UNITS   "centi-seconds"
   MAX-ACCESS  read-only
   STATUS  current
   DESCRIPTION
     "The amount of time between the transmission of
     Configuration bridge PDUs by this node on any port
     when it is the root of the spanning tree or trying
     to become so, in units of hundredths of a second.
     This is the actual value that this bridge is
     currently using."
   REFERENCE
     "IEEE 802.1D-1998: Section 8.5.3.5"
   ::= { pmDot1dStpEntry 10 }

pmDot1dStpForwardDelay OBJECT-TYPE
   SYNTAX  Timeout
   UNITS   "centi-seconds"
   MAX-ACCESS  read-only
   STATUS  current
   DESCRIPTION
     "This time value, measured in units of hundredths
     of a second, controls how fast a port changes its
     spanning state when moving towards the Forwarding
     state.  The value determines how long the port
     stays in each of the Listening and Learning
     states, which precede the Forwarding state.  This
     value is also used, when a topology change has
     been detected and is underway, to age all dynamic
     entries in the Forwarding Database.  [Note that
     this value is the one that this bridge is
     currently using, in contrast to
     pmDot1dStpBridgeForwardDelay which is the value that
     this bridge and all others would start using
     if/when this bridge were to become the root.]"
   REFERENCE
     "IEEE 802.1D-1998: Section 8.5.3.6"
   ::= { pmDot1dStpEntry 12 }

pmDot1dStpBridgeMaxAge OBJECT-TYPE
   SYNTAX  Timeout (600..4000)
   UNITS   "centi-seconds"
   MAX-ACCESS  read-write
   STATUS  current
   DESCRIPTION
     "The value that all bridges use for MaxAge when
     this bridge is acting as the root.  Note that
     802.1D-1998 specifies that the range for this
     parameter is related to the value of
     pmDot1dStpBridgeHelloTime. The granularity of this
     timer is specified by 802.1D-1998 to be 1 second.
     An agent may return a badValue error if a set is
     attemporarilyted to a value which is not a whole number
     of seconds."
   REFERENCE
     "IEEE 802.1D-1998: Section 8.5.3.8"
   ::= { pmDot1dStpEntry 13 }

pmDot1dStpBridgeHelloTime OBJECT-TYPE
   SYNTAX  Timeout (100|200)
   UNITS       "centi-seconds"
   MAX-ACCESS  read-write
   STATUS  current
   DESCRIPTION
     "The value that all bridges use for HelloTime when
     this bridge is acting as the root.  The
     granularity of this timer is specified by 802.1D-
     1990 to be 1 second.  An agent may return a
     badValue error if a set is attemporarilyted to a value
     which is not a whole number of seconds."
   REFERENCE
     "IEEE 802.1D-1998: Section 8.5.3.9"
   ::= { pmDot1dStpEntry 14 }

pmDot1dStpBridgeForwardDelay OBJECT-TYPE
   SYNTAX  Timeout (400..3000)
   UNITS       "centi-seconds"
   MAX-ACCESS  read-write
   STATUS  current
   DESCRIPTION
     "The value that all bridges use for ForwardDelay
     when this bridge is acting as the root.  Note that
     802.1D-1998 specifies that the range for this
     parameter is related to the value of
     pmDot1dStpBridgeMaxAge.  The granularity of this
     timer is specified by 802.1D-1998 to be 1 second.
     An agent may return a badValue error if a set is
     attemporarilyted to a value which is not a whole number
     of seconds."
   REFERENCE
     "IEEE 802.1D-1998: Section 8.5.3.10"
   ::= { pmDot1dStpEntry 15 }

          -- The Spanning Tree Port Table

pmDot1dStpPortTable OBJECT-TYPE
   SYNTAX  SEQUENCE OF PmDot1dStpPortEntry
   MAX-ACCESS  not-accessible
   STATUS  current
   DESCRIPTION
     "A table that contains port-specific information
     for the Spanning Tree Protocol."
   ::= { pmDot1dStp 2 }

pmDot1dStpPortEntry OBJECT-TYPE
   SYNTAX  PmDot1dStpPortEntry
   MAX-ACCESS  not-accessible
   STATUS  current
   DESCRIPTION
     "A list of information maintained by every port
     about the Spanning Tree Protocol state for that
     port."
   INDEX   { pmDot1dStpPort }
   ::= { pmDot1dStpPortTable 1 }

PmDot1dStpPortEntry ::=
   SEQUENCE {
          pmDot1dStpPort
             Integer32,
          pmDot1dStpPortPriority
             Integer32,
          pmDot1dStpPortState
             INTEGER,
          pmDot1dStpPortEnable
             INTEGER,
          pmDot1dStpPortPathCost
             Integer32,
          pmDot1dStpPortDesignatedRoot
             BridgeId,
          pmDot1dStpPortDesignatedCost
             Integer32,
          pmDot1dStpPortDesignatedBridge
             BridgeId,
          pmDot1dStpPortDesignatedPort
             OCTET STRING,
          pmDot1dStpPortForwardTransitions
               Counter32,
          pmDot1dStpPortPathCost32
               Integer32
}

pmDot1dStpPort OBJECT-TYPE
   SYNTAX  Integer32 (1..65535)
   MAX-ACCESS  not-accessible
   STATUS  current
   DESCRIPTION
     "The port number of the port for which this entry
     contains Spanning Tree Protocol management
     information."
   REFERENCE
     "IEEE 802.1D-1998: Section 14.8.2.1.2"
   ::= { pmDot1dStpPortEntry 1 }

pmDot1dStpPortPriority OBJECT-TYPE
   SYNTAX  Integer32 (0..255)
   MAX-ACCESS  read-write
   STATUS  current
   DESCRIPTION
     "The value of the priority field which is
     contained in the first (in network byte order)
     octet of the (2 octet long) Port ID.  The other
     octet of the Port ID is given by the value of
     pmDot1dStpPort.
     On bridges supporting IEEE 802.1t or IEEE 802.1w,
     permissible values are 0-240, in steps of 16."
                
   REFERENCE
      "IEEE 802.1D-1998 clause 8.10.2, Table 8-4,

       IEEE 802.1t clause 8.10.2, Table 8-4, clause 14.3."

   ::= { pmDot1dStpPortEntry 2 }

pmDot1dStpPortState OBJECT-TYPE
   SYNTAX  INTEGER {
               disabled(1),
               blocking(2),
               listening(3),
               learning(4),
               forwarding(5),
               broken(6)
           }
   MAX-ACCESS  read-only
   STATUS  current
   DESCRIPTION
     "The port's current state as defined by
     application of the Spanning Tree Protocol.  This
     state controls what action a port takes on
     reception of a frame.  If the bridge has detected
     a port that is malfunctioning it will place that
     port into the broken(6) state.  For ports which
     are disabled (see pmDot1dStpPortEnable), this object
     will have a value of disabled(1)."
   REFERENCE
     "IEEE 802.1D-1998: Section 8.5.5.2"
   ::= { pmDot1dStpPortEntry 3 }

pmDot1dStpPortEnable OBJECT-TYPE
   SYNTAX  INTEGER {
               enabled(1),
               disabled(2)
           }
   MAX-ACCESS  read-write
   STATUS  current
   DESCRIPTION
     "The enabled/disabled status of the port."
   REFERENCE
     "IEEE 802.1D-1998: Section 8.5.5.2"
   ::= { pmDot1dStpPortEntry 4 }

pmDot1dStpPortDesignatedRoot OBJECT-TYPE
   SYNTAX  BridgeId
   MAX-ACCESS  read-only
   STATUS  current
   DESCRIPTION
     "The unique Bridge Identifier of the Bridge
     recorded as the Root in the Configuration BPDUs
     transmitted by the Designated Bridge for the
     segment to which the port is attached."
   REFERENCE
     "IEEE 802.1D-1998: Section 8.5.5.4"
   ::= { pmDot1dStpPortEntry 6 }

pmDot1dStpPortDesignatedCost OBJECT-TYPE
   SYNTAX  Integer32
   MAX-ACCESS  read-only
   STATUS  current
   DESCRIPTION
     "The path cost of the Designated Port of the
     segment connected to this port.  This value is
     compared to the Root Path Cost field in received
     bridge PDUs."
   REFERENCE
     "IEEE 802.1D-1998: Section 8.5.5.5"
   ::= { pmDot1dStpPortEntry 7 }

pmDot1dStpPortDesignatedBridge OBJECT-TYPE
   SYNTAX  BridgeId
   MAX-ACCESS  read-only
   STATUS  current
   DESCRIPTION
     "The Bridge Identifier of the bridge which this
     port considers to be the Designated Bridge for
     this port's segment."
   REFERENCE
     "IEEE 802.1D-1998: Section 8.5.5.6"
   ::= { pmDot1dStpPortEntry 8 }

pmDot1dStpPortDesignatedPort OBJECT-TYPE
   SYNTAX  OCTET STRING (SIZE (2))
   MAX-ACCESS  read-only
   STATUS  current
   DESCRIPTION
     "The Port Identifier of the port on the Designated
     Bridge for this port's segment."
   REFERENCE
     "IEEE 802.1D-1998: Section 8.5.5.7"
   ::= { pmDot1dStpPortEntry 9 }

pmDot1dStpPortForwardTransitions OBJECT-TYPE
   SYNTAX  Counter32
   MAX-ACCESS  read-only
   STATUS  current
   DESCRIPTION
     "The number of times this port has transitioned
     from the Learning state to the Forwarding state."
   ::= { pmDot1dStpPortEntry 10 }

pmDot1dStpPortPathCost32 OBJECT-TYPE
       SYNTAX      Integer32 (1..200000000)
       MAX-ACCESS  read-write
       STATUS      current
       DESCRIPTION
           "The contribution of this port to the path cost of
           paths towards the spanning tree root which include
           this port.  802.1D-1998 recommends that the default
           value of this parameter be in inverse proportion to
           the speed of the attached LAN.

           This object replaces pmDot1dStpPortPathCost to support
           IEEE 802.1t."
       REFERENCE
           "IEEE 802.1t clause 8.10.2, Table 8-5."
       ::= { pmDot1dStpPortEntry 11 }

   -- the pmDot1dTp group

   -- Implementation of the pmDot1dTp group is optional.  It is
   -- implemented by those bridges that support the transparent
   -- bridging mode.  A transparent or SRT bridge will implement
   -- this group.
   
pmDot1dTpTable OBJECT-TYPE
   SYNTAX       SEQUENCE OF PmDot1dTpEntry
   MAX-ACCESS   not-accessible
   STATUS       current
   DESCRIPTION
      "Table of Tp per virtual bridge"
   ::= { pmDot1dTp 1 }

pmDot1dTpEntry OBJECT-TYPE
   SYNTAX       PmDot1dTpEntry
   MAX-ACCESS   not-accessible
   STATUS       current
   DESCRIPTION
     "Per bridge TpScalars"
   INDEX { pmDot1dBaseContextId}
   ::= { pmDot1dTpTable 1 }

PmDot1dTpEntry ::=
   SEQUENCE {
          pmDot1dTpLearnedEntryDiscards
             Counter32,
          pmDot1dTpAgingTime
             Integer32
}

pmDot1dTpAgingTime OBJECT-TYPE
   SYNTAX   Integer32 (10..1000000)
   UNITS       "seconds"
   MAX-ACCESS   read-write
   STATUS   current
   DESCRIPTION
     "The timeout period in seconds for aging out
     dynamically learned forwarding information.
     802.1D-1998 recommends a default of 300 seconds."
   REFERENCE
     "IEEE 802.1D-1998: Section 14.7.1.1.3"
   ::= { pmDot1dTpEntry 2 }


pmMIDot1wPmRst             OBJECT IDENTIFIER ::= { privateMIRstMIB 1 }

-- pmMIDot1wPmRst group 

pmMIDot1wPmRstTable OBJECT-TYPE
   SYNTAX SEQUENCE OF PmMIDot1wPmRstEntry
   MAX-ACCESS  not-accessible
   STATUS      current
   DESCRIPTION
      "List of per virtual context RstModule Parameters"
   ::= { pmMIDot1wPmRst 3}

pmMIDot1wPmRstEntry OBJECT-TYPE
   SYNTAX      PmMIDot1wPmRstEntry
   MAX-ACCESS  not-accessible
   STATUS      current
   DESCRIPTION
      "Virtual Bridge RstModule Parameters."
   INDEX { pmMIDot1wPmRstContextId }
   ::= { pmMIDot1wPmRstTable 1 }

PmMIDot1wPmRstEntry ::=
         SEQUENCE {
                 pmMIDot1wPmRstContextId
                    Integer32,
                 pmMIRstSystemControl
                    INTEGER,
                 pmMIRstModuleStatus
                    EnabledStatus,
                 pmMIRstDynamicPathcostCalculation
                    TruthValue,
                 pmMIRstCalcPortPathCostOnSpeedChg
                    TruthValue,
                pmMIRstFlushInterval
                    Timeout,
                pmMIRstFlushIndicationThreshold
                    Integer32,
                pmMIRstTotalFlushCount
                    Counter32,
                pmMIRstFwdDelayAltPortRoleTrOptimization
                    EnabledStatus,
                pmMIRstBpduGuard
                    INTEGER
         }

pmMIDot1wPmRstContextId OBJECT-TYPE
   SYNTAX      Integer32 (0..65535)
   MAX-ACCESS  not-accessible
   STATUS      current
   DESCRIPTION
      "Identifies the Virtual Bridge Context."
   ::= { pmMIDot1wPmRstEntry 1 }

pmMIRstModuleStatus OBJECT-TYPE
   SYNTAX      EnabledStatus
   MAX-ACCESS  read-write
   STATUS      current
   DESCRIPTION
      "The administrative module status requested by management for the RSTP
      Module. This enables or disables RSTP in the system. A value of 'enabled'
      (1) indicates that RSTP must be enabled in the device on all the ports.
      A value of 'disabled'(2) indicates that RSTP must be disabled in the
      device on all the ports. This object can be set only after the object
      pmMIRstSystemControl has been set."
   ::= {pmMIDot1wPmRstEntry 3 }

pmMIRstDynamicPathcostCalculation OBJECT-TYPE
      SYNTAX      TruthValue               
      MAX-ACCESS  read-write           
      STATUS      current
      DESCRIPTION
         "This object is used to determine whether dynamic pathcost
          calculation is allowed or not.The value is determined by 
          management. If set to true, pathcost is calculated dynamically 
          from port speed(when the operational status of the port changes 
          from down to up), otherwise the link speed at the time of port 
          creation is used for calculating the path cost. In both cases
          if the user has configured a pathcost for the port that will be 
          used. By default dynamic pathcost calculation is set to false."
      DEFVAL { false }
   ::= { pmMIDot1wPmRstEntry 13 }

pmMIRstCalcPortPathCostOnSpeedChg OBJECT-TYPE
      SYNTAX      TruthValue
      MAX-ACCESS  read-write
      STATUS      current
      DESCRIPTION
         "This object is used to determine whether dynamic pathcost
          calculation is done for a port for which Port Speed is changing
          dynamically. This is mainly intended for Link Aggregated ports where
          depening on Active ports speed of Link aggregated port changes.
          By default dynamic pathcost calculation on change in speed is set to
          false."
      DEFVAL { false }
      ::= { pmMIDot1wPmRstEntry 15 }

pmMIRstFlushInterval OBJECT-TYPE
   SYNTAX      Timeout (0..500) 
   UNITS       "centi-seconds"
   MAX-ACCESS  read-write  
   STATUS      current
   DESCRIPTION
           "This time value, measured in units of hundredths
           of a second, controls the number of flush indications 
           invoked from RSTP module. 
           
           If set to zero, then normal port based flushing will take place
           in RSTP (for backward compatibility, which will be retained as
           default value). 

           If set to non-zero, then global/port based flushing will be done
           based on the pmMIRstFlushIndicationThreshold value.  
           
           This scale would help to adjust the timer value, 
           based on the deployment scenario."
   DEFVAL {0}
   ::= { pmMIDot1wPmRstEntry 21 }

pmMIRstFlushIndicationThreshold OBJECT-TYPE
   SYNTAX      Integer32 (0..65535) 
   MAX-ACCESS  read-write  
   STATUS      current
   DESCRIPTION
         "This indicates the number of flush indications to go before
         timer method triggers. (i.e) The number of flush indications
         to trigger the FlushInterval Timer. 
         
         This value can be configurable only when pmMIRstFlushInterval
         is other than default value. 
         
         When the value is retained as default value and flush interval 
         is being configured other than default value(0), then 
         global flushing will happen. 
         
         When this value is non-default and the flush interval is being 
         configured other than default value(0), then the port
         based flushing will happen until the actual flush indication 
         reaches the threshold. Once the threshold is reached, timer 
         will be started and during timer expiry gloabl flushing will 
         happen. "
   DEFVAL {0}
   ::= { pmMIDot1wPmRstEntry 22 }

pmMIRstTotalFlushCount OBJECT-TYPE
   SYNTAX      Counter32
   MAX-ACCESS  read-only
   STATUS      current
   DESCRIPTION
         "The number of times flush is being triggered from 
         the STP stack in case of RSTP mode." 
   ::= { pmMIDot1wPmRstEntry 23 } 
   
pmMIRstBpduGuard OBJECT-TYPE
    SYNTAX      INTEGER    {
                    enable (1),
                    disable (2)
                    }
      MAX-ACCESS  read-write
      STATUS      current
      DESCRIPTION
          "This object configures BPDU guard globally in RSTP 
           and this global BPDU is applicable if and only if no Port specific 
           BpduGuard is configured.
           Enable - enables  BPDU Guard feature on edge ports globally and
           moves the port to disabled discarding state when BPDU is received 
           on the edge ports.
           Disable - disables  BPDU Guard feature on edge ports globally"           
    DEFVAL { 2 }
   ::= { pmMIDot1wPmRstEntry 25 }

-- -------------------------------------
-- RSTP Port Extention Group 
-- -------------------------------------

pmMIRstPortExtTable OBJECT-TYPE
   SYNTAX SEQUENCE OF PmMIRstPortExtEntry
   MAX-ACCESS not-accessible
   STATUS     current
   DESCRIPTION
      "This is a table that is an extension to the dot1dStpExtPortTable.
      This contains object(s) that are Port-based."
   ::= { pmMIDot1wPmRst 4 }

pmMIRstPortExtEntry OBJECT-TYPE
   SYNTAX      PmMIRstPortExtEntry
   MAX-ACCESS  not-accessible
   STATUS      current
   DESCRIPTION
      "Each entry in this table is for each port present in the system.
      This table is indexed by the pmMIRstPort."
   INDEX { pmMIRstPort }
   ::= { pmMIRstPortExtTable 1 }
      
PmMIRstPortExtEntry ::=
   SEQUENCE {
      pmMIRstPort
         Integer32,
      pmMIRstPortRole
         INTEGER,
      pmMIRstPortRxRstBpduCount
         Counter32,
      pmMIRstPortRxConfigBpduCount
         Counter32,
      pmMIRstPortRxTcnBpduCount
         Counter32,
      pmMIRstPortTxRstBpduCount
         Counter32,
      pmMIRstPortTxConfigBpduCount
         Counter32,
      pmMIRstPortTxTcnBpduCount
         Counter32,
      pmMIRstPortInvalidRstBpduRxCount
         Counter32,
      pmMIRstPortProtocolMigrationCount
         Counter32,
      pmMIRstPortAutoEdge
         TruthValue,
      pmMIRstPortRestrictedRole 
          TruthValue, 
      pmMIRstPortRestrictedTCN 
          TruthValue,
      pmMIRstPortEnableBPDURx
          TruthValue,
      pmMIRstPortEnableBPDUTx
          TruthValue,
      pmMIRstPortPseudoRootId
          BridgeId,
      pmMIRstPortIsL2Gp
          TruthValue,
      pmMIRstPortLoopGuard
          TruthValue,
      pmMIRstPortRowStatus 
          RowStatus,
      pmMIRstLoopInconsistentState 
          TruthValue
      }

pmMIRstPort OBJECT-TYPE
   SYNTAX      Integer32 (1..4096)
   MAX-ACCESS  not-accessible
   STATUS      current
   DESCRIPTION
      "A unique value, greater than zero, indicating the Port number."
   ::= { pmMIRstPortExtEntry 1 }

pmMIRstPortRole OBJECT-TYPE
   SYNTAX      INTEGER {
                  disabledPort(0),
                  alternatePort(1),
                  backupPort(2),
                  rootPort(3),
                  designatedPort(4)
               }
   MAX-ACCESS  read-only
   STATUS      current
   DESCRIPTION
      "This indicates the current Port Role assumed by this Port."
   ::= { pmMIRstPortExtEntry 2 }

pmMIRstPortRxRstBpduCount OBJECT-TYPE
   SYNTAX      Counter32
   MAX-ACCESS  read-only
   STATUS      current
   DESCRIPTION
      "The number of RST BPDUs that have been received on this Port."
   ::= { pmMIRstPortExtEntry 10 }

pmMIRstPortRxConfigBpduCount OBJECT-TYPE
   SYNTAX      Counter32
   MAX-ACCESS  read-only
   STATUS      current
   DESCRIPTION
      "The number of Config BPDUs that have been received on this Port."
   ::= { pmMIRstPortExtEntry 11 }

pmMIRstPortRxTcnBpduCount OBJECT-TYPE
   SYNTAX      Counter32
   MAX-ACCESS  read-only
   STATUS      current
   DESCRIPTION
      "The number of TCN BPDUs that have been received on this Port."
   ::= { pmMIRstPortExtEntry 12 }

pmMIRstPortTxRstBpduCount OBJECT-TYPE
   SYNTAX      Counter32
   MAX-ACCESS  read-only
   STATUS      current
   DESCRIPTION
      "The number of RST BPDUs that have been transmitted by this Port."
   ::= { pmMIRstPortExtEntry 13 }

pmMIRstPortTxConfigBpduCount OBJECT-TYPE
   SYNTAX      Counter32
   MAX-ACCESS  read-only
   STATUS      current
   DESCRIPTION
      "The number of Config BPDUs that have been transmitted by this Port."
   ::= { pmMIRstPortExtEntry 14 }

pmMIRstPortTxTcnBpduCount OBJECT-TYPE
   SYNTAX      Counter32
   MAX-ACCESS  read-only
   STATUS      current
   DESCRIPTION
      "The number of TCN BPDUs that have been transmitted by this Port."
   ::= { pmMIRstPortExtEntry 15 }

pmMIRstPortInvalidRstBpduRxCount OBJECT-TYPE
   SYNTAX      Counter32
   MAX-ACCESS  read-only
   STATUS      current
   DESCRIPTION
      "The number of invalid RSTP BPDUs that have been received on this Port.
       A Trap is generated on the occurrence of this event."
   ::= { pmMIRstPortExtEntry 16 }

pmMIRstPortProtocolMigrationCount OBJECT-TYPE
   SYNTAX      Counter32
   MAX-ACCESS  read-only
   STATUS      current
   DESCRIPTION
      "The number of times this Port has migrated from one STP protocol 
       version to another. The relevant protocols are STP-COMPATIBLE and RSTP.
       A Trap is generated on the occurrence of this event."
   ::= { pmMIRstPortExtEntry 19 }

pmMIRstPortAutoEdge OBJECT-TYPE
    SYNTAX      TruthValue
    MAX-ACCESS  read-write
    STATUS      current
    DESCRIPTION
        " This parameter when TRUE(1) indicates that detection of a port 
         as Edge Port happens automatically and FALSE(2) 
         indicates that this feature is disabled."
    
    ::= { pmMIRstPortExtEntry 21 }

pmMIRstPortRestrictedRole OBJECT-TYPE 
    SYNTAX      TruthValue 
    MAX-ACCESS  read-write 
    STATUS      current 
    DESCRIPTION 
        "A Boolean value set by management. If TRUE causes the Port not 
        to be selected as Root Port for the CIST or any MSTI, even it has 
        the best spanning tree priority vector. Such a Port will be selected 
        as an Alternate Port after the Root Port has been selected. This 
        parameter should be FALSE by default. If set it can cause lack of 
        spanning tree connectivity. It is set by a network administrator to 
        prevent bridges external to a core region of the network influencing 
        the spanning tree active topology, possibly because those bridges are 
        not under the full control of the administrator. 
                                                                                        This administrator configuration is also known as 'Root Guard'." 
        
        ::= {pmMIRstPortExtEntry 22} 

pmMIRstPortRestrictedTCN OBJECT-TYPE 
    SYNTAX      TruthValue 
    MAX-ACCESS  read-write 
    STATUS      current 
    DESCRIPTION 
        "A Boolean value set by management. If TRUE causes the Port not 
        to propagate received topology change notifications and topology 
        changes to other Ports. This parameter should be FALSE by default. 
        If set it can cause temporarilyorary loss of connectivity after changes in 
        a spanning trees active topology as a result of persistent 
        incorrectly learnt station location information. It is set by a 
        network administrator to prevent bridges external to a core region of 
        the network causing address flushing in that region, possibly because 
        those bridges are not under the full control of the administrator or 
        MAC_Operational for the attached LANs transitions frequently." 

        ::= {pmMIRstPortExtEntry 23} 

pmMIRstPortEnableBPDURx OBJECT-TYPE
    SYNTAX      TruthValue
    MAX-ACCESS  read-write
    STATUS      current
    DESCRIPTION
        "A Boolean value set by management. If FALSE, the BPDUs received on
        the port are ignored."
    DEFVAL { true }
    ::= {pmMIRstPortExtEntry 24 }

pmMIRstPortEnableBPDUTx OBJECT-TYPE
    SYNTAX      TruthValue
    MAX-ACCESS  read-write
    STATUS      current
    DESCRIPTION
        "A Boolean value set by management. If FALSE, no BPDUs are transmitted
        by this port. This variable should be FALSE before configuring port
        as a Layer Two Gateway Port."
    DEFVAL { true }
    ::= {pmMIRstPortExtEntry 25 }

pmMIRstPortPseudoRootId OBJECT-TYPE
    SYNTAX      BridgeId
    MAX-ACCESS  read-write
    STATUS      current
    DESCRIPTION
        "In RSTP Bridge, the pmMIRstPortPseudoRootId parameter value.
        By default, it is set to the BridgeIdentifier.
        The pseudoRootId is used by Layer Two Gateway Port as the RootId
        in generated BPDUs."
    ::= {pmMIRstPortExtEntry 26 }

pmMIRstPortIsL2Gp OBJECT-TYPE
    SYNTAX      TruthValue
    MAX-ACCESS  read-write
    STATUS      current
    DESCRIPTION
        "A Boolean value set by management. If TRUE, then port is functioning
        as a Layer Two Gateway Port. The pmMIRstPortEnableBPDUTx should be
        FALSE to set pmMIRstPortIsL2Gp to TRUE."
    DEFVAL { false }
    ::= {pmMIRstPortExtEntry 27 }

pmMIRstPortLoopGuard OBJECT-TYPE
    SYNTAX      TruthValue
    MAX-ACCESS  read-write
    STATUS      current
    DESCRIPTION
        "A Boolean value set by management. If TRUE, then it will not age out
        the information even if the peer does not send information. If the port
        continues to receive information through BPDUs the operation
        on this port will be normal. This will be useful when the neighbor
        bridge is faulty, i.e. it cannot send BPDUs but continues to send data
        traffic."

    DEFVAL { false }
    ::= { pmMIRstPortExtEntry 28 }

pmMIRstPortRowStatus OBJECT-TYPE
   SYNTAX      RowStatus
   MAX-ACCESS  read-create
   STATUS      current
   DESCRIPTION
      "This object is used to create or delete interfaces at RSTP module
       level.Ports can be created at RSTP module level only for ports that
       have been created in Interface manager and mapped to a context .
       This is applicable only when Automatic Port Create Feature is Disabled. "
   ::= { pmMIRstPortExtEntry 34 }

pmMIRstLoopInconsistentState   OBJECT-TYPE 
   SYNTAX      TruthValue 
   MAX-ACCESS  read-only 
   STATUS      current 
   DESCRIPTION 
       " A Boolean value set when the non-designated port on expiry of received information while timer 
        transitions to Designated/Discarding state when the superior BPDU's are not received with the 
        loop guard feature being enabled on that port. 
        A value of TRUE, indicates that the state of this port is moved into an loop-inconsistent 
        state.A value of  FALSE, indicates that this port is not moved into an loop-inconsistent 
        state " 
   DEFVAL { false } 
   ::= { pmMIRstPortExtEntry 35 } 

-- END OF TABLE

      pmMIDot1sPmMst         OBJECT IDENTIFIER ::= { privateMIMstMIB 1 }

pmMIDot1sPmMstTable OBJECT-TYPE
    SYNTAX SEQUENCE OF PmMIDot1sPmMstEntry
    MAX-ACCESS    not-accessible
    STATUS        current
    DESCRIPTION
       "List of per Virtual Context Mst Module Parameters."
    ::= { pmMIDot1sPmMst 3 }

pmMIDot1sPmMstEntry OBJECT-TYPE
   SYNTAX       PmMIDot1sPmMstEntry
   MAX-ACCESS   not-accessible
   STATUS       current
   DESCRIPTION
      "Virtual Context Mst Module Parameters."
   INDEX { pmMIDot1sPmMstContextId }
   ::= { pmMIDot1sPmMstTable 1 }

PmMIDot1sPmMstEntry ::=
    SEQUENCE {
           pmMIDot1sPmMstContextId
              Integer32,
           pmMIMstModuleStatus
              EnabledStatus,
           pmMIMstMaxHopCount
              Integer32,
           pmMIMstBrgAddress
              MacAddress,
           pmMIMstCistRoot
              BridgeId,
           pmMIMstCistRegionalRoot
              BridgeId,
           pmMIMstCistRootCost
              Integer32,
           pmMIMstCistRegionalRootCost
              Integer32,
           pmMIMstCistRootPort
              Integer32,
           pmMIMstCistBridgePriority
              Integer32,
           pmMIMstCistBridgeMaxAge
              Timeout,
           pmMIMstCistBridgeForwardDelay
              Timeout,
           pmMIMstCistMaxAge
              Timeout,
           pmMIMstCistForwardDelay
              Timeout,
           pmMIMstForceProtocolVersion
              INTEGER,
           pmMIMstTxHoldCount
              Integer32,
           pmMIMstCistTimeSinceTopologyChange
              TimeTicks,
           pmMIMstCistTopChanges
              Counter32,
           pmMIMstCistHelloTime
              Timeout,
           pmMIMstCistBridgeHelloTime
              Timeout,
           pmMIMstCistDynamicPathcostCalculation
              TruthValue,
           pmMIMstCalcPortPathCostOnSpeedChg
              TruthValue,
           pmMIMstFlushInterval
              Timeout,
           pmMIMstCistFlushIndicationThreshold
              Integer32,
           pmMIMstCistTotalFlushCount
              Counter32,
           pmMIMstBpduGuard
              INTEGER
    }

pmMIDot1sPmMstContextId OBJECT-TYPE
   SYNTAX        Integer32 (0..65535)
   MAX-ACCESS    not-accessible
   STATUS        current
   DESCRIPTION
      "Identifies the Virtual Context."
   ::= { pmMIDot1sPmMstEntry 1 }

pmMIMstModuleStatus OBJECT-TYPE
   SYNTAX      EnabledStatus
   MAX-ACCESS  read-write
   STATUS      current
   DESCRIPTION
      "The administrative status requested by management for the MST  
      feature. The value enabled(1) indicates that Mst should be enabled  
      in the device on all ports. The value disabled(2) indicates that 
      Mst should be disabled in the device on all ports. The object can 
      be set to enabled(1) if and only if, pmMIMstSystemControl set to start."
   ::= { pmMIDot1sPmMstEntry 3 }  

pmMIMstMaxHopCount OBJECT-TYPE
   SYNTAX      Integer32 (600..4000)
   MAX-ACCESS  read-write
   STATUS      current
   DESCRIPTION
      "Indicates the Maximum Hop Count value. One-hundredth of the
      configured value will be set as Max Hop Count.
      An agent may return a badValue error if a set is attemporarilyted
      to a value which is not a multiples of hundred."
   DEFVAL { 2000 }
   ::= { pmMIDot1sPmMstEntry 6 }  

pmMIMstBrgAddress OBJECT-TYPE
   SYNTAX      MacAddress
   MAX-ACCESS  read-only
   STATUS      current
   DESCRIPTION
         "The MAC address used by this bridge when it must
          be referred to in a unique fashion.   It is
          recommended that this be the numerically smallest
          MAC address of all ports that belong to this
          bridge.  However it is only required to be unique.
          When concatenated with pmMIMstCistBridgePriority or 
          pmMIMstMstiBridgePriority a unique BridgeIdentifier 
          is formed which is used in the Spanning Tree Protocol."
   ::= { pmMIDot1sPmMstEntry 7 } 

pmMIMstCistRoot OBJECT-TYPE
   SYNTAX      BridgeId  
   MAX-ACCESS  read-only
   STATUS      current
   DESCRIPTION
        "The bridge identifier of the Root of the common spanning
         tree as determined by the Spanning Tree Protocol
         as executed by this node.  This value is used as
         the CIST Root Identifier parameter in all Configuration
         Bridge PDUs originated by this node."
   ::= { pmMIDot1sPmMstEntry 8 } 

pmMIMstCistRegionalRoot OBJECT-TYPE
   SYNTAX      BridgeId  
   MAX-ACCESS  read-only
   STATUS      current
   DESCRIPTION
        "The bridge identifier of the Root of the Multiple
         spanning tree region as determined by the Spanning Tree
         Protocol as executed by this node.  This value is used as
         the CIST Regional Root Identifier parameter in all Configuration
         Bridge PDUs originated by this node."
   ::= { pmMIDot1sPmMstEntry 9 } 

pmMIMstCistRootCost OBJECT-TYPE
   SYNTAX      Integer32 
   MAX-ACCESS  read-only
   STATUS      current
   DESCRIPTION
        "The Cost of the path to the CIST Root as seen 
        from this bridge."
   ::= { pmMIDot1sPmMstEntry 10 } 

pmMIMstCistRegionalRootCost OBJECT-TYPE
   SYNTAX      Integer32 
   MAX-ACCESS  read-only
   STATUS      current
   DESCRIPTION
        "The Cost of the path to the CIST Regional Root 
        as seen from this bridge."
   ::= { pmMIDot1sPmMstEntry 11 } 

pmMIMstCistRootPort OBJECT-TYPE
   SYNTAX      Integer32  
   MAX-ACCESS  read-only      
   STATUS      current 
   DESCRIPTION 
      "The Port Number of the Port which offers the lowest    
       path cost from this bridge to the CIST Root Bridge."
   ::= { pmMIDot1sPmMstEntry 12 } 

pmMIMstCistBridgePriority OBJECT-TYPE
   SYNTAX      Integer32 (0..61440) 
   MAX-ACCESS  read-write
   STATUS      current
   DESCRIPTION
        "The Value of the writable portion of the Bridge
        Identifier comprising of the first two octets.
        The values that are set for Bridge Priority must be 
        in steps of 4096."
   DEFVAL {32768}
   ::= { pmMIDot1sPmMstEntry 13 } 

pmMIMstCistBridgeMaxAge OBJECT-TYPE
   SYNTAX      Timeout (600..4000)  
   UNITS       "centi-seconds"
   MAX-ACCESS  read-write
   STATUS      current
   DESCRIPTION
        "The value that all bridges use for MaxAge when
         this bridge is acting as the root. The granularity 
         of this timer is specified to be 1 second.
         An agent may return a badValue error if a set is
         attemporarilyted to a value which is not a whole number
         of seconds."
   DEFVAL {2000}
   ::= { pmMIDot1sPmMstEntry 14 } 

pmMIMstCistBridgeForwardDelay OBJECT-TYPE
   SYNTAX      Timeout (400..3000)  
   UNITS       "centi-seconds"
   MAX-ACCESS  read-write
   STATUS      current
   DESCRIPTION
        "The value that all bridges use for ForwardDelay
         when this bridge is acting as the root.  Note that
         802.1D specifies that the range for this
         parameter is related to the value of
         BridgeMaxAge.  The granularity of this
         timer is specified to be 1 second.
         An agent may return a badValue error if a set is
         attemporarilyted to a value which is not a whole number
         of seconds."
   DEFVAL {1500}
   ::= { pmMIDot1sPmMstEntry 15 } 

pmMIMstCistMaxAge OBJECT-TYPE
   SYNTAX      Timeout
   UNITS       "centi-seconds"
   MAX-ACCESS  read-only  
   STATUS      current
   DESCRIPTION
         "The maximum age of Spanning Tree Protocol
          information learned from the network on any port
          before it is discarded, in units of hundredths of
          a second.  This is the actual value that this
          bridge is currently using."
   ::= { pmMIDot1sPmMstEntry 17 } 

pmMIMstCistForwardDelay OBJECT-TYPE
   SYNTAX      Timeout
   UNITS       "centi-seconds"
   MAX-ACCESS  read-only  
   STATUS      current
   DESCRIPTION
      "This time value, measured in units of hundredths
       of a second, controls how fast a port changes its
       spanning state when moving towards the Forwarding
       state.  The value determines how long the port
       stays in a particular state before moving to the
       next state."
   ::= { pmMIDot1sPmMstEntry 18 } 

pmMIMstForceProtocolVersion OBJECT-TYPE
   SYNTAX      INTEGER {
                  stpCompatible(0),
                  rstp(2),
                  mstp(3)
               }
   MAX-ACCESS  read-write 
   STATUS      current
   DESCRIPTION
    "The version of Spanning Tree Protocol the bridge is
    currently running.  The value 'stpCompatible(0)'
    indicates the Spanning Tree Protocol specified in
    IEEE 802.1D and 'rstp(2)' indicates the Rapid Spanning
    Tree Protocol specified in IEEE 802.1w and 'mstp(3)'
    indicates the Multiple Spanning Tree Protocol Specified
    in IEEE 802.1s." 

   DEFVAL { mstp }
   ::= { pmMIDot1sPmMstEntry 24 } 

pmMIMstTxHoldCount OBJECT-TYPE
    SYNTAX      Integer32 (1..10)
    MAX-ACCESS  read-write
    STATUS      current
    DESCRIPTION
        "The value used by the Port Transmit state machine to limit
         the maximum transmission rate."
    DEFVAL  { 6 }
   ::= { pmMIDot1sPmMstEntry 25 } 

pmMIMstCistTimeSinceTopologyChange OBJECT-TYPE
   SYNTAX      TimeTicks 
   UNITS       "centi-seconds"
   MAX-ACCESS  read-only
   STATUS      current
   DESCRIPTION
         "The time (in hundredths of a second) since the
         TcWhile Timer for any port in this Bridge was 
         non-zero for Common Spanning Tree context."
   ::= { pmMIDot1sPmMstEntry 34 } 

pmMIMstCistTopChanges OBJECT-TYPE
   SYNTAX      Counter32
   MAX-ACCESS  read-only
   STATUS      current
   DESCRIPTION
         "The number of times that there have been atleast
         one non-zero TcWhile Timer on this Bridge for Common
         Spanning Tree context."
   ::= { pmMIDot1sPmMstEntry 35 } 

pmMIMstCistHelloTime OBJECT-TYPE
   SYNTAX      Timeout
   UNITS       "centi-seconds"
   MAX-ACCESS  read-only  
   STATUS      current
   DESCRIPTION
           "This time value, measured in units of hundredths
           of a second, specifies the amount of time between
           the transmission of configuration BPDUs by this node
           on any port when it is the root of the spanning tree 
           or trying to become so."
   ::= { pmMIDot1sPmMstEntry 37 } 

pmMIMstCistBridgeHelloTime OBJECT-TYPE
   SYNTAX      Timeout (100|200)  
   UNITS       "centi-seconds"
   MAX-ACCESS  read-write  
   STATUS      current
   DESCRIPTION
           "The amount of time between the transmission of
           Configuration bridge PDUs by this node in units 
           of hundredths of a second."
      ::= { pmMIDot1sPmMstEntry 38 }

pmMIMstCistDynamicPathcostCalculation OBJECT-TYPE
      SYNTAX      TruthValue               
      MAX-ACCESS  read-write           
      STATUS      current
      DESCRIPTION
         "This object is used to determine whether dynamic pathcost
          calculation is allowed or not.The value is determined by 
          management. If set to true, pathcost is calculated dynamically 
          from port speed(when the operational status of the port changes 
          from down to up), otherwise the link speed at the time of port 
          creation is used for calculating the path cost. In both cases
          if the user has configured a pathcost for the port that will be 
          used. By default dynamic pathcost calculation is set to false."
      DEFVAL { false }
      ::= { pmMIDot1sPmMstEntry 39 }

pmMIMstCalcPortPathCostOnSpeedChg OBJECT-TYPE
      SYNTAX      TruthValue               
      MAX-ACCESS  read-write           
      STATUS      current
      DESCRIPTION
         "This object is used to determine whether dynamic pathcost
          calculation is done for a port for which Port Speed is changing
          dynamically. This is mainly intended for Link Aggregated ports where
          depening on Active ports speed of Link aggregated port changes.
          By default dynamic pathcost calculation on change in speed is set to
          false."
      DEFVAL { false }
      ::= { pmMIDot1sPmMstEntry 41 }

pmMIMstFlushInterval OBJECT-TYPE
   SYNTAX      Timeout (0..500) 
   UNITS       "centi-seconds"
   MAX-ACCESS  read-write  
   STATUS      current
   DESCRIPTION
           "This time value, measured in units of hundredths
           of a second, controls the number of flush indications 
           invoked from STP module per instance basis. 
           
           If set to zero, then normal port and instance based flushing 
           will take place in MSTP (for backward compatibility, which will 
           be retained as default value). 

           If set to non-zero, then instance based flushing will be done.  
           
           This scale would help to adjust the timer value, 
           based on the deployment scenario."
   DEFVAL {0}
   ::= { pmMIDot1sPmMstEntry 47 }

pmMIMstCistFlushIndicationThreshold OBJECT-TYPE
   SYNTAX      Integer32 (0..65535) 
   MAX-ACCESS  read-write  
   STATUS      current
   DESCRIPTION
         "This indicates the number of flush indications to go before
         timer method triggers. (i.e) The number of flush indications
         to trigger the FlushInterval Timer. 
         
         This value can be configurable only when pmMIMstFlushInterval
         is other than default value. 
         
         When the value is retained as default value and flush interval 
         is being configured other than default value(0), then 
         instance based flushing will happen. 
         
         When this value is non-default and the flush interval is being 
         configured other than default value(0), then the port-instance
         based flushing will happen until the actual flush indication 
         reaches the threshold. Once the threshold is reached, timer 
         will be started and during timer expiry instance based 
         flushing will happen. "
   DEFVAL {0}
   ::= { pmMIDot1sPmMstEntry 48 }

pmMIMstCistTotalFlushCount OBJECT-TYPE
   SYNTAX      Counter32
   MAX-ACCESS  read-only
   STATUS      current
   DESCRIPTION
         "The number of times flush is being triggered from 
         the STP stack in CIST level." 
   ::= { pmMIDot1sPmMstEntry 49 } 
   
pmMIMstBpduGuard OBJECT-TYPE
    SYNTAX      INTEGER    {
                    enable (1),
                    disable (2)
                    }
      MAX-ACCESS  read-write
      STATUS      current
      DESCRIPTION
          "This object configures BPDU guard globally in MSTP 
           and this global BPDU is applicable if and only if no Port specific 
           BpduGuard is configured.
           Enable - enables  BPDU Guard feature on edge ports globally and
           moves the port to disabled discarding state when BPDU is received 
           on the edge ports.
           Disable - disables  BPDU Guard feature on edge ports globally"           
    DEFVAL { 2 }
   ::= { pmMIDot1sPmMstEntry 50 } 
-- -------------------------------------
-- pmMIDot1sPmMstTable - End
-- -------------------------------------

-- -----------------------------------------------------------------
-- Pm Mst Multiple Spanning Tree Instance Bridge Table
-- -----------------------------------------------------------------

pmMIMstMstiBridgeTable OBJECT-TYPE
   SYNTAX      SEQUENCE OF PmMIMstMstiBridgeEntry      
   MAX-ACCESS  not-accessible 
   STATUS      current 
   DESCRIPTION
      "Table containing Bridge Information specific to Spanning 
       Tree Instance. This table maintains context ID as one 
       more index to support Multiple Instances."
   ::= { pmMIDot1sPmMst 4 } 
 
pmMIMstMstiBridgeEntry OBJECT-TYPE
   SYNTAX      PmMIMstMstiBridgeEntry       
   MAX-ACCESS  not-accessible
   STATUS      current
   DESCRIPTION
      "Entry indicating the Bridge Information."
   INDEX { pmMIDot1sPmMstContextId, pmMIMstMstiInstanceIndex }
   ::= { pmMIMstMstiBridgeTable 1 }

PmMIMstMstiBridgeEntry ::=
   SEQUENCE {
      pmMIMstMstiInstanceIndex 
            Integer32,
      pmMIMstMstiBridgeRegionalRoot 
            BridgeId,
      pmMIMstMstiBridgePriority 
            Integer32,
      pmMIMstMstiRootCost 
            Integer32,
      pmMIMstMstiRootPort 
            Integer32,
      pmMIMstMstiTotalFlushCount
            Counter32
   }

pmMIMstMstiInstanceIndex OBJECT-TYPE
   SYNTAX      Integer32 (1..64|4094)
   MAX-ACCESS  not-accessible 
   STATUS      current 
   DESCRIPTION 
      "Spanning Tree Instance to which the information belongs. The
       special MSTID of 4094, known as the PTETID, identifies VIDs 
       that are used by Ethernet Switched Paths (ESPs)."
   ::= { pmMIMstMstiBridgeEntry 1 }

pmMIMstMstiBridgeRegionalRoot OBJECT-TYPE
   SYNTAX      BridgeId  
   MAX-ACCESS  read-only      
   STATUS      current 
   DESCRIPTION 
      "MSTI Regional Root Identifier value for the Instance. This value 
       is used as the MSTI Regional Root Identifier parameter in all
       Configuration Bridge PDUs originated by this node"
   ::= { pmMIMstMstiBridgeEntry 2 }

pmMIMstMstiBridgePriority OBJECT-TYPE
   SYNTAX      Integer32 (0..61440) 
   MAX-ACCESS  read-write     
   STATUS      current 
   DESCRIPTION 
      "The writable portion of the MSTI Bridge Identifier.
       comprising of the first two octets.
       The values that are set for Bridge Priority must be 
       in steps of 4096."
   DEFVAL {32768}
   ::= { pmMIMstMstiBridgeEntry 3 }

pmMIMstMstiRootCost OBJECT-TYPE
   SYNTAX      Integer32  
   MAX-ACCESS  read-only      
   STATUS      current 
   DESCRIPTION 
      "The Cost of the path to the MSTI Regional Root as seen 
       by this bridge." 
   ::= { pmMIMstMstiBridgeEntry 4 }

pmMIMstMstiRootPort OBJECT-TYPE
   SYNTAX      Integer32  
   MAX-ACCESS  read-only      
   STATUS      current 
   DESCRIPTION 
      "The Port Number of the Port which offers the lowest    
       path cost from this bridge to the MSTI Region Root Bridge."
   ::= { pmMIMstMstiBridgeEntry 5 }

pmMIMstMstiTotalFlushCount OBJECT-TYPE
   SYNTAX      Counter32
   MAX-ACCESS  read-only
   STATUS      current
   DESCRIPTION
         "The number of times flush is being triggered from 
         the STP stack for this specific instance level." 
     ::= { pmMIMstMstiBridgeEntry 15 } 

-- -----------------------------------------------------------------
-- Pm Mst VlanId to Instance Mapping Table              
-- -----------------------------------------------------------------

pmMIMstVlanInstanceMappingTable OBJECT-TYPE
    SYNTAX      SEQUENCE OF PmMIMstVlanInstanceMappingEntry
    MAX-ACCESS  not-accessible
    STATUS      current
    DESCRIPTION
          "This table contains one entry for each instance of MSTP. 
      This table maintains context ID as one more index to 
      support Multiple Instances." 
     ::= { pmMIDot1sPmMst 5 }

pmMIMstVlanInstanceMappingEntry OBJECT-TYPE
      SYNTAX      PmMIMstVlanInstanceMappingEntry
      MAX-ACCESS  not-accessible
      STATUS      current
      DESCRIPTION
          "A conceptual row containing the status of the MSTP instance."
      INDEX  { pmMIDot1sPmMstContextId, pmMIMstInstanceIndex }
      ::= { pmMIMstVlanInstanceMappingTable 1 }

PmMIMstVlanInstanceMappingEntry ::= 
   SEQUENCE {
       pmMIMstInstanceIndex  
            Integer32
   }

pmMIMstInstanceIndex OBJECT-TYPE
      SYNTAX      Integer32 (1..64|4094)
      MAX-ACCESS  not-accessible
      STATUS      current
      DESCRIPTION
          "An arbitrary integer within the range from 1 to the value of
           Max Instance Number that uniquely identifies an instance. In
           a Bridge that supports PBB-TE, the special MSTID of 4094, the
           PTETID, identifies VIDs that can be used by Ethernet Switched
           Paths (ESPs). ESPs are provisioned seperately by any external agent
           and do not use spanning tree."
      ::= { pmMIMstVlanInstanceMappingEntry 1 }

-- -----------------------------------------------------------------
-- Pm Mst Common Spanning Tree Port Table     
-- -----------------------------------------------------------------

pmMIMstCistPortTable OBJECT-TYPE
    SYNTAX      SEQUENCE OF PmMIMstCistPortEntry              
    MAX-ACCESS  not-accessible
    STATUS      current
    DESCRIPTION
          "This table contains Common Spanning Tree Port
           Information."
     ::= { pmMIDot1sPmMst 6 }

pmMIMstCistPortEntry OBJECT-TYPE
      SYNTAX      PmMIMstCistPortEntry               
      MAX-ACCESS  not-accessible
      STATUS      current
      DESCRIPTION
          "A list of information maintained by every port for 
          Common Spanning tree."
      INDEX  { pmMIMstCistPort }
      ::= { pmMIMstCistPortTable 1 }

PmMIMstCistPortEntry ::= 
   SEQUENCE {
       pmMIMstCistPort  
            Integer32,
       pmMIMstCistPortPathCost 
            Integer32,
       pmMIMstCistPortPriority 
            Integer32,
       pmMIMstCistPortDesignatedRoot 
            BridgeId,
       pmMIMstCistPortDesignatedBridge 
            BridgeId,
       pmMIMstCistPortDesignatedPort 
            OCTET STRING,
       pmMIMstCistPortAdminP2P 
            INTEGER,
       pmMIMstCistPortOperP2P 
            TruthValue,
       pmMIMstCistPortAdminEdgeStatus 
            TruthValue,
       pmMIMstCistPortOperEdgeStatus 
            TruthValue,
       pmMIMstCistPortState 
            INTEGER,
       pmMIMstCistForcePortState 
            INTEGER,
       pmMIMstCistPortForwardTransitions 
            Counter32,
       pmMIMstCistPortRxMstBpduCount
            Counter32,
       pmMIMstCistPortRxRstBpduCount
            Counter32,
       pmMIMstCistPortRxConfigBpduCount
            Counter32,
       pmMIMstCistPortRxTcnBpduCount
            Counter32,
       pmMIMstCistPortTxMstBpduCount
            Counter32,
       pmMIMstCistPortTxRstBpduCount
            Counter32,
       pmMIMstCistPortTxConfigBpduCount
            Counter32,
       pmMIMstCistPortTxTcnBpduCount
            Counter32,
       pmMIMstCistPortInvalidMstBpduRxCount
            Counter32,
       pmMIMstCistProtocolMigrationCount 
            Counter32,
       pmMIMstCistPortDesignatedCost 
            Integer32,
       pmMIMstCistPortRegionalRoot 
            BridgeId,
       pmMIMstCistPortRegionalPathCost 
            Integer32,
       pmMIMstCistCurrentPortRole  
            INTEGER,
       pmMIMstCistPortHelloTime 
            Timeout,
       pmMIMstCistPortAutoEdgeStatus 
            TruthValue,
       pmMIMstCistPortRestrictedRole 
           TruthValue, 
       pmMIMstCistPortRestrictedTCN 
           TruthValue,
       pmMIMstCistPortEnableBPDURx
           TruthValue,
       pmMIMstCistPortEnableBPDUTx
           TruthValue,
       pmMIMstCistPortPseudoRootId
            BridgeId,
       pmMIMstCistPortIsL2Gp
           TruthValue,
       pmMIMstCistPortLoopGuard
           TruthValue,
       pmMIMstCistLoopInconsistentState 
               TruthValue
}

pmMIMstCistPort OBJECT-TYPE
      SYNTAX      Integer32 (1..65535)
      MAX-ACCESS  not-accessible
      STATUS      current
      DESCRIPTION
          "The Port number of the port for which this entry contains   
           spanning tree information."                                      
      ::= { pmMIMstCistPortEntry 1 }

pmMIMstCistPortPathCost OBJECT-TYPE
      SYNTAX      Integer32 (1..200000000)
      MAX-ACCESS  read-write           
      STATUS      current
      DESCRIPTION
            "The contribution of this port to the path cost of
             paths towards the CIST Root which include this port."
      ::= { pmMIMstCistPortEntry 2 }

pmMIMstCistPortPriority OBJECT-TYPE
      SYNTAX      Integer32 (0..240)
      MAX-ACCESS  read-write           
      STATUS      current
      DESCRIPTION
          "The four most significant bits of the Port Identifier 
          of the Spanning Tree instance can be modified by setting 
          the CistPortPriority value. The values that are set for Port 
          Priority must be in steps of 16."
     DEFVAL {128}
      ::= { pmMIMstCistPortEntry 3 }

pmMIMstCistPortDesignatedRoot OBJECT-TYPE
      SYNTAX      BridgeId                 
      MAX-ACCESS  read-only            
      STATUS      current
      DESCRIPTION
          "The unique Bridge Identifier of the bridge recorded as the  
           CIST Root in the configuration BPDUs transmitted."      
      ::= { pmMIMstCistPortEntry 4 }

pmMIMstCistPortDesignatedBridge OBJECT-TYPE
      SYNTAX      BridgeId                 
      MAX-ACCESS  read-only            
      STATUS      current
      DESCRIPTION
          "The unique Bridge Identifier of the bridge which this port  
           considers to be the Designated Bridge for the port's segment."   
      ::= { pmMIMstCistPortEntry 5 }

pmMIMstCistPortDesignatedPort OBJECT-TYPE
      SYNTAX  OCTET STRING (SIZE (2))
      MAX-ACCESS  read-only            
      STATUS      current
      DESCRIPTION
          "The Port identifier of the port on the Designated Bridge    
           for this port's segment."                                           
      ::= { pmMIMstCistPortEntry 6 }

pmMIMstCistPortAdminP2P OBJECT-TYPE
      SYNTAX      INTEGER {               
                    forceTrue(0),
                    forceFalse(1),
                    auto(2)
                  }
      MAX-ACCESS  read-write           
      STATUS      current
      DESCRIPTION
          "The administrative point-to-point status of the LAN segment
          attached to this port.  A value of forceTrue(0) indicates that
          this port should always be treated as if it is connected to
          a point-to-point link.  A value of forceFalse(1) indicates
          that this port should be treated as having a shared media
          connection.  A value of auto(2) indicates that this port is
          considered to have a point-to-point link if it is an Aggregator
          and all of its members are aggregatable, or if the MAC entity
          is configured for full duplex operation, either through
          auto-negotiation or by management means."
      ::= { pmMIMstCistPortEntry 7 }

pmMIMstCistPortOperP2P OBJECT-TYPE
      SYNTAX      TruthValue               
      MAX-ACCESS  read-only            
      STATUS      current
      DESCRIPTION
          "The operational point-to-point status of the LAN segment
          attached to this port.  It indicates whether a port is
          considered to have a point-to-point connection or not.
          The value is determined by management or by auto-detection,
          as described in the pmMIMstCistPortAdminP2P object."
      ::= { pmMIMstCistPortEntry 8 }

pmMIMstCistPortAdminEdgeStatus OBJECT-TYPE
      SYNTAX      TruthValue               
      MAX-ACCESS  read-write           
      STATUS      current
      DESCRIPTION
          "The administrative value of the Edge Port parameter.  A
          value of TRUE(1) indicates that this port should be
          assumed as an edge-port and a value of FALSE(2) indicates
          that this port should be assumed as a non-edge-port."
      ::= { pmMIMstCistPortEntry 9 }

pmMIMstCistPortOperEdgeStatus OBJECT-TYPE
      SYNTAX      TruthValue               
      MAX-ACCESS  read-only            
      STATUS      current
      DESCRIPTION
          "The operational value of the Edge Port parameter.  The
          object is initialized to the value of
          pmMIMstCistPortAdminEdgeStatus and is set FALSE on reception 
          of a BPDU."
      ::= { pmMIMstCistPortEntry 10 }

pmMIMstCistPortState OBJECT-TYPE
      SYNTAX      INTEGER {              
                  disabled (1),
                  discarding (2),
                  learning (4),
                  forwarding (5)
                  }
      MAX-ACCESS  read-only            
      STATUS      current
      DESCRIPTION
          "Current state of the Port as defined by the Common    
           spanning tree protocol." 
      ::= { pmMIMstCistPortEntry 12 }

pmMIMstCistForcePortState OBJECT-TYPE
      SYNTAX      INTEGER {
                   disabled(0),
                   enabled(1)
                  }
      MAX-ACCESS  read-write           
      STATUS      current
      DESCRIPTION
          "Current state of the Port which can be changed to either 
           Disabled or Enabled for ALL spanning tree   
           instances. Setting this object will override the port's
           status in any of the MSTI contexts"                                        
      ::= { pmMIMstCistPortEntry 13 }

pmMIMstCistPortForwardTransitions OBJECT-TYPE 
      SYNTAX      Counter32                
      MAX-ACCESS  read-only            
      STATUS      current
      DESCRIPTION
          "Number of times this port has transitioned to the     
           Forwarding State."                                     
      ::= { pmMIMstCistPortEntry 14 }

pmMIMstCistPortRxMstBpduCount OBJECT-TYPE 
      SYNTAX      Counter32                
      MAX-ACCESS  read-only            
      STATUS      current
      DESCRIPTION
          "Number of MST BPDUs received on this port."     
      ::= { pmMIMstCistPortEntry 15 }

pmMIMstCistPortRxRstBpduCount OBJECT-TYPE 
      SYNTAX      Counter32                
      MAX-ACCESS  read-only            
      STATUS      current
      DESCRIPTION
          "Number of RST BPDUs received on this port."     
      ::= { pmMIMstCistPortEntry 16 }

pmMIMstCistPortRxConfigBpduCount OBJECT-TYPE 
      SYNTAX      Counter32                
      MAX-ACCESS  read-only            
      STATUS      current
      DESCRIPTION
          "Number of Configuration BPDUs received on this port."     
      ::= { pmMIMstCistPortEntry 17 }

pmMIMstCistPortRxTcnBpduCount OBJECT-TYPE 
      SYNTAX      Counter32                
      MAX-ACCESS  read-only            
      STATUS      current
      DESCRIPTION
          "Number of TCN BPDUs received on this port."     
      ::= { pmMIMstCistPortEntry 18 }

pmMIMstCistPortTxMstBpduCount OBJECT-TYPE 
      SYNTAX      Counter32                
      MAX-ACCESS  read-only            
      STATUS      current
      DESCRIPTION
          "Number of MST BPDUs Transmitted from this port."     
      ::= { pmMIMstCistPortEntry 19 }

pmMIMstCistPortTxRstBpduCount OBJECT-TYPE 
      SYNTAX      Counter32                
      MAX-ACCESS  read-only            
      STATUS      current
      DESCRIPTION
          "Number of RST BPDUs Transmitted from this port."     
      ::= { pmMIMstCistPortEntry 20 }

pmMIMstCistPortTxConfigBpduCount OBJECT-TYPE 
      SYNTAX      Counter32                
      MAX-ACCESS  read-only            
      STATUS      current
      DESCRIPTION
          "Number of Configuration BPDUs Transmitted from this port."     
      ::= { pmMIMstCistPortEntry 21 }

pmMIMstCistPortTxTcnBpduCount OBJECT-TYPE 
      SYNTAX      Counter32                
      MAX-ACCESS  read-only            
      STATUS      current
      DESCRIPTION
          "Number of TCN BPDUs Transmitted from this port."     
      ::= { pmMIMstCistPortEntry 22 }

pmMIMstCistPortInvalidMstBpduRxCount OBJECT-TYPE 
      SYNTAX      Counter32                
      MAX-ACCESS  read-only            
      STATUS      current
      DESCRIPTION
          "Number of Invalid MST BPDUs Received on this port."     
      ::= { pmMIMstCistPortEntry 23 }

pmMIMstCistProtocolMigrationCount OBJECT-TYPE
   SYNTAX      Counter32 
   MAX-ACCESS  read-only  
   STATUS      current
   DESCRIPTION
        "The number of times this Port has migrated from one STP protocol 
        version to another. The relevant protocols are STP-COMPATIBLE and 
        RSTP/MSTP.
        A Trap is generated on the occurence of this event."
      ::= { pmMIMstCistPortEntry 30 }

pmMIMstCistPortDesignatedCost OBJECT-TYPE
      SYNTAX      Integer32
      MAX-ACCESS  read-only           
      STATUS      current
      DESCRIPTION
           "The path cost of the Designated Port of the
            segment connected to this port."
      ::= { pmMIMstCistPortEntry 31 }

pmMIMstCistPortRegionalRoot OBJECT-TYPE
      SYNTAX      BridgeId                 
      MAX-ACCESS  read-only            
      STATUS      current
      DESCRIPTION
          "The unique Bridge Identifier of the bridge recorded as the  
           CIST Regional Root Identifier in the configuration BPDUs 
           transmitted."      
      ::= { pmMIMstCistPortEntry 32 }

pmMIMstCistPortRegionalPathCost OBJECT-TYPE
      SYNTAX      Integer32
      MAX-ACCESS  read-only           
      STATUS      current
      DESCRIPTION
          "The contribution of this port to the path cost of paths     
           towards the CIST Regional Root which include this port."         
      ::= { pmMIMstCistPortEntry 33 }

pmMIMstCistCurrentPortRole OBJECT-TYPE
      SYNTAX      INTEGER {              
                   disabled(0),
                   alternate(1),
                   backup(2),
                   root(3),
                   designated(4)
                  }
      MAX-ACCESS  read-only        
      STATUS      current
      DESCRIPTION
          "Current Port Role of the port for this spanning 
          tree instance."                                      
      ::= { pmMIMstCistPortEntry 35 }

pmMIMstCistPortHelloTime OBJECT-TYPE
   SYNTAX      Timeout (100|200)  
   UNITS       "centi-seconds"
   MAX-ACCESS  read-write  
   STATUS      current
   DESCRIPTION
      "The amount of time between the transmission of
       Configuration bridge PDUs by this node on this port
       in units of hundredths of a second."
      ::= { pmMIMstCistPortEntry 40 }

pmMIMstCistPortAutoEdgeStatus OBJECT-TYPE
      SYNTAX      TruthValue               
      MAX-ACCESS  read-write           
      STATUS      current
      DESCRIPTION
          "This parameter when TRUE(1) indicates that detection 
          of a port as Edge Port happens automatically
          and FALSE(2) indicates that this feature is disabled."
      ::= { pmMIMstCistPortEntry 43 }

pmMIMstCistPortRestrictedRole OBJECT-TYPE 
    SYNTAX      TruthValue 
    MAX-ACCESS  read-write 
    STATUS      current 
    DESCRIPTION 
        "A Boolean value set by management. If TRUE causes the Port not 
        to be selected as Root Port for the CIST or any MSTI, even it has 
        the best spanning tree priority vector. Such a Port will be selected 
        as an Alternate Port after the Root Port has been selected. This 
        parameter should be FALSE by default. If set it can cause lack of 
        spanning tree connectivity. It is set by a network administrator to 
        prevent bridges external to a core region of the network influencing 
        the spanning tree active topology, possibly because those bridges are 
        not under the full control of the administrator. 
       
        This administrator configuration is also known as 'Root Guard'." 

        ::= {pmMIMstCistPortEntry 44} 

pmMIMstCistPortRestrictedTCN OBJECT-TYPE 
    SYNTAX      TruthValue 
    MAX-ACCESS  read-write 
    STATUS      current 
    DESCRIPTION 
        "A Boolean value set by management. If TRUE causes the Port not 
        to propagate received topology change notifications and topology 
        changes to other Ports. This parameter should be FALSE by default. 
        If set it can cause temporarilyorary loss of connectivity after changes in 
        a spanning trees active topology as a result of persistent 
        incorrectly learnt station location information. It is set by a 
        network administrator to prevent bridges external to a core region of 
        the network causing address flushing in that region, possibly because 
        those bridges are not under the full control of the administrator or 
        MAC_Operational for the attached LANs transitions frequently." 

        ::= {pmMIMstCistPortEntry 45} 

pmMIMstCistPortEnableBPDURx OBJECT-TYPE
    SYNTAX      TruthValue
    MAX-ACCESS  read-write
    STATUS      current
    DESCRIPTION
        "A Boolean value set by management. If FALSE, the BPDUs received on
        the port are ignored."
    REFERENCE   "IEEE802.1ah - 13.25.18"
    DEFVAL { true }
        ::= { pmMIMstCistPortEntry 47 }

pmMIMstCistPortEnableBPDUTx OBJECT-TYPE
    SYNTAX      TruthValue
    MAX-ACCESS  read-write
    STATUS      current
    DESCRIPTION
        "A Boolean value set by management. If FALSE, no BPDUs are transmitted
        by this port. This variable should be FALSE before configuring port
        as a Layer Two Gateway Port."
    REFERENCE   "IEEE802.1ah - 13.25.19"
    DEFVAL { true }
        ::= { pmMIMstCistPortEntry 48 }

pmMIMstCistPortPseudoRootId OBJECT-TYPE
    SYNTAX      BridgeId
    MAX-ACCESS  read-write
    STATUS      current
    DESCRIPTION
        "In MSTP Bridge, the pseudoRootId parameter value. By default, it
        is set to the BridgeIdentifier. The pseudoRootId is used by
        Layer Two Gateway Port as the RootId in generated BPDUs."
    REFERENCE   "IEEE802.1ah - 13.25.20"
        ::= { pmMIMstCistPortEntry 49 }

pmMIMstCistPortIsL2Gp OBJECT-TYPE
    SYNTAX      TruthValue
    MAX-ACCESS  read-write
    STATUS      current
    DESCRIPTION
        "A Boolean value set by management. If TRUE, then port is functioning
        as a Layer Two Gateway Port. The pmMIMstCistPortEnableBPDUTx should be
        FALSE to set pmMIMstCistPortIsL2Gp to TRUE."
    REFERENCE   "IEEE802.1ah - 13.25.21"
    DEFVAL { false }
        ::= { pmMIMstCistPortEntry 50 }
                                                                                                
pmMIMstCistPortLoopGuard OBJECT-TYPE
    SYNTAX     TruthValue
    MAX-ACCESS read-write
    STATUS     current
    DESCRIPTION
        "A Boolean value set by management. If TRUE, then it will not age out
        the information even if the peer does not send information. If the port
        continues to receive information through BPDUs the operation
        on this port will be normal. This will be useful when the neighbor
        bridge is faulty, i.e. it cannot send BPDUs but continues to send data
        traffic."

    DEFVAL { false }
        ::= { pmMIMstCistPortEntry 51 }

pmMIMstCistLoopInconsistentState   OBJECT-TYPE 
    SYNTAX      TruthValue 
    MAX-ACCESS  read-only 
    STATUS      current 
    DESCRIPTION 
        " A Boolean value set when the non-designated port on expiry of received information while timer 
        transitions to Designated/Discarding state when the superior BPDU's are not received  with the 
        loop guard feature being enabled on that port. 
        A value of TRUE, indicates that the state of this port is moved into an loop-inconsistent 
        state.A value of  FALSE, indicates that this port is not moved into an loop-inconsistent 
        state " 
    DEFVAL { false } 
    ::= { pmMIMstCistPortEntry 56 } 

-- -----------------------------------------------------------------
-- Pm Mst Multiple Spanning Tree Instance Port Table     
-- -----------------------------------------------------------------
pmMIMstMstiPortTable OBJECT-TYPE
    SYNTAX      SEQUENCE OF PmMIMstMstiPortEntry              
    MAX-ACCESS  not-accessible
    STATUS      current
    DESCRIPTION
          "This table contains Spanning Tree Instance Specific Port
           Information."
     ::= { pmMIDot1sPmMst 7 }

pmMIMstMstiPortEntry OBJECT-TYPE
      SYNTAX      PmMIMstMstiPortEntry               
      MAX-ACCESS  not-accessible
      STATUS      current
      DESCRIPTION
          "A list of information maintained by every port for each 
           and every spanning tree instance."
      INDEX  { pmMIMstMstiPort, pmMIMstInstanceIndex }
      ::= { pmMIMstMstiPortTable 1 }

PmMIMstMstiPortEntry ::= 
   SEQUENCE {
       pmMIMstMstiPort  
            Integer32,
       pmMIMstMstiPortPathCost 
            Integer32,
       pmMIMstMstiPortPriority 
            Integer32,
       pmMIMstMstiPortDesignatedRoot 
            BridgeId,
       pmMIMstMstiPortDesignatedBridge 
            BridgeId,
       pmMIMstMstiPortDesignatedPort 
            OCTET STRING,
       pmMIMstMstiPortState 
            INTEGER,
       pmMIMstMstiForcePortState 
            INTEGER,
       pmMIMstMstiPortForwardTransitions 
            Counter32,
       pmMIMstMstiPortReceivedBPDUs 
            Counter32,
       pmMIMstMstiPortTransmittedBPDUs 
            Counter32,
       pmMIMstMstiPortInvalidBPDUsRcvd 
            Counter32,
       pmMIMstMstiPortDesignatedCost 
            Integer32,
       pmMIMstMstiCurrentPortRole  
            INTEGER,
       pmMIMstMstiPortPseudoRootId
            BridgeId
}

pmMIMstMstiPort OBJECT-TYPE
      SYNTAX      Integer32 (1..65535)
      MAX-ACCESS  not-accessible
      STATUS      current
      DESCRIPTION
          "The Port number of the port for which this entry contains   
           spanning tree information."                                      
      ::= { pmMIMstMstiPortEntry 1 }

pmMIMstMstiPortPathCost OBJECT-TYPE
      SYNTAX      Integer32 (1..200000000)
      MAX-ACCESS  read-write           
      STATUS      current
      DESCRIPTION
          "The contribution of this port to the path cost of
           paths towards the MSTI Root which include this port."
      ::= { pmMIMstMstiPortEntry 2 }

pmMIMstMstiPortPriority OBJECT-TYPE
      SYNTAX      Integer32 (0..240)
      MAX-ACCESS  read-write           
      STATUS      current
      DESCRIPTION
          "The four most significant bits of the Port Identifier 
          for a given Spanning Tree instance can be modified 
          independently for each Spanning Tree instance 
          supported by the Bridge. The values that are set for Port 
          Priority must be in steps of 16."
    DEFVAL {128}
      ::= { pmMIMstMstiPortEntry 3 }

pmMIMstMstiPortDesignatedRoot OBJECT-TYPE
      SYNTAX      BridgeId                 
      MAX-ACCESS  read-only            
      STATUS      current
      DESCRIPTION
          "The unique Bridge Identifier of the bridge recorded as the  
           MSTI Regional Root in the configuration BPDUs transmitted."      
      ::= { pmMIMstMstiPortEntry 4 }

pmMIMstMstiPortDesignatedBridge OBJECT-TYPE
      SYNTAX      BridgeId                 
      MAX-ACCESS  read-only            
      STATUS      current
      DESCRIPTION
          "The unique Bridge Identifier of the bridge which this port  
           considers to be the Designated Bridge for the port's segment."   
      ::= { pmMIMstMstiPortEntry 5 }

pmMIMstMstiPortDesignatedPort OBJECT-TYPE
      SYNTAX  OCTET STRING (SIZE (2))
      MAX-ACCESS  read-only            
      STATUS      current
      DESCRIPTION
          "The Port identifier of the port on the Designated Bridge    
           for this port's segment."                                           
      ::= { pmMIMstMstiPortEntry 6 }

pmMIMstMstiPortState OBJECT-TYPE
      SYNTAX      INTEGER {
                  disabled (1),
                  discarding (2),
                  learning (4),
                  forwarding (5)
                  }
      MAX-ACCESS  read-only            
      STATUS      current
      DESCRIPTION
          "Current state of the Port as defined by the Multiple  
           spanning tree protocol. Port which is Forwarding state
           in one instance can be in Discarding (Blocking) state 
           in another instance."
      ::= { pmMIMstMstiPortEntry 7 }

pmMIMstMstiForcePortState OBJECT-TYPE
      SYNTAX      INTEGER {
                   disabled(0),
                   enabled(1)
                  }
      MAX-ACCESS  read-write           
      STATUS      current
      DESCRIPTION
          "Current state of the Port which can be changed to either 
           Disabled or Enabled for the specific spanning tree   
           instance. This object can be set to enabled only if the 
           'pmMIMstCistForcePortState' is set to 'enabled' for this port"                                            
      ::= { pmMIMstMstiPortEntry 8 }

pmMIMstMstiPortForwardTransitions OBJECT-TYPE 
      SYNTAX      Counter32                
      MAX-ACCESS  read-only            
      STATUS      current
      DESCRIPTION
          "Number of times this port has transitioned to the     
           Forwarding State for specific instance."                                     
      ::= { pmMIMstMstiPortEntry 9 }

pmMIMstMstiPortReceivedBPDUs OBJECT-TYPE 
      SYNTAX      Counter32                
      MAX-ACCESS  read-only            
      STATUS      current
      DESCRIPTION
          "Number of BPDUs received by this port for this 
          spanning tree instance."                            
      ::= { pmMIMstMstiPortEntry 10 }

pmMIMstMstiPortTransmittedBPDUs OBJECT-TYPE 
      SYNTAX      Counter32                
      MAX-ACCESS  read-only            
      STATUS      current
      DESCRIPTION
          "Number of BPDUs transmitted on this port for 
          this spanning tree instance."                            
      ::= { pmMIMstMstiPortEntry 11 }

pmMIMstMstiPortInvalidBPDUsRcvd OBJECT-TYPE 
      SYNTAX      Counter32                
      MAX-ACCESS  read-only            
      STATUS      current
      DESCRIPTION
          "Number of Invalid BPDUs received on this Port
           for this spanning tree instance."                            
      ::= { pmMIMstMstiPortEntry 12 }

pmMIMstMstiPortDesignatedCost OBJECT-TYPE
      SYNTAX      Integer32
      MAX-ACCESS  read-only           
      STATUS      current
      DESCRIPTION
            "The path cost of the Designated Port of the
             segment connected to this port."
      ::= { pmMIMstMstiPortEntry 13 }

pmMIMstMstiCurrentPortRole OBJECT-TYPE
      SYNTAX      INTEGER {              
                   disabled(0),
                   alternate(1),
                   backup(2),
                   root(3),
                   designated(4),
                   master(5)
                  }
      MAX-ACCESS  read-only        
      STATUS      current
      DESCRIPTION
          "Current Port Role of the port for this spanning 
          tree instance."                                      
      ::= { pmMIMstMstiPortEntry 15 }

pmMIMstMstiPortPseudoRootId OBJECT-TYPE
    SYNTAX      BridgeId
    MAX-ACCESS  read-write
    STATUS      current
    DESCRIPTION
        "In MSTP Bridge, the pseudoRootId parameter value. By default, it
        is set to the BridgeIdentifier. The pseudoRootId is used by
        Layer Two Gateway Port as the RootId in generated BPDUs."
    REFERENCE   "IEEE802.1ah - 13.25.20"
      ::= { pmMIMstMstiPortEntry 22 }

--LBD Group ------------------------------------------------------    
    pmLBDStateEnable OBJECT-TYPE 
           SYNTAX      INTEGER {
                          enabled(1),
                          disabled(2)
                       }
           MAX-ACCESS  read-write 
           STATUS      current 
           DESCRIPTION 
               "Enable/Disable Loopback detection function.
                The Loopback Detection function is used to detect the loop created
                by a specific port while Spanning Tree Protocol (STP) is not 
                enabled in the network, especially when the down links are hubs 
                or unmanaged switchs.The Switch will automatically shutdown the 
                port and sends a log to the administrator."
        
           DEFVAL  { disabled }
           ::= { privateLBD 1 }
        
    pmLBDInterval  OBJECT-TYPE
           SYNTAX      Integer32 (1..32767)
           MAX-ACCESS  read-write
           STATUS      current
           DESCRIPTION
            "Set a Loop detection Interval between 1 and 32767 seconds.
             The default is 2 seconds.
             This time interval to be used at counting time seconds to
            resend the CTP packet automatically."  
           DEFVAL  { 2 }
           ::= { privateLBD 2 }
           
    pmLBDRecoverTime  OBJECT-TYPE
           SYNTAX      Integer32 (0 | 60..1000000)
           MAX-ACCESS  read-write
           STATUS      current
           DESCRIPTION
            "This time interval to be used at counting time seconds to
            recover the disabled port automatically. 
            The Loop Detection Recover Time can be set at 0 seconds, 
            or 60 to 1000000 seconds.
            Entering 0 will disable the Loop Detection Recover Time.
            The default is 60 seconds."  
           DEFVAL  { 60 }
           ::= { privateLBD 3 }       
        
        -- LBD Port Control Table
        
        pmLBDCtrlTable OBJECT-TYPE 
           SYNTAX      SEQUENCE OF PmLBDCtrlEntry 
           MAX-ACCESS  not-accessible 
           STATUS      current 
           DESCRIPTION 
              "A table to control Loopback detection features either for 
              the entire switch or for each interface in the switch."
           ::= { privateLBD 4 }
        
        pmLBDCtrlEntry OBJECT-TYPE 
           SYNTAX      PmLBDCtrlEntry 
           MAX-ACCESS  not-accessible 
           STATUS      current 
           DESCRIPTION 
               "An entry appears in this table for each interface 
                in the system."
           INDEX { pmLBDCtrlIndex }
           ::= { pmLBDCtrlTable 1 }
           
        PmLBDCtrlEntry ::= 
           SEQUENCE { 
              pmLBDCtrlIndex
                 Integer32, 
              pmLBDPortStatus 
                 INTEGER, 
              pmLBDPortLoopStatus 
                 INTEGER 
          }
        
        pmLBDCtrlIndex OBJECT-TYPE 
           SYNTAX      Integer32 
           MAX-ACCESS  read-only 
           STATUS      current 
           DESCRIPTION 
              "The interface index of the port for which the configuration
              in this entry applies."
           ::= { pmLBDCtrlEntry 1 }
            
        pmLBDPortStatus OBJECT-TYPE 
           SYNTAX      INTEGER {
                       enabled(1),
                       disabled(2)
                       }
           MAX-ACCESS  read-write 
           STATUS      current 
           DESCRIPTION 
               "Provides control to per port enable or disable the loopback detection 
                function. Default is disabled."
           DEFVAL  { disabled }
           ::= { pmLBDCtrlEntry 2 }
        
        pmLBDPortLoopStatus OBJECT-TYPE 
           SYNTAX      INTEGER {
                       normal(1),
                       disabled(2)
                      }
           MAX-ACCESS  read-only 
           STATUS      current 
           DESCRIPTION 
               "The loop status for this port."
           ::= { pmLBDCtrlEntry 3 }
-- ------------------------------------------------------------  
-- groups in the MIB  
-- ------------------------------------------------------------ 

      pmSnoopInst          OBJECT IDENTIFIER ::= { privateSnoop 2 } 
      pmSnoopVlan          OBJECT IDENTIFIER ::= { privateSnoop 3 } 
      pmSnoopStats         OBJECT IDENTIFIER ::= { privateSnoop 4 } 
      pmSnoopPort          OBJECT IDENTIFIER ::= { privateSnoop 5 }

-- ------------------------------------------------------------------ 
-- The SNOOP Instance Group 
-- ------------------------------------------------------------------ 

-- Instance Based Global Configuration Table 
 
      pmSnoopInstanceGlobalTable OBJECT-TYPE 
          SYNTAX      SEQUENCE OF PmSnoopInstanceGlobalEntry 
          MAX-ACCESS  not-accessible 
          STATUS      current 
          DESCRIPTION 
            "This table contains multicast forwarding mode configuration
             for each instance running in the snooping switch" 
          ::= { pmSnoopInst 1 } 
 
      pmSnoopInstanceGlobalEntry OBJECT-TYPE 
          SYNTAX      PmSnoopInstanceGlobalEntry 
          MAX-ACCESS  not-accessible 
          STATUS      current 
          DESCRIPTION 
            "This table contains instance number and the multicast
             forwarding mode configuration for the particular instance"
             INDEX { pmSnoopInstanceGlobalInstId } 
          ::= { pmSnoopInstanceGlobalTable 1 } 
 
      PmSnoopInstanceGlobalEntry ::= SEQUENCE { 
          pmSnoopInstanceGlobalInstId               Integer32,
          pmSnoopInstanceGlobalMcastFwdMode         INTEGER,
          pmSnoopInstanceGlobalSystemControl        INTEGER,
          pmSnoopInstanceGlobalLeaveConfigLevel     INTEGER,
          pmSnoopInstanceGlobalEnhancedMode         INTEGER,
          pmSnoopInstanceGlobalReportProcessConfigLevel    INTEGER,
          pmSnoopInstanceGlobalSparseMode           INTEGER
        } 
 
      pmSnoopInstanceGlobalInstId OBJECT-TYPE 
           SYNTAX      Integer32 (0..255) 
           MAX-ACCESS  not-accessible 
           STATUS      current 
           DESCRIPTION 
              "Instance ID pertaining to the global configuration entry." 
           ::= { pmSnoopInstanceGlobalEntry 1 } 
      
      pmSnoopInstanceGlobalMcastFwdMode OBJECT-TYPE 
          SYNTAX      INTEGER  { ipbased(1), macbased(2) } 
          MAX-ACCESS  read-write 
          STATUS      current 
          DESCRIPTION 
             "Indicates the mode to be used for building the forwarding 
              table i.e, whether IP based or MAC address based.
              The hardware should support programming of S,G and *,G 
              entries for IGS/MLDS to operate in 'ipbased' mode. 
              If the hardware supports only MAC based multicast tables 
              then 'macbased' mode should be chosen."
           DEFVAL  { 2 } 
          ::= { pmSnoopInstanceGlobalEntry 2 } 

      pmSnoopInstanceGlobalLeaveConfigLevel OBJECT-TYPE 
          SYNTAX      INTEGER  { vlanbased(1), portbased(2) } 
          MAX-ACCESS  read-write 
          STATUS      current 
          DESCRIPTION 
              "A global configuration to specify if the leave processing
               mechanism needs to be configured at the vlan level or at 
               the port level. 
               When this object is set to vlanbased, the mib object
               pmSnoopVlanFastLeave must be used to configure the leave
               mechanism. 
               When this object is set to portbased, the mib object
               pmSnoopPortLeaveMode must be used to configure the leave
               mechanism." 
          DEFVAL  { 1 } 
          ::= { pmSnoopInstanceGlobalEntry 4 } 

     pmSnoopInstanceGlobalEnhancedMode OBJECT-TYPE 
         SYNTAX      INTEGER { enable (1), disable (2) }
         MAX-ACCESS  read-create
         STATUS      current 
         DESCRIPTION 
              "This object is used to enable or disable the snooping module 
               functioning in the enhanced mode.
               
               By default, the snooping module operates in the normal or 
               default mode. In the default mode, the module multicasts from 
               an Outer VLAN (SVLAN) to a set of ports. The Inner VLAN (CVLAN) 
               will typically have a value of zero. In this mode, an S-tagged 
               multicast data or query packet from one port can result in 
               multiple packets on separate egress ports, but only one packet 
               on any one egress port with an S-tag or with no tag.
               
               Enabling this object causes the snooping module to operate in 
               the enhanced mode. The module multicasts from an Outer VLAN 
               (SVLAN) to a set of ports & Inner VLANs (CVLAN). In this mode, 
               an S-tagged multicast data or query packet from one port can 
               result in multiple copies of the packet on the same egress port, 
               each with a different C-tag. The Inner VLAN (CVLAN) will 
               typically have a valid value within the designated range. 
               However under certain scenarios, the Inner VLAN may also have a 
               value of zero.
               
               Disabling this object causes the snooping module to operate in 
               the default mode."
    DEFVAL { disable }
    ::= { pmSnoopInstanceGlobalEntry 5}

     pmSnoopInstanceGlobalReportProcessConfigLevel OBJECT-TYPE 
         SYNTAX      INTEGER  { nonrouterports(1), allports(2) } 
         MAX-ACCESS  read-write 
         STATUS      current 
         DESCRIPTION 
              "A global configuration to specify if the report processing
               mechanism needs to be configured for the non-router ports or
               at the all ports level.
               When this object is set to non-router ports, the incoming
               report messages are process only on the non-router ports.
               When this object is set to all-ports, the incoming
               report messages are processed in all ports which includes
               router ports also.
               By default report messages were not processed on the router
               ports(i.e) report process config level is non-router-ports." 
          DEFVAL  { 1 } 
          ::= { pmSnoopInstanceGlobalEntry 6 } 
 
     pmSnoopInstanceGlobalSparseMode OBJECT-TYPE 
         SYNTAX      INTEGER { enable (1), disable (2) }
         MAX-ACCESS  read-create
         STATUS      current 
         DESCRIPTION 
              "This object is used to enable or disable the snooping module 
               functioning in the sparse mode.
               
               By default, the snooping module operates in the non-sparse
               mode. In the non-sparse mode, the module will be used to 
               forward the unknown multicast traffic when IGS is enabled 
               in the switch. In the sparse mode (i.e Sparse mode is enabled), 
               the module will be used to drop the unknown multicast traffic 
               when IGS is enabled in the switch.  
               
               Disabling this object causes the snooping module to operate in 
               the default mode."
    DEFVAL { disable }
    ::= { pmSnoopInstanceGlobalEntry 7 }
 
      pmSnoopInstanceConfigTable OBJECT-TYPE 
          SYNTAX      SEQUENCE OF PmSnoopInstanceConfigEntry 
          MAX-ACCESS  not-accessible 
          STATUS      current 
          DESCRIPTION 
            "This table contains global configuration of snooping for each 
             instance running in switch" 
          ::= { pmSnoopInst 2 } 
 
      pmSnoopInstanceConfigEntry OBJECT-TYPE 
          SYNTAX      PmSnoopInstanceConfigEntry 
          MAX-ACCESS  not-accessible 
          STATUS      current 
          DESCRIPTION 
            "This table contains instance number, address type and the list of 
             global configuration for the particular instance and address type"
             INDEX { pmSnoopInstanceConfigInstId,
                     pmSnoopInetAddressType } 
          ::= { pmSnoopInstanceConfigTable 1 } 
 
      PmSnoopInstanceConfigEntry ::= SEQUENCE { 
          pmSnoopInstanceConfigInstId        Integer32,
          pmSnoopInetAddressType             InetAddressType,
          pmSnoopStatus                      INTEGER,
          pmSnoopProxyReportingStatus        INTEGER,
          pmSnoopRouterPortPurgeInterval     Integer32,
          pmSnoopPortPurgeInterval           Integer32,
          pmSnoopReportForwardInterval       Integer32,
          pmSnoopRetryCount                  Integer32,
          pmSnoopGrpQueryInterval            Integer32,
          pmSnoopReportFwdOnAllPorts         INTEGER,
          pmSnoopTraceOption                 Integer32,
          pmSnoopOperStatus                  INTEGER,
          pmSnoopSendQueryOnTopoChange       INTEGER,
          pmSnoopSendLeaveOnTopoChange       INTEGER,
          pmSnoopFilterStatus                INTEGER,
          pmSnoopMulticastVlanStatus         INTEGER,
          pmSnoopProxyStatus                 INTEGER,
          pmSnoopQueryFwdOnAllPorts          INTEGER
        } 
 
      pmSnoopInstanceConfigInstId OBJECT-TYPE 
           SYNTAX      Integer32 (0..255) 
           MAX-ACCESS  not-accessible 
           STATUS      current 
           DESCRIPTION 
              "Instance ID pertaining to the global configuration entry."
           ::= { pmSnoopInstanceConfigEntry 1 } 
 
      pmSnoopInetAddressType OBJECT-TYPE 
           SYNTAX      InetAddressType 
           MAX-ACCESS  not-accessible 
           STATUS      current 
           DESCRIPTION 
              "Inet Address Type corresponding to  the global configuration entry. 
               This indicates whether the row is for IGMP/MLD Snooping"
           ::= { pmSnoopInstanceConfigEntry 2 } 
 
      pmSnoopStatus OBJECT-TYPE 
          SYNTAX      INTEGER  { enabled(1), disabled(2) } 
          MAX-ACCESS  read-write 
          STATUS      current 
          DESCRIPTION 
             "Enables or disables IGMP/MLD snooping in the system.
              When set to 'enabled', the IGS/MLDS module starts 
              protocol operations.
              When set to 'disabled', the IGS/MLDS module stops performing 
              protocol operations."
          DEFVAL  { 2 } 
          ::= { pmSnoopInstanceConfigEntry 3 } 
 
      pmSnoopProxyReportingStatus OBJECT-TYPE 
          SYNTAX      INTEGER  { enabled(1), disabled(2) } 
          MAX-ACCESS  read-write 
          STATUS      current 
          DESCRIPTION 
             "Enables or disables proxy-reporting in the system.
              When proxy-reporting is 'enabled' the switch generates 
              reports and forwards them to the router based on the 
              available host information.
              When proxy-reporting is 'disabled' the switch forwards 
              all SSM (IGMPv3/MLDv2) and a single ASM (IGMPv2/MLDv1) 
              report to the router.
              Proxy-reporting can be enabled only if Proxy is disabled. "      
           DEFVAL  { 1 } 
          ::= { pmSnoopInstanceConfigEntry 4 } 

      pmSnoopRouterPortPurgeInterval OBJECT-TYPE 
          SYNTAX      Integer32 (60..600) 
          MAX-ACCESS  read-write 
          STATUS      deprecated 
          DESCRIPTION 
             "This is the interval (in seconds) after which a learnt  
              router port entry will be purged. For each router port learnt, 
              this timer runs for 'RouterPortPurgeInterval' seconds.When the 
              timer expires, the learnt router port entry is purged. However 
              if control messages are received from the router before the 
              timer expiry, then the timer is restarted.
              This object is deprecated and corresponding functionality is met
              using the objects in pmSnoopRtrPortTable. If configured,
              this value overrides the value used in pmSnoopRtrPortTable."
          DEFVAL  { 125 } 
          ::= { pmSnoopInstanceConfigEntry 5 } 
 
      pmSnoopPortPurgeInterval OBJECT-TYPE 
          SYNTAX      Integer32 (130..1225) 
          MAX-ACCESS  read-write 
          STATUS      deprecated 
          DESCRIPTION 
             "This is the interval (in seconds) after which a learnt  
              port entry will be purged. For each port on which report
              has been received, this timer runs for 'PortPurgeInterval'
              seconds. This timer will be restarted whenever a report 
              message is received from a host on the specific port. If 
              the timer expires, then , the learnt port entry  will 
              be purged from the multicast group.
              This object is deprecated and corresponding functionality is met
              using a read only object in pmSnoopVlanFilterTable. If configured,
              this value overrides the value used in pmSnoopVlanFilterTable."
          DEFVAL  {260} 
          ::= { pmSnoopInstanceConfigEntry 6 } 
 
      pmSnoopReportForwardInterval OBJECT-TYPE 
          SYNTAX      Integer32 (1..25) 
          MAX-ACCESS  read-write 
          STATUS      current 
          DESCRIPTION 
             "This timer is used when both proxy and proxy-reporting is 
              disabled. The switch then has to suppress multiple 
              IGMPv2/ MLDv1 report messages for the same group from being 
              forwarded to the router.
              This is the interval (in seconds) within which report  
              messages for the same multicast group will not be forwarded. 
              The 'ReportForwardTimer' is per multicast group. This timer is 
              started as soon as a report message for that group is forwarded 
              out. Within this 'ReportForwardInterval' if another report for 
              the same group arrives, that report will not be forwarded." 
          DEFVAL  { 5 } 
          ::= { pmSnoopInstanceConfigEntry 7 } 
           
      pmSnoopRetryCount OBJECT-TYPE
          SYNTAX      Integer32 (1..5)
          MAX-ACCESS  read-write
          STATUS      current
          DESCRIPTION 
             "In proxy/proxy-reporting mode, when the switch receives leave 
              message on a port, it sends group specific query to check if 
              there are any other interested v2 receivers for the group. 
              This attribute defines the maximum number of queries sent by 
              the switch before deleting the port from the group membership 
              information in the forwarding database. If the maximum retry 
              count exceeds 'pmSnoopRetryCount', then the port will be deleted
              from the multicast group membership information in the 
              forwarding database and received leave message
              will be forwarded onto the router ports if there are no 
              interested receivers for the group." 
          DEFVAL  { 2 } 
          ::= { pmSnoopInstanceConfigEntry 8 } 

      pmSnoopGrpQueryInterval OBJECT-TYPE 
          SYNTAX      Integer32 (2..5) 
          MAX-ACCESS  read-write 
          STATUS      current 
          DESCRIPTION 
             "The value of this attribute defines the time period with which 
              the switch will send group specific queries on a port to check 
              if there are any intersted receivers. The switch will send 
              'pmSnoopRetryCount' queries before removing the port from the 
              group membership information in the forwarding database."
          DEFVAL  { 2 }
          ::= { pmSnoopInstanceConfigEntry 9 } 
 
      pmSnoopReportFwdOnAllPorts OBJECT-TYPE 
          SYNTAX      INTEGER  { allports(1), rtrports(2), nonedgeports(3) } 
          MAX-ACCESS  read-write 
          STATUS      current 
          DESCRIPTION 
              "In snooping mode, Snooping module will forward reports only 
               on router ports by default. This object provides administrative
               control either to forward the reports on all the member ports of the 
               VLAN or to forward the report on SpanningTree non edge ports.
               This configuration will not be valid in proxy or proxy-reporting
               mode"
          DEFVAL  { 2 } 
          ::= { pmSnoopInstanceConfigEntry 10 } 

      pmSnoopOperStatus OBJECT-TYPE 
          SYNTAX      INTEGER  { enabled(1), disabled(2) } 
          MAX-ACCESS  read-only 
          STATUS      current 
          DESCRIPTION 
             "The operational status of the IGS/MLDS protocol.
              The value enabled(1) indicates the IGS/MLDS module is currently
              enabled in the system.
              The value disable(1) indicates the IGS/MLDS module is currently
              disabled in the system."
          ::= { pmSnoopInstanceConfigEntry 12 } 

       pmSnoopSendQueryOnTopoChange OBJECT-TYPE
          SYNTAX      INTEGER  { enabled(1), disabled(2) }
          MAX-ACCESS  read-write
          STATUS      current
          DESCRIPTION
             "The Snooping Switch can be configured to send IGMP/MLD General
              queries on all non router ports when spanning tree topology 
              change occurs in a network. If the spanning tree mode is RSTP, 
              IGMP/MLD general queries will be sent on all the non router ports 
              present in the switch.If the spanning tree mode is MSTP, IGMP/MLD 
              general queries will be sent on all the non router ports of the 
              VLAN mapped for the MSTP instance.When this object is set to 
              'enabled' ,the switch will generate general query messages. This 
              object cannot be enabled if pmSnoopSendLeaveOnTopoChange is 
              enabled. "
          DEFVAL  { 2 }
          ::= { pmSnoopInstanceConfigEntry 13 }

      pmSnoopFilterStatus OBJECT-TYPE
          SYNTAX      INTEGER  { enabled(1), disabled(2) }
          MAX-ACCESS  read-write
          STATUS      current
          DESCRIPTION
          "This object is used to enable/disable the IGS filtering feature. 
           Interface mapping configurations will not be affected by this object 
           status.
           When this object is disabled, filters will not be applied in this
           instance but the profile mapping and registration limits can be
           configured."
          DEFVAL  { disabled }
          ::= { pmSnoopInstanceConfigEntry 15 }

      pmSnoopMulticastVlanStatus OBJECT-TYPE
          SYNTAX      INTEGER  { enabled(1), disabled(2) }
          MAX-ACCESS  read-write
          STATUS      current
          DESCRIPTION
          "This object is used to enable/disable the Multicast VLAN feature. 
           When Multicast VLAN feature is enabled, each incoming untagged report 
           or leave message will be classified to an M-VLAN, depending on 
           whether any M-VLAN configuration exists for the particular Group 
           and/or Source address, configured using the 
           pmSnoopVlanMulticastProfileId object. 
           When Multicast VLAN feature is disabled, the usual VLAN 
           classification rules apply."
          DEFVAL  { disabled }
          ::= { pmSnoopInstanceConfigEntry 16 }

      pmSnoopProxyStatus OBJECT-TYPE 
          SYNTAX      INTEGER  { enabled(1), disabled(2) } 
          MAX-ACCESS  read-write 
          STATUS      current 
          DESCRIPTION 
             "This object enables or disables Proxy in the system.
              Proxy can be enabled only if Proxy-reporting is disabled.      
              In proxy mode, the switch act as querier for all 
              downstream interfaces, act as host for all 
              upstream interfaces.
              In proxy mode, switch sends out general query on all 
              downstream interfaces on every query interval and updates 
              membership database based on the reports received. 
              For upstream interfaces, when queried, proxy trasnmits 
              current state consolidated report. For any change in 
              membership databases, state change report is formed and 
              transmitted on upstream interfaces."
           DEFVAL  { 2 } 
          ::= { pmSnoopInstanceConfigEntry 17 } 

      pmSnoopQueryFwdOnAllPorts OBJECT-TYPE 
          SYNTAX      INTEGER  { allports(1), nonrtrports(2) } 
          MAX-ACCESS  read-write 
          STATUS      current 
          DESCRIPTION 
              "In proxy and proxy reporting mode, Snooping module will send
               query messages only to the non-router ports by default.
               This object provides administrative control to forward the 
               query messages on all the member ports of the VLAN."
          DEFVAL  { 2 } 
          ::= { pmSnoopInstanceConfigEntry 18 } 

-- ------------------------------------------------------------------ 
-- The Snoop VLAN Group 
-- ------------------------------------------------------------------ 
 
-- VLAN Based MAC Multicast Forwarding Table 
 
      pmSnoopVlanMcastMacFwdTable OBJECT-TYPE 
          SYNTAX      SEQUENCE OF PmSnoopVlanMcastMacFwdEntry 
          MAX-ACCESS  not-accessible 
          STATUS      current 
          DESCRIPTION 
            "This table contains MAC based multicast forwarding 
             information. This information is applicable only if
             the 'pmSnoopMcastForwardingMode' is set to 'macbased' " 
          ::= { pmSnoopVlan 1 } 
 
      pmSnoopVlanMcastMacFwdEntry OBJECT-TYPE 
          SYNTAX      PmSnoopVlanMcastMacFwdEntry 
          MAX-ACCESS  not-accessible 
          STATUS      current 
          DESCRIPTION 
            "This table contains VLAN ID, multicast group MAC address and the  
             list of ports onto which the multicast data packets for group
             should be forwarded."  

          INDEX { pmSnoopVlanMcastMacFwdInstId, 
                  pmSnoopVlanMcastMacFwdVlanId,
                  pmSnoopVlanMcastMacFwdInetAddressType,  
                  pmSnoopVlanMcastMacFwdGroupAddress } 
          ::= { pmSnoopVlanMcastMacFwdTable 1 } 
 
      PmSnoopVlanMcastMacFwdEntry ::= SEQUENCE { 
          pmSnoopVlanMcastMacFwdInstId           Integer32, 
          pmSnoopVlanMcastMacFwdVlanId           Integer32,
          pmSnoopVlanMcastMacFwdInetAddressType  InetAddressType,  
          pmSnoopVlanMcastMacFwdGroupAddress     MacAddress, 
          pmSnoopVlanMcastMacFwdPortList         PortList,
          pmSnoopVlanMcastMacFwdLocalPortList    PortList,
          pmSnoopVlanMcastMacFwdEntryFlag        Integer32 

        } 

      pmSnoopVlanMcastMacFwdInstId OBJECT-TYPE 
           SYNTAX      Integer32 (0..255) 
           MAX-ACCESS  not-accessible 
           STATUS      current 
           DESCRIPTION 
              "Instance ID pertaining to the Multicast forwarding entry."
           ::= { pmSnoopVlanMcastMacFwdEntry 1 } 

      pmSnoopVlanMcastMacFwdVlanId OBJECT-TYPE 
           SYNTAX      Integer32 (1..4094) 
           MAX-ACCESS  not-accessible 
           STATUS      current 
           DESCRIPTION 
              "VLAN ID pertaining to the Multicast forwarding entry"  
           ::= { pmSnoopVlanMcastMacFwdEntry 2 } 
 
      pmSnoopVlanMcastMacFwdInetAddressType OBJECT-TYPE 
           SYNTAX      InetAddressType 
           MAX-ACCESS  not-accessible 
           STATUS      current 
           DESCRIPTION 
              "InetAddressType pertaining to the Multicast forwarding entry"  
           ::= { pmSnoopVlanMcastMacFwdEntry 3 } 
 
      pmSnoopVlanMcastMacFwdGroupAddress OBJECT-TYPE 
           SYNTAX      MacAddress 
           MAX-ACCESS  not-accessible 
           STATUS      current 
           DESCRIPTION 
               "Multicast group MAC address." 
           ::= { pmSnoopVlanMcastMacFwdEntry 4 } 

     pmSnoopVlanMcastMacFwdLocalPortList OBJECT-TYPE
           SYNTAX      PortList
           MAX-ACCESS  read-only
           STATUS      current
           DESCRIPTION
               "List of ports onto which the multicast data packets destined 
           for this group will be forwarded. Each bit in this object 
           represent interfaces denoted by the object pmVcHlPortId 
           associated to the instance identifier denoted by 
           pmSnoopVlanMcastMacFwdInstId. This object alone should be
           referred in environments where the number of interfaces in the
           system is scaled to a large value, as the object
           pmSnoopVlanMcastMacFwdPortList may not be sufficient to 
           represent the full set of interfaces in each switch instance."

           ::= { pmSnoopVlanMcastMacFwdEntry 6 }


     pmSnoopVlanMcastMacFwdEntryFlag OBJECT-TYPE 
           SYNTAX      Integer32 
           MAX-ACCESS  read-only 
           STATUS      current 
           DESCRIPTION 
             "This flag tell about the entry type: either it is a 
              Static group entry or it is a Dynamic group entry"  
           ::= { pmSnoopVlanMcastMacFwdEntry 7 } 



-- VLAN Based IP Multicast Forwarding Table 
 
      pmSnoopVlanMcastIpFwdTable OBJECT-TYPE 
          SYNTAX      SEQUENCE OF PmSnoopVlanMcastIpFwdEntry 
          MAX-ACCESS  not-accessible 
          STATUS      deprecated
          DESCRIPTION 
            "This table contains IP based multicast forwarding 
             information. This information is applicable only if
             the 'pmSnoopInstMcastForwardingMode' is set to 'ip-based'.
             This table and all its objects are being deprecated. The
             pmSnoopVlanIpFwdTable is to be used instead." 
          ::= { pmSnoopVlan 2 } 
 
      pmSnoopVlanMcastIpFwdEntry OBJECT-TYPE 
          SYNTAX      PmSnoopVlanMcastIpFwdEntry 
          MAX-ACCESS  not-accessible 
          STATUS      deprecated
          DESCRIPTION 
            "This table contains VLAN ID, unicast source address , 
             multicast group address and the list of ports onto which the 
             multicast data packets for group should be forwarded."  

          INDEX { pmSnoopVlanMcastIpFwdInstId, 
                  pmSnoopVlanMcastIpFwdVlanId,
                  pmSnoopVlanMcastIpFwdAddressType,     
                  pmSnoopVlanMcastIpFwdSourceAddress,  
                  pmSnoopVlanMcastIpFwdGroupAddress } 
          ::= { pmSnoopVlanMcastIpFwdTable 1 } 
 
      PmSnoopVlanMcastIpFwdEntry ::= SEQUENCE { 
          pmSnoopVlanMcastIpFwdInstId        Integer32, 
          pmSnoopVlanMcastIpFwdVlanId        Integer32,
          pmSnoopVlanMcastIpFwdAddressType   InetAddressType, 
          pmSnoopVlanMcastIpFwdSourceAddress InetAddress, 
          pmSnoopVlanMcastIpFwdGroupAddress  InetAddress, 
          pmSnoopVlanMcastIpFwdPortList      PortList,
          pmSnoopVlanMcastIpFwdEntryFlag     Integer32 
  
        } 

      pmSnoopVlanMcastIpFwdInstId OBJECT-TYPE 
           SYNTAX      Integer32 (0..255) 
           MAX-ACCESS  not-accessible 
           STATUS      deprecated
           DESCRIPTION 
              "Instance ID pertaining to the Multicast forwarding entry." 
           ::= { pmSnoopVlanMcastIpFwdEntry 1 } 

      pmSnoopVlanMcastIpFwdVlanId OBJECT-TYPE 
           SYNTAX      Integer32 (1..4094) 
           MAX-ACCESS  not-accessible 
           STATUS      deprecated
           DESCRIPTION 
              "VLAN ID pertaining to the Multicast forwarding entry"  
           ::= { pmSnoopVlanMcastIpFwdEntry 2 } 

      pmSnoopVlanMcastIpFwdAddressType OBJECT-TYPE 
           SYNTAX      InetAddressType 
           MAX-ACCESS  not-accessible 
           STATUS      deprecated
           DESCRIPTION 
              "InetAddressType pertaining to the Multicast forwarding entry"  
           ::= { pmSnoopVlanMcastIpFwdEntry 3 } 

       pmSnoopVlanMcastIpFwdSourceAddress OBJECT-TYPE 
           SYNTAX      InetAddress (SIZE (16))
           MAX-ACCESS  not-accessible 
           STATUS      deprecated
           DESCRIPTION 
              "Unicast source address of the data source that sends
               multicast data for this group"
           ::= { pmSnoopVlanMcastIpFwdEntry 4 } 

       pmSnoopVlanMcastIpFwdGroupAddress OBJECT-TYPE 
           SYNTAX      InetAddress (SIZE (16))
           MAX-ACCESS  not-accessible 
           STATUS      deprecated
           DESCRIPTION 
              "IP/IPv6 multicast group address" 
           ::= { pmSnoopVlanMcastIpFwdEntry 5 } 
      
       pmSnoopVlanMcastIpFwdEntryFlag OBJECT-TYPE 
          SYNTAX      Integer32   
          MAX-ACCESS  read-only 
          STATUS      current 
          DESCRIPTION 
              "This flag tell about the entry type: either it is a 
               Static group entry or it is a Dynamic group entry"  
          ::= { pmSnoopVlanMcastIpFwdEntry 7 } 
 

-- VLAN based router table.
 
      pmSnoopVlanRouterTable OBJECT-TYPE 
          SYNTAX      SEQUENCE OF PmSnoopVlanRouterEntry 
          MAX-ACCESS  not-accessible 
          STATUS      current 
          DESCRIPTION 
             "This table contains the list of ports through which 
              a router, in a particular VLAN is reachable." 
          ::= { pmSnoopVlan 3 } 
 
      pmSnoopVlanRouterEntry OBJECT-TYPE 
          SYNTAX      PmSnoopVlanRouterEntry 
          MAX-ACCESS  not-accessible 
          STATUS      current 
          DESCRIPTION 
             "Contains the VLAN ID and list of ports on which 
              routers are present in the VLAN." 
          INDEX { pmSnoopVlanRouterInstId,
                  pmSnoopVlanRouterVlanId,
                  pmSnoopVlanRouterInetAddressType } 
          ::= { pmSnoopVlanRouterTable 1 } 
 
      PmSnoopVlanRouterEntry ::= SEQUENCE { 
          pmSnoopVlanRouterInstId             Integer32,
          pmSnoopVlanRouterVlanId             Integer32,
          pmSnoopVlanRouterInetAddressType    InetAddressType,  
          pmSnoopVlanRouterPortList           PortList,
      pmSnoopVlanRouterLocalPortList      PortList
        }
           
      pmSnoopVlanRouterInstId OBJECT-TYPE 
           SYNTAX      Integer32 (0..255) 
           MAX-ACCESS  not-accessible 
           STATUS      current 
           DESCRIPTION 
              "Instance ID pertaining to the router port entry."
           ::= { pmSnoopVlanRouterEntry 1 } 

      pmSnoopVlanRouterVlanId OBJECT-TYPE 
           SYNTAX      Integer32 (1..4094) 
           MAX-ACCESS  not-accessible 
           STATUS      current 
           DESCRIPTION 
              "VLAN ID of the ports through which router is reachable." 
           ::= { pmSnoopVlanRouterEntry 2 } 
 
      pmSnoopVlanRouterInetAddressType OBJECT-TYPE 
           SYNTAX      InetAddressType 
           MAX-ACCESS  not-accessible 
           STATUS      current 
           DESCRIPTION 
              "It indicates whether the row belongs to IGMP / MLD snooping." 
           ::= { pmSnoopVlanRouterEntry 3 } 

      pmSnoopVlanRouterLocalPortList OBJECT-TYPE
           SYNTAX      PortList
           MAX-ACCESS  read-only
           STATUS      current
           DESCRIPTION
               "List of ports on which routers are present. These router ports 
           are learnt through control messages received from routers, and 
           can also be configured statically. Each bit in this object 
           represent interfaces denoted by the object pmVcHlPortId 
           associated to the instance identifier denoted by 
           pmSnoopVlanRouterInstId. This object alone should be 
           referred in environments where the number of interfaces in the
           system is scaled to a large value, as the object
           pmSnoopVlanRouterPortList may not be sufficient to represent the
           full set of interfaces in each switch instance."

            ::= { pmSnoopVlanRouterEntry 5 }

-- VLAN based filter table 
 
      pmSnoopVlanFilterTable OBJECT-TYPE 
          SYNTAX      SEQUENCE OF PmSnoopVlanFilterEntry 
          MAX-ACCESS  not-accessible 
          STATUS      current 
          DESCRIPTION 
             "This table contains configuration of snooping
              on specific Vlans. This Table is valid only when VLAN is  
              enabled in the system." 
          ::= { pmSnoopVlan 4 } 
 
      pmSnoopVlanFilterEntry OBJECT-TYPE 
          SYNTAX      PmSnoopVlanFilterEntry 
          MAX-ACCESS  not-accessible 
          STATUS      current 
          DESCRIPTION 
             "Contains snooping status , version and fast leave
              configuration for a specific VLAN." 
          INDEX { pmSnoopVlanFilterInstId,
                  pmSnoopVlanFilterVlanId,
                  pmSnoopVlanFilterInetAddressType } 
          ::= { pmSnoopVlanFilterTable 1 } 
 
      PmSnoopVlanFilterEntry ::= SEQUENCE { 
          pmSnoopVlanFilterInstId           Integer32, 
          pmSnoopVlanFilterVlanId           Integer32, 
          pmSnoopVlanFilterInetAddressType  InetAddressType,
          pmSnoopVlanSnoopStatus            INTEGER, 
          pmSnoopVlanOperatingVersion       INTEGER, 
          pmSnoopVlanCfgOperVersion         INTEGER, 
          pmSnoopVlanFastLeave              INTEGER,
          pmSnoopVlanQuerier                INTEGER, 
          pmSnoopVlanCfgQuerier             INTEGER, 
          pmSnoopVlanQueryInterval          Integer32, 
          pmSnoopVlanRtrPortList            PortList, 
          pmSnoopVlanRowStatus              RowStatus,
          pmSnoopVlanStartupQueryCount      Integer32,
          pmSnoopVlanStartupQueryInterval   Integer32,
          pmSnoopVlanOtherQuerierPresentInterval Integer32 
          } 

      pmSnoopVlanFilterInstId OBJECT-TYPE 
           SYNTAX      Integer32 (0..255) 
           MAX-ACCESS  not-accessible 
           STATUS      current 
           DESCRIPTION 
            "Instance ID pertaining to VLAN filter table entry."
           ::= { pmSnoopVlanFilterEntry 1 } 

      pmSnoopVlanFilterVlanId OBJECT-TYPE 
           SYNTAX      Integer32 (1..4094) 
           MAX-ACCESS  not-accessible 
           STATUS      current 
           DESCRIPTION 
            " VLAN ID for which snooping configuration is to be done." 
           ::= { pmSnoopVlanFilterEntry 2 } 
 
      pmSnoopVlanFilterInetAddressType OBJECT-TYPE 
           SYNTAX      InetAddressType 
           MAX-ACCESS  not-accessible 
           STATUS      current 
           DESCRIPTION 
            " Indicates whether the row belongs to IGS/MLD snooping" 
           ::= { pmSnoopVlanFilterEntry 3 } 
 
      pmSnoopVlanSnoopStatus OBJECT-TYPE 
           SYNTAX      INTEGER { enabled(1), disabled(2) } 
           MAX-ACCESS  read-write 
           STATUS      current 
           DESCRIPTION 
               "Enables or disables IGS/MLDS on that specific VLAN"  
           DEFVAL  { 1 }
           ::= { pmSnoopVlanFilterEntry 4 } 

      pmSnoopVlanCfgOperVersion OBJECT-TYPE 
           SYNTAX      INTEGER { v1(1), v2(2), v3(3) } 
           MAX-ACCESS  read-write 
           STATUS      deprecated 
           DESCRIPTION 
               "Indicates the operating version of the IGS/MLDS switch for 
                a specific VLAN. The default operating mode on a specific VLAN 
                is IGMP version 3 i.e, V3(3) or MLD version 2 i.e., V2(2). 
                The 'pmSnoopVlanCfgOperVersion' should be configured on the 
                basis of the router version present in the VLAN.
                This configuration should be used only when one router port 
                is existing in the VLAN. 
                This object is deprecated and corresponding functionality is met
                using pmSnoopRtrPortCfgOperVersion object available in 
                pmSnoopRtrPortTable. If configured, consolidated reports sent 
                on upstream interfaces will use this version." 
           DEFVAL  { 3 }
           ::= { pmSnoopVlanFilterEntry 6 } 

      pmSnoopVlanFastLeave OBJECT-TYPE 
           SYNTAX      INTEGER { enabled(1), disabled(2) } 
           MAX-ACCESS  read-write 
           STATUS      current 
           DESCRIPTION 
               "Enables or disables fast leave for the VLAN. When it is 
                'disabled',on reception of a leave message the switch checks
                if they are any interested receivers for the group by sending 
                a group specific query before removing the port from the 
                forwarding table. If set to 'enabled', the switch does not 
                send a group specific query and immediately removes the port
                from the forwarding table."
           DEFVAL  { 2 }
           ::= { pmSnoopVlanFilterEntry 7 }

      pmSnoopVlanQuerier OBJECT-TYPE 
          SYNTAX      INTEGER  { enabled(1), disabled(2) } 
          MAX-ACCESS  read-only 
          STATUS      current 
          DESCRIPTION 
             "Indicates whether the switch is configured as a querier in the VLAN"
          DEFVAL  { 2 } 
          ::= { pmSnoopVlanFilterEntry 8 } 

      pmSnoopVlanCfgQuerier OBJECT-TYPE 
          SYNTAX      INTEGER  { enabled(1), disabled(2) } 
          MAX-ACCESS  read-write 
          STATUS      current 
          DESCRIPTION 
             "The snooping switch can be configured to send IGMP/MLD queries 
              when IGMP/MLD routers are not present in the VLAN. When set to 
              'enabled' the switch will generate general query messages. 
              The query messages will be suppressed if the switch receives 
              the query message from any other router in the VLAN. Switch 
              should be configured as a querier for a VLAN only when there 
              are no queriers in the network.
              This configuration is valid only in proxy reporting mode."
          DEFVAL  { 2 } 
          ::= { pmSnoopVlanFilterEntry 9 } 

      pmSnoopVlanQueryInterval OBJECT-TYPE 
          SYNTAX      Integer32 (60..600) 
          MAX-ACCESS  read-write 
          STATUS      current 
          DESCRIPTION 
             "This is the interval (in seconds) for which the switch 
              sends general queries in proxy and proxy-reporting mode.
              In proxy-reporting mode, General queries will be sent
              on all downstream interfaces with this interval only if
              the switch is the Querier.   
              In proxy mode, switch will be querier for all downstream 
              interfaces. General queries will be sent on all downstream
              interfaces with this interval."   
          DEFVAL  { 125 } 
          ::= { pmSnoopVlanFilterEntry 10 } 

      pmSnoopVlanRowStatus OBJECT-TYPE 
           SYNTAX      RowStatus 
           MAX-ACCESS  read-write
           STATUS      current 
           DESCRIPTION 
               "The status of a row in the VLAN filter table. Using this 
                object, new entries can be created in the VLAN filter table 
                and the existing entries can be removed from the 
                VLAN filter table"
           ::= { pmSnoopVlanFilterEntry 12 } 

      pmSnoopVlanStartupQueryCount OBJECT-TYPE 
          SYNTAX      Integer32 
          MAX-ACCESS  read-write 
          STATUS      current 
          DESCRIPTION 
             "The Startup Query Count is the number of Queries sent out on 
             startup, separated by the Startup Query Interval. 
             The default value is the Robustness."
          DEFVAL  { 2 } 
          ::= { pmSnoopVlanFilterEntry 13 } 
          
      pmSnoopVlanStartupQueryInterval OBJECT-TYPE 
          SYNTAX      Integer32 (15..150) 
          UNITS       "seconds"
          MAX-ACCESS  read-write 
          STATUS      current 
          DESCRIPTION 
             "Interval between the general query messages sent by the switch 
              during startup of querier election process.
              This value must be <= (Query Interval/4)"
          DEFVAL  { 31 } 
          ::= { pmSnoopVlanFilterEntry 14 } 

-- --------------------------------------------------------------
-- Outer-VLAN, Inner-VLAN Based IP Multicast Forwarding Table 
-- --------------------------------------------------------------
 
      pmSnoopVlanIpFwdTable OBJECT-TYPE 
          SYNTAX      SEQUENCE OF PmSnoopVlanIpFwdEntry 
          MAX-ACCESS  not-accessible 
          STATUS      current 
          DESCRIPTION 
            "This table contains IP multicast forwarding information 
             based on both Outer VLAN and Inner VLAN.                 

             When enhanced mode is enabled this table will be populated 
             with both Outer and Inner VLAN. When operating in the default mode 
             this table will be populated with the Outer VLAN alone and the 
             Inner VLAN will be considered to have a value of zero. When
             the Snoop module receives a packet classified to a single VLAN
             (such as the CVLAN in Customer Bridges, or SVLAN in 802.1ad
             Bridges), then this single VLAN is considered to be the Outer VLAN
             and the Inner VLAN will have a value of zero. 
             
             The information present in this table is applicable only if the 
             object 'pmSnoopInstMcastForwardingMode' is set to 'ip-based'." 
          ::= { pmSnoopVlan 7 } 
 
      pmSnoopVlanIpFwdEntry OBJECT-TYPE 
          SYNTAX      PmSnoopVlanIpFwdEntry 
          MAX-ACCESS  not-accessible 
          STATUS      current 
          DESCRIPTION 
            "This table contains Outer VLAN ID, unicast source address, 
             multicast group address, Inner VLAN ID and the list of ports onto 
             which the multicast data packets for the group should be 
             forwarded."  
          INDEX { pmSnoopVlanIpFwdInstanceId, 
                  pmSnoopVlanIpFwdOuterVlanId,
                  pmSnoopVlanIpFwdInetAddressType,     
                  pmSnoopVlanIpFwdSourceAddress,  
                  pmSnoopVlanIpFwdGroupAddress, 
                  pmSnoopVlanIpFwdInnerVlanId } 
          ::= { pmSnoopVlanIpFwdTable 1 } 
 
      PmSnoopVlanIpFwdEntry ::= SEQUENCE { 
           pmSnoopVlanIpFwdInstanceId      Integer32,
           pmSnoopVlanIpFwdOuterVlanId     VlanIndex,
           pmSnoopVlanIpFwdInetAddressType InetAddressType,
           pmSnoopVlanIpFwdSourceAddress   InetAddress,
           pmSnoopVlanIpFwdGroupAddress    InetAddress,
           pmSnoopVlanIpFwdInnerVlanId     InnerVlanIndex,
       pmSnoopVlanIpFwdLocalPortList   PortList
        } 

      pmSnoopVlanIpFwdInstanceId OBJECT-TYPE
           SYNTAX      Integer32 (0..65535)
           MAX-ACCESS  not-accessible
           STATUS      current
           DESCRIPTION
               "Instance Id pertaining to a particular virtual context."
           ::= { pmSnoopVlanIpFwdEntry 1 }

      pmSnoopVlanIpFwdOuterVlanId OBJECT-TYPE
           SYNTAX      VlanIndex
           MAX-ACCESS  not-accessible
           STATUS      current
           DESCRIPTION
               "The outer vlan id on which the multicast group is learnt."
           ::= { pmSnoopVlanIpFwdEntry 2 }

      pmSnoopVlanIpFwdInetAddressType OBJECT-TYPE 
           SYNTAX      InetAddressType 
           MAX-ACCESS  not-accessible 
           STATUS      current 
           DESCRIPTION 
              "Inet Address Type corresponding to this forwarding table 
               entry. This indicates whether the row is for IGMP/MLD Snooping"
           ::= { pmSnoopVlanIpFwdEntry 3 } 
 
      pmSnoopVlanIpFwdSourceAddress OBJECT-TYPE
           SYNTAX      InetAddress 
           MAX-ACCESS  not-accessible
           STATUS      current
           DESCRIPTION
               "Unicast source address of the data source that sends
                multicast data for this group"
           ::= { pmSnoopVlanIpFwdEntry 4 }

      pmSnoopVlanIpFwdGroupAddress OBJECT-TYPE
           SYNTAX      InetAddress 
           MAX-ACCESS  not-accessible
           STATUS      current
           DESCRIPTION
               "The Multicast group address learnt."
           ::= { pmSnoopVlanIpFwdEntry 5 }

      pmSnoopVlanIpFwdInnerVlanId OBJECT-TYPE
           SYNTAX      InnerVlanIndex
           MAX-ACCESS  not-accessible
           STATUS      current
           DESCRIPTION
               "The inner vlan id on which the multicast group is learnt."
           ::= { pmSnoopVlanIpFwdEntry 6 }

       pmSnoopVlanIpFwdLocalPortList OBJECT-TYPE
           SYNTAX      PortList
           MAX-ACCESS  read-only
           STATUS      current
           DESCRIPTION
               "List of ports onto which the multicast data packets from this 
           source destined for this group, will be forwarded. 
           Each bit in this object represent interfaces denoted by the 
           object pmVcHlPortId associated to the instance identifier 
           denoted by pmSnoopVlanIpFwdInstanceId. This object alone 
           should be referred in environments where the number of 
           interfaces in the system is scaled to a large value, as the 
           object pmSnoopVlanIpFwdPortList may not be sufficient to 
           report the full set of interfaces in each switch instance."
           ::= { pmSnoopVlanIpFwdEntry 8 } 

-- -----------------------------------------------------------------------------
-- The Snoop VLAN Group (Extention)                        --                 
-- -----------------------------------------------------------------------------

-- The Extention table for VLAN based FilterEntry

      pmSnoopVlanFilterXTable OBJECT-TYPE
          SYNTAX      SEQUENCE OF PmSnoopVlanFilterXEntry
          MAX-ACCESS  not-accessible
          STATUS      current
          DESCRIPTION
             "This table is an extention table of pmSnoopVlanFilterTable"
          ::= { pmSnoopVlan 8 }

      pmSnoopVlanFilterXEntry OBJECT-TYPE
          SYNTAX      PmSnoopVlanFilterXEntry
          MAX-ACCESS  not-accessible
          STATUS      current
          DESCRIPTION
             "Each entry contains configurations for specific VLANs"
          AUGMENTS    { pmSnoopVlanFilterEntry }
          ::= { pmSnoopVlanFilterXTable 1 }

      PmSnoopVlanFilterXEntry ::= SEQUENCE {
          pmSnoopVlanMulticastProfileId         Unsigned32,
          pmSnoopVlanPortPurgeInterval          Integer32,
          pmSnoopVlanMaxResponseTime            Integer32,
      pmSnoopVlanRtrLocalPortList           PortList,
      pmSnoopVlanBlkRtrLocalPortList        PortList
      }

      pmSnoopVlanMulticastProfileId OBJECT-TYPE
          SYNTAX      Unsigned32
          MAX-ACCESS  read-write
          STATUS      current 
          DESCRIPTION 
               "This object contains the multicast profile id configured for a 
               particular VLAN and is used for multicast vlan classification.
               When any untagged report or leave message is received (i.e. packet 
               with no tag in a Customer Bridge or packet with no S-tag in a 
               Provider or 802.1ad Bridge), and if the Group & Source address in
               the received packet matches any rule in this profile, then the
               received packet is classified to be associated to the VLAN (that is,
               Multicast VLAN) to which this profile is mapped.
               By default, no profile is associated to any VLAN."
          DEFVAL { 0 }
          ::= { pmSnoopVlanFilterXEntry 6 }

       pmSnoopVlanPortPurgeInterval OBJECT-TYPE 
          SYNTAX      Integer32 
          MAX-ACCESS  read-only 
          STATUS      current 
          DESCRIPTION 
             "This is the interval (in seconds) after which a learnt  
              port entry will be purged. For each port on which report
              has been received,this timer runs for 'PortPurgeInterval'
              seconds. This timer will be restarted whenever a report 
              message is received from a host on the specific port. If 
              the timer expires, then , the learnt port entry  will 
              be purged from the multicast group." 
          ::= { pmSnoopVlanFilterXEntry 7 } 

      pmSnoopVlanMaxResponseTime OBJECT-TYPE
         SYNTAX     Integer32 (0..65025)
         MAX-ACCESS read-create
         STATUS     current
         DESCRIPTION
             "The maximum response code advertised in queries send over this
             vlan.This object is used to configure max response code for
             both IGS and MLDS.Minimum value for the object is zero for both
             IGS and MLDS. Max value and defualt value for the object varries
             for IGS and MLDS. 
             For IGS, the max value supported is 255. The default value is 
             100.Its unit is in tenths of a  second.
             For MLDS, the max value supported is 65025. The default value 
             is 10000. Its unit is in milliseconds."
         ::= { pmSnoopVlanFilterXEntry 8 }

      pmSnoopVlanRtrLocalPortList OBJECT-TYPE
           SYNTAX      PortList
           MAX-ACCESS  read-write
           STATUS      current
           DESCRIPTION
               "List of ports which are configured statically as router ports. 
           Each bit in this object represent interfaces denoted by the 
           object pmVcHlPortId associated to the instance identifier 
           denoted by pmSnoopVlanFilterInstId. This object alone 
           should be referred in environments where the number of 
           interfaces in the system is scaled to a large value , as the 
           object pmSnoopVlanRtrPortList may not be sufficient to represent 
           the full set of interfaces in each switch instance."
           ::= { pmSnoopVlanFilterXEntry 9 }

      pmSnoopVlanBlkRtrLocalPortList OBJECT-TYPE
          SYNTAX      PortList
          MAX-ACCESS  read-write
          STATUS      current
          DESCRIPTION
              "List of ports which are configured statically as blocked router 
          ports. Each bit in this object represent interfaces denoted by 
          the object pmVcHlPortId associated to the instance identifier 
          denoted by pmSnoopVlanFilterInstId. This object alone should be 
          referred in environments where the number of interfaces in the 
          system is scaled to a large value, as the object 
          pmSnoopVlanBlkRtrPortList may not be sufficient to represent the 
          full set of interfaces in each switch instance."
           ::= { pmSnoopVlanFilterXEntry 10 }

 -- Snooping Statistics 
 
      pmSnoopStatsTable OBJECT-TYPE 
          SYNTAX      SEQUENCE OF PmSnoopStatsEntry 
          MAX-ACCESS  not-accessible 
          STATUS      current 
          DESCRIPTION 
             "This table contains snooping statistics  
              maintained by the switch. The statistics are
              maintained on a per VLAN basis."
          ::= { pmSnoopStats 1 } 
 
      pmSnoopStatsEntry OBJECT-TYPE 
          SYNTAX      PmSnoopStatsEntry 
          MAX-ACCESS  not-accessible 
          STATUS      current 
          DESCRIPTION 
             "Contains snooping statistics for a particular VLAN." 
          INDEX { pmSnoopStatsInstId,
                  pmSnoopStatsVlanId,
                  pmSnoopStatsInetAddressType } 
          ::= { pmSnoopStatsTable 1 } 
 
      PmSnoopStatsEntry ::= SEQUENCE { 
          pmSnoopStatsInstId                Integer32, 
          pmSnoopStatsVlanId                Integer32, 
          pmSnoopStatsInetAddressType       InetAddressType,
          pmSnoopStatsRxGenQueries          Counter32,
          pmSnoopStatsRxGrpQueries          Counter32,
          pmSnoopStatsRxGrpAndSrcQueries    Counter32,
          pmSnoopStatsRxAsmReports          Counter32,
          pmSnoopStatsRxSsmReports          Counter32,
          pmSnoopStatsRxSsmIsInMsgs         Counter32,
          pmSnoopStatsRxSsmIsExMsgs         Counter32,
          pmSnoopStatsRxSsmToInMsgs         Counter32,
          pmSnoopStatsRxSsmToExMsgs         Counter32,
          pmSnoopStatsRxSsmAllowMsgs        Counter32,
          pmSnoopStatsRxSsmBlockMsgs        Counter32,
          pmSnoopStatsRxAsmLeaves           Counter32,
          pmSnoopStatsTxGenQueries          Counter32,
          pmSnoopStatsTxGrpQueries          Counter32,
          pmSnoopStatsTxGrpAndSrcQueries    Counter32,
          pmSnoopStatsTxAsmReports          Counter32,
          pmSnoopStatsTxSsmReports          Counter32,
          pmSnoopStatsTxAsmLeaves           Counter32,
          pmSnoopStatsDroppedPkts           Counter32,
          pmSnoopStatsUnsuccessfulJoins     Counter32,
          pmSnoopStatsActiveJoins           Counter32,
          pmSnoopStatsActiveGroups          Counter32
        } 

      pmSnoopStatsInstId OBJECT-TYPE 
           SYNTAX      Integer32 (0..255) 
           MAX-ACCESS  not-accessible 
           STATUS      current 
           DESCRIPTION 
            "Instance ID pertaining for the statistics entry."
           ::= { pmSnoopStatsEntry 1 } 

      pmSnoopStatsVlanId OBJECT-TYPE 
           SYNTAX      Integer32 (1..4094) 
           MAX-ACCESS  not-accessible 
           STATUS      current 
           DESCRIPTION 
            " VLAN ID for which snooping statistics are displayed"
           ::= { pmSnoopStatsEntry 2 } 

      pmSnoopStatsInetAddressType OBJECT-TYPE 
           SYNTAX      InetAddressType 
           MAX-ACCESS  not-accessible 
           STATUS      current 
           DESCRIPTION 
            " Indicates whether the statistics are for IGS/MLDS"
           ::= { pmSnoopStatsEntry 3 } 

      pmSnoopStatsRxGenQueries OBJECT-TYPE 
           SYNTAX      Counter32
           MAX-ACCESS  read-only 
           STATUS      current 
           DESCRIPTION 
               "Provides the statistics of General Queries received by the
                snooping switch." 
           ::= { pmSnoopStatsEntry 4 } 

      pmSnoopStatsRxGrpQueries OBJECT-TYPE 
           SYNTAX      Counter32
           MAX-ACCESS  read-only 
           STATUS      current 
           DESCRIPTION 
               "Provides the statistics of Group Specific Queries received
                by the snooping switch." 
           ::= { pmSnoopStatsEntry 5 } 

      pmSnoopStatsRxGrpAndSrcQueries OBJECT-TYPE 
           SYNTAX      Counter32
           MAX-ACCESS  read-only 
           STATUS      current 
           DESCRIPTION 
               "Provides the statistics of Group and Source Specific Queries
                received by the snooping switch." 
           ::= { pmSnoopStatsEntry 6 } 

      pmSnoopStatsRxAsmReports OBJECT-TYPE 
           SYNTAX      Counter32
           MAX-ACCESS  read-only 
           STATUS      current 
           DESCRIPTION 
               "Provides the statistics of IGMPv1/IGMPv2 Membership reports
                received by the snooping switch. In case of MLDS, it provides
                the statistics of MLDv1 membership reports." 
           ::= { pmSnoopStatsEntry 7 } 

      pmSnoopStatsRxSsmReports OBJECT-TYPE 
           SYNTAX      Counter32
           MAX-ACCESS  read-only 
           STATUS      current 
           DESCRIPTION 
               "Provides the statistics of IGMPv3/MLDv2 Membership reports
                received by the snooping switch."
           ::= { pmSnoopStatsEntry 8 } 

      pmSnoopStatsRxSsmIsInMsgs OBJECT-TYPE 
           SYNTAX      Counter32
           MAX-ACCESS  read-only 
           STATUS      current 
           DESCRIPTION 
               "Provides the statistics of IGMPv3/MLDv2 Membership reports
                of type IS_IN received by the snooping switch." 
           ::= { pmSnoopStatsEntry 9 } 

      pmSnoopStatsRxSsmIsExMsgs OBJECT-TYPE 
           SYNTAX      Counter32
           MAX-ACCESS  read-only 
           STATUS      current 
           DESCRIPTION 
               "Provides the statistics of IGMPv3/MLDv2 Membership reports
                of type IS_EX received by the snooping switch." 
           ::= { pmSnoopStatsEntry 10 } 

      pmSnoopStatsRxSsmToInMsgs OBJECT-TYPE 
           SYNTAX      Counter32
           MAX-ACCESS  read-only 
           STATUS      current 
           DESCRIPTION 
               "Provides the statistics of IGMPv3/MLDv2 Membership reports
                of type TO_IN received by the snooping switch." 
           ::= { pmSnoopStatsEntry 11 } 

      pmSnoopStatsRxSsmToExMsgs OBJECT-TYPE 
           SYNTAX      Counter32
           MAX-ACCESS  read-only 
           STATUS      current 
           DESCRIPTION 
               "Provides the statistics of IGMPv3/MLDv2 Membership reports
                of type TO_EX received by the snooping switch." 
           ::= { pmSnoopStatsEntry 12 } 

      pmSnoopStatsRxSsmAllowMsgs OBJECT-TYPE 
           SYNTAX      Counter32
           MAX-ACCESS  read-only 
           STATUS      current 
           DESCRIPTION 
               "Provides the statistics of IGMPv3/MLDv2 Membership reports
                of type ALLOW received by the snooping switch." 
           ::= { pmSnoopStatsEntry 13 } 

      pmSnoopStatsRxSsmBlockMsgs OBJECT-TYPE 
           SYNTAX      Counter32
           MAX-ACCESS  read-only 
           STATUS      current 
           DESCRIPTION 
               "Provides the statistics of IGMPv3/MLDv2 Membership reports
                of type BLOCK received by the snooping switch." 
           ::= { pmSnoopStatsEntry 14 } 

      pmSnoopStatsRxAsmLeaves OBJECT-TYPE 
           SYNTAX      Counter32
           MAX-ACCESS  read-only 
           STATUS      current 
           DESCRIPTION 
               "Provides the statistics of IGMPv2/MLDv1 Leave messages    
                received by the snooping switch." 
           ::= { pmSnoopStatsEntry 15 } 

      pmSnoopStatsTxGenQueries OBJECT-TYPE 
           SYNTAX      Counter32
           MAX-ACCESS  read-only 
           STATUS      current 
           DESCRIPTION 
               "Provides the statistics of General Queries transmitted by the
                snooping switch." 
           ::= { pmSnoopStatsEntry 16 } 

      pmSnoopStatsTxGrpQueries OBJECT-TYPE 
           SYNTAX      Counter32
           MAX-ACCESS  read-only 
           STATUS      current 
           DESCRIPTION 
               "Provides the statistics of Group Specific Queries transmitted
                by the snooping switch." 
           ::= { pmSnoopStatsEntry 17 } 

      pmSnoopStatsTxGrpAndSrcQueries OBJECT-TYPE 
           SYNTAX      Counter32
           MAX-ACCESS  read-only 
           STATUS      current 
           DESCRIPTION 
               "Provides the statistics of Group and Source Specific Queries
                transmitted by the snooping switch." 
           ::= { pmSnoopStatsEntry 18 } 

      pmSnoopStatsTxAsmReports OBJECT-TYPE 
           SYNTAX      Counter32
           MAX-ACCESS  read-only 
           STATUS      current 
           DESCRIPTION 
               "Provides the statistics of IGMPv1/IGMPv2 Membership reports
                transmitted by the snooping switch." 
           ::= { pmSnoopStatsEntry 19 } 

      pmSnoopStatsTxSsmReports OBJECT-TYPE 
           SYNTAX      Counter32
           MAX-ACCESS  read-only 
           STATUS      current 
           DESCRIPTION 
               "Provides the statistics of IGMPv3/MLDv2 Membership reports
                transmitted by the snooping switch." 
           ::= { pmSnoopStatsEntry 20 } 

      pmSnoopStatsTxAsmLeaves OBJECT-TYPE 
           SYNTAX      Counter32
           MAX-ACCESS  read-only 
           STATUS      current 
           DESCRIPTION 
               "Provides the statistics of IGMPv2/MLDv1 Leave messages    
                transmitted by the snooping switch." 
           ::= { pmSnoopStatsEntry 21 } 

      pmSnoopStatsDroppedPkts OBJECT-TYPE 
           SYNTAX      Counter32
           MAX-ACCESS  read-only 
           STATUS      current 
           DESCRIPTION 
               "Provides the number of erroneous IGMP/MLD packets dropped
                by the snooping switch due to failure in checksum 
                calculation."
           ::= { pmSnoopStatsEntry 22 }
 
       pmSnoopStatsUnsuccessfulJoins OBJECT-TYPE
          SYNTAX       Counter32
          MAX-ACCESS   read-only
          STATUS       current
          DESCRIPTION
              "Provides the total number of IGMP groups or channels dropped, 
              because the maximum limit of groups or channels allowed for the 
              VLAN has been reached. By default, this object is for groups, 
              but if pmSnoopVlanFilterMaxLimitType is 'channels' this object 
              is for channels (S,G) entries."
          ::= { pmSnoopStatsEntry 23 }

      pmSnoopStatsActiveJoins OBJECT-TYPE
           SYNTAX      Counter32
           MAX-ACCESS  read-only
           STATUS      current
           DESCRIPTION
              "Provides the total number of IGMP groups or channels active 
              on this VLAN at the given time. By default, this object is for 
              groups, but if pmSnoopVlanFilterMaxLimitType is 'channels' this 
              object is for channels (S,G) entries."
           ::= { pmSnoopStatsEntry 24 }

      pmSnoopStatsActiveGroups OBJECT-TYPE
           SYNTAX      Counter32
           MAX-ACCESS  read-only
           STATUS      current
           DESCRIPTION
              "Provides the total number of IGMP groups or channels active 
              on this VLAN at the given time."
           ::= { pmSnoopStatsEntry 25 }
-- ------------------------------------------------
-- Port related Configuration
-- ------------------------------------------------
-- ------------------------------------------------------------------ 
-- Snoop Enhanced Port Config Table 
-- ------------------------------------------------------------------ 

       pmSnoopEnhPortTable OBJECT-TYPE 
           SYNTAX      SEQUENCE OF PmSnoopEnhPortEntry 
           MAX-ACCESS  not-accessible 
           STATUS      current 
           DESCRIPTION 
               "This table contains Port-related configurable information.
                This table is applicable only when the snooping module is 
                operating in the enhanced Mode. This table MUST NOT be 
                configured when the snooping module is operating in the 
                default mode."
             ::= { pmSnoopPort 2 } 

      pmSnoopEnhPortEntry OBJECT-TYPE 
          SYNTAX      PmSnoopEnhPortEntry 
          MAX-ACCESS  not-accessible 
          STATUS      current 
          DESCRIPTION 
               "This table contains the list of paramter/attribute objects that 
               can be configured on an interface."
          INDEX {
                    pmSnoopEnhPortIndex,
                    pmSnoopEnhPortInnerVlanId,
                    pmSnoopEnhPortInetAddressType
                   }
          ::= { pmSnoopEnhPortTable 1 }

      PmSnoopEnhPortEntry ::= SEQUENCE {
            pmSnoopEnhPortIndex              InterfaceIndex,
            pmSnoopEnhPortInnerVlanId        InnerVlanIndex,
            pmSnoopEnhPortInetAddressType    InetAddressType,
            pmSnoopEnhPortLeaveMode          INTEGER,
            pmSnoopEnhPortRateLimit          Unsigned32,
            pmSnoopEnhPortMaxLimitType       INTEGER,
            pmSnoopEnhPortMaxLimit           Unsigned32,
            pmSnoopEnhPortProfileId          Unsigned32,
            pmSnoopEnhPortMemberCnt          Unsigned32
      }

      pmSnoopEnhPortIndex OBJECT-TYPE
           SYNTAX      InterfaceIndex
           MAX-ACCESS  not-accessible
           STATUS      current
           DESCRIPTION
               "The interface index of the port."
           ::= { pmSnoopEnhPortEntry 1 }

      pmSnoopEnhPortInnerVlanId OBJECT-TYPE
           SYNTAX      InnerVlanIndex
           MAX-ACCESS  not-accessible
           STATUS      current
           DESCRIPTION
               "The Inner VLAN Identifier."
           ::= { pmSnoopEnhPortEntry 2 }

      pmSnoopEnhPortInetAddressType OBJECT-TYPE 
           SYNTAX      InetAddressType 
           MAX-ACCESS  not-accessible 
           STATUS      current
           DESCRIPTION 
              "Inet Address Type corresponding to this interface configuration 
               entry. This indicates whether the row is for IGMP/MLD Snooping"
           ::= { pmSnoopEnhPortEntry 3 } 

      pmSnoopEnhPortLeaveMode OBJECT-TYPE 
           SYNTAX      INTEGER { 
                                   explicithosttrack (1),
                                   fastleave (2),
                                   normalleave (3) 
                                 }
           MAX-ACCESS  read-write
            STATUS      current
            DESCRIPTION
              "Sets the mechanism to be used for processing the leave messages
              in the down stream interface. 
              
              When this object is set to 'explicitHostTrack', then the leave 
              messages are processed using the explicit host tracking 
              mechanism.
              When this object is set to 'fastLeave', the leave messages
              are processed by the fast leave mechanism.
              When this object is set to 'normalLeave', for every
              leave message received, a group or group specific query is sent
              on the interface.  
              
              This object can be configured only when
              pmSnoopInstanceGlobalLeaveConfigLevel is set to portbased.
              This object is applicable only for processing the igmp v2 leave 
              messages. For igmpv3 reports, the explicit host tracking 
              functionality is always performed for tracking the source 
              registrations and it cannot be disabled.
              For the v3 INCLUDE NONE reports the leave handling behavior is
              similar to the v2 leave messages for the leave modes
              'explicitHostTrack' and 'fastLeave'. For the leave mode
              'normalLeave' query message is not sent on the interface
              and only the host registered for the multicast group is removed"            DEFVAL { normalleave }
            ::= { pmSnoopEnhPortEntry 4 }

       pmSnoopEnhPortRateLimit OBJECT-TYPE
            SYNTAX      Unsigned32
            MAX-ACCESS  read-write
            STATUS      current
            DESCRIPTION
               "Configures the rate-limit for a downstream interface in 
               units of the number of IGMP packets per second. By default, 
               this object will hold the maximum value supported by an 
               unsigned integer and will not rate limit any IGMP packets. 
               The actual rate supported, however, will depend on what the 
               system can support. If this object is configured as zero, then 
               no IGMP packets will be processed on this interface."
            DEFVAL { 4294967295 }
               ::= { pmSnoopEnhPortEntry 5 }

       pmSnoopEnhPortMaxLimitType OBJECT-TYPE 
            SYNTAX      INTEGER { none(0), groups(1), channels(2) } 
            MAX-ACCESS  read-write
            STATUS      current 
            DESCRIPTION 
              "Indicates the type of limit to be applied on this interface. 
               Setting as 'channels' indicates that the limit is set for 
               channel (group, source) registrations whereas setting as 
               'groups' indicates that the limit is set for groups. 
               The channel limit will be applied only for IGMPv3 Include &
               Allow reports whereas the group limit will be applied for
               all IGMP reports.
               By default, this object has a value of 0 ('none') and no 
               limiting is done i.e. the value of pmSnoopEnhPortMaxLimit
               is ignored when this object is set to 'none'."
            DEFVAL { none }
               ::= { pmSnoopEnhPortEntry 6 } 

       pmSnoopEnhPortMaxLimit OBJECT-TYPE
            SYNTAX      Unsigned32
            MAX-ACCESS  read-write
            STATUS      current
            DESCRIPTION
              "Configures the maximum number of unique entries (channel or 
               group) that can be learned simultaneously on this interface. 
               The pmSnoopEnhPortMaxLimitType must be set before configuring 
               this object. However the Max-limit is configurable even if the 
               limit type is 'none', but the limit won't be in effect unless 
               the limit type is set as 'channels' or 'groups'. 

               If pmSnoopEnhPortMaxLimitType is 'channels', 
               this limit applies to number of channels that can be joined 
               on this interface. If pmSnoopEnhPortMaxLimitType is 'groups', 
               this limit applies to number of groups that can be joined on 
               this interface.
               
               By default, this object will hold a value of zero and will 
               not limit any IGMP packets as long as the value of 
               pmSnoopEnhPortMaxLimitType is set to 'none'. However, when
               pmSnoopEnhPortMaxLimitType is set to 'groups' or 'channels',
               if this object has the value of zero, then no IGMP reports will
               be processed on this interface.
               The maximum value supported by this object is dependent on the 
               maximum groups or channels registrations that the system can 
               support."
          DEFVAL { 0 }
               ::= { pmSnoopEnhPortEntry 7 }

       pmSnoopEnhPortProfileId  OBJECT-TYPE
           SYNTAX       Unsigned32
           MAX-ACCESS   read-write
           STATUS       current 
           DESCRIPTION 
             "The multicast profile index configured for the downstream 
                interface. This profile contains a set of allowed or denied 
                rules which are to be applied for the IGMP packets received 
                through this downstream interface. By default, no profiles 
                are applied on the interface."
           DEFVAL { 0 }
             ::= { pmSnoopEnhPortEntry 8 }

        pmSnoopEnhPortMemberCnt OBJECT-TYPE
            SYNTAX      Unsigned32
            MAX-ACCESS  read-only
            STATUS      current
            DESCRIPTION
               "Provides the total number of groups or channels active on the
                interface at the given time."
            ::= { pmSnoopEnhPortEntry 9 }

-- ------------------------------------------------------------------ 
-- Snoop Proxy Upstream Router Port Table
-- ------------------------------------------------------------------ 

       pmSnoopRtrPortTable OBJECT-TYPE 
            SYNTAX      SEQUENCE OF PmSnoopRtrPortEntry 
            MAX-ACCESS  not-accessible 
            STATUS      current 
            DESCRIPTION 
               "This table contains upstream Router Port-related
               configurable information. Router port entry in this table 
               will be created when the router port is either learnt 
               dynamically or when the router port is statically 
               configured through 'pmSnoopVlanRtrPortList'.Only static
               router ports will be restored during save restore."
            ::= { pmSnoopPort 3 } 

       pmSnoopRtrPortEntry OBJECT-TYPE 
            SYNTAX          PmSnoopRtrPortEntry 
            MAX-ACCESS      not-accessible 
            STATUS          current 
            DESCRIPTION 
               "This table contains the upstream router port operating
                and configured version of IGMP."

            INDEX {
                    pmSnoopRtrPortIndex,
                    pmSnoopRtrPortVlanId,
                    pmSnoopRtrPortInetAddressType
                   }
             ::= { pmSnoopRtrPortTable 1 }

       PmSnoopRtrPortEntry ::= SEQUENCE {
            pmSnoopRtrPortIndex              InterfaceIndex,
            pmSnoopRtrPortVlanId             VlanIndex,
            pmSnoopRtrPortInetAddressType    InetAddressType,
            pmSnoopRtrPortOperVersion        INTEGER,
            pmSnoopOlderQuerierInterval      Integer32,
            pmSnoopV3QuerierInterval         Integer32
       }

      pmSnoopRtrPortIndex OBJECT-TYPE
           SYNTAX      InterfaceIndex
           MAX-ACCESS  not-accessible
           STATUS      current
           DESCRIPTION
               "The interface index of the port which is defined
                as an upstream router port."
           ::= { pmSnoopRtrPortEntry 1 }

      pmSnoopRtrPortVlanId OBJECT-TYPE
           SYNTAX      VlanIndex
           MAX-ACCESS  not-accessible
           STATUS      current
           DESCRIPTION
               "The VLAN Identifier for the upstream router port"
           ::= { pmSnoopRtrPortEntry 2 }

      pmSnoopRtrPortInetAddressType OBJECT-TYPE 
           SYNTAX      InetAddressType 
           MAX-ACCESS  not-accessible 
           STATUS      current
           DESCRIPTION 
              "Inet Address Type corresponding to  the global configuration 
               entry. This indicates whether the row is for IGMP/MLD Snooping"
           ::= { pmSnoopRtrPortEntry 3 } 

       pmSnoopRtrPortOperVersion OBJECT-TYPE 
            SYNTAX      INTEGER { v1(1), v2(2), v3(3) }
            MAX-ACCESS  read-only
            STATUS      current
            DESCRIPTION
              "Indicates the operating version of the IGMP Proxy 
               on the upstream router port. Operating version is used by the
               Proxy to send consolidated reports on the router ports.
               Operating version of the router port will change based on the 
               the version of query messages received on that port.
               Otherwise it will be set to the configured version of IGMP on the
               router port. 
               The default operating mode is IGMP version 3
               i.e, V3(3) or MLD version 2 i.e, V2(2)."
            DEFVAL { 3 }
            ::= { pmSnoopRtrPortEntry 4 }

      pmSnoopOlderQuerierInterval OBJECT-TYPE 
            SYNTAX     Integer32 (60..600) 
            MAX-ACCESS read-write 
            STATUS     current 
            DESCRIPTION 
            "The time interval after which proxy assumes that there are no 
            v1/v2 routers present on the upstream port.While OlderQuerierTimer is 
            running, proxy will reply to all queries with consolidated
            v1/v2 (oper version) reports.   
            On time-out, if v2/v3 queriers are not present and if the port 
            is a dynamically learnt port, then it will be purged. 
            Else, proxy will reply to all the queries with consolidated
            reports with the new oper version (v2/v3).The 
            value configured for static router alone will be stored 
            and restored." 
            DEFVAL { 125 }
            ::= { pmSnoopRtrPortEntry 6 } 

     pmSnoopV3QuerierInterval OBJECT-TYPE 
            SYNTAX     Integer32
            MAX-ACCESS read-only 
            STATUS     current 
            DESCRIPTION 
            "The time interval after which proxy assumes that there are no 
            IGMPv3 routers present on the upstream port.While V3QuerierTimer is 
            running, proxy will reply to all queries with consolidated 
            v1/v2/v3 (oper version) reports.
            On time-out, if v1/v2 queriers are not present and if the port
            is a dynamically learnt upstream port, then the port will be purged.
            Else, proxy will reply to all the queries with consolidated 
            reports with the new oper version (v1/v2). " 
            ::= { pmSnoopRtrPortEntry 7 }

-- ------------------------------------------------------------ 
-- groups in the MIB 
-- ------------------------------------------------------------

      pmLaSystem                  OBJECT IDENTIFIER ::= { privateLa 1 }
      pmLaPortChannel             OBJECT IDENTIFIER ::= { privateLa 2 }
      pmLaPort                    OBJECT IDENTIFIER ::= { privateLa 3 }

-- ------------------------------------------------------------------
-- The La System Group
-- ------------------------------------------------------------------

      pmLaStatus OBJECT-TYPE
           SYNTAX      INTEGER { enabled(1), disabled(2) }
           MAX-ACCESS  read-write
           STATUS      current
           DESCRIPTION
               "Sets the Link Aggregation Module administrative status as 
                enabled or disabled. The module can be enabled only when this
                object is set to 'enabled'."
           ::= { pmLaSystem 2 }

      pmLaOperStatus OBJECT-TYPE
           SYNTAX      INTEGER { enabled(1), disabled(2) }
           MAX-ACCESS  read-only
           STATUS      current
           DESCRIPTION
               "This read only objects gives actual status of the Link 
                Aggregation Module (Operational status of module). When
                Module is enabled Link Aggregation protocol starts 
                functioning. When the module is disabled all the dynamically
                allocated memory will be freed and Link Aggregation protocol
                stops functioning."
          ::= { pmLaSystem 6 }


      pmLaActorSystemID    OBJECT-TYPE
                SYNTAX       MacAddress
                MAX-ACCESS   read-write
                STATUS       current
                DESCRIPTION
                  "A 6-octet read-write MAC address value used as a unique
                identifier for the System."
         ::= { pmLaSystem 7 }

      pmLaNoPartnerIndep OBJECT-TYPE
           SYNTAX      INTEGER { enabled(1), disabled(2) }
           MAX-ACCESS  read-write
           STATUS      current
           DESCRIPTION
               "When enabled, and if there is no remote partner information 
                available in the system then the port-channel becomes
                operationally down and the member ports of the port-channel
                operate as independent ports and these ports are visible to 
                higher layers.When disabled and if there is no remote partner
                information available in the system then the port-channel
                becomes operationally up based on the default values assigned
                for the partner and the member ports of the port-channel 
                becomes operationally up and will not be visible to higher
                layers."
        DEFVAL  { 2 }
           ::= { pmLaSystem 8 }

--
-- Port Channel Table
--

pmLaPortChannelTable  OBJECT-TYPE
        SYNTAX     SEQUENCE OF PmLaPortChannelEntry 
        MAX-ACCESS not-accessible
        STATUS     current
        DESCRIPTION
           "A Port-channel is created through ifMain table.
           After the creation of the port-channel, corresponding logical
           interface will be created in the ifMain table. 
           This Port-channel table is indexed through Key values and allows to 
           configure link selection policy and the Mac address for 
           the port-channel. All other objects in this table displays 
           the details of the port-channel"

        ::= { pmLaPortChannel 1 }

pmLaPortChannelEntry OBJECT-TYPE
        SYNTAX     PmLaPortChannelEntry 
        MAX-ACCESS not-accessible
        STATUS     current
        DESCRIPTION
              "There is one entry in this table for each created
               port-channel port"

        INDEX { pmLaPortChannelIfIndex }
        ::= { pmLaPortChannelTable 1 }

PmLaPortChannelEntry ::= 
            SEQUENCE {
              pmLaPortChannelIfIndex                       InterfaceIndex,
              pmLaPortChannelMode                          PortLaMode,
              pmLaPortChannelDefaultPortIndex              InterfaceIndexOrZero,
              pmLaPortChannelMaxPorts                      Integer32, 
              pmLaPortChannelSelectionPolicyBitList        Integer32
              }

pmLaPortChannelIfIndex OBJECT-TYPE
        SYNTAX      InterfaceIndex
        MAX-ACCESS  not-accessible
        STATUS      current
        DESCRIPTION
              "The ifIndex of the port-channel(Aggregator's 
               interface index). "
        ::= { pmLaPortChannelEntry 1 }

pmLaPortChannelMode OBJECT-TYPE
       SYNTAX       PortLaMode
       MAX-ACCESS   read-only
       STATUS       current
       DESCRIPTION
         "Current Operating Channel Mode of the port
                     Lacp(1)    - forcing the port to negotiate with the
                                  partner.
                     manual(2)  - force the port to enable channeling (Manual).
                     disable(3) - channeling is disabled."
        ::= { pmLaPortChannelEntry 5 }

pmLaPortChannelDefaultPortIndex OBJECT-TYPE
        SYNTAX      InterfaceIndexOrZero
        MAX-ACCESS  read-write
        STATUS      current
        DESCRIPTION
              "The ifIndex of the default port that gets attached to the
              aggregator. A value of 0 means there is no default port for
              this port-channel.
               If this object is set to 0, it will remove the current default
              port from the aggregator.
               To change the default port of an aggregator, first reset the
               object to 0 and then set the new ifIndex as default port."
        DEFVAL  { 0 }
        ::= { pmLaPortChannelEntry 9 }

pmLaPortChannelMaxPorts OBJECT-TYPE
        SYNTAX      Integer32 (2..8)
        MAX-ACCESS  read-write
        STATUS      current
        DESCRIPTION
              "This object specifies the maximun number of
               ports that can attach to a port-channel."
        DEFVAL  { 8 } 
        ::= { pmLaPortChannelEntry 10 }

pmLaPortChannelSelectionPolicyBitList  OBJECT-TYPE
          SYNTAX      Integer32
          MAX-ACCESS  read-write
          STATUS      current
          DESCRIPTION
               " This object is used to set the Link selection policy to be
               used by the port-channel.
               A FOUR BYTE integer is used for setting the selecting policy.
               Each BIT in the four byte integer, represents a particular
               selection policy.
               The maping between the bit positions & the selection policy is
               as follows:
                      macSrc(0),     -- source MAC
                      macDst(1),     -- destination MAC
                      vlanId(2),     -- VLAN ID
                      isid(3),       -- ISID
                      mplsLabel0(4), -- MPLS Label 0 ( top label )
                      mplsLabel1(5), -- MPLS Label 1 ( inner label 1)
                      mplsLabel2(6), -- MPLS Label 2 ( inner label 2)
                      ipSrc(7),      -- Source IP address
                      ipDst(8),      -- Destination IP address
                      ip6Src(9),     -- Source IPv6 address
                      ip6Dst(10),    -- Destination IPv6 address
                      l3Protocol(11),-- Layer 3 protocol specified in IP header
                      l4SrcPort(12), -- Layer 4 source port specified in L4 header ( tcp/udp port )
                      l4DstPort (13) -- Layer 4 destination port specified in L4 header ( tcp/udp port )

                The remaining bits are unused. Selection of multiple bits 
                implies selection of corresponding attributes in the 
                packet header for configuring the port-channel selection policy.

                For example if the bits 0 and 1 are set, then the selection
                policy is based on source mac and destination mac.

                This object would return failure if the selected bitlist is not supported in the 
                system(hardware)"
          ::= {pmLaPortChannelEntry 11}

-- END OF LaPortChannel Table

-- -------------------------------------------------------------
-- The Pm Aggregation Port Group 
-- -------------------------------------------------------------

   pmLaPortTable OBJECT-TYPE
      SYNTAX SEQUENCE OF PmLaPortEntry
      MAX-ACCESS         not-accessible
      STATUS             current
      DESCRIPTION
         "A table that contains objects to set the port lacp mode
         of dot3adAggPortTable."
      ::={pmLaPort 1 }

   pmLaPortEntry OBJECT-TYPE
      SYNTAX      PmLaPortEntry
      MAX-ACCESS  not-accessible
      STATUS      current
      DESCRIPTION
         "Each entry in this table is for each physical port that participates 
         in Link Aggregation which can be either aggregatable or individual.
         This table is indexed by the PortIndex."
      INDEX {pmLaPortIndex }
      ::={pmLaPortTable 1 }

   PmLaPortEntry ::=
      SEQUENCE {
         pmLaPortIndex                           InterfaceIndex,
         pmLaPortMode                            PortLaMode,
         pmLaPortBundleState                     INTEGER,
         pmLaPortActorResetAdminState            LacpState,
         pmLaPortAggregateWaitTime               TimeTicks,
         pmLaPortPartnerResetAdminState          LacpState,
         pmLaPortActorAdminPort                  Integer32,
         pmLaPortRestoreMtu                      Integer32,
         pmLaPortSelectAggregator                INTEGER
        }

   pmLaPortIndex OBJECT-TYPE
      SYNTAX     InterfaceIndex
      MAX-ACCESS not-accessible
      STATUS     current
      DESCRIPTION
         "The ifIndex of the port"
      ::={pmLaPortEntry 1 }
      
   pmLaPortMode OBJECT-TYPE
      SYNTAX      PortLaMode
      MAX-ACCESS  read-write
      STATUS      current
      DESCRIPTION
       "This object is used to enable LACP , disable LACP or manually
       aggregate a port"
      ::={pmLaPortEntry 2 }

      
   pmLaPortBundleState OBJECT-TYPE
      SYNTAX  INTEGER {
                      upInBndl(0),
                      standby(1),
                      down(2),
                      upIndividual(3)
      }
      MAX-ACCESS  read-only
      STATUS      current
      DESCRIPTION 
      "This read-only object is used to display the port state in aggregation
         upInBndl(0)      - The port is operationally up and actively 
                            takes part in aggregation.
         standby(1)       - The port is capable of joining in
                            aggregation group, when any of the ports in  
                            aggregation group goes down.
         down(2)          - The port is operationally down in lower layers.
                            or the port is operational in lower layers
                            but temporarilyorarily not able to participate
                            in aggregation because of different partner
                            information in the same group.
         upIndividual(3)  - The port is operating individually and
                            is not taking part in aggregation."
      ::={pmLaPortEntry 3}


    pmLaPortAggregateWaitTime OBJECT-TYPE
      SYNTAX     TimeTicks
      MAX-ACCESS read-write
      STATUS     current
      DESCRIPTION
            "Duration of the port to attach to the PortChannel."
      DEFVAL { 2 }
      ::={pmLaPortEntry 5 }


    pmLaPortActorAdminPort OBJECT-TYPE
      SYNTAX     Integer32 (1..65535)
      MAX-ACCESS read-write
      STATUS     current
      DESCRIPTION
            "The port number used as dot3adAggPortActorPort and is 
             communicated in LACPDUs as the Actor_Port."
      ::={pmLaPortEntry 7 }


-- ------------------------------------------------------------  
-- groups in the MIB  
-- ------------------------------------------------------------ 

      pmLldpSystem        OBJECT IDENTIFIER ::= { privateLldp 1 } 
      pmLldpTLV           OBJECT IDENTIFIER ::= { privateLldp 2 }
      pmlldpv2Config      OBJECT IDENTIFIER ::= { privateLldp 5 }

-- ------------------------------------------------------------------ 
-- The LLDP System Group 
-- ------------------------------------------------------------------ 
 
      pmLldpModuleStatus OBJECT-TYPE 
          SYNTAX      INTEGER  { enabled(1), disabled(2) } 
          MAX-ACCESS  read-write
          STATUS      current 
          DESCRIPTION 
             "The administrative module status of LLDP module. 
              This enables or disables LLDP in the system. A value of 
              'enabled' (1) indicates that LLDP is enabled in the device
              and can be enabled port-wise. A value of 'disabled' (2) 
              indicates that LLDP is disabled in the device and also
              disabled on all ports.
             
              When LLLDP module status is changed from enabled to disabled, 
              a global timer (instead of port specific timers) is started 
              to ensure the successful transmission of shutdown frame on 
              all ports. Module status change from disabled to enabled is 
              not allowed when the global timer is running (i.e., when disable
              is in progress)."
          DEFVAL  { disabled }
          ::= { pmLldpSystem 2 } 

-- ------------------------------------------------------------------ 
-- The LLDP TLV Group 
-- ------------------------------------------------------------------ 

   pmLldpLocChassisIdSubtype  OBJECT-TYPE
      SYNTAX      INTEGER { chassiscomp(1), ifalias(2), portcomp(3),
                            macaddr(4), nwaddr(5), ifname(6), local(7) }
      MAX-ACCESS  read-write
      STATUS      current
      DESCRIPTION
         "The type of encoding used to identify the chassis component
          associated with the local system. 
          
          When chassis id subtype is configured as chassiscomp/portcomp/local
          it is mandatory to configure the pmLldpLocChassisId object. 
          If pmLldpLocChassisId object is not configured then current value of
          pmLldpLocChassisId is advertised.
          
          When chassis id subtype is configured as ifalias/macaddr/nwaddr/
          ifname it is not required to configure pmLldpLocChassisId object. 
          System specific values are used for setting pmLldpLocChassisId 
          object."
      REFERENCE
          "IEEE 802.1AB-2005 9.5.2.2"
      DEFVAL  { macaddr }
      ::= { pmLldpTLV 1 }

pmLldpLocPortTable OBJECT-TYPE
    SYNTAX SEQUENCE OF PmLldpLocPortEntry
    MAX-ACCESS         not-accessible
    STATUS             current
    DESCRIPTION
      "This table contains one or more rows per port information
      associated with the local system known to this agent."
    ::= { pmLldpTLV 3 }

     pmLldpLocPortEntry OBJECT-TYPE
    SYNTAX             PmLldpLocPortEntry
    MAX-ACCESS         not-accessible
    STATUS             current
    DESCRIPTION
      "Information about a particular port component.
      Entries may be created and deleted in this table by the
      agent."
    INDEX {lldpLocPortNum }
    ::= { pmLldpLocPortTable 1 }

     PmLldpLocPortEntry ::= SEQUENCE {
        pmLldpPortConfigNotificationType       INTEGER
    }
    
      pmLldpPortConfigNotificationType       OBJECT-TYPE
      SYNTAX      INTEGER  {
                             remTabChg (1), 
                             misCfg(2),
                             remTabChgAndMisCfg(3)
      } 
      MAX-ACCESS  read-write
      STATUS      current
      DESCRIPTION
             "This object is used to set the notification type. 
    
              If the associated pmLldpNotificationType object has a value of  
              remTabChg (1),then LLDP agent sends trap notification to NMS 
              whenever remote table change occurs.

              If the associated pmLldpNotificationType object has a value of  
              misCfg (1),then LLDP agent sends trap notification to NMS 
              whenever mis-configuration is identified.

              If the associated pmLldpNotificationType object has a value of  
              remTabChgAndMisCfg(3),then LLDP agent sends trap notification to 
              NMS whenever remote table change occurs or/and whenever 
              mis-configuration is identified.

              LLDP agent send the trap messages only when  MIB Object 
              lldpPortConfigNotificationEnable is true.So 
              pmLldpNotificationType Object is valid when 
              lldpPortConfigNotificationEnable Object is true."

       DEFVAL  { misCfg }
    ::= { pmLldpLocPortEntry 3 }

     pmlldpv2Version      OBJECT-TYPE
     SYNTAX  INTEGER {
                           lldpv1 (1),
                           lldpv2 (2)
                     }
     MAX-ACCESS read-write
     STATUS current
     DESCRIPTION
                "The Object to save version type to be used.
                 v1 version is lldpv1 (2005)
                 v2 version is lldpv2 (2009)"
     DEFVAL { lldpv1 }
     ::= { pmlldpv2Config 1 }

pmMIDot1qPmVlan     OBJECT IDENTIFIER   ::= { privateMIVlanMIB 1 } 
 
-- pmMIDot1qPmVlanTunnelConfig - This sub group contains mib objects for 
-- configuring VLAN Stacking (also known 802.1q in 802.1q) feature 
-- in PmVLAN.
pmMIDot1qPmVlanTunnelConfig OBJECT IDENTIFIER  ::= { privateMIVlanMIB 2 }

 
-- pmMIDot1qPmVlan group 
 
pmMIDot1qPmVlanGlobalsTable OBJECT-TYPE
   SYNTAX        SEQUENCE OF PmMIDot1qPmVlanGlobalsEntry
   MAX-ACCESS    not-accessible
   STATUS        current
   DESCRIPTION
      "List of per virtual context Vlan Module Parameters."
   ::= { pmMIDot1qPmVlan 2 }

pmMIDot1qPmVlanGlobalsEntry OBJECT-TYPE
   SYNTAX       PmMIDot1qPmVlanGlobalsEntry
   MAX-ACCESS   not-accessible
   STATUS       current
   DESCRIPTION
      "Per virtual context Vlan module parmaters."
   INDEX { pmMIDot1qPmVlanContextId }
   ::= { pmMIDot1qPmVlanGlobalsTable 1 }

PmMIDot1qPmVlanGlobalsEntry ::=
   SEQUENCE {
       pmMIDot1qPmVlanContextId
          Integer32,
       pmMIDot1qPmVlanStatus 
          EnabledStatus,
       pmMIDot1qPmVlanMacBasedOnAllPorts 
          EnabledStatus,
       pmMIDot1qPmVlanPortProtoBasedOnAllPorts 
          EnabledStatus,
       pmMIDot1qPmVlanLearningMode 
          INTEGER,
       pmMIDot1qPmVlanHybridTypeDefault 
          INTEGER,
       pmMIDot1qPmVlanOperStatus
          EnabledStatus,
       pmMIDot1qPmGvrpOperStatus
          EnabledStatus,
       pmMIDot1qPmGmrpOperStatus
          EnabledStatus,
       pmMIDot1qPmUnicastMacLearningLimit
          Unsigned32,
       pmMIDot1qPmBaseBridgeMode
          INTEGER,
       pmMIDot1qPmVlanSubnetBasedOnAllPorts 
          EnabledStatus,
       pmMIDot1qPmVlanGlobalMacLearningStatus
          EnabledStatus,
       pmMIDot1qPmVlanApplyEnhancedFilteringCriteria
          TruthValue
   }

pmMIDot1qPmVlanContextId OBJECT-TYPE
   SYNTAX        Integer32 (0..65535)
   MAX-ACCESS    not-accessible
   STATUS        current
   DESCRIPTION
      "Identifies the virtual context in the system."
   ::= { pmMIDot1qPmVlanGlobalsEntry 1 }

pmMIDot1qPmVlanStatus OBJECT-TYPE 
   SYNTAX      EnabledStatus 
   MAX-ACCESS  read-write 
   STATUS      current 
   DESCRIPTION 
      "The administrative status requested by management for the Vlan 
      feature. The value enabled(1) indicates that Vlan should be enabled  
      in the device on all ports. The value disabled(2) indicates that 
      Vlan should be disabled in the device on all ports. The object can 
      be set to disabled if and only if, pmMIDot1qGvrpStatus and 
      pmMIDot1dGmrpStatus are disabled. The object should NOT be enabled 
      before setting 'pmMIDot1qPmVlanType'. Setting this object will 
      affect the operational status of the VLAN module 
      (pmMIDot1qPmVlanOperStatus)." 
   ::= { pmMIDot1qPmVlanGlobalsEntry 2 } 
 
pmMIDot1qPmVlanMacBasedOnAllPorts OBJECT-TYPE 
   SYNTAX      EnabledStatus
   MAX-ACCESS  read-write
   STATUS      current
   DESCRIPTION 
      "This object is only used to enable/disable the mac based type on all 
      ports of pmMIDot1qPmVlanPortMacBasedClassification"
   ::= { pmMIDot1qPmVlanGlobalsEntry 3 } 

pmMIDot1qPmVlanPortProtoBasedOnAllPorts OBJECT-TYPE 
   SYNTAX      EnabledStatus
   MAX-ACCESS  read-write
   STATUS      current
   DESCRIPTION 
      "This object is only used to enable/disable the port protocol based 
      type on all ports of 
      pmMIDot1qPmVlanPortPortProtoBasedClassification"
   ::= { pmMIDot1qPmVlanGlobalsEntry 4 } 
 
pmMIDot1qPmVlanLearningMode OBJECT-TYPE
   SYNTAX      INTEGER {
               ivl (1),
               svl (2),
               hybrid (3)
               }
   MAX-ACCESS  read-write
   STATUS      current
   DESCRIPTION
         "The Type of VLAN learning mode.
          When the object value is modified, the static
          fid-vlan mappings and static unicast entries
          need to be reconfigured. Static unicast configurations 
          associated with old fid will get deleted." 
   DEFVAL  { ivl }
   ::= { pmMIDot1qPmVlanGlobalsEntry 8 }

pmMIDot1qPmVlanHybridTypeDefault OBJECT-TYPE
   SYNTAX      INTEGER {
               ivl(1),
               svl(2)
               }
   MAX-ACCESS  read-write
   STATUS      current
   DESCRIPTION
         "The default learning mode of the switch if 
          pmMIDot1qPmVlanLearningMode is hvl (3).
          When the object value is modified, the static
          fid-vlan mappings and static unicast entries
          need to be reconfigured. Static unicast configurations 
          associated with old fid will get deleted."
   DEFVAL  { ivl }
   ::= { pmMIDot1qPmVlanGlobalsEntry 9 }

pmMIDot1qPmVlanOperStatus OBJECT-TYPE 
   SYNTAX      EnabledStatus 
   MAX-ACCESS  read-only 
   STATUS      current 
   DESCRIPTION 
      "The operational status of the Vlan module. 
      The value enabled(1) indicates that Vlan module is currently enabled  
      in the device. 
      The value disabled(2) indicates that Vlan module is currently disabled 
      in the device." 
   ::= { pmMIDot1qPmVlanGlobalsEntry 10 } 

pmMIDot1qPmGvrpOperStatus OBJECT-TYPE 
   SYNTAX      EnabledStatus 
   MAX-ACCESS  read-only 
   STATUS      current 
   DESCRIPTION 
      "The operational status of the GVRP module. 
      The value enabled(1) indicates that GVRP module is currently enabled  
      in the device. 
      The value disabled(2) indicates that GVRP module is currently disabled 
      in the device." 
   ::= { pmMIDot1qPmVlanGlobalsEntry 11 } 

pmMIDot1qPmGmrpOperStatus OBJECT-TYPE 
   SYNTAX      EnabledStatus 
   MAX-ACCESS  read-only 
   STATUS      current 
   DESCRIPTION 
      "The operational status of the GMRP module. 
      The value enabled(1) indicates that GMRP module is currently enabled  
      in the device. 
      The value disabled(2) indicates that GMRP module is currently disabled 
      in the device." 
   ::= { pmMIDot1qPmVlanGlobalsEntry 12 } 
 
pmMIDot1qPmUnicastMacLearningLimit OBJECT-TYPE
   SYNTAX      Unsigned32 (0..4294967295) 
   MAX-ACCESS  read-write
   STATUS      current
   DESCRIPTION
      "The Limiting value on the number of distinct unicast MAC addresses
       that can be learnt in the specified virtual context.

       The upper limit value that can be SET for this object is determined 
       by the underlying hardware. The value that can be SET for this object 
       cannot be less than the value set for the UnicastMacLimit per vlan for 
       any of the vlans in the specified virtual context."
   ::= { pmMIDot1qPmVlanGlobalsEntry 15 }

pmMIDot1qPmBaseBridgeMode OBJECT-TYPE
   SYNTAX      INTEGER
                {
                 dot1dTransparentMode(1),
                 dot1qVlanMode(2)
                }

   MAX-ACCESS  read-write
   STATUS      current
   DESCRIPTION
     "This object indicates Base Bridge-Mode of the Switch.
      Setting the value to transparent mode will make
      switch behave according to IEEE 802.1d implementation.
      Setting the value to VLAN mode will make switch behave
      according to IEEE 802.1q Implementation"
   ::= { pmMIDot1qPmVlanGlobalsEntry 16 }

pmMIDot1qPmVlanSubnetBasedOnAllPorts OBJECT-TYPE 
   SYNTAX      EnabledStatus
   MAX-ACCESS  read-write
   STATUS      current
   DESCRIPTION 
      "This object is used to enable/disable the subnet based VLAN Classification
       on all ports of dot1qPmVlanPortSubnetBasedClassification. On setting
       this object to enable/disable status, Subnet based VLAN classification 
       will be enabled/disabled on all the ports."
   ::= { pmMIDot1qPmVlanGlobalsEntry 17 } 

pmMIDot1qPmVlanGlobalMacLearningStatus OBJECT-TYPE 
   SYNTAX      EnabledStatus
   MAX-ACCESS  read-write
   STATUS      current
   DESCRIPTION 
         "This object specifies the global  MAC learning status of the
          switch. The default value of global mac learning status of
          the switch is enabled.
          This object can take only two values enabled or disabled.
          The value as specified by this object will be applied
          for a newly created VLAN. The configuration of this object 
          will override the value of pmMIDot1qPmVlanAdminMacLearningStatus 
          provided  the value of pmMIDot1qPmVlanAdminMacLearningStatus is 
          default only."
   DEFVAL  {enabled}
   ::= { pmMIDot1qPmVlanGlobalsEntry 18 } 

pmMIDot1qPmVlanApplyEnhancedFilteringCriteria OBJECT-TYPE
   SYNTAX      TruthValue 
   MAX-ACCESS  read-write
   STATUS      current
   DESCRIPTION
   "If this object is set as 'false', then only default filtering
   utility criteria will be applied on all ports in this context.
   Otherwise the filtering criteria to be used for the ports in this
   context will be taken from pmMIDot1qPmVlanFilteringUtilityCriteria 
   for the respective ports.
    - It is recommended to configure this object before doing any port
    to virtual context mapping in the system."
   DEFVAL  {true}
   ::= { pmMIDot1qPmVlanGlobalsEntry 19 }



-- ------------------------------------------------------------------------- 
-- Pm Vlan Port Table 
-- ------------------------------------------------------------------------- 
 
pmMIDot1qPmVlanPortTable OBJECT-TYPE 
   SYNTAX      SEQUENCE OF PmMIDot1qPmVlanPortEntry 
   MAX-ACCESS  not-accessible 
   STATUS      current 
   DESCRIPTION 
      "Table containing the port type information." 
   ::= { pmMIDot1qPmVlan 3 } 
 
pmMIDot1qPmVlanPortEntry OBJECT-TYPE 
   SYNTAX      PmMIDot1qPmVlanPortEntry 
   MAX-ACCESS  not-accessible 
   STATUS      current 
   DESCRIPTION 
      "Entry indicating the type of the port." 
   INDEX { pmMIDot1qPmVlanPort } 
   ::= { pmMIDot1qPmVlanPortTable 1 } 
    
PmMIDot1qPmVlanPortEntry ::= 
   SEQUENCE { 
      pmMIDot1qPmVlanPort Integer32, 
      pmMIDot1qPmVlanPortType INTEGER, 
      pmMIDot1qPmVlanPortMacBasedClassification EnabledStatus,
      pmMIDot1qPmVlanPortPortProtoBasedClassification EnabledStatus,
      pmMIDot1qPmVlanFilteringUtilityCriteria INTEGER,
      pmMIDot1qPmVlanPortProtected TruthValue, 
      pmMIDot1qPmVlanPortSubnetBasedClassification EnabledStatus,
      pmMIDot1qPmVlanPortUnicastMacLearning EnabledStatus,
      pmMIDot1qPmVlanPortGvrpJoinEmptyTxCount Counter32,
      pmMIDot1qPmVlanPortGvrpJoinEmptyRxCount Counter32,
      pmMIDot1qPmVlanPortGvrpJoinInTxCount Counter32,
      pmMIDot1qPmVlanPortGvrpJoinInRxCount Counter32,
      pmMIDot1qPmVlanPortGvrpLeaveInTxCount Counter32,
      pmMIDot1qPmVlanPortGvrpLeaveInRxCount Counter32,
      pmMIDot1qPmVlanPortGvrpLeaveEmptyTxCount Counter32,
      pmMIDot1qPmVlanPortGvrpLeaveEmptyRxCount Counter32,
      pmMIDot1qPmVlanPortGvrpEmptyTxCount Counter32,
      pmMIDot1qPmVlanPortGvrpEmptyRxCount Counter32,
      pmMIDot1qPmVlanPortGvrpLeaveAllTxCount Counter32,
      pmMIDot1qPmVlanPortGvrpLeaveAllRxCount Counter32,
      pmMIDot1qPmVlanPortGvrpDiscardCount Counter32
   } 
 
pmMIDot1qPmVlanPort OBJECT-TYPE 
   SYNTAX      Integer32 (1..65535) 
   MAX-ACCESS  not-accessible 
   STATUS      current 
   DESCRIPTION 
      "The port number of the port for which this entry applies." 
   ::= { pmMIDot1qPmVlanPortEntry 1 } 
 
pmMIDot1qPmVlanPortType OBJECT-TYPE 
   SYNTAX      INTEGER { 
                  accessPort (1), 
                  trunkPort (2), 
                  hybridPort (3),
                  hostPort (4), 
                  promiscuousPort (5)
               } 
   MAX-ACCESS  read-write 
   STATUS      current 
   DESCRIPTION 
      "The type of the port is by default hybrid port. 
       When configured as access port, the port can accept and send 
       only untagged frames.
       When configured as a trunk port, port is added as 
       member of all the existing Vlans and also for any new vlan
       created. 
       When configured as hybrid port, the port can send or accept both 
       tagged and untagged frames.  
       
       hostPort, promiscuousPort are types of port in PVLAN domain.
       Behaviour of host port varies based on the secondary vlan to which
       it is configured as member port.

       If a host port is a member port of an isolated VLAN, traffic from the 
       host port is sent only to the promiscuous port of the Private VLAN and 
       the trunk port.

       If a host port is a member port of the community VLAN, traffic from the 
       port can be sent only to other ports of the community VLAN , trunk port 
       and promiscuous port of the private VLAN.

       A host port can be associated with only one secondary vlan and with
       the associated primary vlan.

       The PVID of host port will be set the ID of the secondary vlan
       to which it belongs to.
       If a host port is member port of primary vlan, but is not member port 
       of any secondary vlan, then its PVID will be set to primary vlan id.

       Promiscuous ports should be configured as member port of primary vlan 
       and member port of all(some) secondary vlans associated with that 
       primary vlan.

       The PVID of promiscuous port will be set as the ID of the primary 
       vlan to which it belongs to.

       Host and  promiscuous ports should be configured as untagged members
       of primary/secondary vlans.

       When a access/hybrid port is configured as a member port of a
       primary/secondary vlan, it becomes a hostPort automatically."

   DEFVAL   { hybridPort } 
   ::= { pmMIDot1qPmVlanPortEntry 2 } 

pmMIDot1qPmVlanPortMacBasedClassification OBJECT-TYPE 
   SYNTAX      EnabledStatus
   MAX-ACCESS  read-write 
   STATUS      current 
   DESCRIPTION 
      "Object to expilicitly enable/disable the Mac based Classification 
      on port. This can be independently set without 
      any dependency in available configuration of
       pmMIDot1qPmVlanMacBasedOnAllPorts " 
   ::= { pmMIDot1qPmVlanPortEntry 3 } 

pmMIDot1qPmVlanPortPortProtoBasedClassification OBJECT-TYPE 
   SYNTAX      EnabledStatus
   MAX-ACCESS  read-write 
   STATUS      current 
   DESCRIPTION 
      "Object to expilicitly enable/disable the port and protocol
      Classification on port. This can be independently set without 
      any dependency in available configuration of
       pmMIDot1qPmVlanPortProtoBasedOnAllPorts " 
   ::= { pmMIDot1qPmVlanPortEntry 4 } 
 
pmMIDot1qPmVlanFilteringUtilityCriteria OBJECT-TYPE 
   SYNTAX      INTEGER { 
                  default  (1), 
                  enhanced (2)
               } 
   MAX-ACCESS  read-write 
   STATUS      current 
   DESCRIPTION 
      "Based on this object, learning on a port is decided.
      
      If default filtering utility Criteria is selected on a port, then
      learning of source mac from a received packet on that port will be
      done only if there is atleast on member port in that vlan.

      If enhanced filtering utility criteria is selected on a port,then
      learning of source mac from a received packet on that port will be
      done if the following are satisfied: 
      
      -    if at least one VLAN that uses the FID includes the reception
      Port and at least one other Port with a Port State of Learning or
      Forwarding in its member set, and:
       
       o The operPointToPointMAC parameter is false for the reception Port; or
       o Ingress to the VLAN is permitted through a third Port.
       
       The third port can, but is not required to, be in the member set."
   DEFVAL   { default } 
   ::= { pmMIDot1qPmVlanPortEntry 5 } 
 
pmMIDot1qPmVlanPortProtected  OBJECT-TYPE
   SYNTAX      TruthValue
   MAX-ACCESS  read-write
   STATUS      current
   DESCRIPTION
      "The Split Horizon property of the port. If set to true, frames that 
       are received on any other port, that has the same property set to true,
       will not be forwarded on this port."
   DEFVAL   { false }
   ::= { pmMIDot1qPmVlanPortEntry 6 }
 
pmMIDot1qPmVlanPortSubnetBasedClassification OBJECT-TYPE 
   SYNTAX      EnabledStatus
   MAX-ACCESS  read-write 
   STATUS      current 
   DESCRIPTION 
      "Object to expilicitly enable/disable the Subnet based Vlan Classification 
      on port. This can be independently set without any dependency in 
      available configuration of dot1qPmVlanSubnetBasedOnAllPorts. This
      object is not used in case of BCM chipsets." 
   ::= { pmMIDot1qPmVlanPortEntry 7 } 

pmMIDot1qPmVlanPortUnicastMacLearning OBJECT-TYPE
   SYNTAX      EnabledStatus
   MAX-ACCESS  read-write
   STATUS      current
   DESCRIPTION
      "A Truth value indicating the unicast MAC learning enabled/disabled
       status for this port. 
       When Unicast Mac Learning is disabled, 
       no unicast mac entry will be learnt on this port.
       When Mac Learning is enabled, unicast mac entries will be learnt on this 
       port. Configuration of this object will not get affected by the value
       configured for pmMIDot1qPmVlanGlobalMacLearningStatus "
   DEFVAL   { enabled }
   ::= { pmMIDot1qPmVlanPortEntry 8 }

pmMIDot1qPmVlanPortGvrpJoinEmptyTxCount OBJECT-TYPE
   SYNTAX      Counter32
   MAX-ACCESS  read-only
   STATUS      current
   DESCRIPTION
            " Number of Gvrp Join Empty packets transmitted by this port."
   ::= { pmMIDot1qPmVlanPortEntry 22 }

pmMIDot1qPmVlanPortGvrpJoinEmptyRxCount OBJECT-TYPE
   SYNTAX      Counter32
   MAX-ACCESS  read-only
   STATUS      current
   DESCRIPTION
            " Number of Gvrp Join Empty packets received on this port."
   ::= { pmMIDot1qPmVlanPortEntry 23 }

pmMIDot1qPmVlanPortGvrpJoinInTxCount OBJECT-TYPE
   SYNTAX      Counter32
   MAX-ACCESS  read-only
   STATUS      current
   DESCRIPTION
            " Number of Gvrp Join In packets transmitted by this port."
   ::= { pmMIDot1qPmVlanPortEntry 24 }

pmMIDot1qPmVlanPortGvrpJoinInRxCount OBJECT-TYPE
   SYNTAX      Counter32
   MAX-ACCESS  read-only
   STATUS      current
   DESCRIPTION
            " Number of Gvrp Join In packets received on this port."
   ::= { pmMIDot1qPmVlanPortEntry 25 }

pmMIDot1qPmVlanPortGvrpLeaveInTxCount OBJECT-TYPE
   SYNTAX      Counter32
   MAX-ACCESS  read-only
   STATUS      current
   DESCRIPTION
            " Number of Gvrp Leave In packets transmitted by this port."
   ::= { pmMIDot1qPmVlanPortEntry 26 }

pmMIDot1qPmVlanPortGvrpLeaveInRxCount OBJECT-TYPE
   SYNTAX      Counter32
   MAX-ACCESS  read-only
   STATUS      current
   DESCRIPTION
            " Number of Gvrp Leave In packets received on this port."
   ::= { pmMIDot1qPmVlanPortEntry 27 }

pmMIDot1qPmVlanPortGvrpLeaveEmptyTxCount OBJECT-TYPE
   SYNTAX      Counter32
   MAX-ACCESS  read-only
   STATUS      current
   DESCRIPTION
            " Number of Gvrp Leave Empty packets transmitted by this port."
   ::= { pmMIDot1qPmVlanPortEntry 28 }

pmMIDot1qPmVlanPortGvrpLeaveEmptyRxCount OBJECT-TYPE
   SYNTAX      Counter32
   MAX-ACCESS  read-only
   STATUS      current
   DESCRIPTION
            " Number of Gvrp Leave Empty packets received on this port."
   ::= { pmMIDot1qPmVlanPortEntry 29 }

pmMIDot1qPmVlanPortGvrpEmptyTxCount OBJECT-TYPE
   SYNTAX      Counter32
   MAX-ACCESS  read-only
   STATUS      current
   DESCRIPTION
            " Number of Gvrp Empty packets transmitted by this port."
   ::= { pmMIDot1qPmVlanPortEntry 30 }

pmMIDot1qPmVlanPortGvrpEmptyRxCount OBJECT-TYPE
   SYNTAX      Counter32
   MAX-ACCESS  read-only
   STATUS      current
   DESCRIPTION
            " Number of Gvrp Empty packets received on this port."
   ::= { pmMIDot1qPmVlanPortEntry 31 }

pmMIDot1qPmVlanPortGvrpLeaveAllTxCount OBJECT-TYPE
   SYNTAX      Counter32
   MAX-ACCESS  read-only
   STATUS      current
   DESCRIPTION
            " Number of Gvrp Leave All packets transmitted by this port."
   ::= { pmMIDot1qPmVlanPortEntry 32 }

pmMIDot1qPmVlanPortGvrpLeaveAllRxCount OBJECT-TYPE
   SYNTAX      Counter32
   MAX-ACCESS  read-only
   STATUS      current
   DESCRIPTION
            " Number of Gvrp Leave All packets received on this port."
   ::= { pmMIDot1qPmVlanPortEntry 33 }

pmMIDot1qPmVlanPortGvrpDiscardCount OBJECT-TYPE
   SYNTAX      Counter32
   MAX-ACCESS  read-only
   STATUS      current
   DESCRIPTION
            " Number of Gvrp packets discarded in this port."
   ::= { pmMIDot1qPmVlanPortEntry 34 }

-- ------------------------------------------------------------------------- 
-- Pm Vlan Vlan-Fid Map Table 
-- ------------------------------------------------------------------------- 
 
pmMIDot1qPmVlanFidMapTable OBJECT-TYPE 
   SYNTAX      SEQUENCE OF PmMIDot1qPmVlanFidMapEntry 
   MAX-ACCESS  not-accessible 
   STATUS      current 
   DESCRIPTION 
      "This table contains information about the Filtering database 
      identifier (FID) used by vlan's to make forwarding decisions. Vlan's 
      can be mapped to use the same FID to share filtering information among 
      them. This will cause the mapped vlan's to operate in shared vlan 
      learning (SVL) mode. Vlan's mapped to a unique FID will operate in 
      independent vlan learning mode (IVL). A SET operation on this table is 
      allowed only when pmMIDot1qPmVlanLearningMode is hybrid. By 
      default all vlan's will be mapped to the FID equal to their vlan id 
      when pmMIDot1qPmVlanHybridTypeDefault is IVL. If the value of 
      pmMIDot1qPmVlanHybridTypeDefault is SVL all vlan's are mapped to 
      filtering database id 1. This table maintains context ID as one more 
      index to support Multiple Instances."

   ::= { pmMIDot1qPmVlan 5 } 
 
pmMIDot1qPmVlanFidMapEntry OBJECT-TYPE 
   SYNTAX      PmMIDot1qPmVlanFidMapEntry 
   MAX-ACCESS  not-accessible 
   STATUS      current 
   DESCRIPTION 
      "Entry mapping VlanId to Filtering database id."
   INDEX { pmMIDot1qPmVlanContextId, pmMIDot1qPmVlanIndex } 
   ::= { pmMIDot1qPmVlanFidMapTable 1 } 
    
PmMIDot1qPmVlanFidMapEntry ::= 
   SEQUENCE { 
      pmMIDot1qPmVlanIndex Unsigned32,
      pmMIDot1qPmVlanFid Unsigned32 
   } 
   
 pmMIDot1qPmVlanIndex OBJECT-TYPE
    SYNTAX      Unsigned32 (1..4094)
    MAX-ACCESS  read-only
    STATUS      current
    DESCRIPTION
        "VLAN ID for which filtering database information is available."
    ::= { pmMIDot1qPmVlanFidMapEntry 1 }

pmMIDot1qPmVlanCounterTable OBJECT-TYPE
   SYNTAX      SEQUENCE OF PmMIDot1qPmVlanCounterEntry
   MAX-ACCESS  not-accessible
   STATUS      current
   DESCRIPTION
             "The table contains the statistics on a per VLAN basis.
              It contains number of unicast, broadcast and unknown unicast
              packets flooded per VLAN."
   ::= { pmMIDot1qPmVlan 6 }

pmMIDot1qPmVlanCounterEntry OBJECT-TYPE
   SYNTAX      PmMIDot1qPmVlanCounterEntry
   MAX-ACCESS  not-accessible
   STATUS      current
   DESCRIPTION
              "The entry contains the VLAN statistics"
   INDEX { pmMIDot1qPmVlanContextId, pmMIDot1qPmVlanIndex }
   ::= { pmMIDot1qPmVlanCounterTable 1 }

PmMIDot1qPmVlanCounterEntry ::=
   SEQUENCE {
             pmMIDot1qPmVlanCounterRxUcast         Counter32,
             pmMIDot1qPmVlanCounterRxMcastBcast    Counter32,
             pmMIDot1qPmVlanCounterTxUnknUcast     Counter32,
             pmMIDot1qPmVlanCounterTxUcast         Counter32,
             pmMIDot1qPmVlanCounterTxBcast         Counter32,
             pmMIDot1qPmVlanCounterStatus          EnabledStatus
            }

pmMIDot1qPmVlanCounterRxUcast OBJECT-TYPE
   SYNTAX      Counter32
   MAX-ACCESS  read-only
   STATUS      current
   DESCRIPTION
            " Number of unicast packets received in this VLAN."
   ::= { pmMIDot1qPmVlanCounterEntry 1 }

pmMIDot1qPmVlanCounterRxMcastBcast OBJECT-TYPE
   SYNTAX      Counter32
   MAX-ACCESS  read-only
   STATUS      current
   DESCRIPTION
            " Number of multicast/broadcast packets received in this VLAN."
   ::= { pmMIDot1qPmVlanCounterEntry 2 }

pmMIDot1qPmVlanCounterTxUnknUcast OBJECT-TYPE
   SYNTAX      Counter32
   MAX-ACCESS  read-only
   STATUS      current
   DESCRIPTION
             " Number of unknown unicast packets flooded in this VLAN."
   ::= { pmMIDot1qPmVlanCounterEntry 3 }

pmMIDot1qPmVlanCounterTxUcast OBJECT-TYPE
   SYNTAX      Counter32
   MAX-ACCESS  read-only
   STATUS      current
   DESCRIPTION
            " Number of known unicast packets forwarded in this VLAN."
   ::= { pmMIDot1qPmVlanCounterEntry 4 }

pmMIDot1qPmVlanCounterTxBcast OBJECT-TYPE
   SYNTAX      Counter32
   MAX-ACCESS  read-only
   STATUS      current
   DESCRIPTION
            " Number of broadcast packets forwarded in this VLAN."
   ::= { pmMIDot1qPmVlanCounterEntry 5 }

pmMIDot1qPmVlanCounterStatus OBJECT-TYPE
   SYNTAX      EnabledStatus
   MAX-ACCESS  read-write
   STATUS      current
   DESCRIPTION
      "A Truth value indicating the statistics collection is enabled/disabled
       for this vlan.

       When statistics collection is set to disabled, Vlan stops collecting
       statistics on this specific vlan.
       When statistics collection is set to enabled, Vlan start collecting
       statistics on this specific vlan"
   DEFVAL   { disabled }       
   ::= {pmMIDot1qPmVlanCounterEntry 6 }

-- -------------------------------------------------------------
-- pmDot1qTpFdbTable
-- -------------------------------------------------------------

pmMIDot1qPmVlanTpFdbTable OBJECT-TYPE
    SYNTAX      SEQUENCE OF PmMIDot1qPmVlanTpFdbEntry
    MAX-ACCESS  not-accessible
    STATUS      current
    DESCRIPTION
        "A table that contains information about unicast entries
        for which the device has forwarding and/or filtering
        information.  This information is used by the
        transparent bridging function in determining how to
        propagate a received frame. This table maintains context ID
        as one more index to support Multiple Instances."
    REFERENCE
        "IEEE 802.1Q/D11 Section 12.7.7"
    ::= { pmMIDot1qPmVlan 9 }

pmMIDot1qPmVlanTpFdbEntry OBJECT-TYPE
    SYNTAX      PmMIDot1qPmVlanTpFdbEntry
    MAX-ACCESS  not-accessible
    STATUS      current
    DESCRIPTION
        "Information about a specific unicast MAC address for
        which the device has some forwarding and/or filtering
        information."
    AUGMENTS { pmDot1qTpFdbEntry }
    ::= { pmMIDot1qPmVlanTpFdbTable 1 }

PmMIDot1qPmVlanTpFdbEntry ::=
    SEQUENCE {
        pmMIDot1qPmVlanOldTpFdbPort
            Integer32,
        pmMIDot1qPmConnectionIdentifier
            MacAddress
    }

pmMIDot1qPmConnectionIdentifier OBJECT-TYPE
    SYNTAX      MacAddress
    MAX-ACCESS  read-only
    STATUS      current
    DESCRIPTION
         "This object is to associate the backbone MAC address of the peer 
         backbone edge brige with customer Mac addresses that can be reached 
         through the peer backbone edge bridge."
    ::= { pmMIDot1qPmVlanTpFdbEntry 2 }

-- -------------------------------------------------------------
-- The Static (Destination-Address Filtering) Database
-- -------------------------------------------------------------

pmMIDot1qPmStaticUnicastExtnTable OBJECT-TYPE
    SYNTAX      SEQUENCE OF PmMIDot1qPmStaticUnicastExtnEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only. This table maintains context ID as
    one more index to support Multiple Instances."
    REFERENCE
        "IEEE 802.1Q/D11 Section 12.7.7,
        ISO/IEC 15802-3 Section 7.9.1"
    ::= { pmMIDot1qPmVlan 12 }

pmMIDot1qPmStaticUnicastExtnEntry OBJECT-TYPE
    SYNTAX      PmMIDot1qPmStaticUnicastExtnEntry
    MAX-ACCESS  not-accessible
    STATUS      current
    DESCRIPTION
        "Filtering information configured into the device by
        (local or network) management specifying the set of
        ports to which frames received from a specific port and
        containing a specific unicast destination address are
        allowed to be forwarded."
    AUGMENTS { pmDot1qStaticUnicastEntry }
    ::= { pmMIDot1qPmStaticUnicastExtnTable 1 }

PmMIDot1qPmStaticUnicastExtnEntry ::=
    SEQUENCE {
        pmMIDot1qPmStaticConnectionIdentifier
            MacAddress
    }

pmMIDot1qPmStaticConnectionIdentifier OBJECT-TYPE
    SYNTAX      MacAddress
    MAX-ACCESS  read-write
    STATUS      current
    DESCRIPTION
         "This object is to associate the backbone MAC address of the 
         peer backbone edge bridge with customer Mac addresses that 
         can be reached through the peer backbone edge bridge."
    ::= { pmMIDot1qPmStaticUnicastExtnEntry 1 }

-- ------------------------------------------------------------------------- 
-- Pm Vlan Subnet Map Table 
-- ------------------------------------------------------------------------- 

pmMIDot1qPmVlanSwStatsEnabled OBJECT-TYPE
   SYNTAX      TruthValue 
   MAX-ACCESS  read-write 
   STATUS      current 
   DESCRIPTION 
   "If set to 'true', statistics collection will be done and stored in 
    software. This object can be set to 'true' only if the data switching
    is done by software.
    If set to 'false', the statistics collection will be done by the 
    hardware and will not be stored in software.
    If data switching is done by software, then the default value of this
    object will be 'true'. Otherwise, the default value will be 'false'.
    - It is recommended to configure this object before doing any port
    to virtual context mapping in the system."

   ::= { pmMIDot1qPmVlan 14 }

 -- pmMIDot1qPmVlanTunnelConfig group 
 
pmMIDot1qPmVlanTunnelConfigTable OBJECT-TYPE
   SYNTAX       SEQUENCE OF PmMIDot1qPmVlanTunnelConfigEntry
   MAX-ACCESS   not-accessible
   STATUS      deprecated
   DESCRIPTION
      "List of per virtual context Vlan Tunnel config parameters."
   ::= { pmMIDot1qPmVlanTunnelConfig 1 }

pmMIDot1qPmVlanTunnelConfigEntry OBJECT-TYPE
   SYNTAX       PmMIDot1qPmVlanTunnelConfigEntry
   MAX-ACCESS   not-accessible
   STATUS      deprecated
   DESCRIPTION
      "Per virtual context Vlan Tunnel config parameters.

      "
      
   INDEX { pmMIDot1qPmVlanContextId }
   ::= { pmMIDot1qPmVlanTunnelConfigTable 1 }

PmMIDot1qPmVlanTunnelConfigEntry ::=
   SEQUENCE {
       pmMIDot1qPmVlanBridgeMode
           INTEGER,
       pmMIDot1qPmVlanTunnelBpduPri
           Integer32
   }

pmMIDot1qPmVlanBridgeMode OBJECT-TYPE
   SYNTAX      INTEGER {
                  customerBridge (1),
                  providerBridge (2),
                  providerCoreBridge (3),
                  providerEdgeBridge (4),
                  invalidBridgeMode  (5)
               }
   MAX-ACCESS  read-write
   STATUS      deprecated
   DESCRIPTION
      
      "This object indicates the Bridge mode of the switch.
      
      Setting this to 'customerBridge' means that the switch will operate 
      as a 802.1Q VLAN Bridge.

      Setting this to 'providerBridge' means that the Bridge will operate as 
      a normal Q-in-Q Bridge.

      Setting this to 'providerCoreBridge' means that the switch will operate 
      as a 802.1ad compliant provider bridge with only S-VLAN component.

      Setting this to 'providerEdgeBridge' means that the switch will operate 
      as a 802.1ad provider edge bridge with S-VLAN component and atleast 
      one C-VLAN component.
      
      For changing the bridge mode, GARP and STP modules should be shutdown."

   ::= { pmMIDot1qPmVlanTunnelConfigEntry 1 } 


-- The Arp Configuration Table

    pmMIArpTable OBJECT-TYPE
    SYNTAX SEQUENCE OF PmMIArpEntry
    MAX-ACCESS not-accessible
    STATUS     current
    DESCRIPTION
        "Table to store the virtual router specific arp configurations"
    ::= {priavteMiArp 1}

    pmMIArpEntry OBJECT-TYPE
    SYNTAX     PmMIArpEntry
    MAX-ACCESS not-accessible
    STATUS     current
    DESCRIPTION
        "Each entry has arp configuration information for the Virtual router"
    INDEX { pmMIStdIpContextId }
    ::= {pmMIArpTable 1}

    PmMIArpEntry ::= SEQUENCE {
        pmMIArpCacheTimeout        Integer32,
        pmMIArpCachePendTime       Integer32,
        pmMIArpMaxRetries          Integer32,
        pmMIArpPendingEntryCount   Integer32,
        pmMIArpCacheEntryCount     Integer32
    }

    pmMIArpCacheTimeout OBJECT-TYPE
    SYNTAX     Integer32 (30..86400)
    MAX-ACCESS read-write
    STATUS     current
    DESCRIPTION
        "Time after which the entry in cache is deleted"
    DEFVAL {7200}
    ::= {pmMIArpEntry 1}

    pmMIArpMaxRetries OBJECT-TYPE
    SYNTAX     Integer32 (2..10)
    MAX-ACCESS read-write
    STATUS     current
    DESCRIPTION
        "Maximum number of retry attemporarilyts before aborting resolving."
    DEFVAL { 3 }
    ::= {pmMIArpEntry 3}

-- ------------------------------------------------------------  
-- groups in the MIB  
-- ------------------------------------------------------------ 

      pmPnacPaeSystem         OBJECT IDENTIFIER ::= { privatePnac 1 } 
      pmPnacPaeAuthenticator  OBJECT IDENTIFIER ::= { privatePnac 2 } 
      pmPnacAuthServer        OBJECT IDENTIFIER ::= { privatePnac 3 }

-- ------------------------------------------------------------------ 
 
 
-- ------------------------------------------------------------------ 
-- The Pae System Group 
-- ------------------------------------------------------------------ 

      pmPnacSystemControl OBJECT-TYPE 
          SYNTAX      INTEGER { 
                        start (1),    
                        shutdown (2)  
                     } 
          MAX-ACCESS  read-write 
          STATUS      current 
          DESCRIPTION  
               "Starts or shutdowns PNAC Module in the system. 
 
                When set as 'start',resources required by PNAC 
                module are allocated & PNAC module starts running. 
 
                When shutdown, all resources used by PNAC module 
                will be released to the system." 
           ::= { pmPnacPaeSystem 1 } 

      pmPnacAuthenticServer OBJECT-TYPE 
          SYNTAX      AuthenticMethod 
          MAX-ACCESS  read-write 
          STATUS      current 
          DESCRIPTION 
              "This object is used to configure for the choice of  
              local or remote Authentication Server to be used by 
              the Authenticator for its authentication services." 
           ::= { pmPnacPaeSystem 3 } 
            
      pmPnacNasId OBJECT-TYPE 
          SYNTAX      DisplayString(SIZE(0..16)) 
          MAX-ACCESS  read-write 
          STATUS      current 
          DESCRIPTION  
              "This object is the Network Access Server Identifier 
              to be presented before the remote Authentication 
              Server." 
          ::= { pmPnacPaeSystem 4 } 
 
 
-- Pae Port Table extensions 
 
 
      pmPnacPaePortTable OBJECT-TYPE 
          SYNTAX      SEQUENCE OF PmPnacPaePortEntry 
          MAX-ACCESS  not-accessible 
          STATUS      current 
          DESCRIPTION 
             "A table of system level information for each port 
             supported by the PNAC. An entry appears in this 
             table for each port of this system. This table is an 
             extension of dot1xPaePortTable of IEEE 802.1x MIB." 
          ::= { pmPnacPaeSystem 5 } 
 
 
      pmPnacPaePortEntry OBJECT-TYPE 
          SYNTAX      PmPnacPaePortEntry 
          MAX-ACCESS  not-accessible 
          STATUS      current 
          DESCRIPTION 
             "Configuration as port based or MAC based authentication 
             and Supplicant count on a port. Index to this table is 
             same as that of the dot1xPaePortTable, which is the 
             InterfaceIndex." 
          INDEX { pmPnacPaePortNumber } 
          ::= { pmPnacPaePortTable 1 } 
 
 
      PmPnacPaePortEntry ::= 
          SEQUENCE { 
             pmPnacPaePortNumber 
                 InterfaceIndex, 
             pmPnacPaePortAuthMode 
                 INTEGER,
             pmPnacPaePortStatus
                 INTEGER
          } 
 
 
      pmPnacPaePortNumber OBJECT-TYPE 
           SYNTAX      InterfaceIndex 
           MAX-ACCESS  not-accessible 
           STATUS      current 
           DESCRIPTION 
               "The port number associated with this port." 
           ::= { pmPnacPaePortEntry 1 } 
 
 
      pmPnacPaePortAuthMode OBJECT-TYPE 
           SYNTAX      INTEGER { 
                           portBased(1), 
                           macBased(2) 
                       } 
           MAX-ACCESS  read-write 
           STATUS      current 
           DESCRIPTION 
               "Configuration of the port, for Port Based  
               Authentication or MAC Based Authentication." 
           ::= { pmPnacPaePortEntry 2 } 
 
      pmPnacPaePortStatus OBJECT-TYPE 
           SYNTAX      PaeControlledPortStatus 
           MAX-ACCESS  read-only 
           STATUS      current 
           DESCRIPTION 
               "The value of the combined Port status." 
           ::= { pmPnacPaePortEntry 6 }
      
-- ------------------------------------------------------------------ 
-- The Pae System Group again 
-- ------------------------------------------------------------------ 
      pmPnacModuleOperStatus OBJECT-TYPE 
            SYNTAX       INTEGER { 
                             enabled(1),  
                             disabled(2)   
                          } 
            MAX-ACCESS    read-only 
            STATUS        current 
            DESCRIPTION 
            "This read only objects gives actual status of the PNAC Module 
            (Operational status of module). When Module is enabled 
            PNAC protocol starts functioning. When the module is disabled 
            all the dynamically allocated memory will be freed and PNAC 
            protocol stops functioning."
            ::= { pmPnacPaeSystem 6 } 

      pmPnacRemoteAuthServerType OBJECT-TYPE 
          SYNTAX      RemoteAuthServerType 
          MAX-ACCESS  read-write 
          STATUS      current 
          DESCRIPTION 
              "This object is used by the Authenticator for its 
              authentication services, to configure the choice of  
              RADIUS or TACACS+ remote authentication servers when
              the authentication method is through a remote server,
              that is, this object can be configured only if 
              pmPnacAuthenticServer is set to remoteServer." 
        DEFVAL  { 1 } 
        ::= { pmPnacPaeSystem 7 }
        
-- ------------------------------------------------------------------ 
-- The Pae Authenticator Group  
-- ------------------------------------------------------------------ 
 
-- Authenticator Session Table 
 
      pmPnacAuthSessionTable OBJECT-TYPE 
          SYNTAX      SEQUENCE OF PmPnacAuthSessionEntry 
          MAX-ACCESS  not-accessible 
          STATUS      current 
          DESCRIPTION 
             "This table contains authentication session information 
             associated with each Supplicant while Authenticator 
             operates in MAC based authentication mode." 
          ::= { pmPnacPaeAuthenticator 1 } 
 
 
      pmPnacAuthSessionEntry OBJECT-TYPE 
          SYNTAX      PmPnacAuthSessionEntry 
          MAX-ACCESS  not-accessible 
          STATUS      current 
          DESCRIPTION 
             "Supplicant's MAC address and session ID, states of 
             Authenticator state machine and Backend state machine 
             for the session." 
          INDEX { pmPnacAuthSessionSuppAddress } 
          ::= { pmPnacAuthSessionTable 1 } 
 
 
      PmPnacAuthSessionEntry ::= 
          SEQUENCE { 
             pmPnacAuthSessionSuppAddress 
                 MacAddress, 
             pmPnacAuthSessionIdentifier 
                 Integer32, 
             pmPnacAuthSessionAuthPaeState 
                 INTEGER,
             pmPnacAuthSessionPortStatus 
                 INTEGER, 
             pmPnacAuthSessionPortNumber 
                 InterfaceIndex
          } 
 
      pmPnacAuthSessionSuppAddress OBJECT-TYPE 
           SYNTAX      MacAddress 
           MAX-ACCESS  not-accessible 
           STATUS      current 
           DESCRIPTION 
               "MAC address of the supplicant for this session." 
           ::= { pmPnacAuthSessionEntry 1 } 
 
 
      pmPnacAuthSessionIdentifier OBJECT-TYPE 
           SYNTAX      Integer32 
           MAX-ACCESS  read-only 
           STATUS      current 
           DESCRIPTION 
               "Session identifier of the supplicant for this  
               session." 
           ::= { pmPnacAuthSessionEntry 2 } 
 
 
      pmPnacAuthSessionAuthPaeState OBJECT-TYPE 
           SYNTAX      INTEGER { 
                           initialize(1), 
                           disconnected(2), 
                           connecting(3), 
                           authenticating(4), 
                           authenticated(5), 
                           aborting(6), 
                           held(7), 
                           forceAuth(8), 
                           forceUnauth(9) 
                       } 
           MAX-ACCESS  read-only 
           STATUS      current 
           DESCRIPTION 
               "Authenticator state machine's state for this  
               session." 
           ::= { pmPnacAuthSessionEntry 3 } 
  
 
      pmPnacAuthSessionPortStatus OBJECT-TYPE 
           SYNTAX      PaeControlledPortStatus 
           MAX-ACCESS  read-only 
           STATUS      current 
           DESCRIPTION 
               "The current value of the controlled Port status 
               parameter for this session." 
           ::= { pmPnacAuthSessionEntry 5 } 
 
 
      pmPnacAuthSessionPortNumber OBJECT-TYPE 
           SYNTAX      InterfaceIndex 
           MAX-ACCESS  read-only 
           STATUS      current 
           DESCRIPTION 
               "The Port in which this session is proceeding." 
           ::= { pmPnacAuthSessionEntry 6 } 


-- Authenticator Session Statistics Table 
 
      pmPnacAuthSessionStatsTable OBJECT-TYPE 
          SYNTAX      SEQUENCE OF PmPnacAuthSessionStatsEntry 
          MAX-ACCESS  not-accessible 
          STATUS      current 
          DESCRIPTION 
             "This table contains the session statistics  
             for the Authenticator PAE associated with each  
             Supplicant,while Authenticator operates in  MAC 
             based authentication mode." 
          ::= { pmPnacPaeAuthenticator 2 } 
 
 
      pmPnacAuthSessionStatsEntry OBJECT-TYPE 
          SYNTAX      PmPnacAuthSessionStatsEntry 
          MAX-ACCESS  not-accessible 
          STATUS      current 
          DESCRIPTION 
             "The session statistics information for an 
             Authenticator PAE. This shows the current values being 
             collected for each session that is still in progress, 
             or the final values for the last valid session on each 
             port where there is no session currently active." 
          INDEX { pmPnacAuthSessionSuppAddress } 
          ::= { pmPnacAuthSessionStatsTable 1 } 
 
 
      PmPnacAuthSessionStatsEntry ::= 
          SEQUENCE {
             pmPnacAuthSessionFramesRx 
                 Counter32, 
             pmPnacAuthSessionFramesTx 
                 Counter32, 
             pmPnacAuthSessionId 
                 SnmpAdminString, 
             pmPnacAuthSessionTerminateCause 
                 INTEGER, 
             pmPnacAuthSessionUserName 
                 SnmpAdminString 
          } 

      pmPnacAuthSessionFramesRx OBJECT-TYPE 
           SYNTAX      Counter32 
           MAX-ACCESS  read-only 
           STATUS      current 
           DESCRIPTION 
               "Counts number of session frames received." 
           ::= { pmPnacAuthSessionStatsEntry 3 } 
 
 
      pmPnacAuthSessionFramesTx OBJECT-TYPE 
           SYNTAX      Counter32 
           MAX-ACCESS  read-only 
           STATUS      current 
           DESCRIPTION 
               "Counts number of session frames transmitted." 
           ::= { pmPnacAuthSessionStatsEntry 4 } 
 
 
      pmPnacAuthSessionId OBJECT-TYPE 
           SYNTAX      SnmpAdminString 
           MAX-ACCESS  read-only 
           STATUS      current 
           DESCRIPTION 
               "A unique Session identifier, in the form of a 
               printable ASCII string of at least three characters." 
           ::= { pmPnacAuthSessionStatsEntry 5 } 


      pmPnacAuthSessionTerminateCause OBJECT-TYPE 
           SYNTAX      INTEGER { 
                           supplicantLogoff(1), 
                           portFailure(2), 
                           supplicantRestart(3), 
                           reauthFailed(4), 
                           authControlForceUnauth(5), 
                           portReInit(6), 
                           portAdminDisabled(7), 
                           notTerminatedYet(999) 
                       } 
           MAX-ACCESS  read-only 
           STATUS      current 
           DESCRIPTION 
               "Reason for the session termination." 
           ::= { pmPnacAuthSessionStatsEntry 8 } 
 
 
      pmPnacAuthSessionUserName OBJECT-TYPE 
           SYNTAX      SnmpAdminString 
           MAX-ACCESS  read-only 
           STATUS      current 
           DESCRIPTION 
               "User name representing the identity of the  
               Supplicant PAE." 
           ::= { pmPnacAuthSessionStatsEntry 9 } 
 
-- ------------------------------------------------------------------ 
-- The Authentication Server Group  
-- ------------------------------------------------------------------ 
 
-- PNAC Local Authentication Server User Configuration Table 
 
      pmPnacASUserConfigTable OBJECT-TYPE 
          SYNTAX      SEQUENCE OF PmPnacASUserConfigEntry 
          MAX-ACCESS  not-accessible 
          STATUS      current 
          DESCRIPTION 
             "This table contains authentication related User 
             configuration information maintained by PNAC 
             local Authentication Server." 
          ::= { pmPnacAuthServer 1 } 
 
 
      pmPnacASUserConfigEntry OBJECT-TYPE 
          SYNTAX      PmPnacASUserConfigEntry 
          MAX-ACCESS  not-accessible 
          STATUS      current 
          DESCRIPTION 
             "Each entry contains User name, Password, Authentication  
             protocol used, Authenticated session timeout and Access 
             ports list of the User seeking authentication." 
          INDEX { pmPnacASUserConfigUserName } 
          ::= { pmPnacASUserConfigTable 1 } 
 
 
      PmPnacASUserConfigEntry ::= 
          SEQUENCE { 
             pmPnacASUserConfigUserName 
                 OCTET STRING,
             pmPnacASUserConfigAuthProtocol 
                 Unsigned32, 
             pmPnacASUserConfigAuthTimeout 
                 Unsigned32, 
             pmPnacASUserConfigPortList 
                 PortList, 
             pmPnacASUserConfigPermission 
                 PermissionType, 
             pmPnacASUserConfigRowStatus 
                 RowStatus 
          } 
 
 
      pmPnacASUserConfigUserName OBJECT-TYPE 
           SYNTAX      OCTET STRING (SIZE(0..115))
           MAX-ACCESS  not-accessible 
           STATUS      current 
           DESCRIPTION 
               "Identity of the User seeking authentication. A string 
               of not more than 20 printable characters." 
           ::= { pmPnacASUserConfigEntry 1 } 


      pmPnacASUserConfigAuthProtocol OBJECT-TYPE 
           SYNTAX      Unsigned32 
           MAX-ACCESS  read-only 
           STATUS      current 
           DESCRIPTION 
               "The Authentication protocol supported for the User." 
           ::= { pmPnacASUserConfigEntry 3 } 
 
  
      pmPnacASUserConfigAuthTimeout OBJECT-TYPE 
           SYNTAX      Unsigned32 
           MAX-ACCESS  read-write 
           STATUS      current 
           DESCRIPTION 
               "The time in seconds after which the Authentication  
               offerred to the User ceases. Maximum value of the 
               object can be 7200 seconds. When the object value 
               is 0, the ReAuthPeriod of the Authenticator port is 
               used by Authenticator." 
           ::= { pmPnacASUserConfigEntry 4 } 
 
 
      pmPnacASUserConfigPortList OBJECT-TYPE 
            SYNTAX     PortList 
            MAX-ACCESS read-write 
            STATUS     current 
            DESCRIPTION 
                "The complete set of ports of Authenticator to 
                which the User is allowed or denied access, on the 
                basis of setting of 'pmPnacASUserConfigPermission'  
                object." 
            ::= { pmPnacASUserConfigEntry 5 } 
 
 
       pmPnacASUserConfigPermission OBJECT-TYPE 
            SYNTAX      PermissionType 
            MAX-ACCESS  read-write 
            STATUS      current 
            DESCRIPTION 
                "For the set of ports indicated by  
                'pmPnacASUserConfigPortList' object, the User is 
                allowed access when this object is set 'allow' and  
                is denied access when this object is set 'deny'." 
            ::= { pmPnacASUserConfigEntry 6 } 
      
 
      pmPnacASUserConfigRowStatus OBJECT-TYPE 
           SYNTAX      RowStatus 
           MAX-ACCESS  read-create 
           STATUS      current 
           DESCRIPTION 
               "The Row status of this entry." 
           ::= { pmPnacASUserConfigEntry 7 } 

   issExt OBJECT IDENTIFIER ::= { privateIssExt 8}
-- ----------------------------------------------------------------- -- 
-- groups in the MIB
-- ----------------------------------------------------------------- -- 

-- ---------------------------------------------------------------- --
   issExtL2Filter              OBJECT IDENTIFIER ::= { issExt 2 }
   issExtL3Filter              OBJECT IDENTIFIER ::= { issExt 3 }
-- ---------------------------------------------------------------- --

-- ------------------------------------------------------------------ 
-- L2 Filter Group --------------------------------------------------

issExtL2FilterTable OBJECT-TYPE 

   SYNTAX      SEQUENCE OF IssExtL2FilterEntry
   MAX-ACCESS  not-accessible 
   STATUS      current 
   DESCRIPTION 
       "A table to configure L2 filter rules in the system."
   ::= { issExtL2Filter 1 }

issExtL2FilterEntry OBJECT-TYPE 
   SYNTAX      IssExtL2FilterEntry
   MAX-ACCESS  not-accessible 
   STATUS      current 
   DESCRIPTION 
       "Each entry in this table is a L2 filter rule.
   
       Index to the table is the L2 filter number."
   INDEX { issExtL2FilterNo}
   ::= { issExtL2FilterTable 1 }
   
IssExtL2FilterEntry ::= 
   SEQUENCE { 
      issExtL2FilterNo 
         Integer32, 
      issExtL2FilterPriority 
         Integer32, 
      issExtL2FilterEtherType
         Integer32, 
      issExtL2FilterProtocolType 
         Unsigned32, 
      issExtL2FilterDstMacAddr 
         MacAddress, 
      issExtL2FilterSrcMacAddr 
         MacAddress, 
      issExtL2FilterVlanId 
         Integer32,
      issExtL2FilterInPortList 
         PortList,
      issExtL2FilterAction 
         INTEGER,
      issExtL2FilterStatus
         RowStatus
  }

issExtL2FilterNo OBJECT-TYPE 
   SYNTAX      Integer32 (1..65535)
   MAX-ACCESS  not-accessible 
   STATUS      current 
   DESCRIPTION 
      "L2 Filter rule number."
   ::= { issExtL2FilterEntry 1 }
    
issExtL2FilterPriority OBJECT-TYPE 
   SYNTAX      Integer32 (1..255)
   MAX-ACCESS  read-write 
   STATUS      current 
   DESCRIPTION 
      "The priority of the L2 filter can be used to decide which filter rule
       is applicable when 
          --> the packet matches with more than one filter rules
          --> All the filter rules result in 'allow'ing the packet

      Higher value of 'filter priority' implies a higher priority.

      Usage of 'L2FilterPriority' is implementation dependant."
   DEFVAL  { 1 }
   ::= { issExtL2FilterEntry 2 }

issExtL2FilterEtherType OBJECT-TYPE 
   SYNTAX      Integer32 (0..65535)
   MAX-ACCESS  read-write 
   STATUS      current 
   DESCRIPTION 
      "The value in the Type/Len field of a frame that will
      be matched to trigger this filter. The default value of
      this object is '0'. When this object is SET with the default
      value, frames are not matched for the value in the Type/Len
      field with the value set for this object."
   DEFVAL  { 0 }
   ::= { issExtL2FilterEntry 3 }

   
issExtL2FilterProtocolType OBJECT-TYPE 
   SYNTAX      Unsigned32 (0..65535) 
   MAX-ACCESS  read-write 
   STATUS      current 
   DESCRIPTION 
      "Specifies the non IP protocol type to be filtered.
       aarp | amber | dec-spanning | decnet-iv | 
       diagnostic | dsm |etype-6000 | etype-8042 | 
       lat | lavc-sca | mop-console | mop-dump | 
       msdos | mumps | netbios | vines-echo |
       vines-ip | xns-idp: A non-IP protocol.

      A value of '0' means, the filter is applicable for all protocols."
   DEFVAL  { 0 }
   ::= { issExtL2FilterEntry 4 }

issExtL2FilterDstMacAddr OBJECT-TYPE 
   SYNTAX      MacAddress
   MAX-ACCESS  read-write 
   STATUS      current 
   DESCRIPTION 
      "Destination MAC address to be matched with the packet. By Default, the
       Destination Mac Address will be zero which means dont care condition ie)
       any Dst Mac Address ."
   ::= { issExtL2FilterEntry 5 }

issExtL2FilterSrcMacAddr OBJECT-TYPE 
   SYNTAX      MacAddress
   MAX-ACCESS  read-write 
   STATUS      current 
   DESCRIPTION 
      "Source MAC address to be matched with the packet. By Default, the Source 
       Mac Address will be zero which means dont care condition ie) any Src Mac 
       address"
   ::= { issExtL2FilterEntry 6 }


issExtL2FilterVlanId OBJECT-TYPE 
   SYNTAX      Integer32 (0..4094)
   MAX-ACCESS  read-write 
   STATUS      current 
   DESCRIPTION 
      "Vlan Id to be filtered. In case of Provider bridges, This Vlan Id will
      be treated as customer Vlan Id. 
      A value of '0' means, this object is unused. Configuring this value is not
      allowed."
   DEFVAL  { 0 }
   ::= { issExtL2FilterEntry 7 }


issExtL2FilterInPortList OBJECT-TYPE 
   SYNTAX      PortList
   MAX-ACCESS  read-write 
   STATUS      current 
   DESCRIPTION 
      "Specifies the complete set of ports over which this filter is applied
       for packets ingress at ports in this list.
       If the In port list is '0', the filter rule is applicable for  the 
       incoming packets on all ports.
       Even though the issExtL2FilterInPortList is configured, It is applicable only
       if issExtL2FilterDirection is configured as 'in'.
       By default inport list is maintained as '0'." 
   ::= { issExtL2FilterEntry 8 }

issExtL2FilterAction OBJECT-TYPE 
   SYNTAX      INTEGER {
                  allow (1),
                  drop  (2)
               }
   MAX-ACCESS  read-write 
   STATUS      current 
   DESCRIPTION 
      "Specifies the action to be taken on the packet if the filter
      rule matches.
      If the action is 'allow', the packet will be forwarded according
      to the forwarding rules.
      If the action is 'drop', the packet will be discarded."
   DEFVAL  { allow } 
   ::= { issExtL2FilterEntry 9 }

issExtL2FilterStatus OBJECT-TYPE 
   SYNTAX      RowStatus
   MAX-ACCESS  read-create 
   STATUS      current 
   DESCRIPTION 
        "This object indicates the status of this entry. An entry is
        created in this table when this object is SET to 'createAndWait'.
        The entry in this table is used when the status of this object 
        is SET 'active'. The entry in this table is not used when this 
        object is SET 'notInService'. An entry created in this table is
        be deleted when this object is SET 'destroy'."
   ::= { issExtL2FilterEntry 11 }


-- ------------------------------------------------------------------ 
-- L3 Filter Group --------------------------------------------------

issExtL3FilterTable OBJECT-TYPE 
   SYNTAX      SEQUENCE OF IssExtL3FilterEntry
   MAX-ACCESS  not-accessible 
   STATUS      current 
   DESCRIPTION 
       " A table to configure L3 filter rules in the system.
       "
   ::= { issExtL3Filter 1 }

issExtL3FilterEntry OBJECT-TYPE 
   SYNTAX      IssExtL3FilterEntry
   MAX-ACCESS  not-accessible 
   STATUS      current 
   DESCRIPTION 
       " Each entry in this table is a L3 filter rule.
         Index to the table is L3 filter number. "
   INDEX { issExtL3FilterNo}
   ::= { issExtL3FilterTable 1 }
   
IssExtL3FilterEntry ::= 
   SEQUENCE { 
      issExtL3FilterNo 
         Integer32, 
      issExtL3FilterPriority 
         Integer32, 
      issExtL3FilterProtocol  
         Integer32, 
      issExtL3FilterMessageType 
         Integer32, 
      issExtL3FilterMessageCode 
         Integer32, 
      issExtL3FilterDstIpAddr 
         IpAddress, 
      issExtL3FilterSrcIpAddr 
         IpAddress, 
      issExtL3FilterDstIpAddrMask 
         IpAddress, 
      issExtL3FilterSrcIpAddrMask 
         IpAddress,
      issExtL3FilterMinDstProtPort
         Unsigned32, 
      issExtL3FilterMaxDstProtPort
         Unsigned32, 
      issExtL3FilterMinSrcProtPort
         Unsigned32, 
      issExtL3FilterMaxSrcProtPort
         Unsigned32, 
      issExtL3FilterInPortList 
         PortList,
      issExtL3FilterOutPortList 
         PortList, 
      issExtL3FilterAckBit
         INTEGER,
      issExtL3FilterRstBit
         INTEGER,
      issExtL3FilterTos
         Integer32,
      issExtL3FilterDscp
         Integer32,
      issExtL3FilterAction 
         INTEGER, 
      issExtL3FilterStatus
         RowStatus
  }

issExtL3FilterNo OBJECT-TYPE 
   SYNTAX      Integer32 (1..65535)
   MAX-ACCESS  not-accessible 
   STATUS      current 
   DESCRIPTION 
      "L3 Filter rule number."
   ::= { issExtL3FilterEntry 1 }
    
issExtL3FilterPriority OBJECT-TYPE 
   SYNTAX      Integer32 (1..255)
   MAX-ACCESS  read-write 
   STATUS      current 
   DESCRIPTION 
      "The priority of the filter can be used to decide which filter rule
       is applicable when 
          --> the packet matches with more than one filter rules
          --> All the filter rules result in 'allow'ing the packet
      Higher value of 'L3 filter priority' implies a higher priority.
      Usage of 'L3FilterPriority' is implementation dependant."
   DEFVAL  { 1 }
   ::= { issExtL3FilterEntry 2 }
   
issExtL3FilterProtocol OBJECT-TYPE 
   SYNTAX      Integer32 (0..255)
   MAX-ACCESS  read-write 
   STATUS      current 
   DESCRIPTION 
      " The type of protocol to be checked against the packet. The
      default value is 255. If the value is 255, it means that the
      protocol type can be anything and it will not be checked to 
      decide the action. "
   DEFVAL   { 255 }
   ::= { issExtL3FilterEntry 3 }

issExtL3FilterMessageType OBJECT-TYPE 
   SYNTAX      Integer32 (0..65535)
   MAX-ACCESS  read-write 
   STATUS      current 
   DESCRIPTION 
     " The message type to be checked against the packet. If the
      message type matches with the packet, then the packet will be
      dropped / allowed based on the action set in issExtL3FilterAction.
      The default value is 255. It means that message type is not
      configured and need not be checked.
      Generally the value zero is given as default. But here
      zero can be an ICMP Type value. Hence 255 is given as the
      default value. 
      Some ICMP message types are: 
           echoReply(0),
           destinationUnreachable(3),
           sourceQuench(4),
           redirect(5),
           echoRequest(8),
           timeExceeded(11),
           parameterProblem(12),
           timestampRequest(13),
           timestampReply(14),
           informationRequest(15),
           informationReply(16),
           addressMaskRequest(17),
           addressMaskReply (18),
           noICMPType(255)
      "
   DEFVAL  { 255 }
   ::= { issExtL3FilterEntry 4 }

issExtL3FilterMessageCode OBJECT-TYPE 
   SYNTAX      Integer32 (0..65535)
   MAX-ACCESS  read-write 
   STATUS      current 
   DESCRIPTION 
      " The message code to be checked against the packet. If the
      packet matches with the message code, then the packet will
      be dropped / allowed based on the action set in issExtL3FilterAction.
      The default value is 255. It means that message code is not 
      configured and need not be checked. Generally the value zero 
      will be given as default. But here, zero can be an ICMP Code 
      value. Hence 255 is given as the default value.
      Some ICMP message codes are :
           networkUnreachable(0),
           hostUnreachable(1),
           protocolUnreachable(2),
           portUnreachable(3),
           fragmentNeed(4),
           sourceRouteFail(5),
           destNetworkUnknown(6),
           destHostUnknown(7),
           srcHostIsolated(8),
           destNetworkAdminProhibited(9),
           destHostAdminProhibited(10),
           networkUnreachableTOS(11),
           hostUnreachableTOS(12),
           noICMPCode(255) 
      "
   DEFVAL   { 255 }
   ::= { issExtL3FilterEntry 5 }     

issExtL3FilterDstIpAddr OBJECT-TYPE 
   SYNTAX      IpAddress
   MAX-ACCESS  read-write 
   STATUS      current 
   DESCRIPTION 
      "Destination IP address to be matched with the packet.
      This object is valid only if the 'issExtFilterType' is 'l3filter'."
   DEFVAL  { '00000000'h }
   ::= { issExtL3FilterEntry 6 }

issExtL3FilterSrcIpAddr OBJECT-TYPE 
   SYNTAX      IpAddress
   MAX-ACCESS  read-write 
   STATUS      current 
   DESCRIPTION 
      "Source IP address to be matched with the packet.
      This object is valid only if the 'issExtFilterType' is 'l3filter'."
   DEFVAL  { '00000000'h }
   ::= { issExtL3FilterEntry 7 }

issExtL3FilterDstIpAddrMask OBJECT-TYPE 
   SYNTAX      IpAddress
   MAX-ACCESS  read-write 
   STATUS      current 
   DESCRIPTION 
      "The IP subnet mask for Destination IP address.
      This object is valid only if the 'issExtFilterType' is 'l3filter'."
   DEFVAL  { 'FFFFFFFF'h }
   ::= { issExtL3FilterEntry 8 }

issExtL3FilterSrcIpAddrMask OBJECT-TYPE 
   SYNTAX      IpAddress
   MAX-ACCESS  read-write 
   STATUS      current 
   DESCRIPTION 
      "The IP subnet mask for Source IP address.
      This object is valid only if the 'issExtFilterType' is 'l3filter'."
   DEFVAL  { 'FFFFFFFF'h }
   ::= { issExtL3FilterEntry 9 }

issExtL3FilterMinDstProtPort OBJECT-TYPE
   SYNTAX      Unsigned32
   MAX-ACCESS  read-write
   STATUS      current
   DESCRIPTION
      "The minimum port in the destination port range. Please note 
       these ports are the TCP / UDP ports."
   DEFVAL   { 0 }
   ::= { issExtL3FilterEntry 10 }

issExtL3FilterMaxDstProtPort OBJECT-TYPE
   SYNTAX      Unsigned32
   MAX-ACCESS  read-write
   STATUS      current
   DESCRIPTION
      "The maximum port in the destination port range. Please note 
       these ports are the TCP / UDP ports."
   DEFVAL   { 65535 }
   ::= { issExtL3FilterEntry 11 }

issExtL3FilterMinSrcProtPort OBJECT-TYPE
   SYNTAX      Unsigned32
   MAX-ACCESS  read-write
   STATUS      current
   DESCRIPTION
      "The minimum port in the source port range. Please note 
       these ports are the TCP / UDP ports."
   DEFVAL   { 0 }
   ::= { issExtL3FilterEntry 12 }

issExtL3FilterMaxSrcProtPort OBJECT-TYPE
   SYNTAX      Unsigned32
   MAX-ACCESS  read-write
   STATUS      current
   DESCRIPTION
      "The maximum port in the source port range. Please note 
       these ports are the TCP / UDP ports."
   DEFVAL   { 65535 }
   ::= { issExtL3FilterEntry 13 }

issExtL3FilterInPortList OBJECT-TYPE 
   SYNTAX      PortList
   MAX-ACCESS  read-write 
   STATUS      current 
   DESCRIPTION 
      "Specifies the complete set of ports over which if the packet arrives
      this filter rule will be applicable.
      If the incoming port list is '0', the filter rule is applicable for all the 
      incoming ports.
      By default inport list is maintained as '0'." 
   ::= { issExtL3FilterEntry 14 }

issExtL3FilterOutPortList OBJECT-TYPE 
   SYNTAX      PortList
   MAX-ACCESS  read-write 
   STATUS      current 
   DESCRIPTION 
      "Specifies the complete set of ports over which if the packet goes out, 
      this filter rule will be applicable.
      If the outgoing port list is '0', the filter rule is applicable for all the 
      outgoing packets in all ports.
      By default outport list is maintained as '0'." 
   ::= { issExtL3FilterEntry 15 }

issExtL3FilterAckBit        OBJECT-TYPE
    SYNTAX  INTEGER {
            establish(1),
                notEstablish(2),
                any(3)  
            }
    MAX-ACCESS  read-create
    STATUS      current
    DESCRIPTION
        " The TCP ACK bit to be checked against the packet. The default 
        value is 'any'(3). It means that ACK bit will not be checked 
                to decide the action. "
    DEFVAL  { any }
    ::= { issExtL3FilterEntry 16 }

issExtL3FilterRstBit     OBJECT-TYPE
    SYNTAX  INTEGER {
                  set(1),
              notSet(2),
              any(3)    
            }
    MAX-ACCESS  read-create
    STATUS      current
    DESCRIPTION
        " The TCP RST bit to be checked against the packet. The default 
        value is 'any'(3). It means that RST bit will not be checked to 
        decide the action. "
    DEFVAL  { any }
    ::= { issExtL3FilterEntry 17 }

issExtL3FilterTos       OBJECT-TYPE
    SYNTAX      Integer32 (-1..7)
    MAX-ACCESS  read-create
    STATUS      current
    DESCRIPTION
        " The IP TOS bit to be checked against the packet. This is a 
        single byte integer of which the last three bits (least 
      significant bits) indicate Delay, Throughput and Reliability 
      i.e 'uuuuudtr', u-unused, d-delay, t-throughput, r-reliability.
        For example '6' indicates low delay and high throughput. 
                A value of '-1' means, the Tos Field becomes dont care"
    DEFVAL  { -1 }
    ::= { issExtL3FilterEntry 18 }

issExtL3FilterDscp      OBJECT-TYPE
    SYNTAX      Integer32 (-1..63)
    MAX-ACCESS  read-create
    STATUS      current
    DESCRIPTION
        " The IP Dscp value to be checked against the packet. 
        A value of '-1' means, the Dscp Field becomes dont care."
    DEFVAL  { -1 }
    ::= { issExtL3FilterEntry 19 }
   
issExtL3FilterAction OBJECT-TYPE 
   SYNTAX      INTEGER {
                  allow (1),
                  drop  (2)
               }
   MAX-ACCESS  read-write 
   STATUS      current 
   DESCRIPTION 
      "Specifies the action to be taken on the packet if the filter
      rule matches.
      If the action is 'allow', the packet will be sent to the
      ports in 'out port list'. If the out port list is '0', 
      the port over which the packet is to be switched will be decided
      based on further processing on the packet.
      If the action is 'drop', the packet will be discarded."
   DEFVAL  { allow } 
   ::= { issExtL3FilterEntry 21 }

issExtL3FilterStatus OBJECT-TYPE 
   SYNTAX      RowStatus
   MAX-ACCESS  read-create 
   STATUS      current 
   DESCRIPTION 
        "This object indicates the status of this entry. An entry is
        created in this table when this object is SET to 'createAndWait'.
        The entry in this table is used when the status of this object 
        is SET 'active'. The entry in this table is not used when this 
        object is SET 'notInService'. An entry created in this table is
        be deleted when this object is SET 'destroy'."
   ::= { issExtL3FilterEntry 23 }
-- ------------------------------------------------------------
-- groups in the MIB 
-- ------------------------------------------------------------

      pmPoeSystem       OBJECT IDENTIFIER ::= { privatePoe 1 }

-- ------------------------------------------------------------------
-- The Poe System Group
-- ------------------------------------------------------------------
      pmPoeGlobalAdminStatus OBJECT-TYPE
           SYNTAX      INTEGER { start(1), shutdown(2)}
           MAX-ACCESS  read-write
           STATUS      current
           DESCRIPTION
               "Start or shutdown PoE Module in the system

                When set as 'start' PoE module initializes data structures and
                gets the power supply status.

                When shutdown, all resources used by PoE module
                will be released back to the system and also power will
                be shut on all PoE enabled ports"
           ::= { pmPoeSystem 1 }

      pmusrMgmtStats    OBJECT IDENTIFIER ::= { privateUsrMgmt 1 }

pmusrMgmtStatsNumOfUsers OBJECT-TYPE
    SYNTAX      Unsigned32
    MAX-ACCESS  read-only
    STATUS      current
    DESCRIPTION
        "The total number of users who have created account."
    ::= { pmusrMgmtStats 1 }

-- ----------------------------------------------------------------- -- 
-- groups in the MIB  
-- ----------------------------------------------------------------- -- 

      sslGeneralGroup        OBJECT IDENTIFIER ::= { privateSsl 1 }
      sslCiphers             OBJECT IDENTIFIER ::= { privateSsl 2 }

-- ---------------------------------------------------------------- --

-- General Group 
-- This object has been renamed as issHttpStatus and moved to pmiss.mib
--sslHttpStatus  OBJECT-TYPE
--   SYNTAX       INTEGER {
--                enable(1),
--                disable(2)
--               }
--   MAX-ACCESS  read-write 
--   STATUS      current 
--   DESCRIPTION 
--      "This object is for enabling or disabling HTTP in the system."
--
--   DEFVAL  { enable } 
--   ::= { sslGeneralGroup 1 }

sslSecureHttpStatus OBJECT-TYPE 
   SYNTAX       INTEGER {
                enable(1),
                disable(2)
                }
   MAX-ACCESS  read-write 
   STATUS      current 
   DESCRIPTION 
      "This object is for enabling or disabling secure HTTP in the system."

   DEFVAL  { disable } 
   ::= { sslGeneralGroup 2 }

sslVersion  OBJECT-TYPE
    SYNTAX  INTEGER {
            all(1),
            ssl3(2),
            tls1(3)
            }
    MAX-ACCESS  read-write
    STATUS  current
    DESCRIPTION
    "This object is to configure the SSL version" 
    DEFVAL  { tls1}
    ::= { sslGeneralGroup 5 }


-- Ciphers group

sslCipherList OBJECT-TYPE
      SYNTAX Integer32
      MAX-ACCESS read-write
      STATUS current
      DESCRIPTION
      
         "This object is to configure the cipher-suites list.

          This field is a bit mask, setting a bit indicates that the 
          corresponding cipher-list will be involved in the server
          authentication.
          
          BIT 0 - RSA-NULL-MD5
          BIT 1 - RSA-NULL-SHA
          BIT 2 - RSA-DES-SHA
          BIT 3 - RSA-3DES-SHA
          BIT 4 - DH-RSA-DES-SHA
          BIT 5 - DH-RSA-3DES-SHA
          BIT 6 - RSA-EXP1024-DES-SHA
          BIT 7 - RSA-WITH-AES-128-CBC-SHA
          BIT 8 - RSA-WITH-AES-256-CBC-SHA
          BIT 9 - DHE-RSA-WITH-AES-128-CBC-SHA
          BIT 10 - DHE-RSA-WITH-AES-256-CBC-SHA 
                                       

          Note:BIT 0 - Least significant bit
               BIT 10 - Most significant bit

          For example,setting the cipher list to the value - 001 0101, 
          will include RSA-NULL-MD5, RSA-DES-SHAa and DH-RSA-DES-SHA as 
          cipher-list for authentication.
         
          In the FIPS (American Security Standard Mode) Mode,  
          Only the following cipher list should be supported.
                 TLS_RSA_3DES_SHA1 
                 TLS_ DHE_RSA_3DES_SHA1
                 TLS_RSA_WITH_AES_128_CBC_SHA 
                 TLS_RSA_WITH_AES_256_CBC_SHA 
                 TLS_DHE_RSA_WITH_AES_128_CBC_SHA 
                 TLS_DHE_RSA_WITH_AES_256_CBC_SHA 
          hence the default value in FIPS mode will be
                 TLS_RSA_3DES_SHA1 | TLS_ DHE_RSA_3DES_SHA1 | TLS_RSA_WITH_AES_128_CBC_SHA |
                 TLS_RSA_WITH_AES_256_CBC_SHA | TLS_DHE_RSA_WITH_AES_128_CBC_SHA |
                 TLS_DHE_RSA_WITH_AES_256_CBC_SHA"

   DEFVAL  { 76 }
   ::= { sslCiphers 1}

-- SCALAR_TABLE_BEGIN

          snmpOverTcpStatus OBJECT-TYPE
              SYNTAX      INTEGER { enabled(1), disabled(2) }
              MAX-ACCESS  read-write
              STATUS  current
              DESCRIPTION "To Enable sending SNMP messages over TCP 
                           If its enabled all the SNMP messages  
                           will be send over TCP instead of UDP."
              DEFVAL { disabled }
              ::=  { privateSnmp3 6 }

          snmpListenTcpPort OBJECT-TYPE
              SYNTAX  Unsigned32 (1..65535)
              MAX-ACCESS  read-write
              STATUS  current
              DESCRIPTION "Contains Port Number on which snmp message
                           are sent to manager over TCP."
              DEFVAL { 161 }
              ::=  { privateSnmp3 7 }

          snmpTrapOverTcpStatus OBJECT-TYPE
              SYNTAX      INTEGER { enabled(1), disabled(2) }
              MAX-ACCESS  read-write
              STATUS  current
              DESCRIPTION "To Enable sending SNMP Trap messages over TCP 
                           If its enabled all the SNMP traps will be send 
                           over TCP instead of TCP."
              DEFVAL { disabled }
              ::=  { privateSnmp3 8 }

          snmpListenTcpTrapPort OBJECT-TYPE
              SYNTAX  Unsigned32 (1..65535)
              MAX-ACCESS  read-write
              STATUS  current
              DESCRIPTION "Contains Port Number on which snmp trap
                           message are sent to manager over TCP."
              DEFVAL { 162 }
              ::=  { privateSnmp3 9 }

-- SCALAR_TABLE_END

-- the SNMP Statistics group

-- SCALAR_TABLE_BEGIN
          snmpColdStartTrapControl OBJECT-TYPE
             SYNTAX      INTEGER { enabled(1), disabled(2) }
             MAX-ACCESS  read-write
             STATUS      current
             DESCRIPTION 
                    "This object is used to enable/disable coldStart Trap."
             ::= { privateSnmp3 11 }

          snmpAgentControl OBJECT-TYPE
             SYNTAX      INTEGER { enabled(1), disabled(2) }
             MAX-ACCESS  read-write
             STATUS      current
             DESCRIPTION 
                    "This object is used to enable/disable the SNMP agent.
                     Agent and Agentx both can not be enabled at the same time"
             DEFVAL     { enabled }
             ::= { privateSnmp3 12 }

    snmpProxyListenTrapPort OBJECT-TYPE
              SYNTAX  Unsigned32(1..65535)
              MAX-ACCESS  read-write
              STATUS  current
              DESCRIPTION "Contains Port Number on which Proxy listens 
                           for trap and inform messages from the Agent."
              DEFVAL { 162 }
              ::=  { privateSnmp3 17 }

--Tabular Object

    rmonStatsTable OBJECT-TYPE
        SYNTAX     SEQUENCE OF RmonStatsEntry
        MAX-ACCESS not-accessible
        STATUS     current
        DESCRIPTION "The table is a enhancement of etherStatsTable in stdrmon.mib."

    ::= {privateRmon 10}

    rmonStatsEntry  OBJECT-TYPE
        SYNTAX      RmonStatsEntry
        MAX-ACCESS not-accessible
        STATUS     current
        DESCRIPTION "An Entry containing Statistics information on OutFCSError."
        AUGMENTS {etherStatsEntry}
    ::= {rmonStatsTable 1}

    RmonStatsEntry  ::= SEQUENCE {
                                    rmonStatsOutFCSErrors   Counter32
                                }
    rmonStatsOutFCSErrors OBJECT-TYPE
        SYNTAX      Counter32
        MAX-ACCESS  read-only
        STATUS      current
        DESCRIPTION
        "The number of frames transmitted with an invalid FCS.
        Whenever a frame is modified during transmission
        (e.g., to add or remove a tag) the frame's original FCS
        is inspected before a new FCS is added to a modified
        frame. If the original FCS is invalid, the new FCS is
        made invalid too and this counter is incremented."

    ::={rmonStatsEntry 1}
-- ----------------------------------------------------------------- --
-- groups in the MIB
-- ----------------------------------------------------------------- --

      sshGeneralGroup   OBJECT IDENTIFIER ::= { privateSsh 1 }

-- ---------------------------------------------------------------- --

-- General Group 

sshStatus  OBJECT-TYPE
   SYNTAX      TruthValue 
   MAX-ACCESS  read-write
   STATUS      current
   DESCRIPTION
      "This object is for enabling or disabling ssh in the system."

   DEFVAL  { true }
   ::= { sshGeneralGroup 5}

sshSrvBindAddr OBJECT-TYPE
    SYNTAX   OCTET STRING (SIZE (4|16))
    MAX-ACCESS  read-write
    STATUS  current
    DESCRIPTION "This object defines the Ip address on which Ssh Server listens"
    ::=  { sshGeneralGroup 7 }

sshServerBindPortNo OBJECT-TYPE
    SYNTAX   Unsigned32
    MAX-ACCESS  read-write
    STATUS  current
    DESCRIPTION "This object defines the primary port number on which Ssh Server listens"
    DEFVAL    { 22 }
    ::=  { sshGeneralGroup 8 }
pmClkIwfObjects       OBJECT IDENTIFIER ::= { privateClkIwfMIB 1 }
pmClkIwfGeneralGroup  OBJECT IDENTIFIER ::= { pmClkIwfObjects 1 }

pmClkIwfClockVariance OBJECT-TYPE
   SYNTAX        Integer32
   MAX-ACCESS    read-write
   STATUS        current
   DESCRIPTION
      "This object denotes the variance of the primary clock. This object
       can reflect the value provisioned by the external source (NTP/SNTP/GPS)
       that synchronize the system clock. The default value of this 
       object is 0 (Minimum variance)"
   DEFVAL  { 0 }
   ::= { pmClkIwfGeneralGroup 1 }

pmClkIwfClockClass OBJECT-TYPE
   SYNTAX        Integer32
   MAX-ACCESS    read-write
   STATUS        current
   DESCRIPTION
      "This object denotes the class of the primary clock. This object
       can reflect the value provisioned by the external source (NTP/SNTP/GPS)
       that synchronize the system clock. "
   DEFVAL  { 248 }
   ::= { pmClkIwfGeneralGroup 2 }

pmClkIwfClockAccuracy OBJECT-TYPE
   SYNTAX        Integer32
   MAX-ACCESS    read-write
   STATUS        current
   DESCRIPTION
      "This object denotes the accuracy of the primary clock. This object
       can reflect the value provisioned by the external source (NTP/SNTP/GPS)
       that synchronize the system clock"
   DEFVAL  { 'FE'H }
   ::= { pmClkIwfGeneralGroup 3 }

pmClkIwfClockTimeSource OBJECT-TYPE
   SYNTAX        INTEGER {
                        atomicClock (16),
                        gps (32),
                        ptp (64),
                        ntp (80),
                        internalOscillator (160)
   }
   MAX-ACCESS    read-write
   STATUS        current
   DESCRIPTION
      "This object denotes the time source of the primary clock. 
       The system clock will be synchronized only through 
       this protocol "
   DEFVAL  { ptp }
   ::= { pmClkIwfGeneralGroup 4 }


pmClkIwfHoldoverSpecification OBJECT-TYPE
   SYNTAX        TruthValue
   MAX-ACCESS    read-write
   STATUS        current
   DESCRIPTION
      "This indicates the system clock is in hold over specification or not. 
       if the value is TRUE it indicates the clock is in holdover mode. 
       If the clock is synchronized or syntonized to another clock but now 
       free-running based on its own internall oscillator, whose frequency is
       adjusted using data acquired while it had been synchronized or syntonized 
       to the other clock then the clock is said to be in holdover mode "
   DEFVAL  { true }
   ::= { pmClkIwfGeneralGroup 7 }

pmClkIwfLostSync OBJECT-TYPE
   SYNTAX        TruthValue
   MAX-ACCESS    read-only
   STATUS        current
   DESCRIPTION
      " If the clock is synchronized or syntonized to another clock but now 
       it lost synchronizing the clock with primary reference using the 
       primary time source then this variable will be set to TRUE"
   DEFVAL  { false }
   ::= { pmClkIwfGeneralGroup 8 }

pmSntp              OBJECT IDENTIFIER ::= { privateSntpMIB 1 }
pmSntpScalars       OBJECT IDENTIFIER ::= { pmSntp 1 }


pmSntpAdminStatus OBJECT-TYPE
    SYNTAX     INTEGER { disabled (0), enabled (1) }
    MAX-ACCESS read-write
    STATUS     current
    DESCRIPTION
        "To enable or disable the sntp client module. All configuration will be 
        acitve only when the SNTP module is enabled"
    DEFVAL  { disabled } 
    ::= { pmSntpScalars 3 }


pmSntpClientPort     OBJECT-TYPE
    SYNTAX     Integer32 ( 123 | 1025..65535)   
    MAX-ACCESS read-write
    STATUS     current
    DESCRIPTION
        "The SNTP client module by default listens on well-know port number 123. 
         When required, the Administrator can change the SNTP Client port value
         to non-default."
    DEFVAL {123}
    ::= { pmSntpScalars 6 }

pmSntpTimeDisplayFormat OBJECT-TYPE
    SYNTAX     INTEGER { hours (1), ampm  (2) }
    MAX-ACCESS read-write
    STATUS     current
    DESCRIPTION
        " The administrator can view the system time in 12 hr AM/PM or 24 
        hours format. "
    DEFVAL  { hours } 
    ::= { pmSntpScalars 7 }

 pmSntpDSTStartTime OBJECT-TYPE
    SYNTAX     DisplayString (SIZE (20))
    MAX-ACCESS read-write
    STATUS     current
    DESCRIPTION
        " Daylight saving time (DST) is a system of setting clocks ahead so
        that both sunrise and sunset occur at a later hour. The effect is
        additional daylight in the evening. Many countries observe DST, 
        although most have their own rules and regulations for when it begins
        and ends. The dates of DST may change from year to year. The Valid 
        format  [weekofmonth-weekofday-month,HH:MM]. 
        Example:- Third-Mon-Apr,17:30 "   
    ::= { pmSntpScalars 12 }

 
 pmSntpDSTEndTime OBJECT-TYPE
    SYNTAX     DisplayString (SIZE (20))
    MAX-ACCESS read-write
    STATUS     current
    DESCRIPTION
        " Daylight saving time (DST) is a system of setting clocks ahead so
        that both sunrise and sunset occur at a later hour. The effect is
        additional daylight in the evening. Many countries observe DST, 
        although most have their own rules and regulations for when it begins
        and ends. The dates of DST may change from year to year. The Valid 
        format  [weekofmonth-weekofday-month,HH:MM].
        Example:- Last-Sun-Nov,16:20 "   
   ::= { pmSntpScalars 13 }

-- ----------------------------------------------------------------- -- 
-- groups in the MIB  
-- ----------------------------------------------------------------- -- 

      pmSyslogGeneralGroup                  OBJECT IDENTIFIER ::= { privateSyslog 1 }
      pmSyslogLogs                          OBJECT IDENTIFIER ::= { privateSyslog 2 }

-- ---------------------------------------------------------------- --

-- General Group 

-- Common objects for syslogLogs and SMTP 

pmSyslogLogging OBJECT-TYPE
   SYNTAX       INTEGER {
                enable(1),
                disable(2)
               }
   MAX-ACCESS  read-write 
   STATUS      current 
   DESCRIPTION 
      "This object is for enabling or disabling syslog and email alert
   features in the system."

   DEFVAL  { enable } 
   ::= { pmSyslogGeneralGroup 1 }

pmSyslogTimeStamp OBJECT-TYPE 
   SYNTAX         INTEGER {
                   enable(1),
                   disable(2)
                  }
   MAX-ACCESS  read-write 
   STATUS      deprecated 
   DESCRIPTION 
      "Currently this object is not used. Timestamp is a mandatory field
       in Syslog Message format"

   DEFVAL  { enable } 
   ::= { pmSyslogGeneralGroup 2 }

pmSyslogConsoleLog OBJECT-TYPE
   SYNTAX         INTEGER {
                   enable(1),
                   disable(2)
                  }
   MAX-ACCESS  read-write 
   STATUS      current 
   DESCRIPTION 
      "This object is for enabling or disabling the console log option.

       When enabled, the messages (log and email alert messages) sent to 
       the server will be displayed in the console also.

       When disabled,the messages will just be sent to the servers and not 
       be displayed in the console." 

   DEFVAL  { enable } 
   ::= { pmSyslogGeneralGroup 3 }

pmSyslogSysBuffers OBJECT-TYPE 
   SYNTAX      Integer32 (1..200)
   MAX-ACCESS  read-write 
   STATUS      current 
   DESCRIPTION 
      "Number of log buffers to be allocated in the system"

   DEFVAL  { 50 }
   ::= { pmSyslogGeneralGroup 4 }

-- pmSyslogConfigTable
-- This table is for configuring the log level options for the module.

  pmSyslogConfigTable       OBJECT-TYPE
         SYNTAX               SEQUENCE OF PmSyslogConfigEntry 
         MAX-ACCESS           not-accessible
         STATUS               current
         DESCRIPTION
            "A table for configuring module specific log levels." 

         ::= { pmSyslogGeneralGroup 6 }

  pmSyslogConfigEntry    OBJECT-TYPE
         SYNTAX            PmSyslogConfigEntry
         MAX-ACCESS        not-accessible
         STATUS            current
         DESCRIPTION
            "An entry containing logging level options for a particular module."
         INDEX { pmSyslogConfigModule }
         ::= { pmSyslogConfigTable 1 }
         
      PmSyslogConfigEntry ::=
         SEQUENCE {
            pmSyslogConfigModule    INTEGER, 
            pmSyslogConfigLogLevel  INTEGER
            }

      pmSyslogConfigModule    OBJECT-TYPE
         SYNTAX                 INTEGER{
                                  web(1),  -- For WEB module
                                  msr(2),  -- For MSR module
                                  tftp(3), -- For TFTP module
                                  cli(4)   -- For CLI module
                                }
         MAX-ACCESS             not-accessible 
         STATUS                 current
         DESCRIPTION
            "Specifies the module for which the log level option has to be 
             configured."
         ::= { pmSyslogConfigEntry 1 }

      pmSyslogConfigLogLevel    OBJECT-TYPE
         SYNTAX                 INTEGER{
                                  emergency(0), -- For logging messages that 
                                                -- are equivalent to panic 
                                                -- condition. 
                                  alert(1),     -- For logging messages that 
                                                -- require immediate attention.
                                  critical(2),  -- For logging critical errors.
                                  error(3),     -- For logging error messages.
                                  warning(4),   -- For logging warning messages.
                                  notice(5),    -- For logging messages that 
                                                -- require attention
                                                -- and not errors.
                                  info(6),      -- For logging informational 
                                                -- messages.
                                  debug(7)      -- For logging debug messages.
                                }
         MAX-ACCESS             read-write
         STATUS                 current
         DESCRIPTION
            "Specifies the log level option to be set for a specific module."
         DEFVAL  { 2 } 
         
         ::= { pmSyslogConfigEntry 2 }

--Table ends

pmSyslogFacility OBJECT-TYPE 
   SYNTAX         INTEGER {
                   local0(128),     -- Reserved local use
                   local1(136),     -- Reserved local use
                   local2(144),     -- Reserved local use
                   local3(152),     -- Reserved local use
                   local4(160),     -- Reserved local use
                   local5(168),     -- Reserved local use
                   local6(176),     -- Reserved local use
                   local7(184)      -- Reserved local use
                  }
   MAX-ACCESS  read-write 
   STATUS      current 
   DESCRIPTION 
      "The Syslog standard facilities.
       The facility to be used when sending Syslog messages to this server."

   DEFVAL  { local0 } 
   ::= { pmSyslogGeneralGroup 7 }


-- Syslog Logs group
-- pmSyslogFwdTable
-- This table is for configuring the Logging server forward table

  pmSyslogFwdTable       OBJECT-TYPE
         SYNTAX               SEQUENCE OF PmSyslogFwdEntry
         MAX-ACCESS           not-accessible
         STATUS               current
         DESCRIPTION
            "A table containing entries of priority,server address type, server address,
             port through which it can send and tranport type."

         ::= { pmSyslogLogs 3 }

  pmSyslogFwdEntry    OBJECT-TYPE
         SYNTAX            PmSyslogFwdEntry
         MAX-ACCESS        not-accessible
         STATUS            current
         DESCRIPTION
            "A table containing index as priority , server address type and server address."
         INDEX { pmSyslogFwdPriority,pmSyslogFwdAddressType,pmSyslogFwdServerIP}
         ::= { pmSyslogFwdTable 1 }

      PmSyslogFwdEntry ::=
         SEQUENCE {
             pmSyslogFwdPriority    Integer32,
             pmSyslogFwdAddressType InetAddressType,
             pmSyslogFwdServerIP    InetAddress,
             pmSyslogFwdPort        Integer32,
             pmSyslogFwdTransType   INTEGER,
             pmSyslogFwdRowStatus   RowStatus

            }

     pmSyslogFwdPriority    OBJECT-TYPE
         SYNTAX                 Integer32(0..191)
         MAX-ACCESS             not-accessible
         STATUS                 current
         DESCRIPTION
            "Specifies the priority which is to be forwarded to the desired server.
             Priority can take the value from 0 to 191."
         ::= { pmSyslogFwdEntry 1 }


         pmSyslogFwdAddressType    OBJECT-TYPE
         SYNTAX                 InetAddressType
         MAX-ACCESS             not-accessible
         STATUS                 current
         DESCRIPTION
            "Specifies the Address type of server.Address type shall be ipv4 or ipv6."
         ::= { pmSyslogFwdEntry 2 }

        pmSyslogFwdServerIP    OBJECT-TYPE
         SYNTAX                 InetAddress(SIZE(4..16))
         MAX-ACCESS             not-accessible
         STATUS                 current
         DESCRIPTION
            "Specifies the ServerIP to which the syslog shall be forwarded."
         ::= { pmSyslogFwdEntry 3 }

      pmSyslogFwdPort    OBJECT-TYPE
         SYNTAX                 Integer32(0..65535)
         MAX-ACCESS             read-write
         STATUS                 current
         DESCRIPTION
            "Specifies the Port through which it can send the syslog message.
             By default the the port  is 514"
         DEFVAL { 514 }
         ::= { pmSyslogFwdEntry 4 }

     pmSyslogFwdTransType    OBJECT-TYPE
         SYNTAX                 INTEGER {
                                           udp (0),
                                           tcp (1),
                                           beep (2)
                                        }
         MAX-ACCESS             read-write
         STATUS                 current
         DESCRIPTION
            "Specifies the Transport type using which it can send syslog message.
             By default the tranport type is udp"
         DEFVAL { udp }
         ::= { pmSyslogFwdEntry 5 }

      pmSyslogFwdRowStatus OBJECT-TYPE
       SYNTAX RowStatus
       MAX-ACCESS  read-write
       STATUS  current
       DESCRIPTION    "The Status of the Fwd  Entry."
         ::= {pmSyslogFwdEntry 6}

--Table ends
-- ***************************************************************************
--                         Groups in the MIB
-- ***************************************************************************

    pmMIDhcpSnpGlobalConfig          OBJECT IDENTIFIER ::= { privateMIDhcpSnp 1 }

-- ***************************************************************************
--                      Global Configuration Table 
-- ***************************************************************************
    pmMIDhcpSnpGlobalConfigTable OBJECT-TYPE
        SYNTAX  SEQUENCE OF PmMIDhcpSnpGlobalConfigEntry
        MAX-ACCESS  not-accessible
        STATUS      current
        DESCRIPTION
            "This table contains the configuration & statistics collection
            parameters of DHCP snooping on a specific VLAN. "
    ::= { pmMIDhcpSnpGlobalConfig 1 } 

    pmMIDhcpSnpGlobalConfigEntry OBJECT-TYPE
        SYNTAX      PmMIDhcpSnpGlobalConfigEntry
        MAX-ACCESS  not-accessible
        STATUS      current
        DESCRIPTION
            "Each row instance gives the DHCP snooping status on VLAN and the
             statistics collected in that VLAN for the DHCP snooping module"
        INDEX { pmMIDhcpSnpContextId }
    ::= { pmMIDhcpSnpGlobalConfigTable 1 }


   PmMIDhcpSnpGlobalConfigEntry ::=
     SEQUENCE {
           pmMIDhcpSnpContextId
              Integer32,
           pmMIDhcpSnpSnoopingAdminStatus
              INTEGER,
           pmMIDhcpSnpMacVerifyStatus
              INTEGER
             }
   pmMIDhcpSnpContextId OBJECT-TYPE
   SYNTAX        Integer32 (0..65535)
   MAX-ACCESS    not-accessible
   STATUS        current
   DESCRIPTION
      "Identifies the Virtual Context."
   ::= { pmMIDhcpSnpGlobalConfigEntry 1 }

    pmMIDhcpSnpSnoopingAdminStatus OBJECT-TYPE
        SYNTAX          INTEGER { enabled(1), disabled(2) }
        MAX-ACCESS      read-write
        STATUS          current
        DESCRIPTION
            "Enables or disables Layer 2 DHCP Snooping globally in the system.
             When set to 'enabled', the DHCP Snooping Module will start the 
             protocol operation. Layer 2 DHCP Snooping should be enabled on 
             per VLAN basis also. When set to 'disabled', the DHCP Snooping 
             Module will stop the protocol operation."
        DEFVAL  { disabled }
    ::= { pmMIDhcpSnpGlobalConfigEntry 2 }
    
     pmMIDhcpSnpMacVerifyStatus OBJECT-TYPE
        SYNTAX          INTEGER { enabled(1), disabled(2) }
        MAX-ACCESS      read-write
        STATUS          current
        DESCRIPTION
            "Enables or disables the MAC address verification. If this option 
             is enabled, the Layer 2 DHCP snooping module will verify the 
             source MAC Address against the client hardware address in the
             DHCP packets received."
         DEFVAL  { enabled }
     ::= { pmMIDhcpSnpGlobalConfigEntry 3 }

pmCdpGlobalConfig           OBJECT IDENTIFIER ::= { privateCDP 1 }
pmCdpPortConfig             OBJECT IDENTIFIER ::= { privateCDP 2 }
pmCdpLocalInformation       OBJECT IDENTIFIER ::= { privateCDP 3 }
pmCdpNeighborInformation    OBJECT IDENTIFIER ::= { privateCDP 4 }

-- ----------------------------------------------------------------- -- 
-- CDP Global Config
-- ----------------------------------------------------------------- -- 
pmCDPStateEnable OBJECT-TYPE 
    SYNTAX      EnabledStatus
    MAX-ACCESS  read-write 
    STATUS      current 
    DESCRIPTION 
        "Enable/Disable Cisco Discovery Protocol.
         The Cisco Discovery Protocol is used in the management
         of connected Cisco devices."
    DEFVAL  { disabled }
    ::= { pmCdpGlobalConfig 1 }

pmCDPVoiceVlanAdvertise  OBJECT-TYPE
    SYNTAX      EnabledStatus
    MAX-ACCESS  read-write
    STATUS      current
    DESCRIPTION
        "Enable/Disable voice VLAN advertisement.
         Local voice VLAN will be advertised to every voice VLAN
         member port that has this function enabled."
    DEFVAL  { disabled }
    ::= { pmCdpGlobalConfig 2 }

pmCDPMandatoryTlvValidate  OBJECT-TYPE
    SYNTAX      EnabledStatus
    MAX-ACCESS  read-write
    STATUS      current
    DESCRIPTION
        "When receiving packets without mandatory TLVs, ignore them 
         and count them in error counter. Mandatory TLVs include 
         Device ID, Address, Port ID, Capabilities, Software Version, 
         and Platform."  
    DEFVAL  { disabled }
    ::= { pmCdpGlobalConfig 3 }

pmCDPVersion  OBJECT-TYPE
    SYNTAX      Integer32 (1..2)
    MAX-ACCESS  read-write
    STATUS      current
    DESCRIPTION
        "CDP Version."  
    DEFVAL  { 2 }
    ::= { pmCdpGlobalConfig 4 }

pmCDPHoldTime  OBJECT-TYPE
    SYNTAX      Integer32 (10..255)
    MAX-ACCESS  read-write
    STATUS      current
    DESCRIPTION
        "The time to live value carried by CDP packets transmitted
         from this device."  
    DEFVAL  { 180 }
    ::= { pmCdpGlobalConfig 5 }

pmCDPTxInterval  OBJECT-TYPE
    SYNTAX      Integer32 (5..254)
    MAX-ACCESS  read-write
    STATUS      current
    DESCRIPTION
        "The time interval the device sends a CDP packet."  
    DEFVAL  { 60 }
    ::= { pmCdpGlobalConfig 6 }

pmCDPDeviceIdFormat  OBJECT-TYPE
    SYNTAX      INTEGER { mac(1), serial-no(2) }
    MAX-ACCESS  read-write
    STATUS      current
    DESCRIPTION
        "The device ID advertised in CDP packets."  
    DEFVAL  { mac }
    ::= { pmCdpGlobalConfig 7 }

pmCDPVoiceVlanMismatchNotify  OBJECT-TYPE
    SYNTAX      EnabledStatus
    MAX-ACCESS  read-write
    STATUS      current
    DESCRIPTION
        "Send a system log when receiving CDP packets
         containing voice VLAN information different
         from local configuration."  
    DEFVAL  { enabled }
    ::= { pmCdpGlobalConfig 8 }

pmCDPVlanMismatchNotify  OBJECT-TYPE
    SYNTAX      EnabledStatus
    MAX-ACCESS  read-write
    STATUS      current
    DESCRIPTION
        "Send a system log when receiving CDP packets
         containing VLAN information different from
        local configuration."  
    DEFVAL  { enabled }
    ::= { pmCdpGlobalConfig 9 }

pmCDPDuplexMismatchNotify  OBJECT-TYPE
    SYNTAX      EnabledStatus
    MAX-ACCESS  read-write
    STATUS      current
    DESCRIPTION
        "Send a system log when receiving CDP packets
         containing duplex information different from
        local configuration."  
    DEFVAL  { enabled }
    ::= { pmCdpGlobalConfig 10 }

-- ----------------------------------------------------------------- -- 
-- CDP Port Config
-- ----------------------------------------------------------------- -- 
pmCDPPortConfigTable OBJECT-TYPE
    SYNTAX      SEQUENCE OF PmCDPPortConfigEntry
    MAX-ACCESS  not-accessible
    STATUS      current
    DESCRIPTION
        "This table contains CDP port configuration."
    ::= { pmCdpPortConfig 1 }

pmCDPPortConfigEntry OBJECT-TYPE
    SYNTAX      PmCDPPortConfigEntry
    MAX-ACCESS  not-accessible
    STATUS      current
    DESCRIPTION
        "A list of configuration maintained by every port for 
         Cisco Discovery Protocol."
    INDEX  { pmCDPPortConfigIndex }
    ::= { pmCDPPortConfigTable 1 }

PmCDPPortConfigEntry ::= 
    SEQUENCE {
        pmCDPPortConfigIndex
            Integer32,
        pmCDPPortStatus 
            EnabledStatus,
        pmCDPPortVoiceVlanMismatchNotify 
            EnabledStatus,
        pmCDPPortVlanMismatchNotify 
            EnabledStatus,
        pmCDPPortDuplexMismatchNotify 
            EnabledStatus
}

pmCDPPortConfigIndex OBJECT-TYPE
    SYNTAX      Integer32 (1..65535)
    MAX-ACCESS  not-accessible
    STATUS      current
    DESCRIPTION
        "The Port number of the port for which this entry contains   
         CDP information."
    ::= { pmCDPPortConfigEntry 1 }

pmCDPPortStatus OBJECT-TYPE
    SYNTAX      EnabledStatus
    MAX-ACCESS  read-write
    STATUS      current
    DESCRIPTION
        "Per port CDP status."
    ::= { pmCDPPortConfigEntry 2 }

pmCDPPortVoiceVlanMismatchNotify OBJECT-TYPE
    SYNTAX      EnabledStatus
    MAX-ACCESS  read-write
    STATUS      current
    DESCRIPTION
        "Sends a system log when this port receives CDP packets 
         containing voice VLAN information different from local 
         configuration."
    ::= { pmCDPPortConfigEntry 3 }

pmCDPPortVlanMismatchNotify OBJECT-TYPE
    SYNTAX      EnabledStatus
    MAX-ACCESS  read-write
    STATUS      current
    DESCRIPTION
        "Sends a system log when this port receives CDP packets
         containing VLAN information different from local 
         configuration."
    ::= { pmCDPPortConfigEntry 4 }

pmCDPPortDuplexMismatchNotify OBJECT-TYPE
    SYNTAX      EnabledStatus
    MAX-ACCESS  read-write
    STATUS      current
    DESCRIPTION
        "Sends a system log when this port receives CDP packets
         containing duplex information different from local 
         configuration."
    ::= { pmCDPPortConfigEntry 5 }

pmCDPPortClearStatistics OBJECT-TYPE
    SYNTAX      Integer32 (1..65536) 
    MAX-ACCESS  read-write
    STATUS      current
    DESCRIPTION
        "Clear Tx, Rx and error counter of specified port."
    ::= { pmCdpPortConfig 2 }

pmCDPPortClearNeighbor OBJECT-TYPE
    SYNTAX      Integer32 (1..65536) 
    MAX-ACCESS  read-write
    STATUS      current
    DESCRIPTION
        "Clear neighbor information of specified port."
    ::= { pmCdpPortConfig 3 }

-- ----------------------------------------------------------------- -- 
-- CDP Local Information
-- ----------------------------------------------------------------- -- 
pmCDPLocalInfoTable OBJECT-TYPE
    SYNTAX      SEQUENCE OF PmCDPLocalInfoEntry
    MAX-ACCESS  not-accessible
    STATUS      current
    DESCRIPTION
        "This table contains CDP local port 
         information."
    ::= { pmCdpLocalInformation 1 }

pmCDPLocalInfoEntry OBJECT-TYPE
    SYNTAX      PmCDPLocalInfoEntry
    MAX-ACCESS  not-accessible
    STATUS      current
    DESCRIPTION
        "A list of local information on every port for 
         Cisco Discovery Protocol."
    INDEX  { pmCDPPortInfoIndex }
    ::= { pmCDPLocalInfoTable 1 }

PmCDPLocalInfoEntry ::= 
    SEQUENCE {
        pmCDPPortInfoIndex
            Integer32,
        pmCDPPortDeviceId 
            DisplayString,
        pmCDPPortSystemName
            DisplayString,
        pmCDPPortAddress1
            DisplayString,
        pmCDPPortAddress2
            DisplayString,
        pmCDPPortAddress3
            DisplayString,
        pmCDPPortPortId
            DisplayString,
        pmCDPPortCapabilities
            DisplayString,
        pmCDPPortVersion
            Integer32,
        pmCDPPortPlatform
            DisplayString,
        pmCDPPortSoftwareVersion
            DisplayString,
        pmCDPPortLocalVlan
            Integer32,
        pmCDPPortVoiceVlan
            Integer32,
        pmCDPPortDuplex
            INTEGER,
        pmCDPPortExtendedTrust
            EnabledStatus,
        pmCDPPortCosForUntrusted
            Integer32,
        pmCDPPortPowerConsumption
            DisplayString,
        pmCDPPortPowerRequestId
            Integer32,
        pmCDPPortPowerManagementId
            Integer32,
        pmCDPPortPowerAvailable
            DisplayString,
        pmCDPPortHasNeighbor
            DisplayString
}

pmCDPPortInfoIndex OBJECT-TYPE
    SYNTAX      Integer32 (1..65535)
    MAX-ACCESS  not-accessible
    STATUS      current
    DESCRIPTION
        "The Port number of the port for which this entry contains 
         CDP information."                                      
    ::= { pmCDPLocalInfoEntry 1 }

pmCDPPortDeviceId OBJECT-TYPE
    SYNTAX      DisplayString
    MAX-ACCESS  read-only
    STATUS      current
    DESCRIPTION
        "The device ID being advertised to the neighbors of this port."
    ::= { pmCDPLocalInfoEntry 2 }

pmCDPPortSystemName OBJECT-TYPE
    SYNTAX      DisplayString
    MAX-ACCESS  read-only
    STATUS      current
    DESCRIPTION
        "The system name being advertised to the neighbors of this port."
    ::= { pmCDPLocalInfoEntry 3 }

pmCDPPortAddress1 OBJECT-TYPE
    SYNTAX      DisplayString
    MAX-ACCESS  read-only
    STATUS      current
    DESCRIPTION
        "The address of local port."
    ::= { pmCDPLocalInfoEntry 4 }

pmCDPPortAddress2 OBJECT-TYPE
    SYNTAX      DisplayString
    MAX-ACCESS  read-only
    STATUS      current
    DESCRIPTION
        "The address of local port."
    ::= { pmCDPLocalInfoEntry 5 }

pmCDPPortAddress3 OBJECT-TYPE
    SYNTAX      DisplayString
    MAX-ACCESS  read-only
    STATUS      current
    DESCRIPTION
        "The address of local port."
    ::= { pmCDPLocalInfoEntry 6 }

pmCDPPortPortId OBJECT-TYPE
    SYNTAX      DisplayString
    MAX-ACCESS  read-only
    STATUS      current
    DESCRIPTION
        "The port interface being advertised to the neighbors of this port."
    ::= { pmCDPLocalInfoEntry 7 }

pmCDPPortCapabilities OBJECT-TYPE
    SYNTAX      DisplayString
    MAX-ACCESS  read-only
    STATUS      current
    DESCRIPTION
        "The capabilities being advertised to the neighbors of this port."
    ::= { pmCDPLocalInfoEntry 8 }

pmCDPPortVersion OBJECT-TYPE
    SYNTAX      Integer32 (1..2)
    MAX-ACCESS  read-only
    STATUS      current
    DESCRIPTION
        "The CDP version currently used."
    ::= { pmCDPLocalInfoEntry 9 }

pmCDPPortPlatform OBJECT-TYPE
    SYNTAX      DisplayString
    MAX-ACCESS  read-only
    STATUS      current
    DESCRIPTION
        "The platform information being advertised to the neighbors of
         this port."
    ::= { pmCDPLocalInfoEntry 10 }

pmCDPPortSoftwareVersion OBJECT-TYPE
    SYNTAX      DisplayString
    MAX-ACCESS  read-only
    STATUS      current
    DESCRIPTION
        "The address of local port."
    ::= { pmCDPLocalInfoEntry 11 }

pmCDPPortLocalVlan OBJECT-TYPE
    SYNTAX      Integer32 (1..4094)
    MAX-ACCESS  read-only
    STATUS      current
    DESCRIPTION
        "The PVID of this port."
    ::= { pmCDPLocalInfoEntry 12 }

pmCDPPortVoiceVlan OBJECT-TYPE
    SYNTAX      Integer32 (1..4094)
    MAX-ACCESS  read-only
    STATUS      current
    DESCRIPTION
        "The voice VLAN of this device."
    ::= { pmCDPLocalInfoEntry 13 }

pmCDPPortDuplex OBJECT-TYPE
    SYNTAX      INTEGER { Half(1), Full(2) }
    MAX-ACCESS  read-only
    STATUS      current
    DESCRIPTION
        "Indicates whether full or half duplex is used on this port."
    ::= { pmCDPLocalInfoEntry 14 }

pmCDPPortExtendedTrust OBJECT-TYPE
    SYNTAX      EnabledStatus
    MAX-ACCESS  read-only
    STATUS      current
    DESCRIPTION
        "Enabled means the device connected to this port is trusted,
         so the CoS value of packets received on this port will not
         be remarked. While disabled means the packets received on 
         this port will be marked using the following field."
    ::= { pmCDPLocalInfoEntry 15 }

pmCDPPortCosForUntrusted OBJECT-TYPE
    SYNTAX      Integer32 (0..7)
    MAX-ACCESS  read-only
    STATUS      current
    DESCRIPTION
        "The CoS value being used to remark packets received on this
        port when extended trust is disabled. This value is 0 if
        extended trust is enabled."
    ::= { pmCDPLocalInfoEntry 16 }

pmCDPPortPowerConsumption OBJECT-TYPE
    SYNTAX      DisplayString
    MAX-ACCESS  read-only
    STATUS      current
    DESCRIPTION
        "Power consumed by PD connected to this port."
    ::= { pmCDPLocalInfoEntry 17 }

pmCDPPortPowerRequestId OBJECT-TYPE
    SYNTAX      Integer32 (0..65535)
    MAX-ACCESS  read-only
    STATUS      current
    DESCRIPTION
        "The latest power request ID received from the neighbor of this
         port."
    ::= { pmCDPLocalInfoEntry 18 }

pmCDPPortPowerManagementId OBJECT-TYPE
    SYNTAX      Integer32 (0..65536)
    MAX-ACCESS  read-only
    STATUS      current
    DESCRIPTION
        "This value increases by 1 or 2 whenever power available
         information changes value."
    ::= { pmCDPLocalInfoEntry 19 }

pmCDPPortPowerAvailable OBJECT-TYPE
    SYNTAX      DisplayString
    MAX-ACCESS  read-only
    STATUS      current
    DESCRIPTION
        "Max power consumption available on this port."
    ::= { pmCDPLocalInfoEntry 20 }

pmCDPPortHasNeighbor OBJECT-TYPE
    SYNTAX      DisplayString
    MAX-ACCESS  read-only
    STATUS      current
    DESCRIPTION
        "To indicate whether this port currently has neighbor."
    ::= { pmCDPLocalInfoEntry 21 }


-- ----------------------------------------------------------------- -- 
-- CDP Local Statistics
-- ----------------------------------------------------------------- -- 
pmCDPLocalStatisticsTable OBJECT-TYPE
    SYNTAX      SEQUENCE OF PmCDPLocalStatisticsEntry
    MAX-ACCESS  not-accessible
    STATUS      current
    DESCRIPTION
        "This table contains CDP local port 
         information."
    ::= { pmCdpLocalInformation 2 }

pmCDPLocalStatisticsEntry OBJECT-TYPE
    SYNTAX      PmCDPLocalStatisticsEntry
    MAX-ACCESS  not-accessible
    STATUS      current
    DESCRIPTION
        "A list of local statistics on every port for 
         Cisco Discovery Protocol."
    INDEX  { pmCDPPortStatisticsIndex }
    ::= { pmCDPLocalStatisticsTable 1 }

PmCDPLocalStatisticsEntry ::= 
    SEQUENCE {
        pmCDPPortStatisticsIndex
            Integer32,
        pmCDPPortRxV1Count
            Integer32,
        pmCDPPortRxV2Count 
            Integer32,
        pmCDPPortRxTotalCount
            Integer32,
        pmCDPPortTxV1Count
            Integer32,
        pmCDPPortTxV2Count 
            Integer32,
        pmCDPPortTxTotalCount
            Integer32,
        pmCDPPortErrorChecksumCount 
            Integer32,
        pmCDPPortErrorOtherCount
            Integer32
}

pmCDPPortStatisticsIndex OBJECT-TYPE
    SYNTAX      Integer32 (1..65535)
    MAX-ACCESS  not-accessible
    STATUS      current
    DESCRIPTION
        "The Port number of the port for which this entry contains 
         CDP statistics."                                      
    ::= { pmCDPLocalStatisticsEntry 1 }

pmCDPPortRxV1Count OBJECT-TYPE
    SYNTAX      Integer32 (1..65535)
    MAX-ACCESS  read-only
    STATUS      current
    DESCRIPTION
        "Received v1 CDP packet count."                                      
    ::= { pmCDPLocalStatisticsEntry 2 }

pmCDPPortRxV2Count OBJECT-TYPE
    SYNTAX      Integer32 (1..65535)
    MAX-ACCESS  read-only
    STATUS      current
    DESCRIPTION
        "Received v2 CDP packet count."
    ::= { pmCDPLocalStatisticsEntry 3 }

pmCDPPortRxTotalCount OBJECT-TYPE
    SYNTAX      Integer32 (1..65535)
    MAX-ACCESS  read-only
    STATUS      current
    DESCRIPTION
        "Received all CDP packet count."
    ::= { pmCDPLocalStatisticsEntry 4 }

pmCDPPortTxV1Count OBJECT-TYPE
    SYNTAX      Integer32 (1..65535)
    MAX-ACCESS  read-only
    STATUS      current
    DESCRIPTION
        "Transmitted v1 CDP packet count."                                      
    ::= { pmCDPLocalStatisticsEntry 5 }

pmCDPPortTxV2Count OBJECT-TYPE
    SYNTAX      Integer32 (1..65535)
    MAX-ACCESS  read-only
    STATUS      current
    DESCRIPTION
        "Transmitted v2 CDP packet count."
    ::= { pmCDPLocalStatisticsEntry 6 }

pmCDPPortTxTotalCount OBJECT-TYPE
    SYNTAX      Integer32 (1..65535)
    MAX-ACCESS  read-only
    STATUS      current
    DESCRIPTION
        "Transmitted all CDP packet count."
    ::= { pmCDPLocalStatisticsEntry 7 }

pmCDPPortErrorChecksumCount OBJECT-TYPE
    SYNTAX      Integer32 (1..65535)
    MAX-ACCESS  read-only
    STATUS      current
    DESCRIPTION
        "Checksum error counter when receiving CDP packet."
    ::= { pmCDPLocalStatisticsEntry 8 }

pmCDPPortErrorOtherCount OBJECT-TYPE
    SYNTAX      Integer32 (1..65535)
    MAX-ACCESS  read-only
    STATUS      current
    DESCRIPTION
        "Other error counter when receiving CDP packet."
    ::= { pmCDPLocalStatisticsEntry 9 }


-- ----------------------------------------------------------------- -- 
-- CDP Neighbor Information
-- ----------------------------------------------------------------- -- 
pmCDPNeighborInfoTable OBJECT-TYPE
    SYNTAX      SEQUENCE OF PmCDPNeighborInfoEntry
    MAX-ACCESS  not-accessible
    STATUS      current
    DESCRIPTION
        "This table contains CDP neighbor port 
         information."
    ::= { pmCdpNeighborInformation 1 }

pmCDPNeighborInfoEntry OBJECT-TYPE
    SYNTAX      PmCDPNeighborInfoEntry
    MAX-ACCESS  not-accessible
    STATUS      current
    DESCRIPTION
        "A list of neighbor information on every port for 
         Cisco Discovery Protocol."
    INDEX  { pmCDPNeighborPortIndex }
    ::= { pmCDPNeighborInfoTable 1 }

PmCDPNeighborInfoEntry ::= 
    SEQUENCE {
        pmCDPNeighborPortIndex
            Integer32,
        pmCDPNeighborDeviceId 
            DisplayString,
        pmCDPNeighborSystemName
            DisplayString,
        pmCDPNeighborCdpVersion
            DisplayString,
        pmCDPNeighborTimeToLive
            DisplayString,
        pmCDPNeighborNeighborInterface
            DisplayString,
        pmCDPNeighborAddress
            DisplayString,
        pmCDPNeighborCapabilities
            DisplayString,
        pmCDPNeighborSoftwareVersion
            DisplayString,
        pmCDPNeighborPlatform
            DisplayString,
        pmCDPNeighborNativeVlan
            DisplayString,
        pmCDPNeighborVoiceVlan
            DisplayString,
        pmCDPNeighborDuplex
            DisplayString,
        pmCDPNeighborExtendedTrust
            DisplayString,
        pmCDPNeighborCosForUntrusted
            DisplayString,
        pmCDPNeighborManagementAddress
            DisplayString,
        pmCDPNeighborPowerConsumption
            DisplayString,
        pmCDPNeighborPowerRequestId
            DisplayString,
        pmCDPNeighborPowerManagementId
            DisplayString,
        pmCDPNeighborPowerAvailable
            DisplayString
    }

pmCDPNeighborPortIndex OBJECT-TYPE
    SYNTAX      Integer32 (1..65535)
    MAX-ACCESS  not-accessible
    STATUS      current
    DESCRIPTION
        "The Port number of the port for which this entry contains 
         CDP neighbor information."                                      
    ::= { pmCDPNeighborInfoEntry 1 }

pmCDPNeighborDeviceId OBJECT-TYPE
    SYNTAX      DisplayString
    MAX-ACCESS  read-only
    STATUS      current
    DESCRIPTION
        "Device ID of the neighbor device."                                      
    ::= { pmCDPNeighborInfoEntry 2 }

pmCDPNeighborSystemName OBJECT-TYPE
    SYNTAX      DisplayString
    MAX-ACCESS  read-only
    STATUS      current
    DESCRIPTION
        "System name of the neighbor device."                                      
    ::= { pmCDPNeighborInfoEntry 3 }

pmCDPNeighborCdpVersion OBJECT-TYPE
    SYNTAX      DisplayString
    MAX-ACCESS  read-only
    STATUS      current
    DESCRIPTION
        "CDP Version being used by the neighbor device."                                      
    ::= { pmCDPNeighborInfoEntry 4 }

pmCDPNeighborTimeToLive OBJECT-TYPE
    SYNTAX      DisplayString
    MAX-ACCESS  read-only
    STATUS      current
    DESCRIPTION
        "Amount of time this information will be kept before expiration."                                      
    ::= { pmCDPNeighborInfoEntry 5 }

pmCDPNeighborNeighborInterface OBJECT-TYPE
    SYNTAX      DisplayString
    MAX-ACCESS  read-only
    STATUS      current
    DESCRIPTION
        "The port being used on the neighbor device."                                      
    ::= { pmCDPNeighborInfoEntry 6 }

pmCDPNeighborAddress OBJECT-TYPE
    SYNTAX      DisplayString
    MAX-ACCESS  read-only
    STATUS      current
    DESCRIPTION
        "Addresses of the neighbor device."                                      
    ::= { pmCDPNeighborInfoEntry 7 }

pmCDPNeighborCapabilities OBJECT-TYPE
    SYNTAX      DisplayString
    MAX-ACCESS  read-only
    STATUS      current
    DESCRIPTION
        "The primary functions of the neighbor device."                                      
    ::= { pmCDPNeighborInfoEntry 8 }

pmCDPNeighborSoftwareVersion OBJECT-TYPE
    SYNTAX      DisplayString
    MAX-ACCESS  read-only
    STATUS      current
    DESCRIPTION
        "Software version of the neighbor device."                                      
    ::= { pmCDPNeighborInfoEntry 9 }

pmCDPNeighborPlatform OBJECT-TYPE
    SYNTAX      DisplayString
    MAX-ACCESS  read-only
    STATUS      current
    DESCRIPTION
        "Platform of the neighbor device."                                      
    ::= { pmCDPNeighborInfoEntry 10 }

pmCDPNeighborNativeVlan OBJECT-TYPE
    SYNTAX      DisplayString
    MAX-ACCESS  read-only
    STATUS      current
    DESCRIPTION
        "VLAN of the neighbor device."                                      
    ::= { pmCDPNeighborInfoEntry 11 }

pmCDPNeighborVoiceVlan OBJECT-TYPE
    SYNTAX      DisplayString
    MAX-ACCESS  read-only
    STATUS      current
    DESCRIPTION
        "Voice VLAN of the neighbor device."                                      
    ::= { pmCDPNeighborInfoEntry 12 }

pmCDPNeighborDuplex OBJECT-TYPE
    SYNTAX      DisplayString
    MAX-ACCESS  read-only
    STATUS      current
    DESCRIPTION
        "Full or half duplex is being used by the neighbor device."                                      
    ::= { pmCDPNeighborInfoEntry 13 }

pmCDPNeighborExtendedTrust OBJECT-TYPE
    SYNTAX      DisplayString
    MAX-ACCESS  read-only
    STATUS      current
    DESCRIPTION
        "Enabled means the CoS value of packets received from this
         neighbor will not be remarked, while disabled means that
         the packets will be remarked using the value of the next field."                                      
    ::= { pmCDPNeighborInfoEntry 14 }

pmCDPNeighborCosForUntrusted OBJECT-TYPE
    SYNTAX      DisplayString
    MAX-ACCESS  read-only
    STATUS      current
    DESCRIPTION
        "The CoS value being used to remark packets received from this
         neighbor when extended trust is disabled. This value is 0 if
         extended trust is enabled."                                      
    ::= { pmCDPNeighborInfoEntry 15 }

pmCDPNeighborManagementAddress OBJECT-TYPE
    SYNTAX      DisplayString
    MAX-ACCESS  read-only
    STATUS      current
    DESCRIPTION
        "The CoS value being used to remark packets received from this
         neighbor when extended trust is disabled. This value is 0 if
         extended trust is enabled."                                      
    ::= { pmCDPNeighborInfoEntry 16 }

pmCDPNeighborPowerConsumption OBJECT-TYPE
    SYNTAX      DisplayString
    MAX-ACCESS  read-only
    STATUS      current
    DESCRIPTION
        "Power consumed by PD of the neighbor."                                      
    ::= { pmCDPNeighborInfoEntry 17 }

pmCDPNeighborPowerRequestId OBJECT-TYPE
    SYNTAX      DisplayString
    MAX-ACCESS  read-only
    STATUS      current
    DESCRIPTION
        "The latest power request ID received from this neighbor."                                      
    ::= { pmCDPNeighborInfoEntry 18 }

pmCDPNeighborPowerManagementId OBJECT-TYPE
    SYNTAX      DisplayString
    MAX-ACCESS  read-only
    STATUS      current
    DESCRIPTION
        "This value increases by 1 or 2 whenever power available
         information changes value."                                      
    ::= { pmCDPNeighborInfoEntry 19 }

pmCDPNeighborPowerAvailable OBJECT-TYPE
    SYNTAX      DisplayString
    MAX-ACCESS  read-only
    STATUS      current
    DESCRIPTION
        "Max power supply on this port."
    ::= { pmCDPNeighborInfoEntry 20 }

pmCDPNeighborCount OBJECT-TYPE
    SYNTAX      Integer32 (1..65535)
    MAX-ACCESS  read-only
    STATUS      current
    DESCRIPTION
        "Total neighbor counter."
    ::= { pmCdpNeighborInformation 2 }


pmCdpGlobalConfig           OBJECT IDENTIFIER ::= { privateCDP 1 }
pmCdpPortConfig             OBJECT IDENTIFIER ::= { privateCDP 2 }
pmCdpLocalInformation       OBJECT IDENTIFIER ::= { privateCDP 3 }
pmCdpNeighborInformation    OBJECT IDENTIFIER ::= { privateCDP 4 }

-- ----------------------------------------------------------------- -- 
-- CDP Global Config
-- ----------------------------------------------------------------- -- 
pmCDPStateEnable OBJECT-TYPE 
    SYNTAX      EnabledStatus
    MAX-ACCESS  read-write 
    STATUS      current 
    DESCRIPTION 
        "Enable/Disable Cisco Discovery Protocol.
         The Cisco Discovery Protocol is used in the management
         of connected Cisco devices."
    DEFVAL  { disabled }
    ::= { pmCdpGlobalConfig 1 }

pmCDPVoiceVlanAdvertise  OBJECT-TYPE
    SYNTAX      EnabledStatus
    MAX-ACCESS  read-write
    STATUS      current
    DESCRIPTION
        "Enable/Disable voice VLAN advertisement.
         Local voice VLAN will be advertised to every voice VLAN
         member port that has this function enabled."
    DEFVAL  { disabled }
    ::= { pmCdpGlobalConfig 2 }

pmCDPMandatoryTlvValidate  OBJECT-TYPE
    SYNTAX      EnabledStatus
    MAX-ACCESS  read-write
    STATUS      current
    DESCRIPTION
        "When receiving packets without mandatory TLVs, ignore them 
         and count them in error counter. Mandatory TLVs include 
         Device ID, Address, Port ID, Capabilities, Software Version, 
         and Platform."  
    DEFVAL  { disabled }
    ::= { pmCdpGlobalConfig 3 }

pmCDPVersion  OBJECT-TYPE
    SYNTAX      Integer32 (1..2)
    MAX-ACCESS  read-write
    STATUS      current
    DESCRIPTION
        "CDP Version."  
    DEFVAL  { 2 }
    ::= { pmCdpGlobalConfig 4 }

pmCDPHoldTime  OBJECT-TYPE
    SYNTAX      Integer32 (10..255)
    MAX-ACCESS  read-write
    STATUS      current
    DESCRIPTION
        "The time to live value carried by CDP packets transmitted
         from this device."  
    DEFVAL  { 180 }
    ::= { pmCdpGlobalConfig 5 }

pmCDPTxInterval  OBJECT-TYPE
    SYNTAX      Integer32 (5..254)
    MAX-ACCESS  read-write
    STATUS      current
    DESCRIPTION
        "The time interval the device sends a CDP packet."  
    DEFVAL  { 60 }
    ::= { pmCdpGlobalConfig 6 }

pmCDPDeviceIdFormat  OBJECT-TYPE
    SYNTAX      INTEGER { mac(1), serial-no(2) }
    MAX-ACCESS  read-write
    STATUS      current
    DESCRIPTION
        "The device ID advertised in CDP packets."  
    DEFVAL  { mac }
    ::= { pmCdpGlobalConfig 7 }

pmCDPVoiceVlanMismatchNotify  OBJECT-TYPE
    SYNTAX      EnabledStatus
    MAX-ACCESS  read-write
    STATUS      current
    DESCRIPTION
        "Send a system log when receiving CDP packets
         containing voice VLAN information different
         from local configuration."  
    DEFVAL  { enabled }
    ::= { pmCdpGlobalConfig 8 }

pmCDPVlanMismatchNotify  OBJECT-TYPE
    SYNTAX      EnabledStatus
    MAX-ACCESS  read-write
    STATUS      current
    DESCRIPTION
        "Send a system log when receiving CDP packets
         containing VLAN information different from
        local configuration."  
    DEFVAL  { enabled }
    ::= { pmCdpGlobalConfig 9 }

pmCDPDuplexMismatchNotify  OBJECT-TYPE
    SYNTAX      EnabledStatus
    MAX-ACCESS  read-write
    STATUS      current
    DESCRIPTION
        "Send a system log when receiving CDP packets
         containing duplex information different from
        local configuration."  
    DEFVAL  { enabled }
    ::= { pmCdpGlobalConfig 10 }

-- ----------------------------------------------------------------- -- 
-- CDP Port Config
-- ----------------------------------------------------------------- -- 
pmCDPPortConfigTable OBJECT-TYPE
    SYNTAX      SEQUENCE OF PmCDPPortConfigEntry
    MAX-ACCESS  not-accessible
    STATUS      current
    DESCRIPTION
        "This table contains CDP port configuration."
    ::= { pmCdpPortConfig 1 }

pmCDPPortConfigEntry OBJECT-TYPE
    SYNTAX      PmCDPPortConfigEntry
    MAX-ACCESS  not-accessible
    STATUS      current
    DESCRIPTION
        "A list of configuration maintained by every port for 
         Cisco Discovery Protocol."
    INDEX  { pmCDPPortConfigIndex }
    ::= { pmCDPPortConfigTable 1 }

PmCDPPortConfigEntry ::= 
    SEQUENCE {
        pmCDPPortConfigIndex
            Integer32,
        pmCDPPortStatus 
            EnabledStatus,
        pmCDPPortVoiceVlanMismatchNotify 
            EnabledStatus,
        pmCDPPortVlanMismatchNotify 
            EnabledStatus,
        pmCDPPortDuplexMismatchNotify 
            EnabledStatus
}

pmCDPPortConfigIndex OBJECT-TYPE
    SYNTAX      Integer32 (1..65535)
    MAX-ACCESS  not-accessible
    STATUS      current
    DESCRIPTION
        "The Port number of the port for which this entry contains   
         CDP information."
    ::= { pmCDPPortConfigEntry 1 }

pmCDPPortStatus OBJECT-TYPE
    SYNTAX      EnabledStatus
    MAX-ACCESS  read-write
    STATUS      current
    DESCRIPTION
        "Per port CDP status."
    ::= { pmCDPPortConfigEntry 2 }

pmCDPPortVoiceVlanMismatchNotify OBJECT-TYPE
    SYNTAX      EnabledStatus
    MAX-ACCESS  read-write
    STATUS      current
    DESCRIPTION
        "Sends a system log when this port receives CDP packets 
         containing voice VLAN information different from local 
         configuration."
    ::= { pmCDPPortConfigEntry 3 }

pmCDPPortVlanMismatchNotify OBJECT-TYPE
    SYNTAX      EnabledStatus
    MAX-ACCESS  read-write
    STATUS      current
    DESCRIPTION
        "Sends a system log when this port receives CDP packets
         containing VLAN information different from local 
         configuration."
    ::= { pmCDPPortConfigEntry 4 }

pmCDPPortDuplexMismatchNotify OBJECT-TYPE
    SYNTAX      EnabledStatus
    MAX-ACCESS  read-write
    STATUS      current
    DESCRIPTION
        "Sends a system log when this port receives CDP packets
         containing duplex information different from local 
         configuration."
    ::= { pmCDPPortConfigEntry 5 }

pmCDPPortClearStatistics OBJECT-TYPE
    SYNTAX      Integer32 (1..65536) 
    MAX-ACCESS  read-write
    STATUS      current
    DESCRIPTION
        "Clear Tx, Rx and error counter of specified port."
    ::= { pmCdpPortConfig 2 }

pmCDPPortClearNeighbor OBJECT-TYPE
    SYNTAX      Integer32 (1..65536) 
    MAX-ACCESS  read-write
    STATUS      current
    DESCRIPTION
        "Clear neighbor information of specified port."
    ::= { pmCdpPortConfig 3 }

-- ----------------------------------------------------------------- -- 
-- CDP Local Information
-- ----------------------------------------------------------------- -- 
pmCDPLocalInfoTable OBJECT-TYPE
    SYNTAX      SEQUENCE OF PmCDPLocalInfoEntry
    MAX-ACCESS  not-accessible
    STATUS      current
    DESCRIPTION
        "This table contains CDP local port 
         information."
    ::= { pmCdpLocalInformation 1 }

pmCDPLocalInfoEntry OBJECT-TYPE
    SYNTAX      PmCDPLocalInfoEntry
    MAX-ACCESS  not-accessible
    STATUS      current
    DESCRIPTION
        "A list of local information on every port for 
         Cisco Discovery Protocol."
    INDEX  { pmCDPPortInfoIndex }
    ::= { pmCDPLocalInfoTable 1 }

PmCDPLocalInfoEntry ::= 
    SEQUENCE {
        pmCDPPortInfoIndex
            Integer32,
        pmCDPPortDeviceId 
            DisplayString,
        pmCDPPortSystemName
            DisplayString,
        pmCDPPortAddress1
            DisplayString,
        pmCDPPortAddress2
            DisplayString,
        pmCDPPortAddress3
            DisplayString,
        pmCDPPortPortId
            DisplayString,
        pmCDPPortCapabilities
            DisplayString,
        pmCDPPortVersion
            Integer32,
        pmCDPPortPlatform
            DisplayString,
        pmCDPPortSoftwareVersion
            DisplayString,
        pmCDPPortLocalVlan
            Integer32,
        pmCDPPortVoiceVlan
            Integer32,
        pmCDPPortDuplex
            INTEGER,
        pmCDPPortExtendedTrust
            EnabledStatus,
        pmCDPPortCosForUntrusted
            Integer32,
        pmCDPPortPowerConsumption
            DisplayString,
        pmCDPPortPowerRequestId
            Integer32,
        pmCDPPortPowerManagementId
            Integer32,
        pmCDPPortPowerAvailable
            DisplayString,
        pmCDPPortHasNeighbor
            DisplayString
}

pmCDPPortInfoIndex OBJECT-TYPE
    SYNTAX      Integer32 (1..65535)
    MAX-ACCESS  not-accessible
    STATUS      current
    DESCRIPTION
        "The Port number of the port for which this entry contains 
         CDP information."                                      
    ::= { pmCDPLocalInfoEntry 1 }

pmCDPPortDeviceId OBJECT-TYPE
    SYNTAX      DisplayString
    MAX-ACCESS  read-only
    STATUS      current
    DESCRIPTION
        "The device ID being advertised to the neighbors of this port."
    ::= { pmCDPLocalInfoEntry 2 }

pmCDPPortSystemName OBJECT-TYPE
    SYNTAX      DisplayString
    MAX-ACCESS  read-only
    STATUS      current
    DESCRIPTION
        "The system name being advertised to the neighbors of this port."
    ::= { pmCDPLocalInfoEntry 3 }

pmCDPPortAddress1 OBJECT-TYPE
    SYNTAX      DisplayString
    MAX-ACCESS  read-only
    STATUS      current
    DESCRIPTION
        "The address of local port."
    ::= { pmCDPLocalInfoEntry 4 }

pmCDPPortAddress2 OBJECT-TYPE
    SYNTAX      DisplayString
    MAX-ACCESS  read-only
    STATUS      current
    DESCRIPTION
        "The address of local port."
    ::= { pmCDPLocalInfoEntry 5 }

pmCDPPortAddress3 OBJECT-TYPE
    SYNTAX      DisplayString
    MAX-ACCESS  read-only
    STATUS      current
    DESCRIPTION
        "The address of local port."
    ::= { pmCDPLocalInfoEntry 6 }

pmCDPPortPortId OBJECT-TYPE
    SYNTAX      DisplayString
    MAX-ACCESS  read-only
    STATUS      current
    DESCRIPTION
        "The port interface being advertised to the neighbors of this port."
    ::= { pmCDPLocalInfoEntry 7 }

pmCDPPortCapabilities OBJECT-TYPE
    SYNTAX      DisplayString
    MAX-ACCESS  read-only
    STATUS      current
    DESCRIPTION
        "The capabilities being advertised to the neighbors of this port."
    ::= { pmCDPLocalInfoEntry 8 }

pmCDPPortVersion OBJECT-TYPE
    SYNTAX      Integer32 (1..2)
    MAX-ACCESS  read-only
    STATUS      current
    DESCRIPTION
        "The CDP version currently used."
    ::= { pmCDPLocalInfoEntry 9 }

pmCDPPortPlatform OBJECT-TYPE
    SYNTAX      DisplayString
    MAX-ACCESS  read-only
    STATUS      current
    DESCRIPTION
        "The platform information being advertised to the neighbors of
         this port."
    ::= { pmCDPLocalInfoEntry 10 }

pmCDPPortSoftwareVersion OBJECT-TYPE
    SYNTAX      DisplayString
    MAX-ACCESS  read-only
    STATUS      current
    DESCRIPTION
        "The address of local port."
    ::= { pmCDPLocalInfoEntry 11 }

pmCDPPortLocalVlan OBJECT-TYPE
    SYNTAX      Integer32 (1..4094)
    MAX-ACCESS  read-only
    STATUS      current
    DESCRIPTION
        "The PVID of this port."
    ::= { pmCDPLocalInfoEntry 12 }

pmCDPPortVoiceVlan OBJECT-TYPE
    SYNTAX      Integer32 (1..4094)
    MAX-ACCESS  read-only
    STATUS      current
    DESCRIPTION
        "The voice VLAN of this device."
    ::= { pmCDPLocalInfoEntry 13 }

pmCDPPortDuplex OBJECT-TYPE
    SYNTAX      INTEGER { Half(1), Full(2) }
    MAX-ACCESS  read-only
    STATUS      current
    DESCRIPTION
        "Indicates whether full or half duplex is used on this port."
    ::= { pmCDPLocalInfoEntry 14 }

pmCDPPortExtendedTrust OBJECT-TYPE
    SYNTAX      EnabledStatus
    MAX-ACCESS  read-only
    STATUS      current
    DESCRIPTION
        "Enabled means the device connected to this port is trusted,
         so the CoS value of packets received on this port will not
         be remarked. While disabled means the packets received on 
         this port will be marked using the following field."
    ::= { pmCDPLocalInfoEntry 15 }

pmCDPPortCosForUntrusted OBJECT-TYPE
    SYNTAX      Integer32 (0..7)
    MAX-ACCESS  read-only
    STATUS      current
    DESCRIPTION
        "The CoS value being used to remark packets received on this
        port when extended trust is disabled. This value is 0 if
        extended trust is enabled."
    ::= { pmCDPLocalInfoEntry 16 }

pmCDPPortPowerConsumption OBJECT-TYPE
    SYNTAX      DisplayString
    MAX-ACCESS  read-only
    STATUS      current
    DESCRIPTION
        "Power consumed by PD connected to this port."
    ::= { pmCDPLocalInfoEntry 17 }

pmCDPPortPowerRequestId OBJECT-TYPE
    SYNTAX      Integer32 (0..65535)
    MAX-ACCESS  read-only
    STATUS      current
    DESCRIPTION
        "The latest power request ID received from the neighbor of this
         port."
    ::= { pmCDPLocalInfoEntry 18 }

pmCDPPortPowerManagementId OBJECT-TYPE
    SYNTAX      Integer32 (0..65536)
    MAX-ACCESS  read-only
    STATUS      current
    DESCRIPTION
        "This value increases by 1 or 2 whenever power available
         information changes value."
    ::= { pmCDPLocalInfoEntry 19 }

pmCDPPortPowerAvailable OBJECT-TYPE
    SYNTAX      DisplayString
    MAX-ACCESS  read-only
    STATUS      current
    DESCRIPTION
        "Max power consumption available on this port."
    ::= { pmCDPLocalInfoEntry 20 }

pmCDPPortHasNeighbor OBJECT-TYPE
    SYNTAX      DisplayString
    MAX-ACCESS  read-only
    STATUS      current
    DESCRIPTION
        "To indicate whether this port currently has neighbor."
    ::= { pmCDPLocalInfoEntry 21 }


-- ----------------------------------------------------------------- -- 
-- CDP Local Statistics
-- ----------------------------------------------------------------- -- 
pmCDPLocalStatisticsTable OBJECT-TYPE
    SYNTAX      SEQUENCE OF PmCDPLocalStatisticsEntry
    MAX-ACCESS  not-accessible
    STATUS      current
    DESCRIPTION
        "This table contains CDP local port 
         information."
    ::= { pmCdpLocalInformation 2 }

pmCDPLocalStatisticsEntry OBJECT-TYPE
    SYNTAX      PmCDPLocalStatisticsEntry
    MAX-ACCESS  not-accessible
    STATUS      current
    DESCRIPTION
        "A list of local statistics on every port for 
         Cisco Discovery Protocol."
    INDEX  { pmCDPPortStatisticsIndex }
    ::= { pmCDPLocalStatisticsTable 1 }

PmCDPLocalStatisticsEntry ::= 
    SEQUENCE {
        pmCDPPortStatisticsIndex
            Integer32,
        pmCDPPortRxV1Count
            Integer32,
        pmCDPPortRxV2Count 
            Integer32,
        pmCDPPortRxTotalCount
            Integer32,
        pmCDPPortTxV1Count
            Integer32,
        pmCDPPortTxV2Count 
            Integer32,
        pmCDPPortTxTotalCount
            Integer32,
        pmCDPPortErrorChecksumCount 
            Integer32,
        pmCDPPortErrorOtherCount
            Integer32
}

pmCDPPortStatisticsIndex OBJECT-TYPE
    SYNTAX      Integer32 (1..65535)
    MAX-ACCESS  not-accessible
    STATUS      current
    DESCRIPTION
        "The Port number of the port for which this entry contains 
         CDP statistics."                                      
    ::= { pmCDPLocalStatisticsEntry 1 }

pmCDPPortRxV1Count OBJECT-TYPE
    SYNTAX      Integer32 (1..65535)
    MAX-ACCESS  read-only
    STATUS      current
    DESCRIPTION
        "Received v1 CDP packet count."                                      
    ::= { pmCDPLocalStatisticsEntry 2 }

pmCDPPortRxV2Count OBJECT-TYPE
    SYNTAX      Integer32 (1..65535)
    MAX-ACCESS  read-only
    STATUS      current
    DESCRIPTION
        "Received v2 CDP packet count."
    ::= { pmCDPLocalStatisticsEntry 3 }

pmCDPPortRxTotalCount OBJECT-TYPE
    SYNTAX      Integer32 (1..65535)
    MAX-ACCESS  read-only
    STATUS      current
    DESCRIPTION
        "Received all CDP packet count."
    ::= { pmCDPLocalStatisticsEntry 4 }

pmCDPPortTxV1Count OBJECT-TYPE
    SYNTAX      Integer32 (1..65535)
    MAX-ACCESS  read-only
    STATUS      current
    DESCRIPTION
        "Transmitted v1 CDP packet count."                                      
    ::= { pmCDPLocalStatisticsEntry 5 }

pmCDPPortTxV2Count OBJECT-TYPE
    SYNTAX      Integer32 (1..65535)
    MAX-ACCESS  read-only
    STATUS      current
    DESCRIPTION
        "Transmitted v2 CDP packet count."
    ::= { pmCDPLocalStatisticsEntry 6 }

pmCDPPortTxTotalCount OBJECT-TYPE
    SYNTAX      Integer32 (1..65535)
    MAX-ACCESS  read-only
    STATUS      current
    DESCRIPTION
        "Transmitted all CDP packet count."
    ::= { pmCDPLocalStatisticsEntry 7 }

pmCDPPortErrorChecksumCount OBJECT-TYPE
    SYNTAX      Integer32 (1..65535)
    MAX-ACCESS  read-only
    STATUS      current
    DESCRIPTION
        "Checksum error counter when receiving CDP packet."
    ::= { pmCDPLocalStatisticsEntry 8 }

pmCDPPortErrorOtherCount OBJECT-TYPE
    SYNTAX      Integer32 (1..65535)
    MAX-ACCESS  read-only
    STATUS      current
    DESCRIPTION
        "Other error counter when receiving CDP packet."
    ::= { pmCDPLocalStatisticsEntry 9 }


-- ----------------------------------------------------------------- -- 
-- CDP Neighbor Information
-- ----------------------------------------------------------------- -- 
pmCDPNeighborInfoTable OBJECT-TYPE
    SYNTAX      SEQUENCE OF PmCDPNeighborInfoEntry
    MAX-ACCESS  not-accessible
    STATUS      current
    DESCRIPTION
        "This table contains CDP neighbor port 
         information."
    ::= { pmCdpNeighborInformation 1 }

pmCDPNeighborInfoEntry OBJECT-TYPE
    SYNTAX      PmCDPNeighborInfoEntry
    MAX-ACCESS  not-accessible
    STATUS      current
    DESCRIPTION
        "A list of neighbor information on every port for 
         Cisco Discovery Protocol."
    INDEX  { pmCDPNeighborPortIndex }
    ::= { pmCDPNeighborInfoTable 1 }

PmCDPNeighborInfoEntry ::= 
    SEQUENCE {
        pmCDPNeighborPortIndex
            Integer32,
        pmCDPNeighborDeviceId 
            DisplayString,
        pmCDPNeighborSystemName
            DisplayString,
        pmCDPNeighborCdpVersion
            DisplayString,
        pmCDPNeighborTimeToLive
            DisplayString,
        pmCDPNeighborNeighborInterface
            DisplayString,
        pmCDPNeighborAddress
            DisplayString,
        pmCDPNeighborCapabilities
            DisplayString,
        pmCDPNeighborSoftwareVersion
            DisplayString,
        pmCDPNeighborPlatform
            DisplayString,
        pmCDPNeighborNativeVlan
            DisplayString,
        pmCDPNeighborVoiceVlan
            DisplayString,
        pmCDPNeighborDuplex
            DisplayString,
        pmCDPNeighborExtendedTrust
            DisplayString,
        pmCDPNeighborCosForUntrusted
            DisplayString,
        pmCDPNeighborManagementAddress
            DisplayString,
        pmCDPNeighborPowerConsumption
            DisplayString,
        pmCDPNeighborPowerRequestId
            DisplayString,
        pmCDPNeighborPowerManagementId
            DisplayString,
        pmCDPNeighborPowerAvailable
            DisplayString
    }

pmCDPNeighborPortIndex OBJECT-TYPE
    SYNTAX      Integer32 (1..65535)
    MAX-ACCESS  not-accessible
    STATUS      current
    DESCRIPTION
        "The Port number of the port for which this entry contains 
         CDP neighbor information."                                      
    ::= { pmCDPNeighborInfoEntry 1 }

pmCDPNeighborDeviceId OBJECT-TYPE
    SYNTAX      DisplayString
    MAX-ACCESS  read-only
    STATUS      current
    DESCRIPTION
        "Device ID of the neighbor device."                                      
    ::= { pmCDPNeighborInfoEntry 2 }

pmCDPNeighborSystemName OBJECT-TYPE
    SYNTAX      DisplayString
    MAX-ACCESS  read-only
    STATUS      current
    DESCRIPTION
        "System name of the neighbor device."                                      
    ::= { pmCDPNeighborInfoEntry 3 }

pmCDPNeighborCdpVersion OBJECT-TYPE
    SYNTAX      DisplayString
    MAX-ACCESS  read-only
    STATUS      current
    DESCRIPTION
        "CDP Version being used by the neighbor device."                                      
    ::= { pmCDPNeighborInfoEntry 4 }

pmCDPNeighborTimeToLive OBJECT-TYPE
    SYNTAX      DisplayString
    MAX-ACCESS  read-only
    STATUS      current
    DESCRIPTION
        "Amount of time this information will be kept before expiration."                                      
    ::= { pmCDPNeighborInfoEntry 5 }

pmCDPNeighborNeighborInterface OBJECT-TYPE
    SYNTAX      DisplayString
    MAX-ACCESS  read-only
    STATUS      current
    DESCRIPTION
        "The port being used on the neighbor device."                                      
    ::= { pmCDPNeighborInfoEntry 6 }

pmCDPNeighborAddress OBJECT-TYPE
    SYNTAX      DisplayString
    MAX-ACCESS  read-only
    STATUS      current
    DESCRIPTION
        "Addresses of the neighbor device."                                      
    ::= { pmCDPNeighborInfoEntry 7 }

pmCDPNeighborCapabilities OBJECT-TYPE
    SYNTAX      DisplayString
    MAX-ACCESS  read-only
    STATUS      current
    DESCRIPTION
        "The primary functions of the neighbor device."                                      
    ::= { pmCDPNeighborInfoEntry 8 }

pmCDPNeighborSoftwareVersion OBJECT-TYPE
    SYNTAX      DisplayString
    MAX-ACCESS  read-only
    STATUS      current
    DESCRIPTION
        "Software version of the neighbor device."                                      
    ::= { pmCDPNeighborInfoEntry 9 }

pmCDPNeighborPlatform OBJECT-TYPE
    SYNTAX      DisplayString
    MAX-ACCESS  read-only
    STATUS      current
    DESCRIPTION
        "Platform of the neighbor device."                                      
    ::= { pmCDPNeighborInfoEntry 10 }

pmCDPNeighborNativeVlan OBJECT-TYPE
    SYNTAX      DisplayString
    MAX-ACCESS  read-only
    STATUS      current
    DESCRIPTION
        "VLAN of the neighbor device."                                      
    ::= { pmCDPNeighborInfoEntry 11 }

pmCDPNeighborVoiceVlan OBJECT-TYPE
    SYNTAX      DisplayString
    MAX-ACCESS  read-only
    STATUS      current
    DESCRIPTION
        "Voice VLAN of the neighbor device."                                      
    ::= { pmCDPNeighborInfoEntry 12 }

pmCDPNeighborDuplex OBJECT-TYPE
    SYNTAX      DisplayString
    MAX-ACCESS  read-only
    STATUS      current
    DESCRIPTION
        "Full or half duplex is being used by the neighbor device."                                      
    ::= { pmCDPNeighborInfoEntry 13 }

pmCDPNeighborExtendedTrust OBJECT-TYPE
    SYNTAX      DisplayString
    MAX-ACCESS  read-only
    STATUS      current
    DESCRIPTION
        "Enabled means the CoS value of packets received from this
         neighbor will not be remarked, while disabled means that
         the packets will be remarked using the value of the next field."                                      
    ::= { pmCDPNeighborInfoEntry 14 }

pmCDPNeighborCosForUntrusted OBJECT-TYPE
    SYNTAX      DisplayString
    MAX-ACCESS  read-only
    STATUS      current
    DESCRIPTION
        "The CoS value being used to remark packets received from this
         neighbor when extended trust is disabled. This value is 0 if
         extended trust is enabled."                                      
    ::= { pmCDPNeighborInfoEntry 15 }

pmCDPNeighborManagementAddress OBJECT-TYPE
    SYNTAX      DisplayString
    MAX-ACCESS  read-only
    STATUS      current
    DESCRIPTION
        "The CoS value being used to remark packets received from this
         neighbor when extended trust is disabled. This value is 0 if
         extended trust is enabled."                                      
    ::= { pmCDPNeighborInfoEntry 16 }

pmCDPNeighborPowerConsumption OBJECT-TYPE
    SYNTAX      DisplayString
    MAX-ACCESS  read-only
    STATUS      current
    DESCRIPTION
        "Power consumed by PD of the neighbor."                                      
    ::= { pmCDPNeighborInfoEntry 17 }

pmCDPNeighborPowerRequestId OBJECT-TYPE
    SYNTAX      DisplayString
    MAX-ACCESS  read-only
    STATUS      current
    DESCRIPTION
        "The latest power request ID received from this neighbor."                                      
    ::= { pmCDPNeighborInfoEntry 18 }

pmCDPNeighborPowerManagementId OBJECT-TYPE
    SYNTAX      DisplayString
    MAX-ACCESS  read-only
    STATUS      current
    DESCRIPTION
        "This value increases by 1 or 2 whenever power available
         information changes value."                                      
    ::= { pmCDPNeighborInfoEntry 19 }

pmCDPNeighborPowerAvailable OBJECT-TYPE
    SYNTAX      DisplayString
    MAX-ACCESS  read-only
    STATUS      current
    DESCRIPTION
        "Max power supply on this port."
    ::= { pmCDPNeighborInfoEntry 20 }

pmCDPNeighborCount OBJECT-TYPE
    SYNTAX      Integer32 (1..65535)
    MAX-ACCESS  read-only
    STATUS      current
    DESCRIPTION
        "Total neighbor counter."
    ::= { pmCdpNeighborInformation 2 }


END
