--
-- Perseus-MIB.mib
-- MIB generated by MG-SOFT Visual MIB Builder 2023 (64-bit) Version 16.00  Build 1600
-- Thursday, June 05, 2025 at 14:48:02
--
 
--  Perseus.mib
-- MIB generated by MG-SOFT Visual MIB Builder 2024 (64-bit) Version 17.00  Build 1700
-- Thursday, January 23, 2025 at 09:32:49
--
--      POSEIDON-MIB 1.00
-- History:    
-- 1. 10        28. 9. 2023 Vit Olmr      - Unification of MIB devices and datalogger
 
        Perseus-MIB DEFINITIONS ::= BEGIN
 
                IMPORTS
                        OBJECT-TYPE                    
                                FROM RFC-1212                  
                        TRAP-TYPE                      
                                FROM RFC-1215                  
                        enterprises, TimeTicks                 
                                FROM RFC1155-SMI                       
                        sysName                
                                FROM RFC1213-MIB;
       
       
--
-- Type definitions
--
       
--  Type definitions
--
-- Type definitions
--
                MeterID ::= INTEGER (1..100000)
 
                State ::= INTEGER
                        {
                        unknown(0),
                        ok(1),
                        varInvalid(2),
                        meterInvalid(3),
                        alarmLow(4),
                        alarmHigh(5),
                        inactive(6)
                        }
 
                Enable ::= INTEGER
                        {
                        disabled(0),
                        enabled(1)
                        }
 
                MeterType ::= INTEGER
                        {
                        local(1),
                        oneWire(2),
                        mbus(4),
                        modbusRTU(5),
                        modbusTCP(6),
                        httpXML(7),
                        virtual(8),
                        mQTT(9),
                        snmp(10),
                        localGPS(11)
                        }
 
                VarUnit ::= OCTET STRING
 
                VarType ::= INTEGER
                        {
                        discreteInput(0),
                        discreteOutput(1),
                        analogSensor(2),
                        analogOutput(3),
                        discreteIncremental(4),
                        none(5),
                        analogIncremental(6)
                        }
 
                ActionType ::= INTEGER
                        {
                        actionSet(0),
                        email(1),
                        sms(2),
                        snmptrap(3),
                        setOutput(4),
                        script(5)
                        }
 
--      0x7FFF FFFF
                NonNegativeInteger ::= INTEGER (0..2147483647)
 
--    Type definitions
--
-- Type definitions
--
-- Type Definitions
--
                PositiveInteger ::= INTEGER (1..2147483647)
 
                SensorID ::= INTEGER (0..65535)
 
--      will hold info that this sensor has alarm (trap) enabled
-- and/or sets output pin (thermostat functionality)
                TimeStamp ::= TimeTicks
 
                UnitType ::= INTEGER
                        {
                        celsius(0),
                        fahrenheit(1),
                        kelvin(2),
                        percent(3),
                        volt(4),
                        miliAmper(5),
                        noUnit(6),
                        pulse(7),
                        switch(8),
                        dewPoint(9),
                        absoluteHumidity(10),
                        pressure(11),
                        universal(12)
                        }
 
                VarName ::= OCTET STRING
 
                VarString ::= OCTET STRING
 
                VarID ::= INTEGER (1..1000000000)
 
       
--
-- Node definitions
--
       
--  Node definitions
--
-- Node definitions
--
-- Node definitions
--
-- Node definitions
--
-- Node Definitions
--
-- 1.3.6.1.4.1.21796
-- 1.3.6.1.4.1.21796
-- 1.3.6.1.4.1.21796
-- 1.3.6.1.4.1.21796
                -- 1.3.6.1.4.1.21796
                hwgroup OBJECT IDENTIFIER ::= { enterprises 21796 }
 
               
--    1.3.6.1.4.1.21796.5
-- 1.3.6.1.4.1.21796.5
-- 1.3.6.1.4.1.21796.5
                -- 1.3.6.1.4.1.21796.5
                charon5 OBJECT IDENTIFIER ::= { hwgroup 5 }
 
               
--     1.3.6.1.4.1.21796.3.3
-- 1.3.6.1.4.1.21796.5.1
-- 1.3.6.1.4.1.21796.5.1
-- 1.3.6.1.4.1.21796.5.1
                -- 1.3.6.1.4.1.21796.5.1
                perseus OBJECT IDENTIFIER ::= { charon5 1 }
 
               
--    1.3.6.1.4.1.21796.5.1.1
-- 1.3.6.1.4.1.21796.5.1.1
-- 1.3.6.1.4.1.21796.5.1.1
                -- 1.3.6.1.4.1.21796.5.1.1
                meterCount OBJECT-TYPE
                        SYNTAX INTEGER
                        ACCESS read-write
                        STATUS mandatory
                        ::= { perseus 1 }
 
               
--     1.3.6.1.4.1.21796.3.3.100
-- 1.3.6.1.4.1.21796.5.1.2
-- 1.3.6.1.4.1.21796.5.1.2
-- 1.3.6.1.4.1.21796.5.1.2
                -- 1.3.6.1.4.1.21796.5.1.2
                meterTable OBJECT-TYPE
                        SYNTAX SEQUENCE OF MeterEntry
                        ACCESS not-accessible
                        STATUS mandatory
                        ::= { perseus 2 }
 
               
--     1.3.6.1.4.1.21796.3.3.100.1
-- 1.3.6.1.4.1.21796.5.1.2.1
-- 1.3.6.1.4.1.21796.5.1.2.1
-- 1.3.6.1.4.1.21796.5.1.2.1
                -- 1.3.6.1.4.1.21796.5.1.2.1
                meterEntry OBJECT-TYPE
                        SYNTAX MeterEntry
                        ACCESS not-accessible
                        STATUS mandatory
                        INDEX { meterID }
                        ::= { meterTable 1 }
 
               
                MeterEntry ::=
                        SEQUENCE {
                                meterID
                                        MeterID,
                                meterName
                                        OCTET STRING,
                                meterState
                                        State,
                                meterEnable
                                        Enable,
                                meterType
                                        MeterType,
                                meterPortID
                                        INTEGER,
                                meterPeriod
                                        INTEGER
                         }
 
--     1.3.6.1.4.1.21796.3.3.100.1.4
-- 1.3.6.1.4.1.21796.5.1.2.1.1
-- 1.3.6.1.4.1.21796.5.1.2.1.1
-- 1.3.6.1.4.1.21796.5.1.2.1.1
                -- 1.3.6.1.4.1.21796.5.1.2.1.1
                meterID OBJECT-TYPE
                        SYNTAX MeterID
                        ACCESS read-only
                        STATUS mandatory
                        ::= { meterEntry 1 }
 
               
--     1.3.6.1.4.1.21796.3.3.100.1.7
-- 1.3.6.1.4.1.21796.5.1.2.1.2
-- 1.3.6.1.4.1.21796.5.1.2.1.2
-- 1.3.6.1.4.1.21796.5.1.2.1.2
                -- 1.3.6.1.4.1.21796.5.1.2.1.2
                meterName OBJECT-TYPE
                        SYNTAX OCTET STRING
                        ACCESS read-write
                        STATUS mandatory
                        ::= { meterEntry 2 }
 
               
--     1.3.6.1.4.1.21796.3.3.100.1.9
-- 1.3.6.1.4.1.21796.5.1.2.1.3
-- 1.3.6.1.4.1.21796.5.1.2.1.3
-- 1.3.6.1.4.1.21796.5.1.2.1.3
                -- 1.3.6.1.4.1.21796.5.1.2.1.3
                meterState OBJECT-TYPE
                        SYNTAX State
                        ACCESS read-write
                        STATUS mandatory
                        ::= { meterEntry 3 }
 
               
--     1.3.6.1.4.1.21796.3.3.100.1.2
-- 1.3.6.1.4.1.21796.5.1.2.1.5
-- 1.3.6.1.4.1.21796.5.1.2.1.5
-- 1.3.6.1.4.1.21796.5.1.2.1.4
                -- 1.3.6.1.4.1.21796.5.1.2.1.4
                meterEnable OBJECT-TYPE
                        SYNTAX Enable
                        ACCESS read-write
                        STATUS mandatory
                        ::= { meterEntry 4 }
 
               
--     1.3.6.1.4.1.21796.3.3.100.1.5
-- 1.3.6.1.4.1.21796.5.1.2.1.6
-- 1.3.6.1.4.1.21796.5.1.2.1.6
-- 1.3.6.1.4.1.21796.5.1.2.1.5
                -- 1.3.6.1.4.1.21796.5.1.2.1.5
                meterType OBJECT-TYPE
                        SYNTAX MeterType
                        ACCESS read-only
                        STATUS mandatory
                        ::= { meterEntry 5 }
 
               
--     1.3.6.1.4.1.21796.3.3.100.1.6
-- 1.3.6.1.4.1.21796.5.1.2.1.7
-- 1.3.6.1.4.1.21796.5.1.2.1.7
-- 1.3.6.1.4.1.21796.5.1.2.1.6
                -- 1.3.6.1.4.1.21796.5.1.2.1.6
                meterPortID OBJECT-TYPE
                        SYNTAX INTEGER
                        ACCESS read-only
                        STATUS mandatory
                        ::= { meterEntry 6 }
 
               
--     1.3.6.1.4.1.21796.3.3.100.1.8
-- 1.3.6.1.4.1.21796.5.1.2.1.8
-- 1.3.6.1.4.1.21796.5.1.2.1.8
-- 1.3.6.1.4.1.21796.5.1.2.1.7
                -- 1.3.6.1.4.1.21796.5.1.2.1.7
                meterPeriod OBJECT-TYPE
                        SYNTAX INTEGER
                        ACCESS read-write
                        STATUS mandatory
                        ::= { meterEntry 7 }
 
               
--     1.3.6.1.4.1.21796.3.3.72
-- 1.3.6.1.4.1.21796.5.1.3
-- 1.3.6.1.4.1.21796.5.1.3
-- 1.3.6.1.4.1.21796.5.1.3
                -- 1.3.6.1.4.1.21796.5.1.3
                varTable OBJECT-TYPE
                        SYNTAX SEQUENCE OF VarEntry
                        ACCESS not-accessible
                        STATUS mandatory
                        ::= { perseus 3 }
 
               
--     1.3.6.1.4.1.21796.3.3.72.1
-- 1.3.6.1.4.1.21796.5.1.3.1
-- 1.3.6.1.4.1.21796.5.1.3.1
-- 1.3.6.1.4.1.21796.5.1.3.1
                -- 1.3.6.1.4.1.21796.5.1.3.1
                varEntry OBJECT-TYPE
                        SYNTAX VarEntry
                        ACCESS not-accessible
                        STATUS mandatory
                        INDEX { meterID, varID }
                        ::= { varTable 1 }
 
               
                VarEntry ::=
                        SEQUENCE {
                                varID
                                        INTEGER,
                                varName
                                        OCTET STRING,
                                varState
                                        State,
                                varValue
                                        OCTET STRING,
                                varUnit
                                        VarUnit,
                                varEnable
                                        Enable,
                                varType
                                        VarType,
                                varApDelta
                                        OCTET STRING,
                                varDecimal
                                        INTEGER,
                                varPulseTime
                                        INTEGER,
                                varWritable
                                        INTEGER,
                                varValueInt
                                        INTEGER
                         }
 
--     1.3.6.1.4.1.21796.3.3.72.1.4
-- 1.3.6.1.4.1.21796.5.1.3.1.1
-- 1.3.6.1.4.1.21796.5.1.3.1.1
-- 1.3.6.1.4.1.21796.5.1.3.1.1
                -- 1.3.6.1.4.1.21796.5.1.3.1.1
                varID OBJECT-TYPE
                        SYNTAX INTEGER (1..100000)
                        ACCESS read-only
                        STATUS mandatory
                        ::= { varEntry 1 }
 
               
--     1.3.6.1.4.1.21796.3.3.72.1.7
-- 1.3.6.1.4.1.21796.5.1.3.1.2
-- 1.3.6.1.4.1.21796.5.1.3.1.2
-- 1.3.6.1.4.1.21796.5.1.3.1.2
                -- 1.3.6.1.4.1.21796.5.1.3.1.2
                varName OBJECT-TYPE
                        SYNTAX OCTET STRING
                        ACCESS read-write
                        STATUS mandatory
                        ::= { varEntry 2 }
 
               
--     1.3.6.1.4.1.21796.3.3.72.1.13
-- 1.3.6.1.4.1.21796.5.1.3.1.3
-- 1.3.6.1.4.1.21796.5.1.3.1.3
-- 1.3.6.1.4.1.21796.5.1.3.1.3
                -- 1.3.6.1.4.1.21796.5.1.3.1.3
                varState OBJECT-TYPE
                        SYNTAX State
                        ACCESS read-write
                        STATUS mandatory
                        ::= { varEntry 3 }
 
               
--     1.3.6.1.4.1.21796.3.3.72.1.9
-- 1.3.6.1.4.1.21796.5.1.3.1.4
-- 1.3.6.1.4.1.21796.5.1.3.1.4
-- 1.3.6.1.4.1.21796.5.1.3.1.4
                -- 1.3.6.1.4.1.21796.5.1.3.1.4
                varValue OBJECT-TYPE
                        SYNTAX OCTET STRING
                        ACCESS read-write
                        STATUS mandatory
                        ::= { varEntry 4 }
 
               
--     1.3.6.1.4.1.21796.3.3.72.1.8
-- 1.3.6.1.4.1.21796.5.1.3.1.5
-- 1.3.6.1.4.1.21796.5.1.3.1.5
-- 1.3.6.1.4.1.21796.5.1.3.1.5
                -- 1.3.6.1.4.1.21796.5.1.3.1.5
                varUnit OBJECT-TYPE
                        SYNTAX VarUnit
                        ACCESS read-write
                        STATUS mandatory
                        ::= { varEntry 5 }
 
               
--     1.3.6.1.4.1.21796.3.3.72.1.2
-- 1.3.6.1.4.1.21796.5.1.3.1.6
-- 1.3.6.1.4.1.21796.5.1.3.1.6
-- 1.3.6.1.4.1.21796.5.1.3.1.6
                -- 1.3.6.1.4.1.21796.5.1.3.1.6
                varEnable OBJECT-TYPE
                        SYNTAX Enable
                        ACCESS read-write
                        STATUS mandatory
                        ::= { varEntry 6 }
 
               
--     1.3.6.1.4.1.21796.3.3.72.1.6
-- 1.3.6.1.4.1.21796.5.1.3.1.8
-- 1.3.6.1.4.1.21796.5.1.3.1.7
-- 1.3.6.1.4.1.21796.5.1.3.1.7
                -- 1.3.6.1.4.1.21796.5.1.3.1.7
                varType OBJECT-TYPE
                        SYNTAX VarType
                        ACCESS read-only
                        STATUS mandatory
                        ::= { varEntry 7 }
 
               
--     1.3.6.1.4.1.21796.3.3.72.1.10
-- 1.3.6.1.4.1.21796.5.1.3.1.9
-- 1.3.6.1.4.1.21796.5.1.3.1.8
-- 1.3.6.1.4.1.21796.5.1.3.1.8
                -- 1.3.6.1.4.1.21796.5.1.3.1.8
                varApDelta OBJECT-TYPE
                        SYNTAX OCTET STRING
                        ACCESS read-write
                        STATUS mandatory
                        ::= { varEntry 8 }
 
               
--     1.3.6.1.4.1.21796.3.3.72.1.11
-- 1.3.6.1.4.1.21796.5.1.3.1.10
-- 1.3.6.1.4.1.21796.5.1.3.1.9
-- 1.3.6.1.4.1.21796.5.1.3.1.9
                -- 1.3.6.1.4.1.21796.5.1.3.1.9
                varDecimal OBJECT-TYPE
                        SYNTAX INTEGER (-15..15)
                        ACCESS read-only
                        STATUS mandatory
                        ::= { varEntry 9 }
 
               
--     1.3.6.1.4.1.21796.3.3.72.1.12
-- 1.3.6.1.4.1.21796.5.1.3.1.11
-- 1.3.6.1.4.1.21796.5.1.3.1.10
-- 1.3.6.1.4.1.21796.5.1.3.1.10
                -- 1.3.6.1.4.1.21796.5.1.3.1.10
                varPulseTime OBJECT-TYPE
                        SYNTAX INTEGER
                        ACCESS read-write
                        STATUS mandatory
                        ::= { varEntry 10 }
 
               
--     1.3.6.1.4.1.21796.3.3.72.1.14
-- 1.3.6.1.4.1.21796.5.1.3.1.12
-- 1.3.6.1.4.1.21796.5.1.3.1.11
-- 1.3.6.1.4.1.21796.5.1.3.1.11
                -- 1.3.6.1.4.1.21796.5.1.3.1.11
                varWritable OBJECT-TYPE
                        SYNTAX INTEGER
                                {
                                no(0),
                                yes(1)
                                }
                        ACCESS read-only
                        STATUS mandatory
                        DEFVAL { 0 }
                        ::= { varEntry 11 }
 
               
--     1.3.6.1.4.1.21796.3.3.72.1.9
-- 1.3.6.1.4.1.21796.5.1.3.1.4
-- 1.3.6.1.4.1.21796.5.1.3.1.12
-- 1.3.6.1.4.1.21796.5.1.3.1.12
                -- 1.3.6.1.4.1.21796.5.1.3.1.12
                varValueInt OBJECT-TYPE
                        SYNTAX INTEGER
                        ACCESS read-write
                        STATUS mandatory
                        ::= { varEntry 12 }
 
               
--     1.3.6.1.4.1.21796.3.3.73
-- 1.3.6.1.4.1.21796.5.1.4
-- 1.3.6.1.4.1.21796.5.1.4
-- 1.3.6.1.4.1.21796.5.1.4
                -- 1.3.6.1.4.1.21796.5.1.4
                conditionTable OBJECT-TYPE
                        SYNTAX SEQUENCE OF ConditionEntry
                        ACCESS not-accessible
                        STATUS mandatory
                        ::= { perseus 4 }
 
               
--     1.3.6.1.4.1.21796.3.3.73.1
-- 1.3.6.1.4.1.21796.5.1.4.1
-- 1.3.6.1.4.1.21796.5.1.4.1
-- 1.3.6.1.4.1.21796.5.1.4.1
                -- 1.3.6.1.4.1.21796.5.1.4.1
                conditionEntry OBJECT-TYPE
                        SYNTAX ConditionEntry
                        ACCESS not-accessible
                        STATUS mandatory
                        INDEX { meterID, varID, conditionID }
                        ::= { conditionTable 1 }
 
               
                ConditionEntry ::=
                        SEQUENCE {
                                conditionID
                                        MeterID,
                                conditionName
                                        OCTET STRING,
                                conditionState
                                        State,
                                conditionEnable
                                        Enable,
                                conditionTextID
                                        OCTET STRING,
                                conditionMin
                                        OCTET STRING,
                                conditionMax
                                        OCTET STRING,
                                conditionHyst
                                        OCTET STRING,
                                conditionDelay
                                        INTEGER
                         }
 
--     1.3.6.1.4.1.21796.3.3.73.1.3
-- 1.3.6.1.4.1.21796.5.1.4.1.1
-- 1.3.6.1.4.1.21796.5.1.4.1.1
-- 1.3.6.1.4.1.21796.5.1.4.1.1
                -- 1.3.6.1.4.1.21796.5.1.4.1.1
                conditionID OBJECT-TYPE
                        SYNTAX MeterID
                        ACCESS read-only
                        STATUS mandatory
                        ::= { conditionEntry 1 }
 
               
--     1.3.6.1.4.1.21796.3.3.73.1.7
-- 1.3.6.1.4.1.21796.5.1.4.1.2
-- 1.3.6.1.4.1.21796.5.1.4.1.2
-- 1.3.6.1.4.1.21796.5.1.4.1.2
                -- 1.3.6.1.4.1.21796.5.1.4.1.2
                conditionName OBJECT-TYPE
                        SYNTAX OCTET STRING
                        ACCESS read-write
                        STATUS mandatory
                        ::= { conditionEntry 2 }
 
               
--     1.3.6.1.4.1.21796.3.3.73.1.12
-- 1.3.6.1.4.1.21796.5.1.4.1.3
-- 1.3.6.1.4.1.21796.5.1.4.1.3
-- 1.3.6.1.4.1.21796.5.1.4.1.3
                -- 1.3.6.1.4.1.21796.5.1.4.1.3
                conditionState OBJECT-TYPE
                        SYNTAX State
                        ACCESS read-only
                        STATUS mandatory
                        ::= { conditionEntry 3 }
 
               
--     1.3.6.1.4.1.21796.3.3.73.1.2
-- 1.3.6.1.4.1.21796.5.1.4.1.4
-- 1.3.6.1.4.1.21796.5.1.4.1.4
-- 1.3.6.1.4.1.21796.5.1.4.1.4
                -- 1.3.6.1.4.1.21796.5.1.4.1.4
                conditionEnable OBJECT-TYPE
                        SYNTAX Enable
                        ACCESS read-write
                        STATUS mandatory
                        ::= { conditionEntry 4 }
 
               
--     1.3.6.1.4.1.21796.3.3.73.1.6
-- 1.3.6.1.4.1.21796.5.1.4.1.5
-- 1.3.6.1.4.1.21796.5.1.4.1.5
-- 1.3.6.1.4.1.21796.5.1.4.1.5
                -- 1.3.6.1.4.1.21796.5.1.4.1.5
                conditionTextID OBJECT-TYPE
                        SYNTAX OCTET STRING
                        ACCESS read-write
                        STATUS mandatory
                        ::= { conditionEntry 5 }
 
               
--     1.3.6.1.4.1.21796.3.3.73.1.8
-- 1.3.6.1.4.1.21796.5.1.4.1.6
-- 1.3.6.1.4.1.21796.5.1.4.1.6
-- 1.3.6.1.4.1.21796.5.1.4.1.6
                -- 1.3.6.1.4.1.21796.5.1.4.1.6
                conditionMin OBJECT-TYPE
                        SYNTAX OCTET STRING
                        ACCESS read-write
                        STATUS mandatory
                        ::= { conditionEntry 6 }
 
               
--     1.3.6.1.4.1.21796.3.3.73.1.9
-- 1.3.6.1.4.1.21796.5.1.4.1.7
-- 1.3.6.1.4.1.21796.5.1.4.1.7
-- 1.3.6.1.4.1.21796.5.1.4.1.7
                -- 1.3.6.1.4.1.21796.5.1.4.1.7
                conditionMax OBJECT-TYPE
                        SYNTAX OCTET STRING
                        ACCESS read-write
                        STATUS mandatory
                        ::= { conditionEntry 7 }
 
               
--     1.3.6.1.4.1.21796.3.3.73.1.10
-- 1.3.6.1.4.1.21796.5.1.4.1.8
-- 1.3.6.1.4.1.21796.5.1.4.1.8
-- 1.3.6.1.4.1.21796.5.1.4.1.8
                -- 1.3.6.1.4.1.21796.5.1.4.1.8
                conditionHyst OBJECT-TYPE
                        SYNTAX OCTET STRING
                        ACCESS read-write
                        STATUS mandatory
                        ::= { conditionEntry 8 }
 
               
--     1.3.6.1.4.1.21796.3.3.73.1.11
-- 1.3.6.1.4.1.21796.5.1.4.1.9
-- 1.3.6.1.4.1.21796.5.1.4.1.9
-- 1.3.6.1.4.1.21796.5.1.4.1.9
                -- 1.3.6.1.4.1.21796.5.1.4.1.9
                conditionDelay OBJECT-TYPE
                        SYNTAX INTEGER
                        ACCESS read-write
                        STATUS mandatory
                        ::= { conditionEntry 9 }
 
               
                -- 1.3.6.1.4.1.21796.5.1.5
                actionTable OBJECT-TYPE
                        SYNTAX SEQUENCE OF ActionEntry
                        ACCESS not-accessible
                        STATUS mandatory
                        ::= { perseus 5 }
 
               
                -- 1.3.6.1.4.1.21796.5.1.5.1
                actionEntry OBJECT-TYPE
                        SYNTAX ActionEntry
                        ACCESS not-accessible
                        STATUS mandatory
                        INDEX { actionID, varID, conditionID }
                        ::= { actionTable 1 }
 
               
                ActionEntry ::=
                        SEQUENCE {
                                actionID
                                        INTEGER,
                                actionName
                                        OCTET STRING
                         }
 
                -- 1.3.6.1.4.1.21796.5.1.5.1.1
                actionID OBJECT-TYPE
                        SYNTAX INTEGER (1..1000000)
                        ACCESS read-only
                        STATUS mandatory
                        ::= { actionEntry 1 }
 
               
                -- 1.3.6.1.4.1.21796.5.1.5.1.2
                actionName OBJECT-TYPE
                        SYNTAX OCTET STRING
                        ACCESS read-only
                        STATUS mandatory
                        ::= { actionEntry 2 }
 
               
--  1.3.6.1.4.1.21796.5.1.100
                -- 1.3.6.1.4.1.21796.5.1.100
                info OBJECT IDENTIFIER ::= { perseus 100 }
 
               
--  1.3.6.1.4.1.21796.5.1.100.1
                -- 1.3.6.1.4.1.21796.5.1.100.1
                macAddress OBJECT-TYPE
                        SYNTAX OCTET STRING (SIZE (17))
                        ACCESS read-write
                        STATUS mandatory
                        ::= { info 1 }
 
               
--  1.3.6.1.4.1.21796.5.1.100.2
                -- 1.3.6.1.4.1.21796.5.1.100.2
                serNumber OBJECT-TYPE
                        SYNTAX OCTET STRING (SIZE (7..15))
                        ACCESS read-write
                        STATUS mandatory
                        ::= { info 2 }
 
               
--  1.3.6.1.4.1.21796.5.1.100.3
                -- 1.3.6.1.4.1.21796.5.1.100.3
                fwVersion OBJECT-TYPE
                        SYNTAX OCTET STRING (SIZE (5..15))
                        ACCESS read-write
                        STATUS mandatory
                        ::= { info 3 }
 
               
       
--
-- Trap definitions
--
       
--  Trap definitions
--
-- Trap of Condition definition
                condAlarm TRAP-TYPE
                        ENTERPRISE snmp
                        VARIABLES { sysName, actionID, actionName, meterID, meterName,
                                meterState, varID, varName, varValueInt, varValue,
                                varState, varDecimal, varUnit, macAddress }
                        ::=  3
 
       
        END
 
--
-- Perseus-MIB.mib
--
