WATCHGUARD-SMI DEFINITIONS ::= BEGIN

IMPORTS
    MODULE-IDENTITY, OBJECT-IDENTITY, enterprises
        FROM SNMPv2-SMI;


watchguard MODULE-IDENTITY
    LAST-UPDATED "200811100000Z"
    ORGANIZATION "WatchGuard Technologies, Inc."
    CONTACT-INFO
               "  WatchGuard Technologies, Inc.
               
                  505 Fifth Avenue South
                  Suite 500
                  Seattle, WA 98104
                  United States
                  
                  +1.206.613.6600 " 
         
    DESCRIPTION
            "The Structure of Management Information for 
            the WatchGuard enterprise."
    REVISION        "200811100000Z"
    DESCRIPTION
            "Initial version."
    ::= { enterprises 3097 }

wgProducts OBJECT-IDENTITY
    STATUS current
    DESCRIPTION
            "wgProducts is the root OBJECT IDENTIFIER of
            WatchGuard Product OIDs."
    ::= { watchguard 1 }

wgSystemConfigMIB OBJECT-IDENTITY
    STATUS current
    DESCRIPTION
            "wgSystemConfig is the root OBJECT IDENTIFIER of
            WatchGuard Firebox system configurations."
    ::= { watchguard 2 }

END
