-- 
-- Dell Management Module MIB
-- Management Information Base
-- 
-- This MIB is intended for use with the OpenManage Enterprise-Modular management software.
--
-- Copyright (c) 2015-2021 Dell Inc. or its subsidiaries.
-- All Rights Reserved.
--
-- Last Changed Revision: 1
-- Last Changed Date: 2021-07-07 22:00:00 -0500 (Wed, 07 July 2021)
--

DELL-MM-MIB DEFINITIONS ::= BEGIN
     
IMPORTS
	enterprises, TimeTicks
		FROM RFC1155-SMI
	OBJECT-TYPE
		FROM RFC-1212
	TRAP-TYPE
		FROM RFC-1215
	DisplayString
		FROM RFC1213-MIB;

-- text convention ------------------------------------------------------------------------     

	-------------------------------------------------------------------------------
	-- This data type is used to model textual information taken
	-- from the NVT ASCII character set.  By convention, objects
	-- with this syntax are declared as having
	--      SIZE (0..1023)
	-------------------------------------------------------------------------------
	DellString ::= DisplayString (SIZE (0..1023))

	DellMmType ::= INTEGER
	{
		other(1),               -- the MM type is not one of the following
		unknown(2),             -- the MM type is unknown
		mxMM(3)                 -- MX Chassis (MM)
	}

	DellStatus ::= INTEGER
	{
		other(1),               -- the status of the object is not one of the following:
		unknown(2),             -- the status of the object is unknown
										--  (not known or monitored)
		ok(3),                  -- the status of the object is ok
		nonCritical(4),         -- the status of the object is warning, non-critical
		critical(5),            -- the status of the object is critical (failure)
		nonRecoverable(6)       -- the status of the object is non-recoverable (dead)
	}

	-------------------------------------------------------------------------------
	-- DellPowerReading is a string representation of a floating point value, 
	--   having exactly 3 digits of precision, and a maximum of 31 characters.
	--
	-- DellChassisPowerIndexRange defines the possible chassis power instances
	--   in this MIB.
	--
	-- DellPSUIndexRange defines the possible Power Supply Unit (PSU) 
	--   instances, per chassis power instance, in this MIB.
	--
	-- DellPSUCapable is an enumeration of PSU presence and/or monitoring 
	--   capabilities.
	--
	-- DellTemperatureReading is an integer value, expressed in degrees Celsius.
	-------------------------------------------------------------------------------
	DellPowerReading ::= DisplayString (SIZE (0..32))

	DellPowerIndexRange ::= INTEGER (1..1)

	DellPSUIndexRange ::= INTEGER (1..6)

	DellPSUCapable ::= INTEGER
	{
		absent(1),      -- power supply is not present
		none(2),        -- no power monitoring abilities
		basic(3)        -- basic power monitoring abilities
	}

	DellTemperatureReading ::= INTEGER

	-------------------------------------------------------------------------------
	-- DellTimestamp is defined in the displayable format:
	--
	--			yyyymmddHHMMSS.uuuuuuDooo
	--
	-- where yyyy is the year, mm is the month number, dd is the day of the month,
	-- HHMMSS are the hours, minutes and seconds, respectively, uuuuuu is the
	-- number of microseconds, D is the UTC offset direction, and ooo is the 
	-- offset from UTC, in minutes. 
	--
	-- Note: D is a plus (+) sign if east of UTC, and a minus (-) if west of UTC.
	--
	-- For example, Wednesday, May 25, 1994, at 1:30:15 PM EDT
	--   would be represented as: 19940525133015.000000-300
	-------------------------------------------------------------------------------
	DellTimestamp ::= DisplayString (SIZE (26))	

-- MIB Objects and Tables --------------------------------------------------------

	dell                          OBJECT IDENTIFIER ::= { enterprises    674   }
	server3                       OBJECT IDENTIFIER ::= { dell           10892 }
	dmmOutOfBandGroup             OBJECT IDENTIFIER ::= { server3             6     }
	dmmInformationGroup           OBJECT IDENTIFIER ::= { dmmOutOfBandGroup     1 }
	dmmProductInfoGroup           OBJECT IDENTIFIER ::= { dmmInformationGroup   1 }
	dmmFirmwareGroup              OBJECT IDENTIFIER ::= { dmmInformationGroup   2 }

	dmmStatusGroup                OBJECT IDENTIFIER ::= { dmmOutOfBandGroup     2 }

	dmmChassisStatusGroup         OBJECT IDENTIFIER ::= { dmmOutOfBandGroup     3 }
	dmmStatusNowGroup             OBJECT IDENTIFIER ::= { dmmChassisStatusGroup 1 }
    
	dmmChassisPowerGroup          OBJECT IDENTIFIER ::= { dmmOutOfBandGroup     4 }

		DmmPowerTableEntry ::= SEQUENCE
		{
			dmmPowerChassisIndex			DellPowerIndexRange,
			dmmPowerIdlePower				DellPowerReading,
			dmmPowerKWhCumulative			DellPowerReading,
			dmmPowerKWhCumulativeTime		DellTimestamp,
			dmmPowerWattsPeakUsage			DellPowerReading,
			dmmPowerWattsPeakTime			DellTimestamp,
			dmmPowerWattsMinUsage			DellPowerReading,
			dmmPowerWattsMinTime			DellTimestamp,
			dmmPowerWattsReading			DellPowerReading
		}

		DmmPSUTableEntry ::= SEQUENCE
		{
			dmmPSUChassisIndex		DellPowerIndexRange,
			dmmPSUIndex				DellPSUIndexRange,
			dmmPSULocation			DellString,
			dmmPSUState				DellString,
			dmmPSUType 				DellString,
			dmmPSUCapacity 			DellPowerReading,
			dmmPSUVoltage  			DellPowerReading,
			dmmPSUCurrStatus  		DellStatus
		}

	dmmChassisAlert2Group         OBJECT IDENTIFIER ::= { dmmOutOfBandGroup    5 }
	dmmChassisAlert2Variables     OBJECT IDENTIFIER ::= { dmmChassisAlert2Group   1 }

	dmmGenericAlertGroup          OBJECT IDENTIFIER ::= { dmmOutOfBandGroup    6 }
	dmmGenericAlertVariables      OBJECT IDENTIFIER ::= { dmmGenericAlertGroup  1 }

	dmmiDRACAlertGroup          OBJECT IDENTIFIER ::= { dmmOutOfBandGroup    7 }

    dmmNWIOMAlertGroup          OBJECT IDENTIFIER ::= { dmmOutOfBandGroup    8 }

    dmmSASIOMAlertGroup          OBJECT IDENTIFIER ::= { dmmOutOfBandGroup    9 }
        

-- Variables and Traps ------------------------------------------------------------------------

	-------------------------------------------------------------------------------
	-- group: product information
	-------------------------------------------------------------------------------

	dmmProductName      OBJECT-TYPE
		SYNTAX          DellString
		ACCESS          read-only
		STATUS          mandatory
		DESCRIPTION     "This attribute defines the product name of a chassis management module." 
			::= { dmmProductInfoGroup 1 }

	dmmProductShortName OBJECT-TYPE
		SYNTAX          DellString
		ACCESS          read-only
		STATUS          mandatory
		DESCRIPTION     "This attribute defines the short product name of a chassis management module. " 
			::= { dmmProductInfoGroup 2 }

	dmmProductDescription OBJECT-TYPE
		SYNTAX          DellString
		ACCESS          read-only
		STATUS          mandatory
		DESCRIPTION     "This attribute defines the product description of a chassis management module. " 
			::= { dmmProductInfoGroup 3 }

	dmmProductManufacturer OBJECT-TYPE
		SYNTAX          DellString
		ACCESS          read-only
		STATUS          mandatory
		DESCRIPTION     "This attribute defines the product manufacturer of a chassis management module. " 
			::= { dmmProductInfoGroup 4 }

	dmmProductVersion OBJECT-TYPE
		SYNTAX          DellString
		ACCESS          read-only
		STATUS          mandatory
		DESCRIPTION     "This attribute defines the product version of a chassis management module. " 
			::= { dmmProductInfoGroup 5 }

	dmmChassisServiceTag OBJECT-TYPE
		SYNTAX          DellString
		ACCESS          read-only
		STATUS          mandatory
		DESCRIPTION     "This attribute defines the Service Tag of the chassis. " 
			::= { dmmProductInfoGroup 6 }

	dmmProductURL       OBJECT-TYPE
		SYNTAX          DellString 
		ACCESS          read-only
		STATUS          mandatory
		DESCRIPTION     "This attribute defines the out-of-band UI URL of a chassis management module. "
			::= { dmmProductInfoGroup 7 }
                        
	dmmProductChassisAssetTag  OBJECT-TYPE
		SYNTAX          DellString 
		ACCESS          read-only
		STATUS          mandatory
		DESCRIPTION     "This attribute defines the Asset Tag of the chassis. "
			::= { dmmProductInfoGroup 8 }

	dmmProductChassisName  OBJECT-TYPE
		SYNTAX          DellString 
		ACCESS          read-only
		STATUS          mandatory
		DESCRIPTION     "This attribute defines the name of the chassis. "
			::= { dmmProductInfoGroup 9 }

	dmmProductType  OBJECT-TYPE
		SYNTAX          DellMmType
		ACCESS          read-only
		STATUS          mandatory
		DESCRIPTION     "This attribute defines type of a remote management module "
			::= { dmmProductInfoGroup 10 }
               
	dmmProductChassisDataCenter  OBJECT-TYPE
		SYNTAX          DellString 
		ACCESS          read-only
		STATUS          mandatory
		DESCRIPTION     "This attribute defines the Data Center locator of the chassis. "
			::= { dmmProductInfoGroup 11 }

	dmmProductChassisAisle  OBJECT-TYPE
		SYNTAX          DellString 
		ACCESS          read-only
		STATUS          mandatory
		DESCRIPTION     "This attribute defines the Aisle locator of the chassis. "
			::= { dmmProductInfoGroup 12 }

	dmmProductChassisRack  OBJECT-TYPE
		SYNTAX          DellString 
		ACCESS          read-only
		STATUS          mandatory
		DESCRIPTION     "This attribute defines the Rack locator of the chassis. "
			::= { dmmProductInfoGroup 13 }

	dmmProductChassisRackSlot  OBJECT-TYPE
		SYNTAX          DellString 
		ACCESS          read-only
		STATUS          mandatory
		DESCRIPTION     "This attribute defines the Rack Slot locator of the chassis. "
			::= { dmmProductInfoGroup 14 }
               
	dmmProductChassisModel  OBJECT-TYPE
		SYNTAX          DellString
		ACCESS          read-only
		STATUS          mandatory
		DESCRIPTION     "This attribute defines the Model of the chassis."
			::= { dmmProductInfoGroup 15 }
               
	dmmProductChassisExpressServiceCode  OBJECT-TYPE
		SYNTAX          DellString
		ACCESS          read-only
		STATUS          mandatory
		DESCRIPTION     "This attribute defines the Express Service Code of the chassis."
			::= { dmmProductInfoGroup 16 }
               
	dmmProductChassisSystemID  OBJECT-TYPE
		SYNTAX          INTEGER
		ACCESS          read-only
		STATUS          mandatory
		DESCRIPTION     "This attribute defines the System ID of the chassis."
			::= { dmmProductInfoGroup 17 }

	-------------------------------------------------------------------------------
	-- group: firmware
	-------------------------------------------------------------------------------

	dmmFirmwareVersion  OBJECT-TYPE
		SYNTAX          DellString
		ACCESS          read-only
		STATUS          mandatory
		DESCRIPTION     "This attribute defines the firmware version of chassis management module 1."
			::= { dmmFirmwareGroup 1 }

	dmmFirmwareVersion2 OBJECT-TYPE
		SYNTAX          DellString
		ACCESS          read-only
		STATUS          mandatory
		DESCRIPTION     "This attribute defines the firmware version of chassis management module 2."
			::= { dmmFirmwareGroup 2 }

	-------------------------------------------------------------------------------
	-- group: chassis status
	-------------------------------------------------------------------------------

	dmmGlobalSystemStatus OBJECT-TYPE
		SYNTAX          DellStatus
		ACCESS          read-only
		STATUS          mandatory
		DESCRIPTION     "This attribute defines the overall chassis status
                      being monitored by the chassis management module." 
			::= { dmmStatusGroup 1 }

	dmmIOMCurrStatus  OBJECT-TYPE
		SYNTAX          DellStatus
		ACCESS          read-only
		STATUS          mandatory
		DESCRIPTION     "This attribute defines the IOM subsystem status
                      being monitored by the chassis management module." 
			::= { dmmStatusNowGroup 1 }

	dmmRedCurrStatus  OBJECT-TYPE
		SYNTAX          DellStatus
		ACCESS          read-only
		STATUS          mandatory
		DESCRIPTION     "This attribute defines the Redundancy status
                      being monitored by the chassis management module." 
			::= { dmmStatusNowGroup 2 }

	dmmPowerCurrStatus OBJECT-TYPE
		SYNTAX          DellStatus
		ACCESS          read-only
		STATUS          mandatory
		DESCRIPTION     "This attribute defines the power subsystem health status
                      being monitored by the chassis management module." 
			::= { dmmStatusNowGroup 3 }

	dmmFanCurrStatus OBJECT-TYPE
		SYNTAX          DellStatus
		ACCESS          read-only
		STATUS          mandatory
		DESCRIPTION     "This attribute defines the Fan subsystem health status
                      being monitored by the chassis management module." 
			::= { dmmStatusNowGroup 4 }

	dmmBladeCurrStatus OBJECT-TYPE
		SYNTAX          DellStatus
		ACCESS          read-only
		STATUS          mandatory
		DESCRIPTION     "This attribute defines the Blade subsystem health status
                      being monitored by the chassis management module." 
			::= { dmmStatusNowGroup 5 }

	dmmTempCurrStatus OBJECT-TYPE
		SYNTAX          DellStatus
		ACCESS          read-only
		STATUS          mandatory
		DESCRIPTION     "This attribute defines the Temp Sensor subsystem health status
                      being monitored by the chassis management module." 
			::= { dmmStatusNowGroup 6 }

	dmmMMCurrStatus OBJECT-TYPE
		SYNTAX          DellStatus
		ACCESS          read-only
		STATUS          mandatory
		DESCRIPTION     "This attribute defines the health status
                      being monitored by the chassis management module." 
			::= { dmmStatusNowGroup 7 }

	dmmChassisFrontPanelAmbientTemperature OBJECT-TYPE
		SYNTAX          DellTemperatureReading
		ACCESS          read-only
		STATUS          mandatory
		DESCRIPTION     "This attribute defines the ambient temperature
                      reading (in degrees Celsius) for the chassis front panel module." 
			::= { dmmStatusNowGroup 8 }

	-------------------------------------------------------------------------------
	-- group: chassis power
	-------------------------------------------------------------------------------

	dmmPowerTable OBJECT-TYPE
		SYNTAX			SEQUENCE OF DmmPowerTableEntry
		ACCESS			not-accessible
		STATUS			mandatory
		DESCRIPTION		"This object defines the power table."
			::= { dmmChassisPowerGroup 1 }

	dmmPowerTableEntry OBJECT-TYPE
		SYNTAX			DmmPowerTableEntry
		ACCESS      	not-accessible
		STATUS      	mandatory
		DESCRIPTION 	"This object defines the power table entry."
		INDEX       	{ dmmPowerChassisIndex }
			::= { dmmPowerTable 1 }

	dmmPSUTable OBJECT-TYPE
		SYNTAX			SEQUENCE OF DmmPSUTableEntry
		ACCESS			not-accessible
		STATUS			mandatory
		DESCRIPTION		"This object defines the PSU table."
			::= { dmmChassisPowerGroup 2 }

	dmmPSUTableEntry OBJECT-TYPE
		SYNTAX			DmmPSUTableEntry
		ACCESS      	not-accessible
		STATUS      	mandatory
		DESCRIPTION 	"This object defines the PSU table entry."
		INDEX       	{ dmmPSUChassisIndex, dmmPSUIndex }
			::= { dmmPSUTable 1 }

	-------------------------------------------------------------------------------
	-- table: power information
	-------------------------------------------------------------------------------

	dmmPowerChassisIndex OBJECT-TYPE
		SYNTAX			DellPowerIndexRange
		ACCESS			read-only
		STATUS			mandatory
		DESCRIPTION		"This attribute defines the index
							(one-based) of the associated chassis."
			::= { dmmPowerTableEntry 1 }


	dmmPowerIdlePower OBJECT-TYPE
		SYNTAX			DellPowerReading
		ACCESS			read-only
		STATUS			mandatory
		DESCRIPTION		"This attribute defines the power (in Watts) required by 
							the chassis	infrastructure, plus the sum of the minimum power requirements
							for all currently powered-on servers."
			::= { dmmPowerTableEntry 2 }

	dmmPowerKWhCumulative OBJECT-TYPE
		SYNTAX			DellPowerReading
		ACCESS			read-only
		STATUS			mandatory
		DESCRIPTION		"This attribute defines the cumulative chassis power
							usage (in KWh) since last reset." 
			::= { dmmPowerTableEntry 3 }

	dmmPowerKWhCumulativeTime OBJECT-TYPE
		SYNTAX			DellTimestamp
		ACCESS			read-only
		STATUS			mandatory
		DESCRIPTION		"This attribute defines the timestamp of the most recent
							chassis power accumulator reset." 
			::= { dmmPowerTableEntry 4 }

	dmmPowerWattsPeakUsage OBJECT-TYPE
		SYNTAX			DellPowerReading
		ACCESS			read-only
		STATUS			mandatory
		DESCRIPTION		"This attribute defines the chassis peak power
							usage (in Watts) since last reset." 
			::= { dmmPowerTableEntry 5 }

	dmmPowerWattsPeakTime OBJECT-TYPE
		SYNTAX			DellTimestamp
		ACCESS			read-only
		STATUS			mandatory
		DESCRIPTION		"This attribute defines the timestamp of the most recent
							chassis peak power usage." 
			::= { dmmPowerTableEntry 6 }

	dmmPowerWattsMinUsage OBJECT-TYPE
		SYNTAX			DellPowerReading
		ACCESS			read-only
		STATUS			mandatory
		DESCRIPTION		"This attribute defines the chassis mimimum power
							usage (in Watts) since last reset." 
			::= { dmmPowerTableEntry 7 }

	dmmPowerWattsMinTime OBJECT-TYPE
		SYNTAX			DellTimestamp
		ACCESS			read-only
		STATUS			mandatory
		DESCRIPTION		"This attribute defines the timestamp of the most recent
							chassis minimum power usage." 
			::= { dmmPowerTableEntry 8 }

	dmmPowerWattsReading OBJECT-TYPE
		SYNTAX			DellPowerReading
		ACCESS			read-only
		STATUS			mandatory
		DESCRIPTION		"This attribute defines the instantaneous chassis power
							usage (in Watts)." 
			::= { dmmPowerTableEntry 9 }

	-------------------------------------------------------------------------------
	-- table: PSU info
	-------------------------------------------------------------------------------

	dmmPSUChassisIndex OBJECT-TYPE
		SYNTAX			DellPowerIndexRange
		ACCESS			read-only
		STATUS			mandatory
		DESCRIPTION		"This attribute defines the index
							(one-based) of the associated chassis."
			::= { dmmPSUTableEntry 1 }

	dmmPSUIndex OBJECT-TYPE
		SYNTAX			DellPSUIndexRange
		ACCESS			read-only
		STATUS			mandatory
		DESCRIPTION		"This attribute defines the index
							(one-based) of the associated PSU."
			::= { dmmPSUTableEntry 2 }

	dmmPSULocation OBJECT-TYPE
		SYNTAX			DellString
		ACCESS			read-only
		STATUS			mandatory
		DESCRIPTION		"This attribute defines the location
							of the PSU."
			::= { dmmPSUTableEntry 3 }
			
	dmmPSUState    OBJECT-TYPE
		SYNTAX			DellString
		ACCESS			read-only
		STATUS			mandatory
		DESCRIPTION		"This attribute defines the enabled state of
							of the PSU."
			::= { dmmPSUTableEntry 4 }
	
	dmmPSUType 	OBJECT-TYPE
		SYNTAX			DellString
		ACCESS			read-only
		STATUS			mandatory
		DESCRIPTION		"This attribute defines the type
							of the PSU."
			::= { dmmPSUTableEntry 5 }
	
	dmmPSUCapacity  OBJECT-TYPE
		SYNTAX			DellPowerReading
		ACCESS			read-only
		STATUS			mandatory
		DESCRIPTION		"This attribute defines the capacity in watts
							of the PSU."
			::= { dmmPSUTableEntry 6 }
	
	dmmPSUVoltage		OBJECT-TYPE
		SYNTAX			DellPowerReading
		ACCESS			read-only
		STATUS			mandatory
		DESCRIPTION		"This attribute defines the input voltage
							of the PSU."
			::= { dmmPSUTableEntry 7 }
	
	dmmPSUCurrStatus	OBJECT-TYPE
		SYNTAX			DellStatus
		ACCESS			read-only
		STATUS			mandatory
		DESCRIPTION		"This attribute defines the current status
							of the PSU."
			::= { dmmPSUTableEntry 8 }

	-------------------------------------------------------------------------------
	-- group: Chassis Alerts 2
	-------------------------------------------------------------------------------

    dmmCA2MessageID     OBJECT-TYPE
        SYNTAX          DisplayString (SIZE (0..8))
        ACCESS          read-only
        STATUS          mandatory
        DESCRIPTION     "Message ID of the alert."
        ::= { dmmChassisAlert2Variables 1 }

    dmmCA2Message       OBJECT-TYPE
        SYNTAX          DellString
        ACCESS          read-only
        STATUS          mandatory
        DESCRIPTION     "Message describing the alert."
        ::= { dmmChassisAlert2Variables 2 }

    dmmCA2MessageArgs   OBJECT-TYPE
        SYNTAX          DellString
        ACCESS          read-only
        STATUS          mandatory
        DESCRIPTION     "Concatenated set of strings representing any message arguments
                         that were used to construct the alert message.  Each message
                         argument string is enclosed in double quotes, and there is a
                         comma after the ending double quote of each message argument
                         string, except the last one.  Any double quotes found within a
                         message argument string were preprocessed and changed to single
                         quotes."
        ::= { dmmChassisAlert2Variables 3 }

    dmmCA2AlertStatus   OBJECT-TYPE
        SYNTAX          DellStatus
        ACCESS          read-only
        STATUS          mandatory
        DESCRIPTION     "Status of the alert."
        ::= { dmmChassisAlert2Variables 4 }

    dmmCA2FQDD          OBJECT-TYPE
        SYNTAX          DisplayString (SIZE (0..512))
        ACCESS          read-only
        STATUS          mandatory
        DESCRIPTION     "Fully qualified device descriptor of device causing the alert."
        ::= { dmmChassisAlert2Variables 5 }


	-------------------------------------------------------------------------------
    -- group: Generic Alerts
	-------------------------------------------------------------------------------

	dmmDeviceServiceTag   OBJECT-TYPE
        SYNTAX            DellString
        ACCESS            read-only
        STATUS            mandatory
        DESCRIPTION
            "Service tag of the device."

        ::= { dmmGenericAlertVariables 1 }

	dmmCategoryName  OBJECT-TYPE
        SYNTAX          DisplayString (SIZE (0..512))
        ACCESS          read-only
        STATUS          mandatory
        DESCRIPTION     "Category Name"
        ::= { dmmGenericAlertVariables 2 }

	dmmSubCategoryName  OBJECT-TYPE
        SYNTAX             DisplayString (SIZE (0..512))
        ACCESS             read-only
        STATUS             mandatory
        DESCRIPTION        "Sub Category Name"
        ::= { dmmGenericAlertVariables 3 }

	dmmSeverity  OBJECT-TYPE
        SYNTAX             DisplayString (SIZE (0..512))
        ACCESS             read-only
        STATUS             mandatory
        DESCRIPTION        "Severity"
        ::= { dmmGenericAlertVariables 4 }

    ------------------------------------------------------------------------------
    -- Chassis Alerts 2: System: Amperage Probe Traps
    --
    -- Category: System/1
    -- Subcategory: AMP/16
    ------------------------------------------------------------------------------

    alert2AmperageProbeNormal TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag }
        DESCRIPTION
            "Current sensor reading is within range."
        --#TYPE       "System: Amperage Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2179

    alert2AmperageProbeWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Current sensor has detected a warning value."
        --#TYPE       "System: Amperage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2178

    alert2AmperageProbeFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Current sensor has detected a failure value."
        --#TYPE       "System: Amperage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2177

    ------------------------------------------------------------------------------
    -- Chassis Alerts 2: System: Battery Traps
    --
    -- Category: System/1
    -- Subcategory: BAT/22
    ------------------------------------------------------------------------------

    alert2BatteryNormal TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Battery state has returned to normal;
             or battery presence had been detected."
        --#TYPE       "System: Battery Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2227

    alert2BatteryWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Battery is low."
        --#TYPE       "System: Battery Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2226

    alert2BatteryFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Battery has failed or battery is absent."
        --#TYPE       "System: Battery Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2225

    ------------------------------------------------------------------------------
    -- Chassis Alerts 2: System: Cable Traps
    --
    -- Category: System/1
    -- Subcategory: CBL/43
    ------------------------------------------------------------------------------

    alert2CableFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Cable failure."
        --#TYPE       "System: Cable Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2393

    ------------------------------------------------------------------------------
    -- Chassis Alerts 2: System: Traps
    --
    -- Category: System/1
    -- Subcategory: MM/62
    ------------------------------------------------------------------------------

    alert2CMCWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Chassis Management Module detected a warning."
        --#TYPE       "System: Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2546

    alert2CMCFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Chassis Management Module detected an error."
        --#TYPE       "System: Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2545

    ------------------------------------------------------------------------------
    -- Chassis Alerts 2: System: Fan Traps
    --
    -- Category: System/1
    -- Subcategory: FAN/13
    ------------------------------------------------------------------------------

    alert2FanInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Fan information."
        --#TYPE       "System: Fan Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2155

    alert2FanWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Fan warning."
        --#TYPE       "System: Fan Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2154

    alert2FanFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Fan failure."
        --#TYPE       "System: Fan Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2153

    ------------------------------------------------------------------------------
    -- Chassis Alerts 2: System: Hardware Configuration Traps
    --
    -- Category: System/1
    -- Subcategory: HWC/35
    ------------------------------------------------------------------------------

    alert2HardwareConfigurationInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Hardware configuration information."
        --#TYPE       "System: Hardware Configuration Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2331

    alert2HardwareConfigurationWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Hardware configuration warning."
        --#TYPE       "System: Hardware Configuration Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2330

    alert2HardwareConfigurationFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Hardware configuration failure or critical event."
        --#TYPE       "System: Hardware Configuration Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2329

    ------------------------------------------------------------------------------
    -- Chassis Alerts 2: System: IO Virtualization Traps
    --
    -- Category: System/1
    -- Subcategory: IOV/63
    ------------------------------------------------------------------------------

    alert2IOVirtualizationInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "IO Virtualization information."
        --#TYPE       "System: IO Virtualization Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2555

    alert2IOVirtualizationWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "IO Virtualization warning."
        --#TYPE       "System: IO Virtualization Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2554

    alert2IOVirtualizationFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "IO Virtualization failure or critical event."
        --#TYPE       "System: IO Virtualization Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2553

    ------------------------------------------------------------------------------
    -- Chassis Alerts 2: System: Link Status Traps
    --
    -- Category: System/1
    -- Subcategory: LNK/25
    ------------------------------------------------------------------------------

    alert2LinkStatusInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Link status information."
        --#TYPE       "System: Link Status Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2251

    alert2LinkStatusWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Link status warning."
        --#TYPE       "System: Link Status Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2250

    alert2LinkStatusFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Link status failure or critical event."
        --#TYPE       "System: Link Status Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2249

    ------------------------------------------------------------------------------
    -- Chassis Alerts 2: System: Power Supply Traps
    --
    -- Category: System/1
    -- Subcategory: PSU/17
    ------------------------------------------------------------------------------

    alert2PowerSupplyNormal TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power supply has returned to normal."
        --#TYPE       "System: Power Supply Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2187

    alert2PowerSupplyWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power supply has detected a warning."
        --#TYPE       "System: Power Supply Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2186

    alert2PowerSupplyFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power supply has detected a failure."
        --#TYPE       "System: Power Supply Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2185

    ------------------------------------------------------------------------------
    -- Chassis Alerts 2: System: Power Supply Absent Traps
    --
    -- Category: System/1
    -- Subcategory: PSUA/52
    ------------------------------------------------------------------------------

    alert2PowerSupplyAbsent TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power supply is absent."
        --#TYPE       "System: Power Supply Absent"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2465

    ------------------------------------------------------------------------------
    -- Chassis Alerts 2: System: Power Usage Traps
    --
    -- Category: System/1
    -- Subcategory: PWR/28
    ------------------------------------------------------------------------------

    alert2PowerUsageInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power usage information."
        --#TYPE       "System: Power Usage Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2275

    alert2PowerUsageWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power usage warning."
        --#TYPE       "System: Power Usage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2274

    alert2PowerUsageFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power usage failure."
        --#TYPE       "System: Power Usage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2273

    ------------------------------------------------------------------------------
    -- Chassis Alerts 2: System: Redundancy Traps
    --
    -- Category: System/1
    -- Subcategory: RDU/53
    ------------------------------------------------------------------------------

    alert2RedundancyInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Redundancy information."
        --#TYPE       "System: Redundancy Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2475

    alert2RedundancyDegraded TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Redundancy is degraded."
        --#TYPE       "System: Redundancy Degraded"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2474

    alert2RedundancyLost TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Redundancy is lost."
        --#TYPE       "System: Redundancy Lost"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2473

    ------------------------------------------------------------------------------
    -- Chassis Alerts 2: System: Security Event Traps
    --
    -- Category: System/1
    -- Subcategory: SEC/42
    ------------------------------------------------------------------------------

    alert2SecurityInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Security information."
        --#TYPE       "System: Security Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2387

    alert2SecurityWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Security warning."
        --#TYPE       "System: Security Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2386

    alert2SecurityFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Security failure or critical event."
        --#TYPE       "System: Security Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 2385

    ------------------------------------------------------------------------------
    -- Chassis Alerts 2: System: System Event Log Traps
    --
    -- Category: System/1
    -- Subcategory: SEL/41
    ------------------------------------------------------------------------------

    alert2SystemEventLogInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "System Event Log information."
        --#TYPE       "System: System Event Log Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2379

    alert2SystemEventLogWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "System Event Log warning."
        --#TYPE       "System: System Event Log Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2378

    alert2SystemEventLogFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "System Event Log failure or critical event."
        --#TYPE       "System: System Event Log Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 2377

    ------------------------------------------------------------------------------
    -- Chassis Alerts 2: System: Software Configuration Traps
    --
    -- Category: System/1
    -- Subcategory: SWC/36
    ------------------------------------------------------------------------------

    alert2SoftwareConfigurationInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software configuration information."
        --#TYPE       "System: Software Configuration Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2339

    alert2SoftwareConfigurationWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software configuration warning."
        --#TYPE       "System: Software Configuration Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2338

    alert2SoftwareConfigurationFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software configuration failure."
        --#TYPE       "System: Software Configuration Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2337

    ------------------------------------------------------------------------------
    -- Chassis Alerts 2: System: Temperature Probe Traps
    --
    -- Category: System/1
    -- Subcategory: TMP/14
    ------------------------------------------------------------------------------

    alert2TemperatureProbeNormal TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Temperature sensor value is within range."
        --#TYPE       "System: Temperature Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2163

    alert2TemperatureProbeWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Temperature sensor has detected a warning value."
        --#TYPE       "System: Temperature Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2162

    alert2TemperatureProbeFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Temperature sensor has detected a failure value."
        --#TYPE       "System: Temperature Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2161

    ------------------------------------------------------------------------------
    -- Chassis Alerts 2: System: Voltage Probe Traps
    --
    -- Category: System/1
    -- Subcategory: VLT/15
    ------------------------------------------------------------------------------

    alert2VoltageProbeNormal TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Voltage sensor reading is within range."
        --#TYPE       "System: Voltage Normal"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 2171

    alert2VoltageProbeWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Voltage sensor has detected a warning value."
        --#TYPE       "System: Voltage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 2170

    alert2VoltageProbeFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Voltage sensor has detected a failure value."
        --#TYPE       "System: Voltage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 2169

    -------------------------------------------------------------------------------
    -- Chassis Alerts 2: Storage: Battery Traps
    --
    -- Category: Storage/2
    -- Subcategory: BAT/22
    -------------------------------------------------------------------------------

    alert2StorageBatteryInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Battery information."
        --#TYPE       "Storage: Battery Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4275

    alert2StorageBatteryWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Battery warning."
        --#TYPE       "Storage: Battery Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4274

    alert2StorageBatteryFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Battery failure."
        --#TYPE       "Storage: Battery Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4273

    ------------------------------------------------------------------------------
    -- Chassis Alerts 2: Storage: Controller Traps
    --
    -- Category: Storage/2
    -- Subcategory: CTL/29
    ------------------------------------------------------------------------------

    alert2StorageControllerInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Controller information."
        --#TYPE       "Storage: Controller Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4331

    alert2StorageControllerWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Controller warning."
        --#TYPE       "Storage: Controller Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4330

    alert2StorageControllerFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Controller failure."
        --#TYPE       "Storage: Controller Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4329

    ------------------------------------------------------------------------------
    -- Chassis Alerts 2: Storage: Enclosure Traps
    --
    -- Category: Storage/2
    -- Subcategory: ENC/30
    ------------------------------------------------------------------------------

    alert2StorageEnclosureInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Enclosure information."
        --#TYPE       "Storage: Enclosure Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4339

    alert2StorageEnclosureWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Enclosure warning."
        --#TYPE       "Storage: Enclosure Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4338

    alert2StorageEnclosureFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Enclosure failure."
        --#TYPE       "Storage: Enclosure Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4337

    ------------------------------------------------------------------------------
    -- Chassis Alerts 2: Storage: Fan Traps
    --
    -- Category: Storage/2
    -- Subcategory: FAN/13
    ------------------------------------------------------------------------------

    alert2StorageFanInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Fan information."
        --#TYPE       "Storage: Fan Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4203

    alert2StorageFanWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Fan warning."
        --#TYPE       "Storage: Fan Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 4202

    alert2StorageFanFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Fan failure."
        --#TYPE       "Storage: Fan Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4201

    ------------------------------------------------------------------------------
    -- Chassis Alerts 2: Storage: Physical Disk Traps
    --
    -- Category: Storage/2
    -- Subcategory: PDR/31
    ------------------------------------------------------------------------------

    alert2StoragePhysicalDiskInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Physical disk information."
        --#TYPE       "Storage: Physical Disk Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4347

    alert2StoragePhysicalDiskWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Physical disk warning."
        --#TYPE       "Storage: Physical Disk Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4346

    alert2StoragePhysicalDiskFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Physical disk failure."
        --#TYPE       "Storage: Physical Disk Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4345

    ------------------------------------------------------------------------------
    -- Chassis Alerts 2: Storage: Power Supply Traps
    --
    -- Category: Storage/2
    -- Subcategory: PSU/17
    ------------------------------------------------------------------------------

    alert2StoragePowerSupplyInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Power supply information."
        --#TYPE       "Storage: Power Supply Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4235

    alert2StoragePowerSupplyWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Power supply warning."
        --#TYPE       "Storage: Power Supply Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4234

    alert2StoragePowerSupplyFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Power supply failure."
        --#TYPE       "Storage: Power Supply Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4233

    ------------------------------------------------------------------------------
    -- Chassis Alerts 2: Storage: Security Event Traps
    --
    -- Category: Storage/2
    -- Subcategory: SEC/42
    ------------------------------------------------------------------------------

    alert2StorageSecurityInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Security information."
        --#TYPE       "Storage: Security Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 4435

    alert2StorageSecurityWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Security warning."
        --#TYPE       "Storage: Security Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 4434

    alert2StorageSecurityFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Security failure or critical event."
        --#TYPE       "Storage: Security Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4433

    ------------------------------------------------------------------------------
    -- Chassis Alerts 2: Storage: Storage Management Status Traps
    --
    -- Category: Storage/2
    -- Subcategory: STOR/10
    ------------------------------------------------------------------------------

    alert2StorageManagementInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Management information.
            There is no global status change associated with this trap."
        --#TYPE       "Storage: Storage Management Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4179

    alert2StorageManagementWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Management has detected a device independent warning
            condition. There is no global status change associated with this
            trap."
        --#TYPE       "Storage: Storage Management Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4178

    alert2StorageManagementFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Storage Management has detected a device independent error condition.
            There is no global status change associated with this trap."
        --#TYPE       "Storage: Storage Management Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4177

    ------------------------------------------------------------------------------
    -- Chassis Alerts 2: Storage: Temperature Probe Traps
    --
    -- Category: Storage/2
    -- Subcategory: TMP/14
    ------------------------------------------------------------------------------

    alert2StorageTemperatureProbeInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Temperature probe information."
        --#TYPE       "Storage: Temperature Probe Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4211

    alert2StorageTemperatureProbeWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Temperature probe warning."
        --#TYPE       "Storage: Temperature Probe Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4210

    alert2StorageTemperatureProbeFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Temperature probe failure."
        --#TYPE       "Storage: Temperature Probe Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4209

    ------------------------------------------------------------------------------
    -- Chassis Alerts 2: Storage: Virtual Disk Traps
    --
    -- Category: Storage/2
    -- Subcategory: VDR/32
    ------------------------------------------------------------------------------

    alert2StorageVirtualDiskInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Virtual disk information."
        --#TYPE       "Storage: Virtual Disk Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      OPERATIONAL
        --#STATUS     MANDATORY
        ::= 4355

    alert2StorageVirtualDiskWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Virtual disk warning."
        --#TYPE       "Storage: Virtual Disk Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 4354

    alert2StorageVirtualDiskFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
             "Storage Virtual disk failure."
        --#TYPE       "Storage: Virtual Disk Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      FAILED
        --#STATUS     MANDATORY
        ::= 4353

    ------------------------------------------------------------------------------
    -- Chassis Alerts 2: Updates: Software Change Traps
    --
    -- Category: Updates/3
    -- Subcategory: SWU/21
    ------------------------------------------------------------------------------

    alert2SoftwareChangeUpdateWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software change update warning."
        --#TYPE       "Updates: Software Change Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 6314

    ------------------------------------------------------------------------------
    -- Chassis Alerts 2: Audit: Traps
    --
    -- Category: Audit/4
    -- Subcategory: /62
    ------------------------------------------------------------------------------

    alert2CMCAuditInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Chassis Management Module audit information."
        --#TYPE       "Audit: Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 8691

    alert2CMCAuditWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Chassis Management Module audit warning."
        --#TYPE       "Audit: Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 8690

    alert2CMCAuditFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Chassis Management Module audit failure or critical event."
        --#TYPE       "Audit: Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 8689

    ------------------------------------------------------------------------------
    -- Chassis Alerts 2: Audit: IO Virtualization Traps
    --
    -- Category: Audit/4
    -- Subcategory: IOV/63
    ------------------------------------------------------------------------------

    alert2IOVirtualizationAuditWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "IO Virtualization audit warning."
        --#TYPE       "Audit: IO Virtualization Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 8698

    ------------------------------------------------------------------------------
    -- Chassis Alerts 2: Audit: License Traps
    --
    -- Category: Audit/4
    -- Subcategory: LIC/40
    ------------------------------------------------------------------------------

    alert2LicenseInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "License information."
        --#TYPE       "Audit: License Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 8515

    alert2LicenseWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "License warning."
        --#TYPE       "Audit: License Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 8514

    alert2LicenseFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "License failure."
        --#TYPE       "Audit: License Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 8513

    ------------------------------------------------------------------------------
    -- Chassis Alerts 2: Audit: PCI Device Traps
    --
    -- Category: Audit/4
    -- Subcategory: PCI/46
    ------------------------------------------------------------------------------

    alert2PCIDeviceAuditWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "PCI device audit warning."
        --#TYPE       "Audit: PCI Device Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 8562

    ------------------------------------------------------------------------------
    -- Chassis Alerts 2: Audit: Power Supply Traps
    --
    -- Category: Audit/4
    -- Subcategory: PSU/17
    ------------------------------------------------------------------------------

    alert2PowerSupplyAuditWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power Supply audit warning."
        --#TYPE       "Audit: Power Supply Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 8330

    alert2PowerSupplyAuditFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power Supply audit failure or critical event."
        --#TYPE       "Audit: Power Supply Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 8329

    ------------------------------------------------------------------------------
    -- Chassis Alerts 2: Audit: Power Usage Traps
    --
    -- Category: Audit/4
    -- Subcategory: PWR/28
    ------------------------------------------------------------------------------

    alert2PowerUsageAuditInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power usage audit information."
        --#TYPE       "Audit: Power Usage Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 8419

    alert2PowerUsageAuditWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power usage audit warning."
        --#TYPE       "Audit: Power Usage Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 8418

    alert2PowerUsageAuditFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Power usage audit failure or critical event."
        --#TYPE       "Audit: Power Usage Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 8417

    ------------------------------------------------------------------------------
    -- Chassis Alerts 2: Audit: Software Change Traps
    --
    -- Category: Audit/4
    -- Subcategory: SWU/21
    ------------------------------------------------------------------------------

    alert2SoftwareChangeAuditFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software change audit failure or critical event."
        --#TYPE       "Audit: Software Change Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 8361

    ------------------------------------------------------------------------------
    -- Chassis Alerts 2: Configuration: IO Virtualization Traps
    --
    -- Category: Configuration/5
    -- Subcategory: IOV/63
    ------------------------------------------------------------------------------

    alert2IOVConfigurationInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "IO Virtualization configuration information."
        --#TYPE       "Configuration: IO Virtualization Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 10747

    alert2IOVConfigurationWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "IO Virtualization configuration warning."
        --#TYPE       "Configuration: IO Virtualization Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 10746

    ------------------------------------------------------------------------------
    -- Chassis Alerts 2: Configuration: PCI Device Traps
    --
    -- Category: Configuration/5
    -- Subcategory: PCI/46
    ------------------------------------------------------------------------------

    alert2PCIDeviceConfigurationInformation TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "PCI device configuration information."
        --#TYPE       "Configuration: PCI Device Information"
        --#SEVERITY   INFORMATIONAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      OPERATIONAL
        --#STATUS     MANDATORY
        ::= 10611

    ------------------------------------------------------------------------------
    -- Chassis Alerts 2: Configuration: Software Configuration Traps
    --
    -- Category: Configuration/5
    -- Subcategory: SWC/36
    ------------------------------------------------------------------------------

    alert2SWCConfigurationWarning TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software configuration warning."
        --#TYPE       "Configuration: Software Configuration Warning"
        --#SEVERITY   MINOR
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Status Events"
        --#STATE      DEGRADED
        --#STATUS     MANDATORY
        ::= 10530

    alert2SWCConfigurationFailure TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Software configuration failure."
        --#TYPE       "Configuration: Software Configuration Failure"
        --#SEVERITY   CRITICAL
        --#SUMMARY    "Message ID: %s, Message: %s,"
        --#SUMMARY    "Device Status: %d, Device FQDD: %s,"
        --#SUMMARY    "Chassis Service Tag: %s, Chassis Name: %s"
        --#ARGUMENTS  {0, 1, 3, 4, 6, 5}
        --#CATEGORY   "Error Events"
        --#STATE      DEGRADED
        --#STATUS     MANDATORY
        ::= 10529

    ------------------------------------------------------------------------------
    -- Chassis Alerts 2: Configuration: Test Traps
    --
    -- Category: Configuration/5
    -- Subcategory: TST/19
    ------------------------------------------------------------------------------

    alert2CMCTestTrap TRAP-TYPE
        ENTERPRISE  dmmChassisAlert2Group
        VARIABLES { dmmCA2MessageID,
                    dmmCA2Message,
                    dmmCA2MessageArgs,
                    dmmCA2AlertStatus,
                    dmmCA2FQDD,
                    dmmProductChassisName,
                    dmmChassisServiceTag}
        DESCRIPTION
            "Test trap generated in response to a user request."
        --#TYPE       "Configuration:  Test Trap"
        --#SEVERITY   INFORMATIONAL
        --#SUMMARY    "%s"
        --#ARGUMENTS  {1}
        --#CATEGORY   "Status Events"
        --#STATE      OPERATIONAL
        --#STATUS     MANDATORY
        ::= 10395

    ------------------------------------------------------------------------------
    -- Alert 1: Internal: Internal MM Traps
    --
    -- Category: Internal/1
    -- Subcategory: Internal/1
    ------------------------------------------------------------------------------
    alertGenericCritical TRAP-TYPE
        ENTERPRISE  dmmGenericAlertGroup
        VARIABLES { dmmCA2MessageID,
                    dmmCA2Message,
                    dmmCA2MessageArgs,
                    dmmCA2AlertStatus,
					dmmDeviceServiceTag,
					dmmCategoryName,
					dmmSubCategoryName,
					dmmSeverity
                    }
        DESCRIPTION
            "MM generic critical system alert."
        --#TYPE       "Internal: MM System Alert"
        --#SEVERITY   CRITICAL
        --#SUMMARY    "Message ID: %s, Message: %s,"
        --#SUMMARY    "Device Status: %d "
        --#ARGUMENTS  {0, 1, 3}
        --#CATEGORY   "Internal Events"
        --#STATE      OPERATIONAL
        --#STATUS     MANDATORY
        ::= 100

    ------------------------------------------------------------------------------
    -- MM Alert 2: Internal: Internal MM Traps
    --
    -- Category: Internal/1
    -- Subcategory: Internal/2
    ------------------------------------------------------------------------------
    alertGenericWarning TRAP-TYPE
        ENTERPRISE  dmmGenericAlertGroup
        VARIABLES { dmmCA2MessageID,
                    dmmCA2Message,
                    dmmCA2MessageArgs,
                    dmmCA2AlertStatus,
					dmmDeviceServiceTag,
					dmmCategoryName,
					dmmSubCategoryName,
					dmmSeverity
                    }
        DESCRIPTION
            "MM generic warning system alert."
        --#TYPE       "Internal: MM System Alert"
        --#SEVERITY   WARNING
        --#SUMMARY    "Message ID: %s, Message: %s,"
        --#SUMMARY    "Device Status: %d "
        --#ARGUMENTS  {0, 1, 3}
        --#CATEGORY   "Internal Events"
        --#STATE      OPERATIONAL
        --#STATUS     MANDATORY
        ::= 200

    ------------------------------------------------------------------------------
    -- MM Alert 3: Internal: Internal MM Traps
    --
    -- Category: Internal/1
    -- Subcategory: Internal/3
    ------------------------------------------------------------------------------
    alertGenericNormal TRAP-TYPE
        ENTERPRISE  dmmGenericAlertGroup
        VARIABLES { dmmCA2MessageID,
                    dmmCA2Message,
                    dmmCA2MessageArgs,
                    dmmCA2AlertStatus,
					dmmDeviceServiceTag,
					dmmCategoryName,
					dmmSubCategoryName,
					dmmSeverity
                    }
        DESCRIPTION
            "MM generic normal system alert."
        --#TYPE       "Internal: MM System Alert"
        --#SEVERITY   NORMAL
        --#SUMMARY    "Message ID: %s, Message: %s,"
        --#SUMMARY    "Device Status: %d "
        --#ARGUMENTS  {0, 1, 3}
        --#CATEGORY   "Internal Events"
        --#STATE      OPERATIONAL
        --#STATUS     MANDATORY
        ::= 300

    ------------------------------------------------------------------------------
    -- MM Alert 4: Internal: Internal MM Traps
    --
    -- Category: Internal/1
    -- Subcategory: Internal/4
    ------------------------------------------------------------------------------
    alertGenericInformational TRAP-TYPE
        ENTERPRISE  dmmGenericAlertGroup
        VARIABLES { dmmCA2MessageID,
                    dmmCA2Message,
                    dmmCA2MessageArgs,
                    dmmCA2AlertStatus,
					dmmDeviceServiceTag,
					dmmCategoryName,
					dmmSubCategoryName,
					dmmSeverity
                    }
        DESCRIPTION
            "MM generic information system alert."
        --#TYPE       "Internal: MM System Alert"
        --#SEVERITY   INFORMATIONAL
        --#SUMMARY    "Message ID: %s, Message: %s,"
        --#SUMMARY    "Device Status: %d "
        --#ARGUMENTS  {0, 1, 3}
        --#CATEGORY   "Internal Events"
        --#STATE      OPERATIONAL
        --#STATUS     MANDATORY
        ::= 400

   ------------------------------------------------------------------------------
    -- MM Alert 5: Internal: Internal MM Traps
    --
    -- Category: Internal/1
    -- Subcategory: Internal/5
    ------------------------------------------------------------------------------
    alertGenericTestTrapEvent TRAP-TYPE
        ENTERPRISE  dmmGenericAlertGroup
        VARIABLES { dmmCA2Message
                    }
        DESCRIPTION
            "MM Generated a test trap event in response to a user request."
        --#TYPE       "Internal: Dell MM Test TRAP Event"
        --#SEVERITY   INFORMATIONAL
        --#SUMMARY    "%s"
        --#ARGUMENTS  {0}
        --#CATEGORY   "Status Events"
        ::= 500


    ------------------------------------------------------------------------------
    -- Alert 6: Internal: Internal MM Audit Traps
    --
    -- Category: Internal/1
    -- Subcategory: Internal/6
    ------------------------------------------------------------------------------
    alertAuditCritical TRAP-TYPE
        ENTERPRISE  dmmGenericAlertGroup
        VARIABLES { dmmCA2MessageID,
                    dmmCA2Message,
                    dmmCA2MessageArgs,
                    dmmCA2AlertStatus,
                    dmmDeviceServiceTag,
                    dmmCategoryName,
                    dmmSubCategoryName,
                    dmmSeverity
                    }
        DESCRIPTION
            "MM audit critical system alert."
        --#TYPE       "Internal: MM System Audit Alert"
        --#SEVERITY   CRITICAL
        --#SUMMARY    "Message ID: %s, Message: %s,"
        --#SUMMARY    "Device Status: %d "
        --#ARGUMENTS  {0, 1, 3}
        --#CATEGORY   "Internal Events"
        --#STATE      OPERATIONAL
        --#STATUS     MANDATORY
        ::= 600

    ------------------------------------------------------------------------------
    -- MM Alert 7: Internal: Internal MM Audit Traps
    --
    -- Category: Internal/1
    -- Subcategory: Internal/7
    ------------------------------------------------------------------------------
    alertAuditWarning TRAP-TYPE
        ENTERPRISE  dmmGenericAlertGroup
        VARIABLES { dmmCA2MessageID,
                    dmmCA2Message,
                    dmmCA2MessageArgs,
                    dmmCA2AlertStatus,
                    dmmDeviceServiceTag,
                    dmmCategoryName,
                    dmmSubCategoryName,
                    dmmSeverity
                    }
        DESCRIPTION
            "MM audit warning system alert."
        --#TYPE       "Internal: MM System Audit Alert"
        --#SEVERITY   WARNING
        --#SUMMARY    "Message ID: %s, Message: %s,"
        --#SUMMARY    "Device Status: %d "
        --#ARGUMENTS  {0, 1, 3}
        --#CATEGORY   "Internal Events"
        --#STATE      OPERATIONAL
        --#STATUS     MANDATORY
        ::= 700


    ------------------------------------------------------------------------------
    -- MM Alert 8: Internal: Internal MM Audit Traps
    --
    -- Category: Internal/1
    -- Subcategory: Internal/8
    ------------------------------------------------------------------------------
    alertAuditNormal TRAP-TYPE
        ENTERPRISE  dmmGenericAlertGroup
        VARIABLES { dmmCA2MessageID,
                    dmmCA2Message,
                    dmmCA2MessageArgs,
                    dmmCA2AlertStatus,
                    dmmDeviceServiceTag,
                    dmmCategoryName,
                    dmmSubCategoryName,
                    dmmSeverity
                    }
        DESCRIPTION
            "MM audit normal system alert."
        --#TYPE       "Internal: MM System Audit Alert"
        --#SEVERITY   NORMAL
        --#SUMMARY    "Message ID: %s, Message: %s,"
        --#SUMMARY    "Device Status: %d "
        --#ARGUMENTS  {0, 1, 3}
        --#CATEGORY   "Internal Events"
        --#STATE      OPERATIONAL
        --#STATUS     MANDATORY
        ::= 800


    ------------------------------------------------------------------------------
    -- MM Alert 9: Internal: Internal MM Audit Traps
    --
    -- Category: Internal/1
    -- Subcategory: Internal/9
    ------------------------------------------------------------------------------
    alertAuditInformational TRAP-TYPE
        ENTERPRISE  dmmGenericAlertGroup
        VARIABLES { dmmCA2MessageID,
                    dmmCA2Message,
                    dmmCA2MessageArgs,
                    dmmCA2AlertStatus,
                    dmmDeviceServiceTag,
                    dmmCategoryName,
                    dmmSubCategoryName,
                    dmmSeverity
                    }
        DESCRIPTION
            "MM audit information system alert."
        --#TYPE       "Internal: MM System Audit Alert"
        --#SEVERITY   INFORMATIONAL
        --#SUMMARY    "Message ID: %s, Message: %s,"
        --#SUMMARY    "Device Status: %d "
        --#ARGUMENTS  {0, 1, 3}
        --#CATEGORY   "Internal Events"
        --#STATE      OPERATIONAL
        --#STATUS     MANDATORY
        ::= 900



    ------------------------------------------------------------------------------
    -- Alert: Forwarded: Forwarded MSM Traps
    --
    -- Category: Configuration
    -- Subcategory: Job Control
    ------------------------------------------------------------------------------
    iDRAC10267alertJobControlConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Job Control configuration information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10267

    ------------------------------------------------------------------------------
    -- Alert: Forwarded: Forwarded MSM Traps
    --
    -- Category: Configuration
    -- Subcategory: Test Alert
    ------------------------------------------------------------------------------
    iDRAC10298alertPRDeviceDetectionWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The indicated device is not detected. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10298

    ------------------------------------------------------------------------------
    -- Alert: Forwarded: Forwarded MSM Traps
    --
    -- Category: Configuration
    -- Subcategory: Test Alert
    ------------------------------------------------------------------------------
    iDRAC10395alertTestTrapEvent TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The iDRAC generated a test trap event in response to a user request. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10395

    ------------------------------------------------------------------------------
    -- Alert: Forwarded: Forwarded MSM Traps
    --
    -- Category: Configuration
    -- Subcategory: Software Config
    ------------------------------------------------------------------------------
    iDRAC10529alertSWCConfigurationFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software configuration failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10529

    ------------------------------------------------------------------------------
    -- Alert: Forwarded: Forwarded MSM Traps
    --
    -- Category: Configuration
    -- Subcategory: Software Config
    ------------------------------------------------------------------------------
    iDRAC10530alertSWCConfigurationWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software configuration warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10530

    ------------------------------------------------------------------------------
    -- Alert: Forwarded: Forwarded MSM Traps
    --
    -- Category: Configuration
    -- Subcategory: Software Config
    ------------------------------------------------------------------------------
    iDRAC10531alertSWCConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software configuration Information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10531

    ------------------------------------------------------------------------------
    -- Alert: Forwarded: Forwarded MSM Traps
    --
    -- Category: Configuration
    -- Subcategory: IP Address
    ------------------------------------------------------------------------------
    iDRAC10547alertIPAddressConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " IP Address configuration information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10547

    ------------------------------------------------------------------------------
    -- Alert: Forwarded: Forwarded MSM Traps
    --
    -- Category: Configuration
    -- Subcategory: Security Event
    ------------------------------------------------------------------------------
    iDRAC10578alertSecurityConfigurationWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Security configuration warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10578

    ------------------------------------------------------------------------------
    -- Alert: Forwarded: Forwarded MSM Traps
    --
    -- Category: Configuration
    -- Subcategory: PCI Device
    ------------------------------------------------------------------------------
    iDRAC10611alertPCIDeviceConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " PCI device configuration information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10611

    ------------------------------------------------------------------------------
    -- Alert: Forwarded: Forwarded MSM Traps
    --
    -- Category: Configuration
    -- Subcategory: System Info
    ------------------------------------------------------------------------------
    iDRAC10627alertSystemConfigurationChangeInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " A Many System Configuration Item Items are changed  "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10627

    ------------------------------------------------------------------------------
    -- Alert: Forwarded: Forwarded MSM Traps
    --
    -- Category: Configuration
    -- Subcategory: Auto-Discovery
    ------------------------------------------------------------------------------
    iDRAC10635alertAutoDiscoveryInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Auto discovery information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10635

    ------------------------------------------------------------------------------
    -- Alert: Forwarded: Forwarded MSM Traps
    --
    -- Category: Configuration
    -- Subcategory: IO Identity Optimization
    ------------------------------------------------------------------------------
    iDRAC10770alertNetworkConfigurationWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Network configuration warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10770

    ------------------------------------------------------------------------------
    -- Alert: Forwarded: Forwarded MSM Traps
    --
    -- Category: Configuration
    -- Subcategory: IO Identity Optimization
    ------------------------------------------------------------------------------
    iDRAC10771alertNetworkConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Network configuration information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 10771

    ------------------------------------------------------------------------------
    -- Alert: Forwarded: Forwarded MSM Traps
    --
    -- Category: Configuration
    -- Subcategory: Other
    ------------------------------------------------------------------------------
    iDRAC11274alertSDKConfigurationWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The iDRAC generated a trap event with SDK plugin configuration change warning "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 11274

    ------------------------------------------------------------------------------
    -- Alert: Forwarded: Forwarded MSM Traps
    --
    -- Category: Configuration
    -- Subcategory: Other
    ------------------------------------------------------------------------------
    iDRAC11275alertSDKConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The iDRAC generated a trap event with SDK plugin Configuration change information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 11275

    ------------------------------------------------------------------------------
    -- Alert: Forwarded: Forwarded MSM Traps
    --
    -- Category: System Health
    -- Subcategory: NIC Configuration
    ------------------------------------------------------------------------------
    iDRAC2089alertNetworkFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Network failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2089

    ------------------------------------------------------------------------------
    -- Alert: Forwarded: Forwarded MSM Traps
    --
    -- Category: System Health
    -- Subcategory: NIC Configuration
    ------------------------------------------------------------------------------
    iDRAC2090alertNetworkWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Network warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2090

    ------------------------------------------------------------------------------
    -- Alert: Forwarded: Forwarded MSM Traps
    --
    -- Category: System Health
    -- Subcategory: NIC Configuration
    ------------------------------------------------------------------------------
    iDRAC2091alertNetworkInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Network information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2091

    ------------------------------------------------------------------------------
    -- Alert: Forwarded: Forwarded MSM Traps
    --
    -- Category: System Health
    -- Subcategory: Fan Event
    ------------------------------------------------------------------------------
    iDRAC2153alertFanFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fan failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2153

    ------------------------------------------------------------------------------
    -- Alert: Forwarded: Forwarded MSM Traps
    --
    -- Category: System Health
    -- Subcategory: Fan Event
    ------------------------------------------------------------------------------
    iDRAC2154alertFanWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fan warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2154

    ------------------------------------------------------------------------------
    -- Alert: Forwarded: Forwarded MSM Traps
    --
    -- Category: System Health
    -- Subcategory: Fan Event
    ------------------------------------------------------------------------------
    iDRAC2155alertFanInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fan information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2155

    ------------------------------------------------------------------------------
    -- Alert: Forwarded: Forwarded MSM Traps
    --
    -- Category: System Health
    -- Subcategory: Temperature
    ------------------------------------------------------------------------------
    iDRAC2161alertTemperatureProbeFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature sensor has detected a failure value. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2161

    ------------------------------------------------------------------------------
    -- Alert: Forwarded: Forwarded MSM Traps
    --
    -- Category: System Health
    -- Subcategory: Temperature
    ------------------------------------------------------------------------------
    iDRAC2162alertTemperatureProbeWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature sensor has detected a warning value. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2162

    ------------------------------------------------------------------------------
    -- Alert: Forwarded: Forwarded MSM Traps
    --
    -- Category: System Health
    -- Subcategory: Temperature
    ------------------------------------------------------------------------------
    iDRAC2163alertTemperatureProbeNormal TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature sensor value is within range. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2163

    ------------------------------------------------------------------------------
    -- Alert: Forwarded: Forwarded MSM Traps
    --
    -- Category: System Health
    -- Subcategory: Voltage
    ------------------------------------------------------------------------------
    iDRAC2169alertVoltageProbeFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Voltage sensor has detected a failure value. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2169

    ------------------------------------------------------------------------------
    -- Alert: Forwarded: Forwarded MSM Traps
    --
    -- Category: System Health
    -- Subcategory: Voltage
    ------------------------------------------------------------------------------
    iDRAC2170alertVoltageProbeWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Voltage sensor has detected a warning value. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2170

    ------------------------------------------------------------------------------
    -- Alert: Forwarded: Forwarded MSM Traps
    --
    -- Category: System Health
    -- Subcategory: Voltage
    ------------------------------------------------------------------------------
    iDRAC2171alertVoltageProbeNormal TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Voltage sensor reading is within range. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2171

    ------------------------------------------------------------------------------
    -- Alert: Forwarded: Forwarded MSM Traps
    --
    -- Category: System Health
    -- Subcategory: Amperage
    ------------------------------------------------------------------------------
    iDRAC2177alertAmperageProbeFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Current sensor has detected a failure value. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2177

    ------------------------------------------------------------------------------
    -- Alert: Forwarded: Forwarded MSM Traps
    --
    -- Category: System Health
    -- Subcategory: Amperage
    ------------------------------------------------------------------------------
    iDRAC2178alertAmperageProbeWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Current sensor has detected a warning value. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2178

    ------------------------------------------------------------------------------
    -- Alert: Forwarded: Forwarded MSM Traps
    --
    -- Category: System Health
    -- Subcategory: Amperage
    ------------------------------------------------------------------------------
    iDRAC2179alertAmperageProbeNormal TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Current sensor reading is within range. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2179

    ------------------------------------------------------------------------------
    -- Alert: Forwarded: Forwarded MSM Traps
    --
    -- Category: System Health
    -- Subcategory: Power Supply
    ------------------------------------------------------------------------------
    iDRAC2185alertPowerSupplyFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply has detected a failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2185

    ------------------------------------------------------------------------------
    -- Alert: Forwarded: Forwarded MSM Traps
    --
    -- Category: System Health
    -- Subcategory: Power Supply
    ------------------------------------------------------------------------------
    iDRAC2186alertPowerSupplyWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply has detected a warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2186

    ------------------------------------------------------------------------------
    -- Alert: Forwarded: Forwarded MSM Traps
    --
    -- Category: System Health
    -- Subcategory: Power Supply
    ------------------------------------------------------------------------------
    iDRAC2187alertPowerSupplyNormal TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply has returned to normal. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2187

    ------------------------------------------------------------------------------
    -- Alert: Forwarded: Forwarded MSM Traps
    --
    -- Category: System Health
    -- Subcategory: IDSDM Media
    ------------------------------------------------------------------------------
    iDRAC2209alertIntegratedDualSDModuleFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2209

    ------------------------------------------------------------------------------
    -- Alert: Forwarded: Forwarded MSM Traps
    --
    -- Category: System Health
    -- Subcategory: IDSDM Media
    ------------------------------------------------------------------------------
    iDRAC2210alertIntegratedDualSDModuleWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2210

    ------------------------------------------------------------------------------
    -- Alert: Forwarded: Forwarded MSM Traps
    --
    -- Category: System Health
    -- Subcategory: IDSDM Media
    ------------------------------------------------------------------------------
    iDRAC2211alertIntegratedDualSDModuleInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2211

    ------------------------------------------------------------------------------
    -- Alert: Forwarded: Forwarded MSM Traps
    --
    -- Category: System Health
    -- Subcategory: Battery Event
    ------------------------------------------------------------------------------
    iDRAC2225alertBatteryFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Battery has failed or battery is absent. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2225

    ------------------------------------------------------------------------------
    -- Alert: Forwarded: Forwarded MSM Traps
    --
    -- Category: System Health
    -- Subcategory: Battery Event
    ------------------------------------------------------------------------------
    iDRAC2226alertBatteryWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Battery is low. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2226

    ------------------------------------------------------------------------------
    -- Alert: Forwarded: Forwarded MSM Traps
    --
    -- Category: System Health
    -- Subcategory: Battery Event
    ------------------------------------------------------------------------------
    iDRAC2227alertBatteryNormal TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Battery state has returned to normal "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2227

    ------------------------------------------------------------------------------
    -- Alert: Forwarded: Forwarded MSM Traps
    --
    -- Category: System Health
    -- Subcategory: Auto System Reset
    ------------------------------------------------------------------------------
    iDRAC2233alertAutomaticSystemRecovery TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Automatic system recovery  ASR  was performed. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2233

    ------------------------------------------------------------------------------
    -- Alert: Forwarded: Forwarded MSM Traps
    --
    -- Category: System Health
    -- Subcategory: Processor
    ------------------------------------------------------------------------------
    iDRAC2241alertProcessorDeviceStatusFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Processor device status has detected a failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2241

    ------------------------------------------------------------------------------
    -- Alert: Forwarded: Forwarded MSM Traps
    --
    -- Category: System Health
    -- Subcategory: Processor
    ------------------------------------------------------------------------------
    iDRAC2242alertProcessorDeviceStatusWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Processor device status has detected a warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2242

    ------------------------------------------------------------------------------
    -- Alert: Forwarded: Forwarded MSM Traps
    --
    -- Category: System Health
    -- Subcategory: Processor
    ------------------------------------------------------------------------------
    iDRAC2243alertProcessorDeviceStatusNormal TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Processor device status has returned to normal. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2243

    ------------------------------------------------------------------------------
    -- Alert: Forwarded: Forwarded MSM Traps
    --
    -- Category: System Health
    -- Subcategory: Link Status
    ------------------------------------------------------------------------------
    iDRAC2249alertLinkStatusFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Link status failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2249

    ------------------------------------------------------------------------------
    -- Alert: Forwarded: Forwarded MSM Traps
    --
    -- Category: System Health
    -- Subcategory: Link Status
    ------------------------------------------------------------------------------
    iDRAC2250alertLinkStatusWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Link status warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2250

    ------------------------------------------------------------------------------
    -- Alert: Forwarded: Forwarded MSM Traps
    --
    -- Category: System Health
    -- Subcategory: Link Status
    ------------------------------------------------------------------------------
    iDRAC2251alertLinkStatusInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Link status information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2251

    ------------------------------------------------------------------------------
    -- Alert: Forwarded: Forwarded MSM Traps
    --
    -- Category: System Health
    -- Subcategory: Memory
    ------------------------------------------------------------------------------
    iDRAC2265alertMemoryDeviceFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Memory device status is critical. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2265

    ------------------------------------------------------------------------------
    -- Alert: Forwarded: Forwarded MSM Traps
    --
    -- Category: System Health
    -- Subcategory: Memory
    ------------------------------------------------------------------------------
    iDRAC2266alertMemoryDeviceWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Memory device status is noncritical. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2266

    ------------------------------------------------------------------------------
    -- Alert: Forwarded: Forwarded MSM Traps
    --
    -- Category: System Health
    -- Subcategory: Memory
    ------------------------------------------------------------------------------
    iDRAC2267alertMemoryDeviceInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Memory device informational event. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2267

    ------------------------------------------------------------------------------
    -- Alert: Forwarded: Forwarded MSM Traps
    --
    -- Category: System Health
    -- Subcategory: Power Usage
    ------------------------------------------------------------------------------
    iDRAC2273alertPowerUsageFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The system halted because system power exceeds capacity "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2273

    ------------------------------------------------------------------------------
    -- Alert: Forwarded: Forwarded MSM Traps
    --
    -- Category: System Health
    -- Subcategory: Power Usage
    ------------------------------------------------------------------------------
    iDRAC2274alertPowerUsageWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System performance degraded. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2274

    ------------------------------------------------------------------------------
    -- Alert: Forwarded: Forwarded MSM Traps
    --
    -- Category: System Health
    -- Subcategory: Power Usage
    ------------------------------------------------------------------------------
    iDRAC2275alertPowerUsageInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System performance restored. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2275

    ------------------------------------------------------------------------------
    -- Alert: Forwarded: Forwarded MSM Traps
    --
    -- Category: System Health
    -- Subcategory: Physical Disk
    ------------------------------------------------------------------------------
    iDRAC2297alertPhysicalDiskFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Physical disk failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2297

    ------------------------------------------------------------------------------
    -- Alert: Forwarded: Forwarded MSM Traps
    --
    -- Category: System Health
    -- Subcategory: Physical Disk
    ------------------------------------------------------------------------------
    iDRAC2298alertPhysicalDiskWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Physical disk warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2298

    ------------------------------------------------------------------------------
    -- Alert: Forwarded: Forwarded MSM Traps
    --
    -- Category: System Health
    -- Subcategory: Physical Disk
    ------------------------------------------------------------------------------
    iDRAC2299alertPhysicalDiskInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Physical disk information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2299

    ------------------------------------------------------------------------------
    -- Alert: Forwarded: Forwarded MSM Traps
    --
    -- Category: System Health
    -- Subcategory: Hardware Config
    ------------------------------------------------------------------------------
    iDRAC2329alertHardwareConfigurationFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Hardware configuration failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2329

    ------------------------------------------------------------------------------
    -- Alert: Forwarded: Forwarded MSM Traps
    --
    -- Category: System Health
    -- Subcategory: Hardware Config
    ------------------------------------------------------------------------------
    iDRAC2330alertHardwareConfigurationWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Hardware configuration warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2330

    ------------------------------------------------------------------------------
    -- Alert: Forwarded: Forwarded MSM Traps
    --
    -- Category: System Health
    -- Subcategory: Hardware Config
    ------------------------------------------------------------------------------
    iDRAC2331alertHardwareConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Hardware configuration information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2331

    ------------------------------------------------------------------------------
    -- Alert: Forwarded: Forwarded MSM Traps
    --
    -- Category: System Health
    -- Subcategory: Software Config
    ------------------------------------------------------------------------------
    iDRAC2337alertSoftwareConfigurationFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software configuration failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2337

    ------------------------------------------------------------------------------
    -- Alert: Forwarded: Forwarded MSM Traps
    --
    -- Category: System Health
    -- Subcategory: Software Config
    ------------------------------------------------------------------------------
    iDRAC2338alertSoftwareConfigurationWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software configuration warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2338

    ------------------------------------------------------------------------------
    -- Alert: Forwarded: Forwarded MSM Traps
    --
    -- Category: System Health
    -- Subcategory: Software Config
    ------------------------------------------------------------------------------
    iDRAC2339alertSoftwareConfigurationInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software configuration information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2339

    ------------------------------------------------------------------------------
    -- Alert: Forwarded: Forwarded MSM Traps
    --
    -- Category: System Health
    -- Subcategory: System Event Log
    ------------------------------------------------------------------------------
    iDRAC2377alertSystemEventLogFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System Event Log failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2377

    ------------------------------------------------------------------------------
    -- Alert: Forwarded: Forwarded MSM Traps
    --
    -- Category: System Health
    -- Subcategory: System Event Log
    ------------------------------------------------------------------------------
    iDRAC2378alertSystemEventLogWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System Event Log warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2378

    ------------------------------------------------------------------------------
    -- Alert: Forwarded: Forwarded MSM Traps
    --
    -- Category: System Health
    -- Subcategory: System Event Log
    ------------------------------------------------------------------------------
    iDRAC2379alertSystemEventLogInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System Event Log information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2379

    ------------------------------------------------------------------------------
    -- Alert: Forwarded: Forwarded MSM Traps
    --
    -- Category: System Health
    -- Subcategory: Security Event
    ------------------------------------------------------------------------------
    iDRAC2385alertSecurityFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Security failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2385

    ------------------------------------------------------------------------------
    -- Alert: Forwarded: Forwarded MSM Traps
    --
    -- Category: System Health
    -- Subcategory: Security Event
    ------------------------------------------------------------------------------
    iDRAC2386alertSecurityWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Security warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2386

    ------------------------------------------------------------------------------
    -- Alert: Forwarded: Forwarded MSM Traps
    --
    -- Category: System Health
    -- Subcategory: Security Event
    ------------------------------------------------------------------------------
    iDRAC2387alertSecurityInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Security information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2387

    ------------------------------------------------------------------------------
    -- Alert: Forwarded: Forwarded MSM Traps
    --
    -- Category: System Health
    -- Subcategory: Cable
    ------------------------------------------------------------------------------
    iDRAC2393alertCableFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Cable failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2393

    ------------------------------------------------------------------------------
    -- Alert: Forwarded: Forwarded MSM Traps
    --
    -- Category: System Health
    -- Subcategory: OS Event
    ------------------------------------------------------------------------------
    iDRAC2409alertOSFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " A critical stop occurred during OS load "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2409

    ------------------------------------------------------------------------------
    -- Alert: Forwarded: Forwarded MSM Traps
    --
    -- Category: System Health
    -- Subcategory: OS Event
    ------------------------------------------------------------------------------
    iDRAC2411alertOSInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " An OS graceful stop occurred "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2411

    ------------------------------------------------------------------------------
    -- Alert: Forwarded: Forwarded MSM Traps
    --
    -- Category: System Health
    -- Subcategory: PCI Device
    ------------------------------------------------------------------------------
    iDRAC2417alertPCIDeviceFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " An error was detected for a PCI device. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2417

    ------------------------------------------------------------------------------
    -- Alert: Forwarded: Forwarded MSM Traps
    --
    -- Category: System Health
    -- Subcategory: PCI Device
    ------------------------------------------------------------------------------
    iDRAC2418alertPCIDeviceWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " A warning event was detected for a PCI device. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2418

    ------------------------------------------------------------------------------
    -- Alert: Forwarded: Forwarded MSM Traps
    --
    -- Category: System Health
    -- Subcategory: PCI Device
    ------------------------------------------------------------------------------
    iDRAC2419alertPCIDeviceInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " An informational event was detected for a PCI device. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2419

    ------------------------------------------------------------------------------
    -- Alert: Forwarded: Forwarded MSM Traps
    --
    -- Category: System Health
    -- Subcategory: BIOS POST
    ------------------------------------------------------------------------------
    iDRAC2425alertBiosPostFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System BIOS detected a failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2425

    ------------------------------------------------------------------------------
    -- Alert: Forwarded: Forwarded MSM Traps
    --
    -- Category: System Health
    -- Subcategory: System Info
    ------------------------------------------------------------------------------
    iDRAC2433alertInternaliDRACMemoryUnresponsive TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Unable to communicate with internal iDRAC memory "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2433

    ------------------------------------------------------------------------------
    -- Alert: Forwarded: Forwarded MSM Traps
    --
    -- Category: System Health
    -- Subcategory: System Info
    ------------------------------------------------------------------------------
    iDRAC2435alertServerIdleTime TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Server is either idle or underutilized "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2435

    ------------------------------------------------------------------------------
    -- Alert: Forwarded: Forwarded MSM Traps
    --
    -- Category: System Health
    -- Subcategory: Processor Absent
    ------------------------------------------------------------------------------
    iDRAC2457alertProcessorDeviceAbsent TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Processor device is absent. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2457

    ------------------------------------------------------------------------------
    -- Alert: Forwarded: Forwarded MSM Traps
    --
    -- Category: System Health
    -- Subcategory: PSU Absent
    ------------------------------------------------------------------------------
    iDRAC2465alertPowerSupplyAbsent TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply is absent. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2465

    ------------------------------------------------------------------------------
    -- Alert: Forwarded: Forwarded MSM Traps
    --
    -- Category: System Health
    -- Subcategory: Redundancy
    ------------------------------------------------------------------------------
    iDRAC2473alertRedundancyLost TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Redundancy is lost. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2473

    ------------------------------------------------------------------------------
    -- Alert: Forwarded: Forwarded MSM Traps
    --
    -- Category: System Health
    -- Subcategory: Redundancy
    ------------------------------------------------------------------------------
    iDRAC2474alertRedundancyDegraded TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Redundancy is degraded. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2474

    ------------------------------------------------------------------------------
    -- Alert: Forwarded: Forwarded MSM Traps
    --
    -- Category: System Health
    -- Subcategory: Redundancy
    ------------------------------------------------------------------------------
    iDRAC2475alertRedundancyInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Redundancy information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2475

    ------------------------------------------------------------------------------
    -- Alert: Forwarded: Forwarded MSM Traps
    --
    -- Category: System Health
    -- Subcategory: IDSDM Absent
    ------------------------------------------------------------------------------
    iDRAC2481alertIntegratedDualSDModuleAbsent TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module is absent. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2481

    ------------------------------------------------------------------------------
    -- Alert: Forwarded: Forwarded MSM Traps
    --
    -- Category: System Health
    -- Subcategory: IDSDM Redundancy
    ------------------------------------------------------------------------------
    iDRAC2489alertIntegratedDualSDModuleRedundancyLost TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module redundancy is lost. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2489

    ------------------------------------------------------------------------------
    -- Alert: Forwarded: Forwarded MSM Traps
    --
    -- Category: System Health
    -- Subcategory: IDSDM Redundancy
    ------------------------------------------------------------------------------
    iDRAC2490alertIntegratedDualSDModuleRedundancyDegraded TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module redundancy is degraded. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2490

    ------------------------------------------------------------------------------
    -- Alert: Forwarded: Forwarded MSM Traps
    --
    -- Category: System Health
    -- Subcategory: IDSDM Redundancy
    ------------------------------------------------------------------------------
    iDRAC2491alertIntegratedDualSDModuleRedundancyInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Integrated Dual SD Module redundancy information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2491

    ------------------------------------------------------------------------------
    -- Alert: Forwarded: Forwarded MSM Traps
    --
    -- Category: System Health
    -- Subcategory: vFlash Event
    ------------------------------------------------------------------------------
    iDRAC2505alertvFlashMediaDeviceFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " vFlash Media device failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2505

    ------------------------------------------------------------------------------
    -- Alert: Forwarded: Forwarded MSM Traps
    --
    -- Category: System Health
    -- Subcategory: vFlash Event
    ------------------------------------------------------------------------------
    iDRAC2506alertvFlashMediaDeviceWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " vFlash Media device warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2506

    ------------------------------------------------------------------------------
    -- Alert: Forwarded: Forwarded MSM Traps
    --
    -- Category: System Health
    -- Subcategory: vFlash Event
    ------------------------------------------------------------------------------
    iDRAC2507alertvFlashMediaDeviceInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " vFlash Media device information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2507

    ------------------------------------------------------------------------------
    -- Alert: Forwarded: Forwarded MSM Traps
    --
    -- Category: System Health
    -- Subcategory: vFlash Absent
    ------------------------------------------------------------------------------
    iDRAC2515alertvFlashMediaDeviceAbsent TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " vFlash Media device is absent. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2515

    ------------------------------------------------------------------------------
    -- Alert: Forwarded: Forwarded MSM Traps
    --
    -- Category: System Health
    -- Subcategory: Temperature Statistics
    ------------------------------------------------------------------------------
    iDRAC2521alertTemperatureStatisticsFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature has been above the warning or critical threshold level"
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2521

    ------------------------------------------------------------------------------
    -- Alert: Forwarded: Forwarded MSM Traps
    --
    -- Category: System Health
    -- Subcategory: Temperature Statistics
    ------------------------------------------------------------------------------
    iDRAC2522alertTemperatureStatisticsWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature has been above the warning or critical threshold level"
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2522

    ------------------------------------------------------------------------------
    -- Alert: Forwarded: Forwarded MSM Traps
    --
    -- Category: System Health
    -- Subcategory: RAC Event
    ------------------------------------------------------------------------------
    iDRAC2531alertRACInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " RAC information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2531

    ------------------------------------------------------------------------------
    -- Alert: Forwarded: Forwarded MSM Traps
    --
    -- Category: System Health
    -- Subcategory: Fibre Channel
    ------------------------------------------------------------------------------
    iDRAC2537alertFiberChannelFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fiber Channel failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2537

    ------------------------------------------------------------------------------
    -- Alert: Forwarded: Forwarded MSM Traps
    --
    -- Category: System Health
    -- Subcategory: Fibre Channel
    ------------------------------------------------------------------------------
    iDRAC2538alertFiberChannelWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fiber Channel warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2538

    ------------------------------------------------------------------------------
    -- Alert: Forwarded: Forwarded MSM Traps
    --
    -- Category: System Health
    -- Subcategory: Fibre Channel
    ------------------------------------------------------------------------------
    iDRAC2539alertFiberChannelInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fiber Channel information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2539

    ------------------------------------------------------------------------------
    -- Alert: Forwarded: Forwarded MSM Traps
    --
    -- Category: System Health
    -- Subcategory: Management Module
    ------------------------------------------------------------------------------
    iDRAC2545alertCMCFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Chassis Management Controller detected an error. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2545

    ------------------------------------------------------------------------------
    -- Alert: Forwarded: Forwarded MSM Traps
    --
    -- Category: System Health
    -- Subcategory: Management Module
    ------------------------------------------------------------------------------
    iDRAC2546alertCMCWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Chassis Management Controller detected a warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2546

    ------------------------------------------------------------------------------
    -- Alert: Forwarded: Forwarded MSM Traps
    --
    -- Category: System Health
    -- Subcategory: IO Virtualization
    ------------------------------------------------------------------------------
    iDRAC2553alertIOVirtualizationFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " IO Virtualization failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2553

    ------------------------------------------------------------------------------
    -- Alert: Forwarded: Forwarded MSM Traps
    --
    -- Category: System Health
    -- Subcategory: System Performance Event
    ------------------------------------------------------------------------------
    iDRAC2650alertSystemPerformanceWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " System Performance warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 2650

    ------------------------------------------------------------------------------
    -- Alert: Forwarded: Forwarded MSM Traps
    --
    -- Category: System Health
    -- Subcategory: Other
    ------------------------------------------------------------------------------
    iDRAC3049alertLiquidCoolingLeakFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " A large leak is detected on the device "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 3049

    ------------------------------------------------------------------------------
    -- Alert: Forwarded: Forwarded MSM Traps
    --
    -- Category: System Health
    -- Subcategory: Other
    ------------------------------------------------------------------------------
    iDRAC3050alertLiquidCoolingLeakWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " A small leak is detected on the device "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 3050

    ------------------------------------------------------------------------------
    -- Alert: Forwarded: Forwarded MSM Traps
    --
    -- Category: System Health
    -- Subcategory: Other
    ------------------------------------------------------------------------------
    iDRAC3051alertLiquidCoolingLeakInformational TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " A small leak that was earlier detected on the device is now resolved. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 3051

    ------------------------------------------------------------------------------
    -- Alert: Forwarded: Forwarded MSM Traps
    --
    -- Category: System Health
    -- Subcategory: Other
    ------------------------------------------------------------------------------
    iDRAC3082alertSDKSystemWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The iDRAC generated a trap event due to a warning from SDK plugin. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 3082

    ------------------------------------------------------------------------------
    -- Alert: Forwarded: Forwarded MSM Traps
    --
    -- Category: System Health
    -- Subcategory: Other
    ------------------------------------------------------------------------------
    iDRAC3083alertSDKSystemInformational TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " The iDRAC generated a trap as iDRAC SDK plugin started working as expected. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 3083

    ------------------------------------------------------------------------------
    -- Alert: Forwarded: Forwarded MSM Traps
    --
    -- Category: Storage
    -- Subcategory: Storage
    ------------------------------------------------------------------------------
    iDRAC4177alertStorageManagementFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Storage Management has detected a device independent error condition."
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4177

    ------------------------------------------------------------------------------
    -- Alert: Forwarded: Forwarded MSM Traps
    --
    -- Category: Storage
    -- Subcategory: Storage
    ------------------------------------------------------------------------------
    iDRAC4178alertStorageManagementWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Storage Management has detected a device independent warning"
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4178

    ------------------------------------------------------------------------------
    -- Alert: Forwarded: Forwarded MSM Traps
    --
    -- Category: Storage
    -- Subcategory: Storage
    ------------------------------------------------------------------------------
    iDRAC4179alertStorageManagementInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Storage Management Information."
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4179

    ------------------------------------------------------------------------------
    -- Alert: Forwarded: Forwarded MSM Traps
    --
    -- Category: Storage
    -- Subcategory: Fan Event
    ------------------------------------------------------------------------------
    iDRAC4201alertStorageFanFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fan failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4201

    ------------------------------------------------------------------------------
    -- Alert: Forwarded: Forwarded MSM Traps
    --
    -- Category: Storage
    -- Subcategory: Fan Event
    ------------------------------------------------------------------------------
    iDRAC4202alertStorageFanWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fan warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4202

    ------------------------------------------------------------------------------
    -- Alert: Forwarded: Forwarded MSM Traps
    --
    -- Category: Storage
    -- Subcategory: Fan Event
    ------------------------------------------------------------------------------
    iDRAC4203alertStorageFanInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Fan information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4203

    ------------------------------------------------------------------------------
    -- Alert: Forwarded: Forwarded MSM Traps
    --
    -- Category: Storage
    -- Subcategory: Temperature
    ------------------------------------------------------------------------------
    iDRAC4209alertStorageTemperatureProbeFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature probe failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4209

    ------------------------------------------------------------------------------
    -- Alert: Forwarded: Forwarded MSM Traps
    --
    -- Category: Storage
    -- Subcategory: Temperature
    ------------------------------------------------------------------------------
    iDRAC4210alertStorageTemperatureProbeWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature probe warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4210

    ------------------------------------------------------------------------------
    -- Alert: Forwarded: Forwarded MSM Traps
    --
    -- Category: Storage
    -- Subcategory: Temperature
    ------------------------------------------------------------------------------
    iDRAC4211alertStorageTemperatureProbeInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature probe information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4211

    ------------------------------------------------------------------------------
    -- Alert: Forwarded: Forwarded MSM Traps
    --
    -- Category: Storage
    -- Subcategory: Power Supply
    ------------------------------------------------------------------------------
    iDRAC4233alertStoragePowerSupplyFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4233

    ------------------------------------------------------------------------------
    -- Alert: Forwarded: Forwarded MSM Traps
    --
    -- Category: Storage
    -- Subcategory: Power Supply
    ------------------------------------------------------------------------------
    iDRAC4234alertStoragePowerSupplyWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4234

    ------------------------------------------------------------------------------
    -- Alert: Forwarded: Forwarded MSM Traps
    --
    -- Category: Storage
    -- Subcategory: Power Supply
    ------------------------------------------------------------------------------
    iDRAC4235alertStoragePowerSupplyInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power supply information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4235

    ------------------------------------------------------------------------------
    -- Alert: Forwarded: Forwarded MSM Traps
    --
    -- Category: Storage
    -- Subcategory: Battery Event
    ------------------------------------------------------------------------------
    iDRAC4273alertStorageBatteryFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Battery failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4273

    ------------------------------------------------------------------------------
    -- Alert: Forwarded: Forwarded MSM Traps
    --
    -- Category: Storage
    -- Subcategory: Battery Event
    ------------------------------------------------------------------------------
    iDRAC4274alertStorageBatteryWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Battery warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4274

    ------------------------------------------------------------------------------
    -- Alert: Forwarded: Forwarded MSM Traps
    --
    -- Category: Storage
    -- Subcategory: Battery Event
    ------------------------------------------------------------------------------
    iDRAC4275alertStorageBatteryInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Battery information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4275

    ------------------------------------------------------------------------------
    -- Alert: Forwarded: Forwarded MSM Traps
    --
    -- Category: Storage
    -- Subcategory: Storage Controller
    ------------------------------------------------------------------------------
    iDRAC4329alertStorageControllerFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Controller failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4329

    ------------------------------------------------------------------------------
    -- Alert: Forwarded: Forwarded MSM Traps
    --
    -- Category: Storage
    -- Subcategory: Storage Controller
    ------------------------------------------------------------------------------
    iDRAC4330alertStorageControllerWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Controller warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4330

    ------------------------------------------------------------------------------
    -- Alert: Forwarded: Forwarded MSM Traps
    --
    -- Category: Storage
    -- Subcategory: Storage Controller
    ------------------------------------------------------------------------------
    iDRAC4331alertStorageControllerInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Controller information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4331

    ------------------------------------------------------------------------------
    -- Alert: Forwarded: Forwarded MSM Traps
    --
    -- Category: Storage
    -- Subcategory: Storage Enclosure
    ------------------------------------------------------------------------------
    iDRAC4337alertStorageEnclosureFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Enclosure failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4337

    ------------------------------------------------------------------------------
    -- Alert: Forwarded: Forwarded MSM Traps
    --
    -- Category: Storage
    -- Subcategory: Storage Enclosure
    ------------------------------------------------------------------------------
    iDRAC4338alertStorageEnclosureWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Enclosure warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4338

    ------------------------------------------------------------------------------
    -- Alert: Forwarded: Forwarded MSM Traps
    --
    -- Category: Storage
    -- Subcategory: Storage Enclosure
    ------------------------------------------------------------------------------
    iDRAC4339alertStorageEnclosureInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Enclosure information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4339

    ------------------------------------------------------------------------------
    -- Alert: Forwarded: Forwarded MSM Traps
    --
    -- Category: Storage
    -- Subcategory: Physical Disk
    ------------------------------------------------------------------------------
    iDRAC4345alertStoragePhysicalDiskFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Physical disk failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4345

    ------------------------------------------------------------------------------
    -- Alert: Forwarded: Forwarded MSM Traps
    --
    -- Category: Storage
    -- Subcategory: Physical Disk
    ------------------------------------------------------------------------------
    iDRAC4346alertStoragePhysicalDiskWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Physical disk warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4346

    ------------------------------------------------------------------------------
    -- Alert: Forwarded: Forwarded MSM Traps
    --
    -- Category: Storage
    -- Subcategory: Physical Disk
    ------------------------------------------------------------------------------
    iDRAC4347alertStoragePhysicalDiskInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Physical disk information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4347

    ------------------------------------------------------------------------------
    -- Alert: Forwarded: Forwarded MSM Traps
    --
    -- Category: Storage
    -- Subcategory: Virtual Disk
    ------------------------------------------------------------------------------
    iDRAC4353alertStorageVirtualDiskFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Virtual disk failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4353

    ------------------------------------------------------------------------------
    -- Alert: Forwarded: Forwarded MSM Traps
    --
    -- Category: Storage
    -- Subcategory: Virtual Disk
    ------------------------------------------------------------------------------
    iDRAC4354alertStorageVirtualDiskWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Virtual disk warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4354

    ------------------------------------------------------------------------------
    -- Alert: Forwarded: Forwarded MSM Traps
    --
    -- Category: Storage
    -- Subcategory: Virtual Disk
    ------------------------------------------------------------------------------
    iDRAC4355alertStorageVirtualDiskInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Virtual disk information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4355

    ------------------------------------------------------------------------------
    -- Alert: Forwarded: Forwarded MSM Traps
    --
    -- Category: Storage
    -- Subcategory: SSD Devices
    ------------------------------------------------------------------------------
    iDRAC4370alertStorageSolidstateDrive TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " SSD is less than the threshold value. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4370

    ------------------------------------------------------------------------------
    -- Alert: Forwarded: Forwarded MSM Traps
    --
    -- Category: Storage
    -- Subcategory: Security Event
    ------------------------------------------------------------------------------
    iDRAC4433alertStorageSecurityFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Storage Security failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4433

    ------------------------------------------------------------------------------
    -- Alert: Forwarded: Forwarded MSM Traps
    --
    -- Category: Storage
    -- Subcategory: Security Event
    ------------------------------------------------------------------------------
    iDRAC4434alertStorageSecurityWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Storage Security warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4434

    ------------------------------------------------------------------------------
    -- Alert: Forwarded: Forwarded MSM Traps
    --
    -- Category: Storage
    -- Subcategory: Security Event
    ------------------------------------------------------------------------------
    iDRAC4435alertStorageSecurityInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Storage Security information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4435

    ------------------------------------------------------------------------------
    -- Alert: Forwarded: Forwarded MSM Traps
    --
    -- Category: Storage
    -- Subcategory: Software Defined Storage
    ------------------------------------------------------------------------------
    iDRAC4761alertStorageSoftwareDefinedSubSystemFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software defined storage subsystem failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4761

    ------------------------------------------------------------------------------
    -- Alert: Forwarded: Forwarded MSM Traps
    --
    -- Category: Storage
    -- Subcategory: Software Defined Storage
    ------------------------------------------------------------------------------
    iDRAC4762alertStorageSoftwareDefinedSubSystemWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software defined storage subsystem warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 4762

    ------------------------------------------------------------------------------
    -- Alert: Forwarded: Forwarded MSM Traps
    --
    -- Category: Updates
    -- Subcategory: Firmware Download
    ------------------------------------------------------------------------------
    iDRAC6211alertUpdateJobInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Update job information "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 6211

    ------------------------------------------------------------------------------
    -- Alert: Forwarded: Forwarded MSM Traps
    --
    -- Category: Updates
    -- Subcategory: Software Change
    ------------------------------------------------------------------------------
    iDRAC6314alertSoftwareChangeUpdateWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Software change update warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 6314

    ------------------------------------------------------------------------------
    -- Alert: Forwarded: Forwarded MSM Traps
    --
    -- Category: Audit
    -- Subcategory: Temperature
    ------------------------------------------------------------------------------
    iDRAC8305alertTemperatureProbeChangeFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Temperature increase Error. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8305

    ------------------------------------------------------------------------------
    -- Alert: Forwarded: Forwarded MSM Traps
    --
    -- Category: Audit
    -- Subcategory: Temperature
    ------------------------------------------------------------------------------
    iDRAC8306alertTemperatureProbeReadWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Unable to read Temperature Sensors "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8306

    ------------------------------------------------------------------------------
    -- Alert: Forwarded: Forwarded MSM Traps
    --
    -- Category: Audit
    -- Subcategory: Power Supply
    ------------------------------------------------------------------------------
    iDRAC8329alertPowerSupplyAuditFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power Supply audit failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8329

    ------------------------------------------------------------------------------
    -- Alert: Forwarded: Forwarded MSM Traps
    --
    -- Category: Audit
    -- Subcategory: Power Supply
    ------------------------------------------------------------------------------
    iDRAC8330alertPowerSupplyAuditWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power Supply audit warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8330

    ------------------------------------------------------------------------------
    -- Alert: Forwarded: Forwarded MSM Traps
    --
    -- Category: Audit
    -- Subcategory: Power Usage
    ------------------------------------------------------------------------------
    iDRAC8417alertPowerUsageAuditFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power usage audit failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8417

    ------------------------------------------------------------------------------
    -- Alert: Forwarded: Forwarded MSM Traps
    --
    -- Category: Audit
    -- Subcategory: Power Usage
    ------------------------------------------------------------------------------
    iDRAC8418alertPowerUsageAuditWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power usage audit warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8418

    ------------------------------------------------------------------------------
    -- Alert: Forwarded: Forwarded MSM Traps
    --
    -- Category: Audit
    -- Subcategory: Power Usage
    ------------------------------------------------------------------------------
    iDRAC8419alertPowerUsageAuditInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Power usage audit information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8419

    ------------------------------------------------------------------------------
    -- Alert: Forwarded: Forwarded MSM Traps
    --
    -- Category: Audit
    -- Subcategory: Hardware Config
    ------------------------------------------------------------------------------
    iDRAC8474alertHWCAuditWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Hardware configuration warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8474

    ------------------------------------------------------------------------------
    -- Alert: Forwarded: Forwarded MSM Traps
    --
    -- Category: Audit
    -- Subcategory: Hardware Config
    ------------------------------------------------------------------------------
    iDRAC8475alertHWCAuditInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Hardware configuration audit information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8475

    ------------------------------------------------------------------------------
    -- Alert: Forwarded: Forwarded MSM Traps
    --
    -- Category: Audit
    -- Subcategory: User Tracking
    ------------------------------------------------------------------------------
    iDRAC8490alertUserTrackingWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " User Tracking warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8490

    ------------------------------------------------------------------------------
    -- Alert: Forwarded: Forwarded MSM Traps
    --
    -- Category: Audit
    -- Subcategory: IP Address
    ------------------------------------------------------------------------------
    iDRAC8499alertiDRACIPAddressChange TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " iDRAC IP address has changed. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8499

    ------------------------------------------------------------------------------
    -- Alert: Forwarded: Forwarded MSM Traps
    --
    -- Category: Audit
    -- Subcategory: Licensing
    ------------------------------------------------------------------------------
    iDRAC8513alertLicenseFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " License failure. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8513

    ------------------------------------------------------------------------------
    -- Alert: Forwarded: Forwarded MSM Traps
    --
    -- Category: Audit
    -- Subcategory: Licensing
    ------------------------------------------------------------------------------
    iDRAC8514alertLicenseWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " License warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8514

    ------------------------------------------------------------------------------
    -- Alert: Forwarded: Forwarded MSM Traps
    --
    -- Category: Audit
    -- Subcategory: Licensing
    ------------------------------------------------------------------------------
    iDRAC8515alertLicenseInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " License information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8515

    ------------------------------------------------------------------------------
    -- Alert: Forwarded: Forwarded MSM Traps
    --
    -- Category: Audit
    -- Subcategory: PCI Device
    ------------------------------------------------------------------------------
    iDRAC8562alertPCIDeviceAuditWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " PCI device audit warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8562

    ------------------------------------------------------------------------------
    -- Alert: Forwarded: Forwarded MSM Traps
    --
    -- Category: Audit
    -- Subcategory: System Info
    ------------------------------------------------------------------------------
    iDRAC8579alertSystemPowerStateChangeInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Host is going through a power state change"
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8579

    ------------------------------------------------------------------------------
    -- Alert: Forwarded: Forwarded MSM Traps
    --
    -- Category: Audit
    -- Subcategory: Debug
    ------------------------------------------------------------------------------
    iDRAC8594alertDebugWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Debug authorization failed. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8594

    ------------------------------------------------------------------------------
    -- Alert: Forwarded: Forwarded MSM Traps
    --
    -- Category: Audit
    -- Subcategory: Debug
    ------------------------------------------------------------------------------
    iDRAC8595alertDebugInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Debug authorized. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8595

    ------------------------------------------------------------------------------
    -- Alert: Forwarded: Forwarded MSM Traps
    --
    -- Category: Audit
    -- Subcategory: RAC Event
    ------------------------------------------------------------------------------
    iDRAC8674alertRacConfigurationChangewarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Configuration or state Change warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8674

    ------------------------------------------------------------------------------
    -- Alert: Forwarded: Forwarded MSM Traps
    --
    -- Category: Audit
    -- Subcategory: RAC Event
    ------------------------------------------------------------------------------
    iDRAC8675alertRacConfigurationChangeInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Configuration or state Change Information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8675

    ------------------------------------------------------------------------------
    -- Alert: Forwarded: Forwarded MSM Traps
    --
    -- Category: Audit
    -- Subcategory: Management Module
    ------------------------------------------------------------------------------
    iDRAC8689alertCMCAuditFailure TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Chassis Management Controller audit failure or critical event. "
            --#TYPE       "Forwarded: Forwarded iDRAC Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8689

    ------------------------------------------------------------------------------
    -- Alert: Forwarded: Forwarded MSM Traps
    --
    -- Category: Audit
    -- Subcategory: Management Module
    ------------------------------------------------------------------------------
    iDRAC8690alertCMCAuditWarning TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Chassis Management Controller audit warning. "
            --#TYPE       "Forwarded: Forwarded iDRAC Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8690

    ------------------------------------------------------------------------------
    -- Alert: Forwarded: Forwarded MSM Traps
    --
    -- Category: Audit
    -- Subcategory: Management Module
    ------------------------------------------------------------------------------
    iDRAC8691alertCMCAuditInformation TRAP-TYPE
            ENTERPRISE  dmmiDRACAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                " Chassis Management Controller audit information. "
            --#TYPE       "Forwarded: Forwarded iDRAC Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 8691

    ------------------------------------------------------------------------------
    -- Alert: Forwarded: Forwarded MSM Traps
    --
    -- Category: Audit
    -- Subcategory: Devices
    ------------------------------------------------------------------------------
    alert851138RCPRestoreInformational TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The automatic restoration of chassis settings is completed on the right control panel."
            --#TYPE       "Forwarded: Forwarded console Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 851138

    ------------------------------------------------------------------------------
    -- Alert: Forwarded: Forwarded MSM Traps
    --
    -- Category: Audit
    -- Subcategory: Devices
    ------------------------------------------------------------------------------
    alert851139RCPRestoreCritical TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The automatic restoration of chassis settings is either unsuccessful orcompleted with warnings on the right control panel."
            --#TYPE       "Forwarded: Forwarded console Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 851139

    ------------------------------------------------------------------------------
    -- Alert: Forwarded: Forwarded MSM Traps
    --
    -- Category: System Health
    -- Subcategory: Devices
    ------------------------------------------------------------------------------
    alert856129DeviceStateInformational TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The device health status has changed."
            --#TYPE       "Forwarded: Forwarded console Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856129

    ------------------------------------------------------------------------------
    -- Alert: Forwarded: Forwarded MSM Traps
    --
    -- Category: System Health
    -- Subcategory: Devices
    ------------------------------------------------------------------------------
    alert856130DeviceStateCritical TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The device power state has changed."
            --#TYPE       "Forwarded: Forwarded console Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856130

    ------------------------------------------------------------------------------
    -- Alert: Forwarded: Forwarded MSM Traps
    --
    -- Category: System Health
    -- Subcategory: Devices
    ------------------------------------------------------------------------------
    alert856131DeviceStateCritical TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The operation cannot be performed on the device because connection with the device is lost."
            --#TYPE       "Forwarded: Forwarded console Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856131

    ------------------------------------------------------------------------------
    -- Alert: Forwarded: Forwarded MSM Traps
    --
    -- Category: Audit
    -- Subcategory: Devices
    ------------------------------------------------------------------------------
    alert856132DeviceStateInformational TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "A new device is detected in the chassis."
            --#TYPE       "Forwarded: Forwarded console Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856132

    ------------------------------------------------------------------------------
    -- Alert: Forwarded: Forwarded MSM Traps
    --
    -- Category: Configuration
    -- Subcategory: Devices
    ------------------------------------------------------------------------------
    alert856133DeviceStateInformational TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "A new device is successfully inserted in the chassis."
            --#TYPE       "Forwarded: Forwarded console Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856133

    ------------------------------------------------------------------------------
    -- Alert: Forwarded: Forwarded MSM Traps
    --
    -- Category: Configuration
    -- Subcategory: Devices
    ------------------------------------------------------------------------------
    alert856134DeviceStateInformational TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "A device is removed from the chassis."
            --#TYPE       "Forwarded: Forwarded console Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856134

    ------------------------------------------------------------------------------
    -- Alert: Forwarded: Forwarded MSM Traps
    --
    -- Category: System Health
    -- Subcategory: Devices
    ------------------------------------------------------------------------------
    alert856172DeviceStateInformational TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "Device Health Changed to OK."
            --#TYPE       "Forwarded: Forwarded console Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856172

    ------------------------------------------------------------------------------
    -- Alert: Forwarded: Forwarded MSM Traps
    --
    -- Category: System Health
    -- Subcategory: Devices
    ------------------------------------------------------------------------------
    alert856173DeviceStateCritical TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The device health status has changed."
            --#TYPE       "Forwarded: Forwarded console Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856173

    ------------------------------------------------------------------------------
    -- Alert: Forwarded: Forwarded MSM Traps
    --
    -- Category: System Health
    -- Subcategory: Devices
    ------------------------------------------------------------------------------
    alert856174DeviceStateCritical TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The device health status has changed."
            --#TYPE       "Forwarded: Forwarded console Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856174

    ------------------------------------------------------------------------------
    -- Alert: Forwarded: Forwarded MSM Traps
    --
    -- Category: System Health
    -- Subcategory: Devices
    ------------------------------------------------------------------------------
    alert856175DeviceStateWarning TRAP-TYPE
            ENTERPRISE  dmmChassisAlert2Group
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The device health status has changed."
            --#TYPE       "Forwarded: Forwarded console Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 856175

    ------------------------------------------------------------------------------
    -- Alert: Forwarded: Forwarded MSM Traps
    --
    -- Category: System Health
    -- Subcategory: Fabric
    ------------------------------------------------------------------------------
    nwIOM980021AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The health status of SmartFabric identified in the message is ok."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980021

    ------------------------------------------------------------------------------
    -- Alert: Forwarded: Forwarded MSM Traps
    --
    -- Category: System Health
    -- Subcategory: Fabric
    ------------------------------------------------------------------------------
    nwIOM980022AlertFabricWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The health status of the SmartFabric identified in the message is in the Warning state."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980022

    ------------------------------------------------------------------------------
    -- Alert: Forwarded: Forwarded MSM Traps
    --
    -- Category: System Health
    -- Subcategory: Fabric
    ------------------------------------------------------------------------------
    nwIOM980023AlertFabricCritical TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The health status of the SmartFabric identified in the message is in Critical state."
            --#TYPE       "Forwarded: Forwarded nwIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980023

    ------------------------------------------------------------------------------
    -- Alert: Forwarded: Forwarded MSM Traps
    --
    -- Category: System Health
    -- Subcategory: Fabric
    ------------------------------------------------------------------------------
    nwIOM980024AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SmartFabric identified in the message is valid. The SmartFabric validation criteria such as design  fabric node inventory  I O module placement requirements  and inter node connectivity are consistent."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980024

    ------------------------------------------------------------------------------
    -- Alert: Forwarded: Forwarded MSM Traps
    --
    -- Category: System Health
    -- Subcategory: Fabric
    ------------------------------------------------------------------------------
    nwIOM980025AlertFabricWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The validation of the SmartFabric for the selected fabric design has failed."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980025

    ------------------------------------------------------------------------------
    -- Alert: Forwarded: Forwarded MSM Traps
    --
    -- Category: Audit
    -- Subcategory: Fabric
    ------------------------------------------------------------------------------
    nwIOM980026AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The creation or deletion of SmartFabric with the fabric ID identified in the message is started."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980026

    ------------------------------------------------------------------------------
    -- Alert: Forwarded: Forwarded MSM Traps
    --
    -- Category: Audit
    -- Subcategory: Fabric
    ------------------------------------------------------------------------------
    nwIOM980027AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SmartFabric with the fabric ID identified in the message is currently being created or deleted."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980027

    ------------------------------------------------------------------------------
    -- Alert: Forwarded: Forwarded MSM Traps
    --
    -- Category: Audit
    -- Subcategory: Fabric
    ------------------------------------------------------------------------------
    nwIOM980028AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The creation or deletion of SmartFabric with the fabric ID identified in the message is successfully completed."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980028

    ------------------------------------------------------------------------------
    -- Alert: Forwarded: Forwarded MSM Traps
    --
    -- Category: Audit
    -- Subcategory: Fabric
    ------------------------------------------------------------------------------
    nwIOM980029AlertFabricCritical TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The creation or deletion of SmartFabric with the fabric ID identified in the message cannot be completed because of many ongoing maintenance operations."
            --#TYPE       "Forwarded: Forwarded nwIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980029

    ------------------------------------------------------------------------------
    -- Alert: Forwarded: Forwarded MSM Traps
    --
    -- Category: System Health
    -- Subcategory: Fabric
    ------------------------------------------------------------------------------
    nwIOM980030AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "New fabric design is updated after the chassis change."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980030

    ------------------------------------------------------------------------------
    -- Alert: Forwarded: Forwarded MSM Traps
    --
    -- Category: Audit
    -- Subcategory: Fabric
    ------------------------------------------------------------------------------
    nwIOM980031AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SmartFabric identified in the message is successfully deleted by the Fabric Manager. The switches will automatically restart and be in the Full Switch mode."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980031

    ------------------------------------------------------------------------------
    -- Alert: Forwarded: Forwarded MSM Traps
    --
    -- Category: Audit
    -- Subcategory: Fabric
    ------------------------------------------------------------------------------
    nwIOM980032AlertFabricInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The switch identified in the message is detected as a potential replacement switch for a faulty or old switch  which must be replaced. The old or faulty switch belongs to the SmartFabric that has the fabric ID as identified in the message."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 980032

    ------------------------------------------------------------------------------
    -- Alert: Forwarded: Forwarded MSM Traps
    --
    -- Category: Audit
    -- Subcategory: Interface
    ------------------------------------------------------------------------------
    nwIOM990001AlertInterfaceInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The interface identified in the message is in operational status."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 990001

    ------------------------------------------------------------------------------
    -- Alert: Forwarded: Forwarded MSM Traps
    --
    -- Category: Audit
    -- Subcategory: Interface
    ------------------------------------------------------------------------------
    nwIOM990002AlertInterfaceWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The interface identified in the message is not operational."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 990002

    ------------------------------------------------------------------------------
    -- Alert: Forwarded: Forwarded MSM Traps
    --
    -- Category: Audit
    -- Subcategory: Link
    ------------------------------------------------------------------------------
    nwIOM1000001AlertLinkInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The link between Source and Destination identified in the message is created."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1000001

    ------------------------------------------------------------------------------
    -- Alert: Forwarded: Forwarded MSM Traps
    --
    -- Category: Audit
    -- Subcategory: Link
    ------------------------------------------------------------------------------
    nwIOM1000002AlertLinkWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The link identified in the message is successfully deleted."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1000002

    ------------------------------------------------------------------------------
    -- Alert: Forwarded: Forwarded MSM Traps
    --
    -- Category: System Health
    -- Subcategory: Node
    ------------------------------------------------------------------------------
    nwIOM1010001AlertNodeInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The I O Module identified in the message is operational."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010001

    ------------------------------------------------------------------------------
    -- Alert: Forwarded: Forwarded MSM Traps
    --
    -- Category: System Health
    -- Subcategory: Node
    ------------------------------------------------------------------------------
    nwIOM1010002AlertNodeWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The operational status of the I O Module identified in the message has ended. Possible reasons could be that the MCM Group maintenance is in progress or Management Module maintenance is in progress or Fabric maintenance is in progress or Node maintenance is in progress."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010002

    ------------------------------------------------------------------------------
    -- Alert: Forwarded: Forwarded MSM Traps
    --
    -- Category: Audit
    -- Subcategory: Node
    ------------------------------------------------------------------------------
    nwIOM1010003AlertNodeInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The I O Module identified in the message is discovered."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010003

    ------------------------------------------------------------------------------
    -- Alert: Forwarded: Forwarded MSM Traps
    --
    -- Category: Audit
    -- Subcategory: Node
    ------------------------------------------------------------------------------
    nwIOM1010004AlertNodeWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The I O Module identified in the message cannot be detected because of physical connection and operational issues."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010004

    ------------------------------------------------------------------------------
    -- Alert: Forwarded: Forwarded MSM Traps
    --
    -- Category: Audit
    -- Subcategory: Node
    ------------------------------------------------------------------------------
    nwIOM1010005AlertNodeInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The MX7116n Fabric Expander Module identified in the message is discovered."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010005

    ------------------------------------------------------------------------------
    -- Alert: Forwarded: Forwarded MSM Traps
    --
    -- Category: Audit
    -- Subcategory: Node
    ------------------------------------------------------------------------------
    nwIOM1010006AlertNodeWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The MX7116n Fabric Expander Module identified in the message cannot be detected because of physical connection issues."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010006

    ------------------------------------------------------------------------------
    -- Alert: Forwarded: Forwarded MSM Traps
    --
    -- Category: Audit
    -- Subcategory: Node
    ------------------------------------------------------------------------------
    nwIOM1010007AlertNodeWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "A simple I O module swap operation cannot be performed because the replacement I O module software version is different from the fabric software version as identified in the message."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1010007

    ------------------------------------------------------------------------------
    -- Alert: Forwarded: Forwarded MSM Traps
    --
    -- Category: Audit
    -- Subcategory: Server
    ------------------------------------------------------------------------------
    nwIOM1020001AlertServerInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The server identified in the message is detected."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020001

    ------------------------------------------------------------------------------
    -- Alert: Forwarded: Forwarded MSM Traps
    --
    -- Category: Audit
    -- Subcategory: Server
    ------------------------------------------------------------------------------
    nwIOM1020002AlertServerWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The server identified in the message is not detected. Possible reasons could be that the fabric node to which the server is connected is operationally down or the server is moved or replaced from the existing slot."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020002

    ------------------------------------------------------------------------------
    -- Alert: Forwarded: Forwarded MSM Traps
    --
    -- Category: Audit
    -- Subcategory: Server
    ------------------------------------------------------------------------------
    nwIOM1020003AlertServerInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The configuration of server identified in the message is validated and onboarded."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020003

    ------------------------------------------------------------------------------
    -- Alert: Forwarded: Forwarded MSM Traps
    --
    -- Category: Audit
    -- Subcategory: Server
    ------------------------------------------------------------------------------
    nwIOM1020004AlertServerWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The detected server and its configuration is no longer validated."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020004

    ------------------------------------------------------------------------------
    -- Alert: Forwarded: Forwarded MSM Traps
    --
    -- Category: Audit
    -- Subcategory: Server
    ------------------------------------------------------------------------------
    nwIOM1020005AlertServerInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The configuration of server identified in the message is validated and successfully onboarded."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020005

    ------------------------------------------------------------------------------
    -- Alert: Forwarded: Forwarded MSM Traps
    --
    -- Category: Audit
    -- Subcategory: Server
    ------------------------------------------------------------------------------
    nwIOM1020006AlertServerWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The detected server interface and its configuration is not validated."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020006

    ------------------------------------------------------------------------------
    -- Alert: Forwarded: Forwarded MSM Traps
    --
    -- Category: Audit
    -- Subcategory: Server
    ------------------------------------------------------------------------------
    nwIOM1020007AlertServerInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The server and server interfaces identified in the message are bonded."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020007

    ------------------------------------------------------------------------------
    -- Alert: Forwarded: Forwarded MSM Traps
    --
    -- Category: Audit
    -- Subcategory: Server
    ------------------------------------------------------------------------------
    nwIOM1020008AlertServerWarning TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The server and server interfaces identified in the message are unbonded."
            --#TYPE       "Forwarded: Forwarded nwIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1020008

    ------------------------------------------------------------------------------
    -- Alert: Forwarded: Forwarded MSM Traps
    --
    -- Category: Audit
    -- Subcategory: REST
    ------------------------------------------------------------------------------
    nwIOM1052505AlertRESTInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "Feature capability ofSmartFabric Manager has changed."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1052505

    ------------------------------------------------------------------------------
    -- Alert: Forwarded: Forwarded MSM Traps
    --
    -- Category: Audit
    -- Subcategory: REST
    ------------------------------------------------------------------------------
    nwIOM1052506AlertRESTInformational TRAP-TYPE
            ENTERPRISE  dmmNWIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "Feature capability ofSmartFabric Manager has changed."
            --#TYPE       "Forwarded: Forwarded nwIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1052506

    ------------------------------------------------------------------------------
    -- Alert: Forwarded: Forwarded MSM Traps
    --
    -- Category: System Health
    -- Subcategory: SAS IOM
    ------------------------------------------------------------------------------
    sasIOM1120001AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM devices identified in the message could not communicate with each other via the inter IOM link."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120001

    ------------------------------------------------------------------------------
    -- Alert: Forwarded: Forwarded MSM Traps
    --
    -- Category: System Health
    -- Subcategory: SAS IOM
    ------------------------------------------------------------------------------
    sasIOM1120002AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The communication between the SAS IOM devices identified in the message is successfully restored. The PartnerInterconnectCommunicationFault event is resolved."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120002

    ------------------------------------------------------------------------------
    -- Alert: Forwarded: Forwarded MSM Traps
    --
    -- Category: System Health
    -- Subcategory: SAS IOM
    ------------------------------------------------------------------------------
    sasIOM1120003AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM is currently configured for redundancy but the firmware version of the SAS IOM devices identified in the message do not match."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120003

    ------------------------------------------------------------------------------
    -- Alert: Forwarded: Forwarded MSM Traps
    --
    -- Category: System Health
    -- Subcategory: SAS IOM
    ------------------------------------------------------------------------------
    sasIOM1120004AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The firmware version mismatch between the SAS IOM devices identified in the message is successfully resolved."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120004

    ------------------------------------------------------------------------------
    -- Alert: Forwarded: Forwarded MSM Traps
    --
    -- Category: System Health
    -- Subcategory: SAS IOM
    ------------------------------------------------------------------------------
    sasIOM1120005AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "This event indicates that the SAS IOM has been configured for dual domain operation but only one module is currently present."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120005

    ------------------------------------------------------------------------------
    -- Alert: Forwarded: Forwarded MSM Traps
    --
    -- Category: System Health
    -- Subcategory: SAS IOM
    ------------------------------------------------------------------------------
    sasIOM1120006AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device redundancy issue is resolved. The specified number of IOMs are now present in the slots."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120006

    ------------------------------------------------------------------------------
    -- Alert: Forwarded: Forwarded MSM Traps
    --
    -- Category: System Health
    -- Subcategory: SAS IOM
    ------------------------------------------------------------------------------
    sasIOM1120007AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "Unable to update the firmware version of the device because of an internal error."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120007

    ------------------------------------------------------------------------------
    -- Alert: Forwarded: Forwarded MSM Traps
    --
    -- Category: System Health
    -- Subcategory: SAS IOM
    ------------------------------------------------------------------------------
    sasIOM1120008AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The firmware version cannot be updated because the firmware image file is invalid. This could indicate conditions such as corrupted or unsigned package."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120008

    ------------------------------------------------------------------------------
    -- Alert: Forwarded: Forwarded MSM Traps
    --
    -- Category: System Health
    -- Subcategory: SAS IOM
    ------------------------------------------------------------------------------
    sasIOM1120009AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The firmware is successfully updated."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120009

    ------------------------------------------------------------------------------
    -- Alert: Forwarded: Forwarded MSM Traps
    --
    -- Category: System Health
    -- Subcategory: SAS IOM
    ------------------------------------------------------------------------------
    sasIOM1120010AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The storage assignment cannot be applied."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120010

    ------------------------------------------------------------------------------
    -- Alert: Forwarded: Forwarded MSM Traps
    --
    -- Category: System Health
    -- Subcategory: SAS IOM
    ------------------------------------------------------------------------------
    sasIOM1120011AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The storage assignment is successfully applied."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120011

    ------------------------------------------------------------------------------
    -- Alert: Forwarded: Forwarded MSM Traps
    --
    -- Category: System Health
    -- Subcategory: SAS IOM
    ------------------------------------------------------------------------------
    sasIOM1120012AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device cannot communicate with the drive available at the location identified in the message."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120012

    ------------------------------------------------------------------------------
    -- Alert: Forwarded: Forwarded MSM Traps
    --
    -- Category: System Health
    -- Subcategory: SAS IOM
    ------------------------------------------------------------------------------
    sasIOM1120013AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The drive at the location identified in the message is working."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120013

    ------------------------------------------------------------------------------
    -- Alert: Forwarded: Forwarded MSM Traps
    --
    -- Category: System Health
    -- Subcategory: SAS IOM
    ------------------------------------------------------------------------------
    sasIOM1120016AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "This event indicates that the expanders within a storage module have different firmware versions."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120016

    ------------------------------------------------------------------------------
    -- Alert: Forwarded: Forwarded MSM Traps
    --
    -- Category: System Health
    -- Subcategory: SAS IOM
    ------------------------------------------------------------------------------
    sasIOM1120017AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "This event indicates that the expanders within a storage module now have the same firmware."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120017

    ------------------------------------------------------------------------------
    -- Alert: Forwarded: Forwarded MSM Traps
    --
    -- Category: System Health
    -- Subcategory: SAS IOM
    ------------------------------------------------------------------------------
    sasIOM1120018AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The hot swappable expander identified in the message in the storage enclosure in Chassis slot is not functioning."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120018

    ------------------------------------------------------------------------------
    -- Alert: Forwarded: Forwarded MSM Traps
    --
    -- Category: System Health
    -- Subcategory: SAS IOM
    ------------------------------------------------------------------------------
    sasIOM1120019AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The hot swappable expander identified in the message in the storage enclosure in Chassis slot is functioning."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120019

    ------------------------------------------------------------------------------
    -- Alert: Forwarded: Forwarded MSM Traps
    --
    -- Category: System Health
    -- Subcategory: SAS IOM
    ------------------------------------------------------------------------------
    sasIOM1120020AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The storage enclosure is inserted into the Chassis slot identified in the message. This is for hotplug only."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120020

    ------------------------------------------------------------------------------
    -- Alert: Forwarded: Forwarded MSM Traps
    --
    -- Category: System Health
    -- Subcategory: SAS IOM
    ------------------------------------------------------------------------------
    sasIOM1120021AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The storage enclosure is removed from the Chassis slot identified in the message. The enclosure will also be marked as removed if all SAS connectivity to the enclosure is lost."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120021

    ------------------------------------------------------------------------------
    -- Alert: Forwarded: Forwarded MSM Traps
    --
    -- Category: System Health
    -- Subcategory: SAS IOM
    ------------------------------------------------------------------------------
    sasIOM1120022AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The hot swappable expander identified in the message is inserted. This is for hot plug only."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120022

    ------------------------------------------------------------------------------
    -- Alert: Forwarded: Forwarded MSM Traps
    --
    -- Category: System Health
    -- Subcategory: SAS IOM
    ------------------------------------------------------------------------------
    sasIOM1120023AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The hot swappable expander identified in the message has been removed from the storage Enclosure."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120023

    ------------------------------------------------------------------------------
    -- Alert: Forwarded: Forwarded MSM Traps
    --
    -- Category: System Health
    -- Subcategory: SAS IOM
    ------------------------------------------------------------------------------
    sasIOM1120024AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The Reset operation is initiated on the storage enclosure in the Chassis identified in the message."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120024

    ------------------------------------------------------------------------------
    -- Alert: Forwarded: Forwarded MSM Traps
    --
    -- Category: System Health
    -- Subcategory: SAS IOM
    ------------------------------------------------------------------------------
    sasIOM1120025AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "There is a configuration mismatch between the SAS IOM devices identified in the message."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120025

    ------------------------------------------------------------------------------
    -- Alert: Forwarded: Forwarded MSM Traps
    --
    -- Category: System Health
    -- Subcategory: SAS IOM
    ------------------------------------------------------------------------------
    sasIOM1120026AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The configuration of both SAS IOM devices identified in the message is the same."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120026

    ------------------------------------------------------------------------------
    -- Alert: Forwarded: Forwarded MSM Traps
    --
    -- Category: System Health
    -- Subcategory: SAS IOM
    ------------------------------------------------------------------------------
    sasIOM1120027AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "This event indicates that the foreign SAS IOMs are inserted to the chassis."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120027

    ------------------------------------------------------------------------------
    -- Alert: Forwarded: Forwarded MSM Traps
    --
    -- Category: System Health
    -- Subcategory: SAS IOM
    ------------------------------------------------------------------------------
    sasIOM1120028AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The configuration of both SAS IOM device identified in the message is consistent with the configuration of Chassis."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120028

    ------------------------------------------------------------------------------
    -- Alert: Forwarded: Forwarded MSM Traps
    --
    -- Category: System Health
    -- Subcategory: SAS IOM
    ------------------------------------------------------------------------------
    sasIOM1120029AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device identified in the message has inconsistent firmware versions in its components such as SoC  IOC  and expander."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120029

    ------------------------------------------------------------------------------
    -- Alert: Forwarded: Forwarded MSM Traps
    --
    -- Category: System Health
    -- Subcategory: SAS IOM
    ------------------------------------------------------------------------------
    sasIOM1120030AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device identified in the message requires a power cycle operation to enable the new firmware version."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120030

    ------------------------------------------------------------------------------
    -- Alert: Forwarded: Forwarded MSM Traps
    --
    -- Category: System Health
    -- Subcategory: SAS IOM
    ------------------------------------------------------------------------------
    sasIOM1120031AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device identified in the message is unable to manage the storage assignment."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120031

    ------------------------------------------------------------------------------
    -- Alert: Forwarded: Forwarded MSM Traps
    --
    -- Category: System Health
    -- Subcategory: SAS IOM
    ------------------------------------------------------------------------------
    sasIOM1120032AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device identified in the message is able to manage the storage assignment."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120032

    ------------------------------------------------------------------------------
    -- Alert: Forwarded: Forwarded MSM Traps
    --
    -- Category: System Health
    -- Subcategory: SAS IOM
    ------------------------------------------------------------------------------
    sasIOM1120033AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM device identified in the message has detected multiple Error correcting Code  ECC  errors."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120033

    ------------------------------------------------------------------------------
    -- Alert: Forwarded: Forwarded MSM Traps
    --
    -- Category: System Health
    -- Subcategory: SAS IOM
    ------------------------------------------------------------------------------
    sasIOM1120034AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "An unsupported SATA drive is detected in chassis in the slot indicated in the message."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120034

    ------------------------------------------------------------------------------
    -- Alert: Forwarded: Forwarded MSM Traps
    --
    -- Category: System Health
    -- Subcategory: SAS IOM
    ------------------------------------------------------------------------------
    sasIOM1120035AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "This event indicates that a drive has been added."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120035

    ------------------------------------------------------------------------------
    -- Alert: Forwarded: Forwarded MSM Traps
    --
    -- Category: System Health
    -- Subcategory: SAS IOM
    ------------------------------------------------------------------------------
    sasIOM1120036AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "This event indicates that a drive has been removed."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120036

    ------------------------------------------------------------------------------
    -- Alert: Forwarded: Forwarded MSM Traps
    --
    -- Category: System Health
    -- Subcategory: SAS IOM
    ------------------------------------------------------------------------------
    sasIOM1120039AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM is currently configured for redundancy and the hot spare SAS IOM is not available in the slot."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120039

    ------------------------------------------------------------------------------
    -- Alert: Forwarded: Forwarded MSM Traps
    --
    -- Category: System Health
    -- Subcategory: SAS IOM
    ------------------------------------------------------------------------------
    sasIOM1120040AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM is currently configured for redundancy and communication with the hot spare SAS IOM has ended."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120040

    ------------------------------------------------------------------------------
    -- Alert: Forwarded: Forwarded MSM Traps
    --
    -- Category: System Health
    -- Subcategory: SAS IOM
    ------------------------------------------------------------------------------
    sasIOM1120041AlertHealthCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM is currently configured for redundancy but the firmware version is different from the hot spare SAS IOM."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120041

    ------------------------------------------------------------------------------
    -- Alert: Forwarded: Forwarded MSM Traps
    --
    -- Category: Configuration
    -- Subcategory: SAS IOM
    ------------------------------------------------------------------------------
    sasIOM1120042AlertConfigurationCritical TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "There is a configuration mismatch between the SAS IOM devices identified in the message."
            --#TYPE       "Forwarded: Forwarded sasIOM Alert"
            --#SEVERITY   CRITICAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120042

    ------------------------------------------------------------------------------
    -- Alert: Forwarded: Forwarded MSM Traps
    --
    -- Category: System Health
    -- Subcategory: SAS IOM
    ------------------------------------------------------------------------------
    sasIOM1120069AlertHealthInformational TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The support dump file is successfully created ."
            --#TYPE       "Forwarded: Forwarded sasIOM Alert"
            --#SEVERITY   INFORMATIONAL
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120069

    ------------------------------------------------------------------------------
    -- Alert: Forwarded: Forwarded MSM Traps
    --
    -- Category: System Health
    -- Subcategory: SAS IOM
    ------------------------------------------------------------------------------
    sasIOM1120072AlertHealthWarning TRAP-TYPE
            ENTERPRISE  dmmSASIOMAlertGroup
            VARIABLES { dmmCA2MessageID,
                        dmmCA2Message,
                        dmmCA2MessageArgs,
                        dmmCA2AlertStatus,
                        dmmDeviceServiceTag,
                        dmmCategoryName,
                        dmmSubCategoryName,
                        dmmSeverity
                        }
            DESCRIPTION
                "The SAS IOM has a degraded SAS connection between a SAS IOM and a storage enclosure identified in the message."
            --#TYPE       "Forwarded: Forwarded sasIOM Alert"
            --#SEVERITY   WARNING
            --#SUMMARY    "Message ID: %s, Message: %s,"
            --#SUMMARY    "Device Status: %d "
            --#ARGUMENTS  {0, 1, 3}
            --#CATEGORY   "Forwarded Events"
            --#STATE      OPERATIONAL
            --#STATUS     MANDATORY
            ::= 1120072

END
