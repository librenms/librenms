-- Generated by
-- confdc ++emit-mib /home/harsha/dev/arc_sw_2/arrcus_sw/dpal/common/snmp/ARRCUS-HARDWARE-UTILIZATION-MIB.mib ++oid 1.3.6.1.4.1.51604.3.1 ++module ARRCUS-HARDWARE-UTILIZATION-MIB ++generate-oids -f /etc/confd/ietf-yang-types.fxs /home/harsha/dev/arc_sw_2/arrcus_sw/build/ui/common/arcos-features.fxs /home/harsha/dev/arc_sw_2/arrcus_sw/build/ui/common/arcos-hardware-platform-dnx.fxs /home/harsha/dev/arc_sw_2/arrcus_sw/build/ui/common/arcos-hardware-platform-interface.fxs /home/harsha/dev/arc_sw_2/arrcus_sw/build/ui/common/arcos-hardware-platform-types.fxs /home/harsha/dev/arc_sw_2/arrcus_sw/build/ui/common/arcos-hardware-platform-xgs-interface.fxs /home/harsha/dev/arc_sw_2/arrcus_sw/build/ui/common/arcos-hardware-platform-xgs.fxs /home/harsha/dev/arc_sw_2/arrcus_sw/build/ui/common/arcos-platform.fxs /home/harsha/dev/arc_sw_2/arrcus_sw/build/ui/common/arcos-runtime.fxs /home/harsha/dev/arc_sw_2/arrcus_sw/build/ui/common/ietf-interfaces.fxs /home/harsha/dev/arc_sw_2/arrcus_sw/build/ui/common/openconfig-alarm-types.fxs /home/harsha/dev/arc_sw_2/arrcus_sw/build/ui/common/openconfig-interfaces.fxs /home/harsha/dev/arc_sw_2/arrcus_sw/build/ui/common/openconfig-platform-types.fxs /home/harsha/dev/arc_sw_2/arrcus_sw/build/ui/common/openconfig-platform.fxs /home/harsha/dev/arc_sw_2/arrcus_sw/build/ui/common/openconfig-types.fxs /home/harsha/dev/arc_sw_2/arrcus_sw/build/ui/common/openconfig-yang-types.fxs ++ /home/harsha/dev/arc_sw_2/arrcus_sw/build/ui/common/arcos-hardware.fxs
-- 2022-10-10 06:36:53
-- Namespace: http://yang.arrcus.com/arcos/hardware

ARRCUS-HARDWARE-UTILIZATION-MIB DEFINITIONS ::= BEGIN
aRRCUS-HARDWARE-UTILIZATION-MIB MODULE-IDENTITY
    LAST-UPDATED "@LAST-UPDATED"
    ORGANIZATION "@ORGANIZATION"
    CONTACT-INFO "@CONTACT-INFO"
    DESCRIPTION ""
    REVISION "@REVISION"
    DESCRIPTION "@REVISION-DESCRIPTION"
    ::= { 1 3 6 1 4 1 51604 3 1 }

UnsignedByte ::= TEXTUAL-CONVENTION
    DISPLAY-HINT "d"
    STATUS      current
    DESCRIPTION "xs:unsignedByte"
    SYNTAX      Unsigned32 (0 .. 255)

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

Hw-pltf-fwd-profile ::= TEXTUAL-CONVENTION
    STATUS      current
    DESCRIPTION ""
    SYNTAX      INTEGER {p1(1),p2(2),p3(3),p4(4),p5(5)}

-- Hardware datapath configuration
-- tagpath /hardware
hardware OBJECT IDENTIFIER ::= { aRRCUS-HARDWARE-UTILIZATION-MIB 1 }

-- tagpath /hardware/units
hardwareUnits OBJECT IDENTIFIER ::= { hardware 1 }

-- tagpath /hardware/units/unit-entry
hardwareUnitsTable OBJECT-TYPE
    SYNTAX      SEQUENCE OF HardwareUnitsEntry
    MAX-ACCESS  not-accessible
    STATUS      current
    DESCRIPTION ""
    ::= { hardwareUnits 1 }

-- tagpath /hardware/units/unit-entry
hardwareUnitsEntry OBJECT-TYPE
    SYNTAX      HardwareUnitsEntry
    MAX-ACCESS  not-accessible
    STATUS      current
    DESCRIPTION ""
    INDEX { hardwareUnitId }
        ::= { hardwareUnitsTable 1 }

HardwareUnitsEntry ::=
    SEQUENCE {
        hardwareUnitId Unsigned32,
        hardwareUnitDescr String
    }

-- tagpath /hardware/units/unit-entry/unit-id
hardwareUnitId OBJECT-TYPE
    SYNTAX      Unsigned32
    MAX-ACCESS  not-accessible
    STATUS      current
    DESCRIPTION ""
    ::= { hardwareUnitsEntry 1 }

-- tagpath /hardware/units/unit-entry/unit-descr
hardwareUnitDescr OBJECT-TYPE
    SYNTAX      String
    MAX-ACCESS  read-only
    STATUS      current
    DESCRIPTION ""
    ::= { hardwareUnitsEntry 2 }

-- tagpath /hardware/units/unit-entry/resources/resource-entry
hardwareResourceTable OBJECT-TYPE
    SYNTAX      SEQUENCE OF HardwareResourceEntry
    MAX-ACCESS  not-accessible
    STATUS      current
    DESCRIPTION ""
    ::= { aRRCUS-HARDWARE-UTILIZATION-MIB 2 }

-- tagpath /hardware/units/unit-entry/resources/resource-entry
hardwareResourceEntry OBJECT-TYPE
    SYNTAX      HardwareResourceEntry
    MAX-ACCESS  not-accessible
    STATUS      current
    DESCRIPTION ""
    INDEX { hardwareUnitId, IMPLIED hardwareResourceName }
        ::= { hardwareResourceTable 1 }

HardwareResourceEntry ::=
    SEQUENCE {
        hardwareResourceName String,
        hardwareRawMax ConfdString,
        hardwareRawFree ConfdString
    }

-- tagpath /hardware/units/unit-entry/resources/resource-entry/name
hardwareResourceName OBJECT-TYPE
    SYNTAX      String
    MAX-ACCESS  not-accessible
    STATUS      current
    DESCRIPTION ""
    ::= { hardwareResourceEntry 1 }

-- tagpath /hardware/units/unit-entry/resources/resource-entry/raw-used
hardwareRawMax OBJECT-TYPE
    SYNTAX      ConfdString
    MAX-ACCESS  read-only
    STATUS      current
    DESCRIPTION ""
    ::= { hardwareResourceEntry 2 }

-- tagpath /hardware/units/unit-entry/resources/resource-entry/raw-free
hardwareRawFree OBJECT-TYPE
    SYNTAX      ConfdString
    MAX-ACCESS  read-only
    STATUS      current
    DESCRIPTION ""
    ::= { hardwareResourceEntry 3 }

-- tagpath /hardware/units/unit-entry/resources/resource-entry/feature/feature-entry
hardwareFeatureTable OBJECT-TYPE
    SYNTAX      SEQUENCE OF HardwareFeatureEntry
    MAX-ACCESS  not-accessible
    STATUS      current
    DESCRIPTION ""
    ::= { aRRCUS-HARDWARE-UTILIZATION-MIB 3 }

-- tagpath /hardware/units/unit-entry/resources/resource-entry/feature/feature-entry
hardwareFeatureEntry OBJECT-TYPE
    SYNTAX      HardwareFeatureEntry
    MAX-ACCESS  not-accessible
    STATUS      current
    DESCRIPTION ""
    INDEX { hardwareUnitId, hardwareResourceName, IMPLIED hardwareFeatureName }
        ::= { hardwareFeatureTable 1 }

HardwareFeatureEntry ::=
    SEQUENCE {
        hardwareFeatureName String,
        hardwareFeatureUsed ConfdString,
        hardwareFeatureHigh-watermark ConfdString,
        hardwareFeatureHigh-watermark-time DateAndTime,
        hardwareFeatureEstimatedFree ConfdString,
        hardwareFeatureErrorCount ConfdString
    }

-- tagpath /hardware/units/unit-entry/resources/resource-entry/feature/feature-entry/name
hardwareFeatureName OBJECT-TYPE
    SYNTAX      String
    MAX-ACCESS  not-accessible
    STATUS      current
    DESCRIPTION ""
    ::= { hardwareFeatureEntry 1 }

-- tagpath /hardware/units/unit-entry/resources/resource-entry/feature/feature-entry/objects-allocated
hardwareFeatureUsed OBJECT-TYPE
    SYNTAX      ConfdString
    MAX-ACCESS  read-only
    STATUS      current
    DESCRIPTION ""
    ::= { hardwareFeatureEntry 2 }

-- tagpath /hardware/units/unit-entry/resources/resource-entry/feature/feature-entry/high-watermark
hardwareFeatureHigh-watermark OBJECT-TYPE
    SYNTAX      ConfdString
    MAX-ACCESS  read-only
    STATUS      current
    DESCRIPTION ""
    ::= { hardwareFeatureEntry 3 }

-- tagpath /hardware/units/unit-entry/resources/resource-entry/feature/feature-entry/high-watermark-time
hardwareFeatureHigh-watermark-time OBJECT-TYPE
    SYNTAX      DateAndTime
    MAX-ACCESS  read-only
    STATUS      current
    DESCRIPTION ""
    ::= { hardwareFeatureEntry 4 }

-- tagpath /hardware/units/unit-entry/resources/resource-entry/feature/feature-entry/estimated-free
hardwareFeatureEstimatedFree OBJECT-TYPE
    SYNTAX      ConfdString
    MAX-ACCESS  read-only
    STATUS      current
    DESCRIPTION ""
    ::= { hardwareFeatureEntry 5 }

-- tagpath /hardware/units/unit-entry/resources/resource-entry/feature/feature-entry/errors
hardwareFeatureErrorCount OBJECT-TYPE
    SYNTAX      ConfdString
    MAX-ACCESS  read-only
    STATUS      current
    DESCRIPTION ""
    ::= { hardwareFeatureEntry 6 }

-- tagpath /runtime-instances/runtime-instance/hardware/units/unit-entry
hardwareUnitsUnit-entryTable OBJECT-TYPE
    SYNTAX      SEQUENCE OF HardwareUnitsUnit-entryEntry
    MAX-ACCESS  not-accessible
    STATUS      current
    DESCRIPTION ""
    ::= { aRRCUS-HARDWARE-UTILIZATION-MIB 4 }

-- tagpath /runtime-instances/runtime-instance/hardware/units/unit-entry
hardwareUnitsUnit-entryEntry OBJECT-TYPE
    SYNTAX      HardwareUnitsUnit-entryEntry
    MAX-ACCESS  not-accessible
    STATUS      current
    DESCRIPTION ""
    INDEX { runtime-instanceInstance-name, hardwareUnitsUnit-entryUnit-id }
        ::= { hardwareUnitsUnit-entryTable 1 }

HardwareUnitsUnit-entryEntry ::=
    SEQUENCE {
        hardwareUnitsUnit-entryUnit-id Unsigned32,
        hardwareUnitsUnit-entryUnit-descr String
    }

-- tagpath /runtime-instances/runtime-instance/hardware/units/unit-entry/unit-id
hardwareUnitsUnit-entryUnit-id OBJECT-TYPE
    SYNTAX      Unsigned32
    MAX-ACCESS  not-accessible
    STATUS      current
    DESCRIPTION ""
    ::= { hardwareUnitsUnit-entryEntry 1 }

-- tagpath /runtime-instances/runtime-instance/hardware/units/unit-entry/unit-descr
hardwareUnitsUnit-entryUnit-descr OBJECT-TYPE
    SYNTAX      String
    MAX-ACCESS  read-only
    STATUS      current
    DESCRIPTION ""
    ::= { hardwareUnitsUnit-entryEntry 2 }

-- tagpath /runtime-instances/runtime-instance/hardware/units/unit-entry/resources/resource-entry
hardwareUnitsUnit-entryResourcesResource-entryTable OBJECT-TYPE
    SYNTAX      SEQUENCE OF HardwareUnitsUnit-entryResourcesResource-entryEntry
    MAX-ACCESS  not-accessible
    STATUS      current
    DESCRIPTION ""
    ::= { aRRCUS-HARDWARE-UTILIZATION-MIB 5 }

-- tagpath /runtime-instances/runtime-instance/hardware/units/unit-entry/resources/resource-entry
hardwareUnitsUnit-entryResourcesResource-entryEntry OBJECT-TYPE
    SYNTAX      HardwareUnitsUnit-entryResourcesResource-entryEntry
    MAX-ACCESS  not-accessible
    STATUS      current
    DESCRIPTION ""
    INDEX { runtime-instanceInstance-name, hardwareUnitsUnit-entryUnit-id, IMPLIED hardwareUnitsUnit-entryResourcesResource-entryName }
        ::= { hardwareUnitsUnit-entryResourcesResource-entryTable 1 }

HardwareUnitsUnit-entryResourcesResource-entryEntry ::=
    SEQUENCE {
        hardwareUnitsUnit-entryResourcesResource-entryName String,
        hardwareUnitsUnit-entryResourcesResource-entryRaw-used ConfdString,
        hardwareUnitsUnit-entryResourcesResource-entryRaw-free ConfdString
    }

-- tagpath /runtime-instances/runtime-instance/hardware/units/unit-entry/resources/resource-entry/name
hardwareUnitsUnit-entryResourcesResource-entryName OBJECT-TYPE
    SYNTAX      String
    MAX-ACCESS  not-accessible
    STATUS      current
    DESCRIPTION ""
    ::= { hardwareUnitsUnit-entryResourcesResource-entryEntry 1 }

-- tagpath /runtime-instances/runtime-instance/hardware/units/unit-entry/resources/resource-entry/raw-used
hardwareUnitsUnit-entryResourcesResource-entryRaw-used OBJECT-TYPE
    SYNTAX      ConfdString
    MAX-ACCESS  read-only
    STATUS      current
    DESCRIPTION ""
    ::= { hardwareUnitsUnit-entryResourcesResource-entryEntry 2 }

-- tagpath /runtime-instances/runtime-instance/hardware/units/unit-entry/resources/resource-entry/raw-free
hardwareUnitsUnit-entryResourcesResource-entryRaw-free OBJECT-TYPE
    SYNTAX      ConfdString
    MAX-ACCESS  read-only
    STATUS      current
    DESCRIPTION ""
    ::= { hardwareUnitsUnit-entryResourcesResource-entryEntry 3 }

-- tagpath /runtime-instances/runtime-instance/hardware/units/unit-entry/resources/resource-entry/feature/feature-entry
hardwareUnitsUnit-entryResourcesResource-entryFeatureFeature-entryTable OBJECT-TYPE
    SYNTAX      SEQUENCE OF HardwareUnitsUnit-entryResourcesResource-entryFeatureFeature-entryEntry
    MAX-ACCESS  not-accessible
    STATUS      current
    DESCRIPTION ""
    ::= { aRRCUS-HARDWARE-UTILIZATION-MIB 6 }

-- tagpath /runtime-instances/runtime-instance/hardware/units/unit-entry/resources/resource-entry/feature/feature-entry
hardwareUnitsUnit-entryResourcesResource-entryFeatureFeature-entryEntry OBJECT-TYPE
    SYNTAX      HardwareUnitsUnit-entryResourcesResource-entryFeatureFeature-entryEntry
    MAX-ACCESS  not-accessible
    STATUS      current
    DESCRIPTION ""
    INDEX { runtime-instanceInstance-name, hardwareUnitsUnit-entryUnit-id, hardwareUnitsUnit-entryResourcesResource-entryName, IMPLIED hardwareUnitsUnit-entryResourcesResource-entryFeatureFeature-entryName }
        ::= { hardwareUnitsUnit-entryResourcesResource-entryFeatureFeature-entryTable 1 }

HardwareUnitsUnit-entryResourcesResource-entryFeatureFeature-entryEntry ::=
    SEQUENCE {
        hardwareUnitsUnit-entryResourcesResource-entryFeatureFeature-entryName String,
        hardwareUnitsUnit-entryResourcesResource-entryFeatureFeature-entryObjects-allocated ConfdString,
        hardwareUnitsUnit-entryResourcesResource-entryFeatureFeature-entryHigh-watermark ConfdString,
        hardwareUnitsUnit-entryResourcesResource-entryFeatureFeature-entryHigh-watermark-time DateAndTime,
        hardwareUnitsUnit-entryResourcesResource-entryFeatureFeature-entryEstimated-free ConfdString,
        hardwareUnitsUnit-entryResourcesResource-entryFeatureFeature-entryErrors ConfdString
    }

-- tagpath /runtime-instances/runtime-instance/hardware/units/unit-entry/resources/resource-entry/feature/feature-entry/name
hardwareUnitsUnit-entryResourcesResource-entryFeatureFeature-entryName OBJECT-TYPE
    SYNTAX      String
    MAX-ACCESS  not-accessible
    STATUS      current
    DESCRIPTION ""
    ::= { hardwareUnitsUnit-entryResourcesResource-entryFeatureFeature-entryEntry 1 }

-- tagpath /runtime-instances/runtime-instance/hardware/units/unit-entry/resources/resource-entry/feature/feature-entry/objects-allocated
hardwareUnitsUnit-entryResourcesResource-entryFeatureFeature-entryObjects-allocated OBJECT-TYPE
    SYNTAX      ConfdString
    MAX-ACCESS  read-only
    STATUS      current
    DESCRIPTION ""
    ::= { hardwareUnitsUnit-entryResourcesResource-entryFeatureFeature-entryEntry 2 }

-- tagpath /runtime-instances/runtime-instance/hardware/units/unit-entry/resources/resource-entry/feature/feature-entry/high-watermark
hardwareUnitsUnit-entryResourcesResource-entryFeatureFeature-entryHigh-watermark OBJECT-TYPE
    SYNTAX      ConfdString
    MAX-ACCESS  read-only
    STATUS      current
    DESCRIPTION ""
    ::= { hardwareUnitsUnit-entryResourcesResource-entryFeatureFeature-entryEntry 3 }

-- tagpath /runtime-instances/runtime-instance/hardware/units/unit-entry/resources/resource-entry/feature/feature-entry/high-watermark-time
hardwareUnitsUnit-entryResourcesResource-entryFeatureFeature-entryHigh-watermark-time OBJECT-TYPE
    SYNTAX      DateAndTime
    MAX-ACCESS  read-only
    STATUS      current
    DESCRIPTION ""
    ::= { hardwareUnitsUnit-entryResourcesResource-entryFeatureFeature-entryEntry 4 }

-- tagpath /runtime-instances/runtime-instance/hardware/units/unit-entry/resources/resource-entry/feature/feature-entry/estimated-free
hardwareUnitsUnit-entryResourcesResource-entryFeatureFeature-entryEstimated-free OBJECT-TYPE
    SYNTAX      ConfdString
    MAX-ACCESS  read-only
    STATUS      current
    DESCRIPTION ""
    ::= { hardwareUnitsUnit-entryResourcesResource-entryFeatureFeature-entryEntry 5 }

-- tagpath /runtime-instances/runtime-instance/hardware/units/unit-entry/resources/resource-entry/feature/feature-entry/errors
hardwareUnitsUnit-entryResourcesResource-entryFeatureFeature-entryErrors OBJECT-TYPE
    SYNTAX      ConfdString
    MAX-ACCESS  read-only
    STATUS      current
    DESCRIPTION ""
    ::= { hardwareUnitsUnit-entryResourcesResource-entryFeatureFeature-entryEntry 6 }

-- tagpath /runtime-instances/runtime-instance/hardware/units/unit-entry/indexers/indexer-entry
hardwareUnitsUnit-entryIndexersIndexer-entryTable OBJECT-TYPE
    SYNTAX      SEQUENCE OF HardwareUnitsUnit-entryIndexersIndexer-entryEntry
    MAX-ACCESS  not-accessible
    STATUS      current
    DESCRIPTION ""
    ::= { aRRCUS-HARDWARE-UTILIZATION-MIB 7 }

-- tagpath /runtime-instances/runtime-instance/hardware/units/unit-entry/indexers/indexer-entry
hardwareUnitsUnit-entryIndexersIndexer-entryEntry OBJECT-TYPE
    SYNTAX      HardwareUnitsUnit-entryIndexersIndexer-entryEntry
    MAX-ACCESS  not-accessible
    STATUS      current
    DESCRIPTION ""
    INDEX { runtime-instanceInstance-name, hardwareUnitsUnit-entryUnit-id, IMPLIED hardwareUnitsUnit-entryIndexersIndexer-entryName }
        ::= { hardwareUnitsUnit-entryIndexersIndexer-entryTable 1 }

HardwareUnitsUnit-entryIndexersIndexer-entryEntry ::=
    SEQUENCE {
        hardwareUnitsUnit-entryIndexersIndexer-entryName String,
        hardwareUnitsUnit-entryIndexersIndexer-entryType String,
        hardwareUnitsUnit-entryIndexersIndexer-entryStart-index Unsigned32,
        hardwareUnitsUnit-entryIndexersIndexer-entryCount Unsigned32,
        hardwareUnitsUnit-entryIndexersIndexer-entryUsed Unsigned32,
        hardwareUnitsUnit-entryIndexersIndexer-entryHold-count Unsigned32
    }

-- tagpath /runtime-instances/runtime-instance/hardware/units/unit-entry/indexers/indexer-entry/name
hardwareUnitsUnit-entryIndexersIndexer-entryName OBJECT-TYPE
    SYNTAX      String
    MAX-ACCESS  not-accessible
    STATUS      current
    DESCRIPTION ""
    ::= { hardwareUnitsUnit-entryIndexersIndexer-entryEntry 1 }

-- tagpath /runtime-instances/runtime-instance/hardware/units/unit-entry/indexers/indexer-entry/type
hardwareUnitsUnit-entryIndexersIndexer-entryType OBJECT-TYPE
    SYNTAX      String
    MAX-ACCESS  read-only
    STATUS      current
    DESCRIPTION ""
    ::= { hardwareUnitsUnit-entryIndexersIndexer-entryEntry 2 }

-- tagpath /runtime-instances/runtime-instance/hardware/units/unit-entry/indexers/indexer-entry/start-index
hardwareUnitsUnit-entryIndexersIndexer-entryStart-index OBJECT-TYPE
    SYNTAX      Unsigned32
    MAX-ACCESS  read-only
    STATUS      current
    DESCRIPTION ""
    ::= { hardwareUnitsUnit-entryIndexersIndexer-entryEntry 3 }

-- tagpath /runtime-instances/runtime-instance/hardware/units/unit-entry/indexers/indexer-entry/count
hardwareUnitsUnit-entryIndexersIndexer-entryCount OBJECT-TYPE
    SYNTAX      Unsigned32
    MAX-ACCESS  read-only
    STATUS      current
    DESCRIPTION ""
    ::= { hardwareUnitsUnit-entryIndexersIndexer-entryEntry 4 }

-- tagpath /runtime-instances/runtime-instance/hardware/units/unit-entry/indexers/indexer-entry/used
hardwareUnitsUnit-entryIndexersIndexer-entryUsed OBJECT-TYPE
    SYNTAX      Unsigned32
    MAX-ACCESS  read-only
    STATUS      current
    DESCRIPTION ""
    ::= { hardwareUnitsUnit-entryIndexersIndexer-entryEntry 5 }

-- tagpath /runtime-instances/runtime-instance/hardware/units/unit-entry/indexers/indexer-entry/hold-count
hardwareUnitsUnit-entryIndexersIndexer-entryHold-count OBJECT-TYPE
    SYNTAX      Unsigned32
    MAX-ACCESS  read-only
    STATUS      current
    DESCRIPTION ""
    ::= { hardwareUnitsUnit-entryIndexersIndexer-entryEntry 6 }

END
