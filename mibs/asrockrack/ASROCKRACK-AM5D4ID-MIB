-- ASROCKRACK-AM5D4ID-MIB
-- Derived from the vendor MIB "1U2N2G-AM5_2T" published by the ASRock Rack BMC web UI.
-- Patched for SMI validity so net-snmp can parse it:
--   * module renamed (vendor module name starts with a digit, invalid SMI)
--   * underscores in identifiers replaced with hyphens
-- OIDs are unchanged from the vendor MIB.

ASROCKRACK-AM5D4ID-MIB DEFINITIONS ::= BEGIN

   IMPORTS
   MODULE-IDENTITY, OBJECT-TYPE, Integer32, NOTIFICATION-TYPE FROM SNMPv2-SMI
   DisplayString FROM SNMPv2-TC
   netSnmp FROM NET-SNMP-MIB
   RowStatus, StorageType FROM SNMPv2-TC
   InetAddressType, InetAddress FROM INET-ADDRESS-MIB
   enterprises FROM SNMPv2-SMI;

am5d4id MODULE-IDENTITY
   LAST-UPDATED "202502140810Z"
   ORGANIZATION "ASRock Rack Inc."
   CONTACT-INFO "email: tsd_rack@asrockrack.com"
   DESCRIPTION "Server SNMP MIB objects"
   REVISION "202502140810Z"
   DESCRIPTION "AM5D4ID-2T+/BCM 70.16.00"
   ::= { enterprises 49622 }

PlatformInfo OBJECT IDENTIFIER ::= { am5d4id 1 }
MBModelName OBJECT-TYPE
    SYNTAX DisplayString
    MAX-ACCESS read-only
    STATUS current
    DESCRIPTION "MB Model Name"
    ::= { PlatformInfo 1 }

SystemProduct OBJECT-TYPE
    SYNTAX DisplayString
    MAX-ACCESS read-only
    STATUS current
    DESCRIPTION "System Product"
    ::= { PlatformInfo 2 }

BMCVersion OBJECT-TYPE
    SYNTAX DisplayString
    MAX-ACCESS read-only
    STATUS current
    DESCRIPTION "BMC Version"
    ::= { PlatformInfo 3 }

BIOSVersion OBJECT-TYPE
    SYNTAX DisplayString
    MAX-ACCESS read-only
    STATUS current
    DESCRIPTION "BIOS Version"
    ::= { PlatformInfo 4 }

PSPVersion OBJECT-TYPE
    SYNTAX DisplayString
    MAX-ACCESS read-only
    STATUS current
    DESCRIPTION "PSP Version"
    ::= { PlatformInfo 5 }

BMCMAC1Addr OBJECT-TYPE
    SYNTAX DisplayString
    MAX-ACCESS read-only
    STATUS current
    DESCRIPTION "BMC MAC1 Address"
    ::= { PlatformInfo 6 }

BMCMAC2Addr OBJECT-TYPE
    SYNTAX DisplayString
    MAX-ACCESS read-only
    STATUS current
    DESCRIPTION "BMC MAC2 Address"
    ::= { PlatformInfo 7 }

ChassisPowerStatus OBJECT-TYPE
    SYNTAX Integer32{PowerOff(0), PowerOn(1), PowerCycle(2), HardReset(3), SoftOff(5)}
    MAX-ACCESS read-write
    STATUS current
    DESCRIPTION "Chassis Power Status"
    ::= { PlatformInfo 8 }

UIDLEDStatus OBJECT-TYPE
    SYNTAX Integer32{Off(0), TemporaryOn(1), On(2)}
    MAX-ACCESS read-write
    STATUS current
    DESCRIPTION "UID LED Status"
    ::= { PlatformInfo 9 }

SystemLEDStatus OBJECT-TYPE
    SYNTAX DisplayString
    MAX-ACCESS read-only
    STATUS current
    DESCRIPTION "System LED Status"
    ::= { PlatformInfo 10 }

Config OBJECT IDENTIFIER ::= { am5d4id 2 }
Hostname OBJECT-TYPE
    SYNTAX DisplayString
    MAX-ACCESS read-write
    STATUS current
    DESCRIPTION "BMC Host Name"
    ::= { Config 1 }

NetworkInfo OBJECT IDENTIFIER ::= { am5d4id 3 }
Interface-1 OBJECT-TYPE
    SYNTAX DisplayString
    MAX-ACCESS read-only
    STATUS current
    DESCRIPTION "Interface"
    ::= { NetworkInfo 1 }

NetName-1 OBJECT-TYPE
    SYNTAX DisplayString
    MAX-ACCESS read-only
    STATUS current
    DESCRIPTION "Name"
    ::= { Interface-1 1 }

Channel-1 OBJECT-TYPE
    SYNTAX DisplayString
    MAX-ACCESS read-only
    STATUS current
    DESCRIPTION "Channel number"
    ::= { Interface-1 2 }

ChannelEnabled-1 OBJECT-TYPE
    SYNTAX DisplayString
    MAX-ACCESS read-only
    STATUS current
    DESCRIPTION "Enabled"
    ::= { Interface-1 3 }

MACAddress-1 OBJECT-TYPE
    SYNTAX DisplayString
    MAX-ACCESS read-only
    STATUS current
    DESCRIPTION "MAC Address"
    ::= { Interface-1 4 }

IPV4-1 OBJECT IDENTIFIER ::= { Interface-1 5 }
IPV4Enabled-1 OBJECT-TYPE
    SYNTAX DisplayString
    MAX-ACCESS read-only
    STATUS current
    DESCRIPTION "Enabled"
    ::= { IPV4-1 1 }

IPV4DHCP-1 OBJECT-TYPE
    SYNTAX DisplayString
    MAX-ACCESS read-only
    STATUS current
    DESCRIPTION "DHCP"
    ::= { IPV4-1 2 }

IPV4Address-1 OBJECT-TYPE
    SYNTAX DisplayString
    MAX-ACCESS read-only
    STATUS current
    DESCRIPTION "Address"
    ::= { IPV4-1 3 }

Subnet-1 OBJECT-TYPE
    SYNTAX DisplayString
    MAX-ACCESS read-only
    STATUS current
    DESCRIPTION "Subnet"
    ::= { IPV4-1 4 }

IPV4Gateway-1 OBJECT-TYPE
    SYNTAX DisplayString
    MAX-ACCESS read-only
    STATUS current
    DESCRIPTION "Gatway"
    ::= { IPV4-1 5 }

IPV6-1 OBJECT IDENTIFIER ::= { Interface-1 6 }
IPV6Enabled-1 OBJECT-TYPE
    SYNTAX DisplayString
    MAX-ACCESS read-only
    STATUS current
    DESCRIPTION "Enabled"
    ::= { IPV6-1 1 }

IPV6DHCP-1 OBJECT-TYPE
    SYNTAX DisplayString
    MAX-ACCESS read-only
    STATUS current
    DESCRIPTION "DHCP"
    ::= { IPV6-1 2 }

NetIndex-1 OBJECT-TYPE
    SYNTAX DisplayString
    MAX-ACCESS read-only
    STATUS current
    DESCRIPTION "Subnet"
    ::= { IPV6-1 3 }

IPV6Address-1 OBJECT-TYPE
    SYNTAX DisplayString
    MAX-ACCESS read-only
    STATUS current
    DESCRIPTION "Address"
    ::= { IPV6-1 4 }

PrefixLength-1 OBJECT-TYPE
    SYNTAX DisplayString
    MAX-ACCESS read-only
    STATUS current
    DESCRIPTION "Subnet"
    ::= { IPV6-1 5 }

IPV6Gateway-1 OBJECT-TYPE
    SYNTAX DisplayString
    MAX-ACCESS read-only
    STATUS current
    DESCRIPTION "Gatway"
    ::= { IPV6-1 6 }

VLAN-1 OBJECT IDENTIFIER ::= { Interface-1 7 }
VLANEnabled-1 OBJECT-TYPE
    SYNTAX DisplayString
    MAX-ACCESS read-only
    STATUS current
    DESCRIPTION "Enabled"
    ::= { VLAN-1 1 }

ID-1 OBJECT-TYPE
    SYNTAX DisplayString
    MAX-ACCESS read-only
    STATUS current
    DESCRIPTION "ID"
    ::= { VLAN-1 2 }

Priority-1 OBJECT-TYPE
    SYNTAX DisplayString
    MAX-ACCESS read-only
    STATUS current
    DESCRIPTION "Priority"
    ::= { VLAN-1 3 }

Interface-2 OBJECT-TYPE
    SYNTAX DisplayString
    MAX-ACCESS read-only
    STATUS current
    DESCRIPTION "Interface"
    ::= { NetworkInfo 2 }

NetName-2 OBJECT-TYPE
    SYNTAX DisplayString
    MAX-ACCESS read-only
    STATUS current
    DESCRIPTION "Name"
    ::= { Interface-2 1 }

Channel-2 OBJECT-TYPE
    SYNTAX DisplayString
    MAX-ACCESS read-only
    STATUS current
    DESCRIPTION "Channel number"
    ::= { Interface-2 2 }

ChannelEnabled-2 OBJECT-TYPE
    SYNTAX DisplayString
    MAX-ACCESS read-only
    STATUS current
    DESCRIPTION "Enabled"
    ::= { Interface-2 3 }

MACAddress-2 OBJECT-TYPE
    SYNTAX DisplayString
    MAX-ACCESS read-only
    STATUS current
    DESCRIPTION "MAC Address"
    ::= { Interface-2 4 }

IPV4-2 OBJECT IDENTIFIER ::= { Interface-2 5 }
IPV4Enabled-2 OBJECT-TYPE
    SYNTAX DisplayString
    MAX-ACCESS read-only
    STATUS current
    DESCRIPTION "Enabled"
    ::= { IPV4-2 1 }

IPV4DHCP-2 OBJECT-TYPE
    SYNTAX DisplayString
    MAX-ACCESS read-only
    STATUS current
    DESCRIPTION "DHCP"
    ::= { IPV4-2 2 }

IPV4Address-2 OBJECT-TYPE
    SYNTAX DisplayString
    MAX-ACCESS read-only
    STATUS current
    DESCRIPTION "Address"
    ::= { IPV4-2 3 }

Subnet-2 OBJECT-TYPE
    SYNTAX DisplayString
    MAX-ACCESS read-only
    STATUS current
    DESCRIPTION "Subnet"
    ::= { IPV4-2 4 }

IPV4Gateway-2 OBJECT-TYPE
    SYNTAX DisplayString
    MAX-ACCESS read-only
    STATUS current
    DESCRIPTION "Gatway"
    ::= { IPV4-2 5 }

IPV6-2 OBJECT IDENTIFIER ::= { Interface-2 6 }
IPV6Enabled-2 OBJECT-TYPE
    SYNTAX DisplayString
    MAX-ACCESS read-only
    STATUS current
    DESCRIPTION "Enabled"
    ::= { IPV6-2 1 }

IPV6DHCP-2 OBJECT-TYPE
    SYNTAX DisplayString
    MAX-ACCESS read-only
    STATUS current
    DESCRIPTION "DHCP"
    ::= { IPV6-2 2 }

NetIndex-2 OBJECT-TYPE
    SYNTAX DisplayString
    MAX-ACCESS read-only
    STATUS current
    DESCRIPTION "Subnet"
    ::= { IPV6-2 3 }

IPV6Address-2 OBJECT-TYPE
    SYNTAX DisplayString
    MAX-ACCESS read-only
    STATUS current
    DESCRIPTION "Address"
    ::= { IPV6-2 4 }

PrefixLength-2 OBJECT-TYPE
    SYNTAX DisplayString
    MAX-ACCESS read-only
    STATUS current
    DESCRIPTION "Subnet"
    ::= { IPV6-2 5 }

IPV6Gateway-2 OBJECT-TYPE
    SYNTAX DisplayString
    MAX-ACCESS read-only
    STATUS current
    DESCRIPTION "Gatway"
    ::= { IPV6-2 6 }

VLAN-2 OBJECT IDENTIFIER ::= { Interface-2 7 }
VLANEnabled-2 OBJECT-TYPE
    SYNTAX DisplayString
    MAX-ACCESS read-only
    STATUS current
    DESCRIPTION "Enabled"
    ::= { VLAN-2 1 }

ID-2 OBJECT-TYPE
    SYNTAX DisplayString
    MAX-ACCESS read-only
    STATUS current
    DESCRIPTION "ID"
    ::= { VLAN-2 2 }

Priority-2 OBJECT-TYPE
    SYNTAX DisplayString
    MAX-ACCESS read-only
    STATUS current
    DESCRIPTION "Priority"
    ::= { VLAN-2 3 }

FRUInfo OBJECT IDENTIFIER ::= { am5d4id 4 }
FRUID OBJECT-TYPE
    SYNTAX DisplayString
    MAX-ACCESS read-only
    STATUS current
    DESCRIPTION "FRU ID"
    ::= { FRUInfo 1 }

FRUName OBJECT-TYPE
    SYNTAX DisplayString
    MAX-ACCESS read-only
    STATUS current
    DESCRIPTION "FRU Name"
    ::= { FRUID 1 }

Chassis OBJECT IDENTIFIER ::= { FRUID 2 }
CAreaVersion OBJECT-TYPE
    SYNTAX DisplayString
    MAX-ACCESS read-only
    STATUS current
    DESCRIPTION "Area Version"
    ::= { Chassis 1 }

CLength OBJECT-TYPE
    SYNTAX DisplayString
    MAX-ACCESS read-only
    STATUS current
    DESCRIPTION "Length"
    ::= { Chassis 2 }

CType OBJECT-TYPE
    SYNTAX DisplayString
    MAX-ACCESS read-only
    STATUS current
    DESCRIPTION "Type"
    ::= { Chassis 3 }

CPartNumber OBJECT-TYPE
    SYNTAX DisplayString
    MAX-ACCESS read-only
    STATUS current
    DESCRIPTION "Part Number"
    ::= { Chassis 4 }

CSerialNumber OBJECT-TYPE
    SYNTAX DisplayString
    MAX-ACCESS read-only
    STATUS current
    DESCRIPTION "Serial Number"
    ::= { Chassis 5 }

CManufacturer OBJECT-TYPE
    SYNTAX DisplayString
    MAX-ACCESS read-only
    STATUS current
    DESCRIPTION "Manufacturer"
    ::= { Chassis 6 }

CVersion OBJECT-TYPE
    SYNTAX DisplayString
    MAX-ACCESS read-only
    STATUS current
    DESCRIPTION "Version"
    ::= { Chassis 7 }

CAssetTag OBJECT-TYPE
    SYNTAX DisplayString
    MAX-ACCESS read-only
    STATUS current
    DESCRIPTION "Asset Tag"
    ::= { Chassis 8 }

CSKUNumber OBJECT-TYPE
    SYNTAX DisplayString
    MAX-ACCESS read-only
    STATUS current
    DESCRIPTION "SKU Number"
    ::= { Chassis 9 }

CModel OBJECT-TYPE
    SYNTAX DisplayString
    MAX-ACCESS read-only
    STATUS current
    DESCRIPTION "Model"
    ::= { Chassis 10 }

Board OBJECT IDENTIFIER ::= { FRUID 3 }
BAreaVersion OBJECT-TYPE
    SYNTAX DisplayString
    MAX-ACCESS read-only
    STATUS current
    DESCRIPTION "Area Version"
    ::= { Board 1 }

BLength OBJECT-TYPE
    SYNTAX DisplayString
    MAX-ACCESS read-only
    STATUS current
    DESCRIPTION "Length"
    ::= { Board 2 }

BLanguage OBJECT-TYPE
    SYNTAX DisplayString
    MAX-ACCESS read-only
    STATUS current
    DESCRIPTION "Language"
    ::= { Board 3 }

BManufacturerDate OBJECT-TYPE
    SYNTAX DisplayString
    MAX-ACCESS read-only
    STATUS current
    DESCRIPTION "Manufacturer Date"
    ::= { Board 4 }

BManufacturer OBJECT-TYPE
    SYNTAX DisplayString
    MAX-ACCESS read-only
    STATUS current
    DESCRIPTION "Manufacturer"
    ::= { Board 5 }

BProductName OBJECT-TYPE
    SYNTAX DisplayString
    MAX-ACCESS read-only
    STATUS current
    DESCRIPTION "Product Name"
    ::= { Board 6 }

BSerialNumber OBJECT-TYPE
    SYNTAX DisplayString
    MAX-ACCESS read-only
    STATUS current
    DESCRIPTION "Serial Number"
    ::= { Board 7 }

BPartNumber OBJECT-TYPE
    SYNTAX DisplayString
    MAX-ACCESS read-only
    STATUS current
    DESCRIPTION "Part Number"
    ::= { Board 8 }

BFileID OBJECT-TYPE
    SYNTAX DisplayString
    MAX-ACCESS read-only
    STATUS current
    DESCRIPTION "File ID"
    ::= { Board 9 }

BVersion OBJECT-TYPE
    SYNTAX DisplayString
    MAX-ACCESS read-only
    STATUS current
    DESCRIPTION "Version"
    ::= { Board 10 }

BAssetTag OBJECT-TYPE
    SYNTAX DisplayString
    MAX-ACCESS read-only
    STATUS current
    DESCRIPTION "Asset Tag"
    ::= { Board 11 }

Product OBJECT IDENTIFIER ::= { FRUID 4 }
PAreaVersion OBJECT-TYPE
    SYNTAX DisplayString
    MAX-ACCESS read-only
    STATUS current
    DESCRIPTION "Area Version"
    ::= { Product 1 }

PLength OBJECT-TYPE
    SYNTAX DisplayString
    MAX-ACCESS read-only
    STATUS current
    DESCRIPTION "Length"
    ::= { Product 2 }

PLanguage OBJECT-TYPE
    SYNTAX DisplayString
    MAX-ACCESS read-only
    STATUS current
    DESCRIPTION "Language"
    ::= { Product 3 }

PManufacturer OBJECT-TYPE
    SYNTAX DisplayString
    MAX-ACCESS read-only
    STATUS current
    DESCRIPTION "Manufacturer"
    ::= { Product 4 }

PProductName OBJECT-TYPE
    SYNTAX DisplayString
    MAX-ACCESS read-only
    STATUS current
    DESCRIPTION "Product Name"
    ::= { Product 5 }

PPartNumber OBJECT-TYPE
    SYNTAX DisplayString
    MAX-ACCESS read-only
    STATUS current
    DESCRIPTION "Part Number"
    ::= { Product 6 }

PVersion OBJECT-TYPE
    SYNTAX DisplayString
    MAX-ACCESS read-only
    STATUS current
    DESCRIPTION "Version"
    ::= { Product 7 }

PSerialNumber OBJECT-TYPE
    SYNTAX DisplayString
    MAX-ACCESS read-only
    STATUS current
    DESCRIPTION "Serial Number"
    ::= { Product 8 }

PAssetTag OBJECT-TYPE
    SYNTAX DisplayString
    MAX-ACCESS read-only
    STATUS current
    DESCRIPTION "Asset Tag"
    ::= { Product 9 }

PFileID OBJECT-TYPE
    SYNTAX DisplayString
    MAX-ACCESS read-only
    STATUS current
    DESCRIPTION "File ID"
    ::= { Product 10 }

PUUID OBJECT-TYPE
    SYNTAX DisplayString
    MAX-ACCESS read-only
    STATUS current
    DESCRIPTION "UUID"
    ::= { Product 11 }

PSKUNumber OBJECT-TYPE
    SYNTAX DisplayString
    MAX-ACCESS read-only
    STATUS current
    DESCRIPTION "SKU Number"
    ::= { Product 12 }

PFamily OBJECT-TYPE
    SYNTAX DisplayString
    MAX-ACCESS read-only
    STATUS current
    DESCRIPTION "Family"
    ::= { Product 13 }

FanData OBJECT IDENTIFIER ::= { am5d4id 5 }
PwmValue OBJECT-TYPE
    SYNTAX DisplayString
    MAX-ACCESS read-only
    STATUS current
    DESCRIPTION "PWM value"
    ::= { FanData 1 }

FanFail OBJECT-TYPE
    SYNTAX DisplayString
    MAX-ACCESS read-only
    STATUS current
    DESCRIPTION "Fan fail flag"
    ::= { FanData 2 }

FanCtrlData OBJECT IDENTIFIER ::= { FanData 3 }
ManualModeDuty OBJECT-TYPE
    SYNTAX DisplayString
    MAX-ACCESS read-only
    STATUS current
    DESCRIPTION "Manual Mode Duty"
    ::= { FanCtrlData 1 }

FanControlMode OBJECT-TYPE
    SYNTAX DisplayString
    MAX-ACCESS read-only
    STATUS current
    DESCRIPTION "Fan Control Mode"
    ::= { FanCtrlData 2 }

MinimumDuty OBJECT-TYPE
    SYNTAX Integer32
    MAX-ACCESS read-only
    STATUS current
    DESCRIPTION "Minimum Duty"
    ::= { FanCtrlData 3 }

MaximumDuty OBJECT-TYPE
    SYNTAX Integer32
    MAX-ACCESS read-only
    STATUS current
    DESCRIPTION "Maximum Duty"
    ::= { FanCtrlData 4 }

MiscCtrlFlag OBJECT-TYPE
    SYNTAX DisplayString
    MAX-ACCESS read-only
    STATUS current
    DESCRIPTION "Misc Ctrl Flag"
    ::= { FanCtrlData 5 }

FwUpdateFanCtrl OBJECT-TYPE
    SYNTAX DisplayString
    MAX-ACCESS read-only
    STATUS current
    DESCRIPTION "FW Update Fan Ctrl"
    ::= { FanCtrlData 6 }

OpenLoop OBJECT-TYPE
    SYNTAX DisplayString
    MAX-ACCESS read-only
    STATUS current
    DESCRIPTION "Open Loop Fan Data"
    ::= { FanCtrlData 7 }

OpenTable-1 OBJECT-TYPE
    SYNTAX DisplayString
    MAX-ACCESS read-only
    STATUS current
    DESCRIPTION "Open Loop Fan Table"
    ::= { OpenLoop 1 }

OpenFanTempTable-1 OBJECT-TYPE
    SYNTAX DisplayString
    MAX-ACCESS read-only
    STATUS current
    DESCRIPTION "Fan Temp Table"
    ::= { OpenTable-1 1 }

OpenFanDutyTable-1 OBJECT-TYPE
    SYNTAX DisplayString
    MAX-ACCESS read-only
    STATUS current
    DESCRIPTION "Fan Duty Table"
    ::= { OpenTable-1 2 }

OpenHysteresis-1 OBJECT-TYPE
    SYNTAX Integer32
    MAX-ACCESS read-only
    STATUS current
    DESCRIPTION "Hysteresis"
    ::= { OpenTable-1 3 }

OpenRampDownDuty-1 OBJECT-TYPE
    SYNTAX Integer32
    MAX-ACCESS read-only
    STATUS current
    DESCRIPTION "Ramp Down Duty"
    ::= { OpenTable-1 4 }

OpenRampDownInterval-1 OBJECT-TYPE
    SYNTAX Integer32
    MAX-ACCESS read-only
    STATUS current
    DESCRIPTION "Ramp Down Interval"
    ::= { OpenTable-1 5 }

OpenRampUpDuty-1 OBJECT-TYPE
    SYNTAX Integer32
    MAX-ACCESS read-only
    STATUS current
    DESCRIPTION "Ramp Up Duty"
    ::= { OpenTable-1 6 }

OpenRampUpInterval-1 OBJECT-TYPE
    SYNTAX Integer32
    MAX-ACCESS read-only
    STATUS current
    DESCRIPTION "Ramp Up Interval"
    ::= { OpenTable-1 7 }

OpenTable-2 OBJECT-TYPE
    SYNTAX DisplayString
    MAX-ACCESS read-only
    STATUS current
    DESCRIPTION "Open Loop Fan Table"
    ::= { OpenLoop 2 }

OpenFanTempTable-2 OBJECT-TYPE
    SYNTAX DisplayString
    MAX-ACCESS read-only
    STATUS current
    DESCRIPTION "Fan Temp Table"
    ::= { OpenTable-2 1 }

OpenFanDutyTable-2 OBJECT-TYPE
    SYNTAX DisplayString
    MAX-ACCESS read-only
    STATUS current
    DESCRIPTION "Fan Duty Table"
    ::= { OpenTable-2 2 }

OpenHysteresis-2 OBJECT-TYPE
    SYNTAX Integer32
    MAX-ACCESS read-only
    STATUS current
    DESCRIPTION "Hysteresis"
    ::= { OpenTable-2 3 }

OpenRampDownDuty-2 OBJECT-TYPE
    SYNTAX Integer32
    MAX-ACCESS read-only
    STATUS current
    DESCRIPTION "Ramp Down Duty"
    ::= { OpenTable-2 4 }

OpenRampDownInterval-2 OBJECT-TYPE
    SYNTAX Integer32
    MAX-ACCESS read-only
    STATUS current
    DESCRIPTION "Ramp Down Interval"
    ::= { OpenTable-2 5 }

OpenRampUpDuty-2 OBJECT-TYPE
    SYNTAX Integer32
    MAX-ACCESS read-only
    STATUS current
    DESCRIPTION "Ramp Up Duty"
    ::= { OpenTable-2 6 }

OpenRampUpInterval-2 OBJECT-TYPE
    SYNTAX Integer32
    MAX-ACCESS read-only
    STATUS current
    DESCRIPTION "Ramp Up Interval"
    ::= { OpenTable-2 7 }

OpenTable-3 OBJECT-TYPE
    SYNTAX DisplayString
    MAX-ACCESS read-only
    STATUS current
    DESCRIPTION "Open Loop Fan Table"
    ::= { OpenLoop 3 }

OpenFanTempTable-3 OBJECT-TYPE
    SYNTAX DisplayString
    MAX-ACCESS read-only
    STATUS current
    DESCRIPTION "Fan Temp Table"
    ::= { OpenTable-3 1 }

OpenFanDutyTable-3 OBJECT-TYPE
    SYNTAX DisplayString
    MAX-ACCESS read-only
    STATUS current
    DESCRIPTION "Fan Duty Table"
    ::= { OpenTable-3 2 }

OpenHysteresis-3 OBJECT-TYPE
    SYNTAX Integer32
    MAX-ACCESS read-only
    STATUS current
    DESCRIPTION "Hysteresis"
    ::= { OpenTable-3 3 }

OpenRampDownDuty-3 OBJECT-TYPE
    SYNTAX Integer32
    MAX-ACCESS read-only
    STATUS current
    DESCRIPTION "Ramp Down Duty"
    ::= { OpenTable-3 4 }

OpenRampDownInterval-3 OBJECT-TYPE
    SYNTAX Integer32
    MAX-ACCESS read-only
    STATUS current
    DESCRIPTION "Ramp Down Interval"
    ::= { OpenTable-3 5 }

OpenRampUpDuty-3 OBJECT-TYPE
    SYNTAX Integer32
    MAX-ACCESS read-only
    STATUS current
    DESCRIPTION "Ramp Up Duty"
    ::= { OpenTable-3 6 }

OpenRampUpInterval-3 OBJECT-TYPE
    SYNTAX Integer32
    MAX-ACCESS read-only
    STATUS current
    DESCRIPTION "Ramp Up Interval"
    ::= { OpenTable-3 7 }

OpenTable-4 OBJECT-TYPE
    SYNTAX DisplayString
    MAX-ACCESS read-only
    STATUS current
    DESCRIPTION "Open Loop Fan Table"
    ::= { OpenLoop 4 }

OpenFanTempTable-4 OBJECT-TYPE
    SYNTAX DisplayString
    MAX-ACCESS read-only
    STATUS current
    DESCRIPTION "Fan Temp Table"
    ::= { OpenTable-4 1 }

OpenFanDutyTable-4 OBJECT-TYPE
    SYNTAX DisplayString
    MAX-ACCESS read-only
    STATUS current
    DESCRIPTION "Fan Duty Table"
    ::= { OpenTable-4 2 }

OpenHysteresis-4 OBJECT-TYPE
    SYNTAX Integer32
    MAX-ACCESS read-only
    STATUS current
    DESCRIPTION "Hysteresis"
    ::= { OpenTable-4 3 }

OpenRampDownDuty-4 OBJECT-TYPE
    SYNTAX Integer32
    MAX-ACCESS read-only
    STATUS current
    DESCRIPTION "Ramp Down Duty"
    ::= { OpenTable-4 4 }

OpenRampDownInterval-4 OBJECT-TYPE
    SYNTAX Integer32
    MAX-ACCESS read-only
    STATUS current
    DESCRIPTION "Ramp Down Interval"
    ::= { OpenTable-4 5 }

OpenRampUpDuty-4 OBJECT-TYPE
    SYNTAX Integer32
    MAX-ACCESS read-only
    STATUS current
    DESCRIPTION "Ramp Up Duty"
    ::= { OpenTable-4 6 }

OpenRampUpInterval-4 OBJECT-TYPE
    SYNTAX Integer32
    MAX-ACCESS read-only
    STATUS current
    DESCRIPTION "Ramp Up Interval"
    ::= { OpenTable-4 7 }

OpenTable-5 OBJECT-TYPE
    SYNTAX DisplayString
    MAX-ACCESS read-only
    STATUS current
    DESCRIPTION "Open Loop Fan Table"
    ::= { OpenLoop 5 }

OpenFanTempTable-5 OBJECT-TYPE
    SYNTAX DisplayString
    MAX-ACCESS read-only
    STATUS current
    DESCRIPTION "Fan Temp Table"
    ::= { OpenTable-5 1 }

OpenFanDutyTable-5 OBJECT-TYPE
    SYNTAX DisplayString
    MAX-ACCESS read-only
    STATUS current
    DESCRIPTION "Fan Duty Table"
    ::= { OpenTable-5 2 }

OpenHysteresis-5 OBJECT-TYPE
    SYNTAX Integer32
    MAX-ACCESS read-only
    STATUS current
    DESCRIPTION "Hysteresis"
    ::= { OpenTable-5 3 }

OpenRampDownDuty-5 OBJECT-TYPE
    SYNTAX Integer32
    MAX-ACCESS read-only
    STATUS current
    DESCRIPTION "Ramp Down Duty"
    ::= { OpenTable-5 4 }

OpenRampDownInterval-5 OBJECT-TYPE
    SYNTAX Integer32
    MAX-ACCESS read-only
    STATUS current
    DESCRIPTION "Ramp Down Interval"
    ::= { OpenTable-5 5 }

OpenRampUpDuty-5 OBJECT-TYPE
    SYNTAX Integer32
    MAX-ACCESS read-only
    STATUS current
    DESCRIPTION "Ramp Up Duty"
    ::= { OpenTable-5 6 }

OpenRampUpInterval-5 OBJECT-TYPE
    SYNTAX Integer32
    MAX-ACCESS read-only
    STATUS current
    DESCRIPTION "Ramp Up Interval"
    ::= { OpenTable-5 7 }

OpenTable-6 OBJECT-TYPE
    SYNTAX DisplayString
    MAX-ACCESS read-only
    STATUS current
    DESCRIPTION "Open Loop Fan Table"
    ::= { OpenLoop 6 }

OpenFanTempTable-6 OBJECT-TYPE
    SYNTAX DisplayString
    MAX-ACCESS read-only
    STATUS current
    DESCRIPTION "Fan Temp Table"
    ::= { OpenTable-6 1 }

OpenFanDutyTable-6 OBJECT-TYPE
    SYNTAX DisplayString
    MAX-ACCESS read-only
    STATUS current
    DESCRIPTION "Fan Duty Table"
    ::= { OpenTable-6 2 }

OpenHysteresis-6 OBJECT-TYPE
    SYNTAX Integer32
    MAX-ACCESS read-only
    STATUS current
    DESCRIPTION "Hysteresis"
    ::= { OpenTable-6 3 }

OpenRampDownDuty-6 OBJECT-TYPE
    SYNTAX Integer32
    MAX-ACCESS read-only
    STATUS current
    DESCRIPTION "Ramp Down Duty"
    ::= { OpenTable-6 4 }

OpenRampDownInterval-6 OBJECT-TYPE
    SYNTAX Integer32
    MAX-ACCESS read-only
    STATUS current
    DESCRIPTION "Ramp Down Interval"
    ::= { OpenTable-6 5 }

OpenRampUpDuty-6 OBJECT-TYPE
    SYNTAX Integer32
    MAX-ACCESS read-only
    STATUS current
    DESCRIPTION "Ramp Up Duty"
    ::= { OpenTable-6 6 }

OpenRampUpInterval-6 OBJECT-TYPE
    SYNTAX Integer32
    MAX-ACCESS read-only
    STATUS current
    DESCRIPTION "Ramp Up Interval"
    ::= { OpenTable-6 7 }

OpenTable-7 OBJECT-TYPE
    SYNTAX DisplayString
    MAX-ACCESS read-only
    STATUS current
    DESCRIPTION "Open Loop Fan Table"
    ::= { OpenLoop 7 }

OpenFanTempTable-7 OBJECT-TYPE
    SYNTAX DisplayString
    MAX-ACCESS read-only
    STATUS current
    DESCRIPTION "Fan Temp Table"
    ::= { OpenTable-7 1 }

OpenFanDutyTable-7 OBJECT-TYPE
    SYNTAX DisplayString
    MAX-ACCESS read-only
    STATUS current
    DESCRIPTION "Fan Duty Table"
    ::= { OpenTable-7 2 }

OpenHysteresis-7 OBJECT-TYPE
    SYNTAX Integer32
    MAX-ACCESS read-only
    STATUS current
    DESCRIPTION "Hysteresis"
    ::= { OpenTable-7 3 }

OpenRampDownDuty-7 OBJECT-TYPE
    SYNTAX Integer32
    MAX-ACCESS read-only
    STATUS current
    DESCRIPTION "Ramp Down Duty"
    ::= { OpenTable-7 4 }

OpenRampDownInterval-7 OBJECT-TYPE
    SYNTAX Integer32
    MAX-ACCESS read-only
    STATUS current
    DESCRIPTION "Ramp Down Interval"
    ::= { OpenTable-7 5 }

OpenRampUpDuty-7 OBJECT-TYPE
    SYNTAX Integer32
    MAX-ACCESS read-only
    STATUS current
    DESCRIPTION "Ramp Up Duty"
    ::= { OpenTable-7 6 }

OpenRampUpInterval-7 OBJECT-TYPE
    SYNTAX Integer32
    MAX-ACCESS read-only
    STATUS current
    DESCRIPTION "Ramp Up Interval"
    ::= { OpenTable-7 7 }

OpenTable-8 OBJECT-TYPE
    SYNTAX DisplayString
    MAX-ACCESS read-only
    STATUS current
    DESCRIPTION "Open Loop Fan Table"
    ::= { OpenLoop 8 }

OpenFanTempTable-8 OBJECT-TYPE
    SYNTAX DisplayString
    MAX-ACCESS read-only
    STATUS current
    DESCRIPTION "Fan Temp Table"
    ::= { OpenTable-8 1 }

OpenFanDutyTable-8 OBJECT-TYPE
    SYNTAX DisplayString
    MAX-ACCESS read-only
    STATUS current
    DESCRIPTION "Fan Duty Table"
    ::= { OpenTable-8 2 }

OpenHysteresis-8 OBJECT-TYPE
    SYNTAX Integer32
    MAX-ACCESS read-only
    STATUS current
    DESCRIPTION "Hysteresis"
    ::= { OpenTable-8 3 }

OpenRampDownDuty-8 OBJECT-TYPE
    SYNTAX Integer32
    MAX-ACCESS read-only
    STATUS current
    DESCRIPTION "Ramp Down Duty"
    ::= { OpenTable-8 4 }

OpenRampDownInterval-8 OBJECT-TYPE
    SYNTAX Integer32
    MAX-ACCESS read-only
    STATUS current
    DESCRIPTION "Ramp Down Interval"
    ::= { OpenTable-8 5 }

OpenRampUpDuty-8 OBJECT-TYPE
    SYNTAX Integer32
    MAX-ACCESS read-only
    STATUS current
    DESCRIPTION "Ramp Up Duty"
    ::= { OpenTable-8 6 }

OpenRampUpInterval-8 OBJECT-TYPE
    SYNTAX Integer32
    MAX-ACCESS read-only
    STATUS current
    DESCRIPTION "Ramp Up Interval"
    ::= { OpenTable-8 7 }

ClosedLoop OBJECT-TYPE
    SYNTAX DisplayString
    MAX-ACCESS read-only
    STATUS current
    DESCRIPTION "Closed Loop Fan Data"
    ::= { FanCtrlData 8 }

ClosedTable-1 OBJECT-TYPE
    SYNTAX DisplayString
    MAX-ACCESS read-only
    STATUS current
    DESCRIPTION "Closed Loop Fan Table"
    ::= { ClosedLoop 1 }

ClosedRampDownTemp-1 OBJECT-TYPE
    SYNTAX DisplayString
    MAX-ACCESS read-only
    STATUS current
    DESCRIPTION "Ramp Down Temp"
    ::= { ClosedTable-1 1 }

ClosedRampDownDuty-1 OBJECT-TYPE
    SYNTAX DisplayString
    MAX-ACCESS read-only
    STATUS current
    DESCRIPTION "Ramp Down Duty"
    ::= { ClosedTable-1 2 }

ClosedRampDownInterval-1 OBJECT-TYPE
    SYNTAX DisplayString
    MAX-ACCESS read-only
    STATUS current
    DESCRIPTION "Ramp Down Interval"
    ::= { ClosedTable-1 3 }

ClosedRampUpTemp-1 OBJECT-TYPE
    SYNTAX DisplayString
    MAX-ACCESS read-only
    STATUS current
    DESCRIPTION "Ramp Up Temp"
    ::= { ClosedTable-1 4 }

ClosedRampUpDuty-1 OBJECT-TYPE
    SYNTAX DisplayString
    MAX-ACCESS read-only
    STATUS current
    DESCRIPTION "Ramp Up Duty"
    ::= { ClosedTable-1 5 }

ClosedRampUpInterval-1 OBJECT-TYPE
    SYNTAX DisplayString
    MAX-ACCESS read-only
    STATUS current
    DESCRIPTION "Ramp Up Interval"
    ::= { ClosedTable-1 6 }

ClosedThreshouldTemp-1 OBJECT-TYPE
    SYNTAX Integer32
    MAX-ACCESS read-only
    STATUS current
    DESCRIPTION "Threshould Temp"
    ::= { ClosedTable-1 7 }

ClosedTable-2 OBJECT-TYPE
    SYNTAX DisplayString
    MAX-ACCESS read-only
    STATUS current
    DESCRIPTION "Closed Loop Fan Table"
    ::= { ClosedLoop 2 }

ClosedRampDownTemp-2 OBJECT-TYPE
    SYNTAX DisplayString
    MAX-ACCESS read-only
    STATUS current
    DESCRIPTION "Ramp Down Temp"
    ::= { ClosedTable-2 1 }

ClosedRampDownDuty-2 OBJECT-TYPE
    SYNTAX DisplayString
    MAX-ACCESS read-only
    STATUS current
    DESCRIPTION "Ramp Down Duty"
    ::= { ClosedTable-2 2 }

ClosedRampDownInterval-2 OBJECT-TYPE
    SYNTAX DisplayString
    MAX-ACCESS read-only
    STATUS current
    DESCRIPTION "Ramp Down Interval"
    ::= { ClosedTable-2 3 }

ClosedRampUpTemp-2 OBJECT-TYPE
    SYNTAX DisplayString
    MAX-ACCESS read-only
    STATUS current
    DESCRIPTION "Ramp Up Temp"
    ::= { ClosedTable-2 4 }

ClosedRampUpDuty-2 OBJECT-TYPE
    SYNTAX DisplayString
    MAX-ACCESS read-only
    STATUS current
    DESCRIPTION "Ramp Up Duty"
    ::= { ClosedTable-2 5 }

ClosedRampUpInterval-2 OBJECT-TYPE
    SYNTAX DisplayString
    MAX-ACCESS read-only
    STATUS current
    DESCRIPTION "Ramp Up Interval"
    ::= { ClosedTable-2 6 }

ClosedThreshouldTemp-2 OBJECT-TYPE
    SYNTAX Integer32
    MAX-ACCESS read-only
    STATUS current
    DESCRIPTION "Threshould Temp"
    ::= { ClosedTable-2 7 }

ClosedTable-3 OBJECT-TYPE
    SYNTAX DisplayString
    MAX-ACCESS read-only
    STATUS current
    DESCRIPTION "Closed Loop Fan Table"
    ::= { ClosedLoop 3 }

ClosedRampDownTemp-3 OBJECT-TYPE
    SYNTAX DisplayString
    MAX-ACCESS read-only
    STATUS current
    DESCRIPTION "Ramp Down Temp"
    ::= { ClosedTable-3 1 }

ClosedRampDownDuty-3 OBJECT-TYPE
    SYNTAX DisplayString
    MAX-ACCESS read-only
    STATUS current
    DESCRIPTION "Ramp Down Duty"
    ::= { ClosedTable-3 2 }

ClosedRampDownInterval-3 OBJECT-TYPE
    SYNTAX DisplayString
    MAX-ACCESS read-only
    STATUS current
    DESCRIPTION "Ramp Down Interval"
    ::= { ClosedTable-3 3 }

ClosedRampUpTemp-3 OBJECT-TYPE
    SYNTAX DisplayString
    MAX-ACCESS read-only
    STATUS current
    DESCRIPTION "Ramp Up Temp"
    ::= { ClosedTable-3 4 }

ClosedRampUpDuty-3 OBJECT-TYPE
    SYNTAX DisplayString
    MAX-ACCESS read-only
    STATUS current
    DESCRIPTION "Ramp Up Duty"
    ::= { ClosedTable-3 5 }

ClosedRampUpInterval-3 OBJECT-TYPE
    SYNTAX DisplayString
    MAX-ACCESS read-only
    STATUS current
    DESCRIPTION "Ramp Up Interval"
    ::= { ClosedTable-3 6 }

ClosedThreshouldTemp-3 OBJECT-TYPE
    SYNTAX Integer32
    MAX-ACCESS read-only
    STATUS current
    DESCRIPTION "Threshould Temp"
    ::= { ClosedTable-3 7 }

ClosedTable-4 OBJECT-TYPE
    SYNTAX DisplayString
    MAX-ACCESS read-only
    STATUS current
    DESCRIPTION "Closed Loop Fan Table"
    ::= { ClosedLoop 4 }

ClosedRampDownTemp-4 OBJECT-TYPE
    SYNTAX DisplayString
    MAX-ACCESS read-only
    STATUS current
    DESCRIPTION "Ramp Down Temp"
    ::= { ClosedTable-4 1 }

ClosedRampDownDuty-4 OBJECT-TYPE
    SYNTAX DisplayString
    MAX-ACCESS read-only
    STATUS current
    DESCRIPTION "Ramp Down Duty"
    ::= { ClosedTable-4 2 }

ClosedRampDownInterval-4 OBJECT-TYPE
    SYNTAX DisplayString
    MAX-ACCESS read-only
    STATUS current
    DESCRIPTION "Ramp Down Interval"
    ::= { ClosedTable-4 3 }

ClosedRampUpTemp-4 OBJECT-TYPE
    SYNTAX DisplayString
    MAX-ACCESS read-only
    STATUS current
    DESCRIPTION "Ramp Up Temp"
    ::= { ClosedTable-4 4 }

ClosedRampUpDuty-4 OBJECT-TYPE
    SYNTAX DisplayString
    MAX-ACCESS read-only
    STATUS current
    DESCRIPTION "Ramp Up Duty"
    ::= { ClosedTable-4 5 }

ClosedRampUpInterval-4 OBJECT-TYPE
    SYNTAX DisplayString
    MAX-ACCESS read-only
    STATUS current
    DESCRIPTION "Ramp Up Interval"
    ::= { ClosedTable-4 6 }

ClosedThreshouldTemp-4 OBJECT-TYPE
    SYNTAX Integer32
    MAX-ACCESS read-only
    STATUS current
    DESCRIPTION "Threshould Temp"
    ::= { ClosedTable-4 7 }

ClosedTable-5 OBJECT-TYPE
    SYNTAX DisplayString
    MAX-ACCESS read-only
    STATUS current
    DESCRIPTION "Closed Loop Fan Table"
    ::= { ClosedLoop 5 }

ClosedRampDownTemp-5 OBJECT-TYPE
    SYNTAX DisplayString
    MAX-ACCESS read-only
    STATUS current
    DESCRIPTION "Ramp Down Temp"
    ::= { ClosedTable-5 1 }

ClosedRampDownDuty-5 OBJECT-TYPE
    SYNTAX DisplayString
    MAX-ACCESS read-only
    STATUS current
    DESCRIPTION "Ramp Down Duty"
    ::= { ClosedTable-5 2 }

ClosedRampDownInterval-5 OBJECT-TYPE
    SYNTAX DisplayString
    MAX-ACCESS read-only
    STATUS current
    DESCRIPTION "Ramp Down Interval"
    ::= { ClosedTable-5 3 }

ClosedRampUpTemp-5 OBJECT-TYPE
    SYNTAX DisplayString
    MAX-ACCESS read-only
    STATUS current
    DESCRIPTION "Ramp Up Temp"
    ::= { ClosedTable-5 4 }

ClosedRampUpDuty-5 OBJECT-TYPE
    SYNTAX DisplayString
    MAX-ACCESS read-only
    STATUS current
    DESCRIPTION "Ramp Up Duty"
    ::= { ClosedTable-5 5 }

ClosedRampUpInterval-5 OBJECT-TYPE
    SYNTAX DisplayString
    MAX-ACCESS read-only
    STATUS current
    DESCRIPTION "Ramp Up Interval"
    ::= { ClosedTable-5 6 }

ClosedThreshouldTemp-5 OBJECT-TYPE
    SYNTAX Integer32
    MAX-ACCESS read-only
    STATUS current
    DESCRIPTION "Threshould Temp"
    ::= { ClosedTable-5 7 }

ClosedTable-6 OBJECT-TYPE
    SYNTAX DisplayString
    MAX-ACCESS read-only
    STATUS current
    DESCRIPTION "Closed Loop Fan Table"
    ::= { ClosedLoop 6 }

ClosedRampDownTemp-6 OBJECT-TYPE
    SYNTAX DisplayString
    MAX-ACCESS read-only
    STATUS current
    DESCRIPTION "Ramp Down Temp"
    ::= { ClosedTable-6 1 }

ClosedRampDownDuty-6 OBJECT-TYPE
    SYNTAX DisplayString
    MAX-ACCESS read-only
    STATUS current
    DESCRIPTION "Ramp Down Duty"
    ::= { ClosedTable-6 2 }

ClosedRampDownInterval-6 OBJECT-TYPE
    SYNTAX DisplayString
    MAX-ACCESS read-only
    STATUS current
    DESCRIPTION "Ramp Down Interval"
    ::= { ClosedTable-6 3 }

ClosedRampUpTemp-6 OBJECT-TYPE
    SYNTAX DisplayString
    MAX-ACCESS read-only
    STATUS current
    DESCRIPTION "Ramp Up Temp"
    ::= { ClosedTable-6 4 }

ClosedRampUpDuty-6 OBJECT-TYPE
    SYNTAX DisplayString
    MAX-ACCESS read-only
    STATUS current
    DESCRIPTION "Ramp Up Duty"
    ::= { ClosedTable-6 5 }

ClosedRampUpInterval-6 OBJECT-TYPE
    SYNTAX DisplayString
    MAX-ACCESS read-only
    STATUS current
    DESCRIPTION "Ramp Up Interval"
    ::= { ClosedTable-6 6 }

ClosedThreshouldTemp-6 OBJECT-TYPE
    SYNTAX Integer32
    MAX-ACCESS read-only
    STATUS current
    DESCRIPTION "Threshould Temp"
    ::= { ClosedTable-6 7 }

ClosedTable-7 OBJECT-TYPE
    SYNTAX DisplayString
    MAX-ACCESS read-only
    STATUS current
    DESCRIPTION "Closed Loop Fan Table"
    ::= { ClosedLoop 7 }

ClosedRampDownTemp-7 OBJECT-TYPE
    SYNTAX DisplayString
    MAX-ACCESS read-only
    STATUS current
    DESCRIPTION "Ramp Down Temp"
    ::= { ClosedTable-7 1 }

ClosedRampDownDuty-7 OBJECT-TYPE
    SYNTAX DisplayString
    MAX-ACCESS read-only
    STATUS current
    DESCRIPTION "Ramp Down Duty"
    ::= { ClosedTable-7 2 }

ClosedRampDownInterval-7 OBJECT-TYPE
    SYNTAX DisplayString
    MAX-ACCESS read-only
    STATUS current
    DESCRIPTION "Ramp Down Interval"
    ::= { ClosedTable-7 3 }

ClosedRampUpTemp-7 OBJECT-TYPE
    SYNTAX DisplayString
    MAX-ACCESS read-only
    STATUS current
    DESCRIPTION "Ramp Up Temp"
    ::= { ClosedTable-7 4 }

ClosedRampUpDuty-7 OBJECT-TYPE
    SYNTAX DisplayString
    MAX-ACCESS read-only
    STATUS current
    DESCRIPTION "Ramp Up Duty"
    ::= { ClosedTable-7 5 }

ClosedRampUpInterval-7 OBJECT-TYPE
    SYNTAX DisplayString
    MAX-ACCESS read-only
    STATUS current
    DESCRIPTION "Ramp Up Interval"
    ::= { ClosedTable-7 6 }

ClosedThreshouldTemp-7 OBJECT-TYPE
    SYNTAX Integer32
    MAX-ACCESS read-only
    STATUS current
    DESCRIPTION "Threshould Temp"
    ::= { ClosedTable-7 7 }

ClosedTable-8 OBJECT-TYPE
    SYNTAX DisplayString
    MAX-ACCESS read-only
    STATUS current
    DESCRIPTION "Closed Loop Fan Table"
    ::= { ClosedLoop 8 }

ClosedRampDownTemp-8 OBJECT-TYPE
    SYNTAX DisplayString
    MAX-ACCESS read-only
    STATUS current
    DESCRIPTION "Ramp Down Temp"
    ::= { ClosedTable-8 1 }

ClosedRampDownDuty-8 OBJECT-TYPE
    SYNTAX DisplayString
    MAX-ACCESS read-only
    STATUS current
    DESCRIPTION "Ramp Down Duty"
    ::= { ClosedTable-8 2 }

ClosedRampDownInterval-8 OBJECT-TYPE
    SYNTAX DisplayString
    MAX-ACCESS read-only
    STATUS current
    DESCRIPTION "Ramp Down Interval"
    ::= { ClosedTable-8 3 }

ClosedRampUpTemp-8 OBJECT-TYPE
    SYNTAX DisplayString
    MAX-ACCESS read-only
    STATUS current
    DESCRIPTION "Ramp Up Temp"
    ::= { ClosedTable-8 4 }

ClosedRampUpDuty-8 OBJECT-TYPE
    SYNTAX DisplayString
    MAX-ACCESS read-only
    STATUS current
    DESCRIPTION "Ramp Up Duty"
    ::= { ClosedTable-8 5 }

ClosedRampUpInterval-8 OBJECT-TYPE
    SYNTAX DisplayString
    MAX-ACCESS read-only
    STATUS current
    DESCRIPTION "Ramp Up Interval"
    ::= { ClosedTable-8 6 }

ClosedThreshouldTemp-8 OBJECT-TYPE
    SYNTAX Integer32
    MAX-ACCESS read-only
    STATUS current
    DESCRIPTION "Threshould Temp"
    ::= { ClosedTable-8 7 }

ClosedTable-9 OBJECT-TYPE
    SYNTAX DisplayString
    MAX-ACCESS read-only
    STATUS current
    DESCRIPTION "Closed Loop Fan Table"
    ::= { ClosedLoop 9 }

ClosedRampDownTemp-9 OBJECT-TYPE
    SYNTAX DisplayString
    MAX-ACCESS read-only
    STATUS current
    DESCRIPTION "Ramp Down Temp"
    ::= { ClosedTable-9 1 }

ClosedRampDownDuty-9 OBJECT-TYPE
    SYNTAX DisplayString
    MAX-ACCESS read-only
    STATUS current
    DESCRIPTION "Ramp Down Duty"
    ::= { ClosedTable-9 2 }

ClosedRampDownInterval-9 OBJECT-TYPE
    SYNTAX DisplayString
    MAX-ACCESS read-only
    STATUS current
    DESCRIPTION "Ramp Down Interval"
    ::= { ClosedTable-9 3 }

ClosedRampUpTemp-9 OBJECT-TYPE
    SYNTAX DisplayString
    MAX-ACCESS read-only
    STATUS current
    DESCRIPTION "Ramp Up Temp"
    ::= { ClosedTable-9 4 }

ClosedRampUpDuty-9 OBJECT-TYPE
    SYNTAX DisplayString
    MAX-ACCESS read-only
    STATUS current
    DESCRIPTION "Ramp Up Duty"
    ::= { ClosedTable-9 5 }

ClosedRampUpInterval-9 OBJECT-TYPE
    SYNTAX DisplayString
    MAX-ACCESS read-only
    STATUS current
    DESCRIPTION "Ramp Up Interval"
    ::= { ClosedTable-9 6 }

ClosedThreshouldTemp-9 OBJECT-TYPE
    SYNTAX Integer32
    MAX-ACCESS read-only
    STATUS current
    DESCRIPTION "Threshould Temp"
    ::= { ClosedTable-9 7 }

ClosedTable-10 OBJECT-TYPE
    SYNTAX DisplayString
    MAX-ACCESS read-only
    STATUS current
    DESCRIPTION "Closed Loop Fan Table"
    ::= { ClosedLoop 10 }

ClosedRampDownTemp-10 OBJECT-TYPE
    SYNTAX DisplayString
    MAX-ACCESS read-only
    STATUS current
    DESCRIPTION "Ramp Down Temp"
    ::= { ClosedTable-10 1 }

ClosedRampDownDuty-10 OBJECT-TYPE
    SYNTAX DisplayString
    MAX-ACCESS read-only
    STATUS current
    DESCRIPTION "Ramp Down Duty"
    ::= { ClosedTable-10 2 }

ClosedRampDownInterval-10 OBJECT-TYPE
    SYNTAX DisplayString
    MAX-ACCESS read-only
    STATUS current
    DESCRIPTION "Ramp Down Interval"
    ::= { ClosedTable-10 3 }

ClosedRampUpTemp-10 OBJECT-TYPE
    SYNTAX DisplayString
    MAX-ACCESS read-only
    STATUS current
    DESCRIPTION "Ramp Up Temp"
    ::= { ClosedTable-10 4 }

ClosedRampUpDuty-10 OBJECT-TYPE
    SYNTAX DisplayString
    MAX-ACCESS read-only
    STATUS current
    DESCRIPTION "Ramp Up Duty"
    ::= { ClosedTable-10 5 }

ClosedRampUpInterval-10 OBJECT-TYPE
    SYNTAX DisplayString
    MAX-ACCESS read-only
    STATUS current
    DESCRIPTION "Ramp Up Interval"
    ::= { ClosedTable-10 6 }

ClosedThreshouldTemp-10 OBJECT-TYPE
    SYNTAX Integer32
    MAX-ACCESS read-only
    STATUS current
    DESCRIPTION "Threshould Temp"
    ::= { ClosedTable-10 7 }

FanAssignment OBJECT-TYPE
    SYNTAX DisplayString
    MAX-ACCESS read-only
    STATUS current
    DESCRIPTION "Fan Assignment"
    ::= { FanCtrlData 9 }

AssignTable-1 OBJECT-TYPE
    SYNTAX DisplayString
    MAX-ACCESS read-only
    STATUS current
    DESCRIPTION "Fan Assignment Table"
    ::= { FanAssignment 1 }

TempSensor-1 OBJECT-TYPE
    SYNTAX DisplayString
    MAX-ACCESS read-only
    STATUS current
    DESCRIPTION "Temperature Sensor"
    ::= { AssignTable-1 1 }

OpenLoopTable-1 OBJECT-TYPE
    SYNTAX Integer32
    MAX-ACCESS read-only
    STATUS current
    DESCRIPTION "Open Loop Table"
    ::= { AssignTable-1 2 }

ClosedLoopTable-1 OBJECT-TYPE
    SYNTAX Integer32
    MAX-ACCESS read-only
    STATUS current
    DESCRIPTION "Closed Loop Table"
    ::= { AssignTable-1 3 }

SelectedFan-1 OBJECT-TYPE
    SYNTAX DisplayString
    MAX-ACCESS read-only
    STATUS current
    DESCRIPTION "Selected Fan"
    ::= { AssignTable-1 4 }

AssignTable-2 OBJECT-TYPE
    SYNTAX DisplayString
    MAX-ACCESS read-only
    STATUS current
    DESCRIPTION "Fan Assignment Table"
    ::= { FanAssignment 2 }

TempSensor-2 OBJECT-TYPE
    SYNTAX DisplayString
    MAX-ACCESS read-only
    STATUS current
    DESCRIPTION "Temperature Sensor"
    ::= { AssignTable-2 1 }

OpenLoopTable-2 OBJECT-TYPE
    SYNTAX Integer32
    MAX-ACCESS read-only
    STATUS current
    DESCRIPTION "Open Loop Table"
    ::= { AssignTable-2 2 }

ClosedLoopTable-2 OBJECT-TYPE
    SYNTAX Integer32
    MAX-ACCESS read-only
    STATUS current
    DESCRIPTION "Closed Loop Table"
    ::= { AssignTable-2 3 }

SelectedFan-2 OBJECT-TYPE
    SYNTAX DisplayString
    MAX-ACCESS read-only
    STATUS current
    DESCRIPTION "Selected Fan"
    ::= { AssignTable-2 4 }

AssignTable-3 OBJECT-TYPE
    SYNTAX DisplayString
    MAX-ACCESS read-only
    STATUS current
    DESCRIPTION "Fan Assignment Table"
    ::= { FanAssignment 3 }

TempSensor-3 OBJECT-TYPE
    SYNTAX DisplayString
    MAX-ACCESS read-only
    STATUS current
    DESCRIPTION "Temperature Sensor"
    ::= { AssignTable-3 1 }

OpenLoopTable-3 OBJECT-TYPE
    SYNTAX Integer32
    MAX-ACCESS read-only
    STATUS current
    DESCRIPTION "Open Loop Table"
    ::= { AssignTable-3 2 }

ClosedLoopTable-3 OBJECT-TYPE
    SYNTAX Integer32
    MAX-ACCESS read-only
    STATUS current
    DESCRIPTION "Closed Loop Table"
    ::= { AssignTable-3 3 }

SelectedFan-3 OBJECT-TYPE
    SYNTAX DisplayString
    MAX-ACCESS read-only
    STATUS current
    DESCRIPTION "Selected Fan"
    ::= { AssignTable-3 4 }

AssignTable-4 OBJECT-TYPE
    SYNTAX DisplayString
    MAX-ACCESS read-only
    STATUS current
    DESCRIPTION "Fan Assignment Table"
    ::= { FanAssignment 4 }

TempSensor-4 OBJECT-TYPE
    SYNTAX DisplayString
    MAX-ACCESS read-only
    STATUS current
    DESCRIPTION "Temperature Sensor"
    ::= { AssignTable-4 1 }

OpenLoopTable-4 OBJECT-TYPE
    SYNTAX Integer32
    MAX-ACCESS read-only
    STATUS current
    DESCRIPTION "Open Loop Table"
    ::= { AssignTable-4 2 }

ClosedLoopTable-4 OBJECT-TYPE
    SYNTAX Integer32
    MAX-ACCESS read-only
    STATUS current
    DESCRIPTION "Closed Loop Table"
    ::= { AssignTable-4 3 }

SelectedFan-4 OBJECT-TYPE
    SYNTAX DisplayString
    MAX-ACCESS read-only
    STATUS current
    DESCRIPTION "Selected Fan"
    ::= { AssignTable-4 4 }

AssignTable-5 OBJECT-TYPE
    SYNTAX DisplayString
    MAX-ACCESS read-only
    STATUS current
    DESCRIPTION "Fan Assignment Table"
    ::= { FanAssignment 5 }

TempSensor-5 OBJECT-TYPE
    SYNTAX DisplayString
    MAX-ACCESS read-only
    STATUS current
    DESCRIPTION "Temperature Sensor"
    ::= { AssignTable-5 1 }

OpenLoopTable-5 OBJECT-TYPE
    SYNTAX Integer32
    MAX-ACCESS read-only
    STATUS current
    DESCRIPTION "Open Loop Table"
    ::= { AssignTable-5 2 }

ClosedLoopTable-5 OBJECT-TYPE
    SYNTAX Integer32
    MAX-ACCESS read-only
    STATUS current
    DESCRIPTION "Closed Loop Table"
    ::= { AssignTable-5 3 }

SelectedFan-5 OBJECT-TYPE
    SYNTAX DisplayString
    MAX-ACCESS read-only
    STATUS current
    DESCRIPTION "Selected Fan"
    ::= { AssignTable-5 4 }

AssignTable-6 OBJECT-TYPE
    SYNTAX DisplayString
    MAX-ACCESS read-only
    STATUS current
    DESCRIPTION "Fan Assignment Table"
    ::= { FanAssignment 6 }

TempSensor-6 OBJECT-TYPE
    SYNTAX DisplayString
    MAX-ACCESS read-only
    STATUS current
    DESCRIPTION "Temperature Sensor"
    ::= { AssignTable-6 1 }

OpenLoopTable-6 OBJECT-TYPE
    SYNTAX Integer32
    MAX-ACCESS read-only
    STATUS current
    DESCRIPTION "Open Loop Table"
    ::= { AssignTable-6 2 }

ClosedLoopTable-6 OBJECT-TYPE
    SYNTAX Integer32
    MAX-ACCESS read-only
    STATUS current
    DESCRIPTION "Closed Loop Table"
    ::= { AssignTable-6 3 }

SelectedFan-6 OBJECT-TYPE
    SYNTAX DisplayString
    MAX-ACCESS read-only
    STATUS current
    DESCRIPTION "Selected Fan"
    ::= { AssignTable-6 4 }

AssignTable-7 OBJECT-TYPE
    SYNTAX DisplayString
    MAX-ACCESS read-only
    STATUS current
    DESCRIPTION "Fan Assignment Table"
    ::= { FanAssignment 7 }

TempSensor-7 OBJECT-TYPE
    SYNTAX DisplayString
    MAX-ACCESS read-only
    STATUS current
    DESCRIPTION "Temperature Sensor"
    ::= { AssignTable-7 1 }

OpenLoopTable-7 OBJECT-TYPE
    SYNTAX Integer32
    MAX-ACCESS read-only
    STATUS current
    DESCRIPTION "Open Loop Table"
    ::= { AssignTable-7 2 }

ClosedLoopTable-7 OBJECT-TYPE
    SYNTAX Integer32
    MAX-ACCESS read-only
    STATUS current
    DESCRIPTION "Closed Loop Table"
    ::= { AssignTable-7 3 }

SelectedFan-7 OBJECT-TYPE
    SYNTAX DisplayString
    MAX-ACCESS read-only
    STATUS current
    DESCRIPTION "Selected Fan"
    ::= { AssignTable-7 4 }

AssignTable-8 OBJECT-TYPE
    SYNTAX DisplayString
    MAX-ACCESS read-only
    STATUS current
    DESCRIPTION "Fan Assignment Table"
    ::= { FanAssignment 8 }

TempSensor-8 OBJECT-TYPE
    SYNTAX DisplayString
    MAX-ACCESS read-only
    STATUS current
    DESCRIPTION "Temperature Sensor"
    ::= { AssignTable-8 1 }

OpenLoopTable-8 OBJECT-TYPE
    SYNTAX Integer32
    MAX-ACCESS read-only
    STATUS current
    DESCRIPTION "Open Loop Table"
    ::= { AssignTable-8 2 }

ClosedLoopTable-8 OBJECT-TYPE
    SYNTAX Integer32
    MAX-ACCESS read-only
    STATUS current
    DESCRIPTION "Closed Loop Table"
    ::= { AssignTable-8 3 }

SelectedFan-8 OBJECT-TYPE
    SYNTAX DisplayString
    MAX-ACCESS read-only
    STATUS current
    DESCRIPTION "Selected Fan"
    ::= { AssignTable-8 4 }

AssignTable-9 OBJECT-TYPE
    SYNTAX DisplayString
    MAX-ACCESS read-only
    STATUS current
    DESCRIPTION "Fan Assignment Table"
    ::= { FanAssignment 9 }

TempSensor-9 OBJECT-TYPE
    SYNTAX DisplayString
    MAX-ACCESS read-only
    STATUS current
    DESCRIPTION "Temperature Sensor"
    ::= { AssignTable-9 1 }

OpenLoopTable-9 OBJECT-TYPE
    SYNTAX Integer32
    MAX-ACCESS read-only
    STATUS current
    DESCRIPTION "Open Loop Table"
    ::= { AssignTable-9 2 }

ClosedLoopTable-9 OBJECT-TYPE
    SYNTAX Integer32
    MAX-ACCESS read-only
    STATUS current
    DESCRIPTION "Closed Loop Table"
    ::= { AssignTable-9 3 }

SelectedFan-9 OBJECT-TYPE
    SYNTAX DisplayString
    MAX-ACCESS read-only
    STATUS current
    DESCRIPTION "Selected Fan"
    ::= { AssignTable-9 4 }

AssignTable-10 OBJECT-TYPE
    SYNTAX DisplayString
    MAX-ACCESS read-only
    STATUS current
    DESCRIPTION "Fan Assignment Table"
    ::= { FanAssignment 10 }

TempSensor-10 OBJECT-TYPE
    SYNTAX DisplayString
    MAX-ACCESS read-only
    STATUS current
    DESCRIPTION "Temperature Sensor"
    ::= { AssignTable-10 1 }

OpenLoopTable-10 OBJECT-TYPE
    SYNTAX Integer32
    MAX-ACCESS read-only
    STATUS current
    DESCRIPTION "Open Loop Table"
    ::= { AssignTable-10 2 }

ClosedLoopTable-10 OBJECT-TYPE
    SYNTAX Integer32
    MAX-ACCESS read-only
    STATUS current
    DESCRIPTION "Closed Loop Table"
    ::= { AssignTable-10 3 }

SelectedFan-10 OBJECT-TYPE
    SYNTAX DisplayString
    MAX-ACCESS read-only
    STATUS current
    DESCRIPTION "Selected Fan"
    ::= { AssignTable-10 4 }

AssignTable-11 OBJECT-TYPE
    SYNTAX DisplayString
    MAX-ACCESS read-only
    STATUS current
    DESCRIPTION "Fan Assignment Table"
    ::= { FanAssignment 11 }

TempSensor-11 OBJECT-TYPE
    SYNTAX DisplayString
    MAX-ACCESS read-only
    STATUS current
    DESCRIPTION "Temperature Sensor"
    ::= { AssignTable-11 1 }

OpenLoopTable-11 OBJECT-TYPE
    SYNTAX Integer32
    MAX-ACCESS read-only
    STATUS current
    DESCRIPTION "Open Loop Table"
    ::= { AssignTable-11 2 }

ClosedLoopTable-11 OBJECT-TYPE
    SYNTAX Integer32
    MAX-ACCESS read-only
    STATUS current
    DESCRIPTION "Closed Loop Table"
    ::= { AssignTable-11 3 }

SelectedFan-11 OBJECT-TYPE
    SYNTAX DisplayString
    MAX-ACCESS read-only
    STATUS current
    DESCRIPTION "Selected Fan"
    ::= { AssignTable-11 4 }

AssignTable-12 OBJECT-TYPE
    SYNTAX DisplayString
    MAX-ACCESS read-only
    STATUS current
    DESCRIPTION "Fan Assignment Table"
    ::= { FanAssignment 12 }

TempSensor-12 OBJECT-TYPE
    SYNTAX DisplayString
    MAX-ACCESS read-only
    STATUS current
    DESCRIPTION "Temperature Sensor"
    ::= { AssignTable-12 1 }

OpenLoopTable-12 OBJECT-TYPE
    SYNTAX Integer32
    MAX-ACCESS read-only
    STATUS current
    DESCRIPTION "Open Loop Table"
    ::= { AssignTable-12 2 }

ClosedLoopTable-12 OBJECT-TYPE
    SYNTAX Integer32
    MAX-ACCESS read-only
    STATUS current
    DESCRIPTION "Closed Loop Table"
    ::= { AssignTable-12 3 }

SelectedFan-12 OBJECT-TYPE
    SYNTAX DisplayString
    MAX-ACCESS read-only
    STATUS current
    DESCRIPTION "Selected Fan"
    ::= { AssignTable-12 4 }

AssignTable-13 OBJECT-TYPE
    SYNTAX DisplayString
    MAX-ACCESS read-only
    STATUS current
    DESCRIPTION "Fan Assignment Table"
    ::= { FanAssignment 13 }

TempSensor-13 OBJECT-TYPE
    SYNTAX DisplayString
    MAX-ACCESS read-only
    STATUS current
    DESCRIPTION "Temperature Sensor"
    ::= { AssignTable-13 1 }

OpenLoopTable-13 OBJECT-TYPE
    SYNTAX Integer32
    MAX-ACCESS read-only
    STATUS current
    DESCRIPTION "Open Loop Table"
    ::= { AssignTable-13 2 }

ClosedLoopTable-13 OBJECT-TYPE
    SYNTAX Integer32
    MAX-ACCESS read-only
    STATUS current
    DESCRIPTION "Closed Loop Table"
    ::= { AssignTable-13 3 }

SelectedFan-13 OBJECT-TYPE
    SYNTAX DisplayString
    MAX-ACCESS read-only
    STATUS current
    DESCRIPTION "Selected Fan"
    ::= { AssignTable-13 4 }

AssignTable-14 OBJECT-TYPE
    SYNTAX DisplayString
    MAX-ACCESS read-only
    STATUS current
    DESCRIPTION "Fan Assignment Table"
    ::= { FanAssignment 14 }

TempSensor-14 OBJECT-TYPE
    SYNTAX DisplayString
    MAX-ACCESS read-only
    STATUS current
    DESCRIPTION "Temperature Sensor"
    ::= { AssignTable-14 1 }

OpenLoopTable-14 OBJECT-TYPE
    SYNTAX Integer32
    MAX-ACCESS read-only
    STATUS current
    DESCRIPTION "Open Loop Table"
    ::= { AssignTable-14 2 }

ClosedLoopTable-14 OBJECT-TYPE
    SYNTAX Integer32
    MAX-ACCESS read-only
    STATUS current
    DESCRIPTION "Closed Loop Table"
    ::= { AssignTable-14 3 }

SelectedFan-14 OBJECT-TYPE
    SYNTAX DisplayString
    MAX-ACCESS read-only
    STATUS current
    DESCRIPTION "Selected Fan"
    ::= { AssignTable-14 4 }

AssignTable-15 OBJECT-TYPE
    SYNTAX DisplayString
    MAX-ACCESS read-only
    STATUS current
    DESCRIPTION "Fan Assignment Table"
    ::= { FanAssignment 15 }

TempSensor-15 OBJECT-TYPE
    SYNTAX DisplayString
    MAX-ACCESS read-only
    STATUS current
    DESCRIPTION "Temperature Sensor"
    ::= { AssignTable-15 1 }

OpenLoopTable-15 OBJECT-TYPE
    SYNTAX Integer32
    MAX-ACCESS read-only
    STATUS current
    DESCRIPTION "Open Loop Table"
    ::= { AssignTable-15 2 }

ClosedLoopTable-15 OBJECT-TYPE
    SYNTAX Integer32
    MAX-ACCESS read-only
    STATUS current
    DESCRIPTION "Closed Loop Table"
    ::= { AssignTable-15 3 }

SelectedFan-15 OBJECT-TYPE
    SYNTAX DisplayString
    MAX-ACCESS read-only
    STATUS current
    DESCRIPTION "Selected Fan"
    ::= { AssignTable-15 4 }

AssignTable-16 OBJECT-TYPE
    SYNTAX DisplayString
    MAX-ACCESS read-only
    STATUS current
    DESCRIPTION "Fan Assignment Table"
    ::= { FanAssignment 16 }

TempSensor-16 OBJECT-TYPE
    SYNTAX DisplayString
    MAX-ACCESS read-only
    STATUS current
    DESCRIPTION "Temperature Sensor"
    ::= { AssignTable-16 1 }

OpenLoopTable-16 OBJECT-TYPE
    SYNTAX Integer32
    MAX-ACCESS read-only
    STATUS current
    DESCRIPTION "Open Loop Table"
    ::= { AssignTable-16 2 }

ClosedLoopTable-16 OBJECT-TYPE
    SYNTAX Integer32
    MAX-ACCESS read-only
    STATUS current
    DESCRIPTION "Closed Loop Table"
    ::= { AssignTable-16 3 }

SelectedFan-16 OBJECT-TYPE
    SYNTAX DisplayString
    MAX-ACCESS read-only
    STATUS current
    DESCRIPTION "Selected Fan"
    ::= { AssignTable-16 4 }

AssignTable-17 OBJECT-TYPE
    SYNTAX DisplayString
    MAX-ACCESS read-only
    STATUS current
    DESCRIPTION "Fan Assignment Table"
    ::= { FanAssignment 17 }

TempSensor-17 OBJECT-TYPE
    SYNTAX DisplayString
    MAX-ACCESS read-only
    STATUS current
    DESCRIPTION "Temperature Sensor"
    ::= { AssignTable-17 1 }

OpenLoopTable-17 OBJECT-TYPE
    SYNTAX Integer32
    MAX-ACCESS read-only
    STATUS current
    DESCRIPTION "Open Loop Table"
    ::= { AssignTable-17 2 }

ClosedLoopTable-17 OBJECT-TYPE
    SYNTAX Integer32
    MAX-ACCESS read-only
    STATUS current
    DESCRIPTION "Closed Loop Table"
    ::= { AssignTable-17 3 }

SelectedFan-17 OBJECT-TYPE
    SYNTAX DisplayString
    MAX-ACCESS read-only
    STATUS current
    DESCRIPTION "Selected Fan"
    ::= { AssignTable-17 4 }

AssignTable-18 OBJECT-TYPE
    SYNTAX DisplayString
    MAX-ACCESS read-only
    STATUS current
    DESCRIPTION "Fan Assignment Table"
    ::= { FanAssignment 18 }

TempSensor-18 OBJECT-TYPE
    SYNTAX DisplayString
    MAX-ACCESS read-only
    STATUS current
    DESCRIPTION "Temperature Sensor"
    ::= { AssignTable-18 1 }

OpenLoopTable-18 OBJECT-TYPE
    SYNTAX Integer32
    MAX-ACCESS read-only
    STATUS current
    DESCRIPTION "Open Loop Table"
    ::= { AssignTable-18 2 }

ClosedLoopTable-18 OBJECT-TYPE
    SYNTAX Integer32
    MAX-ACCESS read-only
    STATUS current
    DESCRIPTION "Closed Loop Table"
    ::= { AssignTable-18 3 }

SelectedFan-18 OBJECT-TYPE
    SYNTAX DisplayString
    MAX-ACCESS read-only
    STATUS current
    DESCRIPTION "Selected Fan"
    ::= { AssignTable-18 4 }

AssignTable-19 OBJECT-TYPE
    SYNTAX DisplayString
    MAX-ACCESS read-only
    STATUS current
    DESCRIPTION "Fan Assignment Table"
    ::= { FanAssignment 19 }

TempSensor-19 OBJECT-TYPE
    SYNTAX DisplayString
    MAX-ACCESS read-only
    STATUS current
    DESCRIPTION "Temperature Sensor"
    ::= { AssignTable-19 1 }

OpenLoopTable-19 OBJECT-TYPE
    SYNTAX Integer32
    MAX-ACCESS read-only
    STATUS current
    DESCRIPTION "Open Loop Table"
    ::= { AssignTable-19 2 }

ClosedLoopTable-19 OBJECT-TYPE
    SYNTAX Integer32
    MAX-ACCESS read-only
    STATUS current
    DESCRIPTION "Closed Loop Table"
    ::= { AssignTable-19 3 }

SelectedFan-19 OBJECT-TYPE
    SYNTAX DisplayString
    MAX-ACCESS read-only
    STATUS current
    DESCRIPTION "Selected Fan"
    ::= { AssignTable-19 4 }

AssignTable-20 OBJECT-TYPE
    SYNTAX DisplayString
    MAX-ACCESS read-only
    STATUS current
    DESCRIPTION "Fan Assignment Table"
    ::= { FanAssignment 20 }

TempSensor-20 OBJECT-TYPE
    SYNTAX DisplayString
    MAX-ACCESS read-only
    STATUS current
    DESCRIPTION "Temperature Sensor"
    ::= { AssignTable-20 1 }

OpenLoopTable-20 OBJECT-TYPE
    SYNTAX Integer32
    MAX-ACCESS read-only
    STATUS current
    DESCRIPTION "Open Loop Table"
    ::= { AssignTable-20 2 }

ClosedLoopTable-20 OBJECT-TYPE
    SYNTAX Integer32
    MAX-ACCESS read-only
    STATUS current
    DESCRIPTION "Closed Loop Table"
    ::= { AssignTable-20 3 }

SelectedFan-20 OBJECT-TYPE
    SYNTAX DisplayString
    MAX-ACCESS read-only
    STATUS current
    DESCRIPTION "Selected Fan"
    ::= { AssignTable-20 4 }

AssignTable-21 OBJECT-TYPE
    SYNTAX DisplayString
    MAX-ACCESS read-only
    STATUS current
    DESCRIPTION "Fan Assignment Table"
    ::= { FanAssignment 21 }

TempSensor-21 OBJECT-TYPE
    SYNTAX DisplayString
    MAX-ACCESS read-only
    STATUS current
    DESCRIPTION "Temperature Sensor"
    ::= { AssignTable-21 1 }

OpenLoopTable-21 OBJECT-TYPE
    SYNTAX Integer32
    MAX-ACCESS read-only
    STATUS current
    DESCRIPTION "Open Loop Table"
    ::= { AssignTable-21 2 }

ClosedLoopTable-21 OBJECT-TYPE
    SYNTAX Integer32
    MAX-ACCESS read-only
    STATUS current
    DESCRIPTION "Closed Loop Table"
    ::= { AssignTable-21 3 }

SelectedFan-21 OBJECT-TYPE
    SYNTAX DisplayString
    MAX-ACCESS read-only
    STATUS current
    DESCRIPTION "Selected Fan"
    ::= { AssignTable-21 4 }

AssignTable-22 OBJECT-TYPE
    SYNTAX DisplayString
    MAX-ACCESS read-only
    STATUS current
    DESCRIPTION "Fan Assignment Table"
    ::= { FanAssignment 22 }

TempSensor-22 OBJECT-TYPE
    SYNTAX DisplayString
    MAX-ACCESS read-only
    STATUS current
    DESCRIPTION "Temperature Sensor"
    ::= { AssignTable-22 1 }

OpenLoopTable-22 OBJECT-TYPE
    SYNTAX Integer32
    MAX-ACCESS read-only
    STATUS current
    DESCRIPTION "Open Loop Table"
    ::= { AssignTable-22 2 }

ClosedLoopTable-22 OBJECT-TYPE
    SYNTAX Integer32
    MAX-ACCESS read-only
    STATUS current
    DESCRIPTION "Closed Loop Table"
    ::= { AssignTable-22 3 }

SelectedFan-22 OBJECT-TYPE
    SYNTAX DisplayString
    MAX-ACCESS read-only
    STATUS current
    DESCRIPTION "Selected Fan"
    ::= { AssignTable-22 4 }

AssignTable-23 OBJECT-TYPE
    SYNTAX DisplayString
    MAX-ACCESS read-only
    STATUS current
    DESCRIPTION "Fan Assignment Table"
    ::= { FanAssignment 23 }

TempSensor-23 OBJECT-TYPE
    SYNTAX DisplayString
    MAX-ACCESS read-only
    STATUS current
    DESCRIPTION "Temperature Sensor"
    ::= { AssignTable-23 1 }

OpenLoopTable-23 OBJECT-TYPE
    SYNTAX Integer32
    MAX-ACCESS read-only
    STATUS current
    DESCRIPTION "Open Loop Table"
    ::= { AssignTable-23 2 }

ClosedLoopTable-23 OBJECT-TYPE
    SYNTAX Integer32
    MAX-ACCESS read-only
    STATUS current
    DESCRIPTION "Closed Loop Table"
    ::= { AssignTable-23 3 }

SelectedFan-23 OBJECT-TYPE
    SYNTAX DisplayString
    MAX-ACCESS read-only
    STATUS current
    DESCRIPTION "Selected Fan"
    ::= { AssignTable-23 4 }

AssignTable-24 OBJECT-TYPE
    SYNTAX DisplayString
    MAX-ACCESS read-only
    STATUS current
    DESCRIPTION "Fan Assignment Table"
    ::= { FanAssignment 24 }

TempSensor-24 OBJECT-TYPE
    SYNTAX DisplayString
    MAX-ACCESS read-only
    STATUS current
    DESCRIPTION "Temperature Sensor"
    ::= { AssignTable-24 1 }

OpenLoopTable-24 OBJECT-TYPE
    SYNTAX Integer32
    MAX-ACCESS read-only
    STATUS current
    DESCRIPTION "Open Loop Table"
    ::= { AssignTable-24 2 }

ClosedLoopTable-24 OBJECT-TYPE
    SYNTAX Integer32
    MAX-ACCESS read-only
    STATUS current
    DESCRIPTION "Closed Loop Table"
    ::= { AssignTable-24 3 }

SelectedFan-24 OBJECT-TYPE
    SYNTAX DisplayString
    MAX-ACCESS read-only
    STATUS current
    DESCRIPTION "Selected Fan"
    ::= { AssignTable-24 4 }

AssignTable-25 OBJECT-TYPE
    SYNTAX DisplayString
    MAX-ACCESS read-only
    STATUS current
    DESCRIPTION "Fan Assignment Table"
    ::= { FanAssignment 25 }

TempSensor-25 OBJECT-TYPE
    SYNTAX DisplayString
    MAX-ACCESS read-only
    STATUS current
    DESCRIPTION "Temperature Sensor"
    ::= { AssignTable-25 1 }

OpenLoopTable-25 OBJECT-TYPE
    SYNTAX Integer32
    MAX-ACCESS read-only
    STATUS current
    DESCRIPTION "Open Loop Table"
    ::= { AssignTable-25 2 }

ClosedLoopTable-25 OBJECT-TYPE
    SYNTAX Integer32
    MAX-ACCESS read-only
    STATUS current
    DESCRIPTION "Closed Loop Table"
    ::= { AssignTable-25 3 }

SelectedFan-25 OBJECT-TYPE
    SYNTAX DisplayString
    MAX-ACCESS read-only
    STATUS current
    DESCRIPTION "Selected Fan"
    ::= { AssignTable-25 4 }

AssignTable-26 OBJECT-TYPE
    SYNTAX DisplayString
    MAX-ACCESS read-only
    STATUS current
    DESCRIPTION "Fan Assignment Table"
    ::= { FanAssignment 26 }

TempSensor-26 OBJECT-TYPE
    SYNTAX DisplayString
    MAX-ACCESS read-only
    STATUS current
    DESCRIPTION "Temperature Sensor"
    ::= { AssignTable-26 1 }

OpenLoopTable-26 OBJECT-TYPE
    SYNTAX Integer32
    MAX-ACCESS read-only
    STATUS current
    DESCRIPTION "Open Loop Table"
    ::= { AssignTable-26 2 }

ClosedLoopTable-26 OBJECT-TYPE
    SYNTAX Integer32
    MAX-ACCESS read-only
    STATUS current
    DESCRIPTION "Closed Loop Table"
    ::= { AssignTable-26 3 }

SelectedFan-26 OBJECT-TYPE
    SYNTAX DisplayString
    MAX-ACCESS read-only
    STATUS current
    DESCRIPTION "Selected Fan"
    ::= { AssignTable-26 4 }

AssignTable-27 OBJECT-TYPE
    SYNTAX DisplayString
    MAX-ACCESS read-only
    STATUS current
    DESCRIPTION "Fan Assignment Table"
    ::= { FanAssignment 27 }

TempSensor-27 OBJECT-TYPE
    SYNTAX DisplayString
    MAX-ACCESS read-only
    STATUS current
    DESCRIPTION "Temperature Sensor"
    ::= { AssignTable-27 1 }

OpenLoopTable-27 OBJECT-TYPE
    SYNTAX Integer32
    MAX-ACCESS read-only
    STATUS current
    DESCRIPTION "Open Loop Table"
    ::= { AssignTable-27 2 }

ClosedLoopTable-27 OBJECT-TYPE
    SYNTAX Integer32
    MAX-ACCESS read-only
    STATUS current
    DESCRIPTION "Closed Loop Table"
    ::= { AssignTable-27 3 }

SelectedFan-27 OBJECT-TYPE
    SYNTAX DisplayString
    MAX-ACCESS read-only
    STATUS current
    DESCRIPTION "Selected Fan"
    ::= { AssignTable-27 4 }

AssignTable-28 OBJECT-TYPE
    SYNTAX DisplayString
    MAX-ACCESS read-only
    STATUS current
    DESCRIPTION "Fan Assignment Table"
    ::= { FanAssignment 28 }

TempSensor-28 OBJECT-TYPE
    SYNTAX DisplayString
    MAX-ACCESS read-only
    STATUS current
    DESCRIPTION "Temperature Sensor"
    ::= { AssignTable-28 1 }

OpenLoopTable-28 OBJECT-TYPE
    SYNTAX Integer32
    MAX-ACCESS read-only
    STATUS current
    DESCRIPTION "Open Loop Table"
    ::= { AssignTable-28 2 }

ClosedLoopTable-28 OBJECT-TYPE
    SYNTAX Integer32
    MAX-ACCESS read-only
    STATUS current
    DESCRIPTION "Closed Loop Table"
    ::= { AssignTable-28 3 }

SelectedFan-28 OBJECT-TYPE
    SYNTAX DisplayString
    MAX-ACCESS read-only
    STATUS current
    DESCRIPTION "Selected Fan"
    ::= { AssignTable-28 4 }

AssignTable-29 OBJECT-TYPE
    SYNTAX DisplayString
    MAX-ACCESS read-only
    STATUS current
    DESCRIPTION "Fan Assignment Table"
    ::= { FanAssignment 29 }

TempSensor-29 OBJECT-TYPE
    SYNTAX DisplayString
    MAX-ACCESS read-only
    STATUS current
    DESCRIPTION "Temperature Sensor"
    ::= { AssignTable-29 1 }

OpenLoopTable-29 OBJECT-TYPE
    SYNTAX Integer32
    MAX-ACCESS read-only
    STATUS current
    DESCRIPTION "Open Loop Table"
    ::= { AssignTable-29 2 }

ClosedLoopTable-29 OBJECT-TYPE
    SYNTAX Integer32
    MAX-ACCESS read-only
    STATUS current
    DESCRIPTION "Closed Loop Table"
    ::= { AssignTable-29 3 }

SelectedFan-29 OBJECT-TYPE
    SYNTAX DisplayString
    MAX-ACCESS read-only
    STATUS current
    DESCRIPTION "Selected Fan"
    ::= { AssignTable-29 4 }

AssignTable-30 OBJECT-TYPE
    SYNTAX DisplayString
    MAX-ACCESS read-only
    STATUS current
    DESCRIPTION "Fan Assignment Table"
    ::= { FanAssignment 30 }

TempSensor-30 OBJECT-TYPE
    SYNTAX DisplayString
    MAX-ACCESS read-only
    STATUS current
    DESCRIPTION "Temperature Sensor"
    ::= { AssignTable-30 1 }

OpenLoopTable-30 OBJECT-TYPE
    SYNTAX Integer32
    MAX-ACCESS read-only
    STATUS current
    DESCRIPTION "Open Loop Table"
    ::= { AssignTable-30 2 }

ClosedLoopTable-30 OBJECT-TYPE
    SYNTAX Integer32
    MAX-ACCESS read-only
    STATUS current
    DESCRIPTION "Closed Loop Table"
    ::= { AssignTable-30 3 }

SelectedFan-30 OBJECT-TYPE
    SYNTAX DisplayString
    MAX-ACCESS read-only
    STATUS current
    DESCRIPTION "Selected Fan"
    ::= { AssignTable-30 4 }

AssignTable-31 OBJECT-TYPE
    SYNTAX DisplayString
    MAX-ACCESS read-only
    STATUS current
    DESCRIPTION "Fan Assignment Table"
    ::= { FanAssignment 31 }

TempSensor-31 OBJECT-TYPE
    SYNTAX DisplayString
    MAX-ACCESS read-only
    STATUS current
    DESCRIPTION "Temperature Sensor"
    ::= { AssignTable-31 1 }

OpenLoopTable-31 OBJECT-TYPE
    SYNTAX Integer32
    MAX-ACCESS read-only
    STATUS current
    DESCRIPTION "Open Loop Table"
    ::= { AssignTable-31 2 }

ClosedLoopTable-31 OBJECT-TYPE
    SYNTAX Integer32
    MAX-ACCESS read-only
    STATUS current
    DESCRIPTION "Closed Loop Table"
    ::= { AssignTable-31 3 }

SelectedFan-31 OBJECT-TYPE
    SYNTAX DisplayString
    MAX-ACCESS read-only
    STATUS current
    DESCRIPTION "Selected Fan"
    ::= { AssignTable-31 4 }

AssignTable-32 OBJECT-TYPE
    SYNTAX DisplayString
    MAX-ACCESS read-only
    STATUS current
    DESCRIPTION "Fan Assignment Table"
    ::= { FanAssignment 32 }

TempSensor-32 OBJECT-TYPE
    SYNTAX DisplayString
    MAX-ACCESS read-only
    STATUS current
    DESCRIPTION "Temperature Sensor"
    ::= { AssignTable-32 1 }

OpenLoopTable-32 OBJECT-TYPE
    SYNTAX Integer32
    MAX-ACCESS read-only
    STATUS current
    DESCRIPTION "Open Loop Table"
    ::= { AssignTable-32 2 }

ClosedLoopTable-32 OBJECT-TYPE
    SYNTAX Integer32
    MAX-ACCESS read-only
    STATUS current
    DESCRIPTION "Closed Loop Table"
    ::= { AssignTable-32 3 }

SelectedFan-32 OBJECT-TYPE
    SYNTAX DisplayString
    MAX-ACCESS read-only
    STATUS current
    DESCRIPTION "Selected Fan"
    ::= { AssignTable-32 4 }

AssignTable-33 OBJECT-TYPE
    SYNTAX DisplayString
    MAX-ACCESS read-only
    STATUS current
    DESCRIPTION "Fan Assignment Table"
    ::= { FanAssignment 33 }

TempSensor-33 OBJECT-TYPE
    SYNTAX DisplayString
    MAX-ACCESS read-only
    STATUS current
    DESCRIPTION "Temperature Sensor"
    ::= { AssignTable-33 1 }

OpenLoopTable-33 OBJECT-TYPE
    SYNTAX Integer32
    MAX-ACCESS read-only
    STATUS current
    DESCRIPTION "Open Loop Table"
    ::= { AssignTable-33 2 }

ClosedLoopTable-33 OBJECT-TYPE
    SYNTAX Integer32
    MAX-ACCESS read-only
    STATUS current
    DESCRIPTION "Closed Loop Table"
    ::= { AssignTable-33 3 }

SelectedFan-33 OBJECT-TYPE
    SYNTAX DisplayString
    MAX-ACCESS read-only
    STATUS current
    DESCRIPTION "Selected Fan"
    ::= { AssignTable-33 4 }

AssignTable-34 OBJECT-TYPE
    SYNTAX DisplayString
    MAX-ACCESS read-only
    STATUS current
    DESCRIPTION "Fan Assignment Table"
    ::= { FanAssignment 34 }

TempSensor-34 OBJECT-TYPE
    SYNTAX DisplayString
    MAX-ACCESS read-only
    STATUS current
    DESCRIPTION "Temperature Sensor"
    ::= { AssignTable-34 1 }

OpenLoopTable-34 OBJECT-TYPE
    SYNTAX Integer32
    MAX-ACCESS read-only
    STATUS current
    DESCRIPTION "Open Loop Table"
    ::= { AssignTable-34 2 }

ClosedLoopTable-34 OBJECT-TYPE
    SYNTAX Integer32
    MAX-ACCESS read-only
    STATUS current
    DESCRIPTION "Closed Loop Table"
    ::= { AssignTable-34 3 }

SelectedFan-34 OBJECT-TYPE
    SYNTAX DisplayString
    MAX-ACCESS read-only
    STATUS current
    DESCRIPTION "Selected Fan"
    ::= { AssignTable-34 4 }

AssignTable-35 OBJECT-TYPE
    SYNTAX DisplayString
    MAX-ACCESS read-only
    STATUS current
    DESCRIPTION "Fan Assignment Table"
    ::= { FanAssignment 35 }

TempSensor-35 OBJECT-TYPE
    SYNTAX DisplayString
    MAX-ACCESS read-only
    STATUS current
    DESCRIPTION "Temperature Sensor"
    ::= { AssignTable-35 1 }

OpenLoopTable-35 OBJECT-TYPE
    SYNTAX Integer32
    MAX-ACCESS read-only
    STATUS current
    DESCRIPTION "Open Loop Table"
    ::= { AssignTable-35 2 }

ClosedLoopTable-35 OBJECT-TYPE
    SYNTAX Integer32
    MAX-ACCESS read-only
    STATUS current
    DESCRIPTION "Closed Loop Table"
    ::= { AssignTable-35 3 }

SelectedFan-35 OBJECT-TYPE
    SYNTAX DisplayString
    MAX-ACCESS read-only
    STATUS current
    DESCRIPTION "Selected Fan"
    ::= { AssignTable-35 4 }

AssignTable-36 OBJECT-TYPE
    SYNTAX DisplayString
    MAX-ACCESS read-only
    STATUS current
    DESCRIPTION "Fan Assignment Table"
    ::= { FanAssignment 36 }

TempSensor-36 OBJECT-TYPE
    SYNTAX DisplayString
    MAX-ACCESS read-only
    STATUS current
    DESCRIPTION "Temperature Sensor"
    ::= { AssignTable-36 1 }

OpenLoopTable-36 OBJECT-TYPE
    SYNTAX Integer32
    MAX-ACCESS read-only
    STATUS current
    DESCRIPTION "Open Loop Table"
    ::= { AssignTable-36 2 }

ClosedLoopTable-36 OBJECT-TYPE
    SYNTAX Integer32
    MAX-ACCESS read-only
    STATUS current
    DESCRIPTION "Closed Loop Table"
    ::= { AssignTable-36 3 }

SelectedFan-36 OBJECT-TYPE
    SYNTAX DisplayString
    MAX-ACCESS read-only
    STATUS current
    DESCRIPTION "Selected Fan"
    ::= { AssignTable-36 4 }

AssignTable-37 OBJECT-TYPE
    SYNTAX DisplayString
    MAX-ACCESS read-only
    STATUS current
    DESCRIPTION "Fan Assignment Table"
    ::= { FanAssignment 37 }

TempSensor-37 OBJECT-TYPE
    SYNTAX DisplayString
    MAX-ACCESS read-only
    STATUS current
    DESCRIPTION "Temperature Sensor"
    ::= { AssignTable-37 1 }

OpenLoopTable-37 OBJECT-TYPE
    SYNTAX Integer32
    MAX-ACCESS read-only
    STATUS current
    DESCRIPTION "Open Loop Table"
    ::= { AssignTable-37 2 }

ClosedLoopTable-37 OBJECT-TYPE
    SYNTAX Integer32
    MAX-ACCESS read-only
    STATUS current
    DESCRIPTION "Closed Loop Table"
    ::= { AssignTable-37 3 }

SelectedFan-37 OBJECT-TYPE
    SYNTAX DisplayString
    MAX-ACCESS read-only
    STATUS current
    DESCRIPTION "Selected Fan"
    ::= { AssignTable-37 4 }

AssignTable-38 OBJECT-TYPE
    SYNTAX DisplayString
    MAX-ACCESS read-only
    STATUS current
    DESCRIPTION "Fan Assignment Table"
    ::= { FanAssignment 38 }

TempSensor-38 OBJECT-TYPE
    SYNTAX DisplayString
    MAX-ACCESS read-only
    STATUS current
    DESCRIPTION "Temperature Sensor"
    ::= { AssignTable-38 1 }

OpenLoopTable-38 OBJECT-TYPE
    SYNTAX Integer32
    MAX-ACCESS read-only
    STATUS current
    DESCRIPTION "Open Loop Table"
    ::= { AssignTable-38 2 }

ClosedLoopTable-38 OBJECT-TYPE
    SYNTAX Integer32
    MAX-ACCESS read-only
    STATUS current
    DESCRIPTION "Closed Loop Table"
    ::= { AssignTable-38 3 }

SelectedFan-38 OBJECT-TYPE
    SYNTAX DisplayString
    MAX-ACCESS read-only
    STATUS current
    DESCRIPTION "Selected Fan"
    ::= { AssignTable-38 4 }

AssignTable-39 OBJECT-TYPE
    SYNTAX DisplayString
    MAX-ACCESS read-only
    STATUS current
    DESCRIPTION "Fan Assignment Table"
    ::= { FanAssignment 39 }

TempSensor-39 OBJECT-TYPE
    SYNTAX DisplayString
    MAX-ACCESS read-only
    STATUS current
    DESCRIPTION "Temperature Sensor"
    ::= { AssignTable-39 1 }

OpenLoopTable-39 OBJECT-TYPE
    SYNTAX Integer32
    MAX-ACCESS read-only
    STATUS current
    DESCRIPTION "Open Loop Table"
    ::= { AssignTable-39 2 }

ClosedLoopTable-39 OBJECT-TYPE
    SYNTAX Integer32
    MAX-ACCESS read-only
    STATUS current
    DESCRIPTION "Closed Loop Table"
    ::= { AssignTable-39 3 }

SelectedFan-39 OBJECT-TYPE
    SYNTAX DisplayString
    MAX-ACCESS read-only
    STATUS current
    DESCRIPTION "Selected Fan"
    ::= { AssignTable-39 4 }

AssignTable-40 OBJECT-TYPE
    SYNTAX DisplayString
    MAX-ACCESS read-only
    STATUS current
    DESCRIPTION "Fan Assignment Table"
    ::= { FanAssignment 40 }

TempSensor-40 OBJECT-TYPE
    SYNTAX DisplayString
    MAX-ACCESS read-only
    STATUS current
    DESCRIPTION "Temperature Sensor"
    ::= { AssignTable-40 1 }

OpenLoopTable-40 OBJECT-TYPE
    SYNTAX Integer32
    MAX-ACCESS read-only
    STATUS current
    DESCRIPTION "Open Loop Table"
    ::= { AssignTable-40 2 }

ClosedLoopTable-40 OBJECT-TYPE
    SYNTAX Integer32
    MAX-ACCESS read-only
    STATUS current
    DESCRIPTION "Closed Loop Table"
    ::= { AssignTable-40 3 }

SelectedFan-40 OBJECT-TYPE
    SYNTAX DisplayString
    MAX-ACCESS read-only
    STATUS current
    DESCRIPTION "Selected Fan"
    ::= { AssignTable-40 4 }

AssignTable-41 OBJECT-TYPE
    SYNTAX DisplayString
    MAX-ACCESS read-only
    STATUS current
    DESCRIPTION "Fan Assignment Table"
    ::= { FanAssignment 41 }

TempSensor-41 OBJECT-TYPE
    SYNTAX DisplayString
    MAX-ACCESS read-only
    STATUS current
    DESCRIPTION "Temperature Sensor"
    ::= { AssignTable-41 1 }

OpenLoopTable-41 OBJECT-TYPE
    SYNTAX Integer32
    MAX-ACCESS read-only
    STATUS current
    DESCRIPTION "Open Loop Table"
    ::= { AssignTable-41 2 }

ClosedLoopTable-41 OBJECT-TYPE
    SYNTAX Integer32
    MAX-ACCESS read-only
    STATUS current
    DESCRIPTION "Closed Loop Table"
    ::= { AssignTable-41 3 }

SelectedFan-41 OBJECT-TYPE
    SYNTAX DisplayString
    MAX-ACCESS read-only
    STATUS current
    DESCRIPTION "Selected Fan"
    ::= { AssignTable-41 4 }

AssignTable-42 OBJECT-TYPE
    SYNTAX DisplayString
    MAX-ACCESS read-only
    STATUS current
    DESCRIPTION "Fan Assignment Table"
    ::= { FanAssignment 42 }

TempSensor-42 OBJECT-TYPE
    SYNTAX DisplayString
    MAX-ACCESS read-only
    STATUS current
    DESCRIPTION "Temperature Sensor"
    ::= { AssignTable-42 1 }

OpenLoopTable-42 OBJECT-TYPE
    SYNTAX Integer32
    MAX-ACCESS read-only
    STATUS current
    DESCRIPTION "Open Loop Table"
    ::= { AssignTable-42 2 }

ClosedLoopTable-42 OBJECT-TYPE
    SYNTAX Integer32
    MAX-ACCESS read-only
    STATUS current
    DESCRIPTION "Closed Loop Table"
    ::= { AssignTable-42 3 }

SelectedFan-42 OBJECT-TYPE
    SYNTAX DisplayString
    MAX-ACCESS read-only
    STATUS current
    DESCRIPTION "Selected Fan"
    ::= { AssignTable-42 4 }

AssignTable-43 OBJECT-TYPE
    SYNTAX DisplayString
    MAX-ACCESS read-only
    STATUS current
    DESCRIPTION "Fan Assignment Table"
    ::= { FanAssignment 43 }

TempSensor-43 OBJECT-TYPE
    SYNTAX DisplayString
    MAX-ACCESS read-only
    STATUS current
    DESCRIPTION "Temperature Sensor"
    ::= { AssignTable-43 1 }

OpenLoopTable-43 OBJECT-TYPE
    SYNTAX Integer32
    MAX-ACCESS read-only
    STATUS current
    DESCRIPTION "Open Loop Table"
    ::= { AssignTable-43 2 }

ClosedLoopTable-43 OBJECT-TYPE
    SYNTAX Integer32
    MAX-ACCESS read-only
    STATUS current
    DESCRIPTION "Closed Loop Table"
    ::= { AssignTable-43 3 }

SelectedFan-43 OBJECT-TYPE
    SYNTAX DisplayString
    MAX-ACCESS read-only
    STATUS current
    DESCRIPTION "Selected Fan"
    ::= { AssignTable-43 4 }

AssignTable-44 OBJECT-TYPE
    SYNTAX DisplayString
    MAX-ACCESS read-only
    STATUS current
    DESCRIPTION "Fan Assignment Table"
    ::= { FanAssignment 44 }

TempSensor-44 OBJECT-TYPE
    SYNTAX DisplayString
    MAX-ACCESS read-only
    STATUS current
    DESCRIPTION "Temperature Sensor"
    ::= { AssignTable-44 1 }

OpenLoopTable-44 OBJECT-TYPE
    SYNTAX Integer32
    MAX-ACCESS read-only
    STATUS current
    DESCRIPTION "Open Loop Table"
    ::= { AssignTable-44 2 }

ClosedLoopTable-44 OBJECT-TYPE
    SYNTAX Integer32
    MAX-ACCESS read-only
    STATUS current
    DESCRIPTION "Closed Loop Table"
    ::= { AssignTable-44 3 }

SelectedFan-44 OBJECT-TYPE
    SYNTAX DisplayString
    MAX-ACCESS read-only
    STATUS current
    DESCRIPTION "Selected Fan"
    ::= { AssignTable-44 4 }

AssignTable-45 OBJECT-TYPE
    SYNTAX DisplayString
    MAX-ACCESS read-only
    STATUS current
    DESCRIPTION "Fan Assignment Table"
    ::= { FanAssignment 45 }

TempSensor-45 OBJECT-TYPE
    SYNTAX DisplayString
    MAX-ACCESS read-only
    STATUS current
    DESCRIPTION "Temperature Sensor"
    ::= { AssignTable-45 1 }

OpenLoopTable-45 OBJECT-TYPE
    SYNTAX Integer32
    MAX-ACCESS read-only
    STATUS current
    DESCRIPTION "Open Loop Table"
    ::= { AssignTable-45 2 }

ClosedLoopTable-45 OBJECT-TYPE
    SYNTAX Integer32
    MAX-ACCESS read-only
    STATUS current
    DESCRIPTION "Closed Loop Table"
    ::= { AssignTable-45 3 }

SelectedFan-45 OBJECT-TYPE
    SYNTAX DisplayString
    MAX-ACCESS read-only
    STATUS current
    DESCRIPTION "Selected Fan"
    ::= { AssignTable-45 4 }

AssignTable-46 OBJECT-TYPE
    SYNTAX DisplayString
    MAX-ACCESS read-only
    STATUS current
    DESCRIPTION "Fan Assignment Table"
    ::= { FanAssignment 46 }

TempSensor-46 OBJECT-TYPE
    SYNTAX DisplayString
    MAX-ACCESS read-only
    STATUS current
    DESCRIPTION "Temperature Sensor"
    ::= { AssignTable-46 1 }

OpenLoopTable-46 OBJECT-TYPE
    SYNTAX Integer32
    MAX-ACCESS read-only
    STATUS current
    DESCRIPTION "Open Loop Table"
    ::= { AssignTable-46 2 }

ClosedLoopTable-46 OBJECT-TYPE
    SYNTAX Integer32
    MAX-ACCESS read-only
    STATUS current
    DESCRIPTION "Closed Loop Table"
    ::= { AssignTable-46 3 }

SelectedFan-46 OBJECT-TYPE
    SYNTAX DisplayString
    MAX-ACCESS read-only
    STATUS current
    DESCRIPTION "Selected Fan"
    ::= { AssignTable-46 4 }

AssignTable-47 OBJECT-TYPE
    SYNTAX DisplayString
    MAX-ACCESS read-only
    STATUS current
    DESCRIPTION "Fan Assignment Table"
    ::= { FanAssignment 47 }

TempSensor-47 OBJECT-TYPE
    SYNTAX DisplayString
    MAX-ACCESS read-only
    STATUS current
    DESCRIPTION "Temperature Sensor"
    ::= { AssignTable-47 1 }

OpenLoopTable-47 OBJECT-TYPE
    SYNTAX Integer32
    MAX-ACCESS read-only
    STATUS current
    DESCRIPTION "Open Loop Table"
    ::= { AssignTable-47 2 }

ClosedLoopTable-47 OBJECT-TYPE
    SYNTAX Integer32
    MAX-ACCESS read-only
    STATUS current
    DESCRIPTION "Closed Loop Table"
    ::= { AssignTable-47 3 }

SelectedFan-47 OBJECT-TYPE
    SYNTAX DisplayString
    MAX-ACCESS read-only
    STATUS current
    DESCRIPTION "Selected Fan"
    ::= { AssignTable-47 4 }

AssignTable-48 OBJECT-TYPE
    SYNTAX DisplayString
    MAX-ACCESS read-only
    STATUS current
    DESCRIPTION "Fan Assignment Table"
    ::= { FanAssignment 48 }

TempSensor-48 OBJECT-TYPE
    SYNTAX DisplayString
    MAX-ACCESS read-only
    STATUS current
    DESCRIPTION "Temperature Sensor"
    ::= { AssignTable-48 1 }

OpenLoopTable-48 OBJECT-TYPE
    SYNTAX Integer32
    MAX-ACCESS read-only
    STATUS current
    DESCRIPTION "Open Loop Table"
    ::= { AssignTable-48 2 }

ClosedLoopTable-48 OBJECT-TYPE
    SYNTAX Integer32
    MAX-ACCESS read-only
    STATUS current
    DESCRIPTION "Closed Loop Table"
    ::= { AssignTable-48 3 }

SelectedFan-48 OBJECT-TYPE
    SYNTAX DisplayString
    MAX-ACCESS read-only
    STATUS current
    DESCRIPTION "Selected Fan"
    ::= { AssignTable-48 4 }

AssignTable-49 OBJECT-TYPE
    SYNTAX DisplayString
    MAX-ACCESS read-only
    STATUS current
    DESCRIPTION "Fan Assignment Table"
    ::= { FanAssignment 49 }

TempSensor-49 OBJECT-TYPE
    SYNTAX DisplayString
    MAX-ACCESS read-only
    STATUS current
    DESCRIPTION "Temperature Sensor"
    ::= { AssignTable-49 1 }

OpenLoopTable-49 OBJECT-TYPE
    SYNTAX Integer32
    MAX-ACCESS read-only
    STATUS current
    DESCRIPTION "Open Loop Table"
    ::= { AssignTable-49 2 }

ClosedLoopTable-49 OBJECT-TYPE
    SYNTAX Integer32
    MAX-ACCESS read-only
    STATUS current
    DESCRIPTION "Closed Loop Table"
    ::= { AssignTable-49 3 }

SelectedFan-49 OBJECT-TYPE
    SYNTAX DisplayString
    MAX-ACCESS read-only
    STATUS current
    DESCRIPTION "Selected Fan"
    ::= { AssignTable-49 4 }

AssignTable-50 OBJECT-TYPE
    SYNTAX DisplayString
    MAX-ACCESS read-only
    STATUS current
    DESCRIPTION "Fan Assignment Table"
    ::= { FanAssignment 50 }

TempSensor-50 OBJECT-TYPE
    SYNTAX DisplayString
    MAX-ACCESS read-only
    STATUS current
    DESCRIPTION "Temperature Sensor"
    ::= { AssignTable-50 1 }

OpenLoopTable-50 OBJECT-TYPE
    SYNTAX Integer32
    MAX-ACCESS read-only
    STATUS current
    DESCRIPTION "Open Loop Table"
    ::= { AssignTable-50 2 }

ClosedLoopTable-50 OBJECT-TYPE
    SYNTAX Integer32
    MAX-ACCESS read-only
    STATUS current
    DESCRIPTION "Closed Loop Table"
    ::= { AssignTable-50 3 }

SelectedFan-50 OBJECT-TYPE
    SYNTAX DisplayString
    MAX-ACCESS read-only
    STATUS current
    DESCRIPTION "Selected Fan"
    ::= { AssignTable-50 4 }

AssignTable-51 OBJECT-TYPE
    SYNTAX DisplayString
    MAX-ACCESS read-only
    STATUS current
    DESCRIPTION "Fan Assignment Table"
    ::= { FanAssignment 51 }

TempSensor-51 OBJECT-TYPE
    SYNTAX DisplayString
    MAX-ACCESS read-only
    STATUS current
    DESCRIPTION "Temperature Sensor"
    ::= { AssignTable-51 1 }

OpenLoopTable-51 OBJECT-TYPE
    SYNTAX Integer32
    MAX-ACCESS read-only
    STATUS current
    DESCRIPTION "Open Loop Table"
    ::= { AssignTable-51 2 }

ClosedLoopTable-51 OBJECT-TYPE
    SYNTAX Integer32
    MAX-ACCESS read-only
    STATUS current
    DESCRIPTION "Closed Loop Table"
    ::= { AssignTable-51 3 }

SelectedFan-51 OBJECT-TYPE
    SYNTAX DisplayString
    MAX-ACCESS read-only
    STATUS current
    DESCRIPTION "Selected Fan"
    ::= { AssignTable-51 4 }

AssignTable-52 OBJECT-TYPE
    SYNTAX DisplayString
    MAX-ACCESS read-only
    STATUS current
    DESCRIPTION "Fan Assignment Table"
    ::= { FanAssignment 52 }

TempSensor-52 OBJECT-TYPE
    SYNTAX DisplayString
    MAX-ACCESS read-only
    STATUS current
    DESCRIPTION "Temperature Sensor"
    ::= { AssignTable-52 1 }

OpenLoopTable-52 OBJECT-TYPE
    SYNTAX Integer32
    MAX-ACCESS read-only
    STATUS current
    DESCRIPTION "Open Loop Table"
    ::= { AssignTable-52 2 }

ClosedLoopTable-52 OBJECT-TYPE
    SYNTAX Integer32
    MAX-ACCESS read-only
    STATUS current
    DESCRIPTION "Closed Loop Table"
    ::= { AssignTable-52 3 }

SelectedFan-52 OBJECT-TYPE
    SYNTAX DisplayString
    MAX-ACCESS read-only
    STATUS current
    DESCRIPTION "Selected Fan"
    ::= { AssignTable-52 4 }

AssignTable-53 OBJECT-TYPE
    SYNTAX DisplayString
    MAX-ACCESS read-only
    STATUS current
    DESCRIPTION "Fan Assignment Table"
    ::= { FanAssignment 53 }

TempSensor-53 OBJECT-TYPE
    SYNTAX DisplayString
    MAX-ACCESS read-only
    STATUS current
    DESCRIPTION "Temperature Sensor"
    ::= { AssignTable-53 1 }

OpenLoopTable-53 OBJECT-TYPE
    SYNTAX Integer32
    MAX-ACCESS read-only
    STATUS current
    DESCRIPTION "Open Loop Table"
    ::= { AssignTable-53 2 }

ClosedLoopTable-53 OBJECT-TYPE
    SYNTAX Integer32
    MAX-ACCESS read-only
    STATUS current
    DESCRIPTION "Closed Loop Table"
    ::= { AssignTable-53 3 }

SelectedFan-53 OBJECT-TYPE
    SYNTAX DisplayString
    MAX-ACCESS read-only
    STATUS current
    DESCRIPTION "Selected Fan"
    ::= { AssignTable-53 4 }

AssignTable-54 OBJECT-TYPE
    SYNTAX DisplayString
    MAX-ACCESS read-only
    STATUS current
    DESCRIPTION "Fan Assignment Table"
    ::= { FanAssignment 54 }

TempSensor-54 OBJECT-TYPE
    SYNTAX DisplayString
    MAX-ACCESS read-only
    STATUS current
    DESCRIPTION "Temperature Sensor"
    ::= { AssignTable-54 1 }

OpenLoopTable-54 OBJECT-TYPE
    SYNTAX Integer32
    MAX-ACCESS read-only
    STATUS current
    DESCRIPTION "Open Loop Table"
    ::= { AssignTable-54 2 }

ClosedLoopTable-54 OBJECT-TYPE
    SYNTAX Integer32
    MAX-ACCESS read-only
    STATUS current
    DESCRIPTION "Closed Loop Table"
    ::= { AssignTable-54 3 }

SelectedFan-54 OBJECT-TYPE
    SYNTAX DisplayString
    MAX-ACCESS read-only
    STATUS current
    DESCRIPTION "Selected Fan"
    ::= { AssignTable-54 4 }

AssignTable-55 OBJECT-TYPE
    SYNTAX DisplayString
    MAX-ACCESS read-only
    STATUS current
    DESCRIPTION "Fan Assignment Table"
    ::= { FanAssignment 55 }

TempSensor-55 OBJECT-TYPE
    SYNTAX DisplayString
    MAX-ACCESS read-only
    STATUS current
    DESCRIPTION "Temperature Sensor"
    ::= { AssignTable-55 1 }

OpenLoopTable-55 OBJECT-TYPE
    SYNTAX Integer32
    MAX-ACCESS read-only
    STATUS current
    DESCRIPTION "Open Loop Table"
    ::= { AssignTable-55 2 }

ClosedLoopTable-55 OBJECT-TYPE
    SYNTAX Integer32
    MAX-ACCESS read-only
    STATUS current
    DESCRIPTION "Closed Loop Table"
    ::= { AssignTable-55 3 }

SelectedFan-55 OBJECT-TYPE
    SYNTAX DisplayString
    MAX-ACCESS read-only
    STATUS current
    DESCRIPTION "Selected Fan"
    ::= { AssignTable-55 4 }

AssignTable-56 OBJECT-TYPE
    SYNTAX DisplayString
    MAX-ACCESS read-only
    STATUS current
    DESCRIPTION "Fan Assignment Table"
    ::= { FanAssignment 56 }

TempSensor-56 OBJECT-TYPE
    SYNTAX DisplayString
    MAX-ACCESS read-only
    STATUS current
    DESCRIPTION "Temperature Sensor"
    ::= { AssignTable-56 1 }

OpenLoopTable-56 OBJECT-TYPE
    SYNTAX Integer32
    MAX-ACCESS read-only
    STATUS current
    DESCRIPTION "Open Loop Table"
    ::= { AssignTable-56 2 }

ClosedLoopTable-56 OBJECT-TYPE
    SYNTAX Integer32
    MAX-ACCESS read-only
    STATUS current
    DESCRIPTION "Closed Loop Table"
    ::= { AssignTable-56 3 }

SelectedFan-56 OBJECT-TYPE
    SYNTAX DisplayString
    MAX-ACCESS read-only
    STATUS current
    DESCRIPTION "Selected Fan"
    ::= { AssignTable-56 4 }

AssignTable-57 OBJECT-TYPE
    SYNTAX DisplayString
    MAX-ACCESS read-only
    STATUS current
    DESCRIPTION "Fan Assignment Table"
    ::= { FanAssignment 57 }

TempSensor-57 OBJECT-TYPE
    SYNTAX DisplayString
    MAX-ACCESS read-only
    STATUS current
    DESCRIPTION "Temperature Sensor"
    ::= { AssignTable-57 1 }

OpenLoopTable-57 OBJECT-TYPE
    SYNTAX Integer32
    MAX-ACCESS read-only
    STATUS current
    DESCRIPTION "Open Loop Table"
    ::= { AssignTable-57 2 }

ClosedLoopTable-57 OBJECT-TYPE
    SYNTAX Integer32
    MAX-ACCESS read-only
    STATUS current
    DESCRIPTION "Closed Loop Table"
    ::= { AssignTable-57 3 }

SelectedFan-57 OBJECT-TYPE
    SYNTAX DisplayString
    MAX-ACCESS read-only
    STATUS current
    DESCRIPTION "Selected Fan"
    ::= { AssignTable-57 4 }

AssignTable-58 OBJECT-TYPE
    SYNTAX DisplayString
    MAX-ACCESS read-only
    STATUS current
    DESCRIPTION "Fan Assignment Table"
    ::= { FanAssignment 58 }

TempSensor-58 OBJECT-TYPE
    SYNTAX DisplayString
    MAX-ACCESS read-only
    STATUS current
    DESCRIPTION "Temperature Sensor"
    ::= { AssignTable-58 1 }

OpenLoopTable-58 OBJECT-TYPE
    SYNTAX Integer32
    MAX-ACCESS read-only
    STATUS current
    DESCRIPTION "Open Loop Table"
    ::= { AssignTable-58 2 }

ClosedLoopTable-58 OBJECT-TYPE
    SYNTAX Integer32
    MAX-ACCESS read-only
    STATUS current
    DESCRIPTION "Closed Loop Table"
    ::= { AssignTable-58 3 }

SelectedFan-58 OBJECT-TYPE
    SYNTAX DisplayString
    MAX-ACCESS read-only
    STATUS current
    DESCRIPTION "Selected Fan"
    ::= { AssignTable-58 4 }

AssignTable-59 OBJECT-TYPE
    SYNTAX DisplayString
    MAX-ACCESS read-only
    STATUS current
    DESCRIPTION "Fan Assignment Table"
    ::= { FanAssignment 59 }

TempSensor-59 OBJECT-TYPE
    SYNTAX DisplayString
    MAX-ACCESS read-only
    STATUS current
    DESCRIPTION "Temperature Sensor"
    ::= { AssignTable-59 1 }

OpenLoopTable-59 OBJECT-TYPE
    SYNTAX Integer32
    MAX-ACCESS read-only
    STATUS current
    DESCRIPTION "Open Loop Table"
    ::= { AssignTable-59 2 }

ClosedLoopTable-59 OBJECT-TYPE
    SYNTAX Integer32
    MAX-ACCESS read-only
    STATUS current
    DESCRIPTION "Closed Loop Table"
    ::= { AssignTable-59 3 }

SelectedFan-59 OBJECT-TYPE
    SYNTAX DisplayString
    MAX-ACCESS read-only
    STATUS current
    DESCRIPTION "Selected Fan"
    ::= { AssignTable-59 4 }

AssignTable-60 OBJECT-TYPE
    SYNTAX DisplayString
    MAX-ACCESS read-only
    STATUS current
    DESCRIPTION "Fan Assignment Table"
    ::= { FanAssignment 60 }

TempSensor-60 OBJECT-TYPE
    SYNTAX DisplayString
    MAX-ACCESS read-only
    STATUS current
    DESCRIPTION "Temperature Sensor"
    ::= { AssignTable-60 1 }

OpenLoopTable-60 OBJECT-TYPE
    SYNTAX Integer32
    MAX-ACCESS read-only
    STATUS current
    DESCRIPTION "Open Loop Table"
    ::= { AssignTable-60 2 }

ClosedLoopTable-60 OBJECT-TYPE
    SYNTAX Integer32
    MAX-ACCESS read-only
    STATUS current
    DESCRIPTION "Closed Loop Table"
    ::= { AssignTable-60 3 }

SelectedFan-60 OBJECT-TYPE
    SYNTAX DisplayString
    MAX-ACCESS read-only
    STATUS current
    DESCRIPTION "Selected Fan"
    ::= { AssignTable-60 4 }

AssignTable-61 OBJECT-TYPE
    SYNTAX DisplayString
    MAX-ACCESS read-only
    STATUS current
    DESCRIPTION "Fan Assignment Table"
    ::= { FanAssignment 61 }

TempSensor-61 OBJECT-TYPE
    SYNTAX DisplayString
    MAX-ACCESS read-only
    STATUS current
    DESCRIPTION "Temperature Sensor"
    ::= { AssignTable-61 1 }

OpenLoopTable-61 OBJECT-TYPE
    SYNTAX Integer32
    MAX-ACCESS read-only
    STATUS current
    DESCRIPTION "Open Loop Table"
    ::= { AssignTable-61 2 }

ClosedLoopTable-61 OBJECT-TYPE
    SYNTAX Integer32
    MAX-ACCESS read-only
    STATUS current
    DESCRIPTION "Closed Loop Table"
    ::= { AssignTable-61 3 }

SelectedFan-61 OBJECT-TYPE
    SYNTAX DisplayString
    MAX-ACCESS read-only
    STATUS current
    DESCRIPTION "Selected Fan"
    ::= { AssignTable-61 4 }

AssignTable-62 OBJECT-TYPE
    SYNTAX DisplayString
    MAX-ACCESS read-only
    STATUS current
    DESCRIPTION "Fan Assignment Table"
    ::= { FanAssignment 62 }

TempSensor-62 OBJECT-TYPE
    SYNTAX DisplayString
    MAX-ACCESS read-only
    STATUS current
    DESCRIPTION "Temperature Sensor"
    ::= { AssignTable-62 1 }

OpenLoopTable-62 OBJECT-TYPE
    SYNTAX Integer32
    MAX-ACCESS read-only
    STATUS current
    DESCRIPTION "Open Loop Table"
    ::= { AssignTable-62 2 }

ClosedLoopTable-62 OBJECT-TYPE
    SYNTAX Integer32
    MAX-ACCESS read-only
    STATUS current
    DESCRIPTION "Closed Loop Table"
    ::= { AssignTable-62 3 }

SelectedFan-62 OBJECT-TYPE
    SYNTAX DisplayString
    MAX-ACCESS read-only
    STATUS current
    DESCRIPTION "Selected Fan"
    ::= { AssignTable-62 4 }

AssignTable-63 OBJECT-TYPE
    SYNTAX DisplayString
    MAX-ACCESS read-only
    STATUS current
    DESCRIPTION "Fan Assignment Table"
    ::= { FanAssignment 63 }

TempSensor-63 OBJECT-TYPE
    SYNTAX DisplayString
    MAX-ACCESS read-only
    STATUS current
    DESCRIPTION "Temperature Sensor"
    ::= { AssignTable-63 1 }

OpenLoopTable-63 OBJECT-TYPE
    SYNTAX Integer32
    MAX-ACCESS read-only
    STATUS current
    DESCRIPTION "Open Loop Table"
    ::= { AssignTable-63 2 }

ClosedLoopTable-63 OBJECT-TYPE
    SYNTAX Integer32
    MAX-ACCESS read-only
    STATUS current
    DESCRIPTION "Closed Loop Table"
    ::= { AssignTable-63 3 }

SelectedFan-63 OBJECT-TYPE
    SYNTAX DisplayString
    MAX-ACCESS read-only
    STATUS current
    DESCRIPTION "Selected Fan"
    ::= { AssignTable-63 4 }

AssignTable-64 OBJECT-TYPE
    SYNTAX DisplayString
    MAX-ACCESS read-only
    STATUS current
    DESCRIPTION "Fan Assignment Table"
    ::= { FanAssignment 64 }

TempSensor-64 OBJECT-TYPE
    SYNTAX DisplayString
    MAX-ACCESS read-only
    STATUS current
    DESCRIPTION "Temperature Sensor"
    ::= { AssignTable-64 1 }

OpenLoopTable-64 OBJECT-TYPE
    SYNTAX Integer32
    MAX-ACCESS read-only
    STATUS current
    DESCRIPTION "Open Loop Table"
    ::= { AssignTable-64 2 }

ClosedLoopTable-64 OBJECT-TYPE
    SYNTAX Integer32
    MAX-ACCESS read-only
    STATUS current
    DESCRIPTION "Closed Loop Table"
    ::= { AssignTable-64 3 }

SelectedFan-64 OBJECT-TYPE
    SYNTAX DisplayString
    MAX-ACCESS read-only
    STATUS current
    DESCRIPTION "Selected Fan"
    ::= { AssignTable-64 4 }

AssignTable-65 OBJECT-TYPE
    SYNTAX DisplayString
    MAX-ACCESS read-only
    STATUS current
    DESCRIPTION "Fan Assignment Table"
    ::= { FanAssignment 65 }

TempSensor-65 OBJECT-TYPE
    SYNTAX DisplayString
    MAX-ACCESS read-only
    STATUS current
    DESCRIPTION "Temperature Sensor"
    ::= { AssignTable-65 1 }

OpenLoopTable-65 OBJECT-TYPE
    SYNTAX Integer32
    MAX-ACCESS read-only
    STATUS current
    DESCRIPTION "Open Loop Table"
    ::= { AssignTable-65 2 }

ClosedLoopTable-65 OBJECT-TYPE
    SYNTAX Integer32
    MAX-ACCESS read-only
    STATUS current
    DESCRIPTION "Closed Loop Table"
    ::= { AssignTable-65 3 }

SelectedFan-65 OBJECT-TYPE
    SYNTAX DisplayString
    MAX-ACCESS read-only
    STATUS current
    DESCRIPTION "Selected Fan"
    ::= { AssignTable-65 4 }

AssignTable-66 OBJECT-TYPE
    SYNTAX DisplayString
    MAX-ACCESS read-only
    STATUS current
    DESCRIPTION "Fan Assignment Table"
    ::= { FanAssignment 66 }

TempSensor-66 OBJECT-TYPE
    SYNTAX DisplayString
    MAX-ACCESS read-only
    STATUS current
    DESCRIPTION "Temperature Sensor"
    ::= { AssignTable-66 1 }

OpenLoopTable-66 OBJECT-TYPE
    SYNTAX Integer32
    MAX-ACCESS read-only
    STATUS current
    DESCRIPTION "Open Loop Table"
    ::= { AssignTable-66 2 }

ClosedLoopTable-66 OBJECT-TYPE
    SYNTAX Integer32
    MAX-ACCESS read-only
    STATUS current
    DESCRIPTION "Closed Loop Table"
    ::= { AssignTable-66 3 }

SelectedFan-66 OBJECT-TYPE
    SYNTAX DisplayString
    MAX-ACCESS read-only
    STATUS current
    DESCRIPTION "Selected Fan"
    ::= { AssignTable-66 4 }

AssignTable-67 OBJECT-TYPE
    SYNTAX DisplayString
    MAX-ACCESS read-only
    STATUS current
    DESCRIPTION "Fan Assignment Table"
    ::= { FanAssignment 67 }

TempSensor-67 OBJECT-TYPE
    SYNTAX DisplayString
    MAX-ACCESS read-only
    STATUS current
    DESCRIPTION "Temperature Sensor"
    ::= { AssignTable-67 1 }

OpenLoopTable-67 OBJECT-TYPE
    SYNTAX Integer32
    MAX-ACCESS read-only
    STATUS current
    DESCRIPTION "Open Loop Table"
    ::= { AssignTable-67 2 }

ClosedLoopTable-67 OBJECT-TYPE
    SYNTAX Integer32
    MAX-ACCESS read-only
    STATUS current
    DESCRIPTION "Closed Loop Table"
    ::= { AssignTable-67 3 }

SelectedFan-67 OBJECT-TYPE
    SYNTAX DisplayString
    MAX-ACCESS read-only
    STATUS current
    DESCRIPTION "Selected Fan"
    ::= { AssignTable-67 4 }

AssignTable-68 OBJECT-TYPE
    SYNTAX DisplayString
    MAX-ACCESS read-only
    STATUS current
    DESCRIPTION "Fan Assignment Table"
    ::= { FanAssignment 68 }

TempSensor-68 OBJECT-TYPE
    SYNTAX DisplayString
    MAX-ACCESS read-only
    STATUS current
    DESCRIPTION "Temperature Sensor"
    ::= { AssignTable-68 1 }

OpenLoopTable-68 OBJECT-TYPE
    SYNTAX Integer32
    MAX-ACCESS read-only
    STATUS current
    DESCRIPTION "Open Loop Table"
    ::= { AssignTable-68 2 }

ClosedLoopTable-68 OBJECT-TYPE
    SYNTAX Integer32
    MAX-ACCESS read-only
    STATUS current
    DESCRIPTION "Closed Loop Table"
    ::= { AssignTable-68 3 }

SelectedFan-68 OBJECT-TYPE
    SYNTAX DisplayString
    MAX-ACCESS read-only
    STATUS current
    DESCRIPTION "Selected Fan"
    ::= { AssignTable-68 4 }

AssignTable-69 OBJECT-TYPE
    SYNTAX DisplayString
    MAX-ACCESS read-only
    STATUS current
    DESCRIPTION "Fan Assignment Table"
    ::= { FanAssignment 69 }

TempSensor-69 OBJECT-TYPE
    SYNTAX DisplayString
    MAX-ACCESS read-only
    STATUS current
    DESCRIPTION "Temperature Sensor"
    ::= { AssignTable-69 1 }

OpenLoopTable-69 OBJECT-TYPE
    SYNTAX Integer32
    MAX-ACCESS read-only
    STATUS current
    DESCRIPTION "Open Loop Table"
    ::= { AssignTable-69 2 }

ClosedLoopTable-69 OBJECT-TYPE
    SYNTAX Integer32
    MAX-ACCESS read-only
    STATUS current
    DESCRIPTION "Closed Loop Table"
    ::= { AssignTable-69 3 }

SelectedFan-69 OBJECT-TYPE
    SYNTAX DisplayString
    MAX-ACCESS read-only
    STATUS current
    DESCRIPTION "Selected Fan"
    ::= { AssignTable-69 4 }

AssignTable-70 OBJECT-TYPE
    SYNTAX DisplayString
    MAX-ACCESS read-only
    STATUS current
    DESCRIPTION "Fan Assignment Table"
    ::= { FanAssignment 70 }

TempSensor-70 OBJECT-TYPE
    SYNTAX DisplayString
    MAX-ACCESS read-only
    STATUS current
    DESCRIPTION "Temperature Sensor"
    ::= { AssignTable-70 1 }

OpenLoopTable-70 OBJECT-TYPE
    SYNTAX Integer32
    MAX-ACCESS read-only
    STATUS current
    DESCRIPTION "Open Loop Table"
    ::= { AssignTable-70 2 }

ClosedLoopTable-70 OBJECT-TYPE
    SYNTAX Integer32
    MAX-ACCESS read-only
    STATUS current
    DESCRIPTION "Closed Loop Table"
    ::= { AssignTable-70 3 }

SelectedFan-70 OBJECT-TYPE
    SYNTAX DisplayString
    MAX-ACCESS read-only
    STATUS current
    DESCRIPTION "Selected Fan"
    ::= { AssignTable-70 4 }

AssignTable-71 OBJECT-TYPE
    SYNTAX DisplayString
    MAX-ACCESS read-only
    STATUS current
    DESCRIPTION "Fan Assignment Table"
    ::= { FanAssignment 71 }

TempSensor-71 OBJECT-TYPE
    SYNTAX DisplayString
    MAX-ACCESS read-only
    STATUS current
    DESCRIPTION "Temperature Sensor"
    ::= { AssignTable-71 1 }

OpenLoopTable-71 OBJECT-TYPE
    SYNTAX Integer32
    MAX-ACCESS read-only
    STATUS current
    DESCRIPTION "Open Loop Table"
    ::= { AssignTable-71 2 }

ClosedLoopTable-71 OBJECT-TYPE
    SYNTAX Integer32
    MAX-ACCESS read-only
    STATUS current
    DESCRIPTION "Closed Loop Table"
    ::= { AssignTable-71 3 }

SelectedFan-71 OBJECT-TYPE
    SYNTAX DisplayString
    MAX-ACCESS read-only
    STATUS current
    DESCRIPTION "Selected Fan"
    ::= { AssignTable-71 4 }

AssignTable-72 OBJECT-TYPE
    SYNTAX DisplayString
    MAX-ACCESS read-only
    STATUS current
    DESCRIPTION "Fan Assignment Table"
    ::= { FanAssignment 72 }

TempSensor-72 OBJECT-TYPE
    SYNTAX DisplayString
    MAX-ACCESS read-only
    STATUS current
    DESCRIPTION "Temperature Sensor"
    ::= { AssignTable-72 1 }

OpenLoopTable-72 OBJECT-TYPE
    SYNTAX Integer32
    MAX-ACCESS read-only
    STATUS current
    DESCRIPTION "Open Loop Table"
    ::= { AssignTable-72 2 }

ClosedLoopTable-72 OBJECT-TYPE
    SYNTAX Integer32
    MAX-ACCESS read-only
    STATUS current
    DESCRIPTION "Closed Loop Table"
    ::= { AssignTable-72 3 }

SelectedFan-72 OBJECT-TYPE
    SYNTAX DisplayString
    MAX-ACCESS read-only
    STATUS current
    DESCRIPTION "Selected Fan"
    ::= { AssignTable-72 4 }

AssignTable-73 OBJECT-TYPE
    SYNTAX DisplayString
    MAX-ACCESS read-only
    STATUS current
    DESCRIPTION "Fan Assignment Table"
    ::= { FanAssignment 73 }

TempSensor-73 OBJECT-TYPE
    SYNTAX DisplayString
    MAX-ACCESS read-only
    STATUS current
    DESCRIPTION "Temperature Sensor"
    ::= { AssignTable-73 1 }

OpenLoopTable-73 OBJECT-TYPE
    SYNTAX Integer32
    MAX-ACCESS read-only
    STATUS current
    DESCRIPTION "Open Loop Table"
    ::= { AssignTable-73 2 }

ClosedLoopTable-73 OBJECT-TYPE
    SYNTAX Integer32
    MAX-ACCESS read-only
    STATUS current
    DESCRIPTION "Closed Loop Table"
    ::= { AssignTable-73 3 }

SelectedFan-73 OBJECT-TYPE
    SYNTAX DisplayString
    MAX-ACCESS read-only
    STATUS current
    DESCRIPTION "Selected Fan"
    ::= { AssignTable-73 4 }

AssignTable-74 OBJECT-TYPE
    SYNTAX DisplayString
    MAX-ACCESS read-only
    STATUS current
    DESCRIPTION "Fan Assignment Table"
    ::= { FanAssignment 74 }

TempSensor-74 OBJECT-TYPE
    SYNTAX DisplayString
    MAX-ACCESS read-only
    STATUS current
    DESCRIPTION "Temperature Sensor"
    ::= { AssignTable-74 1 }

OpenLoopTable-74 OBJECT-TYPE
    SYNTAX Integer32
    MAX-ACCESS read-only
    STATUS current
    DESCRIPTION "Open Loop Table"
    ::= { AssignTable-74 2 }

ClosedLoopTable-74 OBJECT-TYPE
    SYNTAX Integer32
    MAX-ACCESS read-only
    STATUS current
    DESCRIPTION "Closed Loop Table"
    ::= { AssignTable-74 3 }

SelectedFan-74 OBJECT-TYPE
    SYNTAX DisplayString
    MAX-ACCESS read-only
    STATUS current
    DESCRIPTION "Selected Fan"
    ::= { AssignTable-74 4 }

AssignTable-75 OBJECT-TYPE
    SYNTAX DisplayString
    MAX-ACCESS read-only
    STATUS current
    DESCRIPTION "Fan Assignment Table"
    ::= { FanAssignment 75 }

TempSensor-75 OBJECT-TYPE
    SYNTAX DisplayString
    MAX-ACCESS read-only
    STATUS current
    DESCRIPTION "Temperature Sensor"
    ::= { AssignTable-75 1 }

OpenLoopTable-75 OBJECT-TYPE
    SYNTAX Integer32
    MAX-ACCESS read-only
    STATUS current
    DESCRIPTION "Open Loop Table"
    ::= { AssignTable-75 2 }

ClosedLoopTable-75 OBJECT-TYPE
    SYNTAX Integer32
    MAX-ACCESS read-only
    STATUS current
    DESCRIPTION "Closed Loop Table"
    ::= { AssignTable-75 3 }

SelectedFan-75 OBJECT-TYPE
    SYNTAX DisplayString
    MAX-ACCESS read-only
    STATUS current
    DESCRIPTION "Selected Fan"
    ::= { AssignTable-75 4 }

AssignTable-76 OBJECT-TYPE
    SYNTAX DisplayString
    MAX-ACCESS read-only
    STATUS current
    DESCRIPTION "Fan Assignment Table"
    ::= { FanAssignment 76 }

TempSensor-76 OBJECT-TYPE
    SYNTAX DisplayString
    MAX-ACCESS read-only
    STATUS current
    DESCRIPTION "Temperature Sensor"
    ::= { AssignTable-76 1 }

OpenLoopTable-76 OBJECT-TYPE
    SYNTAX Integer32
    MAX-ACCESS read-only
    STATUS current
    DESCRIPTION "Open Loop Table"
    ::= { AssignTable-76 2 }

ClosedLoopTable-76 OBJECT-TYPE
    SYNTAX Integer32
    MAX-ACCESS read-only
    STATUS current
    DESCRIPTION "Closed Loop Table"
    ::= { AssignTable-76 3 }

SelectedFan-76 OBJECT-TYPE
    SYNTAX DisplayString
    MAX-ACCESS read-only
    STATUS current
    DESCRIPTION "Selected Fan"
    ::= { AssignTable-76 4 }

AssignTable-77 OBJECT-TYPE
    SYNTAX DisplayString
    MAX-ACCESS read-only
    STATUS current
    DESCRIPTION "Fan Assignment Table"
    ::= { FanAssignment 77 }

TempSensor-77 OBJECT-TYPE
    SYNTAX DisplayString
    MAX-ACCESS read-only
    STATUS current
    DESCRIPTION "Temperature Sensor"
    ::= { AssignTable-77 1 }

OpenLoopTable-77 OBJECT-TYPE
    SYNTAX Integer32
    MAX-ACCESS read-only
    STATUS current
    DESCRIPTION "Open Loop Table"
    ::= { AssignTable-77 2 }

ClosedLoopTable-77 OBJECT-TYPE
    SYNTAX Integer32
    MAX-ACCESS read-only
    STATUS current
    DESCRIPTION "Closed Loop Table"
    ::= { AssignTable-77 3 }

SelectedFan-77 OBJECT-TYPE
    SYNTAX DisplayString
    MAX-ACCESS read-only
    STATUS current
    DESCRIPTION "Selected Fan"
    ::= { AssignTable-77 4 }

AssignTable-78 OBJECT-TYPE
    SYNTAX DisplayString
    MAX-ACCESS read-only
    STATUS current
    DESCRIPTION "Fan Assignment Table"
    ::= { FanAssignment 78 }

TempSensor-78 OBJECT-TYPE
    SYNTAX DisplayString
    MAX-ACCESS read-only
    STATUS current
    DESCRIPTION "Temperature Sensor"
    ::= { AssignTable-78 1 }

OpenLoopTable-78 OBJECT-TYPE
    SYNTAX Integer32
    MAX-ACCESS read-only
    STATUS current
    DESCRIPTION "Open Loop Table"
    ::= { AssignTable-78 2 }

ClosedLoopTable-78 OBJECT-TYPE
    SYNTAX Integer32
    MAX-ACCESS read-only
    STATUS current
    DESCRIPTION "Closed Loop Table"
    ::= { AssignTable-78 3 }

SelectedFan-78 OBJECT-TYPE
    SYNTAX DisplayString
    MAX-ACCESS read-only
    STATUS current
    DESCRIPTION "Selected Fan"
    ::= { AssignTable-78 4 }

AssignTable-79 OBJECT-TYPE
    SYNTAX DisplayString
    MAX-ACCESS read-only
    STATUS current
    DESCRIPTION "Fan Assignment Table"
    ::= { FanAssignment 79 }

TempSensor-79 OBJECT-TYPE
    SYNTAX DisplayString
    MAX-ACCESS read-only
    STATUS current
    DESCRIPTION "Temperature Sensor"
    ::= { AssignTable-79 1 }

OpenLoopTable-79 OBJECT-TYPE
    SYNTAX Integer32
    MAX-ACCESS read-only
    STATUS current
    DESCRIPTION "Open Loop Table"
    ::= { AssignTable-79 2 }

ClosedLoopTable-79 OBJECT-TYPE
    SYNTAX Integer32
    MAX-ACCESS read-only
    STATUS current
    DESCRIPTION "Closed Loop Table"
    ::= { AssignTable-79 3 }

SelectedFan-79 OBJECT-TYPE
    SYNTAX DisplayString
    MAX-ACCESS read-only
    STATUS current
    DESCRIPTION "Selected Fan"
    ::= { AssignTable-79 4 }

AssignTable-80 OBJECT-TYPE
    SYNTAX DisplayString
    MAX-ACCESS read-only
    STATUS current
    DESCRIPTION "Fan Assignment Table"
    ::= { FanAssignment 80 }

TempSensor-80 OBJECT-TYPE
    SYNTAX DisplayString
    MAX-ACCESS read-only
    STATUS current
    DESCRIPTION "Temperature Sensor"
    ::= { AssignTable-80 1 }

OpenLoopTable-80 OBJECT-TYPE
    SYNTAX Integer32
    MAX-ACCESS read-only
    STATUS current
    DESCRIPTION "Open Loop Table"
    ::= { AssignTable-80 2 }

ClosedLoopTable-80 OBJECT-TYPE
    SYNTAX Integer32
    MAX-ACCESS read-only
    STATUS current
    DESCRIPTION "Closed Loop Table"
    ::= { AssignTable-80 3 }

SelectedFan-80 OBJECT-TYPE
    SYNTAX DisplayString
    MAX-ACCESS read-only
    STATUS current
    DESCRIPTION "Selected Fan"
    ::= { AssignTable-80 4 }

SensorInfo OBJECT IDENTIFIER ::= { am5d4id 6 }
VOLT-3VSB-1 OBJECT-TYPE
    SYNTAX DisplayString
    MAX-ACCESS read-only
    STATUS current
    DESCRIPTION "Threshold"
    ::= { SensorInfo 1 }

Index-1 OBJECT-TYPE
    SYNTAX Integer32
    MAX-ACCESS read-only
    STATUS current
    DESCRIPTION "Sensor Index"
    ::= { VOLT-3VSB-1 1 }

Number-1 OBJECT-TYPE
    SYNTAX Integer32
    MAX-ACCESS read-only
    STATUS current
    DESCRIPTION "Sensor Number"
    ::= { VOLT-3VSB-1 2 }

Name-1 OBJECT-TYPE
    SYNTAX DisplayString
    MAX-ACCESS read-only
    STATUS current
    DESCRIPTION "Sensor Name"
    ::= { VOLT-3VSB-1 3 }

Status-1 OBJECT-TYPE
    SYNTAX Integer32
    MAX-ACCESS read-only
    STATUS current
    DESCRIPTION "Sensor Status"
    ::= { VOLT-3VSB-1 4 }

Reading-1 OBJECT-TYPE
    SYNTAX DisplayString
    MAX-ACCESS read-only
    STATUS current
    DESCRIPTION "Sensor Reading"
    ::= { VOLT-3VSB-1 5 }

LowNRT-1 OBJECT-TYPE
    SYNTAX DisplayString
    MAX-ACCESS read-only
    STATUS current
    DESCRIPTION "Sensor Low NRT"
    ::= { VOLT-3VSB-1 6 }

LowCT-1 OBJECT-TYPE
    SYNTAX DisplayString
    MAX-ACCESS read-only
    STATUS current
    DESCRIPTION "Sensor Low CT"
    ::= { VOLT-3VSB-1 7 }

LowNCT-1 OBJECT-TYPE
    SYNTAX DisplayString
    MAX-ACCESS read-only
    STATUS current
    DESCRIPTION "Sensor Low NCT"
    ::= { VOLT-3VSB-1 8 }

UpNCT-1 OBJECT-TYPE
    SYNTAX DisplayString
    MAX-ACCESS read-only
    STATUS current
    DESCRIPTION "Sensor Up NCT"
    ::= { VOLT-3VSB-1 9 }

UpCT-1 OBJECT-TYPE
    SYNTAX DisplayString
    MAX-ACCESS read-only
    STATUS current
    DESCRIPTION "Sensor Up CT"
    ::= { VOLT-3VSB-1 10 }

UpNRT-1 OBJECT-TYPE
    SYNTAX DisplayString
    MAX-ACCESS read-only
    STATUS current
    DESCRIPTION "Sensor Up NRT"
    ::= { VOLT-3VSB-1 11 }

VOLT-5VSB-2 OBJECT-TYPE
    SYNTAX DisplayString
    MAX-ACCESS read-only
    STATUS current
    DESCRIPTION "Threshold"
    ::= { SensorInfo 2 }

Index-2 OBJECT-TYPE
    SYNTAX Integer32
    MAX-ACCESS read-only
    STATUS current
    DESCRIPTION "Sensor Index"
    ::= { VOLT-5VSB-2 1 }

Number-2 OBJECT-TYPE
    SYNTAX Integer32
    MAX-ACCESS read-only
    STATUS current
    DESCRIPTION "Sensor Number"
    ::= { VOLT-5VSB-2 2 }

Name-2 OBJECT-TYPE
    SYNTAX DisplayString
    MAX-ACCESS read-only
    STATUS current
    DESCRIPTION "Sensor Name"
    ::= { VOLT-5VSB-2 3 }

Status-2 OBJECT-TYPE
    SYNTAX Integer32
    MAX-ACCESS read-only
    STATUS current
    DESCRIPTION "Sensor Status"
    ::= { VOLT-5VSB-2 4 }

Reading-2 OBJECT-TYPE
    SYNTAX DisplayString
    MAX-ACCESS read-only
    STATUS current
    DESCRIPTION "Sensor Reading"
    ::= { VOLT-5VSB-2 5 }

LowNRT-2 OBJECT-TYPE
    SYNTAX DisplayString
    MAX-ACCESS read-only
    STATUS current
    DESCRIPTION "Sensor Low NRT"
    ::= { VOLT-5VSB-2 6 }

LowCT-2 OBJECT-TYPE
    SYNTAX DisplayString
    MAX-ACCESS read-only
    STATUS current
    DESCRIPTION "Sensor Low CT"
    ::= { VOLT-5VSB-2 7 }

LowNCT-2 OBJECT-TYPE
    SYNTAX DisplayString
    MAX-ACCESS read-only
    STATUS current
    DESCRIPTION "Sensor Low NCT"
    ::= { VOLT-5VSB-2 8 }

UpNCT-2 OBJECT-TYPE
    SYNTAX DisplayString
    MAX-ACCESS read-only
    STATUS current
    DESCRIPTION "Sensor Up NCT"
    ::= { VOLT-5VSB-2 9 }

UpCT-2 OBJECT-TYPE
    SYNTAX DisplayString
    MAX-ACCESS read-only
    STATUS current
    DESCRIPTION "Sensor Up CT"
    ::= { VOLT-5VSB-2 10 }

UpNRT-2 OBJECT-TYPE
    SYNTAX DisplayString
    MAX-ACCESS read-only
    STATUS current
    DESCRIPTION "Sensor Up NRT"
    ::= { VOLT-5VSB-2 11 }

VOLT-VCORE-3 OBJECT-TYPE
    SYNTAX DisplayString
    MAX-ACCESS read-only
    STATUS current
    DESCRIPTION "Threshold"
    ::= { SensorInfo 3 }

Index-3 OBJECT-TYPE
    SYNTAX Integer32
    MAX-ACCESS read-only
    STATUS current
    DESCRIPTION "Sensor Index"
    ::= { VOLT-VCORE-3 1 }

Number-3 OBJECT-TYPE
    SYNTAX Integer32
    MAX-ACCESS read-only
    STATUS current
    DESCRIPTION "Sensor Number"
    ::= { VOLT-VCORE-3 2 }

Name-3 OBJECT-TYPE
    SYNTAX DisplayString
    MAX-ACCESS read-only
    STATUS current
    DESCRIPTION "Sensor Name"
    ::= { VOLT-VCORE-3 3 }

Status-3 OBJECT-TYPE
    SYNTAX Integer32
    MAX-ACCESS read-only
    STATUS current
    DESCRIPTION "Sensor Status"
    ::= { VOLT-VCORE-3 4 }

Reading-3 OBJECT-TYPE
    SYNTAX DisplayString
    MAX-ACCESS read-only
    STATUS current
    DESCRIPTION "Sensor Reading"
    ::= { VOLT-VCORE-3 5 }

LowNRT-3 OBJECT-TYPE
    SYNTAX DisplayString
    MAX-ACCESS read-only
    STATUS current
    DESCRIPTION "Sensor Low NRT"
    ::= { VOLT-VCORE-3 6 }

LowCT-3 OBJECT-TYPE
    SYNTAX DisplayString
    MAX-ACCESS read-only
    STATUS current
    DESCRIPTION "Sensor Low CT"
    ::= { VOLT-VCORE-3 7 }

LowNCT-3 OBJECT-TYPE
    SYNTAX DisplayString
    MAX-ACCESS read-only
    STATUS current
    DESCRIPTION "Sensor Low NCT"
    ::= { VOLT-VCORE-3 8 }

UpNCT-3 OBJECT-TYPE
    SYNTAX DisplayString
    MAX-ACCESS read-only
    STATUS current
    DESCRIPTION "Sensor Up NCT"
    ::= { VOLT-VCORE-3 9 }

UpCT-3 OBJECT-TYPE
    SYNTAX DisplayString
    MAX-ACCESS read-only
    STATUS current
    DESCRIPTION "Sensor Up CT"
    ::= { VOLT-VCORE-3 10 }

UpNRT-3 OBJECT-TYPE
    SYNTAX DisplayString
    MAX-ACCESS read-only
    STATUS current
    DESCRIPTION "Sensor Up NRT"
    ::= { VOLT-VCORE-3 11 }

VOLT-VDDCR-SOC-4 OBJECT-TYPE
    SYNTAX DisplayString
    MAX-ACCESS read-only
    STATUS current
    DESCRIPTION "Threshold"
    ::= { SensorInfo 4 }

Index-4 OBJECT-TYPE
    SYNTAX Integer32
    MAX-ACCESS read-only
    STATUS current
    DESCRIPTION "Sensor Index"
    ::= { VOLT-VDDCR-SOC-4 1 }

Number-4 OBJECT-TYPE
    SYNTAX Integer32
    MAX-ACCESS read-only
    STATUS current
    DESCRIPTION "Sensor Number"
    ::= { VOLT-VDDCR-SOC-4 2 }

Name-4 OBJECT-TYPE
    SYNTAX DisplayString
    MAX-ACCESS read-only
    STATUS current
    DESCRIPTION "Sensor Name"
    ::= { VOLT-VDDCR-SOC-4 3 }

Status-4 OBJECT-TYPE
    SYNTAX Integer32
    MAX-ACCESS read-only
    STATUS current
    DESCRIPTION "Sensor Status"
    ::= { VOLT-VDDCR-SOC-4 4 }

Reading-4 OBJECT-TYPE
    SYNTAX DisplayString
    MAX-ACCESS read-only
    STATUS current
    DESCRIPTION "Sensor Reading"
    ::= { VOLT-VDDCR-SOC-4 5 }

LowNRT-4 OBJECT-TYPE
    SYNTAX DisplayString
    MAX-ACCESS read-only
    STATUS current
    DESCRIPTION "Sensor Low NRT"
    ::= { VOLT-VDDCR-SOC-4 6 }

LowCT-4 OBJECT-TYPE
    SYNTAX DisplayString
    MAX-ACCESS read-only
    STATUS current
    DESCRIPTION "Sensor Low CT"
    ::= { VOLT-VDDCR-SOC-4 7 }

LowNCT-4 OBJECT-TYPE
    SYNTAX DisplayString
    MAX-ACCESS read-only
    STATUS current
    DESCRIPTION "Sensor Low NCT"
    ::= { VOLT-VDDCR-SOC-4 8 }

UpNCT-4 OBJECT-TYPE
    SYNTAX DisplayString
    MAX-ACCESS read-only
    STATUS current
    DESCRIPTION "Sensor Up NCT"
    ::= { VOLT-VDDCR-SOC-4 9 }

UpCT-4 OBJECT-TYPE
    SYNTAX DisplayString
    MAX-ACCESS read-only
    STATUS current
    DESCRIPTION "Sensor Up CT"
    ::= { VOLT-VDDCR-SOC-4 10 }

UpNRT-4 OBJECT-TYPE
    SYNTAX DisplayString
    MAX-ACCESS read-only
    STATUS current
    DESCRIPTION "Sensor Up NRT"
    ::= { VOLT-VDDCR-SOC-4 11 }

VOLT-VDDIO-MEM-5 OBJECT-TYPE
    SYNTAX DisplayString
    MAX-ACCESS read-only
    STATUS current
    DESCRIPTION "Threshold"
    ::= { SensorInfo 5 }

Index-5 OBJECT-TYPE
    SYNTAX Integer32
    MAX-ACCESS read-only
    STATUS current
    DESCRIPTION "Sensor Index"
    ::= { VOLT-VDDIO-MEM-5 1 }

Number-5 OBJECT-TYPE
    SYNTAX Integer32
    MAX-ACCESS read-only
    STATUS current
    DESCRIPTION "Sensor Number"
    ::= { VOLT-VDDIO-MEM-5 2 }

Name-5 OBJECT-TYPE
    SYNTAX DisplayString
    MAX-ACCESS read-only
    STATUS current
    DESCRIPTION "Sensor Name"
    ::= { VOLT-VDDIO-MEM-5 3 }

Status-5 OBJECT-TYPE
    SYNTAX Integer32
    MAX-ACCESS read-only
    STATUS current
    DESCRIPTION "Sensor Status"
    ::= { VOLT-VDDIO-MEM-5 4 }

Reading-5 OBJECT-TYPE
    SYNTAX DisplayString
    MAX-ACCESS read-only
    STATUS current
    DESCRIPTION "Sensor Reading"
    ::= { VOLT-VDDIO-MEM-5 5 }

LowNRT-5 OBJECT-TYPE
    SYNTAX DisplayString
    MAX-ACCESS read-only
    STATUS current
    DESCRIPTION "Sensor Low NRT"
    ::= { VOLT-VDDIO-MEM-5 6 }

LowCT-5 OBJECT-TYPE
    SYNTAX DisplayString
    MAX-ACCESS read-only
    STATUS current
    DESCRIPTION "Sensor Low CT"
    ::= { VOLT-VDDIO-MEM-5 7 }

LowNCT-5 OBJECT-TYPE
    SYNTAX DisplayString
    MAX-ACCESS read-only
    STATUS current
    DESCRIPTION "Sensor Low NCT"
    ::= { VOLT-VDDIO-MEM-5 8 }

UpNCT-5 OBJECT-TYPE
    SYNTAX DisplayString
    MAX-ACCESS read-only
    STATUS current
    DESCRIPTION "Sensor Up NCT"
    ::= { VOLT-VDDIO-MEM-5 9 }

UpCT-5 OBJECT-TYPE
    SYNTAX DisplayString
    MAX-ACCESS read-only
    STATUS current
    DESCRIPTION "Sensor Up CT"
    ::= { VOLT-VDDIO-MEM-5 10 }

UpNRT-5 OBJECT-TYPE
    SYNTAX DisplayString
    MAX-ACCESS read-only
    STATUS current
    DESCRIPTION "Sensor Up NRT"
    ::= { VOLT-VDDIO-MEM-5 11 }

VOLT-VMISC-RUN-6 OBJECT-TYPE
    SYNTAX DisplayString
    MAX-ACCESS read-only
    STATUS current
    DESCRIPTION "Threshold"
    ::= { SensorInfo 6 }

Index-6 OBJECT-TYPE
    SYNTAX Integer32
    MAX-ACCESS read-only
    STATUS current
    DESCRIPTION "Sensor Index"
    ::= { VOLT-VMISC-RUN-6 1 }

Number-6 OBJECT-TYPE
    SYNTAX Integer32
    MAX-ACCESS read-only
    STATUS current
    DESCRIPTION "Sensor Number"
    ::= { VOLT-VMISC-RUN-6 2 }

Name-6 OBJECT-TYPE
    SYNTAX DisplayString
    MAX-ACCESS read-only
    STATUS current
    DESCRIPTION "Sensor Name"
    ::= { VOLT-VMISC-RUN-6 3 }

Status-6 OBJECT-TYPE
    SYNTAX Integer32
    MAX-ACCESS read-only
    STATUS current
    DESCRIPTION "Sensor Status"
    ::= { VOLT-VMISC-RUN-6 4 }

Reading-6 OBJECT-TYPE
    SYNTAX DisplayString
    MAX-ACCESS read-only
    STATUS current
    DESCRIPTION "Sensor Reading"
    ::= { VOLT-VMISC-RUN-6 5 }

LowNRT-6 OBJECT-TYPE
    SYNTAX DisplayString
    MAX-ACCESS read-only
    STATUS current
    DESCRIPTION "Sensor Low NRT"
    ::= { VOLT-VMISC-RUN-6 6 }

LowCT-6 OBJECT-TYPE
    SYNTAX DisplayString
    MAX-ACCESS read-only
    STATUS current
    DESCRIPTION "Sensor Low CT"
    ::= { VOLT-VMISC-RUN-6 7 }

LowNCT-6 OBJECT-TYPE
    SYNTAX DisplayString
    MAX-ACCESS read-only
    STATUS current
    DESCRIPTION "Sensor Low NCT"
    ::= { VOLT-VMISC-RUN-6 8 }

UpNCT-6 OBJECT-TYPE
    SYNTAX DisplayString
    MAX-ACCESS read-only
    STATUS current
    DESCRIPTION "Sensor Up NCT"
    ::= { VOLT-VMISC-RUN-6 9 }

UpCT-6 OBJECT-TYPE
    SYNTAX DisplayString
    MAX-ACCESS read-only
    STATUS current
    DESCRIPTION "Sensor Up CT"
    ::= { VOLT-VMISC-RUN-6 10 }

UpNRT-6 OBJECT-TYPE
    SYNTAX DisplayString
    MAX-ACCESS read-only
    STATUS current
    DESCRIPTION "Sensor Up NRT"
    ::= { VOLT-VMISC-RUN-6 11 }

VOLT-1-8V-PT21-7 OBJECT-TYPE
    SYNTAX DisplayString
    MAX-ACCESS read-only
    STATUS current
    DESCRIPTION "Threshold"
    ::= { SensorInfo 7 }

Index-7 OBJECT-TYPE
    SYNTAX Integer32
    MAX-ACCESS read-only
    STATUS current
    DESCRIPTION "Sensor Index"
    ::= { VOLT-1-8V-PT21-7 1 }

Number-7 OBJECT-TYPE
    SYNTAX Integer32
    MAX-ACCESS read-only
    STATUS current
    DESCRIPTION "Sensor Number"
    ::= { VOLT-1-8V-PT21-7 2 }

Name-7 OBJECT-TYPE
    SYNTAX DisplayString
    MAX-ACCESS read-only
    STATUS current
    DESCRIPTION "Sensor Name"
    ::= { VOLT-1-8V-PT21-7 3 }

Status-7 OBJECT-TYPE
    SYNTAX Integer32
    MAX-ACCESS read-only
    STATUS current
    DESCRIPTION "Sensor Status"
    ::= { VOLT-1-8V-PT21-7 4 }

Reading-7 OBJECT-TYPE
    SYNTAX DisplayString
    MAX-ACCESS read-only
    STATUS current
    DESCRIPTION "Sensor Reading"
    ::= { VOLT-1-8V-PT21-7 5 }

LowNRT-7 OBJECT-TYPE
    SYNTAX DisplayString
    MAX-ACCESS read-only
    STATUS current
    DESCRIPTION "Sensor Low NRT"
    ::= { VOLT-1-8V-PT21-7 6 }

LowCT-7 OBJECT-TYPE
    SYNTAX DisplayString
    MAX-ACCESS read-only
    STATUS current
    DESCRIPTION "Sensor Low CT"
    ::= { VOLT-1-8V-PT21-7 7 }

LowNCT-7 OBJECT-TYPE
    SYNTAX DisplayString
    MAX-ACCESS read-only
    STATUS current
    DESCRIPTION "Sensor Low NCT"
    ::= { VOLT-1-8V-PT21-7 8 }

UpNCT-7 OBJECT-TYPE
    SYNTAX DisplayString
    MAX-ACCESS read-only
    STATUS current
    DESCRIPTION "Sensor Up NCT"
    ::= { VOLT-1-8V-PT21-7 9 }

UpCT-7 OBJECT-TYPE
    SYNTAX DisplayString
    MAX-ACCESS read-only
    STATUS current
    DESCRIPTION "Sensor Up CT"
    ::= { VOLT-1-8V-PT21-7 10 }

UpNRT-7 OBJECT-TYPE
    SYNTAX DisplayString
    MAX-ACCESS read-only
    STATUS current
    DESCRIPTION "Sensor Up NRT"
    ::= { VOLT-1-8V-PT21-7 11 }

VOLT-MDVDDO-8 OBJECT-TYPE
    SYNTAX DisplayString
    MAX-ACCESS read-only
    STATUS current
    DESCRIPTION "Threshold"
    ::= { SensorInfo 8 }

Index-8 OBJECT-TYPE
    SYNTAX Integer32
    MAX-ACCESS read-only
    STATUS current
    DESCRIPTION "Sensor Index"
    ::= { VOLT-MDVDDO-8 1 }

Number-8 OBJECT-TYPE
    SYNTAX Integer32
    MAX-ACCESS read-only
    STATUS current
    DESCRIPTION "Sensor Number"
    ::= { VOLT-MDVDDO-8 2 }

Name-8 OBJECT-TYPE
    SYNTAX DisplayString
    MAX-ACCESS read-only
    STATUS current
    DESCRIPTION "Sensor Name"
    ::= { VOLT-MDVDDO-8 3 }

Status-8 OBJECT-TYPE
    SYNTAX Integer32
    MAX-ACCESS read-only
    STATUS current
    DESCRIPTION "Sensor Status"
    ::= { VOLT-MDVDDO-8 4 }

Reading-8 OBJECT-TYPE
    SYNTAX DisplayString
    MAX-ACCESS read-only
    STATUS current
    DESCRIPTION "Sensor Reading"
    ::= { VOLT-MDVDDO-8 5 }

LowNRT-8 OBJECT-TYPE
    SYNTAX DisplayString
    MAX-ACCESS read-only
    STATUS current
    DESCRIPTION "Sensor Low NRT"
    ::= { VOLT-MDVDDO-8 6 }

LowCT-8 OBJECT-TYPE
    SYNTAX DisplayString
    MAX-ACCESS read-only
    STATUS current
    DESCRIPTION "Sensor Low CT"
    ::= { VOLT-MDVDDO-8 7 }

LowNCT-8 OBJECT-TYPE
    SYNTAX DisplayString
    MAX-ACCESS read-only
    STATUS current
    DESCRIPTION "Sensor Low NCT"
    ::= { VOLT-MDVDDO-8 8 }

UpNCT-8 OBJECT-TYPE
    SYNTAX DisplayString
    MAX-ACCESS read-only
    STATUS current
    DESCRIPTION "Sensor Up NCT"
    ::= { VOLT-MDVDDO-8 9 }

UpCT-8 OBJECT-TYPE
    SYNTAX DisplayString
    MAX-ACCESS read-only
    STATUS current
    DESCRIPTION "Sensor Up CT"
    ::= { VOLT-MDVDDO-8 10 }

UpNRT-8 OBJECT-TYPE
    SYNTAX DisplayString
    MAX-ACCESS read-only
    STATUS current
    DESCRIPTION "Sensor Up NRT"
    ::= { VOLT-MDVDDO-8 11 }

VOLT-ENET1V9-9 OBJECT-TYPE
    SYNTAX DisplayString
    MAX-ACCESS read-only
    STATUS current
    DESCRIPTION "Threshold"
    ::= { SensorInfo 9 }

Index-9 OBJECT-TYPE
    SYNTAX Integer32
    MAX-ACCESS read-only
    STATUS current
    DESCRIPTION "Sensor Index"
    ::= { VOLT-ENET1V9-9 1 }

Number-9 OBJECT-TYPE
    SYNTAX Integer32
    MAX-ACCESS read-only
    STATUS current
    DESCRIPTION "Sensor Number"
    ::= { VOLT-ENET1V9-9 2 }

Name-9 OBJECT-TYPE
    SYNTAX DisplayString
    MAX-ACCESS read-only
    STATUS current
    DESCRIPTION "Sensor Name"
    ::= { VOLT-ENET1V9-9 3 }

Status-9 OBJECT-TYPE
    SYNTAX Integer32
    MAX-ACCESS read-only
    STATUS current
    DESCRIPTION "Sensor Status"
    ::= { VOLT-ENET1V9-9 4 }

Reading-9 OBJECT-TYPE
    SYNTAX DisplayString
    MAX-ACCESS read-only
    STATUS current
    DESCRIPTION "Sensor Reading"
    ::= { VOLT-ENET1V9-9 5 }

LowNRT-9 OBJECT-TYPE
    SYNTAX DisplayString
    MAX-ACCESS read-only
    STATUS current
    DESCRIPTION "Sensor Low NRT"
    ::= { VOLT-ENET1V9-9 6 }

LowCT-9 OBJECT-TYPE
    SYNTAX DisplayString
    MAX-ACCESS read-only
    STATUS current
    DESCRIPTION "Sensor Low CT"
    ::= { VOLT-ENET1V9-9 7 }

LowNCT-9 OBJECT-TYPE
    SYNTAX DisplayString
    MAX-ACCESS read-only
    STATUS current
    DESCRIPTION "Sensor Low NCT"
    ::= { VOLT-ENET1V9-9 8 }

UpNCT-9 OBJECT-TYPE
    SYNTAX DisplayString
    MAX-ACCESS read-only
    STATUS current
    DESCRIPTION "Sensor Up NCT"
    ::= { VOLT-ENET1V9-9 9 }

UpCT-9 OBJECT-TYPE
    SYNTAX DisplayString
    MAX-ACCESS read-only
    STATUS current
    DESCRIPTION "Sensor Up CT"
    ::= { VOLT-ENET1V9-9 10 }

UpNRT-9 OBJECT-TYPE
    SYNTAX DisplayString
    MAX-ACCESS read-only
    STATUS current
    DESCRIPTION "Sensor Up NRT"
    ::= { VOLT-ENET1V9-9 11 }

VOLT-VDD1P8-10 OBJECT-TYPE
    SYNTAX DisplayString
    MAX-ACCESS read-only
    STATUS current
    DESCRIPTION "Threshold"
    ::= { SensorInfo 10 }

Index-10 OBJECT-TYPE
    SYNTAX Integer32
    MAX-ACCESS read-only
    STATUS current
    DESCRIPTION "Sensor Index"
    ::= { VOLT-VDD1P8-10 1 }

Number-10 OBJECT-TYPE
    SYNTAX Integer32
    MAX-ACCESS read-only
    STATUS current
    DESCRIPTION "Sensor Number"
    ::= { VOLT-VDD1P8-10 2 }

Name-10 OBJECT-TYPE
    SYNTAX DisplayString
    MAX-ACCESS read-only
    STATUS current
    DESCRIPTION "Sensor Name"
    ::= { VOLT-VDD1P8-10 3 }

Status-10 OBJECT-TYPE
    SYNTAX Integer32
    MAX-ACCESS read-only
    STATUS current
    DESCRIPTION "Sensor Status"
    ::= { VOLT-VDD1P8-10 4 }

Reading-10 OBJECT-TYPE
    SYNTAX DisplayString
    MAX-ACCESS read-only
    STATUS current
    DESCRIPTION "Sensor Reading"
    ::= { VOLT-VDD1P8-10 5 }

LowNRT-10 OBJECT-TYPE
    SYNTAX DisplayString
    MAX-ACCESS read-only
    STATUS current
    DESCRIPTION "Sensor Low NRT"
    ::= { VOLT-VDD1P8-10 6 }

LowCT-10 OBJECT-TYPE
    SYNTAX DisplayString
    MAX-ACCESS read-only
    STATUS current
    DESCRIPTION "Sensor Low CT"
    ::= { VOLT-VDD1P8-10 7 }

LowNCT-10 OBJECT-TYPE
    SYNTAX DisplayString
    MAX-ACCESS read-only
    STATUS current
    DESCRIPTION "Sensor Low NCT"
    ::= { VOLT-VDD1P8-10 8 }

UpNCT-10 OBJECT-TYPE
    SYNTAX DisplayString
    MAX-ACCESS read-only
    STATUS current
    DESCRIPTION "Sensor Up NCT"
    ::= { VOLT-VDD1P8-10 9 }

UpCT-10 OBJECT-TYPE
    SYNTAX DisplayString
    MAX-ACCESS read-only
    STATUS current
    DESCRIPTION "Sensor Up CT"
    ::= { VOLT-VDD1P8-10 10 }

UpNRT-10 OBJECT-TYPE
    SYNTAX DisplayString
    MAX-ACCESS read-only
    STATUS current
    DESCRIPTION "Sensor Up NRT"
    ::= { VOLT-VDD1P8-10 11 }

VOLT-V10PHYDOG-11 OBJECT-TYPE
    SYNTAX DisplayString
    MAX-ACCESS read-only
    STATUS current
    DESCRIPTION "Threshold"
    ::= { SensorInfo 11 }

Index-11 OBJECT-TYPE
    SYNTAX Integer32
    MAX-ACCESS read-only
    STATUS current
    DESCRIPTION "Sensor Index"
    ::= { VOLT-V10PHYDOG-11 1 }

Number-11 OBJECT-TYPE
    SYNTAX Integer32
    MAX-ACCESS read-only
    STATUS current
    DESCRIPTION "Sensor Number"
    ::= { VOLT-V10PHYDOG-11 2 }

Name-11 OBJECT-TYPE
    SYNTAX DisplayString
    MAX-ACCESS read-only
    STATUS current
    DESCRIPTION "Sensor Name"
    ::= { VOLT-V10PHYDOG-11 3 }

Status-11 OBJECT-TYPE
    SYNTAX Integer32
    MAX-ACCESS read-only
    STATUS current
    DESCRIPTION "Sensor Status"
    ::= { VOLT-V10PHYDOG-11 4 }

Reading-11 OBJECT-TYPE
    SYNTAX DisplayString
    MAX-ACCESS read-only
    STATUS current
    DESCRIPTION "Sensor Reading"
    ::= { VOLT-V10PHYDOG-11 5 }

LowNRT-11 OBJECT-TYPE
    SYNTAX DisplayString
    MAX-ACCESS read-only
    STATUS current
    DESCRIPTION "Sensor Low NRT"
    ::= { VOLT-V10PHYDOG-11 6 }

LowCT-11 OBJECT-TYPE
    SYNTAX DisplayString
    MAX-ACCESS read-only
    STATUS current
    DESCRIPTION "Sensor Low CT"
    ::= { VOLT-V10PHYDOG-11 7 }

LowNCT-11 OBJECT-TYPE
    SYNTAX DisplayString
    MAX-ACCESS read-only
    STATUS current
    DESCRIPTION "Sensor Low NCT"
    ::= { VOLT-V10PHYDOG-11 8 }

UpNCT-11 OBJECT-TYPE
    SYNTAX DisplayString
    MAX-ACCESS read-only
    STATUS current
    DESCRIPTION "Sensor Up NCT"
    ::= { VOLT-V10PHYDOG-11 9 }

UpCT-11 OBJECT-TYPE
    SYNTAX DisplayString
    MAX-ACCESS read-only
    STATUS current
    DESCRIPTION "Sensor Up CT"
    ::= { VOLT-V10PHYDOG-11 10 }

UpNRT-11 OBJECT-TYPE
    SYNTAX DisplayString
    MAX-ACCESS read-only
    STATUS current
    DESCRIPTION "Sensor Up NRT"
    ::= { VOLT-V10PHYDOG-11 11 }

VOLT-BAT-12 OBJECT-TYPE
    SYNTAX DisplayString
    MAX-ACCESS read-only
    STATUS current
    DESCRIPTION "Threshold"
    ::= { SensorInfo 12 }

Index-12 OBJECT-TYPE
    SYNTAX Integer32
    MAX-ACCESS read-only
    STATUS current
    DESCRIPTION "Sensor Index"
    ::= { VOLT-BAT-12 1 }

Number-12 OBJECT-TYPE
    SYNTAX Integer32
    MAX-ACCESS read-only
    STATUS current
    DESCRIPTION "Sensor Number"
    ::= { VOLT-BAT-12 2 }

Name-12 OBJECT-TYPE
    SYNTAX DisplayString
    MAX-ACCESS read-only
    STATUS current
    DESCRIPTION "Sensor Name"
    ::= { VOLT-BAT-12 3 }

Status-12 OBJECT-TYPE
    SYNTAX Integer32
    MAX-ACCESS read-only
    STATUS current
    DESCRIPTION "Sensor Status"
    ::= { VOLT-BAT-12 4 }

Reading-12 OBJECT-TYPE
    SYNTAX DisplayString
    MAX-ACCESS read-only
    STATUS current
    DESCRIPTION "Sensor Reading"
    ::= { VOLT-BAT-12 5 }

LowNRT-12 OBJECT-TYPE
    SYNTAX DisplayString
    MAX-ACCESS read-only
    STATUS current
    DESCRIPTION "Sensor Low NRT"
    ::= { VOLT-BAT-12 6 }

LowCT-12 OBJECT-TYPE
    SYNTAX DisplayString
    MAX-ACCESS read-only
    STATUS current
    DESCRIPTION "Sensor Low CT"
    ::= { VOLT-BAT-12 7 }

LowNCT-12 OBJECT-TYPE
    SYNTAX DisplayString
    MAX-ACCESS read-only
    STATUS current
    DESCRIPTION "Sensor Low NCT"
    ::= { VOLT-BAT-12 8 }

UpNCT-12 OBJECT-TYPE
    SYNTAX DisplayString
    MAX-ACCESS read-only
    STATUS current
    DESCRIPTION "Sensor Up NCT"
    ::= { VOLT-BAT-12 9 }

UpCT-12 OBJECT-TYPE
    SYNTAX DisplayString
    MAX-ACCESS read-only
    STATUS current
    DESCRIPTION "Sensor Up CT"
    ::= { VOLT-BAT-12 10 }

UpNRT-12 OBJECT-TYPE
    SYNTAX DisplayString
    MAX-ACCESS read-only
    STATUS current
    DESCRIPTION "Sensor Up NRT"
    ::= { VOLT-BAT-12 11 }

VOLT-3V-13 OBJECT-TYPE
    SYNTAX DisplayString
    MAX-ACCESS read-only
    STATUS current
    DESCRIPTION "Threshold"
    ::= { SensorInfo 13 }

Index-13 OBJECT-TYPE
    SYNTAX Integer32
    MAX-ACCESS read-only
    STATUS current
    DESCRIPTION "Sensor Index"
    ::= { VOLT-3V-13 1 }

Number-13 OBJECT-TYPE
    SYNTAX Integer32
    MAX-ACCESS read-only
    STATUS current
    DESCRIPTION "Sensor Number"
    ::= { VOLT-3V-13 2 }

Name-13 OBJECT-TYPE
    SYNTAX DisplayString
    MAX-ACCESS read-only
    STATUS current
    DESCRIPTION "Sensor Name"
    ::= { VOLT-3V-13 3 }

Status-13 OBJECT-TYPE
    SYNTAX Integer32
    MAX-ACCESS read-only
    STATUS current
    DESCRIPTION "Sensor Status"
    ::= { VOLT-3V-13 4 }

Reading-13 OBJECT-TYPE
    SYNTAX DisplayString
    MAX-ACCESS read-only
    STATUS current
    DESCRIPTION "Sensor Reading"
    ::= { VOLT-3V-13 5 }

LowNRT-13 OBJECT-TYPE
    SYNTAX DisplayString
    MAX-ACCESS read-only
    STATUS current
    DESCRIPTION "Sensor Low NRT"
    ::= { VOLT-3V-13 6 }

LowCT-13 OBJECT-TYPE
    SYNTAX DisplayString
    MAX-ACCESS read-only
    STATUS current
    DESCRIPTION "Sensor Low CT"
    ::= { VOLT-3V-13 7 }

LowNCT-13 OBJECT-TYPE
    SYNTAX DisplayString
    MAX-ACCESS read-only
    STATUS current
    DESCRIPTION "Sensor Low NCT"
    ::= { VOLT-3V-13 8 }

UpNCT-13 OBJECT-TYPE
    SYNTAX DisplayString
    MAX-ACCESS read-only
    STATUS current
    DESCRIPTION "Sensor Up NCT"
    ::= { VOLT-3V-13 9 }

UpCT-13 OBJECT-TYPE
    SYNTAX DisplayString
    MAX-ACCESS read-only
    STATUS current
    DESCRIPTION "Sensor Up CT"
    ::= { VOLT-3V-13 10 }

UpNRT-13 OBJECT-TYPE
    SYNTAX DisplayString
    MAX-ACCESS read-only
    STATUS current
    DESCRIPTION "Sensor Up NRT"
    ::= { VOLT-3V-13 11 }

VOLT-5V-14 OBJECT-TYPE
    SYNTAX DisplayString
    MAX-ACCESS read-only
    STATUS current
    DESCRIPTION "Threshold"
    ::= { SensorInfo 14 }

Index-14 OBJECT-TYPE
    SYNTAX Integer32
    MAX-ACCESS read-only
    STATUS current
    DESCRIPTION "Sensor Index"
    ::= { VOLT-5V-14 1 }

Number-14 OBJECT-TYPE
    SYNTAX Integer32
    MAX-ACCESS read-only
    STATUS current
    DESCRIPTION "Sensor Number"
    ::= { VOLT-5V-14 2 }

Name-14 OBJECT-TYPE
    SYNTAX DisplayString
    MAX-ACCESS read-only
    STATUS current
    DESCRIPTION "Sensor Name"
    ::= { VOLT-5V-14 3 }

Status-14 OBJECT-TYPE
    SYNTAX Integer32
    MAX-ACCESS read-only
    STATUS current
    DESCRIPTION "Sensor Status"
    ::= { VOLT-5V-14 4 }

Reading-14 OBJECT-TYPE
    SYNTAX DisplayString
    MAX-ACCESS read-only
    STATUS current
    DESCRIPTION "Sensor Reading"
    ::= { VOLT-5V-14 5 }

LowNRT-14 OBJECT-TYPE
    SYNTAX DisplayString
    MAX-ACCESS read-only
    STATUS current
    DESCRIPTION "Sensor Low NRT"
    ::= { VOLT-5V-14 6 }

LowCT-14 OBJECT-TYPE
    SYNTAX DisplayString
    MAX-ACCESS read-only
    STATUS current
    DESCRIPTION "Sensor Low CT"
    ::= { VOLT-5V-14 7 }

LowNCT-14 OBJECT-TYPE
    SYNTAX DisplayString
    MAX-ACCESS read-only
    STATUS current
    DESCRIPTION "Sensor Low NCT"
    ::= { VOLT-5V-14 8 }

UpNCT-14 OBJECT-TYPE
    SYNTAX DisplayString
    MAX-ACCESS read-only
    STATUS current
    DESCRIPTION "Sensor Up NCT"
    ::= { VOLT-5V-14 9 }

UpCT-14 OBJECT-TYPE
    SYNTAX DisplayString
    MAX-ACCESS read-only
    STATUS current
    DESCRIPTION "Sensor Up CT"
    ::= { VOLT-5V-14 10 }

UpNRT-14 OBJECT-TYPE
    SYNTAX DisplayString
    MAX-ACCESS read-only
    STATUS current
    DESCRIPTION "Sensor Up NRT"
    ::= { VOLT-5V-14 11 }

VOLT-12V-15 OBJECT-TYPE
    SYNTAX DisplayString
    MAX-ACCESS read-only
    STATUS current
    DESCRIPTION "Threshold"
    ::= { SensorInfo 15 }

Index-15 OBJECT-TYPE
    SYNTAX Integer32
    MAX-ACCESS read-only
    STATUS current
    DESCRIPTION "Sensor Index"
    ::= { VOLT-12V-15 1 }

Number-15 OBJECT-TYPE
    SYNTAX Integer32
    MAX-ACCESS read-only
    STATUS current
    DESCRIPTION "Sensor Number"
    ::= { VOLT-12V-15 2 }

Name-15 OBJECT-TYPE
    SYNTAX DisplayString
    MAX-ACCESS read-only
    STATUS current
    DESCRIPTION "Sensor Name"
    ::= { VOLT-12V-15 3 }

Status-15 OBJECT-TYPE
    SYNTAX Integer32
    MAX-ACCESS read-only
    STATUS current
    DESCRIPTION "Sensor Status"
    ::= { VOLT-12V-15 4 }

Reading-15 OBJECT-TYPE
    SYNTAX DisplayString
    MAX-ACCESS read-only
    STATUS current
    DESCRIPTION "Sensor Reading"
    ::= { VOLT-12V-15 5 }

LowNRT-15 OBJECT-TYPE
    SYNTAX DisplayString
    MAX-ACCESS read-only
    STATUS current
    DESCRIPTION "Sensor Low NRT"
    ::= { VOLT-12V-15 6 }

LowCT-15 OBJECT-TYPE
    SYNTAX DisplayString
    MAX-ACCESS read-only
    STATUS current
    DESCRIPTION "Sensor Low CT"
    ::= { VOLT-12V-15 7 }

LowNCT-15 OBJECT-TYPE
    SYNTAX DisplayString
    MAX-ACCESS read-only
    STATUS current
    DESCRIPTION "Sensor Low NCT"
    ::= { VOLT-12V-15 8 }

UpNCT-15 OBJECT-TYPE
    SYNTAX DisplayString
    MAX-ACCESS read-only
    STATUS current
    DESCRIPTION "Sensor Up NCT"
    ::= { VOLT-12V-15 9 }

UpCT-15 OBJECT-TYPE
    SYNTAX DisplayString
    MAX-ACCESS read-only
    STATUS current
    DESCRIPTION "Sensor Up CT"
    ::= { VOLT-12V-15 10 }

UpNRT-15 OBJECT-TYPE
    SYNTAX DisplayString
    MAX-ACCESS read-only
    STATUS current
    DESCRIPTION "Sensor Up NRT"
    ::= { VOLT-12V-15 11 }

FAN5-1-16 OBJECT-TYPE
    SYNTAX DisplayString
    MAX-ACCESS read-only
    STATUS current
    DESCRIPTION "Threshold"
    ::= { SensorInfo 16 }

Index-16 OBJECT-TYPE
    SYNTAX Integer32
    MAX-ACCESS read-only
    STATUS current
    DESCRIPTION "Sensor Index"
    ::= { FAN5-1-16 1 }

Number-16 OBJECT-TYPE
    SYNTAX Integer32
    MAX-ACCESS read-only
    STATUS current
    DESCRIPTION "Sensor Number"
    ::= { FAN5-1-16 2 }

Name-16 OBJECT-TYPE
    SYNTAX DisplayString
    MAX-ACCESS read-only
    STATUS current
    DESCRIPTION "Sensor Name"
    ::= { FAN5-1-16 3 }

Status-16 OBJECT-TYPE
    SYNTAX Integer32
    MAX-ACCESS read-only
    STATUS current
    DESCRIPTION "Sensor Status"
    ::= { FAN5-1-16 4 }

Reading-16 OBJECT-TYPE
    SYNTAX DisplayString
    MAX-ACCESS read-only
    STATUS current
    DESCRIPTION "Sensor Reading"
    ::= { FAN5-1-16 5 }

LowNRT-16 OBJECT-TYPE
    SYNTAX DisplayString
    MAX-ACCESS read-only
    STATUS current
    DESCRIPTION "Sensor Low NRT"
    ::= { FAN5-1-16 6 }

LowCT-16 OBJECT-TYPE
    SYNTAX DisplayString
    MAX-ACCESS read-only
    STATUS current
    DESCRIPTION "Sensor Low CT"
    ::= { FAN5-1-16 7 }

LowNCT-16 OBJECT-TYPE
    SYNTAX DisplayString
    MAX-ACCESS read-only
    STATUS current
    DESCRIPTION "Sensor Low NCT"
    ::= { FAN5-1-16 8 }

UpNCT-16 OBJECT-TYPE
    SYNTAX DisplayString
    MAX-ACCESS read-only
    STATUS current
    DESCRIPTION "Sensor Up NCT"
    ::= { FAN5-1-16 9 }

UpCT-16 OBJECT-TYPE
    SYNTAX DisplayString
    MAX-ACCESS read-only
    STATUS current
    DESCRIPTION "Sensor Up CT"
    ::= { FAN5-1-16 10 }

UpNRT-16 OBJECT-TYPE
    SYNTAX DisplayString
    MAX-ACCESS read-only
    STATUS current
    DESCRIPTION "Sensor Up NRT"
    ::= { FAN5-1-16 11 }

FAN6-1-17 OBJECT-TYPE
    SYNTAX DisplayString
    MAX-ACCESS read-only
    STATUS current
    DESCRIPTION "Threshold"
    ::= { SensorInfo 17 }

Index-17 OBJECT-TYPE
    SYNTAX Integer32
    MAX-ACCESS read-only
    STATUS current
    DESCRIPTION "Sensor Index"
    ::= { FAN6-1-17 1 }

Number-17 OBJECT-TYPE
    SYNTAX Integer32
    MAX-ACCESS read-only
    STATUS current
    DESCRIPTION "Sensor Number"
    ::= { FAN6-1-17 2 }

Name-17 OBJECT-TYPE
    SYNTAX DisplayString
    MAX-ACCESS read-only
    STATUS current
    DESCRIPTION "Sensor Name"
    ::= { FAN6-1-17 3 }

Status-17 OBJECT-TYPE
    SYNTAX Integer32
    MAX-ACCESS read-only
    STATUS current
    DESCRIPTION "Sensor Status"
    ::= { FAN6-1-17 4 }

Reading-17 OBJECT-TYPE
    SYNTAX DisplayString
    MAX-ACCESS read-only
    STATUS current
    DESCRIPTION "Sensor Reading"
    ::= { FAN6-1-17 5 }

LowNRT-17 OBJECT-TYPE
    SYNTAX DisplayString
    MAX-ACCESS read-only
    STATUS current
    DESCRIPTION "Sensor Low NRT"
    ::= { FAN6-1-17 6 }

LowCT-17 OBJECT-TYPE
    SYNTAX DisplayString
    MAX-ACCESS read-only
    STATUS current
    DESCRIPTION "Sensor Low CT"
    ::= { FAN6-1-17 7 }

LowNCT-17 OBJECT-TYPE
    SYNTAX DisplayString
    MAX-ACCESS read-only
    STATUS current
    DESCRIPTION "Sensor Low NCT"
    ::= { FAN6-1-17 8 }

UpNCT-17 OBJECT-TYPE
    SYNTAX DisplayString
    MAX-ACCESS read-only
    STATUS current
    DESCRIPTION "Sensor Up NCT"
    ::= { FAN6-1-17 9 }

UpCT-17 OBJECT-TYPE
    SYNTAX DisplayString
    MAX-ACCESS read-only
    STATUS current
    DESCRIPTION "Sensor Up CT"
    ::= { FAN6-1-17 10 }

UpNRT-17 OBJECT-TYPE
    SYNTAX DisplayString
    MAX-ACCESS read-only
    STATUS current
    DESCRIPTION "Sensor Up NRT"
    ::= { FAN6-1-17 11 }

FAN7-1-18 OBJECT-TYPE
    SYNTAX DisplayString
    MAX-ACCESS read-only
    STATUS current
    DESCRIPTION "Threshold"
    ::= { SensorInfo 18 }

Index-18 OBJECT-TYPE
    SYNTAX Integer32
    MAX-ACCESS read-only
    STATUS current
    DESCRIPTION "Sensor Index"
    ::= { FAN7-1-18 1 }

Number-18 OBJECT-TYPE
    SYNTAX Integer32
    MAX-ACCESS read-only
    STATUS current
    DESCRIPTION "Sensor Number"
    ::= { FAN7-1-18 2 }

Name-18 OBJECT-TYPE
    SYNTAX DisplayString
    MAX-ACCESS read-only
    STATUS current
    DESCRIPTION "Sensor Name"
    ::= { FAN7-1-18 3 }

Status-18 OBJECT-TYPE
    SYNTAX Integer32
    MAX-ACCESS read-only
    STATUS current
    DESCRIPTION "Sensor Status"
    ::= { FAN7-1-18 4 }

Reading-18 OBJECT-TYPE
    SYNTAX DisplayString
    MAX-ACCESS read-only
    STATUS current
    DESCRIPTION "Sensor Reading"
    ::= { FAN7-1-18 5 }

LowNRT-18 OBJECT-TYPE
    SYNTAX DisplayString
    MAX-ACCESS read-only
    STATUS current
    DESCRIPTION "Sensor Low NRT"
    ::= { FAN7-1-18 6 }

LowCT-18 OBJECT-TYPE
    SYNTAX DisplayString
    MAX-ACCESS read-only
    STATUS current
    DESCRIPTION "Sensor Low CT"
    ::= { FAN7-1-18 7 }

LowNCT-18 OBJECT-TYPE
    SYNTAX DisplayString
    MAX-ACCESS read-only
    STATUS current
    DESCRIPTION "Sensor Low NCT"
    ::= { FAN7-1-18 8 }

UpNCT-18 OBJECT-TYPE
    SYNTAX DisplayString
    MAX-ACCESS read-only
    STATUS current
    DESCRIPTION "Sensor Up NCT"
    ::= { FAN7-1-18 9 }

UpCT-18 OBJECT-TYPE
    SYNTAX DisplayString
    MAX-ACCESS read-only
    STATUS current
    DESCRIPTION "Sensor Up CT"
    ::= { FAN7-1-18 10 }

UpNRT-18 OBJECT-TYPE
    SYNTAX DisplayString
    MAX-ACCESS read-only
    STATUS current
    DESCRIPTION "Sensor Up NRT"
    ::= { FAN7-1-18 11 }

FAN8-1-19 OBJECT-TYPE
    SYNTAX DisplayString
    MAX-ACCESS read-only
    STATUS current
    DESCRIPTION "Threshold"
    ::= { SensorInfo 19 }

Index-19 OBJECT-TYPE
    SYNTAX Integer32
    MAX-ACCESS read-only
    STATUS current
    DESCRIPTION "Sensor Index"
    ::= { FAN8-1-19 1 }

Number-19 OBJECT-TYPE
    SYNTAX Integer32
    MAX-ACCESS read-only
    STATUS current
    DESCRIPTION "Sensor Number"
    ::= { FAN8-1-19 2 }

Name-19 OBJECT-TYPE
    SYNTAX DisplayString
    MAX-ACCESS read-only
    STATUS current
    DESCRIPTION "Sensor Name"
    ::= { FAN8-1-19 3 }

Status-19 OBJECT-TYPE
    SYNTAX Integer32
    MAX-ACCESS read-only
    STATUS current
    DESCRIPTION "Sensor Status"
    ::= { FAN8-1-19 4 }

Reading-19 OBJECT-TYPE
    SYNTAX DisplayString
    MAX-ACCESS read-only
    STATUS current
    DESCRIPTION "Sensor Reading"
    ::= { FAN8-1-19 5 }

LowNRT-19 OBJECT-TYPE
    SYNTAX DisplayString
    MAX-ACCESS read-only
    STATUS current
    DESCRIPTION "Sensor Low NRT"
    ::= { FAN8-1-19 6 }

LowCT-19 OBJECT-TYPE
    SYNTAX DisplayString
    MAX-ACCESS read-only
    STATUS current
    DESCRIPTION "Sensor Low CT"
    ::= { FAN8-1-19 7 }

LowNCT-19 OBJECT-TYPE
    SYNTAX DisplayString
    MAX-ACCESS read-only
    STATUS current
    DESCRIPTION "Sensor Low NCT"
    ::= { FAN8-1-19 8 }

UpNCT-19 OBJECT-TYPE
    SYNTAX DisplayString
    MAX-ACCESS read-only
    STATUS current
    DESCRIPTION "Sensor Up NCT"
    ::= { FAN8-1-19 9 }

UpCT-19 OBJECT-TYPE
    SYNTAX DisplayString
    MAX-ACCESS read-only
    STATUS current
    DESCRIPTION "Sensor Up CT"
    ::= { FAN8-1-19 10 }

UpNRT-19 OBJECT-TYPE
    SYNTAX DisplayString
    MAX-ACCESS read-only
    STATUS current
    DESCRIPTION "Sensor Up NRT"
    ::= { FAN8-1-19 11 }

FAN5-2-20 OBJECT-TYPE
    SYNTAX DisplayString
    MAX-ACCESS read-only
    STATUS current
    DESCRIPTION "Threshold"
    ::= { SensorInfo 20 }

Index-20 OBJECT-TYPE
    SYNTAX Integer32
    MAX-ACCESS read-only
    STATUS current
    DESCRIPTION "Sensor Index"
    ::= { FAN5-2-20 1 }

Number-20 OBJECT-TYPE
    SYNTAX Integer32
    MAX-ACCESS read-only
    STATUS current
    DESCRIPTION "Sensor Number"
    ::= { FAN5-2-20 2 }

Name-20 OBJECT-TYPE
    SYNTAX DisplayString
    MAX-ACCESS read-only
    STATUS current
    DESCRIPTION "Sensor Name"
    ::= { FAN5-2-20 3 }

Status-20 OBJECT-TYPE
    SYNTAX Integer32
    MAX-ACCESS read-only
    STATUS current
    DESCRIPTION "Sensor Status"
    ::= { FAN5-2-20 4 }

Reading-20 OBJECT-TYPE
    SYNTAX DisplayString
    MAX-ACCESS read-only
    STATUS current
    DESCRIPTION "Sensor Reading"
    ::= { FAN5-2-20 5 }

LowNRT-20 OBJECT-TYPE
    SYNTAX DisplayString
    MAX-ACCESS read-only
    STATUS current
    DESCRIPTION "Sensor Low NRT"
    ::= { FAN5-2-20 6 }

LowCT-20 OBJECT-TYPE
    SYNTAX DisplayString
    MAX-ACCESS read-only
    STATUS current
    DESCRIPTION "Sensor Low CT"
    ::= { FAN5-2-20 7 }

LowNCT-20 OBJECT-TYPE
    SYNTAX DisplayString
    MAX-ACCESS read-only
    STATUS current
    DESCRIPTION "Sensor Low NCT"
    ::= { FAN5-2-20 8 }

UpNCT-20 OBJECT-TYPE
    SYNTAX DisplayString
    MAX-ACCESS read-only
    STATUS current
    DESCRIPTION "Sensor Up NCT"
    ::= { FAN5-2-20 9 }

UpCT-20 OBJECT-TYPE
    SYNTAX DisplayString
    MAX-ACCESS read-only
    STATUS current
    DESCRIPTION "Sensor Up CT"
    ::= { FAN5-2-20 10 }

UpNRT-20 OBJECT-TYPE
    SYNTAX DisplayString
    MAX-ACCESS read-only
    STATUS current
    DESCRIPTION "Sensor Up NRT"
    ::= { FAN5-2-20 11 }

FAN6-2-21 OBJECT-TYPE
    SYNTAX DisplayString
    MAX-ACCESS read-only
    STATUS current
    DESCRIPTION "Threshold"
    ::= { SensorInfo 21 }

Index-21 OBJECT-TYPE
    SYNTAX Integer32
    MAX-ACCESS read-only
    STATUS current
    DESCRIPTION "Sensor Index"
    ::= { FAN6-2-21 1 }

Number-21 OBJECT-TYPE
    SYNTAX Integer32
    MAX-ACCESS read-only
    STATUS current
    DESCRIPTION "Sensor Number"
    ::= { FAN6-2-21 2 }

Name-21 OBJECT-TYPE
    SYNTAX DisplayString
    MAX-ACCESS read-only
    STATUS current
    DESCRIPTION "Sensor Name"
    ::= { FAN6-2-21 3 }

Status-21 OBJECT-TYPE
    SYNTAX Integer32
    MAX-ACCESS read-only
    STATUS current
    DESCRIPTION "Sensor Status"
    ::= { FAN6-2-21 4 }

Reading-21 OBJECT-TYPE
    SYNTAX DisplayString
    MAX-ACCESS read-only
    STATUS current
    DESCRIPTION "Sensor Reading"
    ::= { FAN6-2-21 5 }

LowNRT-21 OBJECT-TYPE
    SYNTAX DisplayString
    MAX-ACCESS read-only
    STATUS current
    DESCRIPTION "Sensor Low NRT"
    ::= { FAN6-2-21 6 }

LowCT-21 OBJECT-TYPE
    SYNTAX DisplayString
    MAX-ACCESS read-only
    STATUS current
    DESCRIPTION "Sensor Low CT"
    ::= { FAN6-2-21 7 }

LowNCT-21 OBJECT-TYPE
    SYNTAX DisplayString
    MAX-ACCESS read-only
    STATUS current
    DESCRIPTION "Sensor Low NCT"
    ::= { FAN6-2-21 8 }

UpNCT-21 OBJECT-TYPE
    SYNTAX DisplayString
    MAX-ACCESS read-only
    STATUS current
    DESCRIPTION "Sensor Up NCT"
    ::= { FAN6-2-21 9 }

UpCT-21 OBJECT-TYPE
    SYNTAX DisplayString
    MAX-ACCESS read-only
    STATUS current
    DESCRIPTION "Sensor Up CT"
    ::= { FAN6-2-21 10 }

UpNRT-21 OBJECT-TYPE
    SYNTAX DisplayString
    MAX-ACCESS read-only
    STATUS current
    DESCRIPTION "Sensor Up NRT"
    ::= { FAN6-2-21 11 }

FAN7-2-22 OBJECT-TYPE
    SYNTAX DisplayString
    MAX-ACCESS read-only
    STATUS current
    DESCRIPTION "Threshold"
    ::= { SensorInfo 22 }

Index-22 OBJECT-TYPE
    SYNTAX Integer32
    MAX-ACCESS read-only
    STATUS current
    DESCRIPTION "Sensor Index"
    ::= { FAN7-2-22 1 }

Number-22 OBJECT-TYPE
    SYNTAX Integer32
    MAX-ACCESS read-only
    STATUS current
    DESCRIPTION "Sensor Number"
    ::= { FAN7-2-22 2 }

Name-22 OBJECT-TYPE
    SYNTAX DisplayString
    MAX-ACCESS read-only
    STATUS current
    DESCRIPTION "Sensor Name"
    ::= { FAN7-2-22 3 }

Status-22 OBJECT-TYPE
    SYNTAX Integer32
    MAX-ACCESS read-only
    STATUS current
    DESCRIPTION "Sensor Status"
    ::= { FAN7-2-22 4 }

Reading-22 OBJECT-TYPE
    SYNTAX DisplayString
    MAX-ACCESS read-only
    STATUS current
    DESCRIPTION "Sensor Reading"
    ::= { FAN7-2-22 5 }

LowNRT-22 OBJECT-TYPE
    SYNTAX DisplayString
    MAX-ACCESS read-only
    STATUS current
    DESCRIPTION "Sensor Low NRT"
    ::= { FAN7-2-22 6 }

LowCT-22 OBJECT-TYPE
    SYNTAX DisplayString
    MAX-ACCESS read-only
    STATUS current
    DESCRIPTION "Sensor Low CT"
    ::= { FAN7-2-22 7 }

LowNCT-22 OBJECT-TYPE
    SYNTAX DisplayString
    MAX-ACCESS read-only
    STATUS current
    DESCRIPTION "Sensor Low NCT"
    ::= { FAN7-2-22 8 }

UpNCT-22 OBJECT-TYPE
    SYNTAX DisplayString
    MAX-ACCESS read-only
    STATUS current
    DESCRIPTION "Sensor Up NCT"
    ::= { FAN7-2-22 9 }

UpCT-22 OBJECT-TYPE
    SYNTAX DisplayString
    MAX-ACCESS read-only
    STATUS current
    DESCRIPTION "Sensor Up CT"
    ::= { FAN7-2-22 10 }

UpNRT-22 OBJECT-TYPE
    SYNTAX DisplayString
    MAX-ACCESS read-only
    STATUS current
    DESCRIPTION "Sensor Up NRT"
    ::= { FAN7-2-22 11 }

FAN8-2-23 OBJECT-TYPE
    SYNTAX DisplayString
    MAX-ACCESS read-only
    STATUS current
    DESCRIPTION "Threshold"
    ::= { SensorInfo 23 }

Index-23 OBJECT-TYPE
    SYNTAX Integer32
    MAX-ACCESS read-only
    STATUS current
    DESCRIPTION "Sensor Index"
    ::= { FAN8-2-23 1 }

Number-23 OBJECT-TYPE
    SYNTAX Integer32
    MAX-ACCESS read-only
    STATUS current
    DESCRIPTION "Sensor Number"
    ::= { FAN8-2-23 2 }

Name-23 OBJECT-TYPE
    SYNTAX DisplayString
    MAX-ACCESS read-only
    STATUS current
    DESCRIPTION "Sensor Name"
    ::= { FAN8-2-23 3 }

Status-23 OBJECT-TYPE
    SYNTAX Integer32
    MAX-ACCESS read-only
    STATUS current
    DESCRIPTION "Sensor Status"
    ::= { FAN8-2-23 4 }

Reading-23 OBJECT-TYPE
    SYNTAX DisplayString
    MAX-ACCESS read-only
    STATUS current
    DESCRIPTION "Sensor Reading"
    ::= { FAN8-2-23 5 }

LowNRT-23 OBJECT-TYPE
    SYNTAX DisplayString
    MAX-ACCESS read-only
    STATUS current
    DESCRIPTION "Sensor Low NRT"
    ::= { FAN8-2-23 6 }

LowCT-23 OBJECT-TYPE
    SYNTAX DisplayString
    MAX-ACCESS read-only
    STATUS current
    DESCRIPTION "Sensor Low CT"
    ::= { FAN8-2-23 7 }

LowNCT-23 OBJECT-TYPE
    SYNTAX DisplayString
    MAX-ACCESS read-only
    STATUS current
    DESCRIPTION "Sensor Low NCT"
    ::= { FAN8-2-23 8 }

UpNCT-23 OBJECT-TYPE
    SYNTAX DisplayString
    MAX-ACCESS read-only
    STATUS current
    DESCRIPTION "Sensor Up NCT"
    ::= { FAN8-2-23 9 }

UpCT-23 OBJECT-TYPE
    SYNTAX DisplayString
    MAX-ACCESS read-only
    STATUS current
    DESCRIPTION "Sensor Up CT"
    ::= { FAN8-2-23 10 }

UpNRT-23 OBJECT-TYPE
    SYNTAX DisplayString
    MAX-ACCESS read-only
    STATUS current
    DESCRIPTION "Sensor Up NRT"
    ::= { FAN8-2-23 11 }

TEMP-CPU-24 OBJECT-TYPE
    SYNTAX DisplayString
    MAX-ACCESS read-only
    STATUS current
    DESCRIPTION "Threshold"
    ::= { SensorInfo 24 }

Index-24 OBJECT-TYPE
    SYNTAX Integer32
    MAX-ACCESS read-only
    STATUS current
    DESCRIPTION "Sensor Index"
    ::= { TEMP-CPU-24 1 }

Number-24 OBJECT-TYPE
    SYNTAX Integer32
    MAX-ACCESS read-only
    STATUS current
    DESCRIPTION "Sensor Number"
    ::= { TEMP-CPU-24 2 }

Name-24 OBJECT-TYPE
    SYNTAX DisplayString
    MAX-ACCESS read-only
    STATUS current
    DESCRIPTION "Sensor Name"
    ::= { TEMP-CPU-24 3 }

Status-24 OBJECT-TYPE
    SYNTAX Integer32
    MAX-ACCESS read-only
    STATUS current
    DESCRIPTION "Sensor Status"
    ::= { TEMP-CPU-24 4 }

Reading-24 OBJECT-TYPE
    SYNTAX DisplayString
    MAX-ACCESS read-only
    STATUS current
    DESCRIPTION "Sensor Reading"
    ::= { TEMP-CPU-24 5 }

LowNRT-24 OBJECT-TYPE
    SYNTAX DisplayString
    MAX-ACCESS read-only
    STATUS current
    DESCRIPTION "Sensor Low NRT"
    ::= { TEMP-CPU-24 6 }

LowCT-24 OBJECT-TYPE
    SYNTAX DisplayString
    MAX-ACCESS read-only
    STATUS current
    DESCRIPTION "Sensor Low CT"
    ::= { TEMP-CPU-24 7 }

LowNCT-24 OBJECT-TYPE
    SYNTAX DisplayString
    MAX-ACCESS read-only
    STATUS current
    DESCRIPTION "Sensor Low NCT"
    ::= { TEMP-CPU-24 8 }

UpNCT-24 OBJECT-TYPE
    SYNTAX DisplayString
    MAX-ACCESS read-only
    STATUS current
    DESCRIPTION "Sensor Up NCT"
    ::= { TEMP-CPU-24 9 }

UpCT-24 OBJECT-TYPE
    SYNTAX DisplayString
    MAX-ACCESS read-only
    STATUS current
    DESCRIPTION "Sensor Up CT"
    ::= { TEMP-CPU-24 10 }

UpNRT-24 OBJECT-TYPE
    SYNTAX DisplayString
    MAX-ACCESS read-only
    STATUS current
    DESCRIPTION "Sensor Up NRT"
    ::= { TEMP-CPU-24 11 }

FSC-INDEX1-25 OBJECT-TYPE
    SYNTAX DisplayString
    MAX-ACCESS read-only
    STATUS current
    DESCRIPTION "Threshold"
    ::= { SensorInfo 25 }

Index-25 OBJECT-TYPE
    SYNTAX Integer32
    MAX-ACCESS read-only
    STATUS current
    DESCRIPTION "Sensor Index"
    ::= { FSC-INDEX1-25 1 }

Number-25 OBJECT-TYPE
    SYNTAX Integer32
    MAX-ACCESS read-only
    STATUS current
    DESCRIPTION "Sensor Number"
    ::= { FSC-INDEX1-25 2 }

Name-25 OBJECT-TYPE
    SYNTAX DisplayString
    MAX-ACCESS read-only
    STATUS current
    DESCRIPTION "Sensor Name"
    ::= { FSC-INDEX1-25 3 }

Status-25 OBJECT-TYPE
    SYNTAX Integer32
    MAX-ACCESS read-only
    STATUS current
    DESCRIPTION "Sensor Status"
    ::= { FSC-INDEX1-25 4 }

Reading-25 OBJECT-TYPE
    SYNTAX DisplayString
    MAX-ACCESS read-only
    STATUS current
    DESCRIPTION "Sensor Reading"
    ::= { FSC-INDEX1-25 5 }

LowNRT-25 OBJECT-TYPE
    SYNTAX DisplayString
    MAX-ACCESS read-only
    STATUS current
    DESCRIPTION "Sensor Low NRT"
    ::= { FSC-INDEX1-25 6 }

LowCT-25 OBJECT-TYPE
    SYNTAX DisplayString
    MAX-ACCESS read-only
    STATUS current
    DESCRIPTION "Sensor Low CT"
    ::= { FSC-INDEX1-25 7 }

LowNCT-25 OBJECT-TYPE
    SYNTAX DisplayString
    MAX-ACCESS read-only
    STATUS current
    DESCRIPTION "Sensor Low NCT"
    ::= { FSC-INDEX1-25 8 }

UpNCT-25 OBJECT-TYPE
    SYNTAX DisplayString
    MAX-ACCESS read-only
    STATUS current
    DESCRIPTION "Sensor Up NCT"
    ::= { FSC-INDEX1-25 9 }

UpCT-25 OBJECT-TYPE
    SYNTAX DisplayString
    MAX-ACCESS read-only
    STATUS current
    DESCRIPTION "Sensor Up CT"
    ::= { FSC-INDEX1-25 10 }

UpNRT-25 OBJECT-TYPE
    SYNTAX DisplayString
    MAX-ACCESS read-only
    STATUS current
    DESCRIPTION "Sensor Up NRT"
    ::= { FSC-INDEX1-25 11 }

TEMP-DDR5-A1-26 OBJECT-TYPE
    SYNTAX DisplayString
    MAX-ACCESS read-only
    STATUS current
    DESCRIPTION "Threshold"
    ::= { SensorInfo 26 }

Index-26 OBJECT-TYPE
    SYNTAX Integer32
    MAX-ACCESS read-only
    STATUS current
    DESCRIPTION "Sensor Index"
    ::= { TEMP-DDR5-A1-26 1 }

Number-26 OBJECT-TYPE
    SYNTAX Integer32
    MAX-ACCESS read-only
    STATUS current
    DESCRIPTION "Sensor Number"
    ::= { TEMP-DDR5-A1-26 2 }

Name-26 OBJECT-TYPE
    SYNTAX DisplayString
    MAX-ACCESS read-only
    STATUS current
    DESCRIPTION "Sensor Name"
    ::= { TEMP-DDR5-A1-26 3 }

Status-26 OBJECT-TYPE
    SYNTAX Integer32
    MAX-ACCESS read-only
    STATUS current
    DESCRIPTION "Sensor Status"
    ::= { TEMP-DDR5-A1-26 4 }

Reading-26 OBJECT-TYPE
    SYNTAX DisplayString
    MAX-ACCESS read-only
    STATUS current
    DESCRIPTION "Sensor Reading"
    ::= { TEMP-DDR5-A1-26 5 }

LowNRT-26 OBJECT-TYPE
    SYNTAX DisplayString
    MAX-ACCESS read-only
    STATUS current
    DESCRIPTION "Sensor Low NRT"
    ::= { TEMP-DDR5-A1-26 6 }

LowCT-26 OBJECT-TYPE
    SYNTAX DisplayString
    MAX-ACCESS read-only
    STATUS current
    DESCRIPTION "Sensor Low CT"
    ::= { TEMP-DDR5-A1-26 7 }

LowNCT-26 OBJECT-TYPE
    SYNTAX DisplayString
    MAX-ACCESS read-only
    STATUS current
    DESCRIPTION "Sensor Low NCT"
    ::= { TEMP-DDR5-A1-26 8 }

UpNCT-26 OBJECT-TYPE
    SYNTAX DisplayString
    MAX-ACCESS read-only
    STATUS current
    DESCRIPTION "Sensor Up NCT"
    ::= { TEMP-DDR5-A1-26 9 }

UpCT-26 OBJECT-TYPE
    SYNTAX DisplayString
    MAX-ACCESS read-only
    STATUS current
    DESCRIPTION "Sensor Up CT"
    ::= { TEMP-DDR5-A1-26 10 }

UpNRT-26 OBJECT-TYPE
    SYNTAX DisplayString
    MAX-ACCESS read-only
    STATUS current
    DESCRIPTION "Sensor Up NRT"
    ::= { TEMP-DDR5-A1-26 11 }

TEMP-DDR5-A2-27 OBJECT-TYPE
    SYNTAX DisplayString
    MAX-ACCESS read-only
    STATUS current
    DESCRIPTION "Threshold"
    ::= { SensorInfo 27 }

Index-27 OBJECT-TYPE
    SYNTAX Integer32
    MAX-ACCESS read-only
    STATUS current
    DESCRIPTION "Sensor Index"
    ::= { TEMP-DDR5-A2-27 1 }

Number-27 OBJECT-TYPE
    SYNTAX Integer32
    MAX-ACCESS read-only
    STATUS current
    DESCRIPTION "Sensor Number"
    ::= { TEMP-DDR5-A2-27 2 }

Name-27 OBJECT-TYPE
    SYNTAX DisplayString
    MAX-ACCESS read-only
    STATUS current
    DESCRIPTION "Sensor Name"
    ::= { TEMP-DDR5-A2-27 3 }

Status-27 OBJECT-TYPE
    SYNTAX Integer32
    MAX-ACCESS read-only
    STATUS current
    DESCRIPTION "Sensor Status"
    ::= { TEMP-DDR5-A2-27 4 }

Reading-27 OBJECT-TYPE
    SYNTAX DisplayString
    MAX-ACCESS read-only
    STATUS current
    DESCRIPTION "Sensor Reading"
    ::= { TEMP-DDR5-A2-27 5 }

LowNRT-27 OBJECT-TYPE
    SYNTAX DisplayString
    MAX-ACCESS read-only
    STATUS current
    DESCRIPTION "Sensor Low NRT"
    ::= { TEMP-DDR5-A2-27 6 }

LowCT-27 OBJECT-TYPE
    SYNTAX DisplayString
    MAX-ACCESS read-only
    STATUS current
    DESCRIPTION "Sensor Low CT"
    ::= { TEMP-DDR5-A2-27 7 }

LowNCT-27 OBJECT-TYPE
    SYNTAX DisplayString
    MAX-ACCESS read-only
    STATUS current
    DESCRIPTION "Sensor Low NCT"
    ::= { TEMP-DDR5-A2-27 8 }

UpNCT-27 OBJECT-TYPE
    SYNTAX DisplayString
    MAX-ACCESS read-only
    STATUS current
    DESCRIPTION "Sensor Up NCT"
    ::= { TEMP-DDR5-A2-27 9 }

UpCT-27 OBJECT-TYPE
    SYNTAX DisplayString
    MAX-ACCESS read-only
    STATUS current
    DESCRIPTION "Sensor Up CT"
    ::= { TEMP-DDR5-A2-27 10 }

UpNRT-27 OBJECT-TYPE
    SYNTAX DisplayString
    MAX-ACCESS read-only
    STATUS current
    DESCRIPTION "Sensor Up NRT"
    ::= { TEMP-DDR5-A2-27 11 }

TEMP-DDR5-B1-28 OBJECT-TYPE
    SYNTAX DisplayString
    MAX-ACCESS read-only
    STATUS current
    DESCRIPTION "Threshold"
    ::= { SensorInfo 28 }

Index-28 OBJECT-TYPE
    SYNTAX Integer32
    MAX-ACCESS read-only
    STATUS current
    DESCRIPTION "Sensor Index"
    ::= { TEMP-DDR5-B1-28 1 }

Number-28 OBJECT-TYPE
    SYNTAX Integer32
    MAX-ACCESS read-only
    STATUS current
    DESCRIPTION "Sensor Number"
    ::= { TEMP-DDR5-B1-28 2 }

Name-28 OBJECT-TYPE
    SYNTAX DisplayString
    MAX-ACCESS read-only
    STATUS current
    DESCRIPTION "Sensor Name"
    ::= { TEMP-DDR5-B1-28 3 }

Status-28 OBJECT-TYPE
    SYNTAX Integer32
    MAX-ACCESS read-only
    STATUS current
    DESCRIPTION "Sensor Status"
    ::= { TEMP-DDR5-B1-28 4 }

Reading-28 OBJECT-TYPE
    SYNTAX DisplayString
    MAX-ACCESS read-only
    STATUS current
    DESCRIPTION "Sensor Reading"
    ::= { TEMP-DDR5-B1-28 5 }

LowNRT-28 OBJECT-TYPE
    SYNTAX DisplayString
    MAX-ACCESS read-only
    STATUS current
    DESCRIPTION "Sensor Low NRT"
    ::= { TEMP-DDR5-B1-28 6 }

LowCT-28 OBJECT-TYPE
    SYNTAX DisplayString
    MAX-ACCESS read-only
    STATUS current
    DESCRIPTION "Sensor Low CT"
    ::= { TEMP-DDR5-B1-28 7 }

LowNCT-28 OBJECT-TYPE
    SYNTAX DisplayString
    MAX-ACCESS read-only
    STATUS current
    DESCRIPTION "Sensor Low NCT"
    ::= { TEMP-DDR5-B1-28 8 }

UpNCT-28 OBJECT-TYPE
    SYNTAX DisplayString
    MAX-ACCESS read-only
    STATUS current
    DESCRIPTION "Sensor Up NCT"
    ::= { TEMP-DDR5-B1-28 9 }

UpCT-28 OBJECT-TYPE
    SYNTAX DisplayString
    MAX-ACCESS read-only
    STATUS current
    DESCRIPTION "Sensor Up CT"
    ::= { TEMP-DDR5-B1-28 10 }

UpNRT-28 OBJECT-TYPE
    SYNTAX DisplayString
    MAX-ACCESS read-only
    STATUS current
    DESCRIPTION "Sensor Up NRT"
    ::= { TEMP-DDR5-B1-28 11 }

TEMP-DDR5-B2-29 OBJECT-TYPE
    SYNTAX DisplayString
    MAX-ACCESS read-only
    STATUS current
    DESCRIPTION "Threshold"
    ::= { SensorInfo 29 }

Index-29 OBJECT-TYPE
    SYNTAX Integer32
    MAX-ACCESS read-only
    STATUS current
    DESCRIPTION "Sensor Index"
    ::= { TEMP-DDR5-B2-29 1 }

Number-29 OBJECT-TYPE
    SYNTAX Integer32
    MAX-ACCESS read-only
    STATUS current
    DESCRIPTION "Sensor Number"
    ::= { TEMP-DDR5-B2-29 2 }

Name-29 OBJECT-TYPE
    SYNTAX DisplayString
    MAX-ACCESS read-only
    STATUS current
    DESCRIPTION "Sensor Name"
    ::= { TEMP-DDR5-B2-29 3 }

Status-29 OBJECT-TYPE
    SYNTAX Integer32
    MAX-ACCESS read-only
    STATUS current
    DESCRIPTION "Sensor Status"
    ::= { TEMP-DDR5-B2-29 4 }

Reading-29 OBJECT-TYPE
    SYNTAX DisplayString
    MAX-ACCESS read-only
    STATUS current
    DESCRIPTION "Sensor Reading"
    ::= { TEMP-DDR5-B2-29 5 }

LowNRT-29 OBJECT-TYPE
    SYNTAX DisplayString
    MAX-ACCESS read-only
    STATUS current
    DESCRIPTION "Sensor Low NRT"
    ::= { TEMP-DDR5-B2-29 6 }

LowCT-29 OBJECT-TYPE
    SYNTAX DisplayString
    MAX-ACCESS read-only
    STATUS current
    DESCRIPTION "Sensor Low CT"
    ::= { TEMP-DDR5-B2-29 7 }

LowNCT-29 OBJECT-TYPE
    SYNTAX DisplayString
    MAX-ACCESS read-only
    STATUS current
    DESCRIPTION "Sensor Low NCT"
    ::= { TEMP-DDR5-B2-29 8 }

UpNCT-29 OBJECT-TYPE
    SYNTAX DisplayString
    MAX-ACCESS read-only
    STATUS current
    DESCRIPTION "Sensor Up NCT"
    ::= { TEMP-DDR5-B2-29 9 }

UpCT-29 OBJECT-TYPE
    SYNTAX DisplayString
    MAX-ACCESS read-only
    STATUS current
    DESCRIPTION "Sensor Up CT"
    ::= { TEMP-DDR5-B2-29 10 }

UpNRT-29 OBJECT-TYPE
    SYNTAX DisplayString
    MAX-ACCESS read-only
    STATUS current
    DESCRIPTION "Sensor Up NRT"
    ::= { TEMP-DDR5-B2-29 11 }

TEMP-CARD-SIDE-30 OBJECT-TYPE
    SYNTAX DisplayString
    MAX-ACCESS read-only
    STATUS current
    DESCRIPTION "Threshold"
    ::= { SensorInfo 30 }

Index-30 OBJECT-TYPE
    SYNTAX Integer32
    MAX-ACCESS read-only
    STATUS current
    DESCRIPTION "Sensor Index"
    ::= { TEMP-CARD-SIDE-30 1 }

Number-30 OBJECT-TYPE
    SYNTAX Integer32
    MAX-ACCESS read-only
    STATUS current
    DESCRIPTION "Sensor Number"
    ::= { TEMP-CARD-SIDE-30 2 }

Name-30 OBJECT-TYPE
    SYNTAX DisplayString
    MAX-ACCESS read-only
    STATUS current
    DESCRIPTION "Sensor Name"
    ::= { TEMP-CARD-SIDE-30 3 }

Status-30 OBJECT-TYPE
    SYNTAX Integer32
    MAX-ACCESS read-only
    STATUS current
    DESCRIPTION "Sensor Status"
    ::= { TEMP-CARD-SIDE-30 4 }

Reading-30 OBJECT-TYPE
    SYNTAX DisplayString
    MAX-ACCESS read-only
    STATUS current
    DESCRIPTION "Sensor Reading"
    ::= { TEMP-CARD-SIDE-30 5 }

LowNRT-30 OBJECT-TYPE
    SYNTAX DisplayString
    MAX-ACCESS read-only
    STATUS current
    DESCRIPTION "Sensor Low NRT"
    ::= { TEMP-CARD-SIDE-30 6 }

LowCT-30 OBJECT-TYPE
    SYNTAX DisplayString
    MAX-ACCESS read-only
    STATUS current
    DESCRIPTION "Sensor Low CT"
    ::= { TEMP-CARD-SIDE-30 7 }

LowNCT-30 OBJECT-TYPE
    SYNTAX DisplayString
    MAX-ACCESS read-only
    STATUS current
    DESCRIPTION "Sensor Low NCT"
    ::= { TEMP-CARD-SIDE-30 8 }

UpNCT-30 OBJECT-TYPE
    SYNTAX DisplayString
    MAX-ACCESS read-only
    STATUS current
    DESCRIPTION "Sensor Up NCT"
    ::= { TEMP-CARD-SIDE-30 9 }

UpCT-30 OBJECT-TYPE
    SYNTAX DisplayString
    MAX-ACCESS read-only
    STATUS current
    DESCRIPTION "Sensor Up CT"
    ::= { TEMP-CARD-SIDE-30 10 }

UpNRT-30 OBJECT-TYPE
    SYNTAX DisplayString
    MAX-ACCESS read-only
    STATUS current
    DESCRIPTION "Sensor Up NRT"
    ::= { TEMP-CARD-SIDE-30 11 }

SYSTEM-INLET-31 OBJECT-TYPE
    SYNTAX DisplayString
    MAX-ACCESS read-only
    STATUS current
    DESCRIPTION "Threshold"
    ::= { SensorInfo 31 }

Index-31 OBJECT-TYPE
    SYNTAX Integer32
    MAX-ACCESS read-only
    STATUS current
    DESCRIPTION "Sensor Index"
    ::= { SYSTEM-INLET-31 1 }

Number-31 OBJECT-TYPE
    SYNTAX Integer32
    MAX-ACCESS read-only
    STATUS current
    DESCRIPTION "Sensor Number"
    ::= { SYSTEM-INLET-31 2 }

Name-31 OBJECT-TYPE
    SYNTAX DisplayString
    MAX-ACCESS read-only
    STATUS current
    DESCRIPTION "Sensor Name"
    ::= { SYSTEM-INLET-31 3 }

Status-31 OBJECT-TYPE
    SYNTAX Integer32
    MAX-ACCESS read-only
    STATUS current
    DESCRIPTION "Sensor Status"
    ::= { SYSTEM-INLET-31 4 }

Reading-31 OBJECT-TYPE
    SYNTAX DisplayString
    MAX-ACCESS read-only
    STATUS current
    DESCRIPTION "Sensor Reading"
    ::= { SYSTEM-INLET-31 5 }

LowNRT-31 OBJECT-TYPE
    SYNTAX DisplayString
    MAX-ACCESS read-only
    STATUS current
    DESCRIPTION "Sensor Low NRT"
    ::= { SYSTEM-INLET-31 6 }

LowCT-31 OBJECT-TYPE
    SYNTAX DisplayString
    MAX-ACCESS read-only
    STATUS current
    DESCRIPTION "Sensor Low CT"
    ::= { SYSTEM-INLET-31 7 }

LowNCT-31 OBJECT-TYPE
    SYNTAX DisplayString
    MAX-ACCESS read-only
    STATUS current
    DESCRIPTION "Sensor Low NCT"
    ::= { SYSTEM-INLET-31 8 }

UpNCT-31 OBJECT-TYPE
    SYNTAX DisplayString
    MAX-ACCESS read-only
    STATUS current
    DESCRIPTION "Sensor Up NCT"
    ::= { SYSTEM-INLET-31 9 }

UpCT-31 OBJECT-TYPE
    SYNTAX DisplayString
    MAX-ACCESS read-only
    STATUS current
    DESCRIPTION "Sensor Up CT"
    ::= { SYSTEM-INLET-31 10 }

UpNRT-31 OBJECT-TYPE
    SYNTAX DisplayString
    MAX-ACCESS read-only
    STATUS current
    DESCRIPTION "Sensor Up NRT"
    ::= { SYSTEM-INLET-31 11 }

TEMP-M-2-32 OBJECT-TYPE
    SYNTAX DisplayString
    MAX-ACCESS read-only
    STATUS current
    DESCRIPTION "Threshold"
    ::= { SensorInfo 32 }

Index-32 OBJECT-TYPE
    SYNTAX Integer32
    MAX-ACCESS read-only
    STATUS current
    DESCRIPTION "Sensor Index"
    ::= { TEMP-M-2-32 1 }

Number-32 OBJECT-TYPE
    SYNTAX Integer32
    MAX-ACCESS read-only
    STATUS current
    DESCRIPTION "Sensor Number"
    ::= { TEMP-M-2-32 2 }

Name-32 OBJECT-TYPE
    SYNTAX DisplayString
    MAX-ACCESS read-only
    STATUS current
    DESCRIPTION "Sensor Name"
    ::= { TEMP-M-2-32 3 }

Status-32 OBJECT-TYPE
    SYNTAX Integer32
    MAX-ACCESS read-only
    STATUS current
    DESCRIPTION "Sensor Status"
    ::= { TEMP-M-2-32 4 }

Reading-32 OBJECT-TYPE
    SYNTAX DisplayString
    MAX-ACCESS read-only
    STATUS current
    DESCRIPTION "Sensor Reading"
    ::= { TEMP-M-2-32 5 }

LowNRT-32 OBJECT-TYPE
    SYNTAX DisplayString
    MAX-ACCESS read-only
    STATUS current
    DESCRIPTION "Sensor Low NRT"
    ::= { TEMP-M-2-32 6 }

LowCT-32 OBJECT-TYPE
    SYNTAX DisplayString
    MAX-ACCESS read-only
    STATUS current
    DESCRIPTION "Sensor Low CT"
    ::= { TEMP-M-2-32 7 }

LowNCT-32 OBJECT-TYPE
    SYNTAX DisplayString
    MAX-ACCESS read-only
    STATUS current
    DESCRIPTION "Sensor Low NCT"
    ::= { TEMP-M-2-32 8 }

UpNCT-32 OBJECT-TYPE
    SYNTAX DisplayString
    MAX-ACCESS read-only
    STATUS current
    DESCRIPTION "Sensor Up NCT"
    ::= { TEMP-M-2-32 9 }

UpCT-32 OBJECT-TYPE
    SYNTAX DisplayString
    MAX-ACCESS read-only
    STATUS current
    DESCRIPTION "Sensor Up CT"
    ::= { TEMP-M-2-32 10 }

UpNRT-32 OBJECT-TYPE
    SYNTAX DisplayString
    MAX-ACCESS read-only
    STATUS current
    DESCRIPTION "Sensor Up NRT"
    ::= { TEMP-M-2-32 11 }

TEMP-MB-33 OBJECT-TYPE
    SYNTAX DisplayString
    MAX-ACCESS read-only
    STATUS current
    DESCRIPTION "Threshold"
    ::= { SensorInfo 33 }

Index-33 OBJECT-TYPE
    SYNTAX Integer32
    MAX-ACCESS read-only
    STATUS current
    DESCRIPTION "Sensor Index"
    ::= { TEMP-MB-33 1 }

Number-33 OBJECT-TYPE
    SYNTAX Integer32
    MAX-ACCESS read-only
    STATUS current
    DESCRIPTION "Sensor Number"
    ::= { TEMP-MB-33 2 }

Name-33 OBJECT-TYPE
    SYNTAX DisplayString
    MAX-ACCESS read-only
    STATUS current
    DESCRIPTION "Sensor Name"
    ::= { TEMP-MB-33 3 }

Status-33 OBJECT-TYPE
    SYNTAX Integer32
    MAX-ACCESS read-only
    STATUS current
    DESCRIPTION "Sensor Status"
    ::= { TEMP-MB-33 4 }

Reading-33 OBJECT-TYPE
    SYNTAX DisplayString
    MAX-ACCESS read-only
    STATUS current
    DESCRIPTION "Sensor Reading"
    ::= { TEMP-MB-33 5 }

LowNRT-33 OBJECT-TYPE
    SYNTAX DisplayString
    MAX-ACCESS read-only
    STATUS current
    DESCRIPTION "Sensor Low NRT"
    ::= { TEMP-MB-33 6 }

LowCT-33 OBJECT-TYPE
    SYNTAX DisplayString
    MAX-ACCESS read-only
    STATUS current
    DESCRIPTION "Sensor Low CT"
    ::= { TEMP-MB-33 7 }

LowNCT-33 OBJECT-TYPE
    SYNTAX DisplayString
    MAX-ACCESS read-only
    STATUS current
    DESCRIPTION "Sensor Low NCT"
    ::= { TEMP-MB-33 8 }

UpNCT-33 OBJECT-TYPE
    SYNTAX DisplayString
    MAX-ACCESS read-only
    STATUS current
    DESCRIPTION "Sensor Up NCT"
    ::= { TEMP-MB-33 9 }

UpCT-33 OBJECT-TYPE
    SYNTAX DisplayString
    MAX-ACCESS read-only
    STATUS current
    DESCRIPTION "Sensor Up CT"
    ::= { TEMP-MB-33 10 }

UpNRT-33 OBJECT-TYPE
    SYNTAX DisplayString
    MAX-ACCESS read-only
    STATUS current
    DESCRIPTION "Sensor Up NRT"
    ::= { TEMP-MB-33 11 }

TEMP-TR1-34 OBJECT-TYPE
    SYNTAX DisplayString
    MAX-ACCESS read-only
    STATUS current
    DESCRIPTION "Threshold"
    ::= { SensorInfo 34 }

Index-34 OBJECT-TYPE
    SYNTAX Integer32
    MAX-ACCESS read-only
    STATUS current
    DESCRIPTION "Sensor Index"
    ::= { TEMP-TR1-34 1 }

Number-34 OBJECT-TYPE
    SYNTAX Integer32
    MAX-ACCESS read-only
    STATUS current
    DESCRIPTION "Sensor Number"
    ::= { TEMP-TR1-34 2 }

Name-34 OBJECT-TYPE
    SYNTAX DisplayString
    MAX-ACCESS read-only
    STATUS current
    DESCRIPTION "Sensor Name"
    ::= { TEMP-TR1-34 3 }

Status-34 OBJECT-TYPE
    SYNTAX Integer32
    MAX-ACCESS read-only
    STATUS current
    DESCRIPTION "Sensor Status"
    ::= { TEMP-TR1-34 4 }

Reading-34 OBJECT-TYPE
    SYNTAX DisplayString
    MAX-ACCESS read-only
    STATUS current
    DESCRIPTION "Sensor Reading"
    ::= { TEMP-TR1-34 5 }

LowNRT-34 OBJECT-TYPE
    SYNTAX DisplayString
    MAX-ACCESS read-only
    STATUS current
    DESCRIPTION "Sensor Low NRT"
    ::= { TEMP-TR1-34 6 }

LowCT-34 OBJECT-TYPE
    SYNTAX DisplayString
    MAX-ACCESS read-only
    STATUS current
    DESCRIPTION "Sensor Low CT"
    ::= { TEMP-TR1-34 7 }

LowNCT-34 OBJECT-TYPE
    SYNTAX DisplayString
    MAX-ACCESS read-only
    STATUS current
    DESCRIPTION "Sensor Low NCT"
    ::= { TEMP-TR1-34 8 }

UpNCT-34 OBJECT-TYPE
    SYNTAX DisplayString
    MAX-ACCESS read-only
    STATUS current
    DESCRIPTION "Sensor Up NCT"
    ::= { TEMP-TR1-34 9 }

UpCT-34 OBJECT-TYPE
    SYNTAX DisplayString
    MAX-ACCESS read-only
    STATUS current
    DESCRIPTION "Sensor Up CT"
    ::= { TEMP-TR1-34 10 }

UpNRT-34 OBJECT-TYPE
    SYNTAX DisplayString
    MAX-ACCESS read-only
    STATUS current
    DESCRIPTION "Sensor Up NRT"
    ::= { TEMP-TR1-34 11 }

TEMP-BCM-LAN-35 OBJECT-TYPE
    SYNTAX DisplayString
    MAX-ACCESS read-only
    STATUS current
    DESCRIPTION "Threshold"
    ::= { SensorInfo 35 }

Index-35 OBJECT-TYPE
    SYNTAX Integer32
    MAX-ACCESS read-only
    STATUS current
    DESCRIPTION "Sensor Index"
    ::= { TEMP-BCM-LAN-35 1 }

Number-35 OBJECT-TYPE
    SYNTAX Integer32
    MAX-ACCESS read-only
    STATUS current
    DESCRIPTION "Sensor Number"
    ::= { TEMP-BCM-LAN-35 2 }

Name-35 OBJECT-TYPE
    SYNTAX DisplayString
    MAX-ACCESS read-only
    STATUS current
    DESCRIPTION "Sensor Name"
    ::= { TEMP-BCM-LAN-35 3 }

Status-35 OBJECT-TYPE
    SYNTAX Integer32
    MAX-ACCESS read-only
    STATUS current
    DESCRIPTION "Sensor Status"
    ::= { TEMP-BCM-LAN-35 4 }

Reading-35 OBJECT-TYPE
    SYNTAX DisplayString
    MAX-ACCESS read-only
    STATUS current
    DESCRIPTION "Sensor Reading"
    ::= { TEMP-BCM-LAN-35 5 }

LowNRT-35 OBJECT-TYPE
    SYNTAX DisplayString
    MAX-ACCESS read-only
    STATUS current
    DESCRIPTION "Sensor Low NRT"
    ::= { TEMP-BCM-LAN-35 6 }

LowCT-35 OBJECT-TYPE
    SYNTAX DisplayString
    MAX-ACCESS read-only
    STATUS current
    DESCRIPTION "Sensor Low CT"
    ::= { TEMP-BCM-LAN-35 7 }

LowNCT-35 OBJECT-TYPE
    SYNTAX DisplayString
    MAX-ACCESS read-only
    STATUS current
    DESCRIPTION "Sensor Low NCT"
    ::= { TEMP-BCM-LAN-35 8 }

UpNCT-35 OBJECT-TYPE
    SYNTAX DisplayString
    MAX-ACCESS read-only
    STATUS current
    DESCRIPTION "Sensor Up NCT"
    ::= { TEMP-BCM-LAN-35 9 }

UpCT-35 OBJECT-TYPE
    SYNTAX DisplayString
    MAX-ACCESS read-only
    STATUS current
    DESCRIPTION "Sensor Up CT"
    ::= { TEMP-BCM-LAN-35 10 }

UpNRT-35 OBJECT-TYPE
    SYNTAX DisplayString
    MAX-ACCESS read-only
    STATUS current
    DESCRIPTION "Sensor Up NRT"
    ::= { TEMP-BCM-LAN-35 11 }

TEMP-GPU-36 OBJECT-TYPE
    SYNTAX DisplayString
    MAX-ACCESS read-only
    STATUS current
    DESCRIPTION "Threshold"
    ::= { SensorInfo 36 }

Index-36 OBJECT-TYPE
    SYNTAX Integer32
    MAX-ACCESS read-only
    STATUS current
    DESCRIPTION "Sensor Index"
    ::= { TEMP-GPU-36 1 }

Number-36 OBJECT-TYPE
    SYNTAX Integer32
    MAX-ACCESS read-only
    STATUS current
    DESCRIPTION "Sensor Number"
    ::= { TEMP-GPU-36 2 }

Name-36 OBJECT-TYPE
    SYNTAX DisplayString
    MAX-ACCESS read-only
    STATUS current
    DESCRIPTION "Sensor Name"
    ::= { TEMP-GPU-36 3 }

Status-36 OBJECT-TYPE
    SYNTAX Integer32
    MAX-ACCESS read-only
    STATUS current
    DESCRIPTION "Sensor Status"
    ::= { TEMP-GPU-36 4 }

Reading-36 OBJECT-TYPE
    SYNTAX DisplayString
    MAX-ACCESS read-only
    STATUS current
    DESCRIPTION "Sensor Reading"
    ::= { TEMP-GPU-36 5 }

LowNRT-36 OBJECT-TYPE
    SYNTAX DisplayString
    MAX-ACCESS read-only
    STATUS current
    DESCRIPTION "Sensor Low NRT"
    ::= { TEMP-GPU-36 6 }

LowCT-36 OBJECT-TYPE
    SYNTAX DisplayString
    MAX-ACCESS read-only
    STATUS current
    DESCRIPTION "Sensor Low CT"
    ::= { TEMP-GPU-36 7 }

LowNCT-36 OBJECT-TYPE
    SYNTAX DisplayString
    MAX-ACCESS read-only
    STATUS current
    DESCRIPTION "Sensor Low NCT"
    ::= { TEMP-GPU-36 8 }

UpNCT-36 OBJECT-TYPE
    SYNTAX DisplayString
    MAX-ACCESS read-only
    STATUS current
    DESCRIPTION "Sensor Up NCT"
    ::= { TEMP-GPU-36 9 }

UpCT-36 OBJECT-TYPE
    SYNTAX DisplayString
    MAX-ACCESS read-only
    STATUS current
    DESCRIPTION "Sensor Up CT"
    ::= { TEMP-GPU-36 10 }

UpNRT-36 OBJECT-TYPE
    SYNTAX DisplayString
    MAX-ACCESS read-only
    STATUS current
    DESCRIPTION "Sensor Up NRT"
    ::= { TEMP-GPU-36 11 }

VOLT-PSU1-VIN-37 OBJECT-TYPE
    SYNTAX DisplayString
    MAX-ACCESS read-only
    STATUS current
    DESCRIPTION "Threshold"
    ::= { SensorInfo 37 }

Index-37 OBJECT-TYPE
    SYNTAX Integer32
    MAX-ACCESS read-only
    STATUS current
    DESCRIPTION "Sensor Index"
    ::= { VOLT-PSU1-VIN-37 1 }

Number-37 OBJECT-TYPE
    SYNTAX Integer32
    MAX-ACCESS read-only
    STATUS current
    DESCRIPTION "Sensor Number"
    ::= { VOLT-PSU1-VIN-37 2 }

Name-37 OBJECT-TYPE
    SYNTAX DisplayString
    MAX-ACCESS read-only
    STATUS current
    DESCRIPTION "Sensor Name"
    ::= { VOLT-PSU1-VIN-37 3 }

Status-37 OBJECT-TYPE
    SYNTAX Integer32
    MAX-ACCESS read-only
    STATUS current
    DESCRIPTION "Sensor Status"
    ::= { VOLT-PSU1-VIN-37 4 }

Reading-37 OBJECT-TYPE
    SYNTAX DisplayString
    MAX-ACCESS read-only
    STATUS current
    DESCRIPTION "Sensor Reading"
    ::= { VOLT-PSU1-VIN-37 5 }

LowNRT-37 OBJECT-TYPE
    SYNTAX DisplayString
    MAX-ACCESS read-only
    STATUS current
    DESCRIPTION "Sensor Low NRT"
    ::= { VOLT-PSU1-VIN-37 6 }

LowCT-37 OBJECT-TYPE
    SYNTAX DisplayString
    MAX-ACCESS read-only
    STATUS current
    DESCRIPTION "Sensor Low CT"
    ::= { VOLT-PSU1-VIN-37 7 }

LowNCT-37 OBJECT-TYPE
    SYNTAX DisplayString
    MAX-ACCESS read-only
    STATUS current
    DESCRIPTION "Sensor Low NCT"
    ::= { VOLT-PSU1-VIN-37 8 }

UpNCT-37 OBJECT-TYPE
    SYNTAX DisplayString
    MAX-ACCESS read-only
    STATUS current
    DESCRIPTION "Sensor Up NCT"
    ::= { VOLT-PSU1-VIN-37 9 }

UpCT-37 OBJECT-TYPE
    SYNTAX DisplayString
    MAX-ACCESS read-only
    STATUS current
    DESCRIPTION "Sensor Up CT"
    ::= { VOLT-PSU1-VIN-37 10 }

UpNRT-37 OBJECT-TYPE
    SYNTAX DisplayString
    MAX-ACCESS read-only
    STATUS current
    DESCRIPTION "Sensor Up NRT"
    ::= { VOLT-PSU1-VIN-37 11 }

CUR-PSU1-IOUT-38 OBJECT-TYPE
    SYNTAX DisplayString
    MAX-ACCESS read-only
    STATUS current
    DESCRIPTION "Threshold"
    ::= { SensorInfo 38 }

Index-38 OBJECT-TYPE
    SYNTAX Integer32
    MAX-ACCESS read-only
    STATUS current
    DESCRIPTION "Sensor Index"
    ::= { CUR-PSU1-IOUT-38 1 }

Number-38 OBJECT-TYPE
    SYNTAX Integer32
    MAX-ACCESS read-only
    STATUS current
    DESCRIPTION "Sensor Number"
    ::= { CUR-PSU1-IOUT-38 2 }

Name-38 OBJECT-TYPE
    SYNTAX DisplayString
    MAX-ACCESS read-only
    STATUS current
    DESCRIPTION "Sensor Name"
    ::= { CUR-PSU1-IOUT-38 3 }

Status-38 OBJECT-TYPE
    SYNTAX Integer32
    MAX-ACCESS read-only
    STATUS current
    DESCRIPTION "Sensor Status"
    ::= { CUR-PSU1-IOUT-38 4 }

Reading-38 OBJECT-TYPE
    SYNTAX DisplayString
    MAX-ACCESS read-only
    STATUS current
    DESCRIPTION "Sensor Reading"
    ::= { CUR-PSU1-IOUT-38 5 }

LowNRT-38 OBJECT-TYPE
    SYNTAX DisplayString
    MAX-ACCESS read-only
    STATUS current
    DESCRIPTION "Sensor Low NRT"
    ::= { CUR-PSU1-IOUT-38 6 }

LowCT-38 OBJECT-TYPE
    SYNTAX DisplayString
    MAX-ACCESS read-only
    STATUS current
    DESCRIPTION "Sensor Low CT"
    ::= { CUR-PSU1-IOUT-38 7 }

LowNCT-38 OBJECT-TYPE
    SYNTAX DisplayString
    MAX-ACCESS read-only
    STATUS current
    DESCRIPTION "Sensor Low NCT"
    ::= { CUR-PSU1-IOUT-38 8 }

UpNCT-38 OBJECT-TYPE
    SYNTAX DisplayString
    MAX-ACCESS read-only
    STATUS current
    DESCRIPTION "Sensor Up NCT"
    ::= { CUR-PSU1-IOUT-38 9 }

UpCT-38 OBJECT-TYPE
    SYNTAX DisplayString
    MAX-ACCESS read-only
    STATUS current
    DESCRIPTION "Sensor Up CT"
    ::= { CUR-PSU1-IOUT-38 10 }

UpNRT-38 OBJECT-TYPE
    SYNTAX DisplayString
    MAX-ACCESS read-only
    STATUS current
    DESCRIPTION "Sensor Up NRT"
    ::= { CUR-PSU1-IOUT-38 11 }

PWR-PSU1-PIN-39 OBJECT-TYPE
    SYNTAX DisplayString
    MAX-ACCESS read-only
    STATUS current
    DESCRIPTION "Threshold"
    ::= { SensorInfo 39 }

Index-39 OBJECT-TYPE
    SYNTAX Integer32
    MAX-ACCESS read-only
    STATUS current
    DESCRIPTION "Sensor Index"
    ::= { PWR-PSU1-PIN-39 1 }

Number-39 OBJECT-TYPE
    SYNTAX Integer32
    MAX-ACCESS read-only
    STATUS current
    DESCRIPTION "Sensor Number"
    ::= { PWR-PSU1-PIN-39 2 }

Name-39 OBJECT-TYPE
    SYNTAX DisplayString
    MAX-ACCESS read-only
    STATUS current
    DESCRIPTION "Sensor Name"
    ::= { PWR-PSU1-PIN-39 3 }

Status-39 OBJECT-TYPE
    SYNTAX Integer32
    MAX-ACCESS read-only
    STATUS current
    DESCRIPTION "Sensor Status"
    ::= { PWR-PSU1-PIN-39 4 }

Reading-39 OBJECT-TYPE
    SYNTAX DisplayString
    MAX-ACCESS read-only
    STATUS current
    DESCRIPTION "Sensor Reading"
    ::= { PWR-PSU1-PIN-39 5 }

LowNRT-39 OBJECT-TYPE
    SYNTAX DisplayString
    MAX-ACCESS read-only
    STATUS current
    DESCRIPTION "Sensor Low NRT"
    ::= { PWR-PSU1-PIN-39 6 }

LowCT-39 OBJECT-TYPE
    SYNTAX DisplayString
    MAX-ACCESS read-only
    STATUS current
    DESCRIPTION "Sensor Low CT"
    ::= { PWR-PSU1-PIN-39 7 }

LowNCT-39 OBJECT-TYPE
    SYNTAX DisplayString
    MAX-ACCESS read-only
    STATUS current
    DESCRIPTION "Sensor Low NCT"
    ::= { PWR-PSU1-PIN-39 8 }

UpNCT-39 OBJECT-TYPE
    SYNTAX DisplayString
    MAX-ACCESS read-only
    STATUS current
    DESCRIPTION "Sensor Up NCT"
    ::= { PWR-PSU1-PIN-39 9 }

UpCT-39 OBJECT-TYPE
    SYNTAX DisplayString
    MAX-ACCESS read-only
    STATUS current
    DESCRIPTION "Sensor Up CT"
    ::= { PWR-PSU1-PIN-39 10 }

UpNRT-39 OBJECT-TYPE
    SYNTAX DisplayString
    MAX-ACCESS read-only
    STATUS current
    DESCRIPTION "Sensor Up NRT"
    ::= { PWR-PSU1-PIN-39 11 }

PWR-PSU1-POUT-40 OBJECT-TYPE
    SYNTAX DisplayString
    MAX-ACCESS read-only
    STATUS current
    DESCRIPTION "Threshold"
    ::= { SensorInfo 40 }

Index-40 OBJECT-TYPE
    SYNTAX Integer32
    MAX-ACCESS read-only
    STATUS current
    DESCRIPTION "Sensor Index"
    ::= { PWR-PSU1-POUT-40 1 }

Number-40 OBJECT-TYPE
    SYNTAX Integer32
    MAX-ACCESS read-only
    STATUS current
    DESCRIPTION "Sensor Number"
    ::= { PWR-PSU1-POUT-40 2 }

Name-40 OBJECT-TYPE
    SYNTAX DisplayString
    MAX-ACCESS read-only
    STATUS current
    DESCRIPTION "Sensor Name"
    ::= { PWR-PSU1-POUT-40 3 }

Status-40 OBJECT-TYPE
    SYNTAX Integer32
    MAX-ACCESS read-only
    STATUS current
    DESCRIPTION "Sensor Status"
    ::= { PWR-PSU1-POUT-40 4 }

Reading-40 OBJECT-TYPE
    SYNTAX DisplayString
    MAX-ACCESS read-only
    STATUS current
    DESCRIPTION "Sensor Reading"
    ::= { PWR-PSU1-POUT-40 5 }

LowNRT-40 OBJECT-TYPE
    SYNTAX DisplayString
    MAX-ACCESS read-only
    STATUS current
    DESCRIPTION "Sensor Low NRT"
    ::= { PWR-PSU1-POUT-40 6 }

LowCT-40 OBJECT-TYPE
    SYNTAX DisplayString
    MAX-ACCESS read-only
    STATUS current
    DESCRIPTION "Sensor Low CT"
    ::= { PWR-PSU1-POUT-40 7 }

LowNCT-40 OBJECT-TYPE
    SYNTAX DisplayString
    MAX-ACCESS read-only
    STATUS current
    DESCRIPTION "Sensor Low NCT"
    ::= { PWR-PSU1-POUT-40 8 }

UpNCT-40 OBJECT-TYPE
    SYNTAX DisplayString
    MAX-ACCESS read-only
    STATUS current
    DESCRIPTION "Sensor Up NCT"
    ::= { PWR-PSU1-POUT-40 9 }

UpCT-40 OBJECT-TYPE
    SYNTAX DisplayString
    MAX-ACCESS read-only
    STATUS current
    DESCRIPTION "Sensor Up CT"
    ::= { PWR-PSU1-POUT-40 10 }

UpNRT-40 OBJECT-TYPE
    SYNTAX DisplayString
    MAX-ACCESS read-only
    STATUS current
    DESCRIPTION "Sensor Up NRT"
    ::= { PWR-PSU1-POUT-40 11 }

TEMP-PSU1-41 OBJECT-TYPE
    SYNTAX DisplayString
    MAX-ACCESS read-only
    STATUS current
    DESCRIPTION "Threshold"
    ::= { SensorInfo 41 }

Index-41 OBJECT-TYPE
    SYNTAX Integer32
    MAX-ACCESS read-only
    STATUS current
    DESCRIPTION "Sensor Index"
    ::= { TEMP-PSU1-41 1 }

Number-41 OBJECT-TYPE
    SYNTAX Integer32
    MAX-ACCESS read-only
    STATUS current
    DESCRIPTION "Sensor Number"
    ::= { TEMP-PSU1-41 2 }

Name-41 OBJECT-TYPE
    SYNTAX DisplayString
    MAX-ACCESS read-only
    STATUS current
    DESCRIPTION "Sensor Name"
    ::= { TEMP-PSU1-41 3 }

Status-41 OBJECT-TYPE
    SYNTAX Integer32
    MAX-ACCESS read-only
    STATUS current
    DESCRIPTION "Sensor Status"
    ::= { TEMP-PSU1-41 4 }

Reading-41 OBJECT-TYPE
    SYNTAX DisplayString
    MAX-ACCESS read-only
    STATUS current
    DESCRIPTION "Sensor Reading"
    ::= { TEMP-PSU1-41 5 }

LowNRT-41 OBJECT-TYPE
    SYNTAX DisplayString
    MAX-ACCESS read-only
    STATUS current
    DESCRIPTION "Sensor Low NRT"
    ::= { TEMP-PSU1-41 6 }

LowCT-41 OBJECT-TYPE
    SYNTAX DisplayString
    MAX-ACCESS read-only
    STATUS current
    DESCRIPTION "Sensor Low CT"
    ::= { TEMP-PSU1-41 7 }

LowNCT-41 OBJECT-TYPE
    SYNTAX DisplayString
    MAX-ACCESS read-only
    STATUS current
    DESCRIPTION "Sensor Low NCT"
    ::= { TEMP-PSU1-41 8 }

UpNCT-41 OBJECT-TYPE
    SYNTAX DisplayString
    MAX-ACCESS read-only
    STATUS current
    DESCRIPTION "Sensor Up NCT"
    ::= { TEMP-PSU1-41 9 }

UpCT-41 OBJECT-TYPE
    SYNTAX DisplayString
    MAX-ACCESS read-only
    STATUS current
    DESCRIPTION "Sensor Up CT"
    ::= { TEMP-PSU1-41 10 }

UpNRT-41 OBJECT-TYPE
    SYNTAX DisplayString
    MAX-ACCESS read-only
    STATUS current
    DESCRIPTION "Sensor Up NRT"
    ::= { TEMP-PSU1-41 11 }

FAN-PSU1-42 OBJECT-TYPE
    SYNTAX DisplayString
    MAX-ACCESS read-only
    STATUS current
    DESCRIPTION "Threshold"
    ::= { SensorInfo 42 }

Index-42 OBJECT-TYPE
    SYNTAX Integer32
    MAX-ACCESS read-only
    STATUS current
    DESCRIPTION "Sensor Index"
    ::= { FAN-PSU1-42 1 }

Number-42 OBJECT-TYPE
    SYNTAX Integer32
    MAX-ACCESS read-only
    STATUS current
    DESCRIPTION "Sensor Number"
    ::= { FAN-PSU1-42 2 }

Name-42 OBJECT-TYPE
    SYNTAX DisplayString
    MAX-ACCESS read-only
    STATUS current
    DESCRIPTION "Sensor Name"
    ::= { FAN-PSU1-42 3 }

Status-42 OBJECT-TYPE
    SYNTAX Integer32
    MAX-ACCESS read-only
    STATUS current
    DESCRIPTION "Sensor Status"
    ::= { FAN-PSU1-42 4 }

Reading-42 OBJECT-TYPE
    SYNTAX DisplayString
    MAX-ACCESS read-only
    STATUS current
    DESCRIPTION "Sensor Reading"
    ::= { FAN-PSU1-42 5 }

LowNRT-42 OBJECT-TYPE
    SYNTAX DisplayString
    MAX-ACCESS read-only
    STATUS current
    DESCRIPTION "Sensor Low NRT"
    ::= { FAN-PSU1-42 6 }

LowCT-42 OBJECT-TYPE
    SYNTAX DisplayString
    MAX-ACCESS read-only
    STATUS current
    DESCRIPTION "Sensor Low CT"
    ::= { FAN-PSU1-42 7 }

LowNCT-42 OBJECT-TYPE
    SYNTAX DisplayString
    MAX-ACCESS read-only
    STATUS current
    DESCRIPTION "Sensor Low NCT"
    ::= { FAN-PSU1-42 8 }

UpNCT-42 OBJECT-TYPE
    SYNTAX DisplayString
    MAX-ACCESS read-only
    STATUS current
    DESCRIPTION "Sensor Up NCT"
    ::= { FAN-PSU1-42 9 }

UpCT-42 OBJECT-TYPE
    SYNTAX DisplayString
    MAX-ACCESS read-only
    STATUS current
    DESCRIPTION "Sensor Up CT"
    ::= { FAN-PSU1-42 10 }

UpNRT-42 OBJECT-TYPE
    SYNTAX DisplayString
    MAX-ACCESS read-only
    STATUS current
    DESCRIPTION "Sensor Up NRT"
    ::= { FAN-PSU1-42 11 }

VOLT-PSU2-VIN-43 OBJECT-TYPE
    SYNTAX DisplayString
    MAX-ACCESS read-only
    STATUS current
    DESCRIPTION "Threshold"
    ::= { SensorInfo 43 }

Index-43 OBJECT-TYPE
    SYNTAX Integer32
    MAX-ACCESS read-only
    STATUS current
    DESCRIPTION "Sensor Index"
    ::= { VOLT-PSU2-VIN-43 1 }

Number-43 OBJECT-TYPE
    SYNTAX Integer32
    MAX-ACCESS read-only
    STATUS current
    DESCRIPTION "Sensor Number"
    ::= { VOLT-PSU2-VIN-43 2 }

Name-43 OBJECT-TYPE
    SYNTAX DisplayString
    MAX-ACCESS read-only
    STATUS current
    DESCRIPTION "Sensor Name"
    ::= { VOLT-PSU2-VIN-43 3 }

Status-43 OBJECT-TYPE
    SYNTAX Integer32
    MAX-ACCESS read-only
    STATUS current
    DESCRIPTION "Sensor Status"
    ::= { VOLT-PSU2-VIN-43 4 }

Reading-43 OBJECT-TYPE
    SYNTAX DisplayString
    MAX-ACCESS read-only
    STATUS current
    DESCRIPTION "Sensor Reading"
    ::= { VOLT-PSU2-VIN-43 5 }

LowNRT-43 OBJECT-TYPE
    SYNTAX DisplayString
    MAX-ACCESS read-only
    STATUS current
    DESCRIPTION "Sensor Low NRT"
    ::= { VOLT-PSU2-VIN-43 6 }

LowCT-43 OBJECT-TYPE
    SYNTAX DisplayString
    MAX-ACCESS read-only
    STATUS current
    DESCRIPTION "Sensor Low CT"
    ::= { VOLT-PSU2-VIN-43 7 }

LowNCT-43 OBJECT-TYPE
    SYNTAX DisplayString
    MAX-ACCESS read-only
    STATUS current
    DESCRIPTION "Sensor Low NCT"
    ::= { VOLT-PSU2-VIN-43 8 }

UpNCT-43 OBJECT-TYPE
    SYNTAX DisplayString
    MAX-ACCESS read-only
    STATUS current
    DESCRIPTION "Sensor Up NCT"
    ::= { VOLT-PSU2-VIN-43 9 }

UpCT-43 OBJECT-TYPE
    SYNTAX DisplayString
    MAX-ACCESS read-only
    STATUS current
    DESCRIPTION "Sensor Up CT"
    ::= { VOLT-PSU2-VIN-43 10 }

UpNRT-43 OBJECT-TYPE
    SYNTAX DisplayString
    MAX-ACCESS read-only
    STATUS current
    DESCRIPTION "Sensor Up NRT"
    ::= { VOLT-PSU2-VIN-43 11 }

CUR-PSU2-IOUT-44 OBJECT-TYPE
    SYNTAX DisplayString
    MAX-ACCESS read-only
    STATUS current
    DESCRIPTION "Threshold"
    ::= { SensorInfo 44 }

Index-44 OBJECT-TYPE
    SYNTAX Integer32
    MAX-ACCESS read-only
    STATUS current
    DESCRIPTION "Sensor Index"
    ::= { CUR-PSU2-IOUT-44 1 }

Number-44 OBJECT-TYPE
    SYNTAX Integer32
    MAX-ACCESS read-only
    STATUS current
    DESCRIPTION "Sensor Number"
    ::= { CUR-PSU2-IOUT-44 2 }

Name-44 OBJECT-TYPE
    SYNTAX DisplayString
    MAX-ACCESS read-only
    STATUS current
    DESCRIPTION "Sensor Name"
    ::= { CUR-PSU2-IOUT-44 3 }

Status-44 OBJECT-TYPE
    SYNTAX Integer32
    MAX-ACCESS read-only
    STATUS current
    DESCRIPTION "Sensor Status"
    ::= { CUR-PSU2-IOUT-44 4 }

Reading-44 OBJECT-TYPE
    SYNTAX DisplayString
    MAX-ACCESS read-only
    STATUS current
    DESCRIPTION "Sensor Reading"
    ::= { CUR-PSU2-IOUT-44 5 }

LowNRT-44 OBJECT-TYPE
    SYNTAX DisplayString
    MAX-ACCESS read-only
    STATUS current
    DESCRIPTION "Sensor Low NRT"
    ::= { CUR-PSU2-IOUT-44 6 }

LowCT-44 OBJECT-TYPE
    SYNTAX DisplayString
    MAX-ACCESS read-only
    STATUS current
    DESCRIPTION "Sensor Low CT"
    ::= { CUR-PSU2-IOUT-44 7 }

LowNCT-44 OBJECT-TYPE
    SYNTAX DisplayString
    MAX-ACCESS read-only
    STATUS current
    DESCRIPTION "Sensor Low NCT"
    ::= { CUR-PSU2-IOUT-44 8 }

UpNCT-44 OBJECT-TYPE
    SYNTAX DisplayString
    MAX-ACCESS read-only
    STATUS current
    DESCRIPTION "Sensor Up NCT"
    ::= { CUR-PSU2-IOUT-44 9 }

UpCT-44 OBJECT-TYPE
    SYNTAX DisplayString
    MAX-ACCESS read-only
    STATUS current
    DESCRIPTION "Sensor Up CT"
    ::= { CUR-PSU2-IOUT-44 10 }

UpNRT-44 OBJECT-TYPE
    SYNTAX DisplayString
    MAX-ACCESS read-only
    STATUS current
    DESCRIPTION "Sensor Up NRT"
    ::= { CUR-PSU2-IOUT-44 11 }

PWR-PSU2-PIN-45 OBJECT-TYPE
    SYNTAX DisplayString
    MAX-ACCESS read-only
    STATUS current
    DESCRIPTION "Threshold"
    ::= { SensorInfo 45 }

Index-45 OBJECT-TYPE
    SYNTAX Integer32
    MAX-ACCESS read-only
    STATUS current
    DESCRIPTION "Sensor Index"
    ::= { PWR-PSU2-PIN-45 1 }

Number-45 OBJECT-TYPE
    SYNTAX Integer32
    MAX-ACCESS read-only
    STATUS current
    DESCRIPTION "Sensor Number"
    ::= { PWR-PSU2-PIN-45 2 }

Name-45 OBJECT-TYPE
    SYNTAX DisplayString
    MAX-ACCESS read-only
    STATUS current
    DESCRIPTION "Sensor Name"
    ::= { PWR-PSU2-PIN-45 3 }

Status-45 OBJECT-TYPE
    SYNTAX Integer32
    MAX-ACCESS read-only
    STATUS current
    DESCRIPTION "Sensor Status"
    ::= { PWR-PSU2-PIN-45 4 }

Reading-45 OBJECT-TYPE
    SYNTAX DisplayString
    MAX-ACCESS read-only
    STATUS current
    DESCRIPTION "Sensor Reading"
    ::= { PWR-PSU2-PIN-45 5 }

LowNRT-45 OBJECT-TYPE
    SYNTAX DisplayString
    MAX-ACCESS read-only
    STATUS current
    DESCRIPTION "Sensor Low NRT"
    ::= { PWR-PSU2-PIN-45 6 }

LowCT-45 OBJECT-TYPE
    SYNTAX DisplayString
    MAX-ACCESS read-only
    STATUS current
    DESCRIPTION "Sensor Low CT"
    ::= { PWR-PSU2-PIN-45 7 }

LowNCT-45 OBJECT-TYPE
    SYNTAX DisplayString
    MAX-ACCESS read-only
    STATUS current
    DESCRIPTION "Sensor Low NCT"
    ::= { PWR-PSU2-PIN-45 8 }

UpNCT-45 OBJECT-TYPE
    SYNTAX DisplayString
    MAX-ACCESS read-only
    STATUS current
    DESCRIPTION "Sensor Up NCT"
    ::= { PWR-PSU2-PIN-45 9 }

UpCT-45 OBJECT-TYPE
    SYNTAX DisplayString
    MAX-ACCESS read-only
    STATUS current
    DESCRIPTION "Sensor Up CT"
    ::= { PWR-PSU2-PIN-45 10 }

UpNRT-45 OBJECT-TYPE
    SYNTAX DisplayString
    MAX-ACCESS read-only
    STATUS current
    DESCRIPTION "Sensor Up NRT"
    ::= { PWR-PSU2-PIN-45 11 }

PWR-PSU2-POUT-46 OBJECT-TYPE
    SYNTAX DisplayString
    MAX-ACCESS read-only
    STATUS current
    DESCRIPTION "Threshold"
    ::= { SensorInfo 46 }

Index-46 OBJECT-TYPE
    SYNTAX Integer32
    MAX-ACCESS read-only
    STATUS current
    DESCRIPTION "Sensor Index"
    ::= { PWR-PSU2-POUT-46 1 }

Number-46 OBJECT-TYPE
    SYNTAX Integer32
    MAX-ACCESS read-only
    STATUS current
    DESCRIPTION "Sensor Number"
    ::= { PWR-PSU2-POUT-46 2 }

Name-46 OBJECT-TYPE
    SYNTAX DisplayString
    MAX-ACCESS read-only
    STATUS current
    DESCRIPTION "Sensor Name"
    ::= { PWR-PSU2-POUT-46 3 }

Status-46 OBJECT-TYPE
    SYNTAX Integer32
    MAX-ACCESS read-only
    STATUS current
    DESCRIPTION "Sensor Status"
    ::= { PWR-PSU2-POUT-46 4 }

Reading-46 OBJECT-TYPE
    SYNTAX DisplayString
    MAX-ACCESS read-only
    STATUS current
    DESCRIPTION "Sensor Reading"
    ::= { PWR-PSU2-POUT-46 5 }

LowNRT-46 OBJECT-TYPE
    SYNTAX DisplayString
    MAX-ACCESS read-only
    STATUS current
    DESCRIPTION "Sensor Low NRT"
    ::= { PWR-PSU2-POUT-46 6 }

LowCT-46 OBJECT-TYPE
    SYNTAX DisplayString
    MAX-ACCESS read-only
    STATUS current
    DESCRIPTION "Sensor Low CT"
    ::= { PWR-PSU2-POUT-46 7 }

LowNCT-46 OBJECT-TYPE
    SYNTAX DisplayString
    MAX-ACCESS read-only
    STATUS current
    DESCRIPTION "Sensor Low NCT"
    ::= { PWR-PSU2-POUT-46 8 }

UpNCT-46 OBJECT-TYPE
    SYNTAX DisplayString
    MAX-ACCESS read-only
    STATUS current
    DESCRIPTION "Sensor Up NCT"
    ::= { PWR-PSU2-POUT-46 9 }

UpCT-46 OBJECT-TYPE
    SYNTAX DisplayString
    MAX-ACCESS read-only
    STATUS current
    DESCRIPTION "Sensor Up CT"
    ::= { PWR-PSU2-POUT-46 10 }

UpNRT-46 OBJECT-TYPE
    SYNTAX DisplayString
    MAX-ACCESS read-only
    STATUS current
    DESCRIPTION "Sensor Up NRT"
    ::= { PWR-PSU2-POUT-46 11 }

TEMP-PSU2-47 OBJECT-TYPE
    SYNTAX DisplayString
    MAX-ACCESS read-only
    STATUS current
    DESCRIPTION "Threshold"
    ::= { SensorInfo 47 }

Index-47 OBJECT-TYPE
    SYNTAX Integer32
    MAX-ACCESS read-only
    STATUS current
    DESCRIPTION "Sensor Index"
    ::= { TEMP-PSU2-47 1 }

Number-47 OBJECT-TYPE
    SYNTAX Integer32
    MAX-ACCESS read-only
    STATUS current
    DESCRIPTION "Sensor Number"
    ::= { TEMP-PSU2-47 2 }

Name-47 OBJECT-TYPE
    SYNTAX DisplayString
    MAX-ACCESS read-only
    STATUS current
    DESCRIPTION "Sensor Name"
    ::= { TEMP-PSU2-47 3 }

Status-47 OBJECT-TYPE
    SYNTAX Integer32
    MAX-ACCESS read-only
    STATUS current
    DESCRIPTION "Sensor Status"
    ::= { TEMP-PSU2-47 4 }

Reading-47 OBJECT-TYPE
    SYNTAX DisplayString
    MAX-ACCESS read-only
    STATUS current
    DESCRIPTION "Sensor Reading"
    ::= { TEMP-PSU2-47 5 }

LowNRT-47 OBJECT-TYPE
    SYNTAX DisplayString
    MAX-ACCESS read-only
    STATUS current
    DESCRIPTION "Sensor Low NRT"
    ::= { TEMP-PSU2-47 6 }

LowCT-47 OBJECT-TYPE
    SYNTAX DisplayString
    MAX-ACCESS read-only
    STATUS current
    DESCRIPTION "Sensor Low CT"
    ::= { TEMP-PSU2-47 7 }

LowNCT-47 OBJECT-TYPE
    SYNTAX DisplayString
    MAX-ACCESS read-only
    STATUS current
    DESCRIPTION "Sensor Low NCT"
    ::= { TEMP-PSU2-47 8 }

UpNCT-47 OBJECT-TYPE
    SYNTAX DisplayString
    MAX-ACCESS read-only
    STATUS current
    DESCRIPTION "Sensor Up NCT"
    ::= { TEMP-PSU2-47 9 }

UpCT-47 OBJECT-TYPE
    SYNTAX DisplayString
    MAX-ACCESS read-only
    STATUS current
    DESCRIPTION "Sensor Up CT"
    ::= { TEMP-PSU2-47 10 }

UpNRT-47 OBJECT-TYPE
    SYNTAX DisplayString
    MAX-ACCESS read-only
    STATUS current
    DESCRIPTION "Sensor Up NRT"
    ::= { TEMP-PSU2-47 11 }

FAN-PSU2-48 OBJECT-TYPE
    SYNTAX DisplayString
    MAX-ACCESS read-only
    STATUS current
    DESCRIPTION "Threshold"
    ::= { SensorInfo 48 }

Index-48 OBJECT-TYPE
    SYNTAX Integer32
    MAX-ACCESS read-only
    STATUS current
    DESCRIPTION "Sensor Index"
    ::= { FAN-PSU2-48 1 }

Number-48 OBJECT-TYPE
    SYNTAX Integer32
    MAX-ACCESS read-only
    STATUS current
    DESCRIPTION "Sensor Number"
    ::= { FAN-PSU2-48 2 }

Name-48 OBJECT-TYPE
    SYNTAX DisplayString
    MAX-ACCESS read-only
    STATUS current
    DESCRIPTION "Sensor Name"
    ::= { FAN-PSU2-48 3 }

Status-48 OBJECT-TYPE
    SYNTAX Integer32
    MAX-ACCESS read-only
    STATUS current
    DESCRIPTION "Sensor Status"
    ::= { FAN-PSU2-48 4 }

Reading-48 OBJECT-TYPE
    SYNTAX DisplayString
    MAX-ACCESS read-only
    STATUS current
    DESCRIPTION "Sensor Reading"
    ::= { FAN-PSU2-48 5 }

LowNRT-48 OBJECT-TYPE
    SYNTAX DisplayString
    MAX-ACCESS read-only
    STATUS current
    DESCRIPTION "Sensor Low NRT"
    ::= { FAN-PSU2-48 6 }

LowCT-48 OBJECT-TYPE
    SYNTAX DisplayString
    MAX-ACCESS read-only
    STATUS current
    DESCRIPTION "Sensor Low CT"
    ::= { FAN-PSU2-48 7 }

LowNCT-48 OBJECT-TYPE
    SYNTAX DisplayString
    MAX-ACCESS read-only
    STATUS current
    DESCRIPTION "Sensor Low NCT"
    ::= { FAN-PSU2-48 8 }

UpNCT-48 OBJECT-TYPE
    SYNTAX DisplayString
    MAX-ACCESS read-only
    STATUS current
    DESCRIPTION "Sensor Up NCT"
    ::= { FAN-PSU2-48 9 }

UpCT-48 OBJECT-TYPE
    SYNTAX DisplayString
    MAX-ACCESS read-only
    STATUS current
    DESCRIPTION "Sensor Up CT"
    ::= { FAN-PSU2-48 10 }

UpNRT-48 OBJECT-TYPE
    SYNTAX DisplayString
    MAX-ACCESS read-only
    STATUS current
    DESCRIPTION "Sensor Up NRT"
    ::= { FAN-PSU2-48 11 }

STS-PSU1-49 OBJECT-TYPE
    SYNTAX DisplayString
    MAX-ACCESS read-only
    STATUS current
    DESCRIPTION "Discrete"
    ::= { SensorInfo 49 }

Index-49 OBJECT-TYPE
    SYNTAX Integer32
    MAX-ACCESS read-only
    STATUS current
    DESCRIPTION "Sensor Index"
    ::= { STS-PSU1-49 1 }

Number-49 OBJECT-TYPE
    SYNTAX Integer32
    MAX-ACCESS read-only
    STATUS current
    DESCRIPTION "Sensor Number"
    ::= { STS-PSU1-49 2 }

Name-49 OBJECT-TYPE
    SYNTAX DisplayString
    MAX-ACCESS read-only
    STATUS current
    DESCRIPTION "Sensor Name"
    ::= { STS-PSU1-49 3 }

Status-49 OBJECT-TYPE
    SYNTAX Integer32
    MAX-ACCESS read-only
    STATUS current
    DESCRIPTION "Sensor Status"
    ::= { STS-PSU1-49 4 }

Reading-49 OBJECT-TYPE
    SYNTAX DisplayString
    MAX-ACCESS read-only
    STATUS current
    DESCRIPTION "Sensor Reading"
    ::= { STS-PSU1-49 5 }

STS-PSU1-FAN-50 OBJECT-TYPE
    SYNTAX DisplayString
    MAX-ACCESS read-only
    STATUS current
    DESCRIPTION "Discrete"
    ::= { SensorInfo 50 }

Index-50 OBJECT-TYPE
    SYNTAX Integer32
    MAX-ACCESS read-only
    STATUS current
    DESCRIPTION "Sensor Index"
    ::= { STS-PSU1-FAN-50 1 }

Number-50 OBJECT-TYPE
    SYNTAX Integer32
    MAX-ACCESS read-only
    STATUS current
    DESCRIPTION "Sensor Number"
    ::= { STS-PSU1-FAN-50 2 }

Name-50 OBJECT-TYPE
    SYNTAX DisplayString
    MAX-ACCESS read-only
    STATUS current
    DESCRIPTION "Sensor Name"
    ::= { STS-PSU1-FAN-50 3 }

Status-50 OBJECT-TYPE
    SYNTAX Integer32
    MAX-ACCESS read-only
    STATUS current
    DESCRIPTION "Sensor Status"
    ::= { STS-PSU1-FAN-50 4 }

Reading-50 OBJECT-TYPE
    SYNTAX DisplayString
    MAX-ACCESS read-only
    STATUS current
    DESCRIPTION "Sensor Reading"
    ::= { STS-PSU1-FAN-50 5 }

STS-PSU1-AC-LOST-51 OBJECT-TYPE
    SYNTAX DisplayString
    MAX-ACCESS read-only
    STATUS current
    DESCRIPTION "Discrete"
    ::= { SensorInfo 51 }

Index-51 OBJECT-TYPE
    SYNTAX Integer32
    MAX-ACCESS read-only
    STATUS current
    DESCRIPTION "Sensor Index"
    ::= { STS-PSU1-AC-LOST-51 1 }

Number-51 OBJECT-TYPE
    SYNTAX Integer32
    MAX-ACCESS read-only
    STATUS current
    DESCRIPTION "Sensor Number"
    ::= { STS-PSU1-AC-LOST-51 2 }

Name-51 OBJECT-TYPE
    SYNTAX DisplayString
    MAX-ACCESS read-only
    STATUS current
    DESCRIPTION "Sensor Name"
    ::= { STS-PSU1-AC-LOST-51 3 }

Status-51 OBJECT-TYPE
    SYNTAX Integer32
    MAX-ACCESS read-only
    STATUS current
    DESCRIPTION "Sensor Status"
    ::= { STS-PSU1-AC-LOST-51 4 }

Reading-51 OBJECT-TYPE
    SYNTAX DisplayString
    MAX-ACCESS read-only
    STATUS current
    DESCRIPTION "Sensor Reading"
    ::= { STS-PSU1-AC-LOST-51 5 }

STS-PSU2-52 OBJECT-TYPE
    SYNTAX DisplayString
    MAX-ACCESS read-only
    STATUS current
    DESCRIPTION "Discrete"
    ::= { SensorInfo 52 }

Index-52 OBJECT-TYPE
    SYNTAX Integer32
    MAX-ACCESS read-only
    STATUS current
    DESCRIPTION "Sensor Index"
    ::= { STS-PSU2-52 1 }

Number-52 OBJECT-TYPE
    SYNTAX Integer32
    MAX-ACCESS read-only
    STATUS current
    DESCRIPTION "Sensor Number"
    ::= { STS-PSU2-52 2 }

Name-52 OBJECT-TYPE
    SYNTAX DisplayString
    MAX-ACCESS read-only
    STATUS current
    DESCRIPTION "Sensor Name"
    ::= { STS-PSU2-52 3 }

Status-52 OBJECT-TYPE
    SYNTAX Integer32
    MAX-ACCESS read-only
    STATUS current
    DESCRIPTION "Sensor Status"
    ::= { STS-PSU2-52 4 }

Reading-52 OBJECT-TYPE
    SYNTAX DisplayString
    MAX-ACCESS read-only
    STATUS current
    DESCRIPTION "Sensor Reading"
    ::= { STS-PSU2-52 5 }

STS-PSU2-FAN-53 OBJECT-TYPE
    SYNTAX DisplayString
    MAX-ACCESS read-only
    STATUS current
    DESCRIPTION "Discrete"
    ::= { SensorInfo 53 }

Index-53 OBJECT-TYPE
    SYNTAX Integer32
    MAX-ACCESS read-only
    STATUS current
    DESCRIPTION "Sensor Index"
    ::= { STS-PSU2-FAN-53 1 }

Number-53 OBJECT-TYPE
    SYNTAX Integer32
    MAX-ACCESS read-only
    STATUS current
    DESCRIPTION "Sensor Number"
    ::= { STS-PSU2-FAN-53 2 }

Name-53 OBJECT-TYPE
    SYNTAX DisplayString
    MAX-ACCESS read-only
    STATUS current
    DESCRIPTION "Sensor Name"
    ::= { STS-PSU2-FAN-53 3 }

Status-53 OBJECT-TYPE
    SYNTAX Integer32
    MAX-ACCESS read-only
    STATUS current
    DESCRIPTION "Sensor Status"
    ::= { STS-PSU2-FAN-53 4 }

Reading-53 OBJECT-TYPE
    SYNTAX DisplayString
    MAX-ACCESS read-only
    STATUS current
    DESCRIPTION "Sensor Reading"
    ::= { STS-PSU2-FAN-53 5 }

STS-PSU2-AC-LOST-54 OBJECT-TYPE
    SYNTAX DisplayString
    MAX-ACCESS read-only
    STATUS current
    DESCRIPTION "Discrete"
    ::= { SensorInfo 54 }

Index-54 OBJECT-TYPE
    SYNTAX Integer32
    MAX-ACCESS read-only
    STATUS current
    DESCRIPTION "Sensor Index"
    ::= { STS-PSU2-AC-LOST-54 1 }

Number-54 OBJECT-TYPE
    SYNTAX Integer32
    MAX-ACCESS read-only
    STATUS current
    DESCRIPTION "Sensor Number"
    ::= { STS-PSU2-AC-LOST-54 2 }

Name-54 OBJECT-TYPE
    SYNTAX DisplayString
    MAX-ACCESS read-only
    STATUS current
    DESCRIPTION "Sensor Name"
    ::= { STS-PSU2-AC-LOST-54 3 }

Status-54 OBJECT-TYPE
    SYNTAX Integer32
    MAX-ACCESS read-only
    STATUS current
    DESCRIPTION "Sensor Status"
    ::= { STS-PSU2-AC-LOST-54 4 }

Reading-54 OBJECT-TYPE
    SYNTAX DisplayString
    MAX-ACCESS read-only
    STATUS current
    DESCRIPTION "Sensor Reading"
    ::= { STS-PSU2-AC-LOST-54 5 }

PROCHOT-CPU-55 OBJECT-TYPE
    SYNTAX DisplayString
    MAX-ACCESS read-only
    STATUS current
    DESCRIPTION "Discrete"
    ::= { SensorInfo 55 }

Index-55 OBJECT-TYPE
    SYNTAX Integer32
    MAX-ACCESS read-only
    STATUS current
    DESCRIPTION "Sensor Index"
    ::= { PROCHOT-CPU-55 1 }

Number-55 OBJECT-TYPE
    SYNTAX Integer32
    MAX-ACCESS read-only
    STATUS current
    DESCRIPTION "Sensor Number"
    ::= { PROCHOT-CPU-55 2 }

Name-55 OBJECT-TYPE
    SYNTAX DisplayString
    MAX-ACCESS read-only
    STATUS current
    DESCRIPTION "Sensor Name"
    ::= { PROCHOT-CPU-55 3 }

Status-55 OBJECT-TYPE
    SYNTAX Integer32
    MAX-ACCESS read-only
    STATUS current
    DESCRIPTION "Sensor Status"
    ::= { PROCHOT-CPU-55 4 }

Reading-55 OBJECT-TYPE
    SYNTAX DisplayString
    MAX-ACCESS read-only
    STATUS current
    DESCRIPTION "Sensor Reading"
    ::= { PROCHOT-CPU-55 5 }

THERMTRIP-CPU-56 OBJECT-TYPE
    SYNTAX DisplayString
    MAX-ACCESS read-only
    STATUS current
    DESCRIPTION "Discrete"
    ::= { SensorInfo 56 }

Index-56 OBJECT-TYPE
    SYNTAX Integer32
    MAX-ACCESS read-only
    STATUS current
    DESCRIPTION "Sensor Index"
    ::= { THERMTRIP-CPU-56 1 }

Number-56 OBJECT-TYPE
    SYNTAX Integer32
    MAX-ACCESS read-only
    STATUS current
    DESCRIPTION "Sensor Number"
    ::= { THERMTRIP-CPU-56 2 }

Name-56 OBJECT-TYPE
    SYNTAX DisplayString
    MAX-ACCESS read-only
    STATUS current
    DESCRIPTION "Sensor Name"
    ::= { THERMTRIP-CPU-56 3 }

Status-56 OBJECT-TYPE
    SYNTAX Integer32
    MAX-ACCESS read-only
    STATUS current
    DESCRIPTION "Sensor Status"
    ::= { THERMTRIP-CPU-56 4 }

Reading-56 OBJECT-TYPE
    SYNTAX DisplayString
    MAX-ACCESS read-only
    STATUS current
    DESCRIPTION "Sensor Reading"
    ::= { THERMTRIP-CPU-56 5 }

STS-CPU-MCE-57 OBJECT-TYPE
    SYNTAX DisplayString
    MAX-ACCESS read-only
    STATUS current
    DESCRIPTION "Discrete"
    ::= { SensorInfo 57 }

Index-57 OBJECT-TYPE
    SYNTAX Integer32
    MAX-ACCESS read-only
    STATUS current
    DESCRIPTION "Sensor Index"
    ::= { STS-CPU-MCE-57 1 }

Number-57 OBJECT-TYPE
    SYNTAX Integer32
    MAX-ACCESS read-only
    STATUS current
    DESCRIPTION "Sensor Number"
    ::= { STS-CPU-MCE-57 2 }

Name-57 OBJECT-TYPE
    SYNTAX DisplayString
    MAX-ACCESS read-only
    STATUS current
    DESCRIPTION "Sensor Name"
    ::= { STS-CPU-MCE-57 3 }

Status-57 OBJECT-TYPE
    SYNTAX Integer32
    MAX-ACCESS read-only
    STATUS current
    DESCRIPTION "Sensor Status"
    ::= { STS-CPU-MCE-57 4 }

Reading-57 OBJECT-TYPE
    SYNTAX DisplayString
    MAX-ACCESS read-only
    STATUS current
    DESCRIPTION "Sensor Reading"
    ::= { STS-CPU-MCE-57 5 }

SEL-58 OBJECT-TYPE
    SYNTAX DisplayString
    MAX-ACCESS read-only
    STATUS current
    DESCRIPTION "Discrete"
    ::= { SensorInfo 58 }

Index-58 OBJECT-TYPE
    SYNTAX Integer32
    MAX-ACCESS read-only
    STATUS current
    DESCRIPTION "Sensor Index"
    ::= { SEL-58 1 }

Number-58 OBJECT-TYPE
    SYNTAX Integer32
    MAX-ACCESS read-only
    STATUS current
    DESCRIPTION "Sensor Number"
    ::= { SEL-58 2 }

Name-58 OBJECT-TYPE
    SYNTAX DisplayString
    MAX-ACCESS read-only
    STATUS current
    DESCRIPTION "Sensor Name"
    ::= { SEL-58 3 }

Status-58 OBJECT-TYPE
    SYNTAX Integer32
    MAX-ACCESS read-only
    STATUS current
    DESCRIPTION "Sensor Status"
    ::= { SEL-58 4 }

Reading-58 OBJECT-TYPE
    SYNTAX DisplayString
    MAX-ACCESS read-only
    STATUS current
    DESCRIPTION "Sensor Reading"
    ::= { SEL-58 5 }

PEF-59 OBJECT-TYPE
    SYNTAX DisplayString
    MAX-ACCESS read-only
    STATUS current
    DESCRIPTION "Discrete"
    ::= { SensorInfo 59 }

Index-59 OBJECT-TYPE
    SYNTAX Integer32
    MAX-ACCESS read-only
    STATUS current
    DESCRIPTION "Sensor Index"
    ::= { PEF-59 1 }

Number-59 OBJECT-TYPE
    SYNTAX Integer32
    MAX-ACCESS read-only
    STATUS current
    DESCRIPTION "Sensor Number"
    ::= { PEF-59 2 }

Name-59 OBJECT-TYPE
    SYNTAX DisplayString
    MAX-ACCESS read-only
    STATUS current
    DESCRIPTION "Sensor Name"
    ::= { PEF-59 3 }

Status-59 OBJECT-TYPE
    SYNTAX Integer32
    MAX-ACCESS read-only
    STATUS current
    DESCRIPTION "Sensor Status"
    ::= { PEF-59 4 }

Reading-59 OBJECT-TYPE
    SYNTAX DisplayString
    MAX-ACCESS read-only
    STATUS current
    DESCRIPTION "Sensor Reading"
    ::= { PEF-59 5 }

WATCHDOG2-60 OBJECT-TYPE
    SYNTAX DisplayString
    MAX-ACCESS read-only
    STATUS current
    DESCRIPTION "Discrete"
    ::= { SensorInfo 60 }

Index-60 OBJECT-TYPE
    SYNTAX Integer32
    MAX-ACCESS read-only
    STATUS current
    DESCRIPTION "Sensor Index"
    ::= { WATCHDOG2-60 1 }

Number-60 OBJECT-TYPE
    SYNTAX Integer32
    MAX-ACCESS read-only
    STATUS current
    DESCRIPTION "Sensor Number"
    ::= { WATCHDOG2-60 2 }

Name-60 OBJECT-TYPE
    SYNTAX DisplayString
    MAX-ACCESS read-only
    STATUS current
    DESCRIPTION "Sensor Name"
    ::= { WATCHDOG2-60 3 }

Status-60 OBJECT-TYPE
    SYNTAX Integer32
    MAX-ACCESS read-only
    STATUS current
    DESCRIPTION "Sensor Status"
    ::= { WATCHDOG2-60 4 }

Reading-60 OBJECT-TYPE
    SYNTAX DisplayString
    MAX-ACCESS read-only
    STATUS current
    DESCRIPTION "Sensor Reading"
    ::= { WATCHDOG2-60 5 }

Timestamp-61 OBJECT-TYPE
    SYNTAX DisplayString
    MAX-ACCESS read-only
    STATUS current
    DESCRIPTION "Discrete"
    ::= { SensorInfo 61 }

Index-61 OBJECT-TYPE
    SYNTAX Integer32
    MAX-ACCESS read-only
    STATUS current
    DESCRIPTION "Sensor Index"
    ::= { Timestamp-61 1 }

Number-61 OBJECT-TYPE
    SYNTAX Integer32
    MAX-ACCESS read-only
    STATUS current
    DESCRIPTION "Sensor Number"
    ::= { Timestamp-61 2 }

Name-61 OBJECT-TYPE
    SYNTAX DisplayString
    MAX-ACCESS read-only
    STATUS current
    DESCRIPTION "Sensor Name"
    ::= { Timestamp-61 3 }

Status-61 OBJECT-TYPE
    SYNTAX Integer32
    MAX-ACCESS read-only
    STATUS current
    DESCRIPTION "Sensor Status"
    ::= { Timestamp-61 4 }

Reading-61 OBJECT-TYPE
    SYNTAX DisplayString
    MAX-ACCESS read-only
    STATUS current
    DESCRIPTION "Sensor Reading"
    ::= { Timestamp-61 5 }

wired-for-management MODULE-IDENTITY
    LAST-UPDATED "202502140810Z"
    ORGANIZATION "ASRock Rack Inc."
    CONTACT-INFO "email: tsd_rack@asrockrack.com"
    DESCRIPTION "AUTO Server SNMP Trap objects"
    REVISION "202502140810Z"
    DESCRIPTION "AM5D4ID-2T+/BCM 70.16.00"
    ::= { enterprises 3183 }

PET OBJECT IDENTIFIER ::= { wired-for-management 1 }
version OBJECT IDENTIFIER ::= { PET 1 }
petTrap-Voltage-LNR-Assert TRAP-TYPE
   ENTERPRISE version
   DESCRIPTION "Lower Non-Recoverable - Going Low - Asserted"
   --#SEVERITY CRITICAL
   ::= 131332

petTrap-Voltage-LNR-Deassert TRAP-TYPE
   ENTERPRISE version
   DESCRIPTION "Lower Non-Recoverable - Going Low - Deasserted"
   --#SEVERITY INFORMATIONAL
   ::= 131460

petTrap-Voltage-LC-Assert TRAP-TYPE
   ENTERPRISE version
   DESCRIPTION "Lower Critical - Going Low - Asserted"
   --#SEVERITY CRITICAL
   ::= 131330

petTrap-Voltage-LC-Deassert TRAP-TYPE
   ENTERPRISE version
   DESCRIPTION "Lower Critical - Going Low - Deasserted"
   --#SEVERITY INFORMATIONAL
   ::= 131460

petTrap-Voltage-LNC-Assert TRAP-TYPE
   ENTERPRISE version
   DESCRIPTION "Lower Non-Critical - Going Low - Asserted"
   --#SEVERITY MAJOR
   ::= 131328

petTrap-Voltage-LNC-Deassert TRAP-TYPE
   ENTERPRISE version
   DESCRIPTION "Lower Non-Critical - Going Low - Deasserted"
   --#SEVERITY INFORMATIONAL
   ::= 131456

petTrap-Voltage-UNC-Assert TRAP-TYPE
   ENTERPRISE version
   DESCRIPTION "Upper Non-Critical - Going High - Asserted"
   --#SEVERITY MAJOR
   ::= 131335

petTrap-Voltage-UNC-Deassert TRAP-TYPE
   ENTERPRISE version
   DESCRIPTION "Upper Non-Critical - Going High - Deasserted"
   --#SEVERITY INFORMATIONAL
   ::= 131463

petTrap-Voltage-UC-Assert TRAP-TYPE
   ENTERPRISE version
   DESCRIPTION "Upper Critical - Going High - Asserted"
   --#SEVERITY CRITICAL
   ::= 131337

petTrap-Voltage-UC-Deassert TRAP-TYPE
   ENTERPRISE version
   DESCRIPTION "Upper Critical - Going High - Deasserted"
   --#SEVERITY INFORMATIONAL
   ::= 131465

petTrap-Voltage-UNR-Assert TRAP-TYPE
   ENTERPRISE version
   DESCRIPTION "Upper Non-Recoverable - Going High - Asserted"
   --#SEVERITY CRITICAL
   ::= 131339

petTrap-Voltage-UNR-Deassert TRAP-TYPE
   ENTERPRISE version
   DESCRIPTION "Upper Non-Recoverable - Going High - Deasserted"
   --#SEVERITY INFORMATIONAL
   ::= 131467

petTrap-Fan-LNR-Assert TRAP-TYPE
   ENTERPRISE version
   DESCRIPTION "Lower Non-Recoverable - Going Low - Asserted"
   --#SEVERITY CRITICAL
   ::= 262404

petTrap-Fan-LNR-Deassert TRAP-TYPE
   ENTERPRISE version
   DESCRIPTION "Lower Non-Recoverable - Going Low - Deasserted"
   --#SEVERITY INFORMATIONAL
   ::= 262532

petTrap-Fan-LC-Assert TRAP-TYPE
   ENTERPRISE version
   DESCRIPTION "Lower Critical - Going Low - Asserted"
   --#SEVERITY CRITICAL
   ::= 262402

petTrap-Fan-LC-Deassert TRAP-TYPE
   ENTERPRISE version
   DESCRIPTION "Lower Critical - Going Low - Deasserted"
   --#SEVERITY INFORMATIONAL
   ::= 262530

petTrap-Fan-LNC-Assert TRAP-TYPE
   ENTERPRISE version
   DESCRIPTION "Lower Non-Critical - Going Low - Asserted"
   --#SEVERITY MAJOR
   ::= 262400

petTrap-Fan-LNC-Deassert TRAP-TYPE
   ENTERPRISE version
   DESCRIPTION "Lower Non-Critical - Going Low - Deasserted"
   --#SEVERITY INFORMATIONAL
   ::= 262528

petTrap-Fan-UNC-Assert TRAP-TYPE
   ENTERPRISE version
   DESCRIPTION "Upper Non-Critical - Going High - Asserted"
   --#SEVERITY MAJOR
   ::= 262407

petTrap-Fan-UNC-Deassert TRAP-TYPE
   ENTERPRISE version
   DESCRIPTION "Upper Non-Critical - Going High - Deasserted"
   --#SEVERITY INFORMATIONAL
   ::= 262535

petTrap-Fan-UC-Assert TRAP-TYPE
   ENTERPRISE version
   DESCRIPTION "Upper Critical - Going High - Asserted"
   --#SEVERITY CRITICAL
   ::= 262409

petTrap-Fan-UC-Deassert TRAP-TYPE
   ENTERPRISE version
   DESCRIPTION "Upper Critical - Going High - Deasserted"
   --#SEVERITY INFORMATIONAL
   ::= 262537

petTrap-Fan-UNR-Assert TRAP-TYPE
   ENTERPRISE version
   DESCRIPTION "Upper Non-Recoverable - Going High - Asserted"
   --#SEVERITY CRITICAL
   ::= 262411

petTrap-Fan-UNR-Deassert TRAP-TYPE
   ENTERPRISE version
   DESCRIPTION "Upper Non-Recoverable - Going High - Deasserted"
   --#SEVERITY INFORMATIONAL
   ::= 262539

petTrap-Temperature-LNR-Assert TRAP-TYPE
   ENTERPRISE version
   DESCRIPTION "Lower Non-Recoverable - Going Low - Asserted"
   --#SEVERITY CRITICAL
   ::= 65792

petTrap-Temperature-LNR-Deassert TRAP-TYPE
   ENTERPRISE version
   DESCRIPTION "Lower Non-Recoverable - Going Low - Deasserted"
   --#SEVERITY INFORMATIONAL
   ::= 65920

petTrap-Temperature-LC-Assert TRAP-TYPE
   ENTERPRISE version
   DESCRIPTION "Lower Critical - Going Low - Asserted"
   --#SEVERITY CRITICAL
   ::= 65794

petTrap-Temperature-LC-Deassert TRAP-TYPE
   ENTERPRISE version
   DESCRIPTION "Lower Critical - Going Low - Deasserted"
   --#SEVERITY INFORMATIONAL
   ::= 65922

petTrap-Temperature-LNC-Assert TRAP-TYPE
   ENTERPRISE version
   DESCRIPTION "Lower Non-Critical - Going Low - Asserted"
   --#SEVERITY MAJOR
   ::= 65796

petTrap-Temperature-LNC-Deassert TRAP-TYPE
   ENTERPRISE version
   DESCRIPTION "Lower Non-Critical - Going Low - Deasserted"
   --#SEVERITY INFORMATIONAL
   ::= 65924

petTrap-Temperature-UNC-Assert TRAP-TYPE
   ENTERPRISE version
   DESCRIPTION "Upper Non-Critical - Going High - Asserted"
   --#SEVERITY MAJOR
   ::= 65799

petTrap-Temperature-UNC-Deassert TRAP-TYPE
   ENTERPRISE version
   DESCRIPTION "Upper Non-Critical - Going High - Deasserted"
   --#SEVERITY INFORMATIONAL
   ::= 65927

petTrap-Temperature-UC-Assert TRAP-TYPE
   ENTERPRISE version
   DESCRIPTION "Upper Critical - Going High - Asserted"
   --#SEVERITY CRITICAL
   ::= 65801

petTrap-Temperature-UC-Deassert TRAP-TYPE
   ENTERPRISE version
   DESCRIPTION "Upper Critical - Going High - Deasserted"
   --#SEVERITY INFORMATIONAL
   ::= 65929

petTrap-Temperature-UNR-Assert TRAP-TYPE
   ENTERPRISE version
   DESCRIPTION "Upper Non-Recoverable - Going High - Asserted"
   --#SEVERITY CRITICAL
   ::= 65803

petTrap-Temperature-UNR-Deassert TRAP-TYPE
   ENTERPRISE version
   DESCRIPTION "Upper Non-Recoverable - Going High - Deasserted"
   --#SEVERITY INFORMATIONAL
   ::= 65931

petTrap-CPU-Prochot-Assert TRAP-TYPE
   ENTERPRISE version
   DESCRIPTION "CPU Prochot - Asserted"
   --#SEVERITY MAJOR
   ::= 459521

petTrap-CPU-Prochot-Deassert TRAP-TYPE
   ENTERPRISE version
   DESCRIPTION "CPU Prochot - Desserted"
   --#SEVERITY INFORMATIONAL
   ::= 459649

petTrap-CPU-ThermalTrip-Assert TRAP-TYPE
   ENTERPRISE version
   DESCRIPTION "Thermal Trip - Asserted"
   --#SEVERITY CRITICAL
   ::= 487169

petTrap-CPU-CATERR-Assert TRAP-TYPE
   ENTERPRISE version
   DESCRIPTION "CPU CATERR - Asserted"
   --#SEVERITY CRITICAL
   ::= 487168

petTrap-CPU-CATERR-Deassert TRAP-TYPE
   ENTERPRISE version
   DESCRIPTION "CPU CATERR - Deasserted"
   --#SEVERITY INFORMATIONAL
   ::= 487296

petTrap-CPU-ERROR-Assert TRAP-TYPE
   ENTERPRISE version
   DESCRIPTION "CPU FIVR FAULT or ERR2 - Asserted"
   --#SEVERITY CRITICAL
   ::= 459777

petTrap-CPU-ERROR-Deassert TRAP-TYPE
   ENTERPRISE version
   DESCRIPTION "CPU FIVR FAULT or ERR2 - Deasserted"
   --#SEVERITY INFORMATIONAL
   ::= 459905

petTrap-PSU-AC-Lost-Assert TRAP-TYPE
   ENTERPRISE version
   DESCRIPTION "PSU AC lost: Power Supply Failure Detected - Asserted"
   --#SEVERITY CRITICAL
   ::= 552705

petTrap-PSU-AC-Lost-Deassert TRAP-TYPE
   ENTERPRISE version
   DESCRIPTION "PSU AC lost: Power Supply Failure Detected - Desserted"
   --#SEVERITY INFORMATIONAL
   ::= 552833

petTrap-PSU-Presence-Assert TRAP-TYPE
   ENTERPRISE version
   DESCRIPTION "PSU Presence: Presence Detected - Asserted"
   --#SEVERITY MINOR
   ::= 552704

petTrap-PSU-Presence-Deassert TRAP-TYPE
   ENTERPRISE version
   DESCRIPTION "PSU Presence: Presence Detected - Deasserted"
   --#SEVERITY INFORMATIONAL
   ::= 552832

petTrap-PSU-Redundancy-Assert TRAP-TYPE
   ENTERPRISE version
   DESCRIPTION "PSU PSU Redundancy: Redundancy mode - Asserted"
   --#SEVERITY MAJOR
   ::= 13004544

petTrap-PSU-Redundancy-Deassert TRAP-TYPE
   ENTERPRISE version
   DESCRIPTION "PSU PSU Redundancy: Redundancy mode - Deasserted"
   --#SEVERITY INFORMATIONAL
   ::= 13004672

petTrap-ChassisIntr-BMC-Assert TRAP-TYPE
   ENTERPRISE version
   DESCRIPTION "ChassisIntr - General Chassis Instrusion - Asserted"
   --#SEVERITY MAJOR
   ::= 356096

petTrap-ChassisIntr-BMC-Deassert TRAP-TYPE
   ENTERPRISE version
   DESCRIPTION "ChassisIntr - General Chassis Instrusion - Deasserted"
   --#SEVERITY INFORMATIONAL
   ::= 356224

petTrap-OS-Shutdown-Assert TRAP-TYPE
   ENTERPRISE version
   DESCRIPTION "OS Shutdown - Graceful Shutdown - Asserted"
   --#SEVERITY INFORMATIONAL
   ::= 2125571

petTrap-OS-Boot-Assert TRAP-TYPE
   ENTERPRISE version
   DESCRIPTION "OS Boot - Boot Completed - Asserted"
   --#SEVERITY INFORMATIONAL
   ::= 2060033

petTrap-TimeClockSync-Assert TRAP-TYPE
   ENTERPRISE version
   DESCRIPTION "Timestamp Clock Synch - Asserted"
   --#SEVERITY INFORMATIONAL
   ::= 1208069

petTrap-Dimm-Uncorrectable-ECC-Assert TRAP-TYPE
   ENTERPRISE version
   DESCRIPTION "Uncorrectable ECC - Asserted"
   --#SEVERITY CRITICAL
   ::= 814849

petTrap-Dimm-Correctable-ECC-Assert TRAP-TYPE
   ENTERPRISE version
   DESCRIPTION "Correctable ECC - Asserted"
   --#SEVERITY MAJOR
   ::= 814848

petTrap-ME-Transition-Power-Off-Assert TRAP-TYPE
   ENTERPRISE version
   DESCRIPTION "ME: Transition to Power Off - Asserted"
   --#SEVERITY INFORMATIONAL
   ::= 1444354

petTrap-ME-Transition-to-Running-Assert TRAP-TYPE
   ENTERPRISE version
   DESCRIPTION "ME: Transition to Running - Asserted"
   --#SEVERITY INFORMATIONAL
   ::= 1444352

petTrap-DIMM-ERROR-Assert TRAP-TYPE
   ENTERPRISE version
   DESCRIPTION "DIMM Error - Asserted"
   --#SEVERITY CRITICAL
   ::= 814853

petTrap-CPU-Utilization-UC-Assert TRAP-TYPE
   ENTERPRISE version
   DESCRIPTION "CPU Utilization Upper Critical - Going High - Asserted"
   --#SEVERITY CRITICAL
   ::= 459017

petTrap-CPU-Utilization-UC-Deassert TRAP-TYPE
   ENTERPRISE version
   DESCRIPTION "CPU Utilization Upper Critical - Going High - Desserted"
   --#SEVERITY INFORMATIONAL
   ::= 459145

petTrap-Memory-Utilization-UC-Assert TRAP-TYPE
   ENTERPRISE version
   DESCRIPTION "Memory Utilization Upper Critical - Going High - Asserted"
   --#SEVERITY CRITICAL
   ::= 786697

petTrap-Memory-Utilization-UC-Deassert TRAP-TYPE
   ENTERPRISE version
   DESCRIPTION "Memory Utilization Upper Critical - Going High - Desserted"
   --#SEVERITY INFORMATIONAL
   ::= 786825

petTrap-BMC-Test-trap TRAP-TYPE
   ENTERPRISE version
   DESCRIPTION "BMC test trap"
   --#SEVERITY INFORMATIONAL
   ::= 1208068

END
