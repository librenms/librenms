LCOS-SX-MIB  DEFINITIONS ::= BEGIN

IMPORTS
    DisplayString,MacAddress,TEXTUAL-CONVENTION,RowStatus                                              FROM SNMPv2-TC
    MODULE-COMPLIANCE,OBJECT-GROUP, NOTIFICATION-GROUP                                                 FROM SNMPv2-CONF
    ifIndex                                                                                            FROM IF-MIB
    enterprises,MODULE-IDENTITY,OBJECT-TYPE,NOTIFICATION-TYPE,Unsigned32,Integer32,Counter32,Counter64,IpAddress  FROM SNMPv2-SMI
--  PortList                                                                                           FROM Q-BRIDGE-MIB
    dot1qTpFdbAddress, dot1qFdbId, dot1qTpFdbPort                                                    FROM Q-BRIDGE-MIB
    InetAddress, InetAddressType                                                                       FROM INET-ADDRESS-MIB
    OwnerString                                                                                        FROM RMON-MIB
    SnmpAdminString                                                                                    FROM SNMP-FRAMEWORK-MIB;
--  MacAddress FROM BRIDGE-MIB;

lcosSX MODULE-IDENTITY
        LAST-UPDATED "201905310310Z"
        ORGANIZATION "LANCOM Systems GmbH"
        CONTACT-INFO
            " 
            Adenauerstrasse 20 / B2
            52146 Wuerselen
            Germany
            
            Phone:  +49 (0)2405 49 93 6 0
            Fax:    +49 (0)2405 49 93 6 99
            E-Mail: info@lancom.de"
        DESCRIPTION
        "Management information base definitions"
	REVISION      "201905310310Z"
        DESCRIPTION
		"Updated to fix bugs"
        REVISION      "201405300000Z"
        DESCRIPTION
		"Initial version of this MIB module."
        ::= { enterprises lancom-systems(2356) 14 }


-- =======================================================================================================================

     OperState ::= TEXTUAL-CONVENTION
       STATUS         current
       DESCRIPTION
                      "Oper state."
       SYNTAX         INTEGER  { up ( 1 ) , down ( 2 ) }

     AdminMode ::= TEXTUAL-CONVENTION
       STATUS      current
       DESCRIPTION
            "The Admin state - default: disable(0)."
       SYNTAX  INTEGER { disable(0), enable(1) }

     AdminMode2 ::= TEXTUAL-CONVENTION
       STATUS      current
       DESCRIPTION
            "The Admin state - default: disable(0)."
       SYNTAX  INTEGER { disable(0), enable(1), notSupported(2) }

     ActivateCmd ::= TEXTUAL-CONVENTION
       STATUS      current
       DESCRIPTION
            "Used to activate commands. default: noAction(0). "
       SYNTAX         INTEGER  {  noAction ( 0 ),
                                  activate ( 1 )
                               }

     KeyType ::= TEXTUAL-CONVENTION
       STATUS      current
       DESCRIPTION
           "The key type specifying the key generated for frames received
            on the port.
            0 : Normal,
            1 : Double Tag,
            2 : IP Address,
            3 : MAC and IP Address."
        SYNTAX      INTEGER  { normal  ( 0 ),
                               doubleTag ( 1 ),
                               ipAddr ( 2 ),
                               macAndIpAddr ( 3 )
                             }

     FrameRate ::= TEXTUAL-CONVENTION
       STATUS      current
       DESCRIPTION
           "The values for frame rate"
       SYNTAX       INTEGER {
                            threeHundredFramesPerSec (0),
                            oneHundredFramesPerSec (1),
                            tenFramesPerSec (2),
                            oneFramePerSec (3),
                            sixFramesPerMin (4),
                            oneFramePerMin  (5),
                            sixFramesPerHour (6)
                            }

     DayOfWeek ::= TEXTUAL-CONVENTION
       STATUS      current
       DESCRIPTION
            "Used to set the days of the week."
       SYNTAX       INTEGER {mon(1),tue(2),wed(3),thur(4),
                             fri(5),sat(6),sun(7) }

     Month ::= TEXTUAL-CONVENTION
       STATUS      current
       DESCRIPTION
            "Used to set the month."
       SYNTAX       INTEGER {jan(1),feb(2),march(3),april(4),
                             may(5),june(6),july(7),aug(8),
                             sept(9),oct(10),nov(11),dec(12)}

     SNMPv3SecurityLevel ::= TEXTUAL-CONVENTION
       STATUS      current
       DESCRIPTION
         "SNMPv3 USM security levels."
       SYNTAX      INTEGER {
                             noAuthNoPriv(1),
                             authNoPriv(2),
                             authPriv(3)
                           }
 
     SNMPv3AuthenticationProtocol ::= TEXTUAL-CONVENTION
       STATUS      current
       DESCRIPTION
         "SNMPv3 USM authentication protocol values."
       SYNTAX      INTEGER {
                             none(0),
                             md5(1),
                             sha1(2),
                             sha224(3),
                             sha256(4),
                             sha384(5),
                             sha512(6)
                           }
 
     SNMPv3PrivacyProtocol ::= TEXTUAL-CONVENTION
       STATUS      current
       DESCRIPTION
         "SNMPv3 USM privacy protocol values."
       SYNTAX      INTEGER {
                             none(0),
                             des(1),
                             aes128(2),
                             aes192(3),
                             aes256(4)
                           }


-- =======================================================================================================================
-- {NODE} 1.3.6.1.4.1.2356.14.1
lcsSystem                   OBJECT IDENTIFIER ::= { lcosSX 1 }

-- =======================================================================================================================
-- {NODE} 1.3.6.1.4.1.2356.14.1.1
lcsSystemInformation        OBJECT IDENTIFIER ::= { lcsSystem 1 }

lcsSystemInfo OBJECT IDENTIFIER ::= { lcsSystemInformation 1 }

lcsSystemInfoModelName OBJECT-TYPE
   SYNTAX       DisplayString
   MAX-ACCESS   read-only
   STATUS       current
   DESCRIPTION
       " "
   ::= { lcsSystemInfo 2 }

lcsSystemInfoSystemDescript OBJECT-TYPE
   SYNTAX       DisplayString
   MAX-ACCESS   read-only
   STATUS       current
   DESCRIPTION
       " "
   ::= { lcsSystemInfo 3 }

lcsSystemInfoLocation OBJECT-TYPE
   SYNTAX       DisplayString
   MAX-ACCESS   read-write
   STATUS       current
   DESCRIPTION
       " "
   ::= { lcsSystemInfo 4 }

lcsSystemInfoContact OBJECT-TYPE
   SYNTAX       DisplayString
   MAX-ACCESS   read-write
   STATUS       current
   DESCRIPTION
       " "
   ::= { lcsSystemInfo 5 }

lcsSystemInfoSystemName OBJECT-TYPE
   SYNTAX       DisplayString
   MAX-ACCESS   read-write
   STATUS       current
   DESCRIPTION
       " "
   ::= { lcsSystemInfo 6 }

lcsSystemInfoSystemDate OBJECT-TYPE
   SYNTAX       DisplayString
   MAX-ACCESS   read-only
   STATUS       current
   DESCRIPTION
       " "
   ::= { lcsSystemInfo 7 }

lcsSystemInfoSystemUptime OBJECT-TYPE
   SYNTAX       DisplayString
   MAX-ACCESS   read-only
   STATUS       current
   DESCRIPTION
       " "
   ::= { lcsSystemInfo 8 }

lcsSystemInfoBootloaderVersion OBJECT-TYPE
   SYNTAX       DisplayString
   MAX-ACCESS   read-only
   STATUS       current
   DESCRIPTION
       " "
   ::= { lcsSystemInfo 9 }

lcsSystemInfoFirmwareVersion OBJECT-TYPE
   SYNTAX       DisplayString
   MAX-ACCESS   read-only
   STATUS       current
   DESCRIPTION
       " "
   ::= { lcsSystemInfo 10 }

lcsSystemInfoHardwareVersion OBJECT-TYPE
   SYNTAX       DisplayString
   MAX-ACCESS   read-only
   STATUS       current
   DESCRIPTION
       " "
   ::= { lcsSystemInfo 11 }

lcsSystemInfoMechanicalVersion OBJECT-TYPE
   SYNTAX       DisplayString
   MAX-ACCESS   read-only
   STATUS       current
   DESCRIPTION
       " "
   ::= { lcsSystemInfo 12 }

lcsSystemInfoSeriesNumber OBJECT-TYPE
   SYNTAX       DisplayString
   MAX-ACCESS   read-only
   STATUS       current
   DESCRIPTION
       " "
   ::= { lcsSystemInfo 13 }

lcsSystemInfoHostMACAddress OBJECT-TYPE
   SYNTAX       DisplayString
   MAX-ACCESS   read-only
   STATUS       current
   DESCRIPTION
       " "
   ::= { lcsSystemInfo 14 }

lcsSystemInfoMemory OBJECT-TYPE
   SYNTAX       DisplayString
   MAX-ACCESS   read-only
   STATUS       current
   DESCRIPTION
       "Total Memory in RAM(MB)"
   ::= { lcsSystemInfo 15 }

lcsSystemInfoFlash OBJECT-TYPE
  SYNTAX       DisplayString
  MAX-ACCESS   read-only
  STATUS       current
  DESCRIPTION
      " "
  ::= { lcsSystemInfo 16 }

lcsSystemInfoFanSpeed OBJECT-TYPE
   SYNTAX       DisplayString
   MAX-ACCESS   read-only
   STATUS       current
   DESCRIPTION
       "Fan Speed"
   ::= { lcsSystemInfo 17 }

-- lcsSystemInfoPowerStatus OBJECT-TYPE
--   SYNTAX       DisplayString
--   MAX-ACCESS   read-only
--   STATUS       current
--   DESCRIPTION
--       " "
--   ::= { lcsSystemInfo 19 }
   
-- lcsSystemInfoPowers OBJECT-TYPE
--   SYNTAX       DisplayString
--   MAX-ACCESS   read-only
--   STATUS       current
--   DESCRIPTION
--       " "
--   ::= { lcsSystemInfo 20 }
   
-- lcsSystemInfoTemperatureStatus OBJECT-TYPE
--   SYNTAX       DisplayString
--   MAX-ACCESS   read-only
--   STATUS       current
--   DESCRIPTION
--       " "
--   ::= { lcsSystemInfo 21 }   

lcsSystemInfoTemperature1 OBJECT-TYPE
   SYNTAX       DisplayString
   MAX-ACCESS   read-only
   STATUS       current
   DESCRIPTION
       " "
   ::= { lcsSystemInfo 22 }

lcsSystemInfoTemperature2 OBJECT-TYPE
   SYNTAX       DisplayString
   MAX-ACCESS   read-only
   STATUS       current
   DESCRIPTION
       " "
   ::= { lcsSystemInfo 23 }
   
lcsSystemInfoCPULoad OBJECT-TYPE
   SYNTAX       DisplayString
   MAX-ACCESS   read-only
   STATUS       current
   DESCRIPTION
       "CPU Utilization."
   ::= { lcsSystemInfo 24 }

lcsSystemInfoProductionDate OBJECT-TYPE
   SYNTAX       DisplayString
   MAX-ACCESS   read-only
   STATUS       current
   DESCRIPTION
       "Production Date."
   ::= { lcsSystemInfo 33 }

lcsSystemInfoTemperature3 OBJECT-TYPE
   SYNTAX       DisplayString
   MAX-ACCESS   read-only
   STATUS       current
   DESCRIPTION
       " "
   ::= { lcsSystemInfo 34 }
   
lcsSystemInfoPhysicalPorts OBJECT-TYPE
    SYNTAX       Integer32
    MAX-ACCESS   read-only
    STATUS       current
    DESCRIPTION
        "Number of physical Ports"
    ::= { lcsSystemInfo 200 }

lcsSystemInfoTemperatureSensor1 OBJECT-TYPE
   SYNTAX       Integer32
   MAX-ACCESS   read-only
   STATUS       current
   DESCRIPTION
       "Temperature sensor 1 in degrees Celsius"
   ::= { lcsSystemInfo 201 }

lcsSystemInfoTemperatureSensor2 OBJECT-TYPE
   SYNTAX       Integer32
   MAX-ACCESS   read-only
   STATUS       current
   DESCRIPTION
       "Temperature sensor 2 in degrees Celsius"
   ::= { lcsSystemInfo 202 }

lcsSystemInfoTemperatureSensor3 OBJECT-TYPE
   SYNTAX       Integer32
   MAX-ACCESS   read-only
   STATUS       current
   DESCRIPTION
       "Temperature sensor 3 in degrees Celsius"
   ::= { lcsSystemInfo 203 }

lcsSystemInfoFreeMemory OBJECT-TYPE
     SYNTAX       Integer32
     MAX-ACCESS   read-only
     STATUS       current
     DESCRIPTION
         "Free memory in RAM(MB)"
     ::= { lcsSystemInfo 204 }


lcsPowerInformation    OBJECT IDENTIFIER ::= { lcsSystemInformation 2 }

lcsPowerInfoDetectedPSUA OBJECT-TYPE
   SYNTAX      DisplayString
   MAX-ACCESS  read-only
   STATUS      current
   DESCRIPTION
       "Is the power supply unit present. "
   ::= {lcsPowerInformation 2 }
   
lcsPowerInfoDetectedPSUB OBJECT-TYPE
   SYNTAX      DisplayString
   MAX-ACCESS  read-only
   STATUS      current
   DESCRIPTION
       "Is the power supply unit present. "
   ::= {lcsPowerInformation 3 }   
   
lcsPowerInfoPSUStatusA OBJECT-TYPE
   SYNTAX      DisplayString
   MAX-ACCESS  read-only
   STATUS      current
   DESCRIPTION
       "The status of power supply unit. "
   ::= {lcsPowerInformation 4 }   

lcsPowerInfoPSUStatusB OBJECT-TYPE
   SYNTAX      DisplayString
   MAX-ACCESS  read-only
   STATUS      current
   DESCRIPTION
       "The status of power supply unit. "
   ::= {lcsPowerInformation 5 } 

lcsPowerInfoFANSpeedA OBJECT-TYPE
   SYNTAX      Integer32
   MAX-ACCESS  read-only
   STATUS      current
   DESCRIPTION
       "The fan speed of power supply unit. "
   ::= {lcsPowerInformation 6 }   

lcsPowerInfoFANSpeedB OBJECT-TYPE
   SYNTAX      Integer32
   MAX-ACCESS  read-only
   STATUS      current
   DESCRIPTION
       "The fan speed of power supply unit. "
   ::= {lcsPowerInformation 7 }      
   
lcsPowerInfoTemperatureA OBJECT-TYPE
   SYNTAX      Integer32
   MAX-ACCESS  read-only
   STATUS      current
   DESCRIPTION
       "The temperature of power supply unit. "
   ::= {lcsPowerInformation 8 }   

lcsPowerInfoTemperatureB OBJECT-TYPE
   SYNTAX      Integer32
   MAX-ACCESS  read-only
   STATUS      current
   DESCRIPTION
       "The temperature of power supply unit. "
   ::= {lcsPowerInformation 9 }    
   
lcsPowerInfoOperatingMode OBJECT-TYPE
   SYNTAX      Integer32 (0|1)
   MAX-ACCESS  read-write
   STATUS      current
   DESCRIPTION
       "The operating mode of power supply unit. 
       0:Boost
       1:Redundant"
   ::= {lcsPowerInformation 10 }    

   
lcsSystemTimeConf                                    OBJECT IDENTIFIER ::= { lcsSystem 2 }

-- lcsSystemNTP                                      OBJECT IDENTIFIER ::= { lcsSystemTimeConf  1 }

lcsSystemTime                                      OBJECT IDENTIFIER ::= { lcsSystemTimeConf  2 }
lcsSystemTimeZone                              OBJECT IDENTIFIER ::= { lcsSystemTime 1 }
lcsSystemTimeDaylightSaving             OBJECT IDENTIFIER ::= { lcsSystemTime 2 }
lcsSystemTimeConfiguration              OBJECT IDENTIFIER ::= { lcsSystemTime 3 }

    --
-- =======================================================================================================================
-- Objects in the lcsSystemNTP Group
-- =======================================================================================================================
--    lcsSystemNTPMode OBJECT-TYPE
--               SYNTAX       INTEGER {useLocal(0),useNTP(1)}
--               MAX-ACCESS   read-write
--               STATUS       current
--               DESCRIPTION
--                   "The system NTP Mode.
--                    useLocal(0) : Use Local Settings,
--                    useNTP(1)   : Use NTP Server."
--               DEFVAL  { useLocal }
--               ::= {     lcsSystemNTP 1 }
--
--    lcsSystemNTPServer1    OBJECT-TYPE
--               SYNTAX            DisplayString
--               MAX-ACCESS        read-write
--               STATUS            current
--               DESCRIPTION
--                   "Get/Set the NTP Time Server1.
--                    You can use the IP address or domain name."
--               ::= {     lcsSystemNTP 2 }
--
--    lcsSystemNTPServer2    OBJECT-TYPE
--               SYNTAX            DisplayString
--               MAX-ACCESS        read-write
--               STATUS            current
--               DESCRIPTION
--                   "Get/Set the NTP Time Server2.
--                    You can use the IP address or domain name."
--               ::= {     lcsSystemNTP 3 }
--
--    lcsSystemNTPServer3    OBJECT-TYPE
--               SYNTAX            DisplayString
--               MAX-ACCESS        read-write
--               STATUS            current
--               DESCRIPTION
--                   "Get/Set the NTP Time Server3.
--                    You can use the IP address or domain name."
--               ::= {     lcsSystemNTP 4 }
--
--    lcsSystemNTPServer4    OBJECT-TYPE
--               SYNTAX            DisplayString
--               MAX-ACCESS        read-write
--               STATUS            current
--               DESCRIPTION
--                   "Get/Set the NTP Time Server4.
--                    You can use the IP address or domain name."
--               ::= {     lcsSystemNTP 5 }
--
--    lcsSystemNTPServer5    OBJECT-TYPE
--               SYNTAX            DisplayString
--               MAX-ACCESS        read-write
--               STATUS            current
--               DESCRIPTION
--                   "Get/Set the NTP Time Server5.
--                    You can use the IP address or domain name."
--               ::= {     lcsSystemNTP 6 }


--
-- =======================================================================================================================
-- Objects in the lcsSystemTime Group
-- =======================================================================================================================
--lcsSystemTimeZone

    lcsSystemTimeZoneConf OBJECT-TYPE
               SYNTAX       Integer32(-7200..7201)
               MAX-ACCESS   read-write
               STATUS       current
               DESCRIPTION
                   "Get/Set the NTP Time Zone.
                    The value range is between -7200 and 7201 (minutes).
                    0 : None.
                    -7200 : (GMT-12:00).
                    -6600 : (GMT-11:00).
                    -6000 : (GMT-10:00).
                    -5400 : (GMT-09:00).
                    -4800 : (GMT-08:00)Pacific Time.
                    -4801 : (GMT-08:00)Tijuana, Baja California.
                    -4200 : (GMT-07:00)Arizona.
                    -4201 : (GMT-07:00)Chihuahua, La Paz, Mazatlan - New.
                    -4202 : (GMT-07:00)Chihuahua, La Paz, Mazatlan - Old.
                    -4203 : (GMT-07:00)Mountain Time.
                    -3600 : (GMT-06:00)Central America.
                    -3601 : (GMT-06:00)Central Time.
                    -3602 : (GMT-06:00)Guadalajara, Mexico City, Monterrey - New.
                    -3603 : (GMT-06:00)Guadalajara, Mexico City, Monterrey - Old.
                    -3604 : (GMT-06:00)Saskatchewan.
                    -3000 : (GMT-05:00)Bogota, Lima, Quito, Rio Branco.
                    -3001 : (GMT-05:00)Eastern Time.
                    -3002 : (GMT-05:00)Indiana.
                    -2700 : (GMT-04:30).
                    -2400 : (GMT-04:00)Atlantic Time.
                    -2401 : (GMT-04:00)La Paz.
                    -2402 : (GMT-04:00)Manaus.
                    -2403 : (GMT-04:00)Santiago.
                    -2100 : (GMT-03:30).
                    -1800 : (GMT-03:00)Brasilia.
                    -1801 : (GMT-03:00)Buenos Aires.
                    -1802 : (GMT-03:00)Georgetown.
                    -1803 : (GMT-03:00)Greenland.
                    -1804 : (GMT-03:00)Montevideo.
                    -1805 : (GMT-02:00).
                    -600 : (GMT-01:00)Azores.
                    -601 : (GMT-01:00)Cape Verde Is.
                    1 : (GMT) Casablanca.
                    2 : (GMT) Greenwich Mean Time.
                    3 : (GMT) Monrovia, Reykjavik.
                    600 : (GMT+01:00) Amsterdam, Berlin, Bern, Rome, Stockholm, Vienna.
                    601 : (GMT+01:00) Belgrade, Bratislava, Budapest, Ljubljana, Prague.
                    602 : (GMT+01:00) Brussels, Copenhagen, Madrid, Paris.
                    603 : (GMT+01:00) Sarajevo, Skopje, Warsaw, Zagreb.
                    604 : (GMT+01:00) West Central Africa.
                    1200 : (GMT+02:00) Amman.
                    1201 : (GMT+02:00) Athens, Bucharest, Istanbul.
                    1202 : (GMT+02:00) Beirut.
                    1203 : (GMT+02:00) Cairo.
                    1204 : (GMT+02:00) Harare, Pretoria.
                    1205 : (GMT+02:00) Helsinki, Kyiv, Riga, Sofia, Tallinn, Vilnius.
                    1206 : (GMT+02:00) Jerusalem.
                    1207 : (GMT+02:00) Minsk.
                    1208 : (GMT+02:00) Windhoek.
                    1800 : (GMT+03:00) Baghdad.
                    1801 : (GMT+03:00) Kuwait, Riyadh.
                    1802 : (GMT+03:00) Moscow, St. Petersburg, Volgograd.
                    1803 : (GMT+03:00) Nairobi.
                    1804 : (GMT+03:00) Tbilisi.
                    2100 : (GMT+03:30) Tehran.
                    2400 : (GMT+04:00) Abu Dhabi, Muscat.
                    2401 : (GMT+04:00) Baku.
                    2402 : (GMT+04:00) Caucasus Standard Time.
                    2403 : (GMT+04:00) Port Louis.
                    2404 : (GMT+04:00) Yerevan.
                    2700 : (GMT+04:30) Kabul.
                    3000 : (GMT+05:00) Ekaterinburg.
                    3001 : (GMT+05:00) Islamabad, Karachi.
                    3002 : (GMT+05:00) Tashkent.
                    3300 : (GMT+05:30) Chennai, Kolkata, Mumbai, New Delhi.
                    3301 : (GMT+05:30) Sri Jayawardenepura.
                    3455 : (GMT+05:45) Kathmandu.
                    3600 : (GMT+06:00) Almaty, Novosibirsk.
                    3601 : (GMT+06:00) Astana, Dhaka.
                    3600 : (GMT+06:30) Yangon (Rangoon).
                    4200 : (GMT+07:00) Bangkok, Hanoi, Jakarta.
                    4201 : (GMT+07:00) Krasnoyarsk.
                    4800 : (GMT+08:00) Beijing, Chongqing, Hong Kong, Urumqi.
                    4801 : (GMT+08:00) Irkutsk, Ulaan Bataar.
                    4802 : (GMT+08:00) Kuala Lumpur, Singapore.
                    4803 : (GMT+08:00) Perth.
                    4804 : (GMT+08:00) Taipei.
                    5400 : (GMT+09:00) Osaka, Sapporo, Tokyo.
                    5401 : (GMT+09:00) Seoul.
                    5402 : (GMT+09:00) Yakutsk.
                    5700 : (GMT+09:30) Adelaide.
                    5701 : (GMT+09:30) Darwin.
                    6000 : (GMT+10:00) Brisbane.
                    6001 : (GMT+10:00) Canberra, Melbourne, Sydney.
                    6002 : (GMT+10:00) Guam, Port Moresby.
                    6003 : (GMT+10:00) Hobart.
                    6004 : (GMT+10:00) Vladivostok.
                    6600 : (GMT+11:00) Magadan, Solomon Is., New Caledonia.
                    7200 : (GMT+12:00) Auckland, Wellington.
                    7201 : (GMT+12:00) Fiji, Kamchatka, Marshall Is."
               ::= {     lcsSystemTimeZone 1 }

    lcsSystemTimeZoneAcronym OBJECT-TYPE
               SYNTAX       DisplayString
               MAX-ACCESS   read-write
               STATUS       current
               DESCRIPTION
                   "Acronym - User can set the acronym of the time zone.
                    This is a User configurable acronym to identify the time zone.
                    Range : 0 - 16 characters."
               ::= {     lcsSystemTimeZone 2 }

--lcsSystemTimeDaylightSaving

    lcsSystemTimeDaylightSavingMode OBJECT-TYPE
               SYNTAX       INTEGER { disable(0), recurring(1), nonRecurring(2) }
               MAX-ACCESS   read-write
               STATUS       current
               DESCRIPTION
                   "The system Daylight Savings Mode.
                    disable(0)   : Disable.
                    recurring(1) : Recurring
                        - configure the Daylight Saving Time duration
                        to repeat the configuration every year.
                    nonRecurring(2): Non-Recurring - configure the Daylight Saving Time
                        duration for single time configuration."
               DEFVAL  { disable }
               ::= {     lcsSystemTimeDaylightSaving 1 }

    lcsSystemTimeDaylightSavingStartWeek OBJECT-TYPE
               SYNTAX       DisplayString
               MAX-ACCESS   read-write
               STATUS       current
               DESCRIPTION
                   "Start time Week. Use in Recurring Mode.
                    Range : first,2,3,4,last.
                    Default : first."
               ::= {     lcsSystemTimeDaylightSaving 2 }

    lcsSystemTimeDaylightSavingStartDay OBJECT-TYPE
               SYNTAX       DayOfWeek
               MAX-ACCESS   read-write
               STATUS       current
               DESCRIPTION
                   "Start time Day. Use in Recurring Mode."
               DEFVAL  { mon }
               ::= {     lcsSystemTimeDaylightSaving 3 }

    lcsSystemTimeDaylightSavingStartMonth OBJECT-TYPE
               SYNTAX       Month
               MAX-ACCESS   read-write
               STATUS       current
               DESCRIPTION
                   "Start time Month."
               DEFVAL  { jan }
               ::= {     lcsSystemTimeDaylightSaving 4 }

    lcsSystemTimeDaylightSavingStartDate OBJECT-TYPE
               SYNTAX       Integer32 (1..31)
               MAX-ACCESS   read-write
               STATUS       current
               DESCRIPTION
                   "Start time Date. Use in Non-Recurring Mode.
                    Range : 1 - 31.
                    Default : 1."
               ::= {     lcsSystemTimeDaylightSaving 5 }

    lcsSystemTimeDaylightSavingStartYear OBJECT-TYPE
               SYNTAX       Integer32 (2000..2097)
               MAX-ACCESS   read-write
               STATUS       current
               DESCRIPTION
                   "Start time Year. Use in Non-Recurring Mode.
                    Range : 2000 - 2097.
                    Default : 2000."
               ::= {     lcsSystemTimeDaylightSaving 6 }

    lcsSystemTimeDaylightSavingStartHours OBJECT-TYPE
               SYNTAX       Integer32 (0..23)
               MAX-ACCESS   read-write
               STATUS       current
               DESCRIPTION
                   "Start time Hours.
                     Range : 0 - 23.
                     Default : 0."
               ::= {     lcsSystemTimeDaylightSaving 7 }

    lcsSystemTimeDaylightSavingStartMinutes OBJECT-TYPE
               SYNTAX       Integer32 (0..59)
               MAX-ACCESS   read-write
               STATUS       current
               DESCRIPTION
                   "Start time Minutes.
                    Range : 0 - 59.
                    Default : 0."
               ::= {     lcsSystemTimeDaylightSaving 8 }

    lcsSystemTimeDaylightSavingEndWeek OBJECT-TYPE
               SYNTAX       DisplayString
               MAX-ACCESS   read-write
               STATUS       current
               DESCRIPTION
                   "End time Week. Use in Recurring Mode.
                    Range : first,2,3,4,last.
                    Default : first."
               ::= {     lcsSystemTimeDaylightSaving 9 }

    lcsSystemTimeDaylightSavingEndDay OBJECT-TYPE
               SYNTAX       DayOfWeek
               MAX-ACCESS   read-write
               STATUS       current
               DESCRIPTION
                   "End time Day. Use in Recurring Mode."
               DEFVAL  { mon }
               ::= {     lcsSystemTimeDaylightSaving 10 }

    lcsSystemTimeDaylightSavingEndMonth OBJECT-TYPE
               SYNTAX       Month
               MAX-ACCESS   read-write
               STATUS       current
               DESCRIPTION
                   "End time Month."
              DEFVAL  { jan }
              ::= {     lcsSystemTimeDaylightSaving 11 }

    lcsSystemTimeDaylightSavingEndDate OBJECT-TYPE
               SYNTAX       Integer32 (1..31)
               MAX-ACCESS   read-write
               STATUS       current
               DESCRIPTION
                   "End time Date. Use in Non-Recurring Mode.
                    Range : 1 - 31.
                    Default : 1."
               ::= {     lcsSystemTimeDaylightSaving 12 }

    lcsSystemTimeDaylightSavingEndYear OBJECT-TYPE
               SYNTAX       Integer32 (2000..2097)
               MAX-ACCESS   read-write
               STATUS       current
               DESCRIPTION
                   "End time Year. Use in Non-Recurring Mode.
                    Range : 2000 - 2097.
                    Default : 2000."
               ::= {     lcsSystemTimeDaylightSaving 13 }

    lcsSystemTimeDaylightSavingEndHours OBJECT-TYPE
               SYNTAX       Integer32 (0..23)
               MAX-ACCESS   read-write
               STATUS       current
               DESCRIPTION
                   "End time Hours.
                    Range : 0 - 23.
                    Default : 0."
               ::= {     lcsSystemTimeDaylightSaving 14 }

    lcsSystemTimeDaylightSavingEndMinutes OBJECT-TYPE
               SYNTAX       Integer32 (0..59)
               MAX-ACCESS   read-write
               STATUS       current
               DESCRIPTION
                   "End time Minutes.
                    Range : 0 - 59.
                    Default : 0."
               ::= {     lcsSystemTimeDaylightSaving 15 }

    lcsSystemTimeDaylightSavingOffset OBJECT-TYPE
               SYNTAX       Integer32 (1..1440)
               MAX-ACCESS   read-write
               STATUS       current
               DESCRIPTION
                   "Offset - the number of minutes to add during Daylight Saving Time.
                    Range : 1 - 1440(Minutes).
                    Default : 1."
               ::= {     lcsSystemTimeDaylightSaving 16 }

    lcsSystemTimeConfigurationClockSource OBJECT-TYPE
               SYNTAX       Integer32
               MAX-ACCESS   read-write
               STATUS       current
               DESCRIPTION
                   "0:Use Local Settings.
                    1:Use NTP Server."
               ::= {     lcsSystemTimeConfiguration 1}

    lcsSystemTimeConfigurationSystemDate OBJECT-TYPE
               SYNTAX       DisplayString
               MAX-ACCESS   read-write
               STATUS       current
               DESCRIPTION
                   "System date. Default format:yyyy-mm-dd.
                    When ClockSource is Use Local Settings, you can set this field."
               ::= {     lcsSystemTimeConfiguration 2}
                          
    lcsSystemTimeConfigurationDateFormat OBJECT-TYPE
               SYNTAX       Integer32 (0|1|2)
               MAX-ACCESS   read-write
               STATUS       current
               DESCRIPTION
                   "The date format of the system.
                   0:yyyy-mm-dd
                   1:mm-dd-yyyy
                   2:dd-mm-yyyy"
               ::= {     lcsSystemTimeConfiguration 3}
               
    lcsSystemTimeConfigurationTimeFormat OBJECT-TYPE
               SYNTAX       Integer32 (0|1)
               MAX-ACCESS   read-write
               STATUS       current
               DESCRIPTION
                   "The time format of the system.
                   0:24-hr, format:hh:mm:ss
                   1:12-hr, format:hh:mm:ss am/pm"
	           ::= {     lcsSystemTimeConfiguration 4}

    lcsSystemTimeConfigurationSystemTime OBJECT-TYPE
               SYNTAX       DisplayString
               MAX-ACCESS   read-write
               STATUS       current
               DESCRIPTION
                   "System date.
                   24-hr, format:hh:mm:ss
                   12-hr, format:hh:mm:ss am/pm
                    When ClockSource is Use Local Settings, you can set this field."
	           ::= {     lcsSystemTimeConfiguration 5}			   

-- =======================================================================================================================
lcsSystemAccount                                         OBJECT IDENTIFIER ::= { lcsSystem 3 }

lcsSystemAccountUsers                                     OBJECT IDENTIFIER  ::= { lcsSystemAccount 1 }

--
-- =======================================================================================================================
-- Start lcsUserConfig group
-- =======================================================================================================================
--lcsUserConfigTable

    lcsUserConfigTable OBJECT-TYPE
               SYNTAX      SEQUENCE OF     LCSUserConfigEntry
               MAX-ACCESS  not-accessible
               STATUS      current
               DESCRIPTION
                   "The User Config Table. "
               ::= {     lcsSystemAccountUsers 1 }

    lcsUserConfigEntry OBJECT-TYPE
               SYNTAX          LCSUserConfigEntry
               MAX-ACCESS  not-accessible
               STATUS      current
               DESCRIPTION
                   "The User Config Entry."
               INDEX    {    lcsUserConfigIndex  }
               ::= {     lcsUserConfigTable 1 }

    LCSUserConfigEntry             ::= SEQUENCE {
                 lcsUserConfigIndex            Integer32,
                 lcsUserConfigUserName         DisplayString,
                 lcsUserConfigPassword         DisplayString,
                 lcsUserConfigPrivilegeLevel   Integer32,
                 lcsUserConfigRowStatus        RowStatus
                }

    lcsUserConfigIndex OBJECT-TYPE
               SYNTAX      Integer32 (1..4094)
               MAX-ACCESS  not-accessible
               STATUS      current
               DESCRIPTION
                   "The user Config Index. "
               ::= {     lcsUserConfigEntry 1 }

    lcsUserConfigUserName OBJECT-TYPE
               SYNTAX      DisplayString(SIZE (1..31))
               MAX-ACCESS  read-create
               STATUS      current
               DESCRIPTION
                   "A string identifying the user name for the entry.
                    string length: 1-31. "
               ::= {     lcsUserConfigEntry 2 }

    lcsUserConfigPassword OBJECT-TYPE
               SYNTAX      DisplayString(SIZE (0..128))
               MAX-ACCESS  read-create
               STATUS      current
               DESCRIPTION
                   "The password of the user.
                    string length: 0-128. "
               ::= {     lcsUserConfigEntry 3 }

    lcsUserConfigPrivilegeLevel OBJECT-TYPE
               SYNTAX      Integer32(1..15)
               MAX-ACCESS  read-create
               STATUS      current
               DESCRIPTION
                   "The privilege level of the user.If the privilege level
                    value is 15, it can access all groups.range: 1-15. "
               ::= {     lcsUserConfigEntry 4 }

    lcsUserConfigRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     lcsUserConfigEntry 5 }


--
-- =======================================================================================================================
-- Start lcsPrivilegeLevelConfig group
-- =======================================================================================================================
--lcsPrivilegeLevelConfigTable

    lcsPrivilegeLevelConfigTable OBJECT-TYPE
               SYNTAX      SEQUENCE OF     LCSPrivilegeLevelConfigEntry
               MAX-ACCESS  not-accessible
               STATUS      current
               DESCRIPTION
                   "The Privilege Level Config Table. "
               ::= {     lcsSystemAccountUsers 2 }

    lcsPrivilegeLevelConfigEntry OBJECT-TYPE
               SYNTAX          LCSPrivilegeLevelConfigEntry
               MAX-ACCESS  not-accessible
               STATUS      current
               DESCRIPTION
                   "The Privilege Level Config Entry."
               INDEX    {    lcsPrivilegeLevelIndex  }
               ::= {     lcsPrivilegeLevelConfigTable 1 }

    LCSPrivilegeLevelConfigEntry             ::= SEQUENCE {
                 lcsPrivilegeLevelIndex                Integer32,
                 lcsPrivilegeLevelGroupName            DisplayString,
                 lcsPrivilegeLevelConfigReadOnly       Integer32,
                 lcsPrivilegeLevelConfigReadWrite      Integer32,
                 lcsPrivilegeLevelStatusReadOnly       Integer32,
                 lcsPrivilegeLevelStatusReadWrite      Integer32
                 }

    lcsPrivilegeLevelIndex OBJECT-TYPE
               SYNTAX      Integer32 (1..4094)
               MAX-ACCESS  not-accessible
               STATUS      current
               DESCRIPTION
                   "The Privilege Level Index. "
               ::= {     lcsPrivilegeLevelConfigEntry 1 }

    lcsPrivilegeLevelGroupName OBJECT-TYPE
               SYNTAX      DisplayString
               MAX-ACCESS  read-only
               STATUS      current
               DESCRIPTION
                   "The name identifying the privilege group."
               ::= {     lcsPrivilegeLevelConfigEntry 2 }

    lcsPrivilegeLevelConfigReadOnly OBJECT-TYPE
               SYNTAX      Integer32(1..15)
               MAX-ACCESS  read-write
               STATUS      current
               DESCRIPTION
                   "The privilege level of configuration read-only.If the
                    privilege level value is 15,it can access all groups.
                    range: 1-15.  "
               ::= {     lcsPrivilegeLevelConfigEntry 3 }

    lcsPrivilegeLevelConfigReadWrite OBJECT-TYPE
               SYNTAX      Integer32(1..15)
               MAX-ACCESS  read-write
               STATUS      current
               DESCRIPTION
                   "The privilege level of configuration/execute read/write.
                    If the privilege level value is 15,it can access all groups.
                    range: 1-15. "
               ::= {     lcsPrivilegeLevelConfigEntry 4 }

    lcsPrivilegeLevelStatusReadOnly OBJECT-TYPE
               SYNTAX      Integer32(1..15)
               MAX-ACCESS  read-write
               STATUS      current
               DESCRIPTION
                   "The privilege level of status/statistics read-only.
                    If the privilege level value is 15,it can access all groups.
                    range: 1-15. "
               ::= {     lcsPrivilegeLevelConfigEntry 5 }

    lcsPrivilegeLevelStatusReadWrite OBJECT-TYPE
               SYNTAX      Integer32(1..15)
               MAX-ACCESS  read-write
               STATUS      current
               DESCRIPTION
                   "The privilege level of status/statistics read-write.
                    If the privilege level value is 15,it can access all groups.
                    range: 1-15. "
               ::= {     lcsPrivilegeLevelConfigEntry 6 }

    lcsSystemAccountSuperUserPassword OBJECT-TYPE
               SYNTAX      DisplayString (SIZE(0..128))
               MAX-ACCESS  read-write
               STATUS      current
               DESCRIPTION
                   "Encrypted admin password"
               ::= { lcsSystemAccountUsers 1500 }

    lcsSystemAccountSuperUserPasswordUnhashed OBJECT-TYPE
               SYNTAX      DisplayString (SIZE(0..128))
               MAX-ACCESS  read-write
               STATUS      current
               DESCRIPTION
                   "Admin password
                    This object will return an empty string even if a password is set."
               ::= { lcsSystemAccountUsers 1501 }

    lcsSystemAccountEnforcePasswordRules OBJECT-TYPE
               SYNTAX      Integer32 (0|1)
               MAX-ACCESS  read-write
               STATUS      current
               DESCRIPTION
                   "Enforce the password policies or not."
               ::= { lcsSystemAccountUsers 1502 }

-- =======================================================================================================================
lcsIP                                                    OBJECT IDENTIFIER ::= { lcsSystem 4 }

lcsIPConfigurationBasic OBJECT IDENTIFIER ::= { lcsIP 1 }

lcsIPConfigIPv4DHCPClientEnable OBJECT-TYPE
   SYNTAX      Integer32 (0|1)
   MAX-ACCESS  read-write
   STATUS      current
   DESCRIPTION
       "IPv4 DHCP Client Enabled
        0: Disable
        1: Enable"
   ::= {lcsIPConfigurationBasic 1 }

lcsIPConfigIPv4Address OBJECT-TYPE
   SYNTAX      DisplayString
   MAX-ACCESS  read-write
   STATUS      current
   DESCRIPTION
       "IPv4 Address."
   ::= {lcsIPConfigurationBasic 2 }
   
lcsIPConfigSubnetMask OBJECT-TYPE
   SYNTAX      DisplayString
   MAX-ACCESS  read-write
   STATUS      current
   DESCRIPTION
       "IPv4 SubnetMask."
   ::= {lcsIPConfigurationBasic 3 }
   
lcsIPConfigGateway OBJECT-TYPE
   SYNTAX      DisplayString
   MAX-ACCESS  read-write
   STATUS      current
   DESCRIPTION
       "IPv4 Gateway."
   ::= {lcsIPConfigurationBasic 4 }
   
lcsIPConfigDNSServer OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
        4. DNS configuration is derived from DHCPv6.
        5. DNS configuration is derived from DHCPv6 on specific VLAN.
        "
   ::= {lcsIPConfigurationBasic 5 }

lcsIPConfigDNSServerValue OBJECT-TYPE
   SYNTAX      DisplayString
   MAX-ACCESS  read-write
   STATUS      current
   DESCRIPTION
       "DNS IPv4 Address or VLAN value."
   ::= {lcsIPConfigurationBasic 6 }  

lcsIPConfiguration OBJECT IDENTIFIER ::= { lcsIP 2 }

lcsMode OBJECT-TYPE
   SYNTAX      Integer32 (0|1)
   MAX-ACCESS  read-write
   STATUS      current
   DESCRIPTION
       "IP Configuration Mode.
        default:0
        0: Host
        1: Router"
   ::= {lcsIPConfiguration 2 }

lcsDNSServerSource1 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
        4. DNS configuration is derived from DHCPv6.
        5. DNS configuration is derived from DHCPv6 on specific VLAN.
        "
   ::= {lcsIPConfiguration 3 }
   
lcsDNSServerSource2 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
        4. DNS configuration is derived from DHCPv6.
        5. DNS configuration is derived from DHCPv6 on specific VLAN.
        "
   ::= {lcsIPConfiguration 4 }   
   
lcsDNSServerSource3 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
        4: DNS configuration is derived from DHCPv6.
        5: DNS configuration is derived from DHCPv6 on specific VLAN.
        "
   ::= {lcsIPConfiguration 5 }  
   
lcsDNSServerSource4 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
        4: DNS configuration is derived from DHCPv6.
        5: DNS configuration is derived from DHCPv6 on specific VLAN.
        "
   ::= {lcsIPConfiguration 6 }    

lcsDNSServerValue1 OBJECT-TYPE
   SYNTAX      DisplayString
   MAX-ACCESS  read-write
   STATUS      current
   DESCRIPTION
       "DNS IPv4/IPv6 Address or VLAN value."
   ::= {lcsIPConfiguration 7 }
   
lcsDNSServerValue2 OBJECT-TYPE
   SYNTAX      DisplayString
   MAX-ACCESS  read-write
   STATUS      current
   DESCRIPTION
      "DNS IPv4/IPv6 Address or VLAN value."
   ::= {lcsIPConfiguration 8 }   
   
lcsDNSServerValue3 OBJECT-TYPE
   SYNTAX      DisplayString
   MAX-ACCESS  read-write
   STATUS      current
   DESCRIPTION
       "DNS IPv4/IPv6 Address or VLAN value."
   ::= {lcsIPConfiguration 9 }    
   
lcsDNSServerValue4 OBJECT-TYPE
   SYNTAX      DisplayString
   MAX-ACCESS  read-write
   STATUS      current
   DESCRIPTION
       "DNS IPv4/IPv6 Address or VLAN value."
   ::= {lcsIPConfiguration 10 }   
   
lcsDNSProxy OBJECT-TYPE
   SYNTAX      Integer32 (0|1)
   MAX-ACCESS  read-write
   STATUS      current
   DESCRIPTION
       "DNS Proxy enable/disable.
        default:0
        0: disable
        1: enable"
   ::= {lcsIPConfiguration 11 }


lcsIPInterfaces OBJECT IDENTIFIER ::= { lcsIP 3 }

lcsIPInterfacesTable OBJECT-TYPE
   SYNTAX      SEQUENCE OF LCSIPInterfacesEntry
   MAX-ACCESS  not-accessible
   STATUS      current
   DESCRIPTION
       "A table of IP interface for switch."
    ::= { lcsIPInterfaces 1 }

lcsIPInterfacesEntry OBJECT-TYPE
    SYNTAX        LCSIPInterfacesEntry
    MAX-ACCESS    not-accessible
    STATUS        current
    DESCRIPTION
        "An entry in the lcsIPInterfacesTable."
    INDEX        { lcsIPInterfacesIndex }
    ::= { lcsIPInterfacesTable 1 }

LCSIPInterfacesEntry ::=
    SEQUENCE {
        lcsIPInterfacesIndex                       Integer32,
        lcsIPInterfacesVLAN                        Integer32,
        lcsIPInterfacesIPv4DHCP                    Integer32,
        lcsIPInterfacesIPv4DHCPFallback            DisplayString,
        lcsIPInterfacesIPv4DHCPCurrentLease        IpAddress,
        lcsIPInterfacesIPv4Address                 IpAddress,
        lcsIPInterfacesIPv4Mask                    Integer32,
        lcsIPInterfacesIPv6DHCP                    Integer32,
        lcsIPInterfacesIPv6RapidCommit             Integer32,
        lcsIPInterfacesIPv6CurrentLease            DisplayString,
        lcsIPInterfacesIPv6Address                 DisplayString,
        lcsIPInterfacesIPv6Mask                    Integer32,
        lcsIPInterfacesRowStatus                   RowStatus
    }

lcsIPInterfacesIndex OBJECT-TYPE
   SYNTAX      Integer32 (1..128)
   MAX-ACCESS  not-accessible
   STATUS      current
   DESCRIPTION
       "interface table index"
   ::= {lcsIPInterfacesEntry 1 }

lcsIPInterfacesVLAN OBJECT-TYPE
   SYNTAX      Integer32 (1..4094)
   MAX-ACCESS  read-write
   STATUS      current
   DESCRIPTION
       "VLAN ID for interface, range: 1-4094."
   ::= {lcsIPInterfacesEntry 2 }

lcsIPInterfacesIPv4DHCP OBJECT-TYPE
   SYNTAX      Integer32 (0|1)
   MAX-ACCESS  read-write
   STATUS      current
   DESCRIPTION
       "IPv4 DHCP Setting for interface.
        default:0
        0: disable
        1: enable"
   ::= {lcsIPInterfacesEntry 3 }

lcsIPInterfacesIPv4DHCPFallback OBJECT-TYPE
   SYNTAX      DisplayString
   MAX-ACCESS  read-write
   STATUS      current
   DESCRIPTION
       "IPv4 DHCP fallbcak. range: 1-4294967295 seconds."
   ::= {lcsIPInterfacesEntry 4 }


lcsIPInterfacesIPv4DHCPCurrentLease OBJECT-TYPE
   SYNTAX      IpAddress
   MAX-ACCESS  read-only
   STATUS      current
   DESCRIPTION
       "IPv4 DHCP Current Lease Address for interface."
   ::= {lcsIPInterfacesEntry 5 }


lcsIPInterfacesIPv4Address OBJECT-TYPE
   SYNTAX      IpAddress
   MAX-ACCESS  read-write
   STATUS      current
   DESCRIPTION
       "IPv4 address for interface."
   ::= {lcsIPInterfacesEntry 6 }

lcsIPInterfacesIPv4Mask OBJECT-TYPE
   SYNTAX      Integer32 (0..32)
   MAX-ACCESS  read-write
   STATUS      current
   DESCRIPTION
       "IPv4 mask for interface."
   ::= { lcsIPInterfacesEntry 7 }

lcsIPInterfacesIPv6DHCP OBJECT-TYPE
   SYNTAX      Integer32 (0|1)
   MAX-ACCESS  read-write
   STATUS      current
   DESCRIPTION
       "IPv6 DHCP Setting for interface.
        default:0
        0: disable
        1: enable"
   ::= {lcsIPInterfacesEntry 8 } 
   
lcsIPInterfacesIPv6RapidCommit OBJECT-TYPE
   SYNTAX      Integer32 (0|1)
   MAX-ACCESS  read-write
   STATUS      current
   DESCRIPTION
       "Enable the DHCPv6 Rapid-Commit option.
        default:0
        0: disable
        1: enable"
   ::= {lcsIPInterfacesEntry 9 }    
   
lcsIPInterfacesIPv6CurrentLease OBJECT-TYPE
   SYNTAX      DisplayString
   MAX-ACCESS  read-only
   STATUS      current
   DESCRIPTION
       "IPv6 DHCP Current Lease Address for interface."
   ::= {lcsIPInterfacesEntry 10 }

   
lcsIPInterfacesIPv6Address OBJECT-TYPE
   SYNTAX      DisplayString (SIZE (0..30))
   MAX-ACCESS  read-write
   STATUS      current
   DESCRIPTION
       "IPv6 address for interface."
   ::= { lcsIPInterfacesEntry 11 }

lcsIPInterfacesIPv6Mask OBJECT-TYPE
   SYNTAX      Integer32 (0..128)
   MAX-ACCESS  read-write
   STATUS      current
   DESCRIPTION
       "IPv6 mask for interface."
   ::= { lcsIPInterfacesEntry 12 }

lcsIPInterfacesRowStatus OBJECT-TYPE
   SYNTAX      RowStatus
   MAX-ACCESS  read-create
   STATUS      current
   DESCRIPTION
       "This object indicates the status of this entry, and is used
        to create/delete entries.  Any object in an entry of this
        table may be modified while the value of the corresponding
        instance of this object is active(1).
        createAndGo, notReady not supported."
   ::= { lcsIPInterfacesEntry 13 }
   

lcsIPRoutes OBJECT IDENTIFIER ::= { lcsIP 4 }

lcsIPRoutesTable OBJECT-TYPE
   SYNTAX      SEQUENCE OF LCSIPRoutesEntry
   MAX-ACCESS  not-accessible
   STATUS      current
   DESCRIPTION
       "IP routes table for switch."
    ::= { lcsIPRoutes 1 }

lcsIPRoutesEntry OBJECT-TYPE
    SYNTAX        LCSIPRoutesEntry
    MAX-ACCESS    not-accessible
    STATUS        current
    DESCRIPTION
        "Entry in the lcsIPRoutesTable."
    INDEX        { lcsIPRoutesIndex }
    ::= { lcsIPRoutesTable 1 }

LCSIPRoutesEntry ::=
    SEQUENCE {
        lcsIPRoutesIndex                       Integer32,
        lcsIPRoutesNetwork                     DisplayString,
        lcsIPRoutesMaskLength                  Integer32,
        lcsIPRoutesGateway                     DisplayString,
        lcsIPRoutesNextHopVLAN                 Integer32,
        lcsIPRoutesRowStatus                   RowStatus
    }

lcsIPRoutesIndex OBJECT-TYPE
   SYNTAX      Integer32 (1..32)
   MAX-ACCESS  not-accessible
   STATUS      current
   DESCRIPTION
       "routes table index"
   ::= {lcsIPRoutesEntry 2 }

lcsIPRoutesNetwork OBJECT-TYPE
   SYNTAX      DisplayString (SIZE (0..30))
   MAX-ACCESS  read-write
   STATUS      current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= {lcsIPRoutesEntry 3 }

lcsIPRoutesMaskLength OBJECT-TYPE
   SYNTAX      Integer32 (0..32)
   MAX-ACCESS  read-write
   STATUS      current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { lcsIPRoutesEntry 4 }

lcsIPRoutesGateway OBJECT-TYPE
   SYNTAX      DisplayString (SIZE (0..30))
   MAX-ACCESS  read-write
   STATUS      current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= {lcsIPRoutesEntry 5 }

lcsIPRoutesNextHopVLAN OBJECT-TYPE
   SYNTAX      Integer32 (1..4094)
   MAX-ACCESS  read-write
   STATUS      current
   DESCRIPTION
       "Next Hop VLAN ID, range: 1-4094.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= {lcsIPRoutesEntry 6 }

lcsIPRoutesRowStatus OBJECT-TYPE
   SYNTAX      RowStatus
   MAX-ACCESS  read-create
   STATUS      current
   DESCRIPTION
       "This object indicates the status of this entry, and is used
        to create/delete entries.  Any object in an entry of this
        table may be modified while the value of the corresponding
        instance of this object is active(1).
        createAndGo, notReady not supported."
   ::= { lcsIPRoutesEntry 7 }

lcsIPStatusInterface OBJECT IDENTIFIER ::= { lcsIP 8 }

lcsIPStatusInterfaceTable OBJECT-TYPE
              SYNTAX      SEQUENCE OF     LCSIPStatusInterfaceEntry
              MAX-ACCESS  not-accessible
              STATUS      current
              DESCRIPTION
                       "The system IP Status table to show all IP interfaces."
                   ::= {     lcsIPStatusInterface 1 }

    lcsIPStatusInterfaceEntry OBJECT-TYPE
               SYNTAX          LCSIPStatusInterfaceEntry
               MAX-ACCESS  not-accessible
               STATUS      current
               DESCRIPTION
                       "An entry in the IP Status Table."
               INDEX    {    lcsIPStatusInterfaceIndex  }
               ::= {     lcsIPStatusInterfaceTable 1 }

    LCSIPStatusInterfaceEntry             ::= SEQUENCE {
            lcsIPStatusInterfaceIndex         Integer32,
            lcsIPStatusInterfaceName          DisplayString,
            lcsIPStatusInterfaceType          DisplayString,
            lcsIPStatusInterfaceAddress       DisplayString,
            lcsIPStatusInterfaceStatus        DisplayString
            }

    lcsIPStatusInterfaceIndex OBJECT-TYPE
               SYNTAX      Integer32(1..1024)
               MAX-ACCESS  not-accessible
               STATUS      current
               DESCRIPTION
                   "The entry of table to show all IP interfaces."
               ::= {     lcsIPStatusInterfaceEntry 1 }

    lcsIPStatusInterfaceName OBJECT-TYPE
               SYNTAX      DisplayString
               MAX-ACCESS  read-only
               STATUS      current
               DESCRIPTION
                   "The name of the interface."
               ::= {     lcsIPStatusInterfaceEntry 2 }

    lcsIPStatusInterfaceType OBJECT-TYPE
               SYNTAX      DisplayString
               MAX-ACCESS  read-only
               STATUS      current
               DESCRIPTION
                   "The address type of the entry. This may be LINK or IPv4."
               ::= {     lcsIPStatusInterfaceEntry 3 }

    lcsIPStatusInterfaceAddress OBJECT-TYPE
               SYNTAX      DisplayString
               MAX-ACCESS  read-only
               STATUS      current
               DESCRIPTION
                   "The current address of the interface (of the given type)."
               ::= {     lcsIPStatusInterfaceEntry 4 }

    lcsIPStatusInterfaceStatus OBJECT-TYPE
               SYNTAX      DisplayString
               MAX-ACCESS  read-only
               STATUS      current
               DESCRIPTION
                   "The status flags of the interface (and/or address)."
               ::= {     lcsIPStatusInterfaceEntry 5 }

lcsIPStatusRoute OBJECT IDENTIFIER ::= { lcsIP 9 }

    lcsIPStatusRouteTable OBJECT-TYPE
              SYNTAX      SEQUENCE OF     LCSIPStatusRouteEntry
              MAX-ACCESS  not-accessible
              STATUS      current
              DESCRIPTION
                       "The IP Status Route table show all routing entries."
                   ::= {     lcsIPStatusRoute 1 }

    lcsIPStatusRouteEntry OBJECT-TYPE
               SYNTAX          LCSIPStatusRouteEntry
               MAX-ACCESS  not-accessible
               STATUS      current
               DESCRIPTION
                       "an entry in the IP Status route table."
               INDEX    {     lcsIPStatusRouteIndex  }
               ::= {     lcsIPStatusRouteTable 1 }

    LCSIPStatusRouteEntry             ::= SEQUENCE {
            lcsIPStatusRouteIndex          Integer32,
            lcsIPStatusRouteNetwork        DisplayString,
            lcsIPStatusRouteGateway        DisplayString,
            lcsIPStatusRouteAddress        DisplayString
     }

    lcsIPStatusRouteIndex OBJECT-TYPE
               SYNTAX      Integer32(1..2048)
               MAX-ACCESS  not-accessible
               STATUS      current
               DESCRIPTION
                   "The entry of table to show all routing entries."
               ::= {     lcsIPStatusRouteEntry 1 }

    lcsIPStatusRouteNetwork OBJECT-TYPE
               SYNTAX      DisplayString
               MAX-ACCESS  read-only
               STATUS      current
               DESCRIPTION
                   "The destination IP network or host address of this route."
               ::= {     lcsIPStatusRouteEntry 2 }

    lcsIPStatusRouteGateway OBJECT-TYPE
               SYNTAX      DisplayString
               MAX-ACCESS  read-only
               STATUS      current
               DESCRIPTION
                   "The gateway address of this route."
               ::= {     lcsIPStatusRouteEntry 3 }

    lcsIPStatusRouteAddress OBJECT-TYPE
               SYNTAX      DisplayString
               MAX-ACCESS  read-only
               STATUS      current
               DESCRIPTION
                   "The route address."
               ::= {     lcsIPStatusRouteEntry 4 }

lcsIPStatusNeighborCache OBJECT IDENTIFIER ::= { lcsIP 10 }

    lcsIPStatusNeighborCacheTable OBJECT-TYPE
               SYNTAX      SEQUENCE OF     LCSIPStatusNeighborCacheEntry
               MAX-ACCESS  not-accessible
               STATUS      current
               DESCRIPTION
                       "The Ip Status Neighbor Cache Table."
                   ::= {     lcsIPStatusNeighborCache 1 }

    lcsIPStatusNeighborCacheEntry OBJECT-TYPE
               SYNTAX          LCSIPStatusNeighborCacheEntry
               MAX-ACCESS  not-accessible
               STATUS      current
               DESCRIPTION
                       "An entry in the Ip Status Neighbor Cache Table."
               INDEX    {     lcsIPStatusNeighborCacheIndex  }
               ::= {     lcsIPStatusNeighborCacheTable 1 }

    LCSIPStatusNeighborCacheEntry             ::= SEQUENCE {
            lcsIPStatusNeighborCacheIndex            Integer32,
            lcsIPStatusNeighborCacheIPAddress        DisplayString,
            lcsIPStatusNeighborCacheLinkAddress      DisplayString
            }

    lcsIPStatusNeighborCacheIndex OBJECT-TYPE
               SYNTAX      Integer32(1..1024)
               MAX-ACCESS  not-accessible
               STATUS      current
               DESCRIPTION
                   "The index for the Ip Status Neighbor Cache Table."
               ::= {     lcsIPStatusNeighborCacheEntry 1 }

    lcsIPStatusNeighborCacheIPAddress OBJECT-TYPE
               SYNTAX      DisplayString
               MAX-ACCESS  read-only
               STATUS      current
               DESCRIPTION
                   "The IP address of the entry."
               ::= {     lcsIPStatusNeighborCacheEntry 2 }

    lcsIPStatusNeighborCacheLinkAddress OBJECT-TYPE
               SYNTAX      DisplayString
               MAX-ACCESS  read-only
               STATUS      current
               DESCRIPTION
                   "The Link (MAC) address for which a binding to the
                    IP address given exist."
               ::= {     lcsIPStatusNeighborCacheEntry 3 }

lcsIPStatusDNSServer OBJECT IDENTIFIER ::= { lcsIP 11 }

    lcsIPStatusDNSServerType OBJECT-TYPE
               SYNTAX      DisplayString
               MAX-ACCESS  read-only
               STATUS      current
               DESCRIPTION
                   "The configuration type of DNS server."
               ::= {     lcsIPStatusDNSServer 1 }

    lcsIPStatusDNSServerIPAddress OBJECT-TYPE
               SYNTAX      DisplayString
               MAX-ACCESS  read-only
               STATUS      current
               DESCRIPTION
                   "The IP address of the DNS server."
               ::= {     lcsIPStatusDNSServer 2 }

    lcsIPStatusDNSServerInterface OBJECT-TYPE
               SYNTAX      DisplayString
               MAX-ACCESS  read-only
               STATUS      current
               DESCRIPTION
                   "The name of the interface."
               ::= {     lcsIPStatusDNSServer 3 }              
               
-- =======================================================================================================================
lcsSyslog                                                OBJECT IDENTIFIER ::= { lcsSystem 5 }

lcsSyslogConf                                            OBJECT IDENTIFIER ::= { lcsSyslog 1 }

lcsSysLogInfo                                            OBJECT IDENTIFIER   ::= {  lcsSyslog 2 }
--
-- =======================================================================================================================
-- Objects in the lcsSystemLog Group
-- =======================================================================================================================
--lcsSystemLogConf

    lcsSystemLogServerMode OBJECT-TYPE
               SYNTAX      AdminMode
               MAX-ACCESS  read-write
               STATUS      current
               DESCRIPTION
                   "The System log server mode admin state."
               DEFVAL  { disable }
               ::= {     lcsSyslogConf 1 }

    lcsSystemLogServerAddress OBJECT-TYPE
               SYNTAX      DisplayString
               MAX-ACCESS  read-write
               STATUS      current
               DESCRIPTION
                   "The Host address of syslog server."
               ::= {     lcsSyslogConf 2 }

--    lcsSystemLogSyslogLevel OBJECT-TYPE
--               SYNTAX      INTEGER {
--                    info(0),
--                    warning(1),
--                    error(2)
--               }
--               MAX-ACCESS  read-write
--               STATUS      current
--               DESCRIPTION
--                   "The syslog level.
--                       info(0)   : Info.
--                       warning(1): Warning.
--                       error(2)  : Error."
--               DEFVAL  { info }
--               ::= {     lcsSyslogConf 3 }

    lcsSystemLogServerPort OBJECT-TYPE
                 SYNTAX      Integer32(1..65535)
                 MAX-ACCESS  read-write
                 STATUS      current
                 DESCRIPTION
                      "syslog service port number.
                 range : 1-65535, default : 514."
               ::= {     lcsSyslogConf 4 }

     lcsSystemLogIncludeHostname OBJECT-TYPE
                 SYNTAX      INTEGER { disable(0), enable(1) }
                 MAX-ACCESS  read-write
                 STATUS      current
                 DESCRIPTION
                 "default: 0
                 0: disable
                 1: enable "
                 ::= { lcsSyslogConf 150 }

--lcsSystemLogInfo
    lcsSystemLogInfoLevel OBJECT-TYPE
               SYNTAX      INTEGER { emergency(0), alert(1), critical(2), error(3), warning(4), notice(5), information(6), debug(7), all(8) }
               MAX-ACCESS  read-write
               STATUS      current
               DESCRIPTION
                  "The Level input field is used to filter the display system log entries.
                   0: Emergency.
                   1: Alert.
                   2: Critical.
                   3: Error.
                   4: Warning.
                   5: Notice.
                   6: Information.
                   7: Debug.
                   8: All."
               DEFVAL  { all }
               ::= {     lcsSysLogInfo 1 }

    lcsSystemLogInfoClearLevel OBJECT-TYPE
               SYNTAX      INTEGER { emergency(0), alert(1), critical(2), error(3), warning(4), notice(5), information(6), debug(7), all(8) }
               MAX-ACCESS  read-write
               STATUS      current
               DESCRIPTION
                  "The Clear Level input field is used to specify which
                  system log entries will be cleared.
                  default: 8 (All).
                   0: Emergency.
                   1: Alert.
                   2: Critical.
                   3: Error.
                   4: Warning.
                   5: Notice.
                   6: Information.
                   7: Debug.
                   8: All."
               DEFVAL  { all }
               ::= {     lcsSysLogInfo 2 }

    lcsSystemLogInfoClearCmd OBJECT-TYPE
               SYNTAX      ActivateCmd
               MAX-ACCESS  read-write
               STATUS      current
               DESCRIPTION
                  "Command to clear the syslog.
                   noAction(0) : do nothing  (read only).
                   activate(1) : Clear Syslog."
               DEFVAL  { noAction }
               ::= {     lcsSysLogInfo 3 }

    lcsSystemLogDetailedInfoTable OBJECT-TYPE
              SYNTAX      SEQUENCE OF     LCSSystemLogDetailedInfoEntry
              MAX-ACCESS  not-accessible
              STATUS      current
              DESCRIPTION
                       "The system detailed Log Info table."
                   ::= {     lcsSysLogInfo 4 }

    lcsSystemLogDetailedInfoEntry OBJECT-TYPE
               SYNTAX          LCSSystemLogDetailedInfoEntry
               MAX-ACCESS  not-accessible
               STATUS      current
               DESCRIPTION
                       "An entry in the system detailed Log Info table."
               INDEX    {     lcsSystemLogDetailedInfoID  }
               ::= {     lcsSystemLogDetailedInfoTable 1 }

    LCSSystemLogDetailedInfoEntry             ::= SEQUENCE {
                lcsSystemLogDetailedSwitchIndex       Integer32,
                lcsSystemLogDetailedInfoID            Integer32,
                lcsSystemLogDetailedInfoLevel         DisplayString,
                lcsSystemLogDetailedInfoTime          DisplayString,
                lcsSystemLogDetailedInfoMessage       DisplayString
                }

    lcsSystemLogDetailedSwitchIndex OBJECT-TYPE
               SYNTAX      Integer32(1..16)
               MAX-ACCESS  not-accessible
               STATUS      current
               DESCRIPTION
                   "The switch index for the system detailed Log Info table."
               ::= {     lcsSystemLogDetailedInfoEntry 1 }

    lcsSystemLogDetailedInfoID OBJECT-TYPE
               SYNTAX      Integer32(1..999)
               MAX-ACCESS  not-accessible
               STATUS      current
               DESCRIPTION
                   "The index for the system detailed Log Info table."
               ::= {     lcsSystemLogDetailedInfoEntry 2 }

    lcsSystemLogDetailedInfoLevel OBJECT-TYPE
               SYNTAX      DisplayString
               MAX-ACCESS  read-only
               STATUS      current
               DESCRIPTION
                   "The Info Level."
               ::= {     lcsSystemLogDetailedInfoEntry 3 }

    lcsSystemLogDetailedInfoTime OBJECT-TYPE
               SYNTAX      DisplayString(SIZE (0..20))
               MAX-ACCESS  read-only
               STATUS      current
               DESCRIPTION
                   "The time"
               ::= {     lcsSystemLogDetailedInfoEntry 4 }

    lcsSystemLogDetailedInfoMessage OBJECT-TYPE
               SYNTAX      DisplayString
               MAX-ACCESS  read-only
               STATUS      current
               DESCRIPTION
                   "The message of this entry."
               ::= {     lcsSystemLogDetailedInfoEntry 5 }
-- =======================================================================================================================
lcsSnmp                                                OBJECT IDENTIFIER ::= { lcsSystem 6 }

lcsSnmpSystem                                            OBJECT IDENTIFIER ::= { lcsSnmp 1 }

lcsSnmpSystemMode OBJECT-TYPE
   SYNTAX       Integer32
   MAX-ACCESS   read-write
   STATUS       current
   DESCRIPTION
       "SNMP mode operation.
        default : 1, 0: disable, 1: enable. "
   ::= { lcsSnmpSystem 1 }

--lcsSnmpSystemVersion OBJECT-TYPE
--   SYNTAX       Integer32
--   MAX-ACCESS   read-write
--   STATUS       current
--   DESCRIPTION
--       "SNMP supported version.
--       default : snmpv2c.
--       0: snmpv1
--       1: snmpv2c
--       3: snmpv3."
--   ::= { lcsSnmpSystem 2 }

lcsSnmpSystemReadCommunity OBJECT-TYPE
   SYNTAX       DisplayString
   MAX-ACCESS   read-write
   STATUS       current
   DESCRIPTION
       "Indicates the community read access string to permit access to SNMP agent.
       The allowed string length is 0 to 255.
       The field is applicable only when SNMP version is SNMPv1 or SNMPv2c."
   ::= { lcsSnmpSystem 3 }

lcsSnmpSystemWriteCommunity OBJECT-TYPE
   SYNTAX       DisplayString
   MAX-ACCESS   read-write
   STATUS       current
   DESCRIPTION
       "Indicates the community write access string to permit access to SNMP agent.
       The allowed string length is 0 to 255.
       The field is applicable only when SNMP version is SNMPv1 or SNMPv2c."
   ::= { lcsSnmpSystem 4 }

--lcsSnmpSystemEngineID OBJECT-TYPE
--   SYNTAX       DisplayString
--   MAX-ACCESS   read-write
--   STATUS       current
--   DESCRIPTION
--       "Indicates the SNMPv3 engine ID.
--        The string must contain an even number(in hexadecimal format) with number of digits between 10 and 64,
--  but all-zeros and all-'F's are not allowed.
--  Allow string length is 10 to 32.
--  Change of the Engine ID will clear all original local users."
--   ::= { lcsSnmpSystem 5 }

lcsSnmpSystemWriteCommunityMode OBJECT-TYPE
   SYNTAX       Integer32
   MAX-ACCESS   read-write
   STATUS       current
   DESCRIPTION
       "SNMP write community mode operation.
        default : 1, 0: disable, 1: enable. "
   ::= { lcsSnmpSystem 6 }

lcsSnmpSystemReadCommunityMode OBJECT-TYPE
   SYNTAX       Integer32
   MAX-ACCESS   read-write
   STATUS       current
   DESCRIPTION
       "SNMP read community mode operation.
        default : 1, 0: disable, 1: enable. "
   ::= { lcsSnmpSystem 7 }


--lcsSnmpTrapGlobalMode OBJECT-TYPE
--   SYNTAX       Integer32
--   MAX-ACCESS   read-write
--   STATUS       current
--   DESCRIPTION
--       "Indicates the trap mode operation.
--        0:Disable.
--  1:Enable."
--   ::= { lcsSnmp 2 }

lcsTrapDestinationConfTable OBJECT-TYPE
   SYNTAX      SEQUENCE OF LCSTrapDestinationConfEntry
   MAX-ACCESS  not-accessible
   STATUS      current
   DESCRIPTION
       "A list of trap host entry. The numbers of entries are given by the value of TrapHostConfNumber."
   ::= { lcsSnmp 3 }

lcsTrapDestinationConfEntry OBJECT-TYPE
   SYNTAX      LCSTrapDestinationConfEntry
   MAX-ACCESS  not-accessible
   STATUS      current
   DESCRIPTION
       "This is the entry information for trap host."
   INDEX    { lcsTrapDestinationConfIndex  }
   ::= { lcsTrapDestinationConfTable 1 }

LCSTrapDestinationConfEntry ::= SEQUENCE {
    lcsTrapDestinationConfIndex                      Integer32,
    lcsTrapDestinationConfTrapConfigName             DisplayString,
    lcsTrapDestinationConfTrapMode                   Integer32,
    lcsTrapDestinationConfTrapVersion                Integer32,
    lcsTrapDestinationConfTrapCommunity              DisplayString,
    lcsTrapDestinationConfTrapDestinationAddres      DisplayString,
    lcsTrapDestinationConfTrapDestinationPort        Integer32,
--  lcsTrapDestinationConfTrapInformMode             Integer32,
--  lcsTrapDestinationConfTrapInformTimeout          Integer32,
--  lcsTrapDestinationConfTrapInformRetryTimes       Integer32,
--  lcsTrapDestinationConfTrapProbeSecurityEngineID  Integer32,
    lcsTrapDestinationConfTrapSecurityEngineID       DisplayString,
    lcsTrapDestinationConfTrapSecurityName           DisplayString,
    lcsTrapDestinationConfTrapRowStatus              Integer32
}

lcsTrapDestinationConfIndex OBJECT-TYPE
   SYNTAX       Integer32 (1..65535)
   MAX-ACCESS   not-accessible
   STATUS       current
   DESCRIPTION
       "Index of tarp destination configurations."
   ::= { lcsTrapDestinationConfEntry 1 }

lcsTrapDestinationConfTrapConfigName OBJECT-TYPE
   SYNTAX       DisplayString
   MAX-ACCESS   read-write
   STATUS       current
   DESCRIPTION
       "Indicates which trap Configuration's name for configuring.
       The allowed string length is 0 to 255, and the allowed content is
       ASCII characters from 33 to 126."
   ::= { lcsTrapDestinationConfEntry 2 }

lcsTrapDestinationConfTrapMode OBJECT-TYPE
   SYNTAX       Integer32
   MAX-ACCESS   read-write
   STATUS       current
   DESCRIPTION
       "Indicates the SNMP mode operation. Possible modes are:
        2: Enable TCP SNMP mode operation.
        1: Enable UDP SNMP mode operation.
        0: Disable SNMP mode operation. "
   ::= { lcsTrapDestinationConfEntry 3 }

lcsTrapDestinationConfTrapVersion OBJECT-TYPE
   SYNTAX       Integer32
   MAX-ACCESS   read-write
   STATUS       current
   DESCRIPTION
       "0: snmpv1
        1: snmpv2c
        3: snmpv3.
        "
   ::= { lcsTrapDestinationConfEntry 4 }

lcsTrapDestinationConfTrapCommunity OBJECT-TYPE
   SYNTAX       DisplayString
   MAX-ACCESS   read-write
   STATUS       current
   DESCRIPTION
       "Indicates the community access string when sending SNMP trap packet.
       The allowed string length is 0 to 255, and the allowed content is
       ASCII characters from 33 to 126."
   ::= { lcsTrapDestinationConfEntry 5 }

lcsTrapDestinationConfTrapDestinationAddres OBJECT-TYPE
   SYNTAX       DisplayString
   MAX-ACCESS   read-write
   STATUS       current
   DESCRIPTION
       "Indicates the SNMP trap destination address.
       It allow a valid IP address in dotted decimal notation ('x.y.z.w').
    And it also allow a valid hostname.
    A valid hostname is a string drawn from the alphabet (A-Za-z), digits (0-9),
    dot (.), dash (-). Spaces are not allowed, the first character must be an alpha character,
    and the first and last characters must not be a dot or a dash.
    Indicates the SNMP trap destination IPv6 address.
    IPv6 address is in 128-bit records represented as eight fields of up to four hexadecimal digits
    with a colon separating each field (:).
    For example, 'fe80::215:c5ff:fe03:4dc7'. The symbol '::' is a special syntax
    that can be used as a shorthand way of representing multiple 16-bit groups of contiguous zeros;
    but it can appear only once.
    It can also represent a legally valid IPv4 address.
    For example, '::192.1.2.34'."
   ::= { lcsTrapDestinationConfEntry 6 }

lcsTrapDestinationConfTrapDestinationPort OBJECT-TYPE
   SYNTAX       Integer32
   MAX-ACCESS   read-write
   STATUS       current
   DESCRIPTION
       "Indicates the SNMP trap destination port.
       SNMP Agent will send SNMP message via this port,
       the port range is 1~65535."
   ::= { lcsTrapDestinationConfEntry 7 }

--lcsTrapDestinationConfTrapInformMode OBJECT-TYPE
--   SYNTAX       Integer32
--   MAX-ACCESS   read-write
--   STATUS       current
--   DESCRIPTION
--       "Indicates the SNMP trap inform mode operation. Possible modes are:
--        1: Enable SNMP trap inform mode operation.
--        0: Disable SNMP trap inform mode operation. "
--   ::= { lcsTrapDestinationConfEntry 8 }
--
--lcsTrapDestinationConfTrapInformTimeout OBJECT-TYPE
--   SYNTAX       Integer32
--   MAX-ACCESS   read-write
--   STATUS       current
--   DESCRIPTION
--       "Indicates the SNMP trap inform timeout. The allowed range is 0 to 2147."
--   ::= { lcsTrapDestinationConfEntry 9 }
--
--lcsTrapDestinationConfTrapInformRetryTimes OBJECT-TYPE
--   SYNTAX       Integer32
--   MAX-ACCESS   read-write
--   STATUS       current
--   DESCRIPTION
--       "Indicates the SNMP trap inform retry times. The allowed range is 0 to 255."
--   ::= { lcsTrapDestinationConfEntry 10 }
--
--lcsTrapDestinationConfTrapProbeSecurityEngineID OBJECT-TYPE
--   SYNTAX       Integer32
--   MAX-ACCESS   read-write
--   STATUS       current
--   DESCRIPTION
--       "Indicates the SNMP trap probe security engine ID mode of operation.
--       Possible values are:
--       1: Enable SNMP trap probe security engine ID mode of operation.
--       0: Disable SNMP trap probe security engine ID mode of operation."
--   ::= { lcsTrapDestinationConfEntry 11 }

lcsTrapDestinationConfTrapSecurityEngineID OBJECT-TYPE
   SYNTAX       DisplayString
   MAX-ACCESS   read-write
   STATUS       current
   DESCRIPTION
       "Indicates the SNMP trap security engine ID.
       SNMPv3 sends traps and informs using USM for authentication and privacy.
       A unique engine ID for these traps and informs is needed.
       When Trap Probe Security Engine ID is enabled, the ID will be probed automatically.
       Otherwise, the ID specified in this field is used.
       The string must contain an even number(in hexadecimal format) with
       number of digits between 10 and 64, but all-zeros and all-'F's are not allowed."
   ::= { lcsTrapDestinationConfEntry 12 }

lcsTrapDestinationConfTrapSecurityName OBJECT-TYPE
   SYNTAX       DisplayString
   MAX-ACCESS   read-write
   STATUS       current
   DESCRIPTION
       "Indicates the SNMP trap security name.
       SNMPv3 traps and informs using USM for authentication and privacy.
       A unique security name is needed when traps and informs are enabled.
       This name from user name of user configuration."
   ::= { lcsTrapDestinationConfEntry 13 }

lcsTrapDestinationConfTrapRowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { lcsTrapDestinationConfEntry 14 }


lcsSNMPCommunityConfTable OBJECT-TYPE
   SYNTAX      SEQUENCE OF LCSSNMPCommunityConfEntry
   MAX-ACCESS  not-accessible
   STATUS      current
   DESCRIPTION
       "A list of snmp community configuration entry."
   ::= { lcsSnmp 5 }

lcsSNMPCommunityConfEntry OBJECT-TYPE
   SYNTAX      LCSSNMPCommunityConfEntry
   MAX-ACCESS  not-accessible
   STATUS      current
   DESCRIPTION
       "This is the entry information for snmp community configuration."
   INDEX    { lcsSNMPCommunityConfIndex  }
   ::= { lcsSNMPCommunityConfTable 1 }

LCSSNMPCommunityConfEntry ::= SEQUENCE {
    lcsSNMPCommunityConfIndex                       Integer32,
    lcsSNMPCommunityConfSNMPv3Community             DisplayString,
    lcsSNMPCommunityConfSNMPv3SourceIP              IpAddress,
    lcsSNMPCommunityConfSNMPv3SourceMask            IpAddress,
    lcsSNMPCommunityConfSNMPv3RowStatus             Integer32
}

lcsSNMPCommunityConfIndex OBJECT-TYPE
   SYNTAX       Integer32 (1..65535)
   MAX-ACCESS   read-write
   STATUS       current
   DESCRIPTION
       "Community configuration index."
   ::= { lcsSNMPCommunityConfEntry 1 }

lcsSNMPCommunityConfSNMPv3Community OBJECT-TYPE
   SYNTAX       DisplayString
   MAX-ACCESS   read-write
   STATUS       current
   DESCRIPTION
       "Indicates the community access string to permit access to SNMPv3 agent.
       The allowed string length is 1 to 32, and the allowed content is
       ASCII characters from 33 to 126.
       The community string will be treated as security name and map a SNMPv1
       or SNMPv2c community string."
   ::= { lcsSNMPCommunityConfEntry 2 }


lcsSNMPCommunityConfSNMPv3SourceIP OBJECT-TYPE
   SYNTAX      IpAddress
   MAX-ACCESS  read-write
   STATUS      current
   DESCRIPTION
       "Indicates the SNMP access source address.
       A particular range of source addresses can be used to restrict source subnet
       when combined with source mask."
   ::= {lcsSNMPCommunityConfEntry 3 }

lcsSNMPCommunityConfSNMPv3SourceMask OBJECT-TYPE
   SYNTAX      IpAddress
   MAX-ACCESS  read-write
   STATUS      current
   DESCRIPTION
       "Indicates the SNMP access source address mask."
   ::= {lcsSNMPCommunityConfEntry 4 }

lcsSNMPCommunityConfSNMPv3RowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { lcsSNMPCommunityConfEntry 5 }

lcsSNMPv3UserConfTable OBJECT-TYPE
   SYNTAX      SEQUENCE OF LCSSNMPv3UserConfEntry
   MAX-ACCESS  not-accessible
   STATUS      current
   DESCRIPTION
       "A list of snmpv3 user configuration entry."
   ::= { lcsSnmp 6 }

lcsSNMPv3UserConfEntry OBJECT-TYPE
   SYNTAX      LCSSNMPv3UserConfEntry
   MAX-ACCESS  not-accessible
   STATUS      current
   DESCRIPTION
       "This is the entry information for snmpv3 user configuration."
   INDEX    { lcsSNMPv3UserConfIndex  }
   ::= { lcsSNMPv3UserConfTable 1 }

LCSSNMPv3UserConfEntry ::= SEQUENCE {
    lcsSNMPv3UserConfIndex                     Integer32,
    lcsSNMPv3UserConfEngineID                  DisplayString,
    lcsSNMPv3UserConfUserName                  DisplayString,
    lcsSNMPv3UserConfSecurityLevel             SNMPv3SecurityLevel,
    lcsSNMPv3UserConfAuthenticationProtocol    SNMPv3AuthenticationProtocol,
    lcsSNMPv3UserConfAuthenticationPassword    DisplayString,
    lcsSNMPv3UserConfPrivacyProtocol           SNMPv3PrivacyProtocol,
    lcsSNMPv3UserConfPrivacyPassword           DisplayString,
    lcsSNMPv3UserConfRowStatus                 RowStatus
}

lcsSNMPv3UserConfIndex OBJECT-TYPE
   SYNTAX       Integer32 (1..65535)
   MAX-ACCESS   not-accessible
   STATUS       current
   DESCRIPTION
       "User configuration index."
   ::= { lcsSNMPv3UserConfEntry 1 }

lcsSNMPv3UserConfEngineID OBJECT-TYPE
   SYNTAX       DisplayString
   MAX-ACCESS   read-write
   STATUS       current
   DESCRIPTION
       "An octet string identifying the engine ID that this entry should belong to.
       The string must contain an even number(in hexadecimal format) with
       number of digits between 10 and 64, but all-zeros and all-'F's are not allowed.
       The SNMPv3 architecture uses the User-based Security Model (USM)
       for message security and the View-based Access Control Model (VACM) for access control.
       For the USM entry, the usmUserEngineID and usmUserName are the entry's keys.
       In a simple agent, usmUserEngineID is always that agent's own snmpEngineID value.
       The value can also take the value of the snmpEngineID of a remote SNMP engine with
       which this user can communicate. In other words, if user engine ID equal system engine ID
       then it is local user; otherwise it's remote user. "
   ::= { lcsSNMPv3UserConfEntry 2 }

lcsSNMPv3UserConfUserName OBJECT-TYPE
   SYNTAX       DisplayString
   MAX-ACCESS   read-write
   STATUS       current
   DESCRIPTION
       "A string identifying the user name that this entry should belong to.
       The allowed string length is 1 to 32, and the allowed contents are
       ASCII characters from 33 to 126."
   ::= { lcsSNMPv3UserConfEntry 3 }

lcsSNMPv3UserConfSecurityLevel OBJECT-TYPE
   SYNTAX       SNMPv3SecurityLevel
   MAX-ACCESS   read-write
   STATUS       current
   DESCRIPTION
       "SNMPv3 USM security level."
   ::= { lcsSNMPv3UserConfEntry 4 }

lcsSNMPv3UserConfAuthenticationProtocol OBJECT-TYPE
   SYNTAX       SNMPv3AuthenticationProtocol
   MAX-ACCESS   read-write
   STATUS       current
   DESCRIPTION
       "SNMPv3 USM authentication protocol."
   ::= { lcsSNMPv3UserConfEntry 5 }

lcsSNMPv3UserConfAuthenticationPassword OBJECT-TYPE
   SYNTAX       DisplayString
   MAX-ACCESS   read-write
   STATUS       current
   DESCRIPTION
       "A string identifying the authentication password phrase.
       The allowed string length is 8 to 128, and the allowed contents are
       ASCII characters from 33 to 126.
       Does only read '*****' instead of the password or localized key."
   ::= { lcsSNMPv3UserConfEntry 6 }

lcsSNMPv3UserConfPrivacyProtocol OBJECT-TYPE
   SYNTAX       SNMPv3PrivacyProtocol
   MAX-ACCESS   read-write
   STATUS       current
   DESCRIPTION
       "SNMPv3 USM privacy protocol."
   ::= { lcsSNMPv3UserConfEntry 7 }

lcsSNMPv3UserConfPrivacyPassword OBJECT-TYPE
   SYNTAX       DisplayString
   MAX-ACCESS   read-write
   STATUS       current
   DESCRIPTION
       "A string identifying the privacy password phrase.
       The allowed string length is 8 to 128, and the allowed contents are
       ASCII characters from 33 to 126.
       Does only read '*****' instead of the password or localized key."
   ::= { lcsSNMPv3UserConfEntry 8 }

lcsSNMPv3UserConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { lcsSNMPv3UserConfEntry 9 }

lcsSNMPv3GroupConfTable OBJECT-TYPE
   SYNTAX      SEQUENCE OF LCSSNMPv3GroupConfEntry
   MAX-ACCESS  not-accessible
   STATUS      current
   DESCRIPTION
       "A list of snmpv3 group configuration entry."
   ::= { lcsSnmp 7 }

lcsSNMPv3GroupConfEntry OBJECT-TYPE
   SYNTAX      LCSSNMPv3GroupConfEntry
   MAX-ACCESS  not-accessible
   STATUS      current
   DESCRIPTION
       "This is the entry information for snmpv3 group configuration."
   INDEX    { lcsSNMPv3GroupConfIndex  }
   ::= { lcsSNMPv3GroupConfTable 1 }

LCSSNMPv3GroupConfEntry ::= SEQUENCE {
    lcsSNMPv3GroupConfIndex                     Integer32,
    lcsSNMPv3GroupConfSecurityModel             Integer32,
    lcsSNMPv3GroupConfSecurityName          DisplayString,
    lcsSNMPv3GroupConfGroupName             DisplayString,
    lcsSNMPv3GroupConfRowStatus                 RowStatus
}

lcsSNMPv3GroupConfIndex OBJECT-TYPE
   SYNTAX       Integer32 (1..65535)
   MAX-ACCESS   read-write
   STATUS       current
   DESCRIPTION
       "Group configuration index."
   ::= { lcsSNMPv3GroupConfEntry 1 }

lcsSNMPv3GroupConfSecurityModel OBJECT-TYPE
   SYNTAX       Integer32
   MAX-ACCESS   read-write
   STATUS       current
   DESCRIPTION
       "1:v1
        2:v2c
        3:usm"
   ::= { lcsSNMPv3GroupConfEntry 2 }

lcsSNMPv3GroupConfSecurityName OBJECT-TYPE
   SYNTAX       DisplayString
   MAX-ACCESS   read-write
   STATUS       current
   DESCRIPTION
       "A string identifying the security name that this entry should belong to.
       The allowed string length is 1 to 32, and the allowed content is
       ASCII characters from 33 to 126.
       This name is from the Community of Community configuration."
   ::= { lcsSNMPv3GroupConfEntry 3 }

lcsSNMPv3GroupConfGroupName OBJECT-TYPE
   SYNTAX       DisplayString
   MAX-ACCESS   read-write
   STATUS       current
   DESCRIPTION
       "A string identifying the group name that this entry should belong to.
       The allowed string length is 1 to 32, and the allowed content is
       ASCII characters from 33 to 126. "
   ::= { lcsSNMPv3GroupConfEntry 4 }


lcsSNMPv3GroupConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { lcsSNMPv3GroupConfEntry 5 }

lcsSNMPv3ViewsConfTable OBJECT-TYPE
   SYNTAX      SEQUENCE OF LCSSNMPv3ViewsConfEntry
   MAX-ACCESS  not-accessible
   STATUS      current
   DESCRIPTION
       "A list of snmpv3 view configuration entry."
   ::= { lcsSnmp 8 }

lcsSNMPv3ViewsConfEntry OBJECT-TYPE
   SYNTAX      LCSSNMPv3ViewsConfEntry
   MAX-ACCESS  not-accessible
   STATUS      current
   DESCRIPTION
       "This is the entry information for snmpv3 view configuration."
   INDEX    { lcsSNMPv3ViewsConfIndex  }
   ::= { lcsSNMPv3ViewsConfTable 1 }

LCSSNMPv3ViewsConfEntry ::= SEQUENCE {
    lcsSNMPv3ViewsConfIndex                   Integer32,
    lcsSNMPv3ViewsConfViewName            DisplayString,
    lcsSNMPv3ViewsConfViewType                Integer32,
    lcsSNMPv3ViewsConfOIDSubtree          DisplayString,
    lcsSNMPv3ViewsConfRowStatus               RowStatus
}

lcsSNMPv3ViewsConfIndex OBJECT-TYPE
   SYNTAX       Integer32 (1..65535)
   MAX-ACCESS   read-write
   STATUS       current
   DESCRIPTION
       "view configuration index."
   ::= { lcsSNMPv3ViewsConfEntry 1 }

lcsSNMPv3ViewsConfViewName OBJECT-TYPE
   SYNTAX       DisplayString
   MAX-ACCESS   read-write
   STATUS       current
   DESCRIPTION
       "A string identifying the view name that this entry should belong to.
       The allowed string length is 1 to 32, and the allowed content is
       ASCII characters from 33 to 126. "
   ::= { lcsSNMPv3ViewsConfEntry 2 }

lcsSNMPv3ViewsConfViewType OBJECT-TYPE
   SYNTAX       Integer32
   MAX-ACCESS   read-write
   STATUS       current
   DESCRIPTION
       "0:included
       1:excluded"
   ::= { lcsSNMPv3ViewsConfEntry 3 }

lcsSNMPv3ViewsConfOIDSubtree OBJECT-TYPE
   SYNTAX       DisplayString
   MAX-ACCESS   read-write
   STATUS       current
   DESCRIPTION
       "The OID defining the root of the subtree to add to the named view.
       The allowed OID length is 1 to 128. The allowed string content is
       digital number or asterisk(*)"
   ::= { lcsSNMPv3ViewsConfEntry 4 }

lcsSNMPv3ViewsConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { lcsSNMPv3ViewsConfEntry 5 }


lcsSNMPv3AccessConfTable OBJECT-TYPE
   SYNTAX      SEQUENCE OF LCSSNMPv3AccessConfEntry
   MAX-ACCESS  not-accessible
   STATUS      current
   DESCRIPTION
       "A list of snmpv3 access configuration entry."
   ::= { lcsSnmp 9 }

lcsSNMPv3AccessConfEntry OBJECT-TYPE
   SYNTAX      LCSSNMPv3AccessConfEntry
   MAX-ACCESS  not-accessible
   STATUS      current
   DESCRIPTION
       "This is the entry information for snmpv3 access configuration."
   INDEX    { lcsSNMPv3AccessConfIndex  }
   ::= { lcsSNMPv3AccessConfTable 1 }

LCSSNMPv3AccessConfEntry ::= SEQUENCE {
    lcsSNMPv3AccessConfIndex                    Integer32,
    lcsSNMPv3AccessConfGroupName            DisplayString,
    lcsSNMPv3AccessConfSecurityModel            Integer32,
    lcsSNMPv3AccessConfSecurityLevel        SNMPv3SecurityLevel,
    lcsSNMPv3AccessConfReadViewName         DisplayString,
    lcsSNMPv3AccessConfWriteViewName        DisplayString,
    lcsSNMPv3AccessConfRowStatus                RowStatus
}

lcsSNMPv3AccessConfIndex OBJECT-TYPE
   SYNTAX       Integer32 (1..65535)
   MAX-ACCESS   read-write
   STATUS       current
   DESCRIPTION
       "Access configuration index"
   ::= { lcsSNMPv3AccessConfEntry 1 }

lcsSNMPv3AccessConfGroupName OBJECT-TYPE
   SYNTAX       DisplayString
   MAX-ACCESS   read-write
   STATUS       current
   DESCRIPTION
       "Group name from Group configuration."
   ::= { lcsSNMPv3AccessConfEntry 2 }

lcsSNMPv3AccessConfSecurityModel OBJECT-TYPE
   SYNTAX       Integer32
   MAX-ACCESS   read-write
   STATUS       current
   DESCRIPTION
       "0:any
        1:v1
        2:v2c
        3:usm"
   ::= { lcsSNMPv3AccessConfEntry 3 }

lcsSNMPv3AccessConfSecurityLevel OBJECT-TYPE
   SYNTAX       SNMPv3SecurityLevel
   MAX-ACCESS   read-write
   STATUS       current
   DESCRIPTION
       "SNMPv3 USM security level."
   ::= { lcsSNMPv3AccessConfEntry 4 }

lcsSNMPv3AccessConfReadViewName OBJECT-TYPE
   SYNTAX       DisplayString
   MAX-ACCESS   read-write
   STATUS       current
   DESCRIPTION
       "Read View Name from View configuration."
   ::= { lcsSNMPv3AccessConfEntry 5 }

lcsSNMPv3AccessConfWriteViewName OBJECT-TYPE
   SYNTAX       DisplayString
   MAX-ACCESS   read-write
   STATUS       current
   DESCRIPTION
       "Write View Name from View configuration."
   ::= { lcsSNMPv3AccessConfEntry 6 }

lcsSNMPv3AccessConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { lcsSNMPv3AccessConfEntry 7 }

-- =======================================================================================================================
lcsDHCPServer                                     OBJECT IDENTIFIER ::= { lcsSystem 9 }

lcsDHCPServerConfig                              OBJECT IDENTIFIER ::= { lcsDHCPServer 7 }

lcsDHCPServerConfigTable OBJECT-TYPE
   SYNTAX      SEQUENCE OF LCSDHCPServerConfigEntry
   MAX-ACCESS  not-accessible
   STATUS      current
   DESCRIPTION
       " "
    ::= { lcsDHCPServerConfig 1 }

lcsDHCPServerConfigEntry OBJECT-TYPE
    SYNTAX        LCSDHCPServerConfigEntry
    MAX-ACCESS    not-accessible
    STATUS        current
    DESCRIPTION
        " "
    INDEX        { lcsDHCPServerConfigIndex }
    ::= { lcsDHCPServerConfigTable 1 }


LCSDHCPServerConfigEntry ::=
    SEQUENCE {
        lcsDHCPServerConfigIndex                    Integer32,
        lcsDHCPServerConfigInterfaceVLAN            Integer32,
        lcsDHCPServerConfigInterfaceMode            Integer32,
        lcsDHCPServerConfigInterfaceStartIPEndIP    DisplayString,
--      lcsDHCPServerConfigInterfaceEndIP           IpAddress,
        lcsDHCPServerConfigInterfaceLeaseTime       Integer32,
        lcsDHCPServerConfigInterfaceSubnetMask      IpAddress,
        lcsDHCPServerConfigInterfaceDefaultRouter   IpAddress,
        lcsDHCPServerConfigInterfaceDNSServer       IpAddress        
    }

lcsDHCPServerConfigIndex OBJECT-TYPE
   SYNTAX      Integer32 (1..4094)
   MAX-ACCESS  not-accessible
   STATUS      current
   DESCRIPTION
       "table index."
   ::= {lcsDHCPServerConfigEntry 1 }
    
lcsDHCPServerConfigInterfaceVLAN OBJECT-TYPE
   SYNTAX      Integer32 (1..4094)
   MAX-ACCESS  read-only
   STATUS      current
   DESCRIPTION
       "The VLAN in which DHCP server is enabled or disabled. "
   ::= {lcsDHCPServerConfigEntry 2 }
    
lcsDHCPServerConfigInterfaceMode OBJECT-TYPE
   SYNTAX      Integer32 (0|1)
   MAX-ACCESS  read-write
   STATUS      current
   DESCRIPTION
       "Indicate the operation mode per VLAN.
       0:disable
       1:enable"
   ::= {lcsDHCPServerConfigEntry 3 }
    
lcsDHCPServerConfigInterfaceStartIPEndIP OBJECT-TYPE
   SYNTAX      DisplayString
   MAX-ACCESS  read-write
   STATUS      current
   DESCRIPTION
       "Please set SubnetMask first.
       Start IP and End IP. Format: x.x.x.x-x.x.x.x"
   ::= {lcsDHCPServerConfigEntry 4 }
    
--lcsDHCPServerConfigInterfaceEndIP OBJECT-TYPE
--   SYNTAX      IpAddress
--   MAX-ACCESS  read-write
--   STATUS      current
--   DESCRIPTION
--       "End IP"
--   ::= {lcsDHCPServerConfigEntry 5 }
    
lcsDHCPServerConfigInterfaceLeaseTime OBJECT-TYPE
   SYNTAX      Integer32
   MAX-ACCESS  read-write
   STATUS      current
   DESCRIPTION
       "The lease time in second."
   ::= {lcsDHCPServerConfigEntry 6 }
   
lcsDHCPServerConfigInterfaceSubnetMask OBJECT-TYPE
   SYNTAX      IpAddress
   MAX-ACCESS  read-write
   STATUS      current
   DESCRIPTION
       "Configure subnet mask of the DHCP address. "
   ::= {lcsDHCPServerConfigEntry 7 }
   
lcsDHCPServerConfigInterfaceDefaultRouter OBJECT-TYPE
   SYNTAX      IpAddress
   MAX-ACCESS  read-write
   STATUS      current
   DESCRIPTION
       "Configure the destination IP network or host address of the default route."
   ::= {lcsDHCPServerConfigEntry 8 } 
   
lcsDHCPServerConfigInterfaceDNSServer OBJECT-TYPE
   SYNTAX      IpAddress
   MAX-ACCESS  read-write
   STATUS      current
   DESCRIPTION
       "Configure the default DNS server. "
   ::= {lcsDHCPServerConfigEntry 9 } 
   
lcsDHCPServerStatus                              OBJECT IDENTIFIER ::= { lcsDHCPServer 8 }

lcsDHCPServerStatusTable OBJECT-TYPE
   SYNTAX      SEQUENCE OF LCSDHCPServerStatusEntry
   MAX-ACCESS  not-accessible
   STATUS      current
   DESCRIPTION
       " "
    ::= { lcsDHCPServerStatus 1 }

lcsDHCPServerStatusEntry OBJECT-TYPE
    SYNTAX        LCSDHCPServerStatusEntry
    MAX-ACCESS    not-accessible
    STATUS        current
    DESCRIPTION
        " "
    INDEX        { lcsDHCPServerStatusIndex }
    ::= { lcsDHCPServerStatusTable 1 }


LCSDHCPServerStatusEntry ::=
    SEQUENCE {
        lcsDHCPServerStatusIndex                    Integer32,
        lcsDHCPServerStatusInterfaceVLAN            Integer32,
        lcsDHCPServerStatusInterfaceType            DisplayString,
        lcsDHCPServerStatusInterfaceStartIP         IpAddress,
        lcsDHCPServerStatusInterfaceEndIP           IpAddress,
        lcsDHCPServerStatusInterfaceLeaseTime       Integer32,
        lcsDHCPServerStatusInterfaceSubnetMask      IpAddress,
        lcsDHCPServerStatusInterfaceDefaultRouter   IpAddress,
        lcsDHCPServerStatusInterfaceDNSServer       IpAddress        
    }

lcsDHCPServerStatusIndex OBJECT-TYPE
   SYNTAX      Integer32 (1..4094)
   MAX-ACCESS  not-accessible
   STATUS      current
   DESCRIPTION
       "table index."
   ::= {lcsDHCPServerStatusEntry 1 }
    
lcsDHCPServerStatusInterfaceVLAN OBJECT-TYPE
   SYNTAX      Integer32 (1..4094)
   MAX-ACCESS  read-only
   STATUS      current
   DESCRIPTION
       "The VLAN in which DHCP server is enabled or disabled. "
   ::= {lcsDHCPServerStatusEntry 2 }
    
lcsDHCPServerStatusInterfaceType OBJECT-TYPE
   SYNTAX      DisplayString
   MAX-ACCESS  read-only
   STATUS      current
   DESCRIPTION
       " "
   ::= {lcsDHCPServerStatusEntry 3 }
   
lcsDHCPServerStatusInterfaceStartIP OBJECT-TYPE
   SYNTAX      IpAddress
   MAX-ACCESS  read-only
   STATUS      current
   DESCRIPTION
       "Start IP"
   ::= {lcsDHCPServerStatusEntry 4 }
    
lcsDHCPServerStatusInterfaceEndIP OBJECT-TYPE
   SYNTAX      IpAddress
   MAX-ACCESS  read-only
   STATUS      current
   DESCRIPTION
       "End IP"
   ::= {lcsDHCPServerStatusEntry 5 }
    
lcsDHCPServerStatusInterfaceLeaseTime OBJECT-TYPE
   SYNTAX      Integer32
   MAX-ACCESS  read-only
   STATUS      current
   DESCRIPTION
       "The lease time in second."
   ::= {lcsDHCPServerStatusEntry 6 }
   
lcsDHCPServerStatusInterfaceSubnetMask OBJECT-TYPE
   SYNTAX      IpAddress
   MAX-ACCESS  read-only
   STATUS      current
   DESCRIPTION
       "Configure subnet mask of the DHCP address. "
   ::= {lcsDHCPServerStatusEntry 7 }
   
lcsDHCPServerStatusInterfaceDefaultRouter OBJECT-TYPE
   SYNTAX      IpAddress
   MAX-ACCESS  read-only
   STATUS      current
   DESCRIPTION
       "Configure the destination IP network or host address of the default route."
   ::= {lcsDHCPServerStatusEntry 8 } 
   
lcsDHCPServerStatusInterfaceDNSServer OBJECT-TYPE
   SYNTAX      IpAddress
   MAX-ACCESS  read-only
   STATUS      current
   DESCRIPTION
       "Configure the default DNS server. "
   ::= {lcsDHCPServerStatusEntry 9 } 
   
--lcsDHCPServerConf                                 OBJECT IDENTIFIER ::= { lcsDHCPServer 1 }
--
--lcsDHCPServerGlobalMode OBJECT-TYPE
--   SYNTAX      Integer32 (0|1)
--   MAX-ACCESS  read-write
--   STATUS      current
--   DESCRIPTION
--       "default: 0,
--        Global Mode :
--        0: Disable,
--        1: Enable.
--       "
--   ::= { lcsDHCPServerConf 1 }
--  
--lcsDHCPServerVLANMode OBJECT-TYPE
--   SYNTAX      Integer32 (0|1)
--   MAX-ACCESS  read-write
--   STATUS      current
--   DESCRIPTION
--       "default: 0,
--        0: Disable,
--        1: Enable.
--       "
--   ::= { lcsDHCPServerConf 2 }  
--
--lcsVLANModeTable OBJECT-TYPE
--   SYNTAX      SEQUENCE OF LCSVLANModeEntry
--   MAX-ACCESS  not-accessible
--   STATUS      current
--   DESCRIPTION
--       "A table of VLAN Mode for DHCP Server."
--    ::= { lcsDHCPServerConf 2 }

--lcsVLANModeEntry OBJECT-TYPE
--    SYNTAX        LCSVLANModeEntry
--    MAX-ACCESS    not-accessible
--    STATUS        current
--    DESCRIPTION
--        "An entry in the lcsVLANModeTable."
--    INDEX        { lcsVLANModeIndex }
--    ::= { lcsVLANModeTable 1 }
--
--LCSVLANModeEntry ::=
--    SEQUENCE {
--        lcsVLANModeIndex                            Integer32,
--        lcsVLANModeRangeLow                         Integer32,
--        lcsVLANModeRangeHigh                        Integer32,
--        lcsVLANModeEnable                           Integer32,
--      lcsVLANModeRowStatus                        RowStatus
--    }
--
--lcsVLANModeIndex OBJECT-TYPE
--   SYNTAX      Integer32 (1..2048)
--   MAX-ACCESS  not-accessible
--   STATUS      current
--   DESCRIPTION
--       "VLAN Mode table index, range: 1-2048."
--   ::= {lcsVLANModeEntry 1 }
--
--lcsVLANModeRangeLow OBJECT-TYPE
--   SYNTAX      Integer32 (1..4094)
--   MAX-ACCESS  read-create
--   STATUS      current
--   DESCRIPTION
--       "VLAN Mode low range: 1-4094."
--   ::= {lcsVLANModeEntry 2 }
--
--lcsVLANModeRangeHigh OBJECT-TYPE
--   SYNTAX      Integer32 (1..4094)
--   MAX-ACCESS  read-create
--   STATUS      current
--   DESCRIPTION
--       "VLAN Mode high range: 1-4094."
--   ::= {lcsVLANModeEntry 3 }
--
--lcsVLANModeEnable OBJECT-TYPE
--   SYNTAX      Integer32 (0..1)
--   MAX-ACCESS  read-create
--   STATUS      current
--   DESCRIPTION
--       "VLAN Mode Enable, Enable:1, Disable:0."
--   ::= {lcsVLANModeEntry 4 }
--
--lcsVLANModeRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {     lcsVLANModeEntry 5 }
--


-- lcsDHCPServerBindingType OBJECT-TYPE
--   SYNTAX      Integer32 (0|1|2|3)
--   MAX-ACCESS  read-only
--   STATUS      current
--   DESCRIPTION
--       "default: None,
--        Global Mode :
--        0: None,
--        1: Automatic,
--        2: Manual,
--        3: Expired.
--       "
--   ::= { lcsDHCPServerConf 2 }

-- lcsDHCPServerBindingState OBJECT-TYPE
--   SYNTAX      Integer32 (0|1|2|3)
--   MAX-ACCESS  read-only
--   STATUS      current
--   DESCRIPTION
--       "default: None,
--        Global Mode :
--        0: None,
--        1: Allocated,
--        2: Committed,
--        3: Expired.
--       "
--   ::= { lcsDHCPServerConf 3 }

-- lcsDHCPServerBindingIP OBJECT-TYPE
--   SYNTAX      DisplayString
--   MAX-ACCESS  read-only
--   STATUS      current
--   DESCRIPTION
--       "The DHCP Server Binding IP"
--   ::= { lcsDHCPServerConf 4 }
--
--
--lcsDHCPServerExcludedIP                                 OBJECT IDENTIFIER ::= { lcsDHCPServer 2 }
--
--lcsExcludedIPTable OBJECT-TYPE
--   SYNTAX      SEQUENCE OF LCSExcludedIPEntry
--   MAX-ACCESS  not-accessible
--   STATUS      current
--   DESCRIPTION
--       "A table of Excluded IP for DHCP Server."
--    ::= { lcsDHCPServerExcludedIP 1 }
--
--lcsExcludedIPEntry OBJECT-TYPE
--    SYNTAX        LCSExcludedIPEntry
--    MAX-ACCESS    not-accessible
--    STATUS        current
--    DESCRIPTION
--        "An entry in the lcsExcludedIPTable."
--    INDEX        { lcsExcludedIPIndex }
--    ::= { lcsExcludedIPTable 1 }
--
--LCSExcludedIPEntry ::=
--    SEQUENCE {
--        lcsExcludedIPIndex                            Integer32,
--        lcsExcludedIPRangeLow                         IpAddress,
--        lcsExcludedIPRangeHigh                        IpAddress,
--      lcsExcludedIPRowStatus                        RowStatus
--    }
--
--lcsExcludedIPIndex OBJECT-TYPE
--   SYNTAX      Integer32 (1..16)
--   MAX-ACCESS  not-accessible
--   STATUS      current
--   DESCRIPTION
--       "Excluded IP table index, range: 1-16."
--   ::= {lcsExcludedIPEntry 1 }
--
--lcsExcludedIPRangeLow OBJECT-TYPE
--   SYNTAX      IpAddress
--   MAX-ACCESS  read-create
--   STATUS      current
--   DESCRIPTION
--       "ExcludedIP low range."
--   ::= {lcsExcludedIPEntry 2 }
--
--lcsExcludedIPRangeHigh OBJECT-TYPE
--   SYNTAX      IpAddress
--   MAX-ACCESS  read-create
--   STATUS      current
--   DESCRIPTION
--       "ExcludedIP high range."
--   ::= {lcsExcludedIPEntry 3 }
--
--lcsExcludedIPRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {lcsExcludedIPEntry 4 }
--
--
--
--lcsDHCPServerPoolConf                                 OBJECT IDENTIFIER ::= { lcsDHCPServer 3 }
--
--lcsDHCPServerPoolTable OBJECT-TYPE
--   SYNTAX      SEQUENCE OF LCSDHCPServerPoolEntry
--   MAX-ACCESS  not-accessible
--   STATUS      current
--   DESCRIPTION
--       "This is the entry information for DHCP Pool."
--   ::= { lcsDHCPServerPoolConf 1 }
--
--lcsDHCPServerPoolEntry OBJECT-TYPE
--   SYNTAX      LCSDHCPServerPoolEntry
--   MAX-ACCESS  not-accessible
--   STATUS      current
--   DESCRIPTION
--       " "
--   INDEX    { lcsDHCPServerConfIndex  }
--   ::= { lcsDHCPServerPoolTable 1 }
--
--LCSDHCPServerPoolEntry ::= SEQUENCE {
--    lcsDHCPServerConfIndex               Integer32,
--    lcsDHCPServerPoolName                DisplayString,
--    lcsDHCPServerPoolType                Integer32,
--    lcsDHCPServerIP                      IpAddress,
--    lcsDHCPServerSubnetMask              IpAddress,
--    lcsDHCPServerLeaseTimeDays           Integer32,
--    lcsDHCPServerLeaseTimeHours          Integer32,
--    lcsDHCPServerLeaseTimeMinutes        Integer32,
--    lcsDHCPServerDomainName              DisplayString,
--    lcsDHCPServerBroadcastAddress        IpAddress,
--    lcsDHCPServerDefRouter1              IpAddress,
--    lcsDHCPServerDefRouter2              IpAddress,
--    lcsDHCPServerDefRouter3              IpAddress,
--    lcsDHCPServerDefRouter4              IpAddress,
--    lcsDHCPServerDNSServer1              IpAddress,
--    lcsDHCPServerDNSServer2              IpAddress,
--    lcsDHCPServerDNSServer3              IpAddress,
--    lcsDHCPServerDNSServer4              IpAddress,
--    lcsDHCPServerNTPServer1              IpAddress,
--    lcsDHCPServerNTPServer2              IpAddress,
--    lcsDHCPServerNTPServer3              IpAddress,
--    lcsDHCPServerNTPServer4              IpAddress,
--    lcsDHCPServerNetbiosType             Integer32,
--    lcsDHCPServerNetbiosScope            DisplayString,
--    lcsDHCPServerNetbiosNameServer1      IpAddress,
--    lcsDHCPServerNetbiosNameServer2      IpAddress,
--    lcsDHCPServerNetbiosNameServer3      IpAddress,
--    lcsDHCPServerNetbiosNameServer4      IpAddress,
--    lcsDHCPServerNisDomainName           DisplayString,
--    lcsDHCPServerNisServer1              IpAddress,
--    lcsDHCPServerNisServer2              IpAddress,
--    lcsDHCPServerNisServer3              IpAddress,
--    lcsDHCPServerNisServer4              IpAddress,
--    lcsDHCPServerClientIDType            Integer32,
--    lcsDHCPServerClientID                DisplayString,
--    lcsDHCPServerHWAddr                  DisplayString,
--    lcsDHCPServerClientName              DisplayString,
--    lcsDHCPServerVendorClassID1          DisplayString,
--    lcsDHCPServerVendorSpecificInfo1     DisplayString,
--    lcsDHCPServerVendorClassID2          DisplayString,
--    lcsDHCPServerVendorSpecificInfo2     DisplayString,
--    lcsDHCPServerVendorClassID3          DisplayString,
--    lcsDHCPServerVendorSpecificInfo3     DisplayString,
--    lcsDHCPServerVendorClassID4          DisplayString,
--    lcsDHCPServerVendorSpecificInfo4     DisplayString,
--    lcsDHCPServerVendorClassID5          DisplayString,
--    lcsDHCPServerVendorSpecificInfo5     DisplayString,
--    lcsDHCPServerVendorClassID6          DisplayString,
--    lcsDHCPServerVendorSpecificInfo6     DisplayString,
--    lcsDHCPServerVendorClassID7          DisplayString,
--    lcsDHCPServerVendorSpecificInfo7     DisplayString,
--    lcsDHCPServerVendorClassID8          DisplayString,
--    lcsDHCPServerVendorSpecificInfo8     DisplayString,
--    lcsDHCPServerRowStatus               RowStatus
--}
--
--lcsDHCPServerConfIndex OBJECT-TYPE
--   SYNTAX      Integer32 (1..64)
--   MAX-ACCESS  not-accessible
--   STATUS      current
--   DESCRIPTION
--       " pool, range : 1 - 64. "
--   ::= { lcsDHCPServerPoolEntry 1 }
--
--lcsDHCPServerPoolName OBJECT-TYPE
--   SYNTAX      DisplayString(SIZE (1..32))
--   MAX-ACCESS  read-create
--   STATUS      current
--   DESCRIPTION
--       " DHCP pool name. "
--   ::= { lcsDHCPServerPoolEntry 2 }
--
--lcsDHCPServerPoolType OBJECT-TYPE
--   SYNTAX      Integer32(0|1|2)
--   MAX-ACCESS  read-create
--   STATUS      current
--   DESCRIPTION
--       " DHCP Server Pool Type.
--     0:None
--     1:Network
--     2:Host, please set DHCP Server IP first."
--   ::= { lcsDHCPServerPoolEntry 3 }
--
--lcsDHCPServerIP OBJECT-TYPE
--   SYNTAX      IpAddress
--   MAX-ACCESS  read-create
--   STATUS      current
--   DESCRIPTION
--       " DHCP Server IP. "
--   ::= { lcsDHCPServerPoolEntry 4 }
--
--lcsDHCPServerSubnetMask OBJECT-TYPE
--   SYNTAX      IpAddress
--   MAX-ACCESS  read-create
--   STATUS      current
--   DESCRIPTION
--       " DHCP Server IPv4 Subnet Mask. "
--   ::= { lcsDHCPServerPoolEntry 5}
--
--lcsDHCPServerLeaseTimeDays OBJECT-TYPE
--   SYNTAX      Integer32(0..365)
--   MAX-ACCESS  read-create
--   STATUS      current
--   DESCRIPTION
--       " DHCP Server IPv4 Lease Time:Days. "
--   ::= { lcsDHCPServerPoolEntry 6 }
--
--lcsDHCPServerLeaseTimeHours OBJECT-TYPE
--   SYNTAX      Integer32(0..23)
--   MAX-ACCESS  read-create
--   STATUS      current
--   DESCRIPTION
--       " DHCP Server IPv4 Lease Time:Hours. "
--   ::= { lcsDHCPServerPoolEntry 7 }
--
--lcsDHCPServerLeaseTimeMinutes OBJECT-TYPE
--   SYNTAX      Integer32(0..59)
--   MAX-ACCESS  read-create
--   STATUS      current
--   DESCRIPTION
--       " DHCP Server IPv4 Lease Time:Minutes. "
--   ::= { lcsDHCPServerPoolEntry 8 }
--
--lcsDHCPServerDomainName OBJECT-TYPE
--   SYNTAX      DisplayString(SIZE (0..128))
--   MAX-ACCESS  read-create
--   STATUS      current
--   DESCRIPTION
--       " DHCP Server Domain Name. "
--   ::= { lcsDHCPServerPoolEntry 9 }
--
--lcsDHCPServerBroadcastAddress OBJECT-TYPE
--   SYNTAX      IpAddress
--   MAX-ACCESS  read-create
--   STATUS      current
--   DESCRIPTION
--       " DHCP Server IPv4 Broadcast Address. "
--   ::= { lcsDHCPServerPoolEntry 10 }
--
--lcsDHCPServerDefRouter1 OBJECT-TYPE
--   SYNTAX      IpAddress
--   MAX-ACCESS  read-create
--   STATUS      current
--   DESCRIPTION
--       " DHCP Server IPv4 Default Router 1. "
--   ::= { lcsDHCPServerPoolEntry 11 }
--
--lcsDHCPServerDefRouter2 OBJECT-TYPE
--   SYNTAX      IpAddress
--   MAX-ACCESS  read-create
--   STATUS      current
--   DESCRIPTION
--       " DHCP Server IPv4 Default Router 2. "
--   ::= { lcsDHCPServerPoolEntry 12 }
--
--lcsDHCPServerDefRouter3 OBJECT-TYPE
--   SYNTAX      IpAddress
--   MAX-ACCESS  read-create
--   STATUS      current
--   DESCRIPTION
--       " DHCP Server IPv4 Default Router 3. "
--   ::= { lcsDHCPServerPoolEntry 13 }
--
--lcsDHCPServerDefRouter4 OBJECT-TYPE
--   SYNTAX      IpAddress
--   MAX-ACCESS  read-create
--   STATUS      current
--   DESCRIPTION
--       " DHCP Server IPv4 Default Router 4. "
--   ::= { lcsDHCPServerPoolEntry 14 }
--
--lcsDHCPServerDNSServer1 OBJECT-TYPE
--   SYNTAX      IpAddress
--   MAX-ACCESS  read-create
--   STATUS      current
--   DESCRIPTION
--       " DHCP Server DNS Server 1. "
--   ::= { lcsDHCPServerPoolEntry 15 }
--
--lcsDHCPServerDNSServer2 OBJECT-TYPE
--   SYNTAX      IpAddress
--   MAX-ACCESS  read-create
--   STATUS      current
--   DESCRIPTION
--       " DHCP Server DNS Server 2. "
--   ::= { lcsDHCPServerPoolEntry 16 }
--
--lcsDHCPServerDNSServer3 OBJECT-TYPE
--   SYNTAX      IpAddress
--   MAX-ACCESS  read-create
--   STATUS      current
--   DESCRIPTION
--       " DHCP Server DNS Server 3. "
--   ::= { lcsDHCPServerPoolEntry 17 }
--
--lcsDHCPServerDNSServer4 OBJECT-TYPE
--   SYNTAX      IpAddress
--   MAX-ACCESS  read-create
--   STATUS      current
--   DESCRIPTION
--       " DHCP Server DNS Server 4. "
--   ::= { lcsDHCPServerPoolEntry 18 }
--
--lcsDHCPServerNTPServer1 OBJECT-TYPE
--   SYNTAX      IpAddress
--   MAX-ACCESS  read-create
--   STATUS      current
--   DESCRIPTION
--       " DHCP Server NTP Server 1. "
--   ::= { lcsDHCPServerPoolEntry 19 }
--
--lcsDHCPServerNTPServer2 OBJECT-TYPE
--   SYNTAX      IpAddress
--   MAX-ACCESS  read-create
--   STATUS      current
--   DESCRIPTION
--       " DHCP Server NTP Server 2. "
--   ::= { lcsDHCPServerPoolEntry 20 }
--
--lcsDHCPServerNTPServer3 OBJECT-TYPE
--   SYNTAX      IpAddress
--   MAX-ACCESS  read-create
--   STATUS      current
--   DESCRIPTION
--       " DHCP Server NTP Server 3. "
--   ::= { lcsDHCPServerPoolEntry 21 }
--
--lcsDHCPServerNTPServer4 OBJECT-TYPE
--   SYNTAX      IpAddress
--   MAX-ACCESS  read-create
--   STATUS      current
--   DESCRIPTION
--       " DHCP Server NTP Server 4. "
--   ::= { lcsDHCPServerPoolEntry 22 }
--
--lcsDHCPServerNetbiosType OBJECT-TYPE
--   SYNTAX      Integer32(1..4)
--   MAX-ACCESS  read-create
--   STATUS      current
--   DESCRIPTION
--       " DHCP Server Netbios Node Type.
--     0:None
--     1:B-node
--     2:P-node
--     3:M-node
--     4:H-node"
--   ::= { lcsDHCPServerPoolEntry 23 }
--
--lcsDHCPServerNetbiosScope OBJECT-TYPE
--   SYNTAX      DisplayString(SIZE (0..128))
--   MAX-ACCESS  read-create
--   STATUS      current
--   DESCRIPTION
--       " DHCP Server Netbios Scope. "
--   ::= { lcsDHCPServerPoolEntry 24 }
--
--lcsDHCPServerNetbiosNameServer1 OBJECT-TYPE
--   SYNTAX      IpAddress
--   MAX-ACCESS  read-create
--   STATUS      current
--   DESCRIPTION
--       " DHCP Server Netbios Name Server 1. "
--   ::= { lcsDHCPServerPoolEntry 25 }
--
--lcsDHCPServerNetbiosNameServer2 OBJECT-TYPE
--   SYNTAX      IpAddress
--   MAX-ACCESS  read-create
--   STATUS      current
--   DESCRIPTION
--       " DHCP Server Netbios Name Server 2. "
--   ::= { lcsDHCPServerPoolEntry 26 }
--
--lcsDHCPServerNetbiosNameServer3 OBJECT-TYPE
--   SYNTAX      IpAddress
--   MAX-ACCESS  read-create
--   STATUS      current
--   DESCRIPTION
--       " DHCP Server Netbios Name Server 3. "
--   ::= { lcsDHCPServerPoolEntry 27 }
--
--lcsDHCPServerNetbiosNameServer4 OBJECT-TYPE
--   SYNTAX      IpAddress
--   MAX-ACCESS  read-create
--   STATUS      current
--   DESCRIPTION
--       " DHCP Server Netbios Name Server 4. "
--   ::= { lcsDHCPServerPoolEntry 28 }
--
--lcsDHCPServerNisDomainName OBJECT-TYPE
--   SYNTAX      DisplayString(SIZE (0..128))
--   MAX-ACCESS  read-create
--   STATUS      current
--   DESCRIPTION
--       " DHCP Server Nis Domain Name. "
--   ::= { lcsDHCPServerPoolEntry 29 }
--
--lcsDHCPServerNisServer1 OBJECT-TYPE
--   SYNTAX      IpAddress
--   MAX-ACCESS  read-create
--   STATUS      current
--   DESCRIPTION
--       " DHCP Server Nis Server 1. "
--   ::= { lcsDHCPServerPoolEntry 30 }
--
--lcsDHCPServerNisServer2 OBJECT-TYPE
--   SYNTAX      IpAddress
--   MAX-ACCESS  read-create
--   STATUS      current
--   DESCRIPTION
--       " DHCP Server Nis Server 2. "
--   ::= { lcsDHCPServerPoolEntry 31 }
--
--lcsDHCPServerNisServer3 OBJECT-TYPE
--   SYNTAX      IpAddress
--   MAX-ACCESS  read-create
--   STATUS      current
--   DESCRIPTION
--       " DHCP Server Nis Server 3. "
--   ::= { lcsDHCPServerPoolEntry 32 }
--
--lcsDHCPServerNisServer4 OBJECT-TYPE
--   SYNTAX      IpAddress
--   MAX-ACCESS  read-create
--   STATUS      current
--   DESCRIPTION
--       " DHCP Server Nis Server 4. "
--   ::= { lcsDHCPServerPoolEntry 33 }
--
--lcsDHCPServerClientIDType OBJECT-TYPE
--   SYNTAX      Integer32(0..2)
--   MAX-ACCESS  read-create
--   STATUS      current
--   DESCRIPTION
--       " DHCP Server Client ID Type.
--     0:None
--     1:FQDN
--     2:MAC"
--   ::= { lcsDHCPServerPoolEntry 34 }
--
--lcsDHCPServerClientID OBJECT-TYPE
--   SYNTAX      DisplayString(SIZE (0..128))
--   MAX-ACCESS  read-create
--   STATUS      current
--   DESCRIPTION
--       " DHCP Server Pool Client ID. "
--   ::= { lcsDHCPServerPoolEntry 35 }
--
--lcsDHCPServerHWAddr OBJECT-TYPE
--   SYNTAX      DisplayString(SIZE (0..17))
--   MAX-ACCESS  read-create
--   STATUS      current
--   DESCRIPTION
--       " DHCP Server Pool Hardware Address. "
--   ::= { lcsDHCPServerPoolEntry 36 }
--
--lcsDHCPServerClientName OBJECT-TYPE
--   SYNTAX      DisplayString(SIZE (0..32))
--   MAX-ACCESS  read-create
--   STATUS      current
--   DESCRIPTION
--       " DHCP Server Pool Client Name. "
--   ::= { lcsDHCPServerPoolEntry 37 }
--
--lcsDHCPServerVendorClassID1 OBJECT-TYPE
--   SYNTAX      DisplayString(SIZE (0..64))
--   MAX-ACCESS  read-create
--   STATUS      current
--   DESCRIPTION
--       " DHCP Server Vendor Class ID 1. Please also set VendorSpecificInfo1."
--   ::= { lcsDHCPServerPoolEntry 38 }
--
--lcsDHCPServerVendorSpecificInfo1 OBJECT-TYPE
--   SYNTAX      DisplayString(SIZE (0..32))
--   MAX-ACCESS  read-create
--   STATUS      current
--   DESCRIPTION
--       " DHCP Server Vendor Specific Info 1. Please also set VendorClassID1."
--   ::= { lcsDHCPServerPoolEntry 39 }
--
--lcsDHCPServerVendorClassID2 OBJECT-TYPE
--   SYNTAX      DisplayString(SIZE (0..64))
--   MAX-ACCESS  read-create
--   STATUS      current
--   DESCRIPTION
--       " DHCP Server Vendor Class ID 2. Please also set VendorSpecificInfo2."
--   ::= { lcsDHCPServerPoolEntry 40 }
--
--lcsDHCPServerVendorSpecificInfo2 OBJECT-TYPE
--   SYNTAX      DisplayString(SIZE (0..32))
--   MAX-ACCESS  read-create
--   STATUS      current
--   DESCRIPTION
--       " DHCP Server Vendor Specific Info 2. Please also set VendorClassID2."
--   ::= { lcsDHCPServerPoolEntry 41 }
--
--lcsDHCPServerVendorClassID3 OBJECT-TYPE
--   SYNTAX      DisplayString(SIZE (0..64))
--   MAX-ACCESS  read-create
--   STATUS      current
--   DESCRIPTION
--       " DHCP Server Vendor Class ID 3. Please also set VendorSpecificInfo3."
--   ::= { lcsDHCPServerPoolEntry 42 }
--
--lcsDHCPServerVendorSpecificInfo3 OBJECT-TYPE
--   SYNTAX      DisplayString(SIZE (0..32))
--   MAX-ACCESS  read-create
--   STATUS      current
--   DESCRIPTION
--       " DHCP Server Vendor Specific Info 3. Please also set VendorClassID3."
--   ::= { lcsDHCPServerPoolEntry 43 }
--
--lcsDHCPServerVendorClassID4 OBJECT-TYPE
--   SYNTAX      DisplayString(SIZE (0..64))
--   MAX-ACCESS  read-create
--   STATUS      current
--   DESCRIPTION
--       " DHCP Server Vendor Class ID 4. Please also set VendorSpecificInfo4."
--   ::= { lcsDHCPServerPoolEntry 44 }
--
--lcsDHCPServerVendorSpecificInfo4 OBJECT-TYPE
--   SYNTAX      DisplayString(SIZE (0..32))
--   MAX-ACCESS  read-create
--   STATUS      current
--   DESCRIPTION
--       " DHCP Server Vendor Specific Info 4. Please also set VendorClassID4."
--   ::= { lcsDHCPServerPoolEntry 45 }
--
--lcsDHCPServerVendorClassID5 OBJECT-TYPE
--   SYNTAX      DisplayString(SIZE (0..64))
--   MAX-ACCESS  read-create
--   STATUS      current
--   DESCRIPTION
--       " DHCP Server Vendor Class ID 5. Please also set VendorSpecificInfo5."
--   ::= { lcsDHCPServerPoolEntry 46 }
--
--lcsDHCPServerVendorSpecificInfo5 OBJECT-TYPE
--   SYNTAX      DisplayString(SIZE (0..32))
--   MAX-ACCESS  read-create
--   STATUS      current
--   DESCRIPTION
--       " DHCP Server Vendor Specific Info 5. Please also set VendorClassID5."
--   ::= { lcsDHCPServerPoolEntry 47 }
--
--lcsDHCPServerVendorClassID6 OBJECT-TYPE
--   SYNTAX      DisplayString(SIZE (0..64))
--   MAX-ACCESS  read-create
--   STATUS      current
--   DESCRIPTION
--       " DHCP Server Vendor Class ID 6. Please also set VendorSpecificInfo6."
--   ::= { lcsDHCPServerPoolEntry 48 }
--
--lcsDHCPServerVendorSpecificInfo6 OBJECT-TYPE
--   SYNTAX      DisplayString(SIZE (0..32))
--   MAX-ACCESS  read-create
--   STATUS      current
--   DESCRIPTION
--       " DHCP Server Vendor Specific Info 6. Please also set VendorClassID6."
--   ::= { lcsDHCPServerPoolEntry 49 }
--
--lcsDHCPServerVendorClassID7 OBJECT-TYPE
--   SYNTAX      DisplayString(SIZE (0..64))
--   MAX-ACCESS  read-create
--   STATUS      current
--   DESCRIPTION
--       " DHCP Server Vendor Class ID 7. Please also set VendorSpecificInfo7."
--   ::= { lcsDHCPServerPoolEntry 50 }
--
--lcsDHCPServerVendorSpecificInfo7 OBJECT-TYPE
--   SYNTAX      DisplayString(SIZE (0..32))
--   MAX-ACCESS  read-create
--   STATUS      current
--   DESCRIPTION
--       " DHCP Server Vendor Specific Info 7. Please also set VendorClassID7."
--   ::= { lcsDHCPServerPoolEntry 51 }
--
--lcsDHCPServerVendorClassID8 OBJECT-TYPE
--   SYNTAX      DisplayString(SIZE (0..64))
--   MAX-ACCESS  read-create
--   STATUS      current
--   DESCRIPTION
--       " DHCP Server Vendor Class ID 8. Please also set VendorSpecificInfo8."
--   ::= { lcsDHCPServerPoolEntry 52 }
--
--lcsDHCPServerVendorSpecificInfo8 OBJECT-TYPE
--   SYNTAX      DisplayString(SIZE (0..32))
--   MAX-ACCESS  read-create
--   STATUS      current
--   DESCRIPTION
--       " DHCP Server Vendor Specific Info 8. Please also set VendorClassID8."
--   ::= { lcsDHCPServerPoolEntry 53 }
--
--lcsDHCPServerRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {lcsDHCPServerPoolEntry 54 }
--
--lcsDHCPServerStatistics                         OBJECT IDENTIFIER ::= { lcsDHCPServer 4 }
--
--lcsDHCPServerStatisticsDatabaseCountersPool OBJECT-TYPE
--   SYNTAX      Integer32
--   MAX-ACCESS  read-only
--   STATUS      current
--   DESCRIPTION
--       "
--       "
--   ::= { lcsDHCPServerStatistics 1 }
--   
--lcsDHCPServerStatisticsDatabaseCountersExcludedIPAddress OBJECT-TYPE
--   SYNTAX      Integer32
--   MAX-ACCESS  read-only
--   STATUS      current
--   DESCRIPTION
--       "
--       "
--   ::= { lcsDHCPServerStatistics 2 }   
--   
--lcsDHCPServerStatisticsDatabaseCountersDeclinedIPAddress OBJECT-TYPE
--   SYNTAX      Integer32
--   MAX-ACCESS  read-only
--   STATUS      current
--   DESCRIPTION
--       "
--       "
--   ::= { lcsDHCPServerStatistics 3 }     
--   
--lcsDHCPServerStatisticsBindingCountersAutomaticBinding OBJECT-TYPE
--   SYNTAX      Integer32
--   MAX-ACCESS  read-only
--   STATUS      current
--   DESCRIPTION
--       "
--       "
--   ::= { lcsDHCPServerStatistics 4 }     
--   
--lcsDHCPServerStatisticsBindingCountersManualBinding OBJECT-TYPE
--   SYNTAX      Integer32
--   MAX-ACCESS  read-only
--   STATUS      current
--   DESCRIPTION
--       "
--       "
--   ::= { lcsDHCPServerStatistics 5 }      
--   
--lcsDHCPServerStatisticsBindingCountersExpiredBinding OBJECT-TYPE
--   SYNTAX      Integer32
--   MAX-ACCESS  read-only
--   STATUS      current
--   DESCRIPTION
--       "
--       "
--   ::= { lcsDHCPServerStatistics 6 }    
--   
--lcsDHCPServerStatisticsDHCPMessageReceivedCountersDISCOVER OBJECT-TYPE
--   SYNTAX      Integer32
--   MAX-ACCESS  read-only
--   STATUS      current
--   DESCRIPTION
--       "
--       "
--   ::= { lcsDHCPServerStatistics 7 }     
--
--lcsDHCPServerStatisticsDHCPMessageReceivedCountersREQUEST OBJECT-TYPE
--   SYNTAX      Integer32
--   MAX-ACCESS  read-only
--   STATUS      current
--   DESCRIPTION
--       "
--       "
--   ::= { lcsDHCPServerStatistics 8 }         
--   
--lcsDHCPServerStatisticsDHCPMessageReceivedCountersDECLINE OBJECT-TYPE
--   SYNTAX      Integer32
--   MAX-ACCESS  read-only
--   STATUS      current
--   DESCRIPTION
--       "
--       "
--   ::= { lcsDHCPServerStatistics 9 }   
--   
--lcsDHCPServerStatisticsDHCPMessageReceivedCountersRELEASE OBJECT-TYPE
--   SYNTAX      Integer32
--   MAX-ACCESS  read-only
--   STATUS      current
--   DESCRIPTION
--       "
--       "
--   ::= { lcsDHCPServerStatistics 10 }   
--
--lcsDHCPServerStatisticsDHCPMessageReceivedCountersINFORM OBJECT-TYPE
--   SYNTAX      Integer32
--   MAX-ACCESS  read-only
--   STATUS      current
--   DESCRIPTION
--       "
--       "
--   ::= { lcsDHCPServerStatistics 11 }     
--   
--lcsDHCPServerStatisticsDHCPMessageSentCountersOFFER OBJECT-TYPE
--   SYNTAX      Integer32
--   MAX-ACCESS  read-only
--   STATUS      current
--   DESCRIPTION
--       "
--       "
--   ::= { lcsDHCPServerStatistics 12 }     
--   
--lcsDHCPServerStatisticsDHCPMessageSentCountersACK OBJECT-TYPE
--   SYNTAX      Integer32
--   MAX-ACCESS  read-only
--   STATUS      current
--   DESCRIPTION
--       "
--       "
--   ::= { lcsDHCPServerStatistics 13 }      
--   
--lcsDHCPServerStatisticsDHCPMessageSentCountersNAK OBJECT-TYPE
--   SYNTAX      Integer32
--   MAX-ACCESS  read-only
--   STATUS      current
--   DESCRIPTION
--       "
--       "
--   ::= { lcsDHCPServerStatistics 14 }    
--   
--lcsDHCPServerClear OBJECT-TYPE
--   SYNTAX      Integer32
--   MAX-ACCESS  read-write
--   STATUS      current
--   DESCRIPTION
--       "
--       "
--   ::= { lcsDHCPServerStatistics 15 }      
--   
--lcsDHCPServerBinding                         OBJECT IDENTIFIER ::= { lcsDHCPServer 5 }
--
--lcsDHCPServerBindingTable OBJECT-TYPE
--   SYNTAX      SEQUENCE OF LCSDHCPServerBindingEntry
--   MAX-ACCESS  not-accessible
--   STATUS      current
--   DESCRIPTION
--       " "
--   ::= { lcsDHCPServerBinding 1 }
--
--lcsDHCPServerBindingEntry OBJECT-TYPE
--   SYNTAX      LCSDHCPServerBindingEntry
--   MAX-ACCESS  not-accessible
--   STATUS      current
--   DESCRIPTION
--       " "
--   INDEX    { lcsDHCPServerBindingIndex  }
--   ::= { lcsDHCPServerBindingTable 1 }
--   
--LCSDHCPServerBindingEntry ::= SEQUENCE {
--   lcsDHCPServerBindingIndex                 Integer32,
--   lcsDHCPServerBindingIP                    DisplayString,
--   lcsDHCPServerBindingType                  DisplayString,
--   lcsDHCPServerBindingState                 DisplayString,
--   lcsDHCPServerBindingPoolName              DisplayString,
--   lcsDHCPServerBindingServerID              DisplayString,
--   lcsDHCPServerBindingVLAN                  Integer32,
--   lcsDHCPServerBindingSubnetMask            DisplayString,
--   lcsDHCPServerBindingClientIDType          DisplayString,
--   lcsDHCPServerBindingClientIDValue         DisplayString,
--   lcsDHCPServerBindingMACAddress            DisplayString, 
--   lcsDHCPServerBindingLeaseTime             DisplayString,
--   lcsDHCPServerBindingWillExpiredIn         DisplayString,
--   lcsDHCPServerBindingDelete                Integer32
--}
--
--lcsDHCPServerBindingIndex OBJECT-TYPE
--   SYNTAX      Integer32
--   MAX-ACCESS  not-accessible
--   STATUS      current
--   DESCRIPTION
--       "Index"
--   ::= { lcsDHCPServerBindingEntry 1 }
--
--lcsDHCPServerBindingIP OBJECT-TYPE
--   SYNTAX      DisplayString
--   MAX-ACCESS  read-only
--   STATUS      current
--   DESCRIPTION
--       " "
--   ::= { lcsDHCPServerBindingEntry 2 }
--
--lcsDHCPServerBindingType OBJECT-TYPE
--   SYNTAX      DisplayString
--   MAX-ACCESS  read-only
--   STATUS      current
--   DESCRIPTION
--       " "
--   ::= { lcsDHCPServerBindingEntry 3 }
--
--lcsDHCPServerBindingState OBJECT-TYPE
--   SYNTAX      DisplayString
--   MAX-ACCESS  read-only
--   STATUS      current
--   DESCRIPTION
--       " "
--   ::= { lcsDHCPServerBindingEntry 4 }
--   
--lcsDHCPServerBindingPoolName OBJECT-TYPE
--   SYNTAX      DisplayString
--   MAX-ACCESS  read-only
--   STATUS      current
--   DESCRIPTION
--       " "
--   ::= { lcsDHCPServerBindingEntry 5 }   
--
--lcsDHCPServerBindingServerID OBJECT-TYPE
--   SYNTAX      DisplayString
--   MAX-ACCESS  read-only
--   STATUS      current
--   DESCRIPTION
--       " "
--   ::= { lcsDHCPServerBindingEntry 6 }   
--
--lcsDHCPServerBindingVLAN OBJECT-TYPE
--   SYNTAX      Integer32
--   MAX-ACCESS  read-only
--   STATUS      current
--   DESCRIPTION
--       " "
--   ::= { lcsDHCPServerBindingEntry 7 }   
--   
--lcsDHCPServerBindingSubnetMask OBJECT-TYPE
--   SYNTAX      DisplayString
--   MAX-ACCESS  read-only
--   STATUS      current
--   DESCRIPTION
--       " "
--   ::= { lcsDHCPServerBindingEntry 8 }   
--   
--lcsDHCPServerBindingClientIDType OBJECT-TYPE
--   SYNTAX      DisplayString
--   MAX-ACCESS  read-only
--   STATUS      current
--   DESCRIPTION
--       " "
--   ::= { lcsDHCPServerBindingEntry 9 }  
--   
--lcsDHCPServerBindingClientIDValue OBJECT-TYPE
--   SYNTAX      DisplayString
--   MAX-ACCESS  read-only
--   STATUS      current
--   DESCRIPTION
--       " "
--   ::= { lcsDHCPServerBindingEntry 10 }  
--   
--lcsDHCPServerBindingMACAddress OBJECT-TYPE
--   SYNTAX      DisplayString
--   MAX-ACCESS  read-only
--   STATUS      current
--   DESCRIPTION
--       " "
--   ::= { lcsDHCPServerBindingEntry 11 }     
--   
--lcsDHCPServerBindingLeaseTime OBJECT-TYPE
--   SYNTAX      DisplayString
--   MAX-ACCESS  read-only
--   STATUS      current
--   DESCRIPTION
--       " "
--   ::= { lcsDHCPServerBindingEntry 12 }       
--   
--lcsDHCPServerBindingWillExpiredIn OBJECT-TYPE
--   SYNTAX      DisplayString
--   MAX-ACCESS  read-only
--   STATUS      current
--   DESCRIPTION
--       " "
--   ::= { lcsDHCPServerBindingEntry 13 }  
--   
--lcsDHCPServerBindingDelete OBJECT-TYPE
--   SYNTAX      Integer32
--   MAX-ACCESS  read-write
--   STATUS      current
--   DESCRIPTION
--       " "
--   ::= { lcsDHCPServerBindingEntry 14 }    
--   
--lcsDHCPServerBindingClearAutomatic   OBJECT-TYPE
--   SYNTAX      Integer32
--   MAX-ACCESS  read-write
--   STATUS      current
--   DESCRIPTION
--     "1:clear"
--   ::= { lcsDHCPServerBinding 2 }
-- 
--lcsDHCPServerBindingClearManual   OBJECT-TYPE
--   SYNTAX      Integer32
--   MAX-ACCESS  read-write
--   STATUS      current
--   DESCRIPTION
--     "1:clear"
--   ::= { lcsDHCPServerBinding 3 }
--
--lcsDHCPServerBindingClearExpired   OBJECT-TYPE
--   SYNTAX      Integer32
--   MAX-ACCESS  read-write
--   STATUS      current
--   DESCRIPTION
--     "1:clear"
--   ::= { lcsDHCPServerBinding 4 }   
--   
--lcsDHCPServerDeclined                         OBJECT IDENTIFIER ::= { lcsDHCPServer 6 }
--
--lcsDHCPServerDeclinedTable OBJECT-TYPE
--   SYNTAX      SEQUENCE OF LCSDHCPServerDeclinedEntry
--   MAX-ACCESS  not-accessible
--   STATUS      current
--   DESCRIPTION
--       " "
--   ::= { lcsDHCPServerDeclined 1 }
--
--lcsDHCPServerDeclinedEntry OBJECT-TYPE
--   SYNTAX      LCSDHCPServerDeclinedEntry
--   MAX-ACCESS  not-accessible
--   STATUS      current
--   DESCRIPTION
--       " "
--   INDEX    { lcsDHCPServerDeclinedIndex  }
--   ::= { lcsDHCPServerDeclinedTable 1 }
--   
--LCSDHCPServerDeclinedEntry ::= SEQUENCE {
--   lcsDHCPServerDeclinedIndex                 Integer32,
--   lcsDHCPServerDeclinedIP                    DisplayString
--}
--
--lcsDHCPServerDeclinedIndex OBJECT-TYPE
--   SYNTAX      Integer32
--   MAX-ACCESS  not-accessible
--   STATUS      current
--   DESCRIPTION
--       "Index"
--   ::= { lcsDHCPServerDeclinedEntry 1 }
--   
--lcsDHCPServerDeclinedIP OBJECT-TYPE
--   SYNTAX      DisplayString
--   MAX-ACCESS  read-only
--   STATUS      current
--   DESCRIPTION
--       " "
--   ::= { lcsDHCPServerDeclinedEntry 2 }  
      
-- =======================================================================================================================
lcsVLANConf                                     OBJECT IDENTIFIER ::= { lcsSystem 10 }

lcsVLAN                                     OBJECT IDENTIFIER ::= { lcsVLANConf 2}

lcsVlanStatus              OBJECT IDENTIFIER   ::= { lcsVLAN 6 }

--
-- =======================================================================================================================
-- Start lcsVlan group
-- =======================================================================================================================
    lcsVlanExistingVLANs  OBJECT-TYPE
               SYNTAX      DisplayString
               MAX-ACCESS  read-write
               STATUS      current
               DESCRIPTION
                   "This field shows the VLANs that are created on the switch.
                    More VLANs may be created by using a
                    list syntax where the individual elements are separated by commas.
                    Ranges are specified with a
                    dash separating the lower and upper bound.
                    The following example will create VLANs 1, 10, 11, 12
                    , 13, 200, and 300: 1,10-13,200,300.
                    default: 1."
               ::= {     lcsVLAN 1 }

    lcsVlanEthertypeforCustomSPorts  OBJECT-TYPE
               SYNTAX      DisplayString
               MAX-ACCESS  read-write
               STATUS      current
               DESCRIPTION
                   "This field specifies the ethertype/TPID (specified in hexadecimal)
                    used for Custom S-ports. The
                    setting is in force for all ports whose Port Type
                    is set to S-Custom-Port.
                    range: 0600-ffff,
                    default: 88a8."
               ::= {     lcsVLAN 2 }

    lcsVlanTable OBJECT-TYPE
               SYNTAX      SEQUENCE OF     LCSVlanEntry
               MAX-ACCESS  not-accessible
               STATUS      current
               DESCRIPTION
                   "Configure Vlan ports Configuration mode.
                    INDEX for this table is ifIndex which is
                    equivalent to the panel port number."
               ::= {     lcsVLAN 3 }

    lcsVlanEntry OBJECT-TYPE
               SYNTAX          LCSVlanEntry
               MAX-ACCESS  not-accessible
               STATUS      current
               DESCRIPTION
                   "The Vlan entry."
               INDEX    {     ifIndex  }
               ::= {     lcsVlanTable 1 }

    LCSVlanEntry             ::= SEQUENCE {
                lcsVlanMode              INTEGER,
                lcsVlanPortVLAN          Integer32,
                lcsVlanPortType          INTEGER,
                lcsVlanIngressFiltering  AdminMode,
--              lcsVlanVLANTrunking      AdminMode,
                lcsVlanIngressAcceptance INTEGER,
                lcsVlanEgressTagging     INTEGER,
                lcsVlanAllowedVLANs      DisplayString,
                lcsVlanForbiddenVLANs    DisplayString
                }

    lcsVlanMode OBJECT-TYPE
               SYNTAX      INTEGER{access(0), trunk(1), hybrid(2)}
               MAX-ACCESS  read-write
               STATUS      current
               DESCRIPTION
                   "The port mode determines the fundamental
                    behavior of the port in question.
                    A port can be in one of three modes as described below.
                    0: access,
                    1: trunk,
                    2: hybrid."
               DEFVAL  { access }
               ::= {     lcsVlanEntry 2 }

    lcsVlanPortVLAN OBJECT-TYPE
               SYNTAX      Integer32(1..4094)
               MAX-ACCESS  read-write
               STATUS      current
               DESCRIPTION
                   "Determines the port's VLAN ID (a.k.a. PVID).
                    range: 1-4094,
                    default: 1."
               ::= {     lcsVlanEntry 3 }

    lcsVlanPortType OBJECT-TYPE
               SYNTAX      INTEGER { unaware(0), cPort(1), sPort(2), sCustomPort(3) }
               MAX-ACCESS  read-write
               STATUS      current
               DESCRIPTION
                   "Ports in hybrid mode allow for changing the port type,
                    that is, whether a frame's VLAN tag is
                    used to classify the frame on ingress to a particular VLAN,
                    and if so, which TPID it reacts on.
                    Likewise, on egress, the Port Type determines the
                    TPID of the tag, if a tag is required.
                    0: unaware,
                    1: c-Port,
                    2: s-Port,
                    3: s-Custom-Port."
                DEFVAL  { cPort }
               ::= {     lcsVlanEntry 4 }

    lcsVlanIngressFiltering OBJECT-TYPE
               SYNTAX      AdminMode
               MAX-ACCESS  read-write
               STATUS      current
               DESCRIPTION
                   "Hybrid ports allow for changing ingress filtering.
                    Access and Trunk ports always have ingress
                    filtering enabled.If ingress filtering is enabled,
                    frames classified to
                    a VLAN that the port is not a member of get discarded."
               ::= {     lcsVlanEntry 5 }

--    lcsVlanVLANTrunking OBJECT-TYPE
--               SYNTAX      AdminMode
--               MAX-ACCESS  read-write
--               STATUS      current
--               DESCRIPTION
--                   "Trunk and Hybrid ports allow for enabling VLAN trunking.
--                    When VLAN trunking is enabled, frames
--                    classified to unknown VLANs are accepted on the port
--                    whether ingress filtering is enabled or not."
--               DEFVAL  { disable }
--               ::= {     lcsVlanEntry 6 }

    lcsVlanIngressAcceptance OBJECT-TYPE
               SYNTAX      INTEGER  { taggedAndUntagged  ( 0 ),
                                      taggedOnly ( 1 ),
                                      untaggedOnly ( 2 )
                                    }
               MAX-ACCESS  read-write
               STATUS      current
               DESCRIPTION
                   "Hybrid ports allow for changing the type of frames that are
                    accepted on ingress.
                    0: Tagged and Untagged,
                    1: Tagged Only,
                    2: Untagged Only."
               ::= {     lcsVlanEntry 7 }

    lcsVlanEgressTagging OBJECT-TYPE
               SYNTAX      INTEGER  { untagPortVlan  ( 0 ),
                                      tagAll ( 1 ),
                                      untagAll ( 2 )
                                    }
               MAX-ACCESS  read-write
               STATUS      current
               DESCRIPTION
                   "Ports in Trunk and Hybrid mode may control the
                    tagging of frames on egress.
                    0: Untag Port VLAN,
                    1: Tag All,
                    2: Untag All."
               ::= {     lcsVlanEntry 8 }

    lcsVlanAllowedVLANs OBJECT-TYPE
               SYNTAX      DisplayString
               MAX-ACCESS  read-write
               STATUS      current
               DESCRIPTION
                   "Ports in Trunk and Hybrid mode may control which
                    VLANs they are allowed to become members of.
                    Access ports can only be member of one VLAN, the Access VLAN.
                    range: 1~4094.
                    '-': Allowed VLANs is empty."
               ::= {     lcsVlanEntry 9 }

    lcsVlanForbiddenVLANs OBJECT-TYPE
               SYNTAX      DisplayString
               MAX-ACCESS  read-write
               STATUS      current
               DESCRIPTION
                   "A port may be configured to never be member of one or
                    more VLANs. This is particularly useful
                    when dynamic VLAN protocols like MVRP and GVRP
                    must be prevented from dynamically adding ports
                    to VLANs.
                    range: 1~4094.
                    '-': Forbidden VLANs is empty."
               ::= {     lcsVlanEntry 10 }

--lcsVLANMembershipStatusTable

    lcsVLANMembershipStatusTable OBJECT-TYPE
               SYNTAX      SEQUENCE OF     LCSVLANMembershipStatusEntry
               MAX-ACCESS  not-accessible
               STATUS      current
               DESCRIPTION
                   "Vlan membership Status table.
                    INDEX for this table is ifIndex which is
                    equivalent to the panel port number."
               ::= {     lcsVlanStatus 1 }

    lcsVLANMembershipStatusEntry OBJECT-TYPE
               SYNTAX          LCSVLANMembershipStatusEntry
               MAX-ACCESS  not-accessible
               STATUS      current
               DESCRIPTION
                   "Vlan membership Status entry."
               INDEX    {     ifIndex, lcsVLANMembershipVlanID    }
               ::= {     lcsVLANMembershipStatusTable 1 }

    LCSVLANMembershipStatusEntry             ::= SEQUENCE {
                lcsVLANMembershipVlanID      Integer32,
                lcsVLANMembershipStatus      INTEGER
                }

    lcsVLANMembershipVlanID OBJECT-TYPE
               SYNTAX      Integer32(1..4094)
               MAX-ACCESS  not-accessible
               STATUS      current
               DESCRIPTION
                   "VLAN ID for which the Port members are displayed."
               ::= {     lcsVLANMembershipStatusEntry 2 }

    lcsVLANMembershipStatus OBJECT-TYPE
               SYNTAX      INTEGER  { portIsNotInVlan  ( 0 ),
                                      portIncludedInVlan ( 1 ),
                                      portInForbiddenPortList( 2 ),
                                      portInForbiddenPortListAndVlan( 3 )
                                    }
               MAX-ACCESS  read-only
               STATUS      current
               DESCRIPTION
                   "portIsNotInVlan(0): A port is nothing in a VLAN.
                    portIncludedInVlan(1): A port is included in a VLAN.
                    portInForbiddenPortList(2): A port is in the forbidden port list.
                    portInForbiddenPortListAndVlan(3):
                     A port is in the forbidden port list and at the same
                     time attempted included in the VLAN."
               ::= {     lcsVLANMembershipStatusEntry 3 }

--lcsVLANPortStatusTable
    lcsVLANPortStatusTable OBJECT-TYPE
               SYNTAX      SEQUENCE OF     LCSVLANPortStatusEntry
               MAX-ACCESS  not-accessible
               STATUS      current
               DESCRIPTION
                   "The vlan port status table.
                    INDEX for this table is ifIndex which is
                    equivalent to the panel port number."
               ::= {     lcsVlanStatus 2 }

    lcsVLANPortStatusEntry OBJECT-TYPE
               SYNTAX          LCSVLANPortStatusEntry
               MAX-ACCESS  not-accessible
               STATUS      current
               DESCRIPTION
                   "The vlan port status entry."
               INDEX    {     ifIndex }
               ::= {     lcsVLANPortStatusTable 1 }

    LCSVLANPortStatusEntry             ::= SEQUENCE {
                lcsVLANPortStatusPortType          DisplayString,
                lcsVLANPortStatusIngressFiltering  AdminMode,
                lcsVLANPortStatusFrameType         DisplayString,
                lcsVLANPortStatusPortVLANID        Integer32,
                lcsVLANPortStatusTxTag             DisplayString,
                lcsVLANPortStatusUntaggedVLANID    Integer32,
                lcsVLANPortStatusConflicts         DisplayString
                }

    lcsVLANPortStatusPortType OBJECT-TYPE
               SYNTAX      DisplayString
               MAX-ACCESS  read-only
               STATUS      current
               DESCRIPTION
                   "Shows the port type (Unaware, C-Port, S-Port,
                    S-Custom-Port.) that a given user wants to configure on
                    the port.The field is empty if not overridden by the selected user."
               ::= {     lcsVLANPortStatusEntry 2 }

    lcsVLANPortStatusIngressFiltering OBJECT-TYPE
               SYNTAX      AdminMode
               MAX-ACCESS  read-only
               STATUS      current
               DESCRIPTION
                   "Shows whether a given user wants ingress filtering enabled or not."
               ::= {     lcsVLANPortStatusEntry 3 }

    lcsVLANPortStatusFrameType OBJECT-TYPE
               SYNTAX      DisplayString
               MAX-ACCESS  read-only
               STATUS      current
               DESCRIPTION
                   "Shows the acceptable frame types (All, Taged,
                    Untagged) that a given user wants to configure on the port.
                    The field is empty if not overridden by the selected user."
               ::= {     lcsVLANPortStatusEntry 4 }

    lcsVLANPortStatusPortVLANID OBJECT-TYPE
               SYNTAX      Integer32 (1..4094)
               MAX-ACCESS  read-only
               STATUS      current
               DESCRIPTION
                   "Shows the Port VLAN ID (PVID) that a given user
                    wants the port to have.
                    The field is 0 if not overridden by the selected user."
               ::= {     lcsVLANPortStatusEntry 5 }

    lcsVLANPortStatusTxTag OBJECT-TYPE
               SYNTAX      DisplayString
               MAX-ACCESS  read-only
               STATUS      current
               DESCRIPTION
                   "Shows the Tx Tag requirements (Tag All, Tag PVID,
                    Tag UVID, Untag All, Untag PVID, Untag UVID)
                    that a given user has on a port.The field is empty
                    if not overridden by the selected user."
               ::= {     lcsVLANPortStatusEntry 6 }

    lcsVLANPortStatusUntaggedVLANID OBJECT-TYPE
               SYNTAX      Integer32(1..4094)
               MAX-ACCESS  read-only
               STATUS      current
               DESCRIPTION
                   "If Tx Tag is overridden by the selected user and is
                    set to Tag or Untag UVID, then this field will show
                    the VLAN ID the user wants to tag or untag on egress.
                    The field is 0 if not overridden by the selected
                    user."
               ::= {     lcsVLANPortStatusEntry 7 }

    lcsVLANPortStatusConflicts OBJECT-TYPE
               SYNTAX      DisplayString
               MAX-ACCESS  read-only
               STATUS      current
               DESCRIPTION
                   "Two users may have conflicting requirements to a port's
                    configuration. For instance, one user may require
                    all frames to be tagged on egress while another requires
                    all frames to be untagged on egress.Since both
                    users cannot win, this gives rise to a conflict,
                    which is solved in a prioritized way. The Administrator
                    has the least priority. Other software modules are
                    prioritized according to their position in the drop-down
                    list: The higher in the list, the higher priority.
                    If conflicts exist, it will be displayed as 'Yes'."
               ::= {     lcsVLANPortStatusEntry 8 }
               
lcsMacBaesdVlanMembershipConfig     OBJECT IDENTIFIER   ::= { lcsVLAN 7 }
               
lcsMacBaesdVlanMembershipConfigTable  OBJECT-TYPE
   SYNTAX      SEQUENCE OF LCSMacBaesdVlanMembershipConfigEntry
   MAX-ACCESS  not-accessible
   STATUS      current
   DESCRIPTION
       "Mac-Based VLAN Membership table"
 ::= { lcsMacBaesdVlanMembershipConfig 1 }

lcsMacBaesdVlanMembershipConfigEntry OBJECT-TYPE
    SYNTAX        LCSMacBaesdVlanMembershipConfigEntry
    MAX-ACCESS    not-accessible
    STATUS        current
    DESCRIPTION
        "Mac-Based VLAN Membership table."
    INDEX        { lcsMacBaesdVlanMembershipConfigIndex }
    ::= { lcsMacBaesdVlanMembershipConfigTable 1 }

LCSMacBaesdVlanMembershipConfigEntry ::=
    SEQUENCE {
        lcsMacBaesdVlanMembershipConfigIndex        Integer32,
        lcsMacBaesdVlanMembershipConfigMACAddress   DisplayString,
        lcsMacBaesdVlanMembershipConfigVLANID       Integer32,
        lcsMacBaesdVlanMembershipConfigPortMembers  DisplayString,
        lcsMacBaesdVlanMembershipConfigRowStatus    RowStatus
    }
    
lcsMacBaesdVlanMembershipConfigIndex OBJECT-TYPE
   SYNTAX      Integer32 (1..65535)
   MAX-ACCESS  not-accessible
   STATUS      current
   DESCRIPTION
       "Mac-Based VLAN membership index."
   ::= {lcsMacBaesdVlanMembershipConfigEntry 1 }    
    
lcsMacBaesdVlanMembershipConfigMACAddress OBJECT-TYPE
   SYNTAX      DisplayString
   MAX-ACCESS  read-create
   STATUS      current
   DESCRIPTION
       "MAC address: xx-xx-xx-xx-xx-xx."
   ::= {lcsMacBaesdVlanMembershipConfigEntry 2 }    
    
lcsMacBaesdVlanMembershipConfigVLANID OBJECT-TYPE
   SYNTAX      Integer32
   MAX-ACCESS  read-create
   STATUS      current
   DESCRIPTION
       "VLAN ID"
   ::= {lcsMacBaesdVlanMembershipConfigEntry 3 }

lcsMacBaesdVlanMembershipConfigPortMembers OBJECT-TYPE
   SYNTAX      DisplayString
   MAX-ACCESS  read-create
   STATUS      current
   DESCRIPTION
       "0:remove or exclude the port from the mapping
        1:include a port in the mapping"
   ::= {lcsMacBaesdVlanMembershipConfigEntry 4 } 

lcsMacBaesdVlanMembershipConfigRowStatus OBJECT-TYPE
   SYNTAX      RowStatus
   MAX-ACCESS  read-create
   STATUS      current
   DESCRIPTION
       "Row Status."
   ::= {lcsMacBaesdVlanMembershipConfigEntry 5 }     
   
lcsMacBaesdVlanMembershipStatusUser   OBJECT-TYPE
       SYNTAX      Integer32
       MAX-ACCESS  read-write
       STATUS      current
       DESCRIPTION
           "MAC-based VLAN Membership Status User"
       ::= { lcsVLAN 8 } 
               
lcsMacBaesdVlanMembershipStatus     OBJECT IDENTIFIER   ::= { lcsVLAN 9 }
               
lcsMacBaesdVlanMembershipStatusTable  OBJECT-TYPE
   SYNTAX      SEQUENCE OF LCSMacBaesdVlanMembershipStatusEntry
   MAX-ACCESS  not-accessible
   STATUS      current
   DESCRIPTION
       "Mac-Based VLAN Membership table"
 ::= { lcsMacBaesdVlanMembershipStatus 1 }

lcsMacBaesdVlanMembershipStatusEntry OBJECT-TYPE
    SYNTAX        LCSMacBaesdVlanMembershipStatusEntry
    MAX-ACCESS    not-accessible
    STATUS        current
    DESCRIPTION
        "Mac-Based VLAN Membership table."
    INDEX        { lcsMacBaesdVlanMembershipStatusIndex }
    ::= { lcsMacBaesdVlanMembershipStatusTable 1 }

LCSMacBaesdVlanMembershipStatusEntry ::=
    SEQUENCE {
        lcsMacBaesdVlanMembershipStatusIndex        Integer32,
        lcsMacBaesdVlanMembershipStatusMACAddress   DisplayString,
        lcsMacBaesdVlanMembershipStatusVLANID       Integer32,
        lcsMacBaesdVlanMembershipStatusPortMembers  DisplayString
    }
    
lcsMacBaesdVlanMembershipStatusIndex OBJECT-TYPE
   SYNTAX      Integer32 (1..65535)
   MAX-ACCESS  not-accessible
   STATUS      current
   DESCRIPTION
       "Mac-Based VLAN membership index."
   ::= {lcsMacBaesdVlanMembershipStatusEntry 1 }    
    
lcsMacBaesdVlanMembershipStatusMACAddress OBJECT-TYPE
   SYNTAX      DisplayString
   MAX-ACCESS  read-only
   STATUS      current
   DESCRIPTION
       "MAC address: xx-xx-xx-xx-xx-xx."
   ::= {lcsMacBaesdVlanMembershipStatusEntry 2 }    
    
lcsMacBaesdVlanMembershipStatusVLANID OBJECT-TYPE
   SYNTAX      Integer32
   MAX-ACCESS  read-only
   STATUS      current
   DESCRIPTION
       "VLAN ID"
   ::= {lcsMacBaesdVlanMembershipStatusEntry 3 }

lcsMacBaesdVlanMembershipStatusPortMembers OBJECT-TYPE
   SYNTAX      DisplayString
   MAX-ACCESS  read-only
   STATUS      current
   DESCRIPTION
       "0:remove or exclude the port from the mapping
        1:include a port in the mapping"
   ::= {lcsMacBaesdVlanMembershipStatusEntry 4 }                

lcsProtocolbasedVLANConfig     OBJECT IDENTIFIER   ::= { lcsVLAN 10 }
               
lcsProtocolbasedVLANConfigTable  OBJECT-TYPE
   SYNTAX      SEQUENCE OF LCSProtocolbasedVLANConfigEntry
   MAX-ACCESS  not-accessible
   STATUS      current
   DESCRIPTION
       "Protocol-based VLAN Config table"
 ::= { lcsProtocolbasedVLANConfig 1 }

lcsProtocolbasedVLANConfigEntry OBJECT-TYPE
    SYNTAX        LCSProtocolbasedVLANConfigEntry
    MAX-ACCESS    not-accessible
    STATUS        current
    DESCRIPTION
        "Protocol-based VLAN Config table"
    INDEX        { lcsProtocolbasedVLANConfigIndex }
    ::= { lcsProtocolbasedVLANConfigTable 1 }

LCSProtocolbasedVLANConfigEntry ::=
    SEQUENCE {
        lcsProtocolbasedVLANConfigIndex               Integer32,
        lcsProtocolbasedVLANConfigFrameType           Integer32,
        lcsProtocolbasedVLANConfigValueEthernetEtype  DisplayString,
        lcsProtocolbasedVLANConfigValueSNAPOUI        DisplayString,
        lcsProtocolbasedVLANConfigValueSNAPPID        DisplayString,
        lcsProtocolbasedVLANConfigValueLLCDSAP        DisplayString,
        lcsProtocolbasedVLANConfigValueLLCSSAP        DisplayString,
        lcsProtocolbasedVLANConfigGroupName           DisplayString,
        lcsProtocolbasedVLANConfigRowStatus           RowStatus
    }
    
lcsProtocolbasedVLANConfigIndex OBJECT-TYPE
   SYNTAX      Integer32 (1..65535)
   MAX-ACCESS  not-accessible
   STATUS      current
   DESCRIPTION
       "Protocol-based VLAN Config index."
   ::= {lcsProtocolbasedVLANConfigEntry 1 }    
    
lcsProtocolbasedVLANConfigFrameType OBJECT-TYPE
   SYNTAX      Integer32
   MAX-ACCESS  read-create
   STATUS      current
   DESCRIPTION
       "Frame Type.
       1:Ethernet
       2:LLC
       3:SNAP"
   ::= {lcsProtocolbasedVLANConfigEntry 2 }    
    
    
lcsProtocolbasedVLANConfigValueEthernetEtype OBJECT-TYPE
   SYNTAX      DisplayString
   MAX-ACCESS  read-create
   STATUS      current
   DESCRIPTION
       "Ethernet Etype.
       Valid values for etype range between 0x0600 and 0xffff "
   ::= {lcsProtocolbasedVLANConfigEntry 3 }    
    
lcsProtocolbasedVLANConfigValueSNAPOUI OBJECT-TYPE
   SYNTAX      DisplayString
   MAX-ACCESS  read-create
   STATUS      current
   DESCRIPTION
       "SNAP OUI.
       Format:xx-xx-xx"
   ::= {lcsProtocolbasedVLANConfigEntry 4 }  

lcsProtocolbasedVLANConfigValueSNAPPID OBJECT-TYPE
   SYNTAX      DisplayString
   MAX-ACCESS  read-create
   STATUS      current
   DESCRIPTION
       "SNAP PID
       Ranging between 0x00 and 0xff."
   ::= {lcsProtocolbasedVLANConfigEntry 5 }    

lcsProtocolbasedVLANConfigValueLLCDSAP OBJECT-TYPE
   SYNTAX      DisplayString
   MAX-ACCESS  read-create
   STATUS      current
   DESCRIPTION
       "LLC DSAP.
       Range: 0x00-0xff"
   ::= {lcsProtocolbasedVLANConfigEntry 6 }   

lcsProtocolbasedVLANConfigValueLLCSSAP OBJECT-TYPE
   SYNTAX      DisplayString
   MAX-ACCESS  read-create
   STATUS      current
   DESCRIPTION
       "LLC SSAP.
       Range: 0x00-0xff"
   ::= {lcsProtocolbasedVLANConfigEntry 7 }   
   
lcsProtocolbasedVLANConfigGroupName OBJECT-TYPE
   SYNTAX      DisplayString
   MAX-ACCESS  read-create
   STATUS      current
   DESCRIPTION
       "Group Name
        16-character long string, unique for every entry, which consists of a combination of alphabets (a-z or A-Z) and integers(0-9)."
   ::= {lcsProtocolbasedVLANConfigEntry 8 }     

lcsProtocolbasedVLANConfigRowStatus OBJECT-TYPE
   SYNTAX      RowStatus
   MAX-ACCESS  read-create
   STATUS      current
   DESCRIPTION
       "Row Status."
   ::= {lcsProtocolbasedVLANConfigEntry 9 } 
               
               
               
lcsGroupNameToVLANMappingConfigTable  OBJECT-TYPE
   SYNTAX      SEQUENCE OF LCSGroupNameToVLANMappingConfigEntry
   MAX-ACCESS  not-accessible
   STATUS      current
   DESCRIPTION
       "Group Name To VLAN Mapping Config table"
 ::= { lcsProtocolbasedVLANConfig 2 }

lcsGroupNameToVLANMappingConfigEntry OBJECT-TYPE
    SYNTAX        LCSGroupNameToVLANMappingConfigEntry
    MAX-ACCESS    not-accessible
    STATUS        current
    DESCRIPTION
        "Group Name To VLAN Mapping Config table."
    INDEX        { lcsGroupNameToVLANMappingConfigIndex }
    ::= { lcsGroupNameToVLANMappingConfigTable 1 }

LCSGroupNameToVLANMappingConfigEntry ::=
    SEQUENCE {
        lcsGroupNameToVLANMappingConfigIndex        Integer32,
        lcsGroupNameToVLANMappingConfigGroupName    DisplayString,
        lcsGroupNameToVLANMappingConfigVLANID       Integer32,
        lcsGroupNameToVLANMappingConfigPortMembers  DisplayString,
        lcsGroupNameToVLANMappingConfigRowStatus    RowStatus
    }
    
lcsGroupNameToVLANMappingConfigIndex OBJECT-TYPE
   SYNTAX      Integer32 (1..65535)
   MAX-ACCESS  not-accessible
   STATUS      current
   DESCRIPTION
       "Group Name To VLAN Mapping Config index."
   ::= {lcsGroupNameToVLANMappingConfigEntry 1 }    
    
lcsGroupNameToVLANMappingConfigGroupName OBJECT-TYPE
   SYNTAX      DisplayString
   MAX-ACCESS  read-create
   STATUS      current
   DESCRIPTION
       "Group Name
        16-character long string, unique for every entry, which consists of a combination of alphabets (a-z or A-Z) and integers(0-9)."
   ::= {lcsGroupNameToVLANMappingConfigEntry 2 }    
    
lcsGroupNameToVLANMappingConfigVLANID OBJECT-TYPE
   SYNTAX      Integer32
   MAX-ACCESS  read-create
   STATUS      current
   DESCRIPTION
       "VLAN ID"
   ::= {lcsGroupNameToVLANMappingConfigEntry 3 }

lcsGroupNameToVLANMappingConfigPortMembers OBJECT-TYPE
   SYNTAX      DisplayString
   MAX-ACCESS  read-create
   STATUS      current
   DESCRIPTION
       "0:remove or exclude the port from the mapping
        1:include a port in the mapping"
   ::= {lcsGroupNameToVLANMappingConfigEntry 4 } 

lcsGroupNameToVLANMappingConfigRowStatus OBJECT-TYPE
   SYNTAX      RowStatus
   MAX-ACCESS  read-create
   STATUS      current
   DESCRIPTION
       "Row Status."
   ::= {lcsGroupNameToVLANMappingConfigEntry 5 }     
               
lcsIPSubnetBasedVLANConfig     OBJECT IDENTIFIER   ::= { lcsVLAN 11 }
               
lcsIPSubnetBasedVLANConfigTable  OBJECT-TYPE
   SYNTAX      SEQUENCE OF LCSIPSubnetBasedVLANConfigEntry
   MAX-ACCESS  not-accessible
   STATUS      current
   DESCRIPTION
       "IP Subnet Based VLAN Config table"
 ::= { lcsIPSubnetBasedVLANConfig 1 }

lcsIPSubnetBasedVLANConfigEntry OBJECT-TYPE
    SYNTAX        LCSIPSubnetBasedVLANConfigEntry
    MAX-ACCESS    not-accessible
    STATUS        current
    DESCRIPTION
        "IP Subnet Based VLAN Config table."
    INDEX        { lcsIPSubnetBasedVLANConfigIndex }
    ::= { lcsIPSubnetBasedVLANConfigTable 1 }

LCSIPSubnetBasedVLANConfigEntry ::=
    SEQUENCE {
        lcsIPSubnetBasedVLANConfigIndex        Integer32,
        lcsIPSubnetBasedVLANConfigIPAddress    IpAddress,
        lcsIPSubnetBasedVLANConfigMaskLength   Integer32,
        lcsIPSubnetBasedVLANConfigGroupName    DisplayString,
        lcsIPSubnetBasedVLANConfigVLANID       Integer32,
        lcsIPSubnetBasedVLANConfigPortMembers  DisplayString,
        lcsIPSubnetBasedVLANConfigRowStatus    RowStatus
    }
    
lcsIPSubnetBasedVLANConfigIndex OBJECT-TYPE
   SYNTAX      Integer32 (1..65535)
   MAX-ACCESS  not-accessible
   STATUS      current
   DESCRIPTION
       "IP Subnet Based VLAN Config index."
   ::= {lcsIPSubnetBasedVLANConfigEntry 1 }    
    
lcsIPSubnetBasedVLANConfigIPAddress OBJECT-TYPE
   SYNTAX      IpAddress
   MAX-ACCESS  read-create
   STATUS      current
   DESCRIPTION
       "The subnet's IP address"
   ::= {lcsIPSubnetBasedVLANConfigEntry 2 }    
    
lcsIPSubnetBasedVLANConfigMaskLength OBJECT-TYPE
   SYNTAX      Integer32
   MAX-ACCESS  read-create
   STATUS      current
   DESCRIPTION
       "The subnet's mask length. "
   ::= {lcsIPSubnetBasedVLANConfigEntry 3 }
    
lcsIPSubnetBasedVLANConfigVLANID OBJECT-TYPE
   SYNTAX      Integer32
   MAX-ACCESS  read-create
   STATUS      current
   DESCRIPTION
       "VLAN ID"
   ::= {lcsIPSubnetBasedVLANConfigEntry 4 }

lcsIPSubnetBasedVLANConfigPortMembers OBJECT-TYPE
   SYNTAX      DisplayString
   MAX-ACCESS  read-create
   STATUS      current
   DESCRIPTION
       "0:remove or exclude the port from the mapping
        1:include a port in the mapping"
   ::= {lcsIPSubnetBasedVLANConfigEntry 5 } 

lcsIPSubnetBasedVLANConfigRowStatus OBJECT-TYPE
   SYNTAX      RowStatus
   MAX-ACCESS  read-create
   STATUS      current
   DESCRIPTION
       "Row Status."
   ::= {lcsIPSubnetBasedVLANConfigEntry 6 }    
               
lcsVLANNameConfig     OBJECT IDENTIFIER   ::= { lcsVLAN 12 }
               
lcsVLANNameConfigTable  OBJECT-TYPE
   SYNTAX      SEQUENCE OF LCSVLANNameConfigEntry
   MAX-ACCESS  not-accessible
   STATUS      current
   DESCRIPTION
       "VLAN Name Config table"
 ::= { lcsVLANNameConfig 1 }

lcsVLANNameConfigEntry OBJECT-TYPE
    SYNTAX        LCSVLANNameConfigEntry
    MAX-ACCESS    not-accessible
    STATUS        current
    DESCRIPTION
        "VLAN Name Config table."
    INDEX        { lcsVLANNameConfigIndex }
    ::= { lcsVLANNameConfigTable 1 }

LCSVLANNameConfigEntry ::=
    SEQUENCE {
        lcsVLANNameConfigIndex        Integer32,
        lcsVLANNameConfigVLANName     DisplayString
    }
    
lcsVLANNameConfigIndex OBJECT-TYPE
   SYNTAX      Integer32 (1..4094)
   MAX-ACCESS  not-accessible
   STATUS      current
   DESCRIPTION
       "VLAN Name Config index."
   ::= {lcsVLANNameConfigEntry 1 }    
    
lcsVLANNameConfigVLANName OBJECT-TYPE
   SYNTAX      DisplayString
   MAX-ACCESS  read-write
   STATUS      current
   DESCRIPTION
       "VLAN Name."
   ::= {lcsVLANNameConfigEntry 2 } 
               
               
lcsNTPConf   OBJECT IDENTIFIER ::= { lcsSystem 12 }

lcsNTPConfigMode OBJECT-TYPE
           SYNTAX       INTEGER {useLocal(0),useNTP(1)}
           MAX-ACCESS   read-write
           STATUS       current
           DESCRIPTION
               "The system NTP Mode.
                useLocal(0) : Use Local Settings,
                useNTP(1)   : Use NTP Server."
           DEFVAL  { useLocal }
           ::= {     lcsNTPConf 1 }

--lcsNTPConfigAutomatic   OBJECT-TYPE
--               SYNTAX      Integer32 (0|1)
--               MAX-ACCESS  read-write
--               STATUS      current
--               DESCRIPTION
--                   "Indicates the Automatic mode operation. Possible modes are:
--                   0:Disable, NTP servers available from the config. 
--                   1:Enable, NTP servers available from the DHCP."
--               ::= { lcsNTPConf 2 }
               
lcsNTPConfigTimeSyncInterval   OBJECT-TYPE
               SYNTAX      Integer32 (5|10|15|30|60|120)
               MAX-ACCESS  read-write
               STATUS      current
               DESCRIPTION
                   "Time-Sync Interval.
                   Valid values are restricted to 5,10,15,30,60,120 minutes. "
               ::= { lcsNTPConf 3 }   

lcsNTPConfigServerAddress1   OBJECT-TYPE
               SYNTAX      DisplayString
               MAX-ACCESS  read-write
               STATUS      current
               DESCRIPTION
                   "Provide the IPv4 or IPv6 address of a NTP server."
               ::= { lcsNTPConf 4 }   

lcsNTPConfigServerAddress2   OBJECT-TYPE
               SYNTAX      DisplayString
               MAX-ACCESS  read-write
               STATUS      current
               DESCRIPTION
                   "Provide the IPv4 or IPv6 address of a NTP server."
               ::= { lcsNTPConf 5 }                
        
lcsNTPConfigServerAddress3   OBJECT-TYPE
               SYNTAX      DisplayString
               MAX-ACCESS  read-write
               STATUS      current
               DESCRIPTION
                   "Provide the IPv4 or IPv6 address of a NTP server."
               ::= { lcsNTPConf 6 }          
               
lcsNTPConfigServerAddress4   OBJECT-TYPE
               SYNTAX      DisplayString
               MAX-ACCESS  read-write
               STATUS      current
               DESCRIPTION
                   "Provide the IPv4 or IPv6 address of a NTP server."
               ::= { lcsNTPConf 7 }                    
    
lcsNTPConfigServerAddress5   OBJECT-TYPE
               SYNTAX      DisplayString
               MAX-ACCESS  read-write
               STATUS      current
               DESCRIPTION
                   "Provide the IPv4 or IPv6 address of a NTP server."
               ::= { lcsNTPConf 8 }  


-- =======================================================================================================================
-- {NODE} 1.3.6.1.4.1.2356.14.2
lcsConfiguration                                        OBJECT IDENTIFIER ::= { lcosSX 2 }

lcsPort                                                  OBJECT IDENTIFIER ::= { lcsConfiguration 1 }

lcsPortConfigurationTable OBJECT-TYPE
   SYNTAX      SEQUENCE OF LCSPortConfigurationEntry
   MAX-ACCESS  not-accessible
   STATUS      current
   DESCRIPTION
       " Show port configurations. "
   ::= { lcsPort 1 }

lcsPortConfigurationEntry OBJECT-TYPE
   SYNTAX      LCSPortConfigurationEntry
   MAX-ACCESS  not-accessible
   STATUS      current
   DESCRIPTION
       " "
   INDEX    { lcsPortConfPort  }
   ::= { lcsPortConfigurationTable 1 }

LCSPortConfigurationEntry ::= SEQUENCE {
   lcsPortConfPort                     Integer32,
   lcsPortConfDescription              DisplayString,
   lcsPortConfLink                     DisplayString,
   lcsPortConfSpeedStatus              DisplayString,
   lcsPortConfSpeedMode                Integer32,
   lcsPortConfFlowControlRxStatus      Integer32,
   lcsPortConfFlowControlTxStatus      Integer32,
   lcsPortConfFlowControlMode          Integer32,
   lcsPortConfMaximumFrameSize         Integer32
-- lcsPortConfExcessiveCollisionMode   Integer32,
-- lcsPortConfPowerControl             Integer32,
-- lcsPortConfPortMedia                DisplayString
}

lcsPortConfPort OBJECT-TYPE
   SYNTAX      Integer32 (1..4094)
   MAX-ACCESS  not-accessible
   STATUS      current
   DESCRIPTION
       " port, range : 1 - port number. "
   ::= { lcsPortConfigurationEntry 1 }

lcsPortConfDescription OBJECT-TYPE
   SYNTAX      DisplayString
   MAX-ACCESS  read-write
   STATUS      current
   DESCRIPTION
       " Interface specific description.
         Up to 47 characters describing this interface. "
   ::= { lcsPortConfigurationEntry 2 }

lcsPortConfLink OBJECT-TYPE
   SYNTAX      DisplayString(SIZE (2..4))
   MAX-ACCESS  read-only
   STATUS      current
   DESCRIPTION
       " The current link state. "
   ::= { lcsPortConfigurationEntry 3 }

lcsPortConfSpeedStatus OBJECT-TYPE
   SYNTAX      DisplayString(SIZE (6..12))
   MAX-ACCESS  read-only
   STATUS      current
   DESCRIPTION
       " The current link speed of the port. "
   ::= { lcsPortConfigurationEntry 4 }

lcsPortConfSpeedMode OBJECT-TYPE
   SYNTAX      Integer32 (0..19)
   MAX-ACCESS  read-write
   STATUS      current
   DESCRIPTION
       "0: disable state,
        1: auto,
        2: 10 Half,
        3: 10 Full,
        4: 100 Half,
        5: 100 Full,
        6: 1G full,
        7: SFP_Auto_AMS,
        8: 100FX_AMS,
        9: 1000X_AMS,
        10: 100-FX,
        11: 1000-X,
        12: 10G Full,
        13: Auto (2.5G/1G),
        14: Auto (2.5G/100M),
        15: Auto (2.5G),
        16: Auto (1G/100M),
        17: Auto (1G),
        18: Auto (100M),
        19: 2.5G Full."
   ::= { lcsPortConfigurationEntry 5 }

lcsPortConfFlowControlRxStatus OBJECT-TYPE
   SYNTAX      Integer32 (0|1)
   MAX-ACCESS  read-only
   STATUS      current
   DESCRIPTION
       "0: disable
        1: enable
        2: not support.  "
   ::= { lcsPortConfigurationEntry 6 }

lcsPortConfFlowControlTxStatus OBJECT-TYPE
   SYNTAX      Integer32 (0|1)
   MAX-ACCESS  read-only
   STATUS      current
   DESCRIPTION
       "0: disable
        1: enable
        2: not support.  "
   ::= { lcsPortConfigurationEntry 7 }

lcsPortConfFlowControlMode OBJECT-TYPE
   SYNTAX      Integer32 (0|1)
   MAX-ACCESS  read-write
   STATUS      current
   DESCRIPTION
       "default: 0,
        0: disable
        1: enable
        2: not support. "
   ::= { lcsPortConfigurationEntry 8 }

lcsPortConfMaximumFrameSize OBJECT-TYPE
   SYNTAX      Integer32 (1518..10240)
   MAX-ACCESS  read-write
   STATUS      current
   DESCRIPTION
       "default: 10240 , range : 1518 - 10240 "
   ::= { lcsPortConfigurationEntry 9 }

--lcsPortConfExcessiveCollisionMode OBJECT-TYPE
--   SYNTAX      Integer32 (0|1)
--   MAX-ACCESS  read-write
--   STATUS      current
--   DESCRIPTION
--       "default: 0,
--        Excessive Collision Mode :
--        0: Discard,
--        1: Restart,
--        2: not support.
--       "
--   ::= { lcsPortConfigurationEntry 10 }

--lcsPortConfPowerControl OBJECT-TYPE
--   SYNTAX      Integer32 (0..3)
--   MAX-ACCESS  read-write
--   STATUS      current
--   DESCRIPTION
--       "default: 0,
--        PowerControl :
--        0: disable,
--        1: Actiphy,
--        2: Dynamic (perfectReach),
--        3: Enable,
--        4: not support.
--       "
--   ::= { lcsPortConfigurationEntry 11 }

--lcsPortConfPortMedia OBJECT-TYPE
--   SYNTAX      DisplayString(SIZE (1..4))
--   MAX-ACCESS  read-only
--   STATUS      current
--   DESCRIPTION
--       " Show port media. "
--   ::= { lcsPortConfigurationEntry 12 } 
   

lcsPortTrafficStatisticsTable OBJECT-TYPE
   SYNTAX      SEQUENCE OF LCSPortTrafficStatisticsEntry
   MAX-ACCESS  not-accessible
   STATUS      current
   DESCRIPTION
       " "
   ::= { lcsPort 2 }

lcsPortTrafficStatisticsEntry OBJECT-TYPE
   SYNTAX      LCSPortTrafficStatisticsEntry
   MAX-ACCESS  not-accessible
   STATUS      current
   DESCRIPTION
       " "
   INDEX    { lcsPortTrafficStatisticsPort  }
   ::= { lcsPortTrafficStatisticsTable 1 }

LCSPortTrafficStatisticsEntry ::= SEQUENCE {
   lcsPortTrafficStatisticsPort          Integer32,
   lcsPortTrafficStatisticsClear         Integer32,
   lcsPortTrafficRxPackets               Counter64,
   lcsPortTrafficRxOctets                Counter64,
   lcsPortTrafficRxUnicast               Counter64,
   lcsPortTrafficRxMulticast             Counter64,
   lcsPortTrafficRxBroadcast             Counter64,
   lcsPortTrafficRxPause                 Counter64,
   lcsPortTrafficRx64Bytes               Counter64,
   lcsPortTrafficRx65to127Bytes          Counter64,
   lcsPortTrafficRx128to255Bytes         Counter64,
   lcsPortTrafficRx256to511Bytes         Counter64,
   lcsPortTrafficRx512to1023Bytes        Counter64,
   lcsPortTrafficRx1024to1526Bytes       Counter64,
   lcsPortTrafficRxExceecd1527Bytes      Counter64,
   lcsPortTrafficRxQ0                    Counter64,
   lcsPortTrafficRxQ1                    Counter64,
   lcsPortTrafficRxQ2                    Counter64,
   lcsPortTrafficRxQ3                    Counter64,
   lcsPortTrafficRxQ4                    Counter64,
   lcsPortTrafficRxQ5                    Counter64,
   lcsPortTrafficRxQ6                    Counter64,
   lcsPortTrafficRxQ7                    Counter64,
   lcsPortTrafficRxDrops                 Counter64,
   lcsPortTrafficRxCRCorAlignment        Counter64,
   lcsPortTrafficRxUndersize             Counter64,
   lcsPortTrafficRxOversize              Counter64,
   lcsPortTrafficRxFragments             Counter64,
   lcsPortTrafficRxJabber                Counter64,
   lcsPortTrafficRxFiltered              Counter64,
   lcsPortTrafficTxPackets               Counter64,
   lcsPortTrafficTxOctets                Counter64,
   lcsPortTrafficTxUnicast               Counter64,
   lcsPortTrafficTxMulticast             Counter64,
   lcsPortTrafficTxBroadcast             Counter64,
   lcsPortTrafficTxPause                 Counter64,
   lcsPortTrafficTx64Bytes               Counter64,
   lcsPortTrafficTx65to127Bytes          Counter64,
   lcsPortTrafficTx128to255Bytes         Counter64,
   lcsPortTrafficTx256to511Bytes         Counter64,
   lcsPortTrafficTx512to1023Bytes        Counter64,
   lcsPortTrafficTx1024to1526Bytes       Counter64,
   lcsPortTrafficTxExceecd1527Bytes      Counter64,
   lcsPortTrafficTxQ0                    Counter64,
   lcsPortTrafficTxQ1                    Counter64,
   lcsPortTrafficTxQ2                    Counter64,
   lcsPortTrafficTxQ3                    Counter64,
   lcsPortTrafficTxQ4                    Counter64,
   lcsPortTrafficTxQ5                    Counter64,
   lcsPortTrafficTxQ6                    Counter64,
   lcsPortTrafficTxQ7                    Counter64,
   lcsPortTrafficTxDrops                 Counter64,
   lcsPortTrafficTxLateOrExcColl         Counter64
}

lcsPortTrafficStatisticsPort OBJECT-TYPE
   SYNTAX      Integer32 (1..4094)
   MAX-ACCESS  not-accessible
   STATUS      current
   DESCRIPTION
       " "
   ::= { lcsPortTrafficStatisticsEntry 1 }

lcsPortTrafficStatisticsClear OBJECT-TYPE
   SYNTAX      Integer32(0|1)
   MAX-ACCESS  read-write
   STATUS      current
   DESCRIPTION
       " "
   ::= { lcsPortTrafficStatisticsEntry 2 }

lcsPortTrafficRxPackets OBJECT-TYPE
   SYNTAX      Counter64
   MAX-ACCESS  read-only
   STATUS      current
   DESCRIPTION
       " "
   ::= { lcsPortTrafficStatisticsEntry 3 }

lcsPortTrafficRxOctets OBJECT-TYPE
   SYNTAX      Counter64
   MAX-ACCESS  read-only
   STATUS      current
   DESCRIPTION
       " "
   ::= { lcsPortTrafficStatisticsEntry 4 }

lcsPortTrafficRxUnicast OBJECT-TYPE
   SYNTAX      Counter64
   MAX-ACCESS  read-only
   STATUS      current
   DESCRIPTION
       " "
   ::= { lcsPortTrafficStatisticsEntry 5 }

lcsPortTrafficRxMulticast OBJECT-TYPE
   SYNTAX      Counter64
   MAX-ACCESS  read-only
   STATUS      current
   DESCRIPTION
       " "
   ::= { lcsPortTrafficStatisticsEntry 6 }

lcsPortTrafficRxBroadcast OBJECT-TYPE
   SYNTAX      Counter64
   MAX-ACCESS  read-only
   STATUS      current
   DESCRIPTION
       " "
   ::= { lcsPortTrafficStatisticsEntry 7 }

lcsPortTrafficRxPause OBJECT-TYPE
   SYNTAX      Counter64
   MAX-ACCESS  read-only
   STATUS      current
   DESCRIPTION
       " "
   ::= { lcsPortTrafficStatisticsEntry 8 }

lcsPortTrafficRx64Bytes OBJECT-TYPE
   SYNTAX      Counter64
   MAX-ACCESS  read-only
   STATUS      current
   DESCRIPTION
       " "
   ::= { lcsPortTrafficStatisticsEntry 9 }

lcsPortTrafficRx65to127Bytes OBJECT-TYPE
   SYNTAX      Counter64
   MAX-ACCESS  read-only
   STATUS      current
   DESCRIPTION
       " "
   ::= { lcsPortTrafficStatisticsEntry 10 }

lcsPortTrafficRx128to255Bytes OBJECT-TYPE
   SYNTAX      Counter64
   MAX-ACCESS  read-only
   STATUS      current
   DESCRIPTION
       " "
   ::= { lcsPortTrafficStatisticsEntry 11 }

lcsPortTrafficRx256to511Bytes OBJECT-TYPE
   SYNTAX      Counter64
   MAX-ACCESS  read-only
   STATUS      current
   DESCRIPTION
       " "
   ::= { lcsPortTrafficStatisticsEntry 12 }

lcsPortTrafficRx512to1023Bytes OBJECT-TYPE
   SYNTAX      Counter64
   MAX-ACCESS  read-only
   STATUS      current
   DESCRIPTION
       " "
   ::= { lcsPortTrafficStatisticsEntry 13 }

lcsPortTrafficRx1024to1526Bytes OBJECT-TYPE
   SYNTAX      Counter64
   MAX-ACCESS  read-only
   STATUS      current
   DESCRIPTION
       " "
   ::= { lcsPortTrafficStatisticsEntry 14 }

lcsPortTrafficRxExceecd1527Bytes OBJECT-TYPE
   SYNTAX      Counter64
   MAX-ACCESS  read-only
   STATUS      current
   DESCRIPTION
       " "
   ::= { lcsPortTrafficStatisticsEntry 15 }

lcsPortTrafficRxQ0 OBJECT-TYPE
   SYNTAX      Counter64
   MAX-ACCESS  read-only
   STATUS      current
   DESCRIPTION
       " "
   ::= { lcsPortTrafficStatisticsEntry 16 }

lcsPortTrafficRxQ1 OBJECT-TYPE
   SYNTAX      Counter64
   MAX-ACCESS  read-only
   STATUS      current
   DESCRIPTION
       " "
   ::= { lcsPortTrafficStatisticsEntry 17 }

lcsPortTrafficRxQ2 OBJECT-TYPE
   SYNTAX      Counter64
   MAX-ACCESS  read-only
   STATUS      current
   DESCRIPTION
       " "
   ::= { lcsPortTrafficStatisticsEntry 18 }

lcsPortTrafficRxQ3 OBJECT-TYPE
   SYNTAX      Counter64
   MAX-ACCESS  read-only
   STATUS      current
   DESCRIPTION
       " "
   ::= { lcsPortTrafficStatisticsEntry 19 }

lcsPortTrafficRxQ4 OBJECT-TYPE
   SYNTAX      Counter64
   MAX-ACCESS  read-only
   STATUS      current
   DESCRIPTION
       " "
   ::= { lcsPortTrafficStatisticsEntry 20 }

lcsPortTrafficRxQ5 OBJECT-TYPE
   SYNTAX      Counter64
   MAX-ACCESS  read-only
   STATUS      current
   DESCRIPTION
       " "
   ::= { lcsPortTrafficStatisticsEntry 21 }

lcsPortTrafficRxQ6 OBJECT-TYPE
   SYNTAX      Counter64
   MAX-ACCESS  read-only
   STATUS      current
   DESCRIPTION
       " "
   ::= { lcsPortTrafficStatisticsEntry 22 }

lcsPortTrafficRxQ7 OBJECT-TYPE
   SYNTAX      Counter64
   MAX-ACCESS  read-only
   STATUS      current
   DESCRIPTION
       " "
   ::= { lcsPortTrafficStatisticsEntry 23 }

lcsPortTrafficRxDrops OBJECT-TYPE
   SYNTAX      Counter64
   MAX-ACCESS  read-only
   STATUS      current
   DESCRIPTION
       " "
   ::= { lcsPortTrafficStatisticsEntry 24 }

lcsPortTrafficRxCRCorAlignment OBJECT-TYPE
   SYNTAX      Counter64
   MAX-ACCESS  read-only
   STATUS      current
   DESCRIPTION
       " "
   ::= { lcsPortTrafficStatisticsEntry 25 }

lcsPortTrafficRxUndersize OBJECT-TYPE
   SYNTAX      Counter64
   MAX-ACCESS  read-only
   STATUS      current
   DESCRIPTION
       " "
   ::= { lcsPortTrafficStatisticsEntry 26 }

lcsPortTrafficRxOversize OBJECT-TYPE
   SYNTAX      Counter64
   MAX-ACCESS  read-only
   STATUS      current
   DESCRIPTION
       " "
   ::= { lcsPortTrafficStatisticsEntry 27 }

lcsPortTrafficRxFragments OBJECT-TYPE
   SYNTAX      Counter64
   MAX-ACCESS  read-only
   STATUS      current
   DESCRIPTION
       " "
   ::= { lcsPortTrafficStatisticsEntry 28 }

lcsPortTrafficRxJabber OBJECT-TYPE
   SYNTAX      Counter64
   MAX-ACCESS  read-only
   STATUS      current
   DESCRIPTION
       " "
   ::= { lcsPortTrafficStatisticsEntry 29 }

lcsPortTrafficRxFiltered OBJECT-TYPE
   SYNTAX      Counter64
   MAX-ACCESS  read-only
   STATUS      current
   DESCRIPTION
       " "
   ::= { lcsPortTrafficStatisticsEntry 30 }

lcsPortTrafficTxPackets OBJECT-TYPE
   SYNTAX      Counter64
   MAX-ACCESS  read-only
   STATUS      current
   DESCRIPTION
       " "
   ::= { lcsPortTrafficStatisticsEntry 31 }

lcsPortTrafficTxOctets OBJECT-TYPE
   SYNTAX      Counter64
   MAX-ACCESS  read-only
   STATUS      current
   DESCRIPTION
       " "
   ::= { lcsPortTrafficStatisticsEntry 32 }

lcsPortTrafficTxUnicast OBJECT-TYPE
   SYNTAX      Counter64
   MAX-ACCESS  read-only
   STATUS      current
   DESCRIPTION
       " "
   ::= { lcsPortTrafficStatisticsEntry 33 }

lcsPortTrafficTxMulticast OBJECT-TYPE
   SYNTAX      Counter64
   MAX-ACCESS  read-only
   STATUS      current
   DESCRIPTION
       " "
   ::= { lcsPortTrafficStatisticsEntry 34 }

lcsPortTrafficTxBroadcast OBJECT-TYPE
   SYNTAX      Counter64
   MAX-ACCESS  read-only
   STATUS      current
   DESCRIPTION
       " "
   ::= { lcsPortTrafficStatisticsEntry 35 }

lcsPortTrafficTxPause OBJECT-TYPE
   SYNTAX      Counter64
   MAX-ACCESS  read-only
   STATUS      current
   DESCRIPTION
       " "
   ::= { lcsPortTrafficStatisticsEntry 36 }

lcsPortTrafficTx64Bytes OBJECT-TYPE
   SYNTAX      Counter64
   MAX-ACCESS  read-only
   STATUS      current
   DESCRIPTION
       " "
   ::= { lcsPortTrafficStatisticsEntry 37 }

lcsPortTrafficTx65to127Bytes OBJECT-TYPE
   SYNTAX      Counter64
   MAX-ACCESS  read-only
   STATUS      current
   DESCRIPTION
       " "
   ::= { lcsPortTrafficStatisticsEntry 38 }

lcsPortTrafficTx128to255Bytes OBJECT-TYPE
   SYNTAX      Counter64
   MAX-ACCESS  read-only
   STATUS      current
   DESCRIPTION
       " "
   ::= { lcsPortTrafficStatisticsEntry 39 }

lcsPortTrafficTx256to511Bytes OBJECT-TYPE
   SYNTAX      Counter64
   MAX-ACCESS  read-only
   STATUS      current
   DESCRIPTION
       " "
   ::= { lcsPortTrafficStatisticsEntry 40 }

lcsPortTrafficTx512to1023Bytes OBJECT-TYPE
   SYNTAX      Counter64
   MAX-ACCESS  read-only
   STATUS      current
   DESCRIPTION
       " "
   ::= { lcsPortTrafficStatisticsEntry 41 }

lcsPortTrafficTx1024to1526Bytes OBJECT-TYPE
   SYNTAX      Counter64
   MAX-ACCESS  read-only
   STATUS      current
   DESCRIPTION
       " "
   ::= { lcsPortTrafficStatisticsEntry 42 }

lcsPortTrafficTxExceecd1527Bytes OBJECT-TYPE
   SYNTAX      Counter64
   MAX-ACCESS  read-only
   STATUS      current
   DESCRIPTION
       " "
   ::= { lcsPortTrafficStatisticsEntry 43 }

lcsPortTrafficTxQ0 OBJECT-TYPE
   SYNTAX      Counter64
   MAX-ACCESS  read-only
   STATUS      current
   DESCRIPTION
       " "
   ::= { lcsPortTrafficStatisticsEntry 44 }

lcsPortTrafficTxQ1 OBJECT-TYPE
   SYNTAX      Counter64
   MAX-ACCESS  read-only
   STATUS      current
   DESCRIPTION
       " "
   ::= { lcsPortTrafficStatisticsEntry 45 }

lcsPortTrafficTxQ2 OBJECT-TYPE
   SYNTAX      Counter64
   MAX-ACCESS  read-only
   STATUS      current
   DESCRIPTION
       " "
   ::= { lcsPortTrafficStatisticsEntry 46 }

lcsPortTrafficTxQ3 OBJECT-TYPE
   SYNTAX      Counter64
   MAX-ACCESS  read-only
   STATUS      current
   DESCRIPTION
       " "
   ::= { lcsPortTrafficStatisticsEntry 47 }

lcsPortTrafficTxQ4 OBJECT-TYPE
   SYNTAX      Counter64
   MAX-ACCESS  read-only
   STATUS      current
   DESCRIPTION
       " "
   ::= { lcsPortTrafficStatisticsEntry 48 }

lcsPortTrafficTxQ5 OBJECT-TYPE
   SYNTAX      Counter64
   MAX-ACCESS  read-only
   STATUS      current
   DESCRIPTION
       " "
   ::= { lcsPortTrafficStatisticsEntry 49 }

lcsPortTrafficTxQ6 OBJECT-TYPE
   SYNTAX      Counter64
   MAX-ACCESS  read-only
   STATUS      current
   DESCRIPTION
       " "
   ::= { lcsPortTrafficStatisticsEntry 50 }


lcsPortTrafficTxQ7 OBJECT-TYPE
   SYNTAX      Counter64
   MAX-ACCESS  read-only
   STATUS      current
   DESCRIPTION
       " "
   ::= { lcsPortTrafficStatisticsEntry 51 }

lcsPortTrafficTxDrops OBJECT-TYPE
   SYNTAX      Counter64
   MAX-ACCESS  read-only
   STATUS      current
   DESCRIPTION
       " "
   ::= { lcsPortTrafficStatisticsEntry 52 }

lcsPortTrafficTxLateOrExcColl OBJECT-TYPE
   SYNTAX      Counter64
   MAX-ACCESS  read-only
   STATUS      current
   DESCRIPTION
       " "
   ::= { lcsPortTrafficStatisticsEntry 53 }


lcsPortQoSStatistics                                     OBJECT IDENTIFIER ::= { lcsPort 3 }

lcsPortQoSStatisticsClear OBJECT-TYPE
   SYNTAX      Integer32(0|1)
   MAX-ACCESS  read-only
   STATUS      current
   DESCRIPTION
       "default: 0
       0: none
       1: clear "
   ::= { lcsPortQoSStatistics 1 }

lcsPortQoSStatisticsTable OBJECT-TYPE
   SYNTAX      SEQUENCE OF LCSPortQoSStatisticsEntry
   MAX-ACCESS  not-accessible
   STATUS      current
   DESCRIPTION
       " "
   ::= { lcsPortQoSStatistics 2 }

lcsPortQoSStatisticsEntry OBJECT-TYPE
   SYNTAX      LCSPortQoSStatisticsEntry
   MAX-ACCESS  not-accessible
   STATUS      current
   DESCRIPTION
       " "
   INDEX    { lcsPortQoSStatisticsPort  }
   ::= { lcsPortQoSStatisticsTable 1 }

LCSPortQoSStatisticsEntry ::= SEQUENCE {
   lcsPortQoSStatisticsPort      Integer32,
   lcsPortQoSQ0Rx                Counter64,
   lcsPortQoSQ0Tx                Counter64,
   lcsPortQoSQ1Rx                Counter64,
   lcsPortQoSQ1Tx                Counter64,
   lcsPortQoSQ2Rx                Counter64,
   lcsPortQoSQ2Tx                Counter64,
   lcsPortQoSQ3Rx                Counter64,
   lcsPortQoSQ3Tx                Counter64,
   lcsPortQoSQ4Rx                Counter64,
   lcsPortQoSQ4Tx                Counter64,
   lcsPortQoSQ5Rx                Counter64,
   lcsPortQoSQ5Tx                Counter64,
   lcsPortQoSQ6Rx                Counter64,
   lcsPortQoSQ6Tx                Counter64,
   lcsPortQoSQ7Rx                Counter64,
   lcsPortQoSQ7Tx                Counter64
}

lcsPortQoSStatisticsPort OBJECT-TYPE
   SYNTAX      Integer32 (1..4094)
   MAX-ACCESS  not-accessible
   STATUS      current
   DESCRIPTION
       " "
   ::= { lcsPortQoSStatisticsEntry 1 }

lcsPortQoSQ0Rx OBJECT-TYPE
   SYNTAX      Counter64
   MAX-ACCESS  read-only
   STATUS      current
   DESCRIPTION
       " "
   ::= { lcsPortQoSStatisticsEntry 2 }

lcsPortQoSQ0Tx OBJECT-TYPE
   SYNTAX      Counter64
   MAX-ACCESS  read-only
   STATUS      current
   DESCRIPTION
       " "
   ::= { lcsPortQoSStatisticsEntry 3 }

lcsPortQoSQ1Rx OBJECT-TYPE
   SYNTAX      Counter64
   MAX-ACCESS  read-only
   STATUS      current
   DESCRIPTION
       " "
   ::= { lcsPortQoSStatisticsEntry 4 }

lcsPortQoSQ1Tx OBJECT-TYPE
   SYNTAX      Counter64
   MAX-ACCESS  read-only
   STATUS      current
   DESCRIPTION
       " "
   ::= { lcsPortQoSStatisticsEntry 5 }

lcsPortQoSQ2Rx OBJECT-TYPE
   SYNTAX      Counter64
   MAX-ACCESS  read-only
   STATUS      current
   DESCRIPTION
       " "
   ::= { lcsPortQoSStatisticsEntry 6 }

lcsPortQoSQ2Tx OBJECT-TYPE
   SYNTAX      Counter64
   MAX-ACCESS  read-only
   STATUS      current
   DESCRIPTION
       " "
   ::= { lcsPortQoSStatisticsEntry 7 }

lcsPortQoSQ3Rx OBJECT-TYPE
   SYNTAX      Counter64
   MAX-ACCESS  read-only
   STATUS      current
   DESCRIPTION
       " "
   ::= { lcsPortQoSStatisticsEntry 8 }

lcsPortQoSQ3Tx OBJECT-TYPE
   SYNTAX      Counter64
   MAX-ACCESS  read-only
   STATUS      current
   DESCRIPTION
       " "
   ::= { lcsPortQoSStatisticsEntry 9 }

lcsPortQoSQ4Rx OBJECT-TYPE
   SYNTAX      Counter64
   MAX-ACCESS  read-only
   STATUS      current
   DESCRIPTION
       " "
   ::= { lcsPortQoSStatisticsEntry 10 }

lcsPortQoSQ4Tx OBJECT-TYPE
   SYNTAX      Counter64
   MAX-ACCESS  read-only
   STATUS      current
   DESCRIPTION
       " "
   ::= { lcsPortQoSStatisticsEntry 11 }

lcsPortQoSQ5Rx OBJECT-TYPE
   SYNTAX      Counter64
   MAX-ACCESS  read-only
   STATUS      current
   DESCRIPTION
       " "
   ::= { lcsPortQoSStatisticsEntry 12 }

lcsPortQoSQ5Tx OBJECT-TYPE
   SYNTAX      Counter64
   MAX-ACCESS  read-only
   STATUS      current
   DESCRIPTION
       " "
   ::= { lcsPortQoSStatisticsEntry 13 }

lcsPortQoSQ6Rx OBJECT-TYPE
   SYNTAX      Counter64
   MAX-ACCESS  read-only
   STATUS      current
   DESCRIPTION
       " "
   ::= { lcsPortQoSStatisticsEntry 14 }

lcsPortQoSQ6Tx OBJECT-TYPE
   SYNTAX      Counter64
   MAX-ACCESS  read-only
   STATUS      current
   DESCRIPTION
       " "
   ::= { lcsPortQoSStatisticsEntry 15 }

lcsPortQoSQ7Rx OBJECT-TYPE
   SYNTAX      Counter64
   MAX-ACCESS  read-only
   STATUS      current
   DESCRIPTION
       " "
   ::= { lcsPortQoSStatisticsEntry 16 }

lcsPortQoSQ7Tx OBJECT-TYPE
   SYNTAX      Counter64
   MAX-ACCESS  read-only
   STATUS      current
   DESCRIPTION
       " "
   ::= { lcsPortQoSStatisticsEntry 17 }

lcsSFPInfoTable OBJECT-TYPE
   SYNTAX      SEQUENCE OF LCSSFPInfoEntry
   MAX-ACCESS  not-accessible
   STATUS      current
   DESCRIPTION
       " "
   ::= { lcsPort 4 }

lcsSFPInfoEntry OBJECT-TYPE
   SYNTAX      LCSSFPInfoEntry
   MAX-ACCESS  not-accessible
   STATUS      current
   DESCRIPTION
       " "
   INDEX    { lcsSFPInfoIndex }
   ::= { lcsSFPInfoTable 1 }

LCSSFPInfoEntry ::= SEQUENCE {
   lcsSFPInfoIndex               Integer32,
   lcsSFPInfoPort                DisplayString,
   lcsSFPConnectorType           DisplayString,
   lcsSFPFiberType               DisplayString,
   lcsSFPTxCentralWavelength     DisplayString,
   lcsSFPBaudRate                DisplayString,
   lcsSFPVendorOUI               DisplayString,
   lcsSFPVendorName              DisplayString,
   lcsSFPVendorPN                DisplayString,
   lcsSFPVendorRev               DisplayString,
   lcsSFPVendorSN                DisplayString,
   lcsSFPDateCode                DisplayString,
   lcsSFPTemperature             DisplayString,
   lcsSFPVcc                     DisplayString,
   lcsSFPMon1Bias                DisplayString,
   lcsSFPMon2TxPWR               DisplayString,
   lcsSFPMon3RxPWR               DisplayString
}

lcsSFPInfoIndex OBJECT-TYPE
   SYNTAX      Integer32 (1..4094)
   MAX-ACCESS  not-accessible
   STATUS      current
   DESCRIPTION
       " "
   ::= { lcsSFPInfoEntry 1 }

lcsSFPInfoPort OBJECT-TYPE
   SYNTAX      DisplayString
   MAX-ACCESS  read-only
   STATUS      current
   DESCRIPTION
       " "
   ::= { lcsSFPInfoEntry 2 }

lcsSFPConnectorType OBJECT-TYPE
   SYNTAX      DisplayString
   MAX-ACCESS  read-only
   STATUS      current
   DESCRIPTION
       " "
   ::= { lcsSFPInfoEntry 3 }

lcsSFPFiberType OBJECT-TYPE
   SYNTAX      DisplayString
   MAX-ACCESS  read-only
   STATUS      current
   DESCRIPTION
       " "
   ::= { lcsSFPInfoEntry 4 }

lcsSFPTxCentralWavelength OBJECT-TYPE
   SYNTAX      DisplayString
   MAX-ACCESS  read-only
   STATUS      current
   DESCRIPTION
       " "
   ::= { lcsSFPInfoEntry 5 }

lcsSFPBaudRate OBJECT-TYPE
   SYNTAX      DisplayString
   MAX-ACCESS  read-only
   STATUS      current
   DESCRIPTION
       " "
   ::= { lcsSFPInfoEntry 6 }

lcsSFPVendorOUI OBJECT-TYPE
   SYNTAX      DisplayString
   MAX-ACCESS  read-only
   STATUS      current
   DESCRIPTION
       " "
   ::= { lcsSFPInfoEntry 7 }

lcsSFPVendorName OBJECT-TYPE
   SYNTAX      DisplayString
   MAX-ACCESS  read-only
   STATUS      current
   DESCRIPTION
       " "
   ::= { lcsSFPInfoEntry 8 }

lcsSFPVendorPN OBJECT-TYPE
   SYNTAX      DisplayString
   MAX-ACCESS  read-only
   STATUS      current
   DESCRIPTION
       " "
   ::= { lcsSFPInfoEntry 9 }

lcsSFPVendorRev OBJECT-TYPE
   SYNTAX      DisplayString
   MAX-ACCESS  read-only
   STATUS      current
   DESCRIPTION
       " "
   ::= { lcsSFPInfoEntry 10 }

lcsSFPVendorSN OBJECT-TYPE
   SYNTAX      DisplayString
   MAX-ACCESS  read-only
   STATUS      current
   DESCRIPTION
       " "
   ::= { lcsSFPInfoEntry 11 }

lcsSFPDateCode OBJECT-TYPE
   SYNTAX      DisplayString
   MAX-ACCESS  read-only
   STATUS      current
   DESCRIPTION
       " "
   ::= { lcsSFPInfoEntry 12 }

lcsSFPTemperature OBJECT-TYPE
   SYNTAX      DisplayString
   MAX-ACCESS  read-only
   STATUS      current
   DESCRIPTION
       " "
   ::= { lcsSFPInfoEntry 13 }

lcsSFPVcc OBJECT-TYPE
   SYNTAX      DisplayString
   MAX-ACCESS  read-only
   STATUS      current
   DESCRIPTION
       " "
   ::= { lcsSFPInfoEntry 14 }

lcsSFPMon1Bias OBJECT-TYPE
   SYNTAX      DisplayString
   MAX-ACCESS  read-only
   STATUS      current
   DESCRIPTION
       " "
   ::= { lcsSFPInfoEntry 15 }

lcsSFPMon2TxPWR OBJECT-TYPE
   SYNTAX      DisplayString
   MAX-ACCESS  read-only
   STATUS      current
   DESCRIPTION
       " "
   ::= { lcsSFPInfoEntry 16 }

lcsSFPMon3RxPWR OBJECT-TYPE
   SYNTAX      DisplayString
   MAX-ACCESS  read-only
   STATUS      current
   DESCRIPTION
       " "
   ::= { lcsSFPInfoEntry 17 }


lcsVoiceVLAN                                             OBJECT IDENTIFIER ::= { lcsConfiguration 2 }

lcsVoiceVLANConf                                         OBJECT IDENTIFIER ::= { lcsVoiceVLAN 1 }

lcsVoiceVLANMode OBJECT-TYPE
   SYNTAX      Integer32 (0|1)
   MAX-ACCESS  read-write
   STATUS      current
   DESCRIPTION
       " Voice VLAN mode operation.
       default: 0,
       0: disable
       1: enable"
   ::= { lcsVoiceVLANConf 1 }

lcsVoiceVLANVLANId OBJECT-TYPE
   SYNTAX      Integer32 (1..4094)
   MAX-ACCESS  read-write
   STATUS      current
   DESCRIPTION
       "Voice VLAN ID.
        default: 1000,
        range : 1-4094. "
   ::= { lcsVoiceVLANConf 2 }

lcsVoiceVLANAgingTime OBJECT-TYPE
   SYNTAX      Integer32 (10..10000000)
   MAX-ACCESS  read-write
   STATUS      current
   DESCRIPTION
       " Voice VLAN secure learning aging time.
         default: 86400,
         range : 10 - 10000000. "
   ::= { lcsVoiceVLANConf 3 }

lcsVoiceVLANTrafficClass OBJECT-TYPE
   SYNTAX      Integer32 (0..7)
   MAX-ACCESS  read-write
   STATUS      current
   DESCRIPTION
       " Voice VLAN traffic class, all traffic on the Voice VLAN
         will apply this class, available value is from 0(Low)
         to 7(High).
         default: 7. "
   ::= { lcsVoiceVLANConf 4 }


lcsVoiceVLANPortTable OBJECT-TYPE
   SYNTAX      SEQUENCE OF LCSVoiceVLANPortEntry
   MAX-ACCESS  not-accessible
   STATUS      current
   DESCRIPTION
       " Show Voice Vlan configuration. "
   ::= { lcsVoiceVLANConf 5 }

lcsVoiceVLANPortEntry OBJECT-TYPE
   SYNTAX      LCSVoiceVLANPortEntry
   MAX-ACCESS  not-accessible
   STATUS      current
   DESCRIPTION
       " "
   INDEX    { lcsVoiceVLANPort  }
   ::= { lcsVoiceVLANPortTable 1 }

LCSVoiceVLANPortEntry ::= SEQUENCE {
   lcsVoiceVLANPort                    Integer32,
   lcsVoiceVLANPortMode                Integer32,
   lcsVoiceVLANPortSecurity            Integer32,
   lcsVoiceVLANPortDiscoveryProtocol   Integer32
}

lcsVoiceVLANPort OBJECT-TYPE
   SYNTAX      Integer32 (1..4094)
   MAX-ACCESS  not-accessible
   STATUS      current
   DESCRIPTION
       " port, range : 1 - port number. "
   ::= { lcsVoiceVLANPortEntry 1 }

lcsVoiceVLANPortMode OBJECT-TYPE
   SYNTAX      Integer32 (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { lcsVoiceVLANPortEntry 2 }

lcsVoiceVLANPortSecurity OBJECT-TYPE
   SYNTAX      Integer32 (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { lcsVoiceVLANPortEntry 3 }

lcsVoiceVLANPortDiscoveryProtocol OBJECT-TYPE
   SYNTAX      Integer32 (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { lcsVoiceVLANPortEntry 4 }


lcsVoiceVLANOUI                                          OBJECT IDENTIFIER ::= { lcsVoiceVLAN 2 }

lcsVoiceVLANOUICreate OBJECT-TYPE
   SYNTAX       Integer32(0|1)
   MAX-ACCESS   read-write
   STATUS       current
   DESCRIPTION
       "default: 0
        0 : None  (read only)
        1 : Create an OUI entry"
   ::= { lcsVoiceVLANOUI 1 }

lcsVoiceVLANOUITable OBJECT-TYPE
   SYNTAX      SEQUENCE OF LCSVoiceVLANOUIEntry
   MAX-ACCESS  not-accessible
   STATUS      current
   DESCRIPTION
       " Create Voice VLAN OUI entry. Modify OUI table will
         restart auto detect OUI process. "
   ::= { lcsVoiceVLANOUI 2 }

lcsVoiceVLANOUIEntry OBJECT-TYPE
   SYNTAX      LCSVoiceVLANOUIEntry
   MAX-ACCESS  not-accessible
   STATUS      current
   DESCRIPTION
       " "
   INDEX    { lcsVoiceVLANOUIIndex  }
   ::= { lcsVoiceVLANOUITable 1 }

LCSVoiceVLANOUIEntry ::= SEQUENCE {
   lcsVoiceVLANOUIIndex         Integer32,
   lcsVoiceVLANTelephonyOUI     DisplayString,
   lcsVoiceVLANDescription      DisplayString,
   lcsVoiceVLANOUIRowStatus     RowStatus
}

lcsVoiceVLANOUIIndex OBJECT-TYPE
   SYNTAX      Integer32 (1..16)
   MAX-ACCESS  not-accessible
   STATUS      current
   DESCRIPTION
       " "
   ::= { lcsVoiceVLANOUIEntry 1 }

lcsVoiceVLANTelephonyOUI OBJECT-TYPE
   SYNTAX      DisplayString (SIZE (1..32))
   MAX-ACCESS  read-create
   STATUS      current
   DESCRIPTION
       "OUI address, format : 0a 1b 2c "
   ::= { lcsVoiceVLANOUIEntry 2 }

lcsVoiceVLANDescription OBJECT-TYPE
   SYNTAX      DisplayString (SIZE (0..32))
   MAX-ACCESS  read-create
   STATUS      current
   DESCRIPTION
       " Up to 32 characters describing OUI address. "
   ::= { lcsVoiceVLANOUIEntry 3 }

lcsVoiceVLANOUIRowStatus OBJECT-TYPE
   SYNTAX      RowStatus
   MAX-ACCESS  read-create
   STATUS      current
   DESCRIPTION
       "This object indicates the status of this entry, and is used
       to create/delete entries.  Any object in an entry of this table
       may be modified while the value of the corresponding instance
       of this object is active(1).
       createAndGo, notReady not supported."
   ::= { lcsVoiceVLANOUIEntry 4 }

--lcsGARP                                                   OBJECT IDENTIFIER ::= { lcsConfiguration 3 }

--lcsGARPConfTable OBJECT-TYPE
--   SYNTAX      SEQUENCE OF LCSGARPConfEntry
--   MAX-ACCESS  not-accessible
--   STATUS      current
--   DESCRIPTION
--       " "
--   ::= { lcsGARP 1 }

--lcsGARPConfEntry OBJECT-TYPE
--   SYNTAX      LCSGARPConfEntry
--   MAX-ACCESS  not-accessible
--   STATUS      current
--   DESCRIPTION
--       " "
--   INDEX    { lcsGARPConfPort  }
--   ::= { lcsGARPConfTable 1 }

--LCSGARPConfEntry ::= SEQUENCE {
--   lcsGARPConfPort           Integer32,
--   lcsGARPJoinTimer          Integer32,
--   lcsGARPLeaveTimer         Integer32,
--   lcsGARPLeaveAllTimer      Integer32,
--   lcsGARPApplicantion       Integer32,
--   lcsGARPAttributeType      Integer32,
--   lcsGARPApplicant          Integer32
--}

--lcsGARPConfPort OBJECT-TYPE
--   SYNTAX      Integer32 (1..4094)
--   MAX-ACCESS  not-accessible
--   STATUS      current
--   DESCRIPTION
--       " "
--   ::= { lcsGARPConfEntry 1 }

--lcsGARPJoinTimer OBJECT-TYPE
--   SYNTAX      Integer32 (200..1000)
--   MAX-ACCESS  read-write
--   STATUS      current
--   DESCRIPTION
--       "default: 200, range : 200 - 1000 "
--   ::= { lcsGARPConfEntry 2 }

--lcsGARPLeaveTimer OBJECT-TYPE
--   SYNTAX      Integer32 (600..3000)
--   MAX-ACCESS  read-write
--   STATUS      current
--   DESCRIPTION
--       "default: 600 , range : 600 - 3000"
--   ::= { lcsGARPConfEntry 3 }

--lcsGARPLeaveAllTimer OBJECT-TYPE
--   SYNTAX      Integer32 (10000..50000)
--   MAX-ACCESS  read-write
--   STATUS      current
--   DESCRIPTION
--       "default: 10000, range : 10000 - 50000 "
--   ::= { lcsGARPConfEntry 4 }

--lcsGARPApplicantion OBJECT-TYPE
--   SYNTAX      Integer32(1)
--   MAX-ACCESS  read-write
--   STATUS      current
--   DESCRIPTION
--       "default: 1
--       1: GVRP"
--   ::= { lcsGARPConfEntry 5 }

--lcsGARPAttributeType OBJECT-TYPE
--   SYNTAX      Integer32(1)
--   MAX-ACCESS  read-write
--   STATUS      current
--   DESCRIPTION
--       "default: 1
--       1: VLAN"
--   ::= { lcsGARPConfEntry 6 }

--lcsGARPApplicant OBJECT-TYPE
--   SYNTAX      Integer32(0|1)
--   MAX-ACCESS  read-write
--   STATUS      current
--   DESCRIPTION
--       "default: 0
--       0: normal-participant
--       1: non-participant"
--   ::= { lcsGARPConfEntry 7 }

--lcsGARPStatisticsTable OBJECT-TYPE
--   SYNTAX      SEQUENCE OF LCSGARPStatisticsEntry
--   MAX-ACCESS  not-accessible
--   STATUS      current
--   DESCRIPTION
--       " Show the basic GARP port statistics. "
--   ::= { lcsGARP 2 }

--lcsGARPStatisticsEntry OBJECT-TYPE
--   SYNTAX      LCSGARPStatisticsEntry
--   MAX-ACCESS  not-accessible
--   STATUS      current
--   DESCRIPTION
--       " "
--   INDEX    { lcsGARPStatisticsPort  }
--   ::= { lcsGARPStatisticsTable 1 }

--LCSGARPStatisticsEntry ::= SEQUENCE {
--   lcsGARPStatisticsPort             Integer32,
--   lcsGARPStatisticsPeerMAC          DisplayString,
--   lcsGARPStatisticsFailedCount      Counter32
--}

--lcsGARPStatisticsPort OBJECT-TYPE
--   SYNTAX      Integer32 (1..4094)
--   MAX-ACCESS  not-accessible
--   STATUS      current
--   DESCRIPTION
--       " port, range : 1 - port number. "
--   ::= { lcsGARPStatisticsEntry 1 }

--lcsGARPStatisticsPeerMAC OBJECT-TYPE
--   SYNTAX      DisplayString
--   MAX-ACCESS  read-only
--   STATUS      current
--   DESCRIPTION
--       " Peer MAC is MAC address of the neighbour Switch from with GARP frame is received.  "
--   ::= { lcsGARPStatisticsEntry 2 }

--lcsGARPStatisticsFailedCount OBJECT-TYPE
--   SYNTAX      Counter32
--   MAX-ACCESS  read-only
--   STATUS      current
--   DESCRIPTION
--       " explain Failed count here. "
--   ::= { lcsGARPStatisticsEntry 3 }

lcsGVRP                                                   OBJECT IDENTIFIER ::= { lcsConfiguration 4 }

lcsGVRPConf                                                   OBJECT IDENTIFIER ::= { lcsGVRP 1 }

lcsGVRPMode OBJECT-TYPE
   SYNTAX      Integer32(0|1)
   MAX-ACCESS  read-write
   STATUS      current
   DESCRIPTION
       "default: 0,
        0: disable,
        1: enable. "
   ::= { lcsGVRPConf 1 }

lcsGVRPMaxVlan OBJECT-TYPE
   SYNTAX      Integer32(1..4094)
   MAX-ACCESS  read-write
   STATUS      current
   DESCRIPTION
       "Number of simultaniously VLANs that GVRP can control. "
   ::= { lcsGVRPConf 2 }

lcsGVRPJoinTime OBJECT-TYPE
   SYNTAX      Integer32(1..20)
   MAX-ACCESS  read-write
   STATUS      current
   DESCRIPTION
       "join-time in units of centi seconds. Range is 1-20. Default is 20. "
   ::= { lcsGVRPConf 3 }

lcsGVRPLeaveTime OBJECT-TYPE
   SYNTAX      Integer32(60..300)
   MAX-ACCESS  read-write
   STATUS      current
   DESCRIPTION
       "leave-time in units of centi seconds. Range is 60-300. Default is 60. "
   ::= { lcsGVRPConf 4 }

lcsGVRPLeaveAllTime OBJECT-TYPE
   SYNTAX      Integer32(1000..5000)
   MAX-ACCESS  read-write
   STATUS      current
   DESCRIPTION
       "leave-all-time in units of centi seconds Range is 1000-5000. Default is 1000"
   ::= { lcsGVRPConf 5 }

lcsGVRPConfTable OBJECT-TYPE
   SYNTAX      SEQUENCE OF LCSGVRPConfEntry
   MAX-ACCESS  not-accessible
   STATUS      current
   DESCRIPTION
       " "
   ::= { lcsGVRPConf 6 }

lcsGVRPConfEntry OBJECT-TYPE
   SYNTAX      LCSGVRPConfEntry
   MAX-ACCESS  not-accessible
   STATUS      current
   DESCRIPTION
       " "
   INDEX    { lcsGVRPConfPort  }
   ::= { lcsGVRPConfTable 1 }

LCSGVRPConfEntry ::= SEQUENCE {
   lcsGVRPConfPort           Integer32,
   lcsGVRPConfPortMode       Integer32
-- lcsGVRPConfPortRRole      Integer32
}

lcsGVRPConfPort OBJECT-TYPE
   SYNTAX      Integer32 (1..4094)
   MAX-ACCESS  not-accessible
   STATUS      current
   DESCRIPTION
       " "
   ::= { lcsGVRPConfEntry 1 }

lcsGVRPConfPortMode OBJECT-TYPE
   SYNTAX      Integer32(0|1)
   MAX-ACCESS  read-write
   STATUS      current
   DESCRIPTION
       "default: 0
       1: enable
       0: disable"
   ::= { lcsGVRPConfEntry 2 }

--lcsGVRPConfPortRRole OBJECT-TYPE
--   SYNTAX      Integer32(0|1)
--   MAX-ACCESS  read-write
--   STATUS      current
--   DESCRIPTION
--       "default: 0
--       1: enable
--       0: disable"
--   ::= { lcsGVRPConfEntry 3 }

--lcsGVRPStatisticsTable OBJECT-TYPE
--   SYNTAX      SEQUENCE OF LCSGVRPStatisticsEntry
--   MAX-ACCESS  not-accessible
--   STATUS      current
--   DESCRIPTION
--       " "
--   ::= { lcsGVRP 2 }

--lcsGVRPStatisticsEntry OBJECT-TYPE
--   SYNTAX      LCSGVRPStatisticsEntry
--   MAX-ACCESS  not-accessible
--   STATUS      current
--   DESCRIPTION
--       " "
--   INDEX    { lcsGVRPStatisticsPort  }
--   ::= { lcsGVRPStatisticsTable 1 }

--LCSGVRPStatisticsEntry ::= SEQUENCE {
--   lcsGVRPStatisticsPort         Integer32,
--   lcsGVRPStatisticsJoinTxCnt    Counter32,
--   lcsGVRPStatisticsLeaveTxCnt   Counter32
--}

--lcsGVRPStatisticsPort OBJECT-TYPE
--   SYNTAX      Integer32 (1..4094)
--   MAX-ACCESS  not-accessible
--   STATUS      current
--   DESCRIPTION
--       " "
--   ::= { lcsGVRPStatisticsEntry 1 }

--lcsGVRPStatisticsJoinTxCnt OBJECT-TYPE
--   SYNTAX      Counter32
--   MAX-ACCESS  read-only
--   STATUS      current
--   DESCRIPTION
--       " "
--   ::= { lcsGVRPStatisticsEntry 2 }

--lcsGVRPStatisticsLeaveTxCnt OBJECT-TYPE
--   SYNTAX      Counter32
--   MAX-ACCESS  read-only
--   STATUS      current
--   DESCRIPTION
--       " "
--   ::= { lcsGVRPStatisticsEntry 3 }


lcsMirroring                                             OBJECT IDENTIFIER ::= { lcsConfiguration 6 }

lcsMonitorSession OBJECT-TYPE
   SYNTAX      Integer32(1..5)
   MAX-ACCESS  read-write
   STATUS      current
   DESCRIPTION
       "Monitor session."
   ::= { lcsMirroring 1 }

lcsPortToMirrorOn OBJECT-TYPE
   SYNTAX      Integer32(0..4094)
   MAX-ACCESS  read-write
   STATUS      current
   DESCRIPTION
       "default: 0
        0: disable,
        range : 1 - port number. "
   ::= { lcsMirroring 2 }

lcsMirrorTable OBJECT-TYPE
   SYNTAX      SEQUENCE OF LCSMirrorEntry
   MAX-ACCESS  not-accessible
   STATUS      current
   DESCRIPTION
       " "
   ::= { lcsMirroring 3 }

lcsMirrorEntry OBJECT-TYPE
   SYNTAX      LCSMirrorEntry
   MAX-ACCESS  not-accessible
   STATUS      current
   DESCRIPTION
       " "
   INDEX    { lcsMirrorPort  }
   ::= { lcsMirrorTable 1 }

LCSMirrorEntry ::= SEQUENCE {
   lcsMirrorPort        Integer32,
   lcsMirrorMode        Integer32
}

lcsMirrorPort OBJECT-TYPE
   SYNTAX      Integer32 (1..4094)
   MAX-ACCESS  not-accessible
   STATUS      current
   DESCRIPTION
       " "
   ::= { lcsMirrorEntry 1 }

lcsMirrorMode OBJECT-TYPE
   SYNTAX      Integer32(0..3)
   MAX-ACCESS  read-write
   STATUS      current
   DESCRIPTION
       "default: 0
       0: disable
       1: rx only
       2: tx only
       3: enable 
       Setting Tx mirroring for analyzer port has no effect. Tx mirroring ignored"
   ::= { lcsMirrorEntry 2 }

lcsTrapEventSeverity                                             OBJECT IDENTIFIER ::= { lcsConfiguration 7 }

lcsTrapEventSeverityTable OBJECT-TYPE
   SYNTAX      SEQUENCE OF LCSTrapEventSeverityEntry
   MAX-ACCESS  not-accessible
   STATUS      current
   DESCRIPTION
       " "
   ::= { lcsTrapEventSeverity 1 }

lcsTrapEventSeverityEntry OBJECT-TYPE
   SYNTAX      LCSTrapEventSeverityEntry
   MAX-ACCESS  not-accessible
   STATUS      current
   DESCRIPTION
       " "
   INDEX    { lcsTrapEventSeverityIndex }
   ::= { lcsTrapEventSeverityTable 1 }

LCSTrapEventSeverityEntry ::= SEQUENCE {
   lcsTrapEventSeverityIndex        Integer32,
   lcsTrapEventSeverityGroupName    DisplayString,
   lcsTrapEventSeverityLevel        Integer32,
   lcsTrapEventSeveritySyslog       Integer32,
   lcsTrapEventSeverityTrap         Integer32,
   lcsTrapEventSeveritySMTP         Integer32
}

lcsTrapEventSeverityIndex OBJECT-TYPE
   SYNTAX      Integer32 (1..65535)
   MAX-ACCESS  not-accessible
   STATUS      current
   DESCRIPTION
       " "
   ::= { lcsTrapEventSeverityEntry 1 }

lcsTrapEventSeverityGroupName OBJECT-TYPE
   SYNTAX      DisplayString
   MAX-ACCESS  read-only
   STATUS      current
   DESCRIPTION
       "Group Name"
   ::= { lcsTrapEventSeverityEntry 2 }

lcsTrapEventSeverityLevel OBJECT-TYPE
   SYNTAX      Integer32
   MAX-ACCESS  read-write
   STATUS      current
   DESCRIPTION
       "0:Emergency
       1:Alert
       2:Critical
       3:Error
       4:Warning
       5:Notice
       6:Information
       7:Debug"
   ::= { lcsTrapEventSeverityEntry 3 }

lcsTrapEventSeveritySyslog OBJECT-TYPE
   SYNTAX      Integer32
   MAX-ACCESS  read-write
   STATUS      current
   DESCRIPTION
       "0:disable
       1:enable"
   ::= { lcsTrapEventSeverityEntry 4 }

lcsTrapEventSeverityTrap OBJECT-TYPE
   SYNTAX      Integer32
   MAX-ACCESS  read-write
   STATUS      current
   DESCRIPTION
       "0:disable
       1:enable"
   ::= { lcsTrapEventSeverityEntry 5 }

lcsTrapEventSeveritySMTP OBJECT-TYPE
   SYNTAX      Integer32
   MAX-ACCESS  read-write
   STATUS      current
   DESCRIPTION
       "0:disable
       1:enable"
   ::= { lcsTrapEventSeverityEntry 6 }

-- =======================================================================================================================
lcsSMTP                                             OBJECT IDENTIFIER ::= { lcsConfiguration 8 }

lcsSMTPMailServer OBJECT-TYPE
   SYNTAX      DisplayString
   MAX-ACCESS  read-write
   STATUS      current
   DESCRIPTION
       " Up to 47 characters describing email server. "
   ::= { lcsSMTP 1 }

lcsSMTPUserName OBJECT-TYPE
   SYNTAX      DisplayString
   MAX-ACCESS  read-write
   STATUS      current
   DESCRIPTION
       " Up to 47 characters describing user name. "
   ::= { lcsSMTP 2 }

lcsSMTPPassword OBJECT-TYPE
   SYNTAX      DisplayString
   MAX-ACCESS  read-write
   STATUS      current
   DESCRIPTION
       " Up to 47 characters describing password. "
   ::= { lcsSMTP 3 }

lcsSMTPSender OBJECT-TYPE
   SYNTAX      DisplayString
   MAX-ACCESS  read-write
   STATUS      current
   DESCRIPTION
       " Up to 47 characters describing sender. "
   ::= { lcsSMTP 5 }

lcsSMTPReturnPath OBJECT-TYPE
   SYNTAX      DisplayString
   MAX-ACCESS  read-write
   STATUS      current
   DESCRIPTION
       " Up to 47 characters describing return path. "
   ::= { lcsSMTP 6 }

lcsSMTPEmailAddress1 OBJECT-TYPE
   SYNTAX      DisplayString
   MAX-ACCESS  read-write
   STATUS      current
   DESCRIPTION
       " Up to 47 characters describing mail address. "
   ::= { lcsSMTP 7 }

lcsSMTPEmailAddress2 OBJECT-TYPE
   SYNTAX      DisplayString
   MAX-ACCESS  read-write
   STATUS      current
   DESCRIPTION
       " Up to 47 characters describing mail address. "
   ::= { lcsSMTP 8 }

lcsSMTPEmailAddress3 OBJECT-TYPE
   SYNTAX      DisplayString
   MAX-ACCESS  read-write
   STATUS      current
   DESCRIPTION
       " Up to 47 characters describing mail address. "
   ::= { lcsSMTP 9 }

lcsSMTPEmailAddress4 OBJECT-TYPE
   SYNTAX      DisplayString
   MAX-ACCESS  read-write
   STATUS      current
   DESCRIPTION
       " Up to 47 characters describing mail address. "
   ::= { lcsSMTP 10 }

lcsSMTPEmailAddress5 OBJECT-TYPE
   SYNTAX      DisplayString
   MAX-ACCESS  read-write
   STATUS      current
   DESCRIPTION
       " Up to 47 characters describing mail address. "
   ::= { lcsSMTP 11 }

lcsSMTPEmailAddress6 OBJECT-TYPE
   SYNTAX      DisplayString
   MAX-ACCESS  read-write
   STATUS      current
   DESCRIPTION
       " Up to 47 characters describing mail address. "
   ::= { lcsSMTP 12 }

-- =======================================================================================================================
lcsACLConf                                              OBJECT IDENTIFIER ::= { lcsConfiguration 9 }

-- RowStatus Info:  createAndGo, notReady not supported.
-- =======================================================================================================================
-- Textual Conventions for the lcs Acl Mib
-- =======================================================================================================================
--
    lcsACL                     OBJECT IDENTIFIER  ::= { lcsACLConf 1 }
    lcsACLACE                  OBJECT IDENTIFIER  ::= { lcsACLConf 3 }

--
-- =======================================================================================================================
-- Start lcsACLPortConf group
-- =======================================================================================================================
--lcsACLPortConfTable

    lcsACLPortConfTable OBJECT-TYPE
               SYNTAX      SEQUENCE OF     LCSACLPortConfEntry
               MAX-ACCESS  not-accessible
               STATUS      current
               DESCRIPTION
                   "The ACL Port Conf Table.
                    INDEX for this table is ifIndex which is
                    equivalent to the panel port number."
               ::= {     lcsACL 1 }

    lcsACLPortConfEntry OBJECT-TYPE
               SYNTAX          LCSACLPortConfEntry
               MAX-ACCESS  not-accessible
               STATUS      current
               DESCRIPTION
                   "The ACL Port Conf Entry. "
               INDEX    {     ifIndex  }
               ::= {     lcsACLPortConfTable 1 }

    LCSACLPortConfEntry             ::=
            SEQUENCE {
                 lcsACLPortConfPolicyID        Integer32,
                 lcsACLPortConfAction          INTEGER,
                 lcsACLPortConfRateLimiterID   Integer32,
                 lcsACLPortConfPortRedirect    Integer32,
                 lcsACLPortConfMirror          AdminMode,
                 lcsACLPortConfLogging         AdminMode,
                 lcsACLPortConfShutdown        AdminMode,
                 lcsACLPortConfState           AdminMode,
                 lcsACLPortConfCounter         Counter32
                 }

    lcsACLPortConfPolicyID OBJECT-TYPE
               SYNTAX       Integer32 (0..127)
               MAX-ACCESS   read-write
               STATUS       current
               DESCRIPTION
                   "The policy to apply to this port.
                    default: 0, range : 0 - 127. "
               ::= {     lcsACLPortConfEntry 2 }

    lcsACLPortConfAction OBJECT-TYPE
               SYNTAX      INTEGER { deny(0), permit(1) }
               MAX-ACCESS  read-write
               STATUS      current
               DESCRIPTION
                   "Whether forwarding is permitted ('Permit') or denied ('Deny').
                    default: 1,
                    0: Deny,
                    1: Permit."
               ::= {     lcsACLPortConfEntry 3 }

    lcsACLPortConfRateLimiterID OBJECT-TYPE
               SYNTAX      Integer32 (0..16)
               MAX-ACCESS  read-write
               STATUS      current
               DESCRIPTION
                   "The rate limiter to apply on this port.
                    0: Disable,
                    range : 0 - 16. "
               ::= {     lcsACLPortConfEntry 4 }

    lcsACLPortConfPortRedirect OBJECT-TYPE
               SYNTAX      Integer32 (0..4094)
               MAX-ACCESS  read-write
               STATUS      current
               DESCRIPTION
                   "Port frames are redirected on.
                    0: Disable,
                    range : 0 - end port number. "
               ::= {     lcsACLPortConfEntry 5 }

    lcsACLPortConfMirror OBJECT-TYPE
               SYNTAX      AdminMode
               MAX-ACCESS  read-write
               STATUS      current
               DESCRIPTION
                   "The mirror operation of this port."
               ::= {     lcsACLPortConfEntry 6 }

    lcsACLPortConfLogging OBJECT-TYPE
               SYNTAX      AdminMode
               MAX-ACCESS  read-write
               STATUS      current
               DESCRIPTION
                   "Specify the logging operation of this port."
               ::= {     lcsACLPortConfEntry 7 }

    lcsACLPortConfShutdown OBJECT-TYPE
               SYNTAX      AdminMode
               MAX-ACCESS  read-write
               STATUS      current
               DESCRIPTION
                   "Specify the port shut down operation of this port."
               DEFVAL  { disable }
               ::= {     lcsACLPortConfEntry 8 }

    lcsACLPortConfState OBJECT-TYPE
               SYNTAX      AdminMode
               MAX-ACCESS  read-write
               STATUS      current
               DESCRIPTION
                   "Specify the port state of this port."
               DEFVAL  { enable }
               ::= {     lcsACLPortConfEntry 9 }

    lcsACLPortConfCounter OBJECT-TYPE
               SYNTAX      Counter32
               MAX-ACCESS  read-only
               STATUS      current
               DESCRIPTION
                   "Counts the number of frames that match this ACE. "
               ::= {     lcsACLPortConfEntry 10 }

--
-- =======================================================================================================================
-- Start lcsACLRateLimiter group
-- =======================================================================================================================
--lcsACLRateLimiterTable

    lcsACLRateLimiterTable OBJECT-TYPE
               SYNTAX      SEQUENCE OF     LCSACLRateLimiterEntry
               MAX-ACCESS  not-accessible
               STATUS      current
               DESCRIPTION
                   "The ACL Rate Limiter Table."
               ::= {     lcsACL 2 }

    lcsACLRateLimiterEntry OBJECT-TYPE
               SYNTAX          LCSACLRateLimiterEntry
               MAX-ACCESS  not-accessible
               STATUS      current
               DESCRIPTION
                   "The ACL Rate Limiter Entry. "
               INDEX    {     lcsACLRateLimiterID  }
               ::= {     lcsACLRateLimiterTable 1 }

    LCSACLRateLimiterEntry             ::= SEQUENCE {
                 lcsACLRateLimiterID       Integer32,
                 lcsACLRateLimiterRate     Integer32,
                 lcsACLRateLimiterUnit     Integer32
                 }

    lcsACLRateLimiterID OBJECT-TYPE
               SYNTAX      Integer32 (1..16)
               MAX-ACCESS  not-accessible
               STATUS      current
               DESCRIPTION
                   "Rate Limiter ID.
                    range : 1-16 "
               ::= {     lcsACLRateLimiterEntry 1 }

    lcsACLRateLimiterRate OBJECT-TYPE
               SYNTAX      Integer32(0..500000)
               MAX-ACCESS  read-write
               STATUS      current
               DESCRIPTION
                   "default: 1,
                    range :
                    <0-500000> 10pps,The valid rate is 0, 10, 20, 30,
                    ..., 5000000 in pps.
                    <0-400000> 25kbps,The valid rate is 0, 25, 50, 75,...,
                    10000000 in kbps."
               ::= {     lcsACLRateLimiterEntry 2 }

    lcsACLRateLimiterUnit OBJECT-TYPE
               SYNTAX      Integer32(0|1)
               MAX-ACCESS  read-write
               STATUS      current
               DESCRIPTION
                   "Specify the rate unit.
                    0: 10pps, 1: 25kbps.
                   "
               ::= {     lcsACLRateLimiterEntry 3 }

--
-- =======================================================================================================================
-- Start lcsACLACE group
-- =======================================================================================================================
--lcsACLACEClear

    lcsACLACEClear OBJECT-TYPE
               SYNTAX      ActivateCmd
               MAX-ACCESS  read-write
               STATUS      current
               DESCRIPTION
                   "Clear all ACE counters."
               ::= {     lcsACLACE 1 }

--lcsACLACETable

    lcsACLACETable OBJECT-TYPE
               SYNTAX      SEQUENCE OF     LCSACLACEEntry
               MAX-ACCESS  not-accessible
               STATUS      current
               DESCRIPTION
                   "Create ACL ACE entry. "
               ::= {     lcsACLACE 2 }

    lcsACLACEEntry OBJECT-TYPE
               SYNTAX          LCSACLACEEntry
               MAX-ACCESS  not-accessible
               STATUS      current
               DESCRIPTION
                   "The ACLACE Table."
               INDEX    {     lcsACLACEIndex  }
               ::= {     lcsACLACETable 1 }

    LCSACLACEEntry             ::= SEQUENCE {
                 lcsACLACEIndex                Integer32,
                 lcsACLACEID                   Integer32,
                 lcsACLACENextID               Integer32,
--               lcsACLACELoopUp               AdminMode,
                 lcsACLACEIngressPort          DisplayString,
                 lcsACLACEPortPolicyNumber     Integer32,
                 lcsACLACEPortPolicyBitmask    Integer32,
                 lcsACLACEFrameType            INTEGER,
                 lcsACLACEAction               INTEGER,
                 lcsACLACEFilterPort           DisplayString,
                 lcsACLACEDenyPortRedirect     DisplayString,
                 lcsACLACERateLimiter          Integer32,
                 lcsACLACEMirror               AdminMode,
                 lcsACLACELogging              AdminMode,
                 lcsACLACEShutdown             AdminMode,
                 lcsACLACECounter              Counter32,
                 lcsACLACEVLAN8021QTagged      INTEGER,
                 lcsACLACEVLANVID              Integer32,
                 lcsACLACEVLANTagPriority      Integer32,
                 lcsACLACESMAC                 DisplayString,
                 lcsACLACEDMACType             INTEGER,
                 lcsACLACEDMAC                 DisplayString,
                 lcsACLACEEtherType            Integer32,
                 lcsACLACEArpOpCode            INTEGER,
                 lcsACLACEArpFlagsRequestReply INTEGER,
                 lcsACLACEArpFlagsArpSMac      INTEGER,
                 lcsACLACEArpFlagsRarpDmac     INTEGER,
                 lcsACLACEArpFlagsLength       INTEGER,
                 lcsACLACEArpFlagsIp           INTEGER,
                 lcsACLACEArpFlagsEthernet     INTEGER,
                 lcsACLACESIPType              INTEGER,
                 lcsACLACESIPIPAddress         IpAddress,
                 lcsACLACESIPIPMask            IpAddress,
                 lcsACLACEDIPType              INTEGER,
                 lcsACLACEDIPIPAddress         IpAddress,
                 lcsACLACEDIPIPMask            IpAddress,
                 lcsACLACEIPProtocol           INTEGER,
                 lcsACLACEIPProtocolValue      Integer32,
                 lcsACLACEIPFlagsTTL           INTEGER,
                 lcsACLACEIPFlagsFragment      INTEGER,
                 lcsACLACEIPFlagsOptions       INTEGER,
                 lcsACLACEICMPType             Integer32,
                 lcsACLACEICMPCode             Integer32,
                 lcsACLACESourcePort           DisplayString,
                 lcsACLACEDestPort             DisplayString,
                 lcsACLACETCPFlagsFin          INTEGER,
                 lcsACLACETCPFlagsSyn          INTEGER,
                 lcsACLACETCPFlagsRst          INTEGER,
                 lcsACLACETCPFlagsPsh          INTEGER,
                 lcsACLACETCPFlagsAck          INTEGER,
                 lcsACLACETCPFlagsUrg          INTEGER,
                 lcsACLACEIPv6SIPAddress       DisplayString,
                 lcsACLACEIPv6SIPBitmask       DisplayString,
                 lcsACLACEIPv6HopLimit         INTEGER,
                 lcsACLACESMACMask             DisplayString,
                 lcsACLACEDMACMask             DisplayString,
                 lcsACLACERowStatus            RowStatus
                 }

    lcsACLACEIndex OBJECT-TYPE
               SYNTAX      Integer32(1..256)
               MAX-ACCESS  not-accessible
               STATUS      current
               DESCRIPTION
                   "The index. "
               ::= {     lcsACLACEEntry 1 }

    lcsACLACEID OBJECT-TYPE
               SYNTAX      Integer32(1..256)
               MAX-ACCESS  read-create
               STATUS      current
               DESCRIPTION
                   "If the ACE ID is specified and an entry with this ACE ID
                    already exists, the ACE will be modified. Otherwise, a
                    new ACE will be added.
                    range : 1 - 256. "
               ::= {     lcsACLACEEntry 2 }

    lcsACLACENextID OBJECT-TYPE
               SYNTAX      Integer32 (0..256)
               MAX-ACCESS  read-create
               STATUS      current
               DESCRIPTION
                   "If the next ACE ID is non zero, the ACE will be placed
                    before this ACE in the list. If the next ACE ID is zero,
                    the ACE will be placed last in the list.
                    range : 0 - 256. "
               ::= {     lcsACLACEEntry 3 }

--    lcsACLACELoopUp OBJECT-TYPE
--               SYNTAX      AdminMode
--               MAX-ACCESS  read-create
--               STATUS      current
--               DESCRIPTION
--                   "Specify the second lookup operation of the ACE."
--               ::= {     lcsACLACEEntry 4 }
--
    lcsACLACEIngressPort OBJECT-TYPE
               SYNTAX      DisplayString
               MAX-ACCESS  read-create
               STATUS      current
               DESCRIPTION
                   "Indicates the ingress port of the ACE. Possible values are:
                    0: All,The ACE will match all ingress port.
                    Port n: The ACE will match a specific ingress port."
               ::= {     lcsACLACEEntry 5 }

    lcsACLACEPortPolicyNumber OBJECT-TYPE
               SYNTAX      Integer32(0..127)
               MAX-ACCESS  read-create
               STATUS      current
               DESCRIPTION
                   "policy value.
                    range : 0 - 127.
                    0: Any."
               ::= {     lcsACLACEEntry 6 }

    lcsACLACEPortPolicyBitmask OBJECT-TYPE
               SYNTAX      Integer32(0..127)
               MAX-ACCESS  read-create
               STATUS      current
               DESCRIPTION
                   "When 'Specific' is selected for the policy filter,
                    you can enter a specific policy bitmask.
                    range : 0 - 127, 0: no data."
               ::= {     lcsACLACEEntry 7 }

    lcsACLACEFrameType OBJECT-TYPE
               SYNTAX      INTEGER {   any(0), etype(1), arp(2),
                                       ipv4(3), ipv6(4) }
               MAX-ACCESS  read-create
               STATUS      current
               DESCRIPTION
                   "Select the frame type for this ACE.
                    When change the type Related oid will set default.
                    0: any,
                    1: etype,
                    2: arp,
                    3: ipv4,
                    4: ipv6."
               ::= {     lcsACLACEEntry 8 }

    lcsACLACEAction OBJECT-TYPE
               SYNTAX      INTEGER { deny(0), permit(1), filter(2) }
               MAX-ACCESS  read-create
               STATUS      current
               DESCRIPTION
                   "0: Deny
                    1: Permit
                    2: Filter"
               ::= {     lcsACLACEEntry 9 }

    lcsACLACEFilterPort OBJECT-TYPE
               SYNTAX      DisplayString
               MAX-ACCESS  read-create
               STATUS      current
               DESCRIPTION
                   "When 'Action' is 'Filter' can set.
                    0: Disable,
                    Port n: The ACE applies to this port number, where n is
                    the number of the switch port.
                    range: 0 - Port number.
                   "
               ::= {     lcsACLACEEntry 10 }

    lcsACLACEDenyPortRedirect OBJECT-TYPE
               SYNTAX      DisplayString
               MAX-ACCESS  read-create
               STATUS      current
               DESCRIPTION
                   "Frames that hit the ACE are redirected to the port
                    number specified here.Disabled,indicates that the port
                    redirect operation is disabled.
                    When 'Action' is 'Deny' can set.
                    0: disabled,
                    Port no: The ACE applies to this port number, where n is
                    the number of the switch port."
               ::= {     lcsACLACEEntry 11 }

    lcsACLACERateLimiter OBJECT-TYPE
               SYNTAX      Integer32(0..16)
               MAX-ACCESS  read-create
               STATUS      current
               DESCRIPTION
                   "default: 0,
                    0: Disable
                    range : 0 - 16 "
               ::= {     lcsACLACEEntry 12 }

    lcsACLACEMirror OBJECT-TYPE
               SYNTAX      AdminMode
               MAX-ACCESS  read-create
               STATUS      current
               DESCRIPTION
                   "default: 0,
                    0: disable - Frames matching the ACE are not mirrored.
                    1: enable - Frames matching the ACE are mirrored.
                   "
               ::= {     lcsACLACEEntry 13 }

    lcsACLACELogging OBJECT-TYPE
               SYNTAX      AdminMode
               MAX-ACCESS  read-create
               STATUS      current
               DESCRIPTION
                   "default: 0,
                    0: disable - Frames matching the ACE are not logged.
                    1: enable - Frames matching the ACE are stored in the
                   system log."
               ::= {     lcsACLACEEntry 14 }

    lcsACLACEShutdown OBJECT-TYPE
               SYNTAX      AdminMode
               MAX-ACCESS  read-create
               STATUS      current
               DESCRIPTION
                   "default: 0,
                    0: disable - Port shut down is disabled for the AC.
                    1: enable - If a frame matches the ACE, the ingress port
                    will be disabled."
               ::= {     lcsACLACEEntry 15 }

    lcsACLACECounter OBJECT-TYPE
               SYNTAX      Counter32
               MAX-ACCESS  read-only
               STATUS      current
               DESCRIPTION
                   "The counter indicates the number of times the ACE was
                    hit by a frame. "
               ::= {     lcsACLACEEntry 16 }

    lcsACLACEVLAN8021QTagged OBJECT-TYPE
               SYNTAX      INTEGER { disable(0), enable(1), any(2) }
               MAX-ACCESS  read-create
               STATUS      current
               DESCRIPTION
                   "Specify whether frames can hit the action according to
                    the 802.1Q tagged.
                    default: 2,
                    0: disable - Untagged frame only.
                    1: enable - Tagged frame only.
                    2: Any - Any value is allowed.
                    "
               ::= {     lcsACLACEEntry 17 }

    lcsACLACEVLANVID OBJECT-TYPE
               SYNTAX      Integer32(0..4094)
               MAX-ACCESS  read-create
               STATUS      current
               DESCRIPTION
                   "Specify the VLAN ID filter for this ACE.
                    The vid can't be set when 802.1Q Tagged is disabled.
                    default: 0,
                    0: Any - No VLAN ID filter is specified.
                    range : 0 - 4094 "
               ::= {     lcsACLACEEntry 18 }

    lcsACLACEVLANTagPriority OBJECT-TYPE
               SYNTAX      Integer32(0..14)
               MAX-ACCESS  read-create
               STATUS      current
               DESCRIPTION
                   "Specify the tag priority for this ACE.
                    The tag priority can't be set when 802.1Q Tagged is disabled.
                    range: 0-14
                    0:0
                    1:1
                    2:2
                    3:3
                    4:4
                    5:5
                    6:6
                    7:7
                    8:0-1
                    9:2-3
                    10:4-5
                    11:6-7
                    12:0-3
                    13:4-7
                    14:Any
                    "
               ::= {     lcsACLACEEntry 19 }

    lcsACLACESMAC OBJECT-TYPE
               SYNTAX      DisplayString
               MAX-ACCESS  read-create
               STATUS      current
               DESCRIPTION
                   "Configure source MAC address for this ACE.
                    <mac-address>: A frame that hits this ACE matches this
                    source MAC address value. xx-xx-xx-xx-xx-xx.
                    Any: Don't care."
               ::= {    lcsACLACEEntry 20 }

    lcsACLACEDMACType OBJECT-TYPE
               SYNTAX      INTEGER { any(0), mc(1), bc(2), uc(3) ,
                                     macAddress(4) , noData(5) }
               MAX-ACCESS  read-create
               STATUS      current
               DESCRIPTION
                   "DMAC Type.
                    default: 0,
                    0: Any - Don't care.
                    1: Multicast - Frame must be multicast.
                    2: Broadcast - Frame must be broadcast.
                    3: Unicast - Frame must be unicast.
                    4: mac address.
                    5: no data."
               DEFVAL  { any }
               ::= {    lcsACLACEEntry 21 }

    lcsACLACEDMAC OBJECT-TYPE
               SYNTAX      DisplayString
               MAX-ACCESS  read-create
               STATUS      current
               DESCRIPTION
                   "Configure destination MAC address for this ACE.
                    <mac-address>: A frame that hits this ACE matches this
                    destination MAC address value. xx-xx-xx-xx-xx-xx."
               ::= {     lcsACLACEEntry 22 }

    lcsACLACEEtherType OBJECT-TYPE
               SYNTAX      Integer32(-1..65535)
               MAX-ACCESS  read-create
               STATUS      current
               DESCRIPTION
                   "0: Any
                   range : 0, or 1536(0x0600) - 65535(0xffff) but excluding 0x0800(IPv4) 0x0806(ARP) and
                    0x86DD(IPv6).
                    -1: No data. "
               ::= {     lcsACLACEEntry 23 }

    lcsACLACEArpOpCode OBJECT-TYPE
               SYNTAX      INTEGER { any(0), arp(1), rarp(2),
                                     other(3), noData(4) }
               MAX-ACCESS  read-create
               STATUS      current
               DESCRIPTION
                   "Configure ARP opcode for this ACE.
                    default: 0,
                    0: Any - Don't care.
                    1: arp.
                    2: rarp.
                    3: other.
                    4: No data."
               DEFVAL  { any }
               ::= {     lcsACLACEEntry 24 }

    lcsACLACEArpFlagsRequestReply OBJECT-TYPE
               SYNTAX      INTEGER { reply(0), request(1), any(2), noData(3)}
               MAX-ACCESS  read-create
               STATUS      current
               DESCRIPTION
                   "Specify the available ARP/RARP opcode (OP) flag for this ACE.
                    default: 2,
                    0: Frame must have ARP Reply or RARP Reply OP flag.
                    1: Frame must have ARP Request or RARP Request OP flag set.
                    2: Any - Don't care.
                    3: No data."
               DEFVAL  { any }
               ::= {     lcsACLACEEntry 25 }

    lcsACLACEArpFlagsArpSMac OBJECT-TYPE
               SYNTAX      INTEGER { notEqualSMAC(0), equalSMAC(1),
                                     any(2), noData(3)}
               MAX-ACCESS  read-create
               STATUS      current
               DESCRIPTION
                   "Specify whether frames can hit the action according to their
                    sender hardware address field (SHA) settings.
                    default: 2,
                    0: ARP frames where SHA is not equal to the SMAC address.
                    1: ARP frames where SHA is equal to the SMAC address.
                    2: Any - Don't care.
                    3: No data."
               DEFVAL  { any }
               ::= {     lcsACLACEEntry 26 }

    lcsACLACEArpFlagsRarpDmac OBJECT-TYPE
               SYNTAX      INTEGER { notEqualDMAC(0), equalDMAC(1),
                                     any(2), noData(3)}
               MAX-ACCESS  read-create
               STATUS      current
               DESCRIPTION
                   "Specify whether frames can hit the action according to
                    their target hardware address field (THA) settings.
                    default: 2,
                    0: RARP frames where THA is not equal to the DMAC address.
                    1: RARP frames where THA is equal to the DMAC address.
                    2: Any - Don't care.
                    3: No data."
               DEFVAL  { any }
               ::= {     lcsACLACEEntry 27 }

    lcsACLACEArpFlagsLength OBJECT-TYPE
               SYNTAX      INTEGER { notEqualEthIpV4 (0), equalEthIpV4(1),
                                     any(2), noData(3)}
               MAX-ACCESS  read-create
               STATUS      current
               DESCRIPTION
                   "Specify whether frames can hit the action according to
                    their ARP/RARP hardware address length (HLN) and protocol
                    address length (PLN) settings.
                    default: 2,
                    0: ARP/RARP frames where the HLN is not equal to
                    Ethernet(0x06) or the (PLN) is not equal to IPv4(0x04).
                    1: ARP/RARP frames where the HLN is equal to Ethernet (0x06)
                    and the (PLN) is equal to IPv4(0x04).
                    2: Any - Don't care.
                    3: No data."
                DEFVAL  { any }
                ::= {     lcsACLACEEntry 28 }

    lcsACLACEArpFlagsIp OBJECT-TYPE
               SYNTAX      INTEGER { notEqualEth(0), equalEth(1),
                                     any(2), noData(3)}
               MAX-ACCESS  read-create
               STATUS      current
               DESCRIPTION
                   "Specify whether frames can hit the action according to
                    their ARP/RARP hardware address space (HRD) settings.
                    default: 2,
                    0: ARP/RARP frames where the HLD is not equal to Ethernet(1).
                    1: ARP/RARP frames where the HLD is equal to Ethernet(1).
                    2: Any - Don't care.
                    3: No data."
               DEFVAL  { any }
               ::= {     lcsACLACEEntry 29 }

    lcsACLACEArpFlagsEthernet OBJECT-TYPE
               SYNTAX      INTEGER { notEqualIp(0), equalIp(1),
                                     any(2), noData(3)}
               MAX-ACCESS  read-create
               STATUS      current
               DESCRIPTION
                   "Specify whether frames can hit the action
                    according to their ARP/RARP protocol address space (PRO) settings.
                    default: 2,
                    0: ARP/RARP frames where the PRO is not equal to IP\n(0x800).
                    1: ARP/RARP frames where the PRO is equal to IP(0x800).
                    2: Any - Don't care.
                    3: No data."
               DEFVAL  { any }
               ::= {     lcsACLACEEntry 30 }

    lcsACLACESIPType OBJECT-TYPE
               SYNTAX      INTEGER { any(0), ip(1), network(2), noData(3) }
               MAX-ACCESS  read-create
               STATUS      current
               DESCRIPTION
                   "Configure source IP address for this ACE.
                    default: 0,
                    0: Any - Don't care.
                    1: IP Address.
                    2: Network.
                    3: No data."
               DEFVAL  { any }
               ::= {     lcsACLACEEntry 31 }

    lcsACLACESIPIPAddress OBJECT-TYPE
               SYNTAX      IpAddress
               MAX-ACCESS  read-create
               STATUS      current
               DESCRIPTION
                   "A frame that hits this ACE matches this source IP address
                    value."
               ::= {     lcsACLACEEntry 32 }

    lcsACLACESIPIPMask OBJECT-TYPE
               SYNTAX      IpAddress
               MAX-ACCESS  read-create
               STATUS      current
               DESCRIPTION
                   "Specific sender IP mask in dotted decimal notation."
               ::= {     lcsACLACEEntry 33 }

    lcsACLACEDIPType OBJECT-TYPE
               SYNTAX      INTEGER { any(0), ip(1), network(2), noData(3) }
               MAX-ACCESS  read-create
               STATUS      current
               DESCRIPTION
                   "Configure destination IP address for this ACE.
                    default: 0,
                    0: Any - Don't care.
                    1: IP Address.
                    2: Network.
                    3: No data."
               DEFVAL  { any }
               ::= {     lcsACLACEEntry 34 }

    lcsACLACEDIPIPAddress OBJECT-TYPE
               SYNTAX      IpAddress
               MAX-ACCESS  read-create
               STATUS      current
               DESCRIPTION
                   "A frame that hits this ACE matches this destination IP
                    address value."
               ::= {     lcsACLACEEntry 35 }

    lcsACLACEDIPIPMask OBJECT-TYPE
               SYNTAX      IpAddress
               MAX-ACCESS  read-create
               STATUS      current
               DESCRIPTION
                   "Specific sender IP mask in dotted decimal notation."
               ::= {     lcsACLACEEntry 36 }

    lcsACLACEIPProtocol OBJECT-TYPE
               SYNTAX      INTEGER{ any(0), icmp(1), udp(2), tcp(3),
                                    other(4), noData(5)}
               MAX-ACCESS  read-create
               STATUS      current
               DESCRIPTION
                   "Specify the IP protocol filter for this ACE.
                    default: 0,
                    0: Any,
                    1: ICMP,
                    2: UDP,
                    3: TCP,
                    4: Other,
                    5: no data."
               DEFVAL  { any }
               ::= {     lcsACLACEEntry 37 }

    lcsACLACEIPProtocolValue OBJECT-TYPE
               SYNTAX      Integer32(0..256)
               MAX-ACCESS  read-create
               STATUS      current
               DESCRIPTION
                   "Configure IP protocol value for this ACE when IP Protocol
                    is 'other'.
                    default: 256,
                    256: No data.
                    range : 0 - 256"
               ::= {     lcsACLACEEntry 38 }

    lcsACLACEIPFlagsTTL OBJECT-TYPE
               SYNTAX      INTEGER { nonZero(0), zero(1), any(2), noData(3) }
               MAX-ACCESS  read-create
               STATUS      current
               DESCRIPTION
                   "Specify the Time-to-Live settings for this ACE.
                    default: 0,
                    0: zero,
                    1: Non-Zero
                    2: Any,,
                    3: No data."
               DEFVAL  { nonZero }
               ::= {     lcsACLACEEntry 39 }

    lcsACLACEIPFlagsFragment OBJECT-TYPE
               SYNTAX      INTEGER{yes(0), no(1), any(2), noData(3)}
               MAX-ACCESS  read-create
               STATUS      current
               DESCRIPTION
                   "Specify the fragment offset settings for this ACE.
                    default: 2,
                    0: No,
                    1: Yes,
                    2: Any,
                    3: No data."
               DEFVAL  { any }
               ::= {     lcsACLACEEntry 40 }

    lcsACLACEIPFlagsOptions OBJECT-TYPE
               SYNTAX      INTEGER{yes(0), no(1), any(2),  noData(3)}
               MAX-ACCESS  read-create
               STATUS      current
               DESCRIPTION
                   "Specify the options flag setting for this ACE.
                    default: 2,
                    0: No,
                    1: Yes,
                    2: Any,
                    3: No data."
               DEFVAL  { any }
               ::= {     lcsACLACEEntry 41 }

    lcsACLACEICMPType OBJECT-TYPE
               SYNTAX      Integer32(0..257)
               MAX-ACCESS  read-create
               STATUS      current
               DESCRIPTION
                   "Configure ICMP type for this ACE.
                    default: 256,
                    256: Any - Don't care.
                    257: No data.
                    range : 0 - 257."
               ::= { lcsACLACEEntry 42 }

    lcsACLACEICMPCode OBJECT-TYPE
               SYNTAX      Integer32(0..257)
               MAX-ACCESS  read-create
               STATUS      current
               DESCRIPTION
                   "Configure ICMP code for this ACE.
                    default: 256,
                    256: Any - Don't care.
                    257: No data.
                    range : 0 - 257."
               ::= {     lcsACLACEEntry 43 }

    lcsACLACESourcePort OBJECT-TYPE
               SYNTAX      DisplayString
               MAX-ACCESS  read-create
               STATUS      current
               DESCRIPTION
                   "Configure Source UDP/TCP port range for this ACE.
                    default: any,
                    specific: 0~65535,
                    range : 0 - 65535."
               ::= {     lcsACLACEEntry 44 }

    lcsACLACEDestPort OBJECT-TYPE
               SYNTAX      DisplayString
               MAX-ACCESS  read-create
               STATUS      current
               DESCRIPTION
                   "Configure Destination UDP/TCP port range for this ACE.
                    default: any,
                    specific: 0~65535,
                    range : 0 - 65535."
               ::= {     lcsACLACEEntry 45 }

    lcsACLACETCPFlagsFin OBJECT-TYPE
               SYNTAX      INTEGER { unset(0), set(1), any(2), noData(3) }
               MAX-ACCESS  read-create
               STATUS      current
               DESCRIPTION
                   "Configure TCP (FIN) flags for this ACE.
                    default: 2,
                    0: TCP frames where the FIN field is unset.
                    1: TCP frames where the FIN field is set.
                    2: Any - Don't care.
                    3: No data."
               DEFVAL  { any }
               ::= {     lcsACLACEEntry 46 }

    lcsACLACETCPFlagsSyn OBJECT-TYPE
               SYNTAX      INTEGER { unset(0), set(1), any(2), noData(3) }
               MAX-ACCESS  read-create
               STATUS      current
               DESCRIPTION
                   "Configure TCP (SYN) flags for this ACE.
                    default: 2,
                    0: TCP frames where the SYN field is unset.
                    1: TCP frames where the SYN field is set.
                    2: Any - Don't care.
                    3: No data."
               DEFVAL  { any }
               ::= {     lcsACLACEEntry 47 }

    lcsACLACETCPFlagsRst OBJECT-TYPE
               SYNTAX      INTEGER { unset(0), set(1), any(2), noData(3) }
               MAX-ACCESS  read-create
               STATUS      current
               DESCRIPTION
                   "Configure TCP (RST) flags for this ACE.
                    default: 2,
                    0: TCP frames where the RST field is unset.
                    1: TCP frames where the RST field is set.
                    2: Any - Don't care.
                    3: No data."
               DEFVAL  { any }
               ::= {     lcsACLACEEntry 48 }

    lcsACLACETCPFlagsPsh OBJECT-TYPE
               SYNTAX      INTEGER { unset(0), set(1), any(2), noData(3) }
               MAX-ACCESS  read-create
               STATUS      current
               DESCRIPTION
                   "Configure TCP (PSH) flags for this ACE.
                    default: 2,
                    0: TCP frames where the PSH field is unset.
                    1: TCP frames where the PSH field is set.
                    2: Any - Don't care.
                    3: No data."
               DEFVAL  { any }
               ::= {     lcsACLACEEntry 49 }

    lcsACLACETCPFlagsAck OBJECT-TYPE
               SYNTAX      INTEGER { unset(0), set(1), any(2), noData(3) }
               MAX-ACCESS  read-create
               STATUS      current
               DESCRIPTION
                   "Configure TCP (ACK) flags for this ACE.
                    default: 2,
                    0: TCP frames where the ACK field is unset.
                    1: TCP frames where the ACK field is set.
                    2: Any - Don't care.
                    3: No data."
               DEFVAL  { any }
               ::= {     lcsACLACEEntry 50 }

    lcsACLACETCPFlagsUrg OBJECT-TYPE
               SYNTAX      INTEGER { unset(0), set(1), any(2), noData(3) }
               MAX-ACCESS  read-create
               STATUS      current
               DESCRIPTION
                   "Configure TCP (URG) flags for this ACE.
                    default: 2,
                    0: TCP frames where the URG field is unset.
                    1: TCP frames where the URG field is set.
                    2: Any - Don't care.
                    3: No data."
               DEFVAL  { any }
               ::= {     lcsACLACEEntry 51 }

    lcsACLACEIPv6SIPAddress OBJECT-TYPE
               SYNTAX      DisplayString
               MAX-ACCESS  read-create
               STATUS      current
               DESCRIPTION
                   "When 'Specific' is selected for the source IPv6 filter,
                    you can enter a specific SIPv6 address.
                    The field only supported last 32 bits for IPv6 address. "
               ::= {     lcsACLACEEntry 52 }

    lcsACLACEIPv6SIPBitmask OBJECT-TYPE
               SYNTAX      DisplayString
               MAX-ACCESS  read-create
               STATUS      current
               DESCRIPTION
                   "When 'Specific' is selected for the source IPv6 filter,
                    you can enter a specific SIPv6 mask.
                    The field only supported last 32 bits for IPv6 address. "
               ::= {     lcsACLACEEntry 53 }

    lcsACLACEIPv6HopLimit OBJECT-TYPE
               SYNTAX      INTEGER { unset(0), set(1), any(2), noData(3) }
               MAX-ACCESS  read-create
               STATUS      current
               DESCRIPTION
                   "Specify the hop limit settings for this ACE.
                    default: 2,
                    0: Where the Hop Limit field is unset.
                    1: Where the Hop Limit field is set.
                    2: Any - Don't care,
                    3: No data."
               DEFVAL  { any }
               ::= {     lcsACLACEEntry 54 }

    lcsACLACESMACMask OBJECT-TYPE
               SYNTAX      DisplayString
               MAX-ACCESS  read-create
               STATUS      current
               DESCRIPTION
                   "Configure source MAC address mask for this ACE.
                    <mac-address>: A frame that hits this ACE matches this
                    source MAC address value. xx-xx-xx-xx-xx-xx."
               ::= {    lcsACLACEEntry 56 }

    lcsACLACEDMACMask OBJECT-TYPE
               SYNTAX      DisplayString
               MAX-ACCESS  read-create
               STATUS      current
               DESCRIPTION
                   "Configure destination MAC address mask for this ACE.
                    <mac-address>: A frame that hits this ACE matches this
                    destination MAC address value. xx-xx-xx-xx-xx-xx."
               ::= {     lcsACLACEEntry 57 }

    lcsACLACERowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     lcsACLACEEntry 58 }

--
-- =======================================================================================================================
-- Start lcsACLStatus group
-- =======================================================================================================================
--lcsACLStatusTable

    lcsACLStatusTable OBJECT-TYPE
               SYNTAX      SEQUENCE OF     LCSACLStatusEntry
               MAX-ACCESS  not-accessible
               STATUS      current
               DESCRIPTION
                   " ACL ACE Status entry. "
               ::= {     lcsACL 4 }

    lcsACLStatusEntry OBJECT-TYPE
               SYNTAX          LCSACLStatusEntry
               MAX-ACCESS  not-accessible
               STATUS      current
               DESCRIPTION
                   "The ACL Status Entry."
               INDEX    {    lcsACLStatusIndex  }
               ::= {     lcsACLStatusTable 1 }

    LCSACLStatusEntry             ::= SEQUENCE {
                 lcsACLStatusIndex          Integer32,
                 lcsACLStatusUser           DisplayString,
                 lcsACLStatusID             Integer32,
                 lcsACLStatusIngressPort    DisplayString,
                 lcsACLStatusFrameType      DisplayString,
                 lcsACLStatusAction         DisplayString,
                 lcsACLStatusRateLimiter    DisplayString,
                 lcsACLStatusPortRedirect   DisplayString,
                 lcsACLStatusMirror         DisplayString,
                 lcsACLStatusCPU            DisplayString,
                 lcsACLStatusCPUOnce        DisplayString,
                 lcsACLStatusCounter        Counter32,
                 lcsACLStatusConflict       DisplayString
                 }

    lcsACLStatusIndex OBJECT-TYPE
               SYNTAX      Integer32(1..256)
               MAX-ACCESS  not-accessible
               STATUS      current
               DESCRIPTION
                   "The ACL status index. "
               ::= {     lcsACLStatusEntry 1 }

    lcsACLStatusUser OBJECT-TYPE
               SYNTAX      DisplayString
               MAX-ACCESS  read-only
               STATUS      current
               DESCRIPTION
                   "Indicates the ACL user.
                    S : Static,
                    IPMG : IP Management,
                    IPSG : IP Source Guard,
                    IPMC : IPMC,
                    ARPI : Arp Inspection,
                    UPnP : UPnP,
                    DHCP : DHCP. "
               ::= {     lcsACLStatusEntry 2 }

    lcsACLStatusID OBJECT-TYPE
               SYNTAX      Integer32(1..256)
               MAX-ACCESS  read-only
               STATUS      current
               DESCRIPTION
                   "ACE ID.
                    range : 1 - 256. "
               ::= {     lcsACLStatusEntry 3 }

    lcsACLStatusIngressPort OBJECT-TYPE
               SYNTAX      DisplayString
               MAX-ACCESS  read-only
               STATUS      current
               DESCRIPTION
                   "Indicates the ingress port of the ACE. Possible values are:
                    All: The ACE will match all ingress port.
                    Port: The ACE will match a specific ingress port. "
               ::= {     lcsACLStatusEntry 4 }

    lcsACLStatusFrameType OBJECT-TYPE
               SYNTAX      DisplayString
               MAX-ACCESS  read-only
               STATUS      current
               DESCRIPTION
                   "Indicates the frame type of the ACE.
                    Any: The ACE will match any frame type.
                    EType: The ACE will match Ethernet Type frames.
                    Note that an Ethernet Type based ACE will not get matched
                    by IP and ARP frames.
                    ARP: The ACE will match ARP/RARP frames.
                    IPv4: The ACE will match all IPv4 frames.
                    IPv4/ICMP: The ACE will match IPv4 frames with ICMP protocol.
                    IPv4/UDP: The ACE will match IPv4 frames with UDP protocol.
                    IPv4/TCP: The ACE will match IPv4 frames with TCP protocol.
                    IPv4/Other: The ACE will match IPv4 frames, which are not
                    ICMP/UDP/TCP.
                    IPv6: The ACE will match all IPv6 standard frames. "
               ::= {     lcsACLStatusEntry 5 }

    lcsACLStatusAction OBJECT-TYPE
               SYNTAX      DisplayString
               MAX-ACCESS  read-only
               STATUS      current
               DESCRIPTION
                   "Indicates the forwarding action of the ACE. "
               ::= {     lcsACLStatusEntry 6 }

    lcsACLStatusRateLimiter OBJECT-TYPE
               SYNTAX      DisplayString
               MAX-ACCESS  read-only
               STATUS      current
               DESCRIPTION
                   "Indicates the rate limiter number of the ACE. "
               ::= {     lcsACLStatusEntry 7 }

    lcsACLStatusPortRedirect OBJECT-TYPE
               SYNTAX      DisplayString
               MAX-ACCESS  read-only
               STATUS      current
               DESCRIPTION
                   "Indicates the port redirect operation of the ACE.
                    Frames matching the ACE are redirected to the port number. "
               ::= {     lcsACLStatusEntry 8 }

    lcsACLStatusMirror OBJECT-TYPE
               SYNTAX      DisplayString
               MAX-ACCESS  read-only
               STATUS      current
               DESCRIPTION
                   "Specify the mirror operation of this port."
               ::= {     lcsACLStatusEntry 9 }

    lcsACLStatusCPU OBJECT-TYPE
               SYNTAX      DisplayString
               MAX-ACCESS  read-only
               STATUS      current
               DESCRIPTION
                   "Forward packet that matched the specific ACE to CPU. "
               ::= {     lcsACLStatusEntry 10 }

    lcsACLStatusCPUOnce OBJECT-TYPE
               SYNTAX      DisplayString
               MAX-ACCESS  read-only
               STATUS      current
               DESCRIPTION
                   "Forward first packet that matched the specific ACE to CPU. "
               ::= {     lcsACLStatusEntry 11 }

    lcsACLStatusCounter OBJECT-TYPE
               SYNTAX      Counter32
               MAX-ACCESS  read-only
               STATUS      current
               DESCRIPTION
                   "The counter indicates the number of times the ACE was hit
                    by a frame. "
               ::= {     lcsACLStatusEntry 12 }

    lcsACLStatusConflict OBJECT-TYPE
               SYNTAX      DisplayString
               MAX-ACCESS  read-only
               STATUS      current
               DESCRIPTION
                   "Indicates the hardware status of the specific ACE.
                    The specific ACE is not applied to the hardware due to
                    hardware limitations. "
               ::= {     lcsACLStatusEntry 13 }


-- =======================================================================================================================
-- lcsAclConformance
-- =======================================================================================================================
lcsAclConformance OBJECT IDENTIFIER ::= { lcsACL 200 }

lcsAclCompliances OBJECT IDENTIFIER ::= { lcsAclConformance 1 }

lcsAclGroups    OBJECT IDENTIFIER ::= { lcsAclConformance 2 }

lcsACLPortConfGroup OBJECT-GROUP
    OBJECTS {
                -- lcsACLPortConfTable
                 lcsACLPortConfPolicyID,
                 lcsACLPortConfAction,
                 lcsACLPortConfRateLimiterID,
                 lcsACLPortConfPortRedirect,
                 lcsACLPortConfMirror,
                 lcsACLPortConfLogging,
                 lcsACLPortConfShutdown,
                 lcsACLPortConfState,
                 lcsACLPortConfCounter
            }
     STATUS  current
     DESCRIPTION
            "The collection of objects which are used to indicate
            lcs ACL information."
    ::= { lcsAclGroups 1 }

lcsACLRateLimiterGroup OBJECT-GROUP
    OBJECTS {
                -- lcsACLRateLimiterTable
                 lcsACLRateLimiterRate,
                 lcsACLRateLimiterUnit
            }
     STATUS  current
     DESCRIPTION
            "The collection of objects which are used to indicate
            lcs ACL information."
    ::= { lcsAclGroups 2 }

lcsACLACEGroup OBJECT-GROUP
    OBJECTS {
                -- lcsACLACEClear
                 lcsACLACEClear,

                -- lcsACLACETable
                 lcsACLACEID,
                 lcsACLACENextID,
--               lcsACLACELoopUp,
                 lcsACLACEIngressPort,
                 lcsACLACEPortPolicyNumber,
                 lcsACLACEPortPolicyBitmask,
                 lcsACLACEFrameType,
                 lcsACLACEAction,
                 lcsACLACEFilterPort,
                 lcsACLACEDenyPortRedirect,
                 lcsACLACERateLimiter,
                 lcsACLACEMirror,
                 lcsACLACELogging,
                 lcsACLACEShutdown,
                 lcsACLACECounter,
                 lcsACLACEVLAN8021QTagged,
                 lcsACLACEVLANVID,
                 lcsACLACEVLANTagPriority,
                 lcsACLACESMAC,
                 lcsACLACEDMACType,
                 lcsACLACEDMAC,
                 lcsACLACEEtherType,
                 lcsACLACEArpOpCode,
                 lcsACLACEArpFlagsRequestReply,
                 lcsACLACEArpFlagsArpSMac,
                 lcsACLACEArpFlagsRarpDmac,
                 lcsACLACEArpFlagsLength,
                 lcsACLACEArpFlagsIp,
                 lcsACLACEArpFlagsEthernet,
                 lcsACLACESIPType,
                 lcsACLACESIPIPAddress,
                 lcsACLACESIPIPMask,
                 lcsACLACEDIPType,
                 lcsACLACEDIPIPAddress,
                 lcsACLACEDIPIPMask,
                 lcsACLACEIPProtocol,
                 lcsACLACEIPProtocolValue,
                 lcsACLACEIPFlagsTTL,
                 lcsACLACEIPFlagsFragment,
                 lcsACLACEIPFlagsOptions,
                 lcsACLACEICMPType,
                 lcsACLACEICMPCode,
                 lcsACLACESourcePort,
                 lcsACLACEDestPort,
                 lcsACLACETCPFlagsFin,
                 lcsACLACETCPFlagsSyn,
                 lcsACLACETCPFlagsRst,
                 lcsACLACETCPFlagsPsh,
                 lcsACLACETCPFlagsAck,
                 lcsACLACETCPFlagsUrg,
                 lcsACLACEIPv6SIPAddress,
                 lcsACLACEIPv6SIPBitmask,
                 lcsACLACEIPv6HopLimit,
                 lcsACLACERowStatus
            }
     STATUS  current
     DESCRIPTION
            "The collection of objects which are used to indicate
            lcs ACL information."
    ::= { lcsAclGroups 3 }

lcsACLStatusGroup OBJECT-GROUP
    OBJECTS {
                -- lcsACLStatusTable
                 lcsACLStatusUser,
                 lcsACLStatusID,
                 lcsACLStatusIngressPort,
                 lcsACLStatusFrameType,
                 lcsACLStatusAction,
                 lcsACLStatusRateLimiter,
                 lcsACLStatusPortRedirect,
                 lcsACLStatusMirror,
                 lcsACLStatusCPU,
                 lcsACLStatusCPUOnce,
                 lcsACLStatusCounter,
                 lcsACLStatusConflict
            }
     STATUS  current
     DESCRIPTION
            "The collection of objects which are used to indicate
            lcs ACL information."
    ::= { lcsAclGroups 4 }


-- =======================================================================================================================
-- =======================================================================================================================
 -- RowStatus Info:  createAndGo, notReady not supported.
-- =======================================================================================================================
-- Textual Conventions for the lcs Qos Mib
-- =======================================================================================================================
--
lcsQosConf                    OBJECT IDENTIFIER ::= { lcsConfiguration 10 }
    lcsQos                        OBJECT IDENTIFIER   ::= { lcsQosConf  1  }
    lcsQosPortClassification      OBJECT IDENTIFIER   ::= { lcsQos 1 }
    lcsQosPortPolicing            OBJECT IDENTIFIER   ::= { lcsQos 2 }
--  lcsQosQueuePolicing           OBJECT IDENTIFIER   ::= { lcsQos 3 }
--  lcsQosPortScheduler           OBJECT IDENTIFIER   ::= { lcsQos 4 }
    lcsQosEgressPortPCPRemarking  OBJECT IDENTIFIER   ::= { lcsQos 6 }
    lcsQosPortDSCP                OBJECT IDENTIFIER   ::= { lcsQos 7 }
    lcsQosDSCPBasedQoS            OBJECT IDENTIFIER   ::= { lcsQos 8 }
    lcsQosDSCPTranslation         OBJECT IDENTIFIER   ::= { lcsQos 9 }
    lcsQosDSCPClassification      OBJECT IDENTIFIER   ::= { lcsQos 10 }
    lcsQosControlList             OBJECT IDENTIFIER   ::= { lcsQos 11 }
    lcsQosStormControl            OBJECT IDENTIFIER   ::= { lcsQos 12 }
    lcsQosPortStormControl        OBJECT IDENTIFIER   ::= { lcsQos 13 }
    lcsQosWRED                    OBJECT IDENTIFIER   ::= { lcsQos 14 }
    lcsQosQCLStatus               OBJECT IDENTIFIER   ::= { lcsQos 15 }
    lcsQosPortShapers             OBJECT IDENTIFIER   ::= { lcsQos 16 }
    lcsQosPortSchedulers          OBJECT IDENTIFIER   ::= { lcsQos 17 }
--
-- =======================================================================================================================
-- Start lcsQosPortClassification group
-- =======================================================================================================================
--lcsQosPortClassificationTable

     lcsQosPortClassificationTable OBJECT-TYPE
               SYNTAX      SEQUENCE OF     LCSQosPortClassificationEntry
               MAX-ACCESS  not-accessible
               STATUS      current
               DESCRIPTION
                   "QoS Ingress Port Classification.
                    INDEX for this table is ifIndex which is
                    equivalent to the panel port number."
               ::= {     lcsQosPortClassification  1 }

    lcsQosPortClassificationEntry OBJECT-TYPE
               SYNTAX          LCSQosPortClassificationEntry
               MAX-ACCESS  not-accessible
               STATUS      current
               DESCRIPTION
                   "The Qos Port Classification Table."
               INDEX    {     ifIndex  }
               ::= {     lcsQosPortClassificationTable 1 }

    LCSQosPortClassificationEntry             ::= SEQUENCE {
                lcsQosPortClassificationQoSClass        Integer32,
                lcsQosPortClassificationDPlevel         Integer32,
                lcsQosPortClassificationPCP             Integer32,
                lcsQosPortClassificationDEI             Integer32,
                lcsQosPortClassificationPCPClassification AdminMode,
                lcsQosPortClassificationDSCPBased       AdminMode,
--              lcsQosPortClassificationQCLAddr         INTEGER,
--              lcsQosPortClassificationKeyType         KeyType,
                lcsQosPortClassificationWredGroup       Integer32 
                }

    lcsQosPortClassificationQoSClass OBJECT-TYPE
               SYNTAX      Integer32(0..7)
               MAX-ACCESS  read-write
               STATUS      current
               DESCRIPTION
                  "Controls the default QoS class, i.e., the QoS class for
                   frames not classified
                   in any way. There is a one to one mapping between
                   QoS class, queue and
                   priority. A QoS class of 0 (zero) has the lowest priority.
                   NOTe: If the QoS class has been dynamically changed, then
                   the actual QoS class
                   is shown in parentheses after the configured QoS class.
                   range: 0~7,
                   default: 0."
               ::= {     lcsQosPortClassificationEntry 2 }

    lcsQosPortClassificationDPlevel OBJECT-TYPE
               SYNTAX      Integer32(0..3)
               MAX-ACCESS  read-write
               STATUS      current
               DESCRIPTION
                   "DP level for frames not classified in any way.
                    range: 0~3,
                    default: 0."
               ::= {     lcsQosPortClassificationEntry 3 }

    lcsQosPortClassificationPCP OBJECT-TYPE
               SYNTAX      Integer32(0..7)
               MAX-ACCESS  read-write
               STATUS      current
               DESCRIPTION
                  "Priority Code Point. It is a 3-bit field storing
                   the priority level for the 802.1Q frame.
                   range: 0~7,
                   default: 0.
                   "
               ::= {     lcsQosPortClassificationEntry 4 }

    lcsQosPortClassificationDEI OBJECT-TYPE
               SYNTAX      Integer32(0|1)
               MAX-ACCESS  read-write
               STATUS      current
               DESCRIPTION
                  "Drop Eligible Indicator. It is a 1-bit field in the VLAN.
                   range 0~1,
                   default: 0.
                  "
               ::= {     lcsQosPortClassificationEntry 5 }

    lcsQosPortClassificationPCPClassification OBJECT-TYPE
               SYNTAX      AdminMode
               MAX-ACCESS  read-write
               STATUS      current
               DESCRIPTION
                  "Configure the classification mode for tagged frames.
                  "
               DEFVAL  { disable }
               ::= {     lcsQosPortClassificationEntry 6 }

    lcsQosPortClassificationDSCPBased OBJECT-TYPE
               SYNTAX      AdminMode
               MAX-ACCESS  read-write
               STATUS      current
               DESCRIPTION
                  "Click to Enable DSCP Based QoS Ingress Port Classification."
               DEFVAL  { disable }
               ::= {     lcsQosPortClassificationEntry 7 }

--    lcsQosPortClassificationQCLAddr OBJECT-TYPE
--               SYNTAX      INTEGER { sMacSip(0), dMacDip (1) }
--               MAX-ACCESS  read-write
--               STATUS      current
--               DESCRIPTION
--                  "Controls the QCL address matching mode.
--                   0: SMAC/SIP,
--                   1: DMAC/DIP,
--                  default: SMAC/SIP.
--                  Only support SPARX_III."
--               DEFVAL  { sMacSip }
--               ::= {     lcsQosPortClassificationEntry 8 }

--    lcsQosPortClassificationKeyType OBJECT-TYPE
--               SYNTAX      KeyType
--               MAX-ACCESS  read-write
--               STATUS      current
--               DESCRIPTION
--                  "The key type specifying the key generated for frames received
--                   on the port.
--                   0: Normal, Half key, match outer tag, SIP/DIP and SMAC/DMAC.
--                   1: Double Tag: Quarter key, match inner and outer tag.
--                   2: IP Address: Half key, match inner and outer tag, SIP and
--                      DIP. For non-IP frames, match outer tag only.
--                   3: MAC and IP Address: Full key, match inner and outer tag,
--                      SMAC, DMAC, SIP and DIP.
--                   Only support on SERVAL version."
--               DEFVAL  { normal }
--               ::= {     lcsQosPortClassificationEntry 9 }
               
    lcsQosPortClassificationWredGroup OBJECT-TYPE
               SYNTAX      Integer32
               MAX-ACCESS  read-write
               STATUS      current
               DESCRIPTION
                  "Controls the WRED group membership. Range:1-3."
               ::= {     lcsQosPortClassificationEntry 10 }            

--lcsQoSIngressPortTagClassificationTable
    lcsQoSIngressPortTagClassificationTable OBJECT-TYPE
               SYNTAX      SEQUENCE OF     LCSQoSIngressPortTagClassificationEntry
               MAX-ACCESS  not-accessible
               STATUS      current
               DESCRIPTION
                   "Show QoS Ingress Port Tag Classification.
                    INDEX for this table is ifIndex which is
                    equivalent to the panel port number."
               ::= {     lcsQosPortClassification 2 }

    lcsQoSIngressPortTagClassificationEntry OBJECT-TYPE
               SYNTAX          LCSQoSIngressPortTagClassificationEntry
               MAX-ACCESS  not-accessible
               STATUS      current
               DESCRIPTION
                   "QoS Ingress Port Tag Classification entry."
               INDEX    {     ifIndex,
                              lcsQoSIngressPortTagPCP,
                              lcsQoSIngressPortTagDEI  }
               ::= {     lcsQoSIngressPortTagClassificationTable 1 }

    LCSQoSIngressPortTagClassificationEntry             ::= SEQUENCE {
                lcsQoSIngressPortTagPCP                   INTEGER,
                lcsQoSIngressPortTagDEI                   INTEGER,
                lcsQoSIngressPortTagQosClass              Integer32,
                lcsQoSIngressPortTagDPLevel               Integer32
                }

    lcsQoSIngressPortTagPCP OBJECT-TYPE
               SYNTAX      INTEGER { pcp0(1),
                                     pcp1(2),
                                     pcp2(3),
                                     pcp3(4),
                                     pcp4(5),
                                     pcp5(6),
                                     pcp6(7),
                                     pcp7(8) }
               MAX-ACCESS  not-accessible
               STATUS      current
               DESCRIPTION
                   "range: 1-8,
                    PCP0:1, PCP1:2..."
               ::= {     lcsQoSIngressPortTagClassificationEntry 2 }

    lcsQoSIngressPortTagDEI OBJECT-TYPE
               SYNTAX      INTEGER { dei0(1), dei1(2) }
               MAX-ACCESS  not-accessible
               STATUS      current
               DESCRIPTION
                   "Ingress Port Tag dei,
                    DEI0:1, DEI1:2."
               ::= {     lcsQoSIngressPortTagClassificationEntry 3 }

    lcsQoSIngressPortTagQosClass OBJECT-TYPE
               SYNTAX      Integer32(0..7)
               MAX-ACCESS  read-write
               STATUS      current
               DESCRIPTION
                   "range: 0-7."
               ::= {     lcsQoSIngressPortTagClassificationEntry 4 }

    lcsQoSIngressPortTagDPLevel OBJECT-TYPE
               SYNTAX      Integer32(0..3)
               MAX-ACCESS  read-write
               STATUS      current
               DESCRIPTION
                   "range: 0-3."
               ::= {     lcsQoSIngressPortTagClassificationEntry 5 }


--
-- =======================================================================================================================
-- Start lcsQosPortPolicing group
-- =======================================================================================================================
--lcsQosPortPolicingTable
   lcsQosPortPolicingTable OBJECT-TYPE
               SYNTAX      SEQUENCE OF     LCSQosPortPolicingEntry
               MAX-ACCESS  not-accessible
               STATUS      current
               DESCRIPTION
                   "The Policer settings.
                    INDEX for this table is ifIndex which is
                    equivalent to the panel port number."
               ::= {     lcsQosPortPolicing 1 }

    lcsQosPortPolicingEntry OBJECT-TYPE
               SYNTAX          LCSQosPortPolicingEntry
               MAX-ACCESS  not-accessible
               STATUS      current
               DESCRIPTION
                   "The Policer setting entry."
               INDEX    {     ifIndex  }
               ::= {     lcsQosPortPolicingTable 1 }

    LCSQosPortPolicingEntry             ::= SEQUENCE {
                lcsQosPortPolicingEnabled         AdminMode,
                lcsQosPortPolicingRate            Integer32,
                lcsQosPortPolicingUnit            Integer32,
                lcsQosPortPolicingFlowControl     AdminMode
                }

    lcsQosPortPolicingEnabled OBJECT-TYPE
               SYNTAX      AdminMode
               MAX-ACCESS  read-write
               STATUS      current
               DESCRIPTION
                  "Controls whether the policer is enabled on this switch port."
               DEFVAL  { disable }
               ::= {     lcsQosPortPolicingEntry 2 }

    lcsQosPortPolicingRate OBJECT-TYPE
               SYNTAX      Integer32
               MAX-ACCESS  read-write
               STATUS      current
               DESCRIPTION
                   "Controls the rate for the policer.
                    default: 500(kbps)."
               ::= {     lcsQosPortPolicingEntry 3 }

    lcsQosPortPolicingUnit OBJECT-TYPE
               SYNTAX      Integer32
               MAX-ACCESS  read-write
               STATUS      current
               DESCRIPTION
                   "Controls the unit of measure for the policer rate.
                    0: kbps
                    1: Mbps
                    2: fps
                    3: kfps
                    "
               ::= {     lcsQosPortPolicingEntry 4 }

    lcsQosPortPolicingFlowControl OBJECT-TYPE
               SYNTAX      AdminMode
               MAX-ACCESS  read-write
               STATUS      current
               DESCRIPTION
                   "If flow control is enabled and the port is in flow control mode,
                    then pause frames are sent instead of discarding frames."
               DEFVAL  { disable }
               ::= {     lcsQosPortPolicingEntry 5 }

--
-- =======================================================================================================================
-- Start lcsQosQueuePolicing group
-- =======================================================================================================================
--lcsQosQueuePolicingTable
--    lcsQosQueuePolicingTable OBJECT-TYPE
--               SYNTAX      SEQUENCE OF     LCSQosQueuePolicingEntry
--               MAX-ACCESS  not-accessible
--               STATUS      current
--               DESCRIPTION
--                   "The Queue Policer settings.
--                    INDEX for this table is ifIndex which is
--                    equivalent to the panel port number."
--               ::= {     lcsQosQueuePolicing 1 }
--
--    lcsQosQueuePolicingEntry OBJECT-TYPE
--               SYNTAX          LCSQosQueuePolicingEntry
--               MAX-ACCESS  not-accessible
--               STATUS      current
--               DESCRIPTION
--                   "The Qos Queue Policing Entry."
--               INDEX    {     ifIndex  }
--               ::= {     lcsQosQueuePolicingTable 1 }
--
--    LCSQosQueuePolicingEntry             ::= SEQUENCE {
--                lcsQosQueuePolicingQueue0Enable   AdminMode,
--                lcsQosQueuePolicingQueue0Rate     Integer32,
--      lcsQosQueuePolicingQueue0Unit     Integer32,
--                lcsQosQueuePolicingQueue1Enable   AdminMode,
--                lcsQosQueuePolicingQueue1Rate     Integer32,
--      lcsQosQueuePolicingQueue1Unit     Integer32,
--                lcsQosQueuePolicingQueue2Enable   AdminMode,
--                lcsQosQueuePolicingQueue2Rate     Integer32,
--                lcsQosQueuePolicingQueue2Unit     Integer32,
--                lcsQosQueuePolicingQueue3Enable   AdminMode,
--                lcsQosQueuePolicingQueue3Rate     Integer32,
--                lcsQosQueuePolicingQueue3Unit     Integer32,
--                lcsQosQueuePolicingQueue4Enable   AdminMode,
--                lcsQosQueuePolicingQueue4Rate     Integer32,
--      lcsQosQueuePolicingQueue4Unit     Integer32,
--                lcsQosQueuePolicingQueue5Enable   AdminMode,
--                lcsQosQueuePolicingQueue5Rate     Integer32,
--      lcsQosQueuePolicingQueue5Unit     Integer32,
--                lcsQosQueuePolicingQueue6Enable   AdminMode,
--                lcsQosQueuePolicingQueue6Rate     Integer32,
--      lcsQosQueuePolicingQueue6Unit     Integer32,
--                lcsQosQueuePolicingQueue7Enable   AdminMode,
--                lcsQosQueuePolicingQueue7Rate     Integer32,
--      lcsQosQueuePolicingQueue7Unit     Integer32
--                }
--
--    lcsQosQueuePolicingQueue0Enable OBJECT-TYPE
--               SYNTAX      AdminMode
--               MAX-ACCESS  read-write
--               STATUS      current
--               DESCRIPTION
--                   "Controls whether the queue 0 policer is enabled on this switch port."
--               DEFVAL  { disable }
--               ::= {     lcsQosQueuePolicingEntry 3 }
--
--    lcsQosQueuePolicingQueue0Rate OBJECT-TYPE
--               SYNTAX      Integer32
--               MAX-ACCESS  read-write
--               STATUS      current
--               DESCRIPTION
--                   "Controls whether the queue 0 policer is enabled on this switch port.
--                    default: 500(Kbps)"
--               ::= {     lcsQosQueuePolicingEntry 4 }
--
--    lcsQosQueuePolicingQueue0Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 5 }            
--             
--    lcsQosQueuePolicingQueue1Enable OBJECT-TYPE
--               SYNTAX      AdminMode
--               MAX-ACCESS  read-write
--               STATUS      current
--               DESCRIPTION
--                   "Controls whether the queue 1 policer is enabled on this switch port."
--               DEFVAL  { disable }
--               ::= {     lcsQosQueuePolicingEntry 6 }
--
--    lcsQosQueuePolicingQueue1Rate OBJECT-TYPE
--               SYNTAX      Integer32
--               MAX-ACCESS  read-write
--               STATUS      current
--               DESCRIPTION
--                   "Controls whether the queue 1 policer is enabled on this switch port.,
--                    default: 500(Kbps)"
--               ::= {     lcsQosQueuePolicingEntry 7 }
--             
--    lcsQosQueuePolicingQueue1Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 8 }            
--             
--    lcsQosQueuePolicingQueue2Enable OBJECT-TYPE
--               SYNTAX      AdminMode
--               MAX-ACCESS  read-write
--               STATUS      current
--               DESCRIPTION
--                   "Controls whether the queue 2 policer is enabled on this switch port."
--               DEFVAL  { disable }
--               ::= {     lcsQosQueuePolicingEntry 9 }
--
--    lcsQosQueuePolicingQueue2Rate OBJECT-TYPE
--               SYNTAX      Integer32
--               MAX-ACCESS  read-write
--               STATUS      current
--               DESCRIPTION
--                   "Controls whether the queue 2 policer is enabled on this switch port.
--                    default: 500(Kbps)"
--               ::= {     lcsQosQueuePolicingEntry 10 }
--             
--    lcsQosQueuePolicingQueue2Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 11 }               
--            
--    lcsQosQueuePolicingQueue3Enable OBJECT-TYPE
--               SYNTAX      AdminMode
--               MAX-ACCESS  read-write
--               STATUS      current
--               DESCRIPTION
--                   "Controls whether the queue 3 policer is enabled on this switch port."
--               DEFVAL  { disable }
--               ::= {     lcsQosQueuePolicingEntry 12 }
--
--    lcsQosQueuePolicingQueue3Rate OBJECT-TYPE
--               SYNTAX      Integer32
--               MAX-ACCESS  read-write
--               STATUS      current
--               DESCRIPTION
--                   "Controls whether the queue 3 policer is enabled on this switch port.
--                    default: 500(Kbps)"
--               ::= {     lcsQosQueuePolicingEntry 13 }
--             
--    lcsQosQueuePolicingQueue3Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 14 }               
--             
--    lcsQosQueuePolicingQueue4Enable OBJECT-TYPE
--               SYNTAX      AdminMode
--               MAX-ACCESS  read-write
--               STATUS      current
--               DESCRIPTION
--                   "Controls whether the queue 4 policer is enabled on this switch port."
--               DEFVAL  { disable }
--               ::= {     lcsQosQueuePolicingEntry 15 }
--
--    lcsQosQueuePolicingQueue4Rate OBJECT-TYPE
--               SYNTAX      Integer32
--               MAX-ACCESS  read-write
--               STATUS      current
--               DESCRIPTION
--                   "Controls whether the queue 4 policer is enabled on this switch port.
--                    default: 500(Kbps)"
--               ::= {     lcsQosQueuePolicingEntry 16 }
--             
--    lcsQosQueuePolicingQueue4Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 17 }               
--             
--    lcsQosQueuePolicingQueue5Enable OBJECT-TYPE
--               SYNTAX      AdminMode
--               MAX-ACCESS  read-write
--               STATUS      current
--               DESCRIPTION
--                   "Controls whether the queue 5 policer is enabled on this switch port."
--               DEFVAL  { disable }
--               ::= {     lcsQosQueuePolicingEntry 18 }
--
--    lcsQosQueuePolicingQueue5Rate OBJECT-TYPE
--               SYNTAX      Integer32
--               MAX-ACCESS  read-write
--               STATUS      current
--               DESCRIPTION
--                   "Controls whether the queue 5 policer is enabled on this switch port.
--                    default: 500(Kbps)"
--               ::= {     lcsQosQueuePolicingEntry 19 }
--
--    lcsQosQueuePolicingQueue5Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 20 }               
--                         
--    lcsQosQueuePolicingQueue6Enable OBJECT-TYPE
--               SYNTAX      AdminMode
--               MAX-ACCESS  read-write
--               STATUS      current
--               DESCRIPTION
--                   "Controls whether the queue 6 policer is enabled on this switch port."
--               DEFVAL  { disable }
--               ::= {     lcsQosQueuePolicingEntry 21 }
--
--    lcsQosQueuePolicingQueue6Rate OBJECT-TYPE
--               SYNTAX      Integer32
--               MAX-ACCESS  read-write
--               STATUS      current
--               DESCRIPTION
--                   "Controls whether the queue 6 policer is enabled on this switch port.
--                    default: 500(Kbps)"
--               ::= {     lcsQosQueuePolicingEntry 22 }
--             
--    lcsQosQueuePolicingQueue6Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 23 }               
--             
--    lcsQosQueuePolicingQueue7Enable OBJECT-TYPE
--               SYNTAX      AdminMode
--               MAX-ACCESS  read-write
--               STATUS      current
--               DESCRIPTION
--                   "Controls whether the queue 7 policer is enabled on this switch port."
--               DEFVAL  { disable }
--               ::= {     lcsQosQueuePolicingEntry 24 }
--
--    lcsQosQueuePolicingQueue7Rate OBJECT-TYPE
--               SYNTAX      Integer32
--               MAX-ACCESS  read-write
--               STATUS      current
--               DESCRIPTION
--                   "Controls whether the queue 7 policer is enabled on this switch port.
--                    default: 500(Kbps)"
--               ::= {     lcsQosQueuePolicingEntry 25 }
--
--    lcsQosQueuePolicingQueue7Unit OBJECT-TYPE
--               SYNTAX      Integer32(0|1)
--               MAX-ACCESS  read-write
--               STATUS      current
--               DESCRIPTION
--                   "Controls the unit of measure for the queue policer rate as kbps or Mbps.
--                    range:
--          0:kbs
--          1:Mbps
--                    default: 0(kbps)"
--               ::= {     lcsQosQueuePolicingEntry 26 }               
--
--
-- =======================================================================================================================
-- Start lcsQosPortScheduler group
-- =======================================================================================================================
--lcsQosPortSchedulerModeTable

--     lcsQosPortSchedulerModeTable OBJECT-TYPE
--               SYNTAX      SEQUENCE OF     LCSQosPortSchedulerModeEntry
--               MAX-ACCESS  not-accessible
--               STATUS      current
--               DESCRIPTION
--                   "The basic QoS Port Scheduler Mode settings.
--                    INDEX for this table is ifIndex which is
--                    equivalent to the panel port number."
--               ::= {     lcsQosPortScheduler  1 }
--
--    lcsQosPortSchedulerModeEntry OBJECT-TYPE
--               SYNTAX          LCSQosPortSchedulerModeEntry
--               MAX-ACCESS  not-accessible
--               STATUS      current
--               DESCRIPTION
--                   "The Qos Port Scheduler Mode entry."
--               INDEX    {     ifIndex  }
--               ::= {     lcsQosPortSchedulerModeTable 1 }
--
--    LCSQosPortSchedulerModeEntry             ::= SEQUENCE {
--                lcsQosSchedulerMode            Integer32,
--                lcsQosSchedulerShaper          AdminMode,
--                lcsQosSchedulerShaperRate      Integer32
--                }
--
--    lcsQosSchedulerMode OBJECT-TYPE
--               SYNTAX      Integer32
--               MAX-ACCESS  read-write
--               STATUS      current
--               DESCRIPTION
--                   "Controls whether the scheduler mode is Strict Priority or Weighted
--                    on this switch port.
--                    0:Strict Priority,
--          2: 2 Queues Weighted
--          3: 3 Queues Weighted: only Jaguar2 support
--          4: 4 Queues Weighted: only Jaguar2 support
--          5: 5 Queues Weighted: only Jaguar2 support
--                    6: 6 Queues Weighted
--          7: 7 Queues Weighted: only Jaguar2 support
--          8: 8 Queues Weighted: only Jaguar2 support"
--               ::= {     lcsQosPortSchedulerModeEntry 2 }
--
--    lcsQosSchedulerShaper OBJECT-TYPE
--               SYNTAX      AdminMode
--               MAX-ACCESS  read-write
--               STATUS      current
--               DESCRIPTION
--                   "Controls whether the port shaper is enabled."
--               DEFVAL  { disable }
--               ::= {     lcsQosPortSchedulerModeEntry 3 }
--
--    lcsQosSchedulerShaperRate OBJECT-TYPE
--               SYNTAX      Integer32
--               MAX-ACCESS  read-write
--               STATUS      current
--               DESCRIPTION
--                   "Controls the rate for the port shaper.
--                    default: 500 kbps."
--               ::= {     lcsQosPortSchedulerModeEntry 4 }
--
--lcsQosPortSchedulerTable
--    lcsQosPortSchedulerTable OBJECT-TYPE
--               SYNTAX      SEQUENCE OF     LCSQosPortSchedulerEntry
--               MAX-ACCESS  not-accessible
--               STATUS      current
--               DESCRIPTION
--                   "Show Qos Port Scheduler.
--                    INDEX for this table is ifIndex which is
--                    equivalent to the panel port number."
--               ::= {     lcsQosPortScheduler 2 }
--
--    lcsQosPortSchedulerEntry OBJECT-TYPE
--               SYNTAX          LCSQosPortSchedulerEntry
--               MAX-ACCESS  not-accessible
--               STATUS      current
--               DESCRIPTION
--                   "The Qos Port Scheduler Entry."
--               INDEX    {     ifIndex,
--                              lcsQosSchedulerPortQueue}
--               ::= {     lcsQosPortSchedulerTable 1 }
--
--    LCSQosPortSchedulerEntry             ::= SEQUENCE {
--                lcsQosSchedulerPortQueue                  INTEGER,
--                lcsQosSchedulerPortQueueShaper            AdminMode,
--                lcsQosSchedulerPortQueueShaperRate        Integer32,
--                lcsQosSchedulerPortQueueShaperExcess      AdminMode,
--                lcsQosSchedulerPortQueueSchedulerWeight   Integer32,
--                lcsQosSchedulerPortQueueSchedulerPercent  DisplayString
--                }
--
--    lcsQosSchedulerPortQueue OBJECT-TYPE
--               SYNTAX      INTEGER { q0(1),
--                                     q1(2),
--                                     q2(3),
--                                     q3(4),
--                                     q4(5),
--                                     q5(6),
--                                     q6(7),
--                                     q7(8) }
--               MAX-ACCESS  not-accessible
--               STATUS      current
--               DESCRIPTION
--                   "range: 1-8.
--                    Q0: 1, Q1: 2, ..."
--               ::= {     lcsQosPortSchedulerEntry 2 }
--
--    lcsQosSchedulerPortQueueShaper OBJECT-TYPE
--               SYNTAX     AdminMode
--               MAX-ACCESS  read-write
--               STATUS      current
--               DESCRIPTION
--                   "Qos scheduler admin state."
--               DEFVAL  { disable }
--               ::= {     lcsQosPortSchedulerEntry 3 }
--
--    lcsQosSchedulerPortQueueShaperRate OBJECT-TYPE
--               SYNTAX      Integer32(100..1000000)
--               MAX-ACCESS  read-write
--               STATUS      current
--               DESCRIPTION
--                   "range: 100..1000000 kbps. "
--               ::= {     lcsQosPortSchedulerEntry 4 }
--
--    lcsQosSchedulerPortQueueShaperExcess OBJECT-TYPE
--               SYNTAX      AdminMode
--               MAX-ACCESS  read-write
--               STATUS      current
--               DESCRIPTION
--                   "admin state lcsQosSchedulerPortQueueShaperExcess"
--               DEFVAL  { disable }
--               ::= {     lcsQosPortSchedulerEntry 5 }
--
--    lcsQosSchedulerPortQueueSchedulerWeight OBJECT-TYPE
--               SYNTAX      Integer32(0..100)
--               MAX-ACCESS  read-write
--               STATUS      current
--               DESCRIPTION
--                   "range: 1-100,
--                    default: 17.
--                    Only use in Q0 - Q5.  Q6 & Q7 show 0"
--               ::= {     lcsQosPortSchedulerEntry 6 }
--
--    lcsQosSchedulerPortQueueSchedulerPercent OBJECT-TYPE
--               SYNTAX      DisplayString
--               MAX-ACCESS  read-only
--               STATUS      current
--               DESCRIPTION
--                   "Only use in Q0 - Q5. Q6 & Q7 show empty"
--               ::= {     lcsQosPortSchedulerEntry 7 }
--
-- =======================================================================================================================
-- Start lcsQosEgressPortPCPRemarking group
-- =======================================================================================================================
--lcsQosEgressPortPCPRemarkingTable
    lcsQosEgressPortPCPRemarkingTable OBJECT-TYPE
               SYNTAX      SEQUENCE OF     LCSQosEgressPortPCPRemarkingEntry
               MAX-ACCESS  not-accessible
               STATUS      current
               DESCRIPTION
                   "The basic Qos Egress Port PCP Remarking
                    Configuration settings.
                    INDEX for this table is ifIndex which is
                    equivalent to the panel port number."
               ::= {     lcsQosEgressPortPCPRemarking  1 }

    lcsQosEgressPortPCPRemarkingEntry OBJECT-TYPE
               SYNTAX          LCSQosEgressPortPCPRemarkingEntry
               MAX-ACCESS  not-accessible
               STATUS      current
               DESCRIPTION
                   "The Qos Egress Port PCP Remarking Entry."
               INDEX    {     ifIndex  }
               ::= {     lcsQosEgressPortPCPRemarkingTable 1 }

    LCSQosEgressPortPCPRemarkingEntry             ::= SEQUENCE {
                lcsQosEgressPortPCPRemarkingMode                    INTEGER
                }

    lcsQosEgressPortPCPRemarkingMode OBJECT-TYPE
               SYNTAX      INTEGER { keep(0), specific(1), mapped(2) }
               MAX-ACCESS  read-write
               STATUS      current
               DESCRIPTION
                   "the tag remarking mode for this port.
                    0:Keep, Use classified PCP/DEI values.
                    1:Specific, Use default PCP/DEI values.
                    2:Mapped, Use mapped versions of QoS class and DP level."
               ::= {     lcsQosEgressPortPCPRemarkingEntry 2 }

--lcsQosEgressPortPCPRemarkingSpecificTable
    lcsQosEgressPortPCPRemarkingSpecificTable OBJECT-TYPE
               SYNTAX      SEQUENCE OF     LCSQosEgressPortPCPRemarkingSpecificEntry
               MAX-ACCESS  not-accessible
               STATUS      current
               DESCRIPTION
                   "The basic Qos Egress Port PCP Remarking Specific
                    Configuration settings.
                    INDEX for this table is ifIndex which is
                    equivalent to the panel port number."
               ::= {     lcsQosEgressPortPCPRemarking  2 }

    lcsQosEgressPortPCPRemarkingSpecificEntry OBJECT-TYPE
               SYNTAX          LCSQosEgressPortPCPRemarkingSpecificEntry
               MAX-ACCESS  not-accessible
               STATUS      current
               DESCRIPTION
                   "The Qos Egress Port PCP Remarking Specific Entry."
               INDEX    {     ifIndex  }
               ::= {     lcsQosEgressPortPCPRemarkingSpecificTable 1 }

    LCSQosEgressPortPCPRemarkingSpecificEntry             ::= SEQUENCE {
                lcsQosEgressPortPCPRemarkingSpecificPCP                Integer32,
                lcsQosEgressPortPCPRemarkingSpecificDEI                AdminMode
                }

    lcsQosEgressPortPCPRemarkingSpecificPCP OBJECT-TYPE
               SYNTAX      Integer32(0..7)
               MAX-ACCESS  read-write
               STATUS      current
               DESCRIPTION
                   "Controls the specific PCP
                    Range : 0-7"
               ::= {     lcsQosEgressPortPCPRemarkingSpecificEntry 2 }

    lcsQosEgressPortPCPRemarkingSpecificDEI OBJECT-TYPE
               SYNTAX      AdminMode
               MAX-ACCESS  read-write
               STATUS      current
               DESCRIPTION
                   "controls the admin state of DEI"
               ::= {     lcsQosEgressPortPCPRemarkingSpecificEntry 3 }

--lcsQosPortEgressTagRemarkingMapDPTable
--    lcsQosPortEgressTagRemarkingMapDPTable OBJECT-TYPE
--               SYNTAX      SEQUENCE OF     LCSQosPortEgressTagRemarkingMapDPEntry
--               MAX-ACCESS  not-accessible
--               STATUS      current
--               DESCRIPTION
--                   "Show Qos Port Egress Tag Remarking Map DP.
--                    INDEX for this table is ifIndex which is
--                    equivalent to the panel port number."
--               ::= {     lcsQosPortEgressTagRemarking 3 }

--    lcsQosPortEgressTagRemarkingMapDPEntry OBJECT-TYPE
--               SYNTAX          LCSQosPortEgressTagRemarkingMapDPEntry
--               MAX-ACCESS  not-accessible
--               STATUS      current
--               DESCRIPTION
--                   "The Qos Port Egress Tag Remarking Map DP Entry."
--               INDEX    {     ifIndex,
--                              lcsQosPortEgressTagRemarkingClassifiedDPLevel}
--               ::= {     lcsQosPortEgressTagRemarkingMapDPTable 1 }

--    LCSQosPortEgressTagRemarkingMapDPEntry             ::= SEQUENCE {
--                lcsQosPortEgressTagRemarkingClassifiedDPLevel      Integer32,
--                lcsQosPortEgressTagRemarkingDPLevel                AdminMode
--                }

--    lcsQosPortEgressTagRemarkingClassifiedDPLevel OBJECT-TYPE
--               SYNTAX      Integer32(1..4)
--               MAX-ACCESS  not-accessible
--               STATUS      current
--               DESCRIPTION
--                   "range: 1-4."
--               ::= {     lcsQosPortEgressTagRemarkingMapDPEntry 2 }

--    lcsQosPortEgressTagRemarkingDPLevel OBJECT-TYPE
--               SYNTAX      AdminMode
--               MAX-ACCESS  read-write
--               STATUS      current
--               DESCRIPTION
--                   "admin state of Tag remark"
--               ::= {     lcsQosPortEgressTagRemarkingMapDPEntry 3 }

--lcsQosEgressPortPCPRemarkingMappedTable
    lcsQosEgressPortPCPRemarkingMappedTable OBJECT-TYPE
               SYNTAX      SEQUENCE OF     LCSQosEgressPortPCPRemarkingMappedEntry
               MAX-ACCESS  not-accessible
               STATUS      current
               DESCRIPTION
                   "Show Qos Egress Port PCP Remarking Mapped.
                    INDEX for this table is ifIndex which is
                    equivalent to the panel port number."
               ::= {     lcsQosEgressPortPCPRemarking 4 }

    lcsQosEgressPortPCPRemarkingMappedEntry OBJECT-TYPE
               SYNTAX          LCSQosEgressPortPCPRemarkingMappedEntry
               MAX-ACCESS  not-accessible
               STATUS      current
               DESCRIPTION
                   "The Qos Egress Port PCP Remarking Mapped Entry."
               INDEX    {     ifIndex,
                              lcsQosEgressPortPCPRemarkingMappedQueuePriority,
                              lcsQosEgressPortPCPRemarkingMappedDPLevel  }
               ::= {     lcsQosEgressPortPCPRemarkingMappedTable 1 }

    LCSQosEgressPortPCPRemarkingMappedEntry             ::= SEQUENCE {
                lcsQosEgressPortPCPRemarkingMappedQueuePriority          INTEGER,
                lcsQosEgressPortPCPRemarkingMappedDPLevel                INTEGER,
                lcsQosEgressPortPCPRemarkingMappedPCP                    Integer32,
                lcsQosEgressPortPCPRemarkingMappedDEI                    Integer32
                }

    lcsQosEgressPortPCPRemarkingMappedQueuePriority OBJECT-TYPE
               SYNTAX      INTEGER {
                        class0(1),
                        class1(2),
                        class2(3),
                        class3(4),
                        class4(5),
                        class5(6),
                        class6(7),
                        class7(8)
                        }
               MAX-ACCESS  not-accessible
               STATUS      current
               DESCRIPTION
                   "range: 1-8,
                    QoS Class0: 1, QoS Class1: 2..."
               ::= {     lcsQosEgressPortPCPRemarkingMappedEntry 2 }

    lcsQosEgressPortPCPRemarkingMappedDPLevel OBJECT-TYPE
               SYNTAX      INTEGER { level0(1), level1(2) }
               MAX-ACCESS  not-accessible
               STATUS      current
               DESCRIPTION
                   "range: 1-2,
                    DP Level0: 1, DP Level1: 2."
               ::= {     lcsQosEgressPortPCPRemarkingMappedEntry 3 }

    lcsQosEgressPortPCPRemarkingMappedPCP OBJECT-TYPE
               SYNTAX      Integer32(0..7)
               MAX-ACCESS  read-write
               STATUS      current
               DESCRIPTION
                   "range: 0-7."
               ::= {     lcsQosEgressPortPCPRemarkingMappedEntry 4 }

    lcsQosEgressPortPCPRemarkingMappedDEI OBJECT-TYPE
               SYNTAX      Integer32 (0|1)
               MAX-ACCESS  read-write
               STATUS      current
               DESCRIPTION
                   "range: 0-1."
               ::= {     lcsQosEgressPortPCPRemarkingMappedEntry 5 }

--
-- =======================================================================================================================
-- Start lcsQosPortDSCP group
-- =======================================================================================================================
--lcsQosPortDSCPTable
    lcsQosPortDSCPTable OBJECT-TYPE
               SYNTAX      SEQUENCE OF     LCSQosPortDSCPEntry
               MAX-ACCESS  not-accessible
               STATUS      current
               DESCRIPTION
                   "The basic QoS Port DSCP Configuration settings.
                    INDEX for this table is ifIndex which is
                    equivalent to the panel port number."
               ::= {     lcsQosPortDSCP 1 }

    lcsQosPortDSCPEntry OBJECT-TYPE
               SYNTAX          LCSQosPortDSCPEntry
               MAX-ACCESS  not-accessible
               STATUS      current
               DESCRIPTION
                   "The Qos Port DSCP Entry."
               INDEX    {     ifIndex  }
               ::= {     lcsQosPortDSCPTable 1 }

    LCSQosPortDSCPEntry             ::= SEQUENCE {
                lcsQosPortDSCPIngressTranslate        AdminMode,
                lcsQosPortDSCPIngressClassify         INTEGER,
                lcsQosPortDSCPEgressRewrite           INTEGER
                }

    lcsQosPortDSCPIngressTranslate OBJECT-TYPE
               SYNTAX      AdminMode
               MAX-ACCESS  read-write
               STATUS      current
               DESCRIPTION
                  "Configure DSCP ingress translation mode."
               DEFVAL  { disable }
               ::= {     lcsQosPortDSCPEntry 2 }

    lcsQosPortDSCPIngressClassify OBJECT-TYPE
               SYNTAX      INTEGER { disable (0), dscp (1), selected (2), all(3) }
               MAX-ACCESS  read-write
               STATUS      current
               DESCRIPTION
                   "Classification for a port have 4 different values.
                    0: disable,
                    1: DSCP=0,
                    2: Selected,
                    3: All."
               DEFVAL  { disable }
               ::= {     lcsQosPortDSCPEntry 3 }

    lcsQosPortDSCPEgressRewrite OBJECT-TYPE
               SYNTAX      INTEGER { disable (0),enable (1),
                                     remap (2) }
               MAX-ACCESS  read-write
               STATUS      current
               DESCRIPTION
                   "Configure the port egress rewriting mode.
                    0: Disable,1: Enable,2: Remap,range: 0-2"
               ::= {     lcsQosPortDSCPEntry 4 }

--
-- =======================================================================================================================
-- Start lcsQosDSCPBasedQoS group
-- =======================================================================================================================
    lcsQosDSCPBasedQoSTable OBJECT-TYPE
               SYNTAX      SEQUENCE OF     LCSQosDSCPBasedQoSEntry
               MAX-ACCESS  not-accessible
               STATUS      current
               DESCRIPTION
                   "configure the basic Qos DSCP-Based QoS Ingress Classification settings for all switches."
               ::= {     lcsQosDSCPBasedQoS 1 }

    lcsQosDSCPBasedQoSEntry OBJECT-TYPE
               SYNTAX          LCSQosDSCPBasedQoSEntry
               MAX-ACCESS  not-accessible
               STATUS      current
               DESCRIPTION
                   "The Qos DSCP Based QoS Entry."
               INDEX    {     lcsQosDSCPBasedQoSList  }
               ::= {     lcsQosDSCPBasedQoSTable 1 }

    LCSQosDSCPBasedQoSEntry             ::= SEQUENCE {
                lcsQosDSCPBasedQoSList          Integer32,
                lcsQosDSCPBasedQoSDSCP          DisplayString,
                lcsQosDSCPBasedQoSTrust         AdminMode,
                lcsQosDSCPBasedQoSQueuePriority Integer32,
                lcsQosDSCPBasedQoSDPL           Integer32
                }

    lcsQosDSCPBasedQoSList OBJECT-TYPE
               SYNTAX      Integer32(1..64)
               MAX-ACCESS  not-accessible
               STATUS      current
               DESCRIPTION
                  "DSCP mapping table index(1-64)."
               ::= {     lcsQosDSCPBasedQoSEntry 1 }

    lcsQosDSCPBasedQoSDSCP OBJECT-TYPE
               SYNTAX      DisplayString
               MAX-ACCESS  read-only
               STATUS      current
               DESCRIPTION
                  "Maximum number of supported DSCP values are 64."
               ::= {     lcsQosDSCPBasedQoSEntry 2 }

    lcsQosDSCPBasedQoSTrust OBJECT-TYPE
               SYNTAX      AdminMode
               MAX-ACCESS  read-write
               STATUS      current
               DESCRIPTION
                  "Controls whether a specific DSCP value is trusted. Only frames with
                   trusted DSCP values are mapped to a specific QoS class
                   and Drop Precedence
                   Level. Frames with untrusted DSCP values are
                   treated as a non-IP frame."
               DEFVAL  { disable }
              ::= {     lcsQosDSCPBasedQoSEntry 3 }

    lcsQosDSCPBasedQoSQueuePriority OBJECT-TYPE
               SYNTAX      Integer32(0..7)
               MAX-ACCESS  read-write
               STATUS      current
               DESCRIPTION
                  "QoS class.
                   range: 0-7,
                   default: 0."
               ::= {     lcsQosDSCPBasedQoSEntry 4 }

    lcsQosDSCPBasedQoSDPL OBJECT-TYPE
               SYNTAX      Integer32(0|1)
               MAX-ACCESS  read-write
               STATUS      current
               DESCRIPTION
                  "Drop Precedence Level.
                   range: 0-1,
                   default: 0."
               ::= {     lcsQosDSCPBasedQoSEntry 5 }

--
-- =======================================================================================================================
-- Start lcsQosDSCPTranslation group
-- =======================================================================================================================
--lcsQosDSCPTranslationTable
    lcsQosDSCPTranslationTable OBJECT-TYPE
               SYNTAX      SEQUENCE OF     LCSQosDSCPTranslationEntry
               MAX-ACCESS  not-accessible
               STATUS      current
               DESCRIPTION
                   "The basic QoS DSCP Translation settings for all switches."
               ::= {     lcsQosDSCPTranslation  1 }

    lcsQosDSCPTranslationEntry OBJECT-TYPE
               SYNTAX          LCSQosDSCPTranslationEntry
               MAX-ACCESS  not-accessible
               STATUS      current
               DESCRIPTION
                   "The Qos DSCP Translation Entry."
               INDEX    {     lcsQosDSCPTranslationList  }
               ::= {     lcsQosDSCPTranslationTable 1 }

    LCSQosDSCPTranslationEntry             ::= SEQUENCE {
                lcsQosDSCPTranslationList                 Integer32,
                lcsQosDSCPTranslationDSCPBasedId          DisplayString,
                lcsQosDSCPTranslationIngressTranslate     Integer32,
                lcsQosDSCPTranslationIngressClassify      AdminMode,
                lcsQosDSCPTranslationEgressRemap          Integer32
--              lcsQosDSCPTranslationEgressRemapDP1       Integer32
                }

    lcsQosDSCPTranslationList OBJECT-TYPE
               SYNTAX      Integer32(1..64)
               MAX-ACCESS  not-accessible
               STATUS      current
               DESCRIPTION
                  "DSCP translation table index(1-64)."
               ::= {     lcsQosDSCPTranslationEntry 1 }

    lcsQosDSCPTranslationDSCPBasedId OBJECT-TYPE
               SYNTAX      DisplayString
               MAX-ACCESS  read-only
               STATUS      current
               DESCRIPTION
                  "Configure global ingress DSCP translation table."
               ::= {     lcsQosDSCPTranslationEntry 2 }

    lcsQosDSCPTranslationIngressTranslate OBJECT-TYPE
               SYNTAX      Integer32(0..63)
               MAX-ACCESS  read-write
               STATUS      current
               DESCRIPTION
                  "DSCP at Ingress side can be translated to any of DSCP values.
                   range: 0-63,
                   default: 0."
               ::= {     lcsQosDSCPTranslationEntry 3 }

    lcsQosDSCPTranslationIngressClassify OBJECT-TYPE
               SYNTAX      AdminMode
               MAX-ACCESS  read-write
               STATUS      current
               DESCRIPTION
                  "Configure DSCP ingress classification."
               DEFVAL  { disable }
               ::= {     lcsQosDSCPTranslationEntry 4 }

    lcsQosDSCPTranslationEgressRemap OBJECT-TYPE
               SYNTAX      Integer32(0..63)
               MAX-ACCESS  read-write
               STATUS      current
               DESCRIPTION
                  "Select the DSCP value from select menu to which you want to remap.
                   range: 0-63,
                   default: 0."
               ::= {     lcsQosDSCPTranslationEntry 5 }

--    lcsQosDSCPTranslationEgressRemapDP1 OBJECT-TYPE
--               SYNTAX      Integer32(0..63)
--               MAX-ACCESS  read-write
--               STATUS      current
--               DESCRIPTION
--                  "Select the DSCP value from select menu to which you want to remap.
--                   range: 0-63,
--                   default: 0.
--                   Only support LUTON26."
--               ::= {     lcsQosDSCPTranslationEntry 6 }

--
-- =======================================================================================================================
-- Start lcsQosDSCPClassification group
-- =======================================================================================================================
--lcsQosDSCPClassificationTable
    lcsQosDSCPClassificationTable OBJECT-TYPE
               SYNTAX      SEQUENCE OF     LCSQosDSCPClassificationEntry
               MAX-ACCESS  not-accessible
               STATUS      current
               DESCRIPTION
                   "The mapping of QoS class  to DSCP value."
               ::= {     lcsQosDSCPClassification 1 }

    lcsQosDSCPClassificationEntry OBJECT-TYPE
               SYNTAX          LCSQosDSCPClassificationEntry
               MAX-ACCESS  not-accessible
               STATUS      current
               DESCRIPTION
                   "The Qos DSCP Classification Entry."
               INDEX    {     lcsQosDSCPClassificationQoSClass  }
               ::= {     lcsQosDSCPClassificationTable 1 }

    LCSQosDSCPClassificationEntry             ::= SEQUENCE {
                lcsQosDSCPClassificationQoSClass   Integer32,
                lcsQosDSCPClassificationDSCPDP0    Integer32,
        lcsQosDSCPClassificationDSCPDP1    Integer32,
        lcsQosDSCPClassificationDSCPDP2    Integer32,
        lcsQosDSCPClassificationDSCPDP3    Integer32
                }

    lcsQosDSCPClassificationQoSClass OBJECT-TYPE
               SYNTAX      Integer32(1..8)
               MAX-ACCESS  not-accessible
               STATUS      current
               DESCRIPTION
                  "This page allows you to configure the mapping of QoS class
                   and Drop Precedence Level to DSCP value.
                   range: 1-8}"
               ::= {     lcsQosDSCPClassificationEntry 1 }

    lcsQosDSCPClassificationDSCPDP0 OBJECT-TYPE
               SYNTAX      Integer32(0..63)
               MAX-ACCESS  read-write
               STATUS      current
               DESCRIPTION
                  "Select the classified DSCP value.
                   range: 0-63,
                   default: 0."
               ::= {     lcsQosDSCPClassificationEntry 2 }

    lcsQosDSCPClassificationDSCPDP1 OBJECT-TYPE
               SYNTAX      Integer32(0..63)
               MAX-ACCESS  read-write
               STATUS      current
               DESCRIPTION
                  "Select the classified DSCP value.
                   range: 0-63,
                   default: 0."
               ::= {     lcsQosDSCPClassificationEntry 3 }

    lcsQosDSCPClassificationDSCPDP2 OBJECT-TYPE
               SYNTAX      Integer32(0..63)
               MAX-ACCESS  read-write
               STATUS      current
               DESCRIPTION
                  "Select the classified DSCP value.
                   range: 0-63,
                   default: 0."
               ::= {     lcsQosDSCPClassificationEntry 4 }

    lcsQosDSCPClassificationDSCPDP3 OBJECT-TYPE
               SYNTAX      Integer32(0..63)
               MAX-ACCESS  read-write
               STATUS      current
               DESCRIPTION
                  "Select the classified DSCP value.
                   range: 0-63,
                   default: 0."
               ::= {     lcsQosDSCPClassificationEntry 5 }
               
--
-- =======================================================================================================================
-- Start lcsQosControlList group
-- =======================================================================================================================
--lcsQosQceTable

    lcsQosQceTable OBJECT-TYPE
               SYNTAX      SEQUENCE OF     LCSQosQceEntry
               MAX-ACCESS  not-accessible
               STATUS      current
               DESCRIPTION
                   "Create Qos QCE entry."
               ::= {     lcsQosControlList 1 }

    lcsQosQceEntry OBJECT-TYPE
               SYNTAX          LCSQosQceEntry
               MAX-ACCESS  not-accessible
               STATUS      current
               DESCRIPTION
                   "Qos Qce Entry."
               INDEX    {     lcsQosQceIndex  }
               ::= {     lcsQosQceTable 1 }

    LCSQosQceEntry             ::= SEQUENCE {
                lcsQosQceIndex                Integer32,
                lcsQosQceID                   Integer32,
                lcsQosQceList                 Integer32,
--              lcsQosQcePortMembersSwitch    Integer32,
                lcsQosQcePortMembers          DisplayString,
                lcsQosQceTag                  DisplayString,
                lcsQosQceVID                  DisplayString,
                lcsQosPCP                     DisplayString,
                lcsQosDEI                     DisplayString,
                lcsQosSMAC                    DisplayString,
                lcsQosDMACType                DisplayString,
                lcsQosDMACValue               DisplayString,
                lcsQosQceInnerTag             DisplayString,
                lcsQosQceInnerVID             DisplayString,
                lcsQosInnerPCP                DisplayString,
                lcsQosInnerDEI                DisplayString,
                lcsQosFrameType               INTEGER,
                lcsQosMacEtherType            DisplayString,
                lcsQosLLCSSAPAddr             DisplayString,
                lcsQosLLCDSAPAddr             DisplayString,
                lcsQosLLCControl              DisplayString,
                lcsQosSNAPPID                 DisplayString,
                lcsQosIpv4Protocol            DisplayString,
                lcsQosIpv4ProtocolValue       Integer32,
                lcsQosIpv4ProtocolUDPSPort    DisplayString,
                lcsQosIpv4ProtocolUDPDPort    DisplayString,
                lcsQosIpv4ProtocolTCPSPort    DisplayString,
                lcsQosIpv4ProtocolTCPDPort    DisplayString,
                lcsQosIpv4SourceIp            DisplayString,
                lcsQosIpv4SourceMask          DisplayString,
                lcsQosIpv4DestIp              DisplayString,
                lcsQosIpv4DestMask            DisplayString,                 
                lcsQosIpv4IPFragment          INTEGER,
                lcsQosIpv4DSCP                DisplayString,
                lcsQosIpv6Protocol            DisplayString,
                lcsQosIpv6ProtocolValue       Integer32,
                lcsQosIpv6ProtocolUDPSPort    DisplayString,
                lcsQosIpv6ProtocolUDPDPort    DisplayString,
                lcsQosIpv6ProtocolTCPSPort    DisplayString,
                lcsQosIpv6ProtocolTCPDPort    DisplayString,
                lcsQosIpv6SourceIp            DisplayString,
                lcsQosIpv6SourceMask          DisplayString,
                lcsQosIpv6DestIp              DisplayString,
                lcsQosIpv6DestMask            DisplayString,                 
                lcsQosIpv6DSCP                DisplayString,
                lcsQosActionQueuePriority     Integer32,
                lcsQosActionDPL               Integer32,
                lcsQosActionDSCP              Integer32,
                lcsQosActionPCP               Integer32,
                lcsQosActionDEI               Integer32,
                lcsQosActionPolicy            Integer32,
                lcsQosActionIngressMapID      Integer32,
                lcsQosQceRowStatus            RowStatus
                }

    lcsQosQceIndex OBJECT-TYPE
               SYNTAX      Integer32(1..256)
               MAX-ACCESS  not-accessible
               STATUS      current
               DESCRIPTION
                   "the index to this table."
               ::= {     lcsQosQceEntry 1 }

    lcsQosQceID OBJECT-TYPE
               SYNTAX      Integer32(1..256)
               MAX-ACCESS  read-only
               STATUS      current
               DESCRIPTION
                   "If the QCE ID is specified and an entry with this QCE ID
                    already exists, the QCE will be modified. Otherwise, a
                    new QCE will be added.
                    range : 1 - 256."
               ::= {     lcsQosQceEntry 2 }

    lcsQosQceList OBJECT-TYPE
               SYNTAX      Integer32(0..256)
               MAX-ACCESS  read-create
               STATUS      current
               DESCRIPTION
                   "If the QCE List is non zero, the QCE will be placed in the list.
                    If the QCE List is zero, the QCE will be placed last in the list.
                    range : 0 - 256."
               ::= {     lcsQosQceEntry 3 }

--    lcsQosQcePortMembersSwitch OBJECT-TYPE
--               SYNTAX      Integer32
--               MAX-ACCESS  read-create
--               STATUS      current
--               DESCRIPTION
--                   "Switch number for port members.
--                   -1:Any.
--                   Only support stacking switch."
--               ::= {     lcsQosQceEntry 4 }

    lcsQosQcePortMembers OBJECT-TYPE
               SYNTAX      DisplayString
               MAX-ACCESS  read-create
               STATUS      current
               DESCRIPTION
                   "Indicates the ingress port of the QCE. Possible values are:
                    All: The QCE will match all ingress port.
                    Port: The QCE will match a specific ingress port.Format: 1,3-6."
               ::= {     lcsQosQceEntry 5 }

    lcsQosQceTag OBJECT-TYPE
               SYNTAX      DisplayString
               MAX-ACCESS  read-create
               STATUS      current
               DESCRIPTION
                  "'Any', 'Untagged' or 'Tagged' or 'C-Tag' or 'S-Tag'"
               ::= {     lcsQosQceEntry 6 }

    lcsQosQceVID OBJECT-TYPE
               SYNTAX      DisplayString
               MAX-ACCESS  read-create
               STATUS      current
               DESCRIPTION
                   "Valid value of VLAN ID can be any value in
                   'Specific 1~4094' or 'range 1-4094' or 'Any'."
               ::= {     lcsQosQceEntry 7 }

    lcsQosPCP OBJECT-TYPE
               SYNTAX      DisplayString
               MAX-ACCESS  read-create
               STATUS      current
               DESCRIPTION
                   "Priority Code Point: Valid value PCP are
                    specific(0, 1, 2, 3, 4, 5, 6, 7)
                    or range(0-1, 2-3, 4-5, 6-7, 0-3, 4-7) or 'Any'."
               ::= {     lcsQosQceEntry 8 }

    lcsQosDEI OBJECT-TYPE
               SYNTAX      DisplayString
               MAX-ACCESS  read-create
               STATUS      current
               DESCRIPTION
                   "Drop Eligible Indicator: Valid value of DEI can be
                    any of values between 0, 1 or 'Any'."
               ::= {     lcsQosQceEntry 9 }

    lcsQosSMAC  OBJECT-TYPE
               SYNTAX      DisplayString
               MAX-ACCESS  read-create
               STATUS      current
               DESCRIPTION
                   "Source MAC address: xx-xx-xx-xx-xx-xx or 'Any'."
               ::= {     lcsQosQceEntry 10 }

    lcsQosDMACType OBJECT-TYPE
               SYNTAX      DisplayString
               MAX-ACCESS  read-create
               STATUS      current
               DESCRIPTION
                   "Destination MAC type: possible values are 'UC'(unicast),
                    'MC'(multicast), 'BC'(broadcast), 'SP'(Specific) or 'Any'."
               ::= {     lcsQosQceEntry 11 }

    lcsQosDMACValue OBJECT-TYPE
               SYNTAX      DisplayString
               MAX-ACCESS  read-create
               STATUS      current
               DESCRIPTION
                   "when QosDMACType is 'SP'(specific) can set mac address.
                   "
               ::= {     lcsQosQceEntry 12 }

    lcsQosQceInnerTag OBJECT-TYPE
               SYNTAX      DisplayString
               MAX-ACCESS  read-create
               STATUS      current
               DESCRIPTION
                   "Value of Inner Tag field can be 'Any', 'Untagged' or 'Tagged' or
                    'C-tagged' or 'S-tagged'."
               ::= {     lcsQosQceEntry 13 }

    lcsQosQceInnerVID OBJECT-TYPE
               SYNTAX      DisplayString
               MAX-ACCESS  read-create
               STATUS      current
               DESCRIPTION
                   "Valid value of Inner VLAN ID can be any value in
                    'Specific 1~4094' or 'range 1-4094' or 'Any'.
                    "
               ::= {     lcsQosQceEntry 14 }

    lcsQosInnerPCP OBJECT-TYPE
               SYNTAX      DisplayString
               MAX-ACCESS  read-create
               STATUS      current
               DESCRIPTION
                   "Valid value Inner PCP are specific(0, 1, 2, 3, 4, 5, 6, 7)
                    or range(0-1, 2-3, 4-5, 6-7, 0-3, 4-7) or 'Any'.
                   "
               ::= {     lcsQosQceEntry 15 }

    lcsQosInnerDEI OBJECT-TYPE
               SYNTAX      DisplayString
               MAX-ACCESS  read-create
               STATUS      current
               DESCRIPTION
                   "Valid value of Inner DEI can be any of values between
                    0, 1 or 'Any'.
                   "
               ::= {     lcsQosQceEntry 16 }

    lcsQosFrameType OBJECT-TYPE
               SYNTAX      INTEGER {
                            any(1),
                            ethernet(2),
                            llc(3),
                            snap(4),
                            ipv4(5),
                            ipv6(6)
                           }
               MAX-ACCESS  read-create
               STATUS      current
               DESCRIPTION
                   "Frame Type can have any of the following values:
                    1: Any,
                    2: Ethernet,
                    3: LLC,
                    4: SNAP,
                    5: IPv4,
                    6: IPv6."
               ::= {     lcsQosQceEntry 17 }

    lcsQosMacEtherType OBJECT-TYPE
               SYNTAX      DisplayString
               MAX-ACCESS  read-create
               STATUS      current
               DESCRIPTION
                   "Valid ethernet type can have a value within 0x600-0xFFFF or 'Any' ,
                    but excluding 0x800(IPv4) and 0x86DD(IPv6),
                    range: 0000-FFFF,
                    default: Any."
               ::= {     lcsQosQceEntry 18 }

    lcsQosLLCSSAPAddr OBJECT-TYPE
               SYNTAX      DisplayString
               MAX-ACCESS  read-create
               STATUS      current
               DESCRIPTION
                   "Valid SSAP(Source Service Access Point) can vary from
                    0x00 to 0xFF or 'Any',
                    range: 00-FF,
                    default: Any."
               ::= {     lcsQosQceEntry 19 }

    lcsQosLLCDSAPAddr OBJECT-TYPE
               SYNTAX      DisplayString
               MAX-ACCESS  read-create
               STATUS      current
               DESCRIPTION
                   "Valid DSAP(Destination Service Access Point) can
                    vary from 0x00 to 0xFF or 'Any',
                    range: 00-FF,
                    default: Any."
               ::= {     lcsQosQceEntry 20 }

    lcsQosLLCControl OBJECT-TYPE
               SYNTAX      DisplayString
               MAX-ACCESS  read-create
               STATUS      current
               DESCRIPTION
                   "Valid Control field can vary from 0x00 to 0xFF or 'Any',
                    range: 00-FF,
                    default: Any."
               ::= {     lcsQosQceEntry 21 }

    lcsQosSNAPPID OBJECT-TYPE
               SYNTAX      DisplayString
               MAX-ACCESS  read-create
               STATUS      current
               DESCRIPTION
                   "Valid PID(a.k.a ethernet type) can have value within
                    0x00-0xFFFF or 'Any',
                    range: 0000-FFFF,
                    default: Any."
               ::= {     lcsQosQceEntry 22 }

   lcsQosIpv4Protocol OBJECT-TYPE
               SYNTAX      DisplayString
               MAX-ACCESS  read-create
               STATUS      current
               DESCRIPTION
                   "IP protocol number: (Other, TCP or UDP) or 'Any'."
               ::= {     lcsQosQceEntry 23 }

    lcsQosIpv4ProtocolValue  OBJECT-TYPE
               SYNTAX      Integer32(0..255)
               MAX-ACCESS  read-create
               STATUS      current
               DESCRIPTION
                   "Ipv4 Protocol is Other.
                    range: 0-255
                    default: 0."
               ::= {     lcsQosQceEntry 24 }

    lcsQosIpv4ProtocolUDPSPort OBJECT-TYPE
               SYNTAX      DisplayString
               MAX-ACCESS  read-create
               STATUS      current
               DESCRIPTION
                   "Source  TCP/UDP Port:(0-65535) or 'Any',
                    specific or port range applicable for IP protocol UDP/TCP."
               ::= {     lcsQosQceEntry 25 }

    lcsQosIpv4ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     lcsQosQceEntry 26 }

    lcsQosIpv4ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     lcsQosQceEntry 27 }

    lcsQosIpv4ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     lcsQosQceEntry 28 }

    lcsQosIpv4SourceIp OBJECT-TYPE
               SYNTAX      DisplayString
               MAX-ACCESS  read-create
               STATUS      current
               DESCRIPTION
                   "Specific Source IP address in value format or value 0.0.0.0 is 'Any'.
                    if Ipv4 Mask value 0.0.0.0 is 'Any' ,IP address value also is 'Any'.
                    (x.y.z.w),x=0 unless y.z.w also 0,x not is 127 or greater than 223."
               ::= {     lcsQosQceEntry 29 }

    lcsQosIpv4SourceMask OBJECT-TYPE
               SYNTAX      DisplayString
               MAX-ACCESS  read-create
               STATUS      current
               DESCRIPTION
                   "Specific Source IP address in mask format or value 0.0.0.0 is 'Any'."
               ::= {     lcsQosQceEntry 30 }
               
    lcsQosIpv4DestIp OBJECT-TYPE
               SYNTAX      DisplayString
               MAX-ACCESS  read-create
               STATUS      current
               DESCRIPTION
                   "Specific Destination IP address in value format or value 0.0.0.0 is 'Any'.
                    if Ipv4 Mask value 0.0.0.0 is 'Any' ,IP address value also is 'Any'.
                    (x.y.z.w),x=0 unless y.z.w also 0,x not is 127 or greater than 223."
               ::= {     lcsQosQceEntry 31 }

    lcsQosIpv4DestMask OBJECT-TYPE
               SYNTAX      DisplayString
               MAX-ACCESS  read-create
               STATUS      current
               DESCRIPTION
                   "Specific Destination IP address in mask format or value 0.0.0.0 is 'Any'."
               ::= {     lcsQosQceEntry 32 }               

    lcsQosIpv4IPFragment OBJECT-TYPE
               SYNTAX      INTEGER { any(0), no(1), yes(2) }
               MAX-ACCESS  read-create
               STATUS      current
               DESCRIPTION
                   "IPv4 frame fragmented option:
                    2: yes,
                    1: no,
                    0: any."
               ::= {     lcsQosQceEntry 33 }

    lcsQosIpv4DSCP OBJECT-TYPE
               SYNTAX      DisplayString
               MAX-ACCESS  read-create
               STATUS      current
               DESCRIPTION
                   "Diffserv Code Point value (DSCP): It can be a specific value,
                    range of values or 'Any'. DSCP values are in the range 0-63."
               ::= {     lcsQosQceEntry 34 }

    lcsQosIpv6Protocol OBJECT-TYPE
               SYNTAX      DisplayString
               MAX-ACCESS  read-create
               STATUS      current
               DESCRIPTION
                   "IP protocol number: (Other, TCP or UDP) or 'Any'."
               ::= {     lcsQosQceEntry 35 }

    lcsQosIpv6ProtocolValue OBJECT-TYPE
               SYNTAX      Integer32(0..255)
               MAX-ACCESS  read-create
               STATUS      current
               DESCRIPTION
                   "when IPv6 protocol is Other ,
                    range: 0-255."
               ::= {     lcsQosQceEntry 36 }

    lcsQosIpv6ProtocolUDPSPort OBJECT-TYPE
               SYNTAX      DisplayString
               MAX-ACCESS  read-create
               STATUS      current
               DESCRIPTION
                   "Source TCP/UDP port:(0-65535) or 'Any',
                    specific or port range applicable for IP protocol UDP/TCP."
               ::= {     lcsQosQceEntry 37 }

    lcsQosIpv6ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     lcsQosQceEntry 38 }

    lcsQosIpv6ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     lcsQosQceEntry 39 }


    lcsQosIpv6ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     lcsQosQceEntry 40 }

    lcsQosIpv6SourceIp OBJECT-TYPE
               SYNTAX      DisplayString
               MAX-ACCESS  read-create
               STATUS      current
               DESCRIPTION
                   "IPv6 source address: (a.b.c.d) or value 0.0.0.0 is 'Any', 32 LS bits."
               ::= {     lcsQosQceEntry 41 }

    lcsQosIpv6SourceMask OBJECT-TYPE
               SYNTAX      DisplayString
               MAX-ACCESS  read-create
               STATUS      current
               DESCRIPTION
                   "IPv6 mask address: (a.b.c.d) or value 0.0.0.0 is 'Any', 32 LS bits."
               ::= {     lcsQosQceEntry 42 }

    lcsQosIpv6DestIp OBJECT-TYPE
               SYNTAX      DisplayString
               MAX-ACCESS  read-create
               STATUS      current
               DESCRIPTION
                   "IPv6 destination address: (a.b.c.d) or value 0.0.0.0 is 'Any', 32 LS bits."
               ::= {     lcsQosQceEntry 43 }

    lcsQosIpv6DestMask OBJECT-TYPE
               SYNTAX      DisplayString
               MAX-ACCESS  read-create
               STATUS      current
               DESCRIPTION
                   "IPv6 mask address: (a.b.c.d) or value 0.0.0.0 is 'Any', 32 LS bits."
               ::= {     lcsQosQceEntry 44 }   
               
    lcsQosIpv6DSCP OBJECT-TYPE
               SYNTAX      DisplayString
               MAX-ACCESS  read-create
               STATUS      current
               DESCRIPTION
                   "Diffserv Code Point value (DSCP): It can be a specific value,
                    range of values or 'Any'. DSCP values are in the
                    range 0-63 including BE,
                    CS1-CS7, EF or AF11-AF43."
               ::= {     lcsQosQceEntry 45 }

    lcsQosActionQueuePriority  OBJECT-TYPE
               SYNTAX      Integer32(0..8)
               MAX-ACCESS  read-create
               STATUS      current
               DESCRIPTION
                   "QoS class: (0-7) or 8: Default."
               ::= {     lcsQosQceEntry 46 }

    lcsQosActionDPL OBJECT-TYPE
               SYNTAX      Integer32 (0..4)
               MAX-ACCESS  read-create
               STATUS      current
               DESCRIPTION
                   "range:0-4. 4: Default"
               ::= {     lcsQosQceEntry 47 }

    lcsQosActionDSCP OBJECT-TYPE
               SYNTAX      Integer32(0..64)
               MAX-ACCESS  read-create
               STATUS      current
               DESCRIPTION
                   "Valid DSCP value can be (0-63, BE, CS1-CS7,
                    EF or AF11-AF43) or 64: Default."
               ::= {     lcsQosQceEntry 48 }

    lcsQosActionPCP  OBJECT-TYPE
               SYNTAX      Integer32(0..8)
               MAX-ACCESS  read-create
               STATUS      current
               DESCRIPTION
                   "pcp: (0-7) or 8: Default.
                   "
               ::= {     lcsQosQceEntry 49 }

    lcsQosActionDEI OBJECT-TYPE
               SYNTAX      Integer32 (0..2)
               MAX-ACCESS  read-create
               STATUS      current
               DESCRIPTION
                   "dei: (0-1) or 2: Default.
                    "
               ::= {     lcsQosQceEntry 50 }

    lcsQosActionPolicy OBJECT-TYPE
               SYNTAX      Integer32(0..128)
               MAX-ACCESS  read-create
               STATUS      current
               DESCRIPTION
                   "ACL Policy number: (0-127) or 'empty'(128). Default: empty.
                    "
               ::= {     lcsQosQceEntry 51 }

    lcsQosActionIngressMapID OBJECT-TYPE
               SYNTAX      Integer32(-1..255)
               MAX-ACCESS  read-create
               STATUS      current
               DESCRIPTION
                   "Classify Ingress Map ID: 
                   Range: 0-255
                   Default: -1
                   "
               ::= {     lcsQosQceEntry 52 }

    lcsQosQceRowStatus OBJECT-TYPE
               SYNTAX      RowStatus
               MAX-ACCESS  read-create
               STATUS      current
               DESCRIPTION
                   "This object indicates the status of this entry, and is used
                   to create/delete entries.  Any object in an entry of this table
                   may be modified while the value of the corresponding instance
                   of this object is active(1).
                   createAndGo, notReady not supported."
               ::= {     lcsQosQceEntry 53 }

--
-- =======================================================================================================================
-- Start  lcsQosStormControl group
-- =======================================================================================================================
--lcsQosStormControlTable
    lcsQosStormControlTable OBJECT-TYPE
               SYNTAX      SEQUENCE OF     LCSQosStormControlEntry
               MAX-ACCESS  not-accessible
               STATUS      current
               DESCRIPTION
                   "The basic QoS DSCP Translation settings for all switches."
               ::= {     lcsQosStormControl  1 }

    lcsQosStormControlEntry OBJECT-TYPE
               SYNTAX          LCSQosStormControlEntry
               MAX-ACCESS  not-accessible
               STATUS      current
               DESCRIPTION
                   "The Qos Storm Control Entry."
               INDEX    {     lcsQosStormControlFrameType  }
               ::= {     lcsQosStormControlTable 1 }

    LCSQosStormControlEntry             ::= SEQUENCE {
                lcsQosStormControlFrameType        INTEGER,
                lcsQosStormControlEnabled          AdminMode,
                lcsQosStormControlRate             Integer32,
        lcsQosStormControlUnit             Integer32
                }

    lcsQosStormControlFrameType OBJECT-TYPE
               SYNTAX      INTEGER { unicast(1), multicast (2), broadcast (3)}
               MAX-ACCESS  not-accessible
               STATUS      current
               DESCRIPTION
                   "The settings in a particular row apply to the frame type listed here.
                    1:Unicast,
                    2:Multicast,
                    3:Broadcast."
               ::= {     lcsQosStormControlEntry 1 }

    lcsQosStormControlEnabled OBJECT-TYPE
               SYNTAX      AdminMode
               MAX-ACCESS  read-write
               STATUS      current
               DESCRIPTION
                  "Enable or disable the global storm policer for the given frame type."
               ::= {     lcsQosStormControlEntry 2 }

    lcsQosStormControlRate OBJECT-TYPE
               SYNTAX      Integer32
               MAX-ACCESS  read-write
               STATUS      current
               DESCRIPTION
                   "Controls the rate for the global storm policer."
               ::= {     lcsQosStormControlEntry 3 }
               
    lcsQosStormControlUnit OBJECT-TYPE
               SYNTAX      Integer32
               MAX-ACCESS  read-write
               STATUS      current
               DESCRIPTION
                   "Controls the unit of measure for the global storm policer rate as fps or kfps.
           0: kbps
           1: Mbps                 
               2: fps
                   3: kfps"				   
               ::= {     lcsQosStormControlEntry 4 }               

--
-- =======================================================================================================================
-- Start  lcsQosPortStormControl group
-- =======================================================================================================================
--lcsQosPortStormControlTable
    lcsQosPortStormControlTable OBJECT-TYPE
               SYNTAX      SEQUENCE OF     LCSQosPortStormControlEntry
               MAX-ACCESS  not-accessible
               STATUS      current
               DESCRIPTION
                   "Configure the storm control settings.
                    INDEX for this table is ifIndex which is
                    equivalent to the panel port number."
               ::= {     lcsQosPortStormControl  1 }

    lcsQosPortStormControlEntry OBJECT-TYPE
               SYNTAX      LCSQosPortStormControlEntry
               MAX-ACCESS  not-accessible
               STATUS      current
               DESCRIPTION
                   "The Qos Port Storm Control Entry."
               INDEX    {     ifIndex  }
               ::= {     lcsQosPortStormControlTable 1 }

    LCSQosPortStormControlEntry             ::= SEQUENCE {
                lcsQosPortStormControlUnicastEnabled   AdminMode,
                lcsQosPortStormControlUnicastRate      Integer32,
                lcsQosPortStormControlUnicastUnit      Integer32,
                lcsQosPortStormControlBroadcastEnabled AdminMode,
                lcsQosPortStormControlBroadcastRate    Integer32,
                lcsQosPortStormControlBroadcastUnit    Integer32,
                lcsQosPortStormControlUnknownEnabled   AdminMode,
                lcsQosPortStormControlUnknownRate      Integer32,
                lcsQosPortStormControlUnknownUnit      Integer32
                }

     lcsQosPortStormControlUnicastEnabled OBJECT-TYPE
               SYNTAX      AdminMode
               MAX-ACCESS  read-write
               STATUS      current
               DESCRIPTION
                  "Controls whether the storm control is enabled on this
                   switch port."
               ::= {     lcsQosPortStormControlEntry 2 }

    lcsQosPortStormControlUnicastRate OBJECT-TYPE
               SYNTAX      Integer32
               MAX-ACCESS  read-write
               STATUS      current
               DESCRIPTION
                   "Controls the rate for the storm control."
               ::= {     lcsQosPortStormControlEntry 3 }

    lcsQosPortStormControlUnicastUnit OBJECT-TYPE
               SYNTAX      Integer32
               MAX-ACCESS  read-write
               STATUS      current
               DESCRIPTION
                   "Controls the unit of measure for the storm control rate.
                   0: kbps
                   1: Mbps
                   2: fps
                   3: kfps"
               ::= {     lcsQosPortStormControlEntry 4 }

     lcsQosPortStormControlBroadcastEnabled  OBJECT-TYPE
               SYNTAX      AdminMode
               MAX-ACCESS  read-write
               STATUS      current
               DESCRIPTION
                  "Controls whether the storm control is enabled on this
                   switch port."
               ::= {     lcsQosPortStormControlEntry 5 }

    lcsQosPortStormControlBroadcastRate OBJECT-TYPE
               SYNTAX      Integer32
               MAX-ACCESS  read-write
               STATUS      current
               DESCRIPTION
                   "Controls the rate for the storm control."
               ::= {     lcsQosPortStormControlEntry 6 }

    lcsQosPortStormControlBroadcastUnit OBJECT-TYPE
               SYNTAX      Integer32
               MAX-ACCESS  read-write
               STATUS      current
               DESCRIPTION
                   "Controls the unit of measure for the storm control rate.
		   0: kbps
		   1: Mbps				   
	           2: fps
                   3: kfps"
               ::= {     lcsQosPortStormControlEntry 7 }

    lcsQosPortStormControlUnknownEnabled  OBJECT-TYPE
               SYNTAX      AdminMode
               MAX-ACCESS  read-write
               STATUS      current
               DESCRIPTION
                  "Controls whether the storm control is enabled on this
                   switch port."
               ::= {     lcsQosPortStormControlEntry 8 }

    lcsQosPortStormControlUnknownRate OBJECT-TYPE
               SYNTAX      Integer32
               MAX-ACCESS  read-write
               STATUS      current
               DESCRIPTION
                   "Controls the rate for the storm control."
               ::= {     lcsQosPortStormControlEntry 9 }

    lcsQosPortStormControlUnknownUnit OBJECT-TYPE
               SYNTAX      Integer32
               MAX-ACCESS  read-write
               STATUS      current
               DESCRIPTION
                   "Controls the unit of measure for the storm control rate.
		   0: kbps
		   1: Mbps				   
	           2: fps
                   3: kfps"
               ::= {     lcsQosPortStormControlEntry 10 }

--
-- =======================================================================================================================
-- Start  lcsQosWRED group
-- =======================================================================================================================
--lcsQosWREDTable
    lcsQosWREDTable OBJECT-TYPE
               SYNTAX      SEQUENCE OF     LCSQosWREDEntry
               MAX-ACCESS  not-accessible
               STATUS      current
               DESCRIPTION
                   "The basic QoS DSCP Translation settings for all switches."
               ::= {     lcsQosWRED  1 }

    lcsQosWREDEntry OBJECT-TYPE
               SYNTAX          LCSQosWREDEntry
               MAX-ACCESS  not-accessible
               STATUS      current
               DESCRIPTION
                   "The Qos WRED Entry."
               INDEX    {     lcsQosWREDQueue  }
               ::= {     lcsQosWREDTable 1 }

    LCSQosWREDEntry             ::= SEQUENCE {
                lcsQosWREDGroupIndex      Integer32,
                lcsQosWREDQueue           Integer32,
                lcsQosWREDDPL             Integer32,
                lcsQosWREDEnable          AdminMode,
                lcsQosWREDMinThreshold    Integer32,
                lcsQosWREDMaxThreshold    Integer32,
                lcsQosWREDMaxUnit         INTEGER
                }

    lcsQosWREDGroupIndex OBJECT-TYPE
               SYNTAX      Integer32
               MAX-ACCESS  not-accessible
               STATUS      current
               DESCRIPTION
                   "The group number for which the configuration
                    below applies."
               ::= {     lcsQosWREDEntry 1 }

    lcsQosWREDQueue OBJECT-TYPE
               SYNTAX      Integer32 (1..65535)
               MAX-ACCESS  not-accessible
               STATUS      current
               DESCRIPTION
                   "The queue number (QoS class) for which the configuration
                    below applies."
               ::= {     lcsQosWREDEntry 2 }

    lcsQosWREDDPL OBJECT-TYPE
               SYNTAX      Integer32
               MAX-ACCESS  not-accessible
               STATUS      current
               DESCRIPTION
                   "The dpl number for which the configuration
                    below applies."
               ::= {     lcsQosWREDEntry 3 }
               
               
    lcsQosWREDEnable OBJECT-TYPE
               SYNTAX      AdminMode
               MAX-ACCESS  read-write
               STATUS      current
               DESCRIPTION
                  "Controls whether RED is enabled for this queue.
                  "
               DEFVAL  { disable }
               ::= {     lcsQosWREDEntry 4 }

    lcsQosWREDMinThreshold OBJECT-TYPE
               SYNTAX      Integer32(0..100)
               MAX-ACCESS  read-write
               STATUS      current
               DESCRIPTION
                   "Controls the lower RED fill level threshold. If the queue filling
                    level is below this threshold, the drop probability is zero.
                    range:0-100%,
                    default: 0.
                  "
               ::= {     lcsQosWREDEntry 5 }

    lcsQosWREDMaxThreshold OBJECT-TYPE
               SYNTAX      Integer32(0..100)
               MAX-ACCESS  read-write
               STATUS      current
               DESCRIPTION
                   "Controls the upper RED drop probability or fill level threshold
                    for frames marked with Drop Precedence Level 1 (yellow frames).
                    range:0-100%,
                    default: 50.
                  "
               ::= {     lcsQosWREDEntry 6 }

    lcsQosWREDMaxUnit OBJECT-TYPE
               SYNTAX      INTEGER {dropProbability (0), fillLevel (1) }
               MAX-ACCESS  read-write
               STATUS      current
               DESCRIPTION
                   "Selects the unit for Max.
                    0: Drop Probability,
                    1: Fill Level,
                    default: Drop Probability.
                  "
               DEFVAL  { dropProbability }
               ::= {     lcsQosWREDEntry 7 }

--
-- =======================================================================================================================
-- Start  lcsQosQCLStatus
-- =======================================================================================================================

--lcsQosQCLStatusTable
    lcsQosQCLStatusTable OBJECT-TYPE
               SYNTAX      SEQUENCE OF     LCSQosQCLStatusEntry
               MAX-ACCESS  not-accessible
               STATUS      current
               DESCRIPTION
                   "The basic QoS DSCP Translation settings for all switches."
               ::= {     lcsQosQCLStatus 1 }

    lcsQosQCLStatusEntry OBJECT-TYPE
               SYNTAX          LCSQosQCLStatusEntry
               MAX-ACCESS  not-accessible
               STATUS      current
               DESCRIPTION
                   "The Qos QCL Status Entry."
               INDEX    {     lcsQosQCLStatusList  }
               ::= {     lcsQosQCLStatusTable 1 }

    LCSQosQCLStatusEntry             ::= SEQUENCE {
        lcsQosQCLStatusList               Integer32,
        lcsQosQCLStatusUser               DisplayString,
        lcsQosQCLStatusQCEId              DisplayString,
        lcsQosQCLStatusFrameType          DisplayString,
        lcsQosQCLStatusPortlist           DisplayString,
        lcsQosQCLStatusActionQueuePriority DisplayString,
        lcsQosQCLStatusActionDPL          DisplayString,
        lcsQosQCLStatusActionDSCP         DisplayString,
        lcsQosQCLStatusActionPCP          DisplayString,
        lcsQosQCLStatusActionDEL          DisplayString,
        lcsQosQCLStatusActionPolicy       DisplayString,
        lcsQosQCLStatusConflict           DisplayString,
--      lcsQosQCLStatusSwitch             Integer32,
        lcsQosQCLStatusDMAC               DisplayString,
        lcsQosQCLStatusSMAC               DisplayString,
        lcsQosQCLStatusTag                DisplayString,
        lcsQosQCLStatusVID                DisplayString,
        lcsQosQCLStatusPCP                DisplayString,
        lcsQosQCLStatusDEI                DisplayString
                }

    lcsQosQCLStatusList OBJECT-TYPE
               SYNTAX      Integer32(1..4094)
               MAX-ACCESS  not-accessible
               STATUS      current
               DESCRIPTION
                   "QCL table index."
               ::= {     lcsQosQCLStatusEntry 1}

    lcsQosQCLStatusUser OBJECT-TYPE
               SYNTAX      DisplayString
               MAX-ACCESS  read-only
               STATUS      current
               DESCRIPTION
                   "Indicates the QCL user."
               ::= {     lcsQosQCLStatusEntry 2 }

    lcsQosQCLStatusQCEId OBJECT-TYPE
               SYNTAX      DisplayString
               MAX-ACCESS  read-only
               STATUS      current
               DESCRIPTION
                  "Indicates the index of QCE."
               ::= {     lcsQosQCLStatusEntry 3}

    lcsQosQCLStatusFrameType OBJECT-TYPE
               SYNTAX      DisplayString
               MAX-ACCESS  read-only
               STATUS      current
               DESCRIPTION
                   "Indicates the type of frame to look for incomming frames.
                    Any: The QCE will match all frame type.
                    Ethernet: Only Ethernet frames (with Ether Type 0x600-0xFFFF)
                    are allowed.
                    LLC: Only (LLC) frames are allowed.
                    SNAP: Only (SNAP) frames are allowed.
                    IPv4: The QCE will match only IPV4 frames.
                    IPv6: The QCE will match only IPV6 frames."
               ::= {     lcsQosQCLStatusEntry 4}

    lcsQosQCLStatusPortlist OBJECT-TYPE
               SYNTAX      DisplayString
               MAX-ACCESS  read-only
               STATUS      current
               DESCRIPTION
                   "Indicates the list of ports configured with the QCE."
               ::= {     lcsQosQCLStatusEntry 5}

    lcsQosQCLStatusActionQueuePriority OBJECT-TYPE
               SYNTAX      DisplayString
               MAX-ACCESS  read-only
               STATUS      current
               DESCRIPTION
                   "Classified QoS class; if a frame matches the
                    QCE it will be put in the  queue."
               ::= {     lcsQosQCLStatusEntry 6}

    lcsQosQCLStatusActionDPL OBJECT-TYPE
               SYNTAX      DisplayString
               MAX-ACCESS  read-only
               STATUS      current
               DESCRIPTION
                   "Drop Precedence Level; if a frame matches the QCE then
                    DP level will set to value displayed under DPL column."
               ::= {     lcsQosQCLStatusEntry 7}

    lcsQosQCLStatusActionDSCP OBJECT-TYPE
               SYNTAX      DisplayString
               MAX-ACCESS  read-only
               STATUS      current
               DESCRIPTION
                   "If a frame matches the QCE then DSCP will be
                    classified with the value
                    displayed under DSCP column."
               ::= {     lcsQosQCLStatusEntry 8}

    lcsQosQCLStatusActionPCP OBJECT-TYPE
               SYNTAX      DisplayString
               MAX-ACCESS  read-only
               STATUS      current
               DESCRIPTION
                   "Classify PCP value.
                    Only support SERVAL."
               ::= {     lcsQosQCLStatusEntry 9}

    lcsQosQCLStatusActionDEL OBJECT-TYPE
               SYNTAX      DisplayString
               MAX-ACCESS  read-only
               STATUS      current
               DESCRIPTION
                   "Classify DEI value.
                    Only support SERVAL."
               ::= {     lcsQosQCLStatusEntry 10}

    lcsQosQCLStatusActionPolicy OBJECT-TYPE
               SYNTAX      DisplayString
               MAX-ACCESS  read-only
               STATUS      current
               DESCRIPTION
                   "Classify ACL Policy number.
                    "
               ::= {     lcsQosQCLStatusEntry 11}

    lcsQosQCLStatusConflict OBJECT-TYPE
               SYNTAX      DisplayString
               MAX-ACCESS  read-only
               STATUS      current
               DESCRIPTION
                   "Displays Conflict status of QCL entries."
               ::= {     lcsQosQCLStatusEntry 12}

--    lcsQosQCLStatusSwitch OBJECT-TYPE
--               SYNTAX      Integer32
--               MAX-ACCESS  read-only
--               STATUS      current
--               DESCRIPTION
--                   "Switch number for port members. -1:Any.
--                    Only support stacking switch."
--               ::= {     lcsQosQCLStatusEntry 13}
               
    lcsQosQCLStatusDMAC OBJECT-TYPE
               SYNTAX      DisplayString
               MAX-ACCESS  read-only
               STATUS      current
               DESCRIPTION
                   "Destination MAC address: Possible values are 'Unicast', 'Multicast', 'Broadcast' or 'Any'."
               ::= {     lcsQosQCLStatusEntry 14}

    lcsQosQCLStatusSMAC OBJECT-TYPE
               SYNTAX      DisplayString
               MAX-ACCESS  read-only
               STATUS      current
               DESCRIPTION
                   "Source MAC address: xx-xx-xx-xx-xx-xx or 'Any'."
               ::= {     lcsQosQCLStatusEntry 15}

    lcsQosQCLStatusTag OBJECT-TYPE
               SYNTAX      DisplayString
               MAX-ACCESS  read-only
               STATUS      current
               DESCRIPTION
                   "Value of Tag field can be 'Untagged', 'Tagged', 'C-Tagged', 'S-Tagged' or 'Any'."
               ::= {     lcsQosQCLStatusEntry 16}

    lcsQosQCLStatusVID OBJECT-TYPE
               SYNTAX      DisplayString
               MAX-ACCESS  read-only
               STATUS      current
               DESCRIPTION
                   "Valid value of VLAN ID can be any value in the range 1-4094 or 'Any'"
               ::= {     lcsQosQCLStatusEntry 17}              

    lcsQosQCLStatusPCP OBJECT-TYPE
               SYNTAX      DisplayString
               MAX-ACCESS  read-only
               STATUS      current
               DESCRIPTION
                   "Valid value PCP are specific (0, 1, 2, 3, 4, 5, 6, 7) or range (0-1, 2-3, 4-5, 6-7, 0-3, 4-7) or 'Any'."
               ::= {     lcsQosQCLStatusEntry 18}   

    lcsQosQCLStatusDEI OBJECT-TYPE
               SYNTAX      DisplayString
               MAX-ACCESS  read-only
               STATUS      current
               DESCRIPTION
                   "Valid value of DEI can be '0', '1' or 'Any'."
               ::= {     lcsQosQCLStatusEntry 19}                  

    lcsQosPortShaperTable OBJECT-TYPE
               SYNTAX      SEQUENCE OF     LCSQosPortShaperEntry
               MAX-ACCESS  not-accessible
               STATUS      current
               DESCRIPTION
                   "INDEX for this table is ifIndex which is
                    equivalent to the panel port number."
               ::= {     lcsQosPortShapers 1 }

    lcsQosPortShaperEntry OBJECT-TYPE
               SYNTAX          LCSQosPortShaperEntry
               MAX-ACCESS  not-accessible
               STATUS      current
               DESCRIPTION
                   "The Qos Port Shaper Entry."
               INDEX    {     ifIndex  }
               ::= {     lcsQosPortShaperTable 1 }

    LCSQosPortShaperEntry             ::= SEQUENCE {
                lcsQosPortShaperQueue0Enable   AdminMode,
                lcsQosPortShaperQueue0Rate     Integer32,
                lcsQosPortShaperQueue0Unit     Integer32,
                lcsQosPortShaperQueue1Enable   AdminMode,
                lcsQosPortShaperQueue1Rate     Integer32,
                lcsQosPortShaperQueue1Unit     Integer32,
                lcsQosPortShaperQueue2Enable   AdminMode,
                lcsQosPortShaperQueue2Rate     Integer32,
                lcsQosPortShaperQueue2Unit     Integer32,
                lcsQosPortShaperQueue3Enable   AdminMode,
                lcsQosPortShaperQueue3Rate     Integer32,
                lcsQosPortShaperQueue3Unit     Integer32,
                lcsQosPortShaperQueue4Enable   AdminMode,
                lcsQosPortShaperQueue4Rate     Integer32,
                lcsQosPortShaperQueue4Unit     Integer32,
                lcsQosPortShaperQueue5Enable   AdminMode,
                lcsQosPortShaperQueue5Rate     Integer32,
                lcsQosPortShaperQueue5Unit     Integer32,
                lcsQosPortShaperQueue6Enable   AdminMode,
                lcsQosPortShaperQueue6Rate     Integer32,
                lcsQosPortShaperQueue6Unit     Integer32,
                lcsQosPortShaperQueue7Enable   AdminMode,
                lcsQosPortShaperQueue7Rate     Integer32,
                lcsQosPortShaperQueue7Unit     Integer32,
                lcsQosPortShaperEnable         AdminMode,
                lcsQosPortShaperRate           Integer32,
                lcsQosPortShaperRateType       Integer32
                }

    lcsQosPortShaperQueue0Enable OBJECT-TYPE
               SYNTAX      AdminMode
               MAX-ACCESS  read-write
               STATUS      current
               DESCRIPTION
                   "Controls whether the queue shaper is enabled on this switch port."
               DEFVAL  { disable }
               ::= {     lcsQosPortShaperEntry 3 }

    lcsQosPortShaperQueue0Rate OBJECT-TYPE
               SYNTAX      Integer32
               MAX-ACCESS  read-write
               STATUS      current
               DESCRIPTION
                   "Controls whether the queue shaper rate.
                    default: 500(Kbps)"
               ::= {     lcsQosPortShaperEntry 4 }

    lcsQosPortShaperQueue0Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 5 }             
               
    lcsQosPortShaperQueue1Enable OBJECT-TYPE
               SYNTAX      AdminMode
               MAX-ACCESS  read-write
               STATUS      current
               DESCRIPTION
                   "Controls whether the queue shaper is enabled on this switch port."
               DEFVAL  { disable }
               ::= {     lcsQosPortShaperEntry 6 }

    lcsQosPortShaperQueue1Rate OBJECT-TYPE
               SYNTAX      Integer32
               MAX-ACCESS  read-write
               STATUS      current
               DESCRIPTION
                   "Controls whether the queue shaper rate.
                    default: 500(Kbps)"
               ::= {     lcsQosPortShaperEntry 7 }

    lcsQosPortShaperQueue1Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 8 }             
               
    lcsQosPortShaperQueue2Enable OBJECT-TYPE
               SYNTAX      AdminMode
               MAX-ACCESS  read-write
               STATUS      current
               DESCRIPTION
                   "Controls whether the queue shaper is enabled on this switch port."
               DEFVAL  { disable }
               ::= {     lcsQosPortShaperEntry 9 }

    lcsQosPortShaperQueue2Rate OBJECT-TYPE
               SYNTAX      Integer32
               MAX-ACCESS  read-write
               STATUS      current
               DESCRIPTION
                   "Controls whether the queue shaper rate.
                    default: 500(Kbps)"
               ::= {     lcsQosPortShaperEntry 10 }

    lcsQosPortShaperQueue2Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 11 }               

    lcsQosPortShaperQueue3Enable OBJECT-TYPE
               SYNTAX      AdminMode
               MAX-ACCESS  read-write
               STATUS      current
               DESCRIPTION
                   "Controls whether the queue shaper is enabled on this switch port."
               DEFVAL  { disable }
               ::= {     lcsQosPortShaperEntry 12 }

    lcsQosPortShaperQueue3Rate OBJECT-TYPE
               SYNTAX      Integer32
               MAX-ACCESS  read-write
               STATUS      current
               DESCRIPTION
                   "Controls whether the queue shaper rate.
                    default: 500(Kbps)"
               ::= {     lcsQosPortShaperEntry 13 }

    lcsQosPortShaperQueue3Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 14 } 
               
    lcsQosPortShaperQueue4Enable OBJECT-TYPE
               SYNTAX      AdminMode
               MAX-ACCESS  read-write
               STATUS      current
               DESCRIPTION
                   "Controls whether the queue shaper is enabled on this switch port."
               DEFVAL  { disable }
               ::= {     lcsQosPortShaperEntry 15 }

    lcsQosPortShaperQueue4Rate OBJECT-TYPE
               SYNTAX      Integer32
               MAX-ACCESS  read-write
               STATUS      current
               DESCRIPTION
                   "Controls whether the queue shaper rate.
                    default: 500(Kbps)"
               ::= {     lcsQosPortShaperEntry 16 }

    lcsQosPortShaperQueue4Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 17 } 
               
    lcsQosPortShaperQueue5Enable OBJECT-TYPE
               SYNTAX      AdminMode
               MAX-ACCESS  read-write
               STATUS      current
               DESCRIPTION
                   "Controls whether the queue shaper is enabled on this switch port."
               DEFVAL  { disable }
               ::= {     lcsQosPortShaperEntry 18 }

    lcsQosPortShaperQueue5Rate OBJECT-TYPE
               SYNTAX      Integer32
               MAX-ACCESS  read-write
               STATUS      current
               DESCRIPTION
                   "Controls whether the queue shaper rate.
                    default: 500(Kbps)"
               ::= {     lcsQosPortShaperEntry 19 }

    lcsQosPortShaperQueue5Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 20 } 
               
    lcsQosPortShaperQueue6Enable OBJECT-TYPE
               SYNTAX      AdminMode
               MAX-ACCESS  read-write
               STATUS      current
               DESCRIPTION
                   "Controls whether the queue shaper is enabled on this switch port."
               DEFVAL  { disable }
               ::= {     lcsQosPortShaperEntry 21 }

    lcsQosPortShaperQueue6Rate OBJECT-TYPE
               SYNTAX      Integer32
               MAX-ACCESS  read-write
               STATUS      current
               DESCRIPTION
                   "Controls whether the queue shaper rate.
                    default: 500(Kbps)"
               ::= {     lcsQosPortShaperEntry 22 }

    lcsQosPortShaperQueue6Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 23 } 
               
    lcsQosPortShaperQueue7Enable OBJECT-TYPE
               SYNTAX      AdminMode
               MAX-ACCESS  read-write
               STATUS      current
               DESCRIPTION
                   "Controls whether the queue shaper is enabled on this switch port."
               DEFVAL  { disable }
               ::= {     lcsQosPortShaperEntry 24 }

    lcsQosPortShaperQueue7Rate OBJECT-TYPE
               SYNTAX      Integer32
               MAX-ACCESS  read-write
               STATUS      current
               DESCRIPTION
                   "Controls whether the queue shaper rate.
                    default: 500(Kbps)"
               ::= {     lcsQosPortShaperEntry 25 }

    lcsQosPortShaperQueue7Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     lcsQosPortShaperEntry 26 } 
               
    lcsQosPortShaperEnable OBJECT-TYPE
               SYNTAX      AdminMode
               MAX-ACCESS  read-write
               STATUS      current
               DESCRIPTION
                   "Controls whether the port shaper is enabled."
               DEFVAL  { disable }
               ::= {     lcsQosPortShaperEntry 27 }

    lcsQosPortShaperRate OBJECT-TYPE
               SYNTAX      Integer32
               MAX-ACCESS  read-write
               STATUS      current
               DESCRIPTION
                   "Controls the rate for the port shaper.
                    default: 500 kbps."
               ::= {     lcsQosPortShaperEntry 28 }

    lcsQosPortShaperRateType OBJECT-TYPE
               SYNTAX      Integer32(0|1)
               MAX-ACCESS  read-write
               STATUS      current
               DESCRIPTION
                   "The rate type of the port shaper. 
                    0:Line
                    1:Data"
               ::= {     lcsQosPortShaperEntry 29 }
               
    lcsQosPortSchedulersTable OBJECT-TYPE
               SYNTAX      SEQUENCE OF     LCSQosPortSchedulersEntry
               MAX-ACCESS  not-accessible
               STATUS      current
               DESCRIPTION
                   "INDEX for this table is ifIndex which is
                    equivalent to the panel port number."
               ::= {     lcsQosPortSchedulers 1 }

    lcsQosPortSchedulersEntry OBJECT-TYPE
               SYNTAX          LCSQosPortSchedulersEntry
               MAX-ACCESS  not-accessible
               STATUS      current
               DESCRIPTION
                   "The Qos Port Shaper Entry."
               INDEX    {     ifIndex  }
               ::= {     lcsQosPortSchedulersTable 1 }

    LCSQosPortSchedulersEntry             ::= SEQUENCE {
                lcsQosPortSchedulersMode     Integer32,
                lcsQosPortSchedulersQ0Weight Integer32,
                lcsQosPortSchedulersQ1Weight Integer32,
                lcsQosPortSchedulersQ2Weight Integer32,
                lcsQosPortSchedulersQ3Weight Integer32,
                lcsQosPortSchedulersQ4Weight Integer32,
                lcsQosPortSchedulersQ5Weight Integer32,
                lcsQosPortSchedulersQ6Weight Integer32,
                lcsQosPortSchedulersQ7Weight Integer32               
                }

    lcsQosPortSchedulersMode OBJECT-TYPE
               SYNTAX      Integer32(0|8)
               MAX-ACCESS  read-write
               STATUS      current
               DESCRIPTION
                   "0:Strict Priority
                    8:Weighted"
               ::= {     lcsQosPortSchedulersEntry 2 }
    
    lcsQosPortSchedulersQ0Weight OBJECT-TYPE
               SYNTAX      Integer32(1..100)
               MAX-ACCESS  read-write
               STATUS      current
               DESCRIPTION
                   "Controls the weight for this queue. This value is restricted to 1-100."
               ::= {     lcsQosPortSchedulersEntry 3 }  

    lcsQosPortSchedulersQ1Weight OBJECT-TYPE
               SYNTAX      Integer32(1..100)
               MAX-ACCESS  read-write
               STATUS      current
               DESCRIPTION
                   "Controls the weight for this queue. This value is restricted to 1-100."
               ::= {     lcsQosPortSchedulersEntry 4 }  

    lcsQosPortSchedulersQ2Weight OBJECT-TYPE
               SYNTAX      Integer32(1..100)
               MAX-ACCESS  read-write
               STATUS      current
               DESCRIPTION
                   "Controls the weight for this queue. This value is restricted to 1-100."
               ::= {     lcsQosPortSchedulersEntry 5 }  
               
    lcsQosPortSchedulersQ3Weight OBJECT-TYPE
               SYNTAX      Integer32(1..100)
               MAX-ACCESS  read-write
               STATUS      current
               DESCRIPTION
                   "Controls the weight for this queue. This value is restricted to 1-100."
               ::= {     lcsQosPortSchedulersEntry 6 }  

    lcsQosPortSchedulersQ4Weight OBJECT-TYPE
               SYNTAX      Integer32(1..100)
               MAX-ACCESS  read-write
               STATUS      current
               DESCRIPTION
                   "Controls the weight for this queue. This value is restricted to 1-100."
               ::= {     lcsQosPortSchedulersEntry 7 }  
   
    lcsQosPortSchedulersQ5Weight OBJECT-TYPE
               SYNTAX      Integer32(1..100)
               MAX-ACCESS  read-write
               STATUS      current
               DESCRIPTION
                   "Controls the weight for this queue. This value is restricted to 1-100."
               ::= {     lcsQosPortSchedulersEntry 8 }  

    lcsQosPortSchedulersQ6Weight OBJECT-TYPE
               SYNTAX      Integer32(1..100)
               MAX-ACCESS  read-write
               STATUS      current
               DESCRIPTION
                   "Controls the weight for this queue. This value is restricted to 1-100."
               ::= {     lcsQosPortSchedulersEntry 9 }  

    lcsQosPortSchedulersQ7Weight OBJECT-TYPE
               SYNTAX      Integer32(1..100)
               MAX-ACCESS  read-write
               STATUS      current
               DESCRIPTION
                   "Controls the weight for this queue. This value is restricted to 1-100."
               ::= {     lcsQosPortSchedulersEntry 10 }  
               
-- =======================================================================================================================
--lcsBroadcastStormProtection                                                  OBJECT IDENTIFIER ::= { lcsConfiguration 11 }
--
--lcsBroadcastStormProtectionConfigurationTable OBJECT-TYPE
--   SYNTAX      SEQUENCE OF LCSBroadcastStormProtectionConfigurationEntry
--   MAX-ACCESS  not-accessible
--   STATUS      current
--   DESCRIPTION
--       " Show Broadcast Storm Protection configurations. "
--   ::= { lcsBroadcastStormProtection 1 }
--
--lcsBroadcastStormProtectionConfigurationEntry OBJECT-TYPE
--   SYNTAX      LCSBroadcastStormProtectionConfigurationEntry
--   MAX-ACCESS  not-accessible
--   STATUS      current
--   DESCRIPTION
--       ""
--   INDEX    { lcsBroadcastStormProtectionConfPort  }
--   ::= { lcsBroadcastStormProtectionConfigurationTable 1 }
--
--LCSBroadcastStormProtectionConfigurationEntry ::= SEQUENCE {
--   lcsBroadcastStormProtectionConfPort        Integer32,
--   lcsBroadcastStormProtectionConfMode        INTEGER,
--   lcsBroadcastStormProtectionConfAction  Integer32,
--   lcsBroadcastStormProtectionConfPPS     Integer32,
--   lcsBroadcastStormProtectionConfTimer   Integer32,
--   lcsBroadcastStormProtectionConfstatus  DisplayString
--}
--
--lcsBroadcastStormProtectionConfPort OBJECT-TYPE
--   SYNTAX      Integer32 (1..4094)
--   MAX-ACCESS  not-accessible
--   STATUS      current
--   DESCRIPTION
--       " port, range : 1 - port number. "
--   ::= { lcsBroadcastStormProtectionConfigurationEntry 1 }
--
--lcsBroadcastStormProtectionConfMode OBJECT-TYPE
--   SYNTAX      INTEGER { disable(0), enable(1)}
--   MAX-ACCESS  read-write
--   STATUS      current
--   DESCRIPTION
--       " Configure broadcast storm protection port mode.
--         0: disable, 
--         1: enable
--         default: disable. "
--   ::= { lcsBroadcastStormProtectionConfigurationEntry 2 }
--
--lcsBroadcastStormProtectionConfAction OBJECT-TYPE
--   SYNTAX      Integer32 (0..2)
--   MAX-ACCESS  read-write
--   STATUS      current
--   DESCRIPTION
--       " Configure broadcast storm protection port action.
--         0: Shutdown port, 
--         1: Shutdown port and Log,
--         2: Log Only,
--         default: Shutdown port. "
--   ::= { lcsBroadcastStormProtectionConfigurationEntry 3 }
--
--lcsBroadcastStormProtectionConfPPS OBJECT-TYPE
--   SYNTAX      Integer32 (0..1000000)
--   MAX-ACCESS  read-write
--   STATUS      current
--   DESCRIPTION
--       " Configure broadcast storm protection pps.
--         default: 0. "
--   ::= { lcsBroadcastStormProtectionConfigurationEntry 4 }
--
--lcsBroadcastStormProtectionConfTimer OBJECT-TYPE
--   SYNTAX      Integer32 (0..65535)
--   MAX-ACCESS  read-write
--   STATUS      current
--   DESCRIPTION
--       "Configure broadcast storm protection timer(seconds)
--        default: 300(seconds). "
--   ::= { lcsBroadcastStormProtectionConfigurationEntry 5 }
--
--lcsBroadcastStormProtectionConfstatus OBJECT-TYPE
--   SYNTAX      DisplayString
--   MAX-ACCESS  read-only
--   STATUS      current
--   DESCRIPTION
--       " Show broadcast storm protection status. "
--   ::= { lcsBroadcastStormProtectionConfigurationEntry 6 }
-- 
-- =======================================================================================================================
lcsLoopProtection                                                  OBJECT IDENTIFIER ::= { lcsConfiguration 12 }

lcsLoopProtectionConfig                                            OBJECT IDENTIFIER ::= { lcsLoopProtection 1 }

lcsLoopProtectionGlobalEnable OBJECT-TYPE
   SYNTAX      Integer32(0|1)
   MAX-ACCESS  read-write
   STATUS      current
   DESCRIPTION
       "Configure loop protection mode.
        0: disable,
        1: enable,
        default: disable. "
   ::= { lcsLoopProtectionConfig 1 }

lcsLoopProtectionTranmisstionTime OBJECT-TYPE
   SYNTAX      Integer32(1..10)
   MAX-ACCESS  read-write
   STATUS      current
   DESCRIPTION
       "Configure loop protection transmit interval.
        default: 5,
        range: 1-10. "
   ::= { lcsLoopProtectionConfig 2 }

lcsLoopProtectionShutdownTime OBJECT-TYPE
   SYNTAX      Integer32(0..604800)
   MAX-ACCESS  read-write
   STATUS      current
   DESCRIPTION
       "Configure loop protection shutdown time.
        default: 180,
        range: 0-604800. "
   ::= { lcsLoopProtectionConfig 3 }

lcsLoopProtectionConfigurationTable OBJECT-TYPE
   SYNTAX      SEQUENCE OF LCSLoopProtectionConfigurationEntry
   MAX-ACCESS  not-accessible
   STATUS      current
   DESCRIPTION
       " Show Loop Protection configurations. "
   ::= { lcsLoopProtectionConfig 4 }

lcsLoopProtectionConfigurationEntry OBJECT-TYPE
   SYNTAX      LCSLoopProtectionConfigurationEntry
   MAX-ACCESS  not-accessible
   STATUS      current
   DESCRIPTION
       " "
   INDEX    { lcsLoopProtectionConfPort  }
   ::= { lcsLoopProtectionConfigurationTable 1 }

LCSLoopProtectionConfigurationEntry ::= SEQUENCE {
   lcsLoopProtectionConfPort        Integer32,
   lcsLoopProtectionConfEnable  Integer32,
   lcsLoopProtectionConfAction  Integer32,
   lcsLoopProtectionConfTxmode  Integer32
}

lcsLoopProtectionConfPort OBJECT-TYPE
   SYNTAX      Integer32 (1..4094)
   MAX-ACCESS  not-accessible
   STATUS      current
   DESCRIPTION
       " port, range : 1 - port number. "
   ::= { lcsLoopProtectionConfigurationEntry 1 }

lcsLoopProtectionConfEnable OBJECT-TYPE
   SYNTAX      Integer32(0|1)
   MAX-ACCESS  read-write
   STATUS      current
   DESCRIPTION
       "Configure loop protection port mode.
        0: disable,
        1: enable,
        default: enable. "
   ::= { lcsLoopProtectionConfigurationEntry 2 }

lcsLoopProtectionConfAction OBJECT-TYPE
   SYNTAX      Integer32(0..2)
   MAX-ACCESS  read-write
   STATUS      current
   DESCRIPTION
       " Configure loop protection port action.
         0: Shutdown port,
         1: Shutdown port and Log,
         2: Log Only,
         default: Shutdown port. "
   ::= { lcsLoopProtectionConfigurationEntry 3 }

lcsLoopProtectionConfTxmode OBJECT-TYPE
   SYNTAX      Integer32(0|1)
   MAX-ACCESS  read-write
   STATUS      current
   DESCRIPTION
       "Configure loop protection port transmit mode.
        0: disable,
        1: enable,
        default: enable. "
   ::= { lcsLoopProtectionConfigurationEntry 4 }

lcsLoopProtectionConfActPort OBJECT-TYPE
   SYNTAX      Integer32(0..2)
   MAX-ACCESS  read-write
   STATUS      current
   DESCRIPTION
       " Configure loop protection act port.
         0: Recipient port,
         1: Source port,
         2: Both,
         default: Recipient port."
   ::= { lcsLoopProtectionConfigurationEntry 101 }

lcsLoopProtectionStatusTable OBJECT-TYPE
   SYNTAX      SEQUENCE OF LCSLoopProtectionStatusEntry
   MAX-ACCESS  not-accessible
   STATUS      current
   DESCRIPTION
       " Show Loop Protection Status. "
   ::= { lcsLoopProtection 2 }

lcsLoopProtectionStatusEntry OBJECT-TYPE
   SYNTAX      LCSLoopProtectionStatusEntry
   MAX-ACCESS  not-accessible
   STATUS      current
   DESCRIPTION
       " "
   INDEX    { lcsLoopProtectionStatusPort  }
   ::= { lcsLoopProtectionStatusTable 1 }

LCSLoopProtectionStatusEntry ::= SEQUENCE {
   lcsLoopProtectionStatusPort         Integer32,
   lcsLoopProtectionStatusAction           DisplayString,
   lcsLoopProtectionStatusTransmit     DisplayString,
   lcsLoopProtectionStatusLoops        Integer32,
   lcsLoopProtectionStatusStatus           DisplayString,
   lcsLoopProtectionStatusLoop         DisplayString,
   lcsLoopProtectionStatusTimeLastLoop  DisplayString
}

lcsLoopProtectionStatusPort OBJECT-TYPE
   SYNTAX      Integer32 (1..4094)
   MAX-ACCESS  not-accessible
   STATUS      current
   DESCRIPTION
       " port, range : 1 - port number. "
   ::= { lcsLoopProtectionStatusEntry 1 }

lcsLoopProtectionStatusAction OBJECT-TYPE
   SYNTAX      DisplayString
   MAX-ACCESS  read-only
   STATUS      current
   DESCRIPTION
       " The currently configured port action. "
   ::= { lcsLoopProtectionStatusEntry 2 }

lcsLoopProtectionStatusTransmit OBJECT-TYPE
   SYNTAX      DisplayString
   MAX-ACCESS  read-only
   STATUS      current
   DESCRIPTION
       " The currently configured port transmit mode. "
   ::= { lcsLoopProtectionStatusEntry 3 }

lcsLoopProtectionStatusLoops OBJECT-TYPE
   SYNTAX      Counter32
   MAX-ACCESS  read-only
   STATUS      current
   DESCRIPTION
       " The number of loops detected on this port. "
   ::= { lcsLoopProtectionStatusEntry 4 }

lcsLoopProtectionStatusStatus OBJECT-TYPE
   SYNTAX      DisplayString
   MAX-ACCESS  read-only
   STATUS      current
   DESCRIPTION
       " The current loop protection status of the port. "
   ::= { lcsLoopProtectionStatusEntry 5 }

lcsLoopProtectionStatusLoop OBJECT-TYPE
   SYNTAX      DisplayString
   MAX-ACCESS  read-only
   STATUS      current
   DESCRIPTION
       " Whether a loop is currently detected on the port. "
   ::= { lcsLoopProtectionStatusEntry 6 }

lcsLoopProtectionStatusTimeLastLoop OBJECT-TYPE
   SYNTAX      DisplayString
   MAX-ACCESS  read-only
   STATUS      current
   DESCRIPTION
       " The time of the last loop event detected. "
   ::= { lcsLoopProtectionStatusEntry 7 }

lcsLoopProtectionStatusActPort OBJECT-TYPE
   SYNTAX      DisplayString
   MAX-ACCESS  read-only
   STATUS      current
   DESCRIPTION
       " The currently configured act port. "
   ::= { lcsLoopProtectionStatusEntry 101 }

-- =======================================================================================================================
lcsPoe                                                           OBJECT IDENTIFIER ::= { lcsConfiguration 13 }

lcsPoeStatus                                            OBJECT IDENTIFIER ::= { lcsPoe 1 }

lcsPoeStatusTable OBJECT-TYPE
   SYNTAX      SEQUENCE OF LCSPoeStatusEntry
   MAX-ACCESS  not-accessible
   STATUS      current
   DESCRIPTION
       " Configure PoE Scheduling Table. "
   ::= { lcsPoeStatus 1 }

lcsPoeStatusEntry OBJECT-TYPE
   SYNTAX      LCSPoeStatusEntry
   MAX-ACCESS  not-accessible
   STATUS      current
   DESCRIPTION
       " "
   INDEX    { lcsPoeStatusLocalPort }
   ::= { lcsPoeStatusTable 1 }

LCSPoeStatusEntry ::= SEQUENCE {
   lcsPoeStatusLocalPort              Integer32,
   lcsPoeStatusPDclass            DisplayString,
   lcsPoeStatusPowerRequested     DisplayString,
   lcsPoeStatusPowerAllocated     DisplayString,
   lcsPoeStatusPowerUsed          DisplayString,
   lcsPoeStatusCurrentUsed        DisplayString,
   lcsPoeStatusPriority           DisplayString,
   lcsPoeStatusPortStatus         DisplayString
}

lcsPoeStatusLocalPort OBJECT-TYPE
   SYNTAX      Integer32 (1..10)
   MAX-ACCESS  not-accessible
   STATUS      current
   DESCRIPTION
       "Local port Index."
   ::= { lcsPoeStatusEntry 1 }


lcsPoeStatusPDclass OBJECT-TYPE
   SYNTAX      DisplayString
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { lcsPoeStatusEntry 2 }

lcsPoeStatusPowerRequested OBJECT-TYPE
   SYNTAX      DisplayString
   MAX-ACCESS  read-only
   STATUS      current
   DESCRIPTION
      " The Power Requested shows the requested amount of power the PD wants to be reserved. "
   ::= { lcsPoeStatusEntry 3}

lcsPoeStatusPowerAllocated OBJECT-TYPE
   SYNTAX      DisplayString
   MAX-ACCESS  read-only
   STATUS      current
   DESCRIPTION
      " The Power Allocated shows the amount of power the switch has allocated for the PD. "
   ::= { lcsPoeStatusEntry 4}

lcsPoeStatusPowerUsed OBJECT-TYPE
   SYNTAX      DisplayString
   MAX-ACCESS  read-only
   STATUS      current
   DESCRIPTION
      " The Power Used shows how much power the PD currently is using. "
   ::= { lcsPoeStatusEntry 5}

lcsPoeStatusCurrentUsed OBJECT-TYPE
   SYNTAX      DisplayString
   MAX-ACCESS  read-only
   STATUS      current
   DESCRIPTION
      " The Power Used shows how much current the PD currently is using. "
   ::= { lcsPoeStatusEntry 6}

lcsPoeStatusPriority OBJECT-TYPE
   SYNTAX      DisplayString
   MAX-ACCESS  read-only
   STATUS      current
   DESCRIPTION
      " The Priority shows the port's priority configured by the user.  "
   ::= { lcsPoeStatusEntry 7}

lcsPoeStatusPortStatus OBJECT-TYPE
   SYNTAX      DisplayString
   MAX-ACCESS  read-only
   STATUS      current
   DESCRIPTION
      " The Port Status shows the port's status.  "
   ::= { lcsPoeStatusEntry 8}

lcsPoeStatusTotalTable OBJECT-TYPE
   SYNTAX      SEQUENCE OF LCSPoeStatusTotalEntry
   MAX-ACCESS  not-accessible
   STATUS      current
   DESCRIPTION
       " Configure PoE Scheduling Total Table. "
   ::= { lcsPoeStatus 2 }

lcsPoeStatusTotalEntry OBJECT-TYPE
   SYNTAX      LCSPoeStatusTotalEntry
   MAX-ACCESS  not-accessible
   STATUS      current
   DESCRIPTION
       " "
   INDEX    { lcsPoeStatusSwitchIndex }
   ::= { lcsPoeStatusTotalTable 1 }

LCSPoeStatusTotalEntry ::= SEQUENCE {
   lcsPoeStatusSwitchIndex            Integer32,
   lcsPoeStatusTotalPowerRequested    DisplayString,
   lcsPoeStatusTotalPowerAllocated    DisplayString,
   lcsPoeStatusTotalPowerUsed         DisplayString,
   lcsPoeStatusTotalCurrentUsed       DisplayString
}

lcsPoeStatusSwitchIndex OBJECT-TYPE
   SYNTAX      Integer32 (1..16)
   MAX-ACCESS  not-accessible
   STATUS      current
   DESCRIPTION
       "Switch Index."
   ::= { lcsPoeStatusTotalEntry 1 }

lcsPoeStatusTotalPowerRequested OBJECT-TYPE
   SYNTAX      DisplayString
   MAX-ACCESS  read-only
   STATUS      current
   DESCRIPTION
      " Total Power Requested."
   ::= { lcsPoeStatusTotalEntry 2}

lcsPoeStatusTotalPowerAllocated OBJECT-TYPE
   SYNTAX      DisplayString
   MAX-ACCESS  read-only
   STATUS      current
   DESCRIPTION
      " Total Power allocated."
   ::= { lcsPoeStatusTotalEntry 3}

lcsPoeStatusTotalPowerUsed OBJECT-TYPE
   SYNTAX      DisplayString
   MAX-ACCESS  read-only
   STATUS      current
   DESCRIPTION
      " Total Power Used."
   ::= { lcsPoeStatusTotalEntry 4}

lcsPoeStatusTotalCurrentUsed OBJECT-TYPE
   SYNTAX      DisplayString
   MAX-ACCESS  read-only
   STATUS      current
   DESCRIPTION
      " Total Current Used."
   ::= { lcsPoeStatusTotalEntry 5}


lcsPoePowerDelay                                                 OBJECT IDENTIFIER ::= { lcsPoe 2 }

lcsPoePowerDelayTable OBJECT-TYPE
   SYNTAX      SEQUENCE OF LCSPoePowerDelayEntry
   MAX-ACCESS  not-accessible
   STATUS      current
   DESCRIPTION
       " Configure PoE Power Delay mode. "
   ::= { lcsPoePowerDelay 1 }

lcsPoePowerDelayEntry OBJECT-TYPE
   SYNTAX      LCSPoePowerDelayEntry
   MAX-ACCESS  not-accessible
   STATUS      current
   DESCRIPTION
       " "
   INDEX    { lcsPoePowerDelayPort  }
   ::= { lcsPoePowerDelayTable 1 }

LCSPoePowerDelayEntry ::= SEQUENCE {
   lcsPoePowerDelayPort         Integer32,
   lcsPoePowerDelayMode         Integer32,
   lcsPoePowerDelayTime         Integer32
}

lcsPoePowerDelayPort OBJECT-TYPE
   SYNTAX      Integer32 (1..4094)
   MAX-ACCESS  not-accessible
   STATUS      current
   DESCRIPTION
       " port, range : 1 - port number. "
   ::= { lcsPoePowerDelayEntry 1 }

lcsPoePowerDelayMode OBJECT-TYPE
   SYNTAX      Integer32(0|1)
   MAX-ACCESS  read-write
   STATUS      current
   DESCRIPTION
       "Turn on / off the power delay function,
        0: disable,
        1: enable,
        default: disable. "
   ::= { lcsPoePowerDelayEntry 2 }

lcsPoePowerDelayTime OBJECT-TYPE
   SYNTAX      Integer32(0..300)
   MAX-ACCESS  read-write
   STATUS      current
   DESCRIPTION
       "set Delay Time,
        default: 0,
        range: 0-300 sec. "
   ::= { lcsPoePowerDelayEntry 3 }

lcsPoeAutoCheck                                                 OBJECT IDENTIFIER ::= { lcsPoe 3 }

lcsPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { lcsPoeAutoCheck 1 }

lcsPoeAutoCheckTable OBJECT-TYPE
   SYNTAX      SEQUENCE OF LCSPoeAutoCheckEntry
   MAX-ACCESS  not-accessible
   STATUS      current
   DESCRIPTION
       " Configure PoE Auto check mode. "
   ::= { lcsPoeAutoCheck 2 }

lcsPoeAutoCheckEntry OBJECT-TYPE
   SYNTAX      LCSPoeAutoCheckEntry
   MAX-ACCESS  not-accessible
   STATUS      current
   DESCRIPTION
       " "
   INDEX    { lcsPoeAutoCheckPort  }
   ::= { lcsPoeAutoCheckTable 1 }

LCSPoeAutoCheckEntry ::= SEQUENCE {
   lcsPoeAutoCheckPort           Integer32,
   lcsPoeAutoCheckPingIPAddress  DisplayString,
   lcsPoeAutoCheckStartupTime    Integer32,
   lcsPoeAutoCheckIntervalTime   Integer32,
   lcsPoeAutoCheckRetryTime      Integer32,
   lcsPoeAutoCheckFailureLog     DisplayString,
   lcsPoeAutoCheckFailureAction  INTEGER,
   lcsPoeAutoCheckRebootTime     Integer32,
   lcsPoeAutoCheckMaxRebootTimes Integer32
}

lcsPoeAutoCheckPort OBJECT-TYPE
   SYNTAX      Integer32(1..4094)
   MAX-ACCESS  not-accessible
   STATUS      current
   DESCRIPTION
       " port, range : 1 - port number. "
   ::= { lcsPoeAutoCheckEntry 1 }

lcsPoeAutoCheckPingIPAddress OBJECT-TYPE
   SYNTAX      DisplayString
   MAX-ACCESS  read-write
   STATUS      current
   DESCRIPTION
       "IP Address the system should ping.
        default: 0.0.0.0 . "
   ::= { lcsPoeAutoCheckEntry 2 }

lcsPoeAutoCheckStartupTime OBJECT-TYPE
   SYNTAX      Integer32(30..600)
   MAX-ACCESS  read-write
   STATUS      current
   DESCRIPTION
       "When PD has been start up, the Switch will wait Start up time to do PoE Auto Checking. default: 60, range: 30-600 sec. "
   ::= { lcsPoeAutoCheckEntry 3 }

lcsPoeAutoCheckIntervalTime OBJECT-TYPE
   SYNTAX      Integer32(10..120)
   MAX-ACCESS  read-write
   STATUS      current
   DESCRIPTION
       "Device will send checking message to PD each interval time.
        default: 30,
        range: 10-120 sec.  "
   ::= { lcsPoeAutoCheckEntry 4 }

lcsPoeAutoCheckRetryTime OBJECT-TYPE
   SYNTAX      Integer32(1..5)
   MAX-ACCESS  read-write
   STATUS      current
   DESCRIPTION
       "It will retry to send detection again.
        default: 3,
        range: 1-5.  "
   ::= { lcsPoeAutoCheckEntry 5 }

lcsPoeAutoCheckFailureLog OBJECT-TYPE
   SYNTAX      DisplayString
   MAX-ACCESS  read-only
   STATUS      current
   DESCRIPTION
       "Failure loggings counter. "
   ::= { lcsPoeAutoCheckEntry 6 }

lcsPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { lcsPoeAutoCheckEntry 7 }

lcsPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { lcsPoeAutoCheckEntry 8 }

lcsPoeAutoCheckMaxRebootTimes OBJECT-TYPE
   SYNTAX      Integer32(0..10)
   MAX-ACCESS  read-write
   STATUS      current
   DESCRIPTION
        "When Failure Action is Reboot Remote PD, it limits times of Reboot.
         default: 3,
         range: 0-10. 0 means without reboot limits."
   ::= { lcsPoeAutoCheckEntry 10 }

lcsPoeScheduling                                                 OBJECT IDENTIFIER ::= { lcsPoe 4 }

lcsPoeSchedulingProfileNumber OBJECT-TYPE
   SYNTAX      Integer32
   MAX-ACCESS  read-write
   STATUS      current
   DESCRIPTION
       "Specify the PoE Profile Number that want to configure. Range:1-16"
   ::= { lcsPoeScheduling 1 }

lcsPoeSchedulingPorofileName OBJECT-TYPE
   SYNTAX      DisplayString
   MAX-ACCESS  read-write
   STATUS      current
   DESCRIPTION
       "Profile Name. Maximum length:32."
   ::= { lcsPoeScheduling 2 }

lcsPoeSchedulingTimeTable OBJECT-TYPE
   SYNTAX      SEQUENCE OF LCSPoeSchedulingTimeEntry
   MAX-ACCESS  not-accessible
   STATUS      current
   DESCRIPTION
       " Show Poe Scheduling Time Config. "
   ::= { lcsPoeScheduling 3 }

lcsPoeSchedulingTimeEntry OBJECT-TYPE
   SYNTAX      LCSPoeSchedulingTimeEntry
   MAX-ACCESS  not-accessible
   STATUS      current
   DESCRIPTION
       " "
   INDEX    { lcsPoeSchedulingTimeWeekIndex  }
   ::= { lcsPoeSchedulingTimeTable 1 }

LCSPoeSchedulingTimeEntry ::= SEQUENCE {
   lcsPoeSchedulingTimeWeekIndex        Integer32,
   lcsPoeSchedulingTimeStartTimeHourMinute  DisplayString,
   lcsPoeSchedulingTimeEndTimeHourMinute    DisplayString
}

lcsPoeSchedulingTimeWeekIndex OBJECT-TYPE
   SYNTAX      Integer32 (1..7)
   MAX-ACCESS  not-accessible
   STATUS      current
   DESCRIPTION
       "Week Index. 
       1: Mon, 2:Tue, 3: Wed, 4: Thu, 5: Fri, 6: Sat, 7: Sun"
   ::= { lcsPoeSchedulingTimeEntry 1 }

lcsPoeSchedulingTimeStartTimeHourMinute OBJECT-TYPE
   SYNTAX      DisplayString
   MAX-ACCESS  read-write
   STATUS      current
   DESCRIPTION
       "PoE Scheduling Start Time. Format: HH:MM. Hour Range: 0-23. Minute Range:0,5,10,...,55."
   ::= { lcsPoeSchedulingTimeEntry 2 }

lcsPoeSchedulingTimeEndTimeHourMinute OBJECT-TYPE
   SYNTAX      DisplayString
   MAX-ACCESS  read-write
   STATUS      current
   DESCRIPTION
       "PoE Scheduling End Time. Format: HH:MM. Hour Range: 0-23. Minute Range:0,5,10,...,55."
   ::= { lcsPoeSchedulingTimeEntry 3 }

lcsPoeConfiguration                                                 OBJECT IDENTIFIER ::= { lcsPoe 5 }

lcsPoeConfigurationPowerManagementMode OBJECT-TYPE
   SYNTAX      Integer32(0..5)
   MAX-ACCESS  read-write
   STATUS      current
   DESCRIPTION
       "The power management mode for PoE port.
        0: CLASS_RESERVED,
        1: CLASS_CONSUMP,
        2: ALLOCATED_RESERVED,
        3: ALLOCATED_CONSUMP,
        4: LLDPMED_RESERVED,
        5: LLDPMED_CONSUMP,
        default: CLASS_RESERVED. "
   ::= { lcsPoeConfiguration 1 }

lcsPoeConfigurationLegacyPDDetection OBJECT-TYPE
   SYNTAX      Integer32(0..1)
   MAX-ACCESS  read-write
   STATUS      current
   DESCRIPTION
       "The capacitor detection mode.
        0: Disable
        1: Enable
       "
   ::= { lcsPoeConfiguration 2 }

lcsPoeConfigurationTable OBJECT-TYPE
   SYNTAX      SEQUENCE OF LCSPoeConfigurationEntry
   MAX-ACCESS  not-accessible
   STATUS      current
   DESCRIPTION
       " Configure PoE Configuration mode. "
   ::= { lcsPoeConfiguration 4 }

lcsPoeConfigurationEntry OBJECT-TYPE
   SYNTAX      LCSPoeConfigurationEntry
   MAX-ACCESS  not-accessible
   STATUS      current
   DESCRIPTION
       " "
   INDEX    { lcsPoeConfigurationSwitch  }
   ::= { lcsPoeConfigurationTable 1 }

LCSPoeConfigurationEntry ::= SEQUENCE {
   lcsPoeConfigurationSwitch                       Integer32,
   lcsPoeConfigurationPoEFirmwareVersion        DisplayString,
   lcsPoeConfigurationPrimaryPowerSupply        Integer32
}

lcsPoeConfigurationSwitch OBJECT-TYPE
   SYNTAX      Integer32 (1..16)
   MAX-ACCESS  not-accessible
   STATUS      current
   DESCRIPTION
       " switch index, range : 1 - 16. "
   ::= { lcsPoeConfigurationEntry 1 }

lcsPoeConfigurationPoEFirmwareVersion OBJECT-TYPE
   SYNTAX      DisplayString
   MAX-ACCESS  read-only
   STATUS      current
   DESCRIPTION
       "PoE Firmware Version."
   ::= { lcsPoeConfigurationEntry 2 }
   
lcsPoeConfigurationPrimaryPowerSupply  OBJECT-TYPE
   SYNTAX      Integer32(0..2000)
   MAX-ACCESS  read-only
   STATUS      current
   DESCRIPTION
       "It must be defined what amount of power the primary and backup power sources
        can deliver. "
   ::= { lcsPoeConfigurationEntry 3 }

lcsPoeConfigurationPortTable OBJECT-TYPE
   SYNTAX      SEQUENCE OF LCSPoeConfigurationPortEntry
   MAX-ACCESS  not-accessible
   STATUS      current
   DESCRIPTION
       " Configure PoE Port Configuration mode. "
   ::= { lcsPoeConfiguration 5 }

lcsPoeConfigurationPortEntry OBJECT-TYPE
   SYNTAX      LCSPoeConfigurationPortEntry
   MAX-ACCESS  not-accessible
   STATUS      current
   DESCRIPTION
       " "
   INDEX    { lcsPoeConfigurationPort  }
   ::= { lcsPoeConfigurationPortTable 1 }

LCSPoeConfigurationPortEntry ::= SEQUENCE {
   lcsPoeConfigurationPort         Integer32,
   lcsPoeConfigurationPortPoEMode       INTEGER,
   lcsPoeConfigurationPortPriority      INTEGER,
   lcsPoeConfigurationPortMaximumPower  DisplayString,
   lcsPoeConfigurationPortDetection     Integer32,
-- lcsPoeConfigurationPortPoEScheduleByProfileID     Integer32,
   lcsPoeConfigurationPortPoEScheduleByProfileName   DisplayString,
   lcsPoeConfigurationPortDelayMode     Integer32,
   lcsPoeConfigurationPortDelayTime     Integer32
}

lcsPoeConfigurationPort OBJECT-TYPE
   SYNTAX      Integer32 (1..4094)
   MAX-ACCESS  not-accessible
   STATUS      current
   DESCRIPTION
       " port, range : 1 - port number. "
   ::= { lcsPoeConfigurationPortEntry 1 }

  lcsPoeConfigurationPortPoEMode OBJECT-TYPE
    SYNTAX      INTEGER { disable(0), poe(1), 4pair60W(2), 4pair90W(3), 8023bt(4) }
    MAX-ACCESS  read-write
    STATUS      current
    DESCRIPTION
        "The PoE Mode represents the PoE operating mode for the port.
          0: Disable,
          1: Enable,
          2: 4-Pair 60W,
          3: 4-Pair 90W,
          4: 802.3bt,
          default: Enable. "
    ::= { lcsPoeConfigurationPortEntry 2 }

lcsPoeConfigurationPortPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { lcsPoeConfigurationPortEntry 3 }

lcsPoeConfigurationPortMaximumPower OBJECT-TYPE
   SYNTAX      DisplayString
   MAX-ACCESS  read-write
   STATUS      current
   DESCRIPTION
       "The Maximum Power value contains a numerical value that indicates the maximum
        power in watts that can be delivered to a remote device.
        max: 30[W]. "
   ::= { lcsPoeConfigurationPortEntry 4 }

lcsPoeConfigurationPortDetection OBJECT-TYPE
   SYNTAX      Integer32(1..5)
   MAX-ACCESS  read-write
   STATUS      current
   DESCRIPTION
       "The Detection represents the PoE capacitor detection for the port.
          -1:Not support.
       1:Legacy : Legacy capacitive detection only.
       2:4-point : IEEE 802.3af 4-point detection only.
       3:4-point-legacy : IEEE 802.3af 4-point detection followed by Legacy detection.
       4:2-point : IEEE 802.3af 2-point detection only.
       5:2-point-legacy : IEEE 802.3af 2-point detection followed by Legacy detection.
       "
   ::= { lcsPoeConfigurationPortEntry 5 }

-- lcsPoeConfigurationPortPoEScheduleByProfileID OBJECT-TYPE
--   SYNTAX      Integer32(0..16)
--   MAX-ACCESS  read-write
--   STATUS      current
--   DESCRIPTION
--       "Specify a valid PoE schedule profile by profile id. 0:disable,1-16:1-16 profile."
--   ::= { lcsPoeConfigurationPortEntry 6 }
   
lcsPoeConfigurationPortPoEScheduleByProfileName OBJECT-TYPE
   SYNTAX      DisplayString
   MAX-ACCESS  read-write
   STATUS      current
   DESCRIPTION
       "Specify a valid PoE schedule profile by profile name. disabled: disable profile schedule."
   ::= { lcsPoeConfigurationPortEntry 7 }   
   
lcsPoeConfigurationPortDelayMode OBJECT-TYPE
   SYNTAX      Integer32(0..1)
   MAX-ACCESS  read-write
   STATUS      current
   DESCRIPTION
       "Turn on off the power delay function. 
       0: Disable
        1: Enable"
   ::= { lcsPoeConfigurationPortEntry 8 }
   
lcsPoeConfigurationPortDelayTime OBJECT-TYPE
   SYNTAX      Integer32(0..300)
   MAX-ACCESS  read-write
   STATUS      current
   DESCRIPTION
       "When rebooting, the PoE port will start to provide power to the PD when it out of delay time.
       Range:0-300"
   ::= { lcsPoeConfigurationPortEntry 9 }
   
lcsPoeChipsetRebootSchedule OBJECT IDENTIFIER ::= { lcsPoe 6 }  

lcsPoeChipsetRebootMode OBJECT-TYPE
   SYNTAX      Integer32
   MAX-ACCESS  read-write
   STATUS      current
   DESCRIPTION
       "PoE Chipset Reboot Mode
        0:disable
        1:enable"
   ::= { lcsPoeChipsetRebootSchedule 1 }

lcsPoeChipsetRebootTimeTable OBJECT-TYPE
   SYNTAX      SEQUENCE OF LCSPoeChipsetRebootTimeEntry
   MAX-ACCESS  not-accessible
   STATUS      current
   DESCRIPTION
       " Configure PoE Chipset Reboot Time."
   ::= { lcsPoeChipsetRebootSchedule 2 }

lcsPoeChipsetRebootTimeEntry OBJECT-TYPE
   SYNTAX      LCSPoeChipsetRebootTimeEntry
   MAX-ACCESS  not-accessible
   STATUS      current
   DESCRIPTION
       " "
   INDEX    { lcsPoeChipsetRebootWeekIndex  }
   ::= { lcsPoeChipsetRebootTimeTable 1 }

LCSPoeChipsetRebootTimeEntry ::= SEQUENCE {
   lcsPoeChipsetRebootWeekIndex        Integer32,
   lcsPoeChipsetRebootTimeHour           Integer32,
   lcsPoeChipsetRebootTimeMinute         Integer32
}

lcsPoeChipsetRebootWeekIndex OBJECT-TYPE
   SYNTAX      Integer32 (1..7)
   MAX-ACCESS  not-accessible
   STATUS      current
   DESCRIPTION
       "PoE chipset reboot week index.
       1: Mon, 2:Tue, 3: Wed, 4: Thu, 5: Fri, 6: Sat, 7: Sun"
   ::= { lcsPoeChipsetRebootTimeEntry 1 }

lcsPoeChipsetRebootTimeHour OBJECT-TYPE
   SYNTAX      Integer32 (-1..23)
   MAX-ACCESS  read-write
   STATUS      current
   DESCRIPTION
       "PoE Chipset Reboot Time (Hour). Range: 0-23. 
       -1:disable"
   ::= { lcsPoeChipsetRebootTimeEntry 2 }

lcsPoeChipsetRebootTimeMinute OBJECT-TYPE
   SYNTAX      Integer32 (-1..55)
   MAX-ACCESS  read-write
   STATUS      current
   DESCRIPTION
       "PoE Chipset Reboot Time (Minute). Range:0,5,10,...,55. 
       -1:disable"
   ::= { lcsPoeChipsetRebootTimeEntry 3 }
   
-- =======================================================================================================================
-- RowStatus Info:  createAndWait, notReady, notInService not supported.
-- =======================================================================================================================
-- Textual Conventions for the lcs AAA Mib
-- =======================================================================================================================
--
lcsAAAMIB                   OBJECT IDENTIFIER  ::= { lcsConfiguration 15 }
    lcsAAA                  OBJECT IDENTIFIER  ::= { lcsAAAMIB 1 }
    lcsRADIUS               OBJECT IDENTIFIER  ::= { lcsAAA 1 }
    lcsRADIUSGlobalConfig   OBJECT IDENTIFIER  ::= { lcsRADIUS 1 }

    lcsTACACS               OBJECT IDENTIFIER  ::= { lcsAAA 2 }

--
-- =======================================================================================================================
-- Start lcsRADIUS group
-- =======================================================================================================================
--lcsRADIUSGlobalConfig

    lcsRADIUSGlobalConfigTimeout OBJECT-TYPE
               SYNTAX      Integer32(1..1000)
               MAX-ACCESS  read-write
               STATUS      current
               DESCRIPTION
                   "Timeout is the number of seconds, to wait for a reply
                    from a RADIUS server before retransmitting the request.
                    range: 1-1000."
               ::= {     lcsRADIUSGlobalConfig 1 }

    lcsRADIUSGlobalConfigRetransmit OBJECT-TYPE
               SYNTAX      Integer32(1..1000)
               MAX-ACCESS  read-write
               STATUS      current
               DESCRIPTION
                   "Retransmit is the number of times,a RADIUS request is
                    retransmitted to a server that is not responding.If the
                    server has not responded after the last retransmit it is
                    considered to be dead.
                    range: 1-1000."
               ::= {     lcsRADIUSGlobalConfig 2 }

    lcsRADIUSGlobalConfigDeadtime OBJECT-TYPE
               SYNTAX      Integer32(0..1440)
               MAX-ACCESS  read-write
               STATUS      current
               DESCRIPTION
                   "This will stop the switch from continually trying to
                    contact a server that it has already determined as dead.
                    range: 0-1440."
               ::= {     lcsRADIUSGlobalConfig 3 }

    lcsRADIUSGlobalConfigKey OBJECT-TYPE
               SYNTAX      DisplayString
               MAX-ACCESS  read-write
               STATUS      current
               DESCRIPTION
                   "The secret key shared between the RADIUS server and
                    the switch.
                    On set sets the plain value as secret key, on get
                    only returns an encrypted value."
               ::= {     lcsRADIUSGlobalConfig 4 }

    lcsRADIUSGlobalConfigKeyHashed OBJECT-TYPE
               SYNTAX      DisplayString
               MAX-ACCESS  read-write
               STATUS      current
               DESCRIPTION
                   "The secret key shared between the RADIUS server and
                    the switch.
                    On set sets the value as encrypted secret key, on get
                    returns the encrypted value."
               ::= {     lcsRADIUSGlobalConfig 50 }

    lcsRADIUSGlobalConfigKeyWrite OBJECT-TYPE
               SYNTAX      DisplayString
               MAX-ACCESS  read-write
               STATUS      current
               DESCRIPTION
                   "The secret key shared between the RADIUS server and
                    the switch.
                    On set sets the value as secret key, on get
                    always returns empty string."
               ::= {     lcsRADIUSGlobalConfig 51 }

    lcsRADIUSGlobalConfigNASIPv4 OBJECT-TYPE
               SYNTAX      IpAddress
               MAX-ACCESS  read-write
               STATUS      current
               DESCRIPTION
                   "The IPv4 address to be used as attribute 4 in RADIUS
                    Access-Request packets.
                    Setting 0.0.0.0 will disable this attribute."
               ::= {     lcsRADIUSGlobalConfig 5 }

    lcsRADIUSGlobalConfigNASIPv6 OBJECT-TYPE
               SYNTAX      DisplayString
               MAX-ACCESS  read-write
               STATUS      current
               DESCRIPTION
                   "The IPv6 address to be used as attribute 95 in RADIUS
                    Access-Request packets.
                    Leaving it blank will disable this attribute."
               ::= {     lcsRADIUSGlobalConfig 6 }

    lcsRADIUSGlobalConfigNASIdentifier OBJECT-TYPE
               SYNTAX      DisplayString
               MAX-ACCESS  read-write
               STATUS      current
               DESCRIPTION
                   "The identifier to be used as attribute 32 in RADIUS
                    Access-Request packets.
                    Leaving it blank will disable this attribute."
               ::= {     lcsRADIUSGlobalConfig 7 }

--RADIUSMacformatTable

    lcsRADIUSMacformatTable OBJECT-TYPE
               SYNTAX      SEQUENCE OF LCSRADIUSMacformatEntry
               MAX-ACCESS  not-accessible
               STATUS      current
               DESCRIPTION
                   "The RADIUS / NAS Mac Format Configuration Table."
               ::= {     lcsRADIUSGlobalConfig 100 }

    lcsRADIUSMacformatEntry OBJECT-TYPE
               SYNTAX      LCSRADIUSMacformatEntry
               MAX-ACCESS  not-accessible
               STATUS      current
               DESCRIPTION
                   "The RADIUS / NAS Mac Format Configuration Entry."
               INDEX       { lcsRADIUSMacformatIndex }
               ::= {     lcsRADIUSMacformatTable 1 }

    LCSRADIUSMacformatEntry ::= SEQUENCE {
                 lcsRADIUSMacformatIndex        INTEGER,
                 lcsRADIUSMacformatGroupsize    INTEGER,
                 lcsRADIUSMacformatSeparator    INTEGER,
                 lcsRADIUSMacformatCase         INTEGER
                 }

    lcsRADIUSMacformatIndex OBJECT-TYPE
               SYNTAX      INTEGER { called-station(1), calling-station(2), macbased-identity(3) }
               MAX-ACCESS  not-accessible
               STATUS      current
               DESCRIPTION
                   "The Mac Format index.
                    1: Mac Format for the Called-Station Attribute
                    2: Mac Format for the Calling-Station Attribute
                    3: Mac Format for the Identity for Mac-Based Auth"
               ::= {     lcsRADIUSMacformatEntry 1 }

    lcsRADIUSMacformatGroupsize OBJECT-TYPE
               SYNTAX      INTEGER(1|2|4|12)
               MAX-ACCESS  read-write
               STATUS      current
               DESCRIPTION
                   "The Groupsize in which the Mac Address will be formatted.
                    1: x-x-x-x-x-x-x-x-x-x-x-x
                    2: xx-xx-xx-xx-xx-xx
                    4: xxxx-xxxx-xxxx
                    12: xxxxxxxxxxxx"
               ::= {     lcsRADIUSMacformatEntry 2 }

    lcsRADIUSMacformatSeparator OBJECT-TYPE
               SYNTAX      INTEGER { hypen(0), colon(1), dot(2) }
               MAX-ACCESS  read-write
               STATUS      current
               DESCRIPTION
                   "The Separator to use for separating the character groups.
                    0: Hypen (-)
                    1: Colon (:)
                    2: Dot (.)"
               ::= {     lcsRADIUSMacformatEntry 3 }

    lcsRADIUSMacformatCase OBJECT-TYPE
               SYNTAX      INTEGER { lowercase(0), uppercase(1) }
               MAX-ACCESS  read-write
               STATUS      current
               DESCRIPTION
                   "Whether to format the hex characters lowercase or uppercase.
                    0: Lowercase
                    1: Uppercase"
               ::= {     lcsRADIUSMacformatEntry 4 }

--lcsRADIUSServerConfigTable

    lcsRADIUSServerConfigTable OBJECT-TYPE
               SYNTAX      SEQUENCE OF     LCSRADIUSServerConfigEntry
               MAX-ACCESS  not-accessible
               STATUS      current
               DESCRIPTION
                   "The RADIUS Server Configuration Table."
               ::= {     lcsRADIUS 2 }

    lcsRADIUSServerConfigEntry OBJECT-TYPE
               SYNTAX          LCSRADIUSServerConfigEntry
               MAX-ACCESS  not-accessible
               STATUS      current
               DESCRIPTION
                   "The RADIUS Server Configuration Entry."
               INDEX    {    lcsRADIUSServerConfServerNo  }
               ::= {     lcsRADIUSServerConfigTable 1 }

    LCSRADIUSServerConfigEntry             ::= SEQUENCE {
                 lcsRADIUSServerConfServerNo      Integer32,
                 lcsRADIUSServerConfHostname      DisplayString,
                 lcsRADIUSServerConfAuthPort      Integer32,
                 lcsRADIUSServerConfAcctPort      Integer32,
                 lcsRADIUSServerConfTimeout       Integer32,
                 lcsRADIUSServerConfRetransmit    Integer32,
                 lcsRADIUSServerConfKey           DisplayString,
                 lcsRADIUSServerConfRowStatus     RowStatus
                 }

    lcsRADIUSServerConfServerNo OBJECT-TYPE
               SYNTAX      Integer32(1..5)
               MAX-ACCESS  not-accessible
               STATUS      current
               DESCRIPTION
                   "The RADIUS server number.
                    max: 5."
               ::= {     lcsRADIUSServerConfigEntry 1 }

    lcsRADIUSServerConfHostname OBJECT-TYPE
               SYNTAX      DisplayString
               MAX-ACCESS  read-create
               STATUS      current
               DESCRIPTION
                   "The IP address or hostname of the RADIUS server. "
               ::= {     lcsRADIUSServerConfigEntry 2 }

    lcsRADIUSServerConfAuthPort OBJECT-TYPE
               SYNTAX      Integer32(0..65535)
               MAX-ACCESS  read-create
               STATUS      current
               DESCRIPTION
                   "The UDP port to use on the RADIUS server for
                    authentication.
                    range: 0-65535. "
               ::= {     lcsRADIUSServerConfigEntry 3 }

    lcsRADIUSServerConfAcctPort OBJECT-TYPE
               SYNTAX      Integer32(0..65535)
               MAX-ACCESS  read-create
               STATUS      current
               DESCRIPTION
                   "The UDP port to use on the RADIUS server for accounting.
                    range: 0-65535. "
               ::= {     lcsRADIUSServerConfigEntry 4 }

    lcsRADIUSServerConfTimeout OBJECT-TYPE
               SYNTAX      Integer32(0..1000)
               MAX-ACCESS  read-create
               STATUS      current
               DESCRIPTION
                   "This optional setting overrides the global timeout value.
                    Setting to 0 will use the global timeout value.
                    range: 1-1000. "
               ::= {     lcsRADIUSServerConfigEntry 5 }

    lcsRADIUSServerConfRetransmit OBJECT-TYPE
               SYNTAX      Integer32(0..1000)
               MAX-ACCESS  read-create
               STATUS      current
               DESCRIPTION
                   "This optional setting overrides the global retransmit value.
                    Setting to 0 will use the global retransmit value.
                    range: 1-1000. "
               ::= {     lcsRADIUSServerConfigEntry 6 }

    lcsRADIUSServerConfKey OBJECT-TYPE
               SYNTAX      DisplayString
               MAX-ACCESS  read-create
               STATUS      current
               DESCRIPTION
                   "This optional setting overrides the global key. Leaving
                    it blank will use the global key.
                    On set sets the plain value as secret key, on get
                    only returns an encrypted value."
               ::= {     lcsRADIUSServerConfigEntry 7 }

    lcsRADIUSServerConfKeyHashed OBJECT-TYPE
               SYNTAX      DisplayString
               MAX-ACCESS  read-create
               STATUS      current
               DESCRIPTION
                   "This optional setting overrides the global key. Leaving
                    it blank will use the global key.
                    On set sets the value as encrypted secret key, on get
                    returns the encrypted value."
               ::= {     lcsRADIUSServerConfigEntry 50 }

    lcsRADIUSServerConfKeyWrite OBJECT-TYPE
               SYNTAX      DisplayString
               MAX-ACCESS  read-create
               STATUS      current
               DESCRIPTION
                   "This optional setting overrides the global key. Leaving
                    it blank will use the global key.
                    On set sets the value as secret key, on get
                    always returns empty string."
               ::= {     lcsRADIUSServerConfigEntry 51 }

    lcsRADIUSServerConfRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     lcsRADIUSServerConfigEntry 8 }

--lcsRADIUSDetailTable

    lcsRADIUSDetailTable OBJECT-TYPE
               SYNTAX      SEQUENCE OF     LCSRADIUSDetailEntry
               MAX-ACCESS  not-accessible
               STATUS      current
               DESCRIPTION
                   "The RADIUS Detail Table."
               ::= {     lcsRADIUS 3 }

    lcsRADIUSDetailEntry OBJECT-TYPE
               SYNTAX          LCSRADIUSDetailEntry
               MAX-ACCESS  not-accessible
               STATUS      current
               DESCRIPTION
                   "The RADIUS Detail Entry."
               INDEX    {    lcsRADIUSServerConfServerNo  }
               ::= {     lcsRADIUSDetailTable 1 }

    LCSRADIUSDetailEntry             ::= SEQUENCE {
                 lcsRADIUSAuthIPAddress               DisplayString,
                 lcsRADIUSAuthStatus                  DisplayString,
                 lcsRADIUSAuthRoundTripTime           Integer32,
                 lcsRADIUSAuthRxAccessAccept          Counter32,
                 lcsRADIUSAuthRxAccessReject          Counter32,
                 lcsRADIUSAuthRxAccessChallenge       Counter32,
                 lcsRADIUSAuthRxAccessResponse        Counter32,
                 lcsRADIUSAuthRxBadAuth               Counter32,
                 lcsRADIUSAuthRxUnknownType           Counter32,
                 lcsRADIUSAuthRxPacketsDropped        Counter32,
                 lcsRADIUSAuthTxAccessRequest         Counter32,
                 lcsRADIUSAuthTxAccessRetransmission  Counter32,
                 lcsRADIUSAuthTxPendingRequest        Counter32,
                 lcsRADIUSAuthTxTimeout               Counter32,
                 lcsRADIUSAccountIPAddress            IpAddress,
                 lcsRADIUSAccountStatus               DisplayString,
                 lcsRADIUSAccountRoundTripTime        Integer32,
                 lcsRADIUSAccountRxResponses          Counter32,
                 lcsRADIUSAccountRxMalformedResponse  Counter32,
                 lcsRADIUSAccountRxBadAuth            Counter32,
                 lcsRADIUSAccountRxUnknownType        Counter32,
                 lcsRADIUSAccountRxPacketsDrop        Counter32,
                 lcsRADIUSAccountTxRequest            Counter32,
                 lcsRADIUSAccountTxRetransmission     Counter32,
                 lcsRADIUSAccountTxPendingRequest     Counter32,
                 lcsRADIUSAccountTxTimeout            Counter32,
                 lcsRADIUSDetailClearCmd              ActivateCmd
                 }

    lcsRADIUSAuthIPAddress OBJECT-TYPE
               SYNTAX      DisplayString
               MAX-ACCESS  read-only
               STATUS      current
               DESCRIPTION
                   "IP address and UDP port for the authentication
                    server in question."
               ::= {     lcsRADIUSDetailEntry 2 }

    lcsRADIUSAuthStatus OBJECT-TYPE
               SYNTAX      DisplayString
               MAX-ACCESS  read-only
               STATUS      current
               DESCRIPTION
                   "Shows the state of the server."
               ::= {     lcsRADIUSDetailEntry 3 }

    lcsRADIUSAuthRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     lcsRADIUSDetailEntry 4 }

    lcsRADIUSAuthRxAccessAccept OBJECT-TYPE
               SYNTAX      Counter32
               MAX-ACCESS  read-only
               STATUS      current
               DESCRIPTION
                   "The number of RADIUS Access-Accept packets
                   (valid or invalid) received from the server."
               ::= {     lcsRADIUSDetailEntry 5 }

    lcsRADIUSAuthRxAccessReject OBJECT-TYPE
               SYNTAX      Counter32
               MAX-ACCESS  read-only
               STATUS      current
               DESCRIPTION
                   "The number of RADIUS Access-Reject packets
                    (valid or invalid) received from the server."
               ::= {     lcsRADIUSDetailEntry 6 }

    lcsRADIUSAuthRxAccessChallenge OBJECT-TYPE
               SYNTAX      Counter32
               MAX-ACCESS  read-only
               STATUS      current
               DESCRIPTION
                   "The number of RADIUS Access-Challenge packets
                    (valid or invalid) received from the server."
               ::= {     lcsRADIUSDetailEntry 7 }

    lcsRADIUSAuthRxAccessResponse OBJECT-TYPE
               SYNTAX      Counter32
               MAX-ACCESS  read-only
               STATUS      current
               DESCRIPTION
                   "The number of malformed RADIUS Access-Response
                    packets received from the server."
               ::= {     lcsRADIUSDetailEntry 8 }

    lcsRADIUSAuthRxBadAuth OBJECT-TYPE
               SYNTAX      Counter32
               MAX-ACCESS  read-only
               STATUS      current
               DESCRIPTION
                   "The number of RADIUS Access-Response packets containing
                    invalid authenticators or Message Authenticator
                    attributes received from the server."
               ::= {     lcsRADIUSDetailEntry 9 }

    lcsRADIUSAuthRxUnknownType OBJECT-TYPE
               SYNTAX      Counter32
               MAX-ACCESS  read-only
               STATUS      current
               DESCRIPTION
                   "The number of RADIUS packets that were received with
                    unknown types from the server on the authentication
                    port and dropped."
               ::= {     lcsRADIUSDetailEntry 10 }

    lcsRADIUSAuthRxPacketsDropped OBJECT-TYPE
               SYNTAX      Counter32
               MAX-ACCESS  read-only
               STATUS      current
               DESCRIPTION
                   "The number of RADIUS packets that were received from
                    the server on the authentication port and dropped for
                    some other reason."
               ::= {     lcsRADIUSDetailEntry 11 }

    lcsRADIUSAuthTxAccessRequest OBJECT-TYPE
               SYNTAX      Counter32
               MAX-ACCESS  read-only
               STATUS      current
               DESCRIPTION
                   "The number of RADIUS Access-Request packets sent to
                    the server. This does not include retransmissions."
               ::= {     lcsRADIUSDetailEntry 12 }

    lcsRADIUSAuthTxAccessRetransmission OBJECT-TYPE
               SYNTAX      Counter32
               MAX-ACCESS  read-only
               STATUS      current
               DESCRIPTION
                   "The number of RADIUS Access-Request packets
                    retransmitted to the RADIUS authentication server."
               ::= {     lcsRADIUSDetailEntry 13 }

    lcsRADIUSAuthTxPendingRequest OBJECT-TYPE
               SYNTAX      Counter32
               MAX-ACCESS  read-only
               STATUS      current
               DESCRIPTION
                   "The number of RADIUS Access-Request packets destined
                    for the server that have not yet timed out or received
                    a response. "
               ::= {     lcsRADIUSDetailEntry 14 }

    lcsRADIUSAuthTxTimeout OBJECT-TYPE
               SYNTAX      Counter32
               MAX-ACCESS  read-only
               STATUS      current
               DESCRIPTION
                   "The number of authentication timeouts to the server.
                    After a timeout, the client may retry to the same server,
                    send to a different server, or give up."
               ::= {     lcsRADIUSDetailEntry 15 }

    lcsRADIUSAccountIPAddress OBJECT-TYPE
               SYNTAX      IpAddress
               MAX-ACCESS  read-only
               STATUS      current
               DESCRIPTION
                   "IP address and UDP port for the authentication server
                    in question."
               ::= {     lcsRADIUSDetailEntry 16 }

    lcsRADIUSAccountStatus OBJECT-TYPE
               SYNTAX      DisplayString
               MAX-ACCESS  read-only
               STATUS      current
               DESCRIPTION
                   "Shows the state of the server. "
               ::= {     lcsRADIUSDetailEntry 17 }

    lcsRADIUSAccountRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     lcsRADIUSDetailEntry 18 }

    lcsRADIUSAccountRxResponses OBJECT-TYPE
               SYNTAX      Counter32
               MAX-ACCESS  read-only
               STATUS      current
               DESCRIPTION
                   "The number of RADIUS packets (valid or invalid)
                    received from the server."
               ::= {     lcsRADIUSDetailEntry 19 }

    lcsRADIUSAccountRxMalformedResponse OBJECT-TYPE
               SYNTAX      Counter32
               MAX-ACCESS  read-only
               STATUS      current
               DESCRIPTION
                   "The number of malformed RADIUS packets received from
                    the server. "
               ::= {     lcsRADIUSDetailEntry 20 }

    lcsRADIUSAccountRxBadAuth OBJECT-TYPE
               SYNTAX      Counter32
               MAX-ACCESS  read-only
               STATUS      current
               DESCRIPTION
                   "The number of RADIUS packets containing invalid
                    authenticators received from the server."
               ::= {     lcsRADIUSDetailEntry 21 }

    lcsRADIUSAccountRxUnknownType OBJECT-TYPE
               SYNTAX      Counter32
               MAX-ACCESS  read-only
               STATUS      current
               DESCRIPTION
                   "The number of RADIUS packets of unknown types that were
                    received from the server on the accounting port. "
               ::= {     lcsRADIUSDetailEntry 22 }

    lcsRADIUSAccountRxPacketsDrop OBJECT-TYPE
               SYNTAX      Counter32
               MAX-ACCESS  read-only
               STATUS      current
               DESCRIPTION
                   "The number of RADIUS packets that were received from
                    the server on the accounting port and dropped for some
                    other reason."
               ::= {     lcsRADIUSDetailEntry 23 }

    lcsRADIUSAccountTxRequest OBJECT-TYPE
               SYNTAX      Counter32
               MAX-ACCESS  read-only
               STATUS      current
               DESCRIPTION
                   "The number of RADIUS packets sent to the server.
                    This does not include retransmissions."
               ::= {     lcsRADIUSDetailEntry 24 }

    lcsRADIUSAccountTxRetransmission OBJECT-TYPE
               SYNTAX      Counter32
               MAX-ACCESS  read-only
               STATUS      current
               DESCRIPTION
                   "The number of RADIUS packets retransmitted to the RADIUS
                    accounting server."
               ::= {     lcsRADIUSDetailEntry 25 }

    lcsRADIUSAccountTxPendingRequest OBJECT-TYPE
               SYNTAX      Counter32
               MAX-ACCESS  read-only
               STATUS      current
               DESCRIPTION
                   "The number of RADIUS packets destined for the server
                    that have not yet timed out or received a response."
               ::= {     lcsRADIUSDetailEntry 26 }

    lcsRADIUSAccountTxTimeout OBJECT-TYPE
               SYNTAX      Counter32
               MAX-ACCESS  read-only
               STATUS      current
               DESCRIPTION
                   "The number of accounting timeouts to the server.
                    After a timeout, the client may retry to the same
                    server, send to a different server, or give up."
               ::= {     lcsRADIUSDetailEntry 27 }

    lcsRADIUSDetailClearCmd OBJECT-TYPE
               SYNTAX      ActivateCmd
               MAX-ACCESS  read-only
               STATUS      current
               DESCRIPTION
                   "Clears the counters for the selected server."
               ::= {     lcsRADIUSDetailEntry 28 }

--
-- =======================================================================================================================
-- Start lcsTACACS group
-- =======================================================================================================================
--lcsTACACSGlobalConfig

    lcsTACACSGlobalConfigTimeout OBJECT-TYPE
               SYNTAX      Integer32(1..1000)
               MAX-ACCESS  read-write
               STATUS      current
               DESCRIPTION
                   "Timeout is the number of seconds,to wait for a reply
                    from a TACACS+ server before it is considered to be dead.
                    range: 1-1000 seconds,
                    default: 5 seconds."
               ::= {     lcsTACACS 1 }

    lcsTACACSGlobalConfigDeadtime OBJECT-TYPE
               SYNTAX      Integer32(0..1440)
               MAX-ACCESS  read-write
               STATUS      current
               DESCRIPTION
                   "The period during which the switch will not send new
                    requests to a server that has failed to respond to a
                    previous request. This will stop the switch from
                    continually trying to contact a server that it has
                    already determined as dead.
                    range: 0-1440 minutes,
                    default: 0 minutes."
               ::= {     lcsTACACS 2 }

    lcsTACACSGlobalConfigKey OBJECT-TYPE
               SYNTAX      DisplayString
               MAX-ACCESS  read-write
               STATUS      current
               DESCRIPTION
                   "The secret key shared between the TACACS+ server and
                    the switch."
               ::= {     lcsTACACS 3 }

--lcsTACACSServerConfigTable

    lcsTACACSServerConfigTable OBJECT-TYPE
               SYNTAX      SEQUENCE OF     LCSTACACSServerConfigEntry
               MAX-ACCESS  not-accessible
               STATUS      current
               DESCRIPTION
                   "The TACACS Server configuration Table."
               ::= {     lcsTACACS 4 }

    lcsTACACSServerConfigEntry OBJECT-TYPE
               SYNTAX          LCSTACACSServerConfigEntry
               MAX-ACCESS  not-accessible
               STATUS      current
               DESCRIPTION
                   "The TACACS Server configuration Entry."
               INDEX    {    lcsTACACSServerConfigServerNo  }
               ::= {     lcsTACACSServerConfigTable 1 }

    LCSTACACSServerConfigEntry             ::= SEQUENCE {
                 lcsTACACSServerConfigServerNo        Integer32,
                 lcsTACACSServerConfigHostname        DisplayString,
                 lcsTACACSServerConfigPort            Integer32,
                 lcsTACACSServerConfigTimeout         Integer32,
                 lcsTACACSServerConfigKey             DisplayString,
                 lcsTACACSServerConfigRowStatus       RowStatus
                 }

    lcsTACACSServerConfigServerNo OBJECT-TYPE
               SYNTAX      Integer32(1..5)
               MAX-ACCESS  not-accessible
               STATUS      current
               DESCRIPTION
                   "The TACACS server number.
                    max: 5."
               ::= {     lcsTACACSServerConfigEntry 1 }

    lcsTACACSServerConfigHostname OBJECT-TYPE
               SYNTAX      DisplayString
               MAX-ACCESS  read-create
               STATUS      current
               DESCRIPTION
                   "The IP address or hostname of the TACACS+ server."
               ::= {     lcsTACACSServerConfigEntry 2 }

    lcsTACACSServerConfigPort OBJECT-TYPE
               SYNTAX      Integer32(0..65535)
               MAX-ACCESS  read-create
               STATUS      current
               DESCRIPTION
                   "The TCP port to use on the TACACS+ server for
                    authentication."
               ::= {     lcsTACACSServerConfigEntry 3 }

    lcsTACACSServerConfigTimeout OBJECT-TYPE
               SYNTAX      Integer32(1..1000)
               MAX-ACCESS  read-create
               STATUS      current
               DESCRIPTION
                   "This optional setting overrides the global timeout
                    value. Leaving it blank will use the global timeout
                    value.
                    range: 1-1000."
               ::= {     lcsTACACSServerConfigEntry 4 }

    lcsTACACSServerConfigKey OBJECT-TYPE
               SYNTAX      DisplayString
               MAX-ACCESS  read-create
               STATUS      current
               DESCRIPTION
                   "This optional setting overrides the global key.
                    Leaving it blank will use the global key. "
               ::= {     lcsTACACSServerConfigEntry 5 }

    lcsTACACSServerConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     lcsTACACSServerConfigEntry 6 }

-- =======================================================================================================================
--
-- =======================================================================================================================
-- Textual Conventions for the lcs Nas Mib
-- =======================================================================================================================
--
lcsNasMIB                   OBJECT IDENTIFIER  ::= { lcsConfiguration 16 }
    lcsNAS                  OBJECT IDENTIFIER  ::= { lcsNasMIB 1 }
    lcsNASConf              OBJECT IDENTIFIER  ::= { lcsNAS 1 }
    lcsNASStatus            OBJECT IDENTIFIER  ::= { lcsNAS 2 }

--
-- =======================================================================================================================
-- Start lcsNAS group
-- =======================================================================================================================
--lcsNASConf

    lcsNASConfMode OBJECT-TYPE
               SYNTAX      AdminMode
               MAX-ACCESS  read-write
               STATUS      current
               DESCRIPTION
                   "Indicates if NAS is globally enabled or disabled on
                    the switch."
               DEFVAL  { disable }
               ::= {     lcsNASConf 1 }

    lcsNASConfReauthenticationEnabled OBJECT-TYPE
               SYNTAX      AdminMode
               MAX-ACCESS  read-write
               STATUS      current
               DESCRIPTION
                   "If enable, successfully authenticated supplicants/clients
                    are reauthenticated after the interval specified by the
                    Reauthentication Period."
               DEFVAL  { disable }
               ::= {     lcsNASConf 2 }

    lcsNASConfReauthenticationPeriod OBJECT-TYPE
               SYNTAX      Integer32(1..3600)
               MAX-ACCESS  read-write
               STATUS      current
               DESCRIPTION
                   "Determines the period, in seconds, after which a
                    connected client must be reauthenticated.
                    default: 3600 sec,
                    range: 1-3600 sec."
               ::= {     lcsNASConf 3 }

    lcsNASConfEAPOLTimeout OBJECT-TYPE
               SYNTAX      Integer32(1..65535)
               MAX-ACCESS  read-write
               STATUS      current
               DESCRIPTION
                   "Determines the time for retransmission of Request
                    Identity EAPOL frames.
                    default: 30 sec,
                    range: 1-65535 sec."
               ::= {     lcsNASConf 4 }

    lcsNASConfAgingPeriod OBJECT-TYPE
               SYNTAX      Integer32(0|10..1000000)
               MAX-ACCESS  read-write
               STATUS      current
               DESCRIPTION
                   "When the NAS module uses the Port Security module to
                    secure MAC addresses, the Port Security module needs to
                    check for activity on the MAC address in question at regular
                    intervals and free resources if no activity is seen within
                    a given period of time.
                    default: 300 sec,
                    0: no support.
                    range: 0,10-1000000 sec."
               ::= {     lcsNASConf 5 }

    lcsNASConfHoldTime OBJECT-TYPE
               SYNTAX      Integer32(0|10..1000000)
               MAX-ACCESS  read-write
               STATUS      current
               DESCRIPTION
                   "If a client is denied access - either because the RADIUS
                    server denies the client access or because the RADIUS server
                    request times out - the client is put on hold in the
                    Unauthorized state.
                    default: 10 sec,
                    0: no support.
                    range: 0,10-1000000 sec."
               ::= {     lcsNASConf 6 }

    lcsNASConfRADIUSQoSEnabled OBJECT-TYPE
               SYNTAX      AdminMode
               MAX-ACCESS  read-write
               STATUS      current
               DESCRIPTION
                   "RADIUS-assigned QoS provides a means to centrally control
                    the traffic class to which traffic coming from a successfully
                    authenticated supplicant is assigned on the switch."
               DEFVAL  { disable }
               ::= {     lcsNASConf 7 }

    lcsNASConfRADIUSVLANEnabled OBJECT-TYPE
               SYNTAX      AdminMode
               MAX-ACCESS  read-write
               STATUS      current
               DESCRIPTION
                   "RADIUS-assigned VLAN provides a means to centrally control
                    the VLAN on which a successfully authenticated supplicant
                    is placed on the switch."
               DEFVAL  { disable }
               ::= {     lcsNASConf 8 }

    lcsNASConfGuestVLANEnabled OBJECT-TYPE
               SYNTAX      AdminMode
               MAX-ACCESS  read-write
               STATUS      current
               DESCRIPTION
                   "A Guest VLAN is a special VLAN - typically with limited
                    network access - on which 802.1X-unaware clients are placed
                    after a network administrator-defined timeout."
               DEFVAL  { disable }
               ::= {     lcsNASConf 9 }

    lcsNASConfGuestVLANID OBJECT-TYPE
               SYNTAX      Integer32(1..4094)
               MAX-ACCESS  read-write
               STATUS      current
               DESCRIPTION
                   "This is the value that a port's Port VLAN ID is set to if
                    a port is moved into the Guest VLAN.
                    default: 1,
                    range: 1-4094."
               ::= {     lcsNASConf 10 }

    lcsNASConfMaxReauthCount OBJECT-TYPE
               SYNTAX      Integer32(1..255)
               MAX-ACCESS  read-write
               STATUS      current
               DESCRIPTION
                   "The number of times the switch transmits an EAPOL Request
                    Identity frame without response before considering entering
                    the Guest VLAN is adjusted with this setting.
                    default: 2,
                    range: 1-255."
               ::= {     lcsNASConf 11 }

    lcsNASConfAllowGuestVLAN OBJECT-TYPE
               SYNTAX      AdminMode
               MAX-ACCESS  read-write
               STATUS      current
               DESCRIPTION
                   "The switch remembers if an EAPOL frame has been received
                    on the port for the life-time of the port."
               DEFVAL  { disable }
               ::= {     lcsNASConf 12 }

    lcsNASConfMacBasedUseEAP OBJECT-TYPE
               SYNTAX      AdminMode
               MAX-ACCESS  read-write
               STATUS      current
               DESCRIPTION
                   "The switch can do the RADIUS authentication on behalf of the client in the
                    MAC-based Auth. port authentication mode. It can either present itself as a
                    normal 802.1X client to the RADIUS Server and use EAP, supporting only the
                    MD5-Challenge, or alternativly can use plain RADIUS with username / passwort
                    authentification without EAP if this setting is disabled."
               ::= {     lcsNASConf 101 }

--lcsNASPortConfTable

    lcsNASPortConfTable OBJECT-TYPE
               SYNTAX      SEQUENCE OF     LCSNASPortConfEntry
               MAX-ACCESS  not-accessible
               STATUS      current
               DESCRIPTION
                   "The NAS Port Configuration Table.
                    INDEX for this table is ifIndex which is
                    equivalent to the panel port number."
               ::= {     lcsNASConf 13 }

    lcsNASPortConfEntry OBJECT-TYPE
               SYNTAX          LCSNASPortConfEntry
               MAX-ACCESS  not-accessible
               STATUS      current
               DESCRIPTION
                   "The NAS Port Configuration Entry."
               INDEX    {    ifIndex  }
               ::= {     lcsNASPortConfTable 1 }

    LCSNASPortConfEntry             ::= SEQUENCE {
                 lcsNASPortConfAdminState         Integer32,
                 lcsNASPortConfRADIUSQoSEnabled   AdminMode,
                 lcsNASPortConfRADIUSVLANEnabled  AdminMode,
                 lcsNASPortConfGuestVLANEnabled   AdminMode,
                 lcsNASPortConfFallbackEnabled    AdminMode,
                 lcsNASPortConfPortState          DisplayString,
                 lcsNASPortConfReauthenticateCmd  INTEGER,
                 lcsNASPortConfReinitializeCmd    INTEGER
                 }

    lcsNASPortConfAdminState OBJECT-TYPE
               SYNTAX      Integer32(0..6)
               MAX-ACCESS  read-write
               STATUS      current
               DESCRIPTION
                   "This selection controls the port's authentication mode.
                    0: Force Authorized,
                    1: Force Unauthorized,
                    2: Port-based 802.1X,
                    3: Single 802.1X,
                    4: Multi 802.1X,
                    5: MAC-based Auth,
                    6: MAC-based Single Auth.
                    range: 0-6."
               ::= {     lcsNASPortConfEntry 2 }

    lcsNASPortConfRADIUSQoSEnabled OBJECT-TYPE
               SYNTAX      AdminMode
               MAX-ACCESS  read-write
               STATUS      current
               DESCRIPTION
                   "When RADIUS-Assigned QoS is both globally enabled and
                    enabled on a given port, the switch reacts to QoS Class
                    information carried in the RADIUS Access-Accept packet
                    transmitted by the RADIUS server when a supplicant is
                    successfully authenticated."
               ::= {     lcsNASPortConfEntry 3 }

    lcsNASPortConfRADIUSVLANEnabled OBJECT-TYPE
               SYNTAX      AdminMode
               MAX-ACCESS  read-write
               STATUS      current
               DESCRIPTION
                   "When RADIUS-Assigned VLAN is both globally enabled and
                    enabled for a given port, the switch reacts to VLAN ID
                    information carried in the RADIUS Access-Accept packet
                    transmitted by the RADIUS server when a supplicant is
                    successfully authenticated."
               ::= {     lcsNASPortConfEntry 4 }

    lcsNASPortConfGuestVLANEnabled OBJECT-TYPE
               SYNTAX      AdminMode
               MAX-ACCESS  read-write
               STATUS      current
               DESCRIPTION
                   "When Guest VLAN is both globally enabled and enabled for
                    a given port, the switch considers moving the port into
                    the Guest VLAN according to the rules."
               ::= {     lcsNASPortConfEntry 5 }

    lcsNASPortConfPortState OBJECT-TYPE
               SYNTAX      DisplayString
               MAX-ACCESS  read-only
               STATUS      current
               DESCRIPTION
                   "The current state of the port."
               ::= {     lcsNASPortConfEntry 6 }

    lcsNASPortConfReauthenticateCmd OBJECT-TYPE
               SYNTAX      ActivateCmd
               MAX-ACCESS  read-write
               STATUS      current
               DESCRIPTION
                   "Schedules a reauthentication whenever the quiet-period of
                    the port runs out (EAPOL-based authentication). For
                    MAC-based authentication, reauthentication will be attempted
                    immediately.The button only has effect for successfully
                    authenticated clients on the port and will not cause the
                    clients to get temporarily unauthorized."
               DEFVAL  { noAction }
               ::= {     lcsNASPortConfEntry 7 }

    lcsNASPortConfReinitializeCmd OBJECT-TYPE
               SYNTAX      ActivateCmd
               MAX-ACCESS  read-write
               STATUS      current
               DESCRIPTION
                   "Forces a reinitialization of the clients on the port and
                    thereby a reauthentication immediately. The clients will
                    transfer to the unauthorized state while the
                    reauthentication is in progress."
               DEFVAL  { noAction }
               ::= {     lcsNASPortConfEntry 8 }

    lcsNASPortConfFallbackEnabled OBJECT-TYPE
               SYNTAX      AdminMode
               MAX-ACCESS  read-write
               STATUS      current
               DESCRIPTION
                   "When Fallback is enabled, the switch will take over the supplicants role
                    after max reauthentication count is reached and tries to authenticate the
                    client on its behalf as described for MAC-based Auth.
                    Admin State supported : Single and Multi 802.1X."
               ::= {     lcsNASPortConfEntry 101 }

--lcsNASSwitchStatusTable

    lcsNASSwitchStatusTable OBJECT-TYPE
               SYNTAX      SEQUENCE OF     LCSNASSwitchStatusEntry
               MAX-ACCESS  not-accessible
               STATUS      current
               DESCRIPTION
                   "The NAS Switch Status Table.
                    INDEX for this table is ifIndex which is
                    equivalent to the panel port number."
               ::= {     lcsNASStatus 1 }

    lcsNASSwitchStatusEntry OBJECT-TYPE
               SYNTAX          LCSNASSwitchStatusEntry
               MAX-ACCESS  not-accessible
               STATUS      current
               DESCRIPTION
                   "The NAS Switch Status Entry."
               INDEX    {    ifIndex  }
               ::= {     lcsNASSwitchStatusTable 1 }

    LCSNASSwitchStatusEntry             ::= SEQUENCE {
                 lcsNASSwitchStatusAdminState   DisplayString,
                 lcsNASSwitchStatusPortState    DisplayString,
                 lcsNASSwitchStatusLastSource   DisplayString,
                 lcsNASSwitchStatusLastID       DisplayString,
                 lcsNASSwitchStatusQoSClass     DisplayString,
                 lcsNASSwitchStatusPortVLANID   DisplayString
                 }

    lcsNASSwitchStatusAdminState OBJECT-TYPE
               SYNTAX      DisplayString
               MAX-ACCESS  read-only
               STATUS      current
               DESCRIPTION
                   "The port's current administrative state."
               ::= {     lcsNASSwitchStatusEntry 2 }

    lcsNASSwitchStatusPortState OBJECT-TYPE
               SYNTAX      DisplayString
               MAX-ACCESS  read-only
               STATUS      current
               DESCRIPTION
                   "The current state of the port."
               ::= {     lcsNASSwitchStatusEntry 3 }

    lcsNASSwitchStatusLastSource OBJECT-TYPE
               SYNTAX      DisplayString
               MAX-ACCESS  read-only
               STATUS      current
               DESCRIPTION
                   "The source MAC address carried in the most recently
                    received EAPOL frame for EAPOL-based authentication,
                    and the most recently received frame from a new client
                    for MAC-based authentication."
               ::= {     lcsNASSwitchStatusEntry 4 }

    lcsNASSwitchStatusLastID OBJECT-TYPE
               SYNTAX      DisplayString
               MAX-ACCESS  read-only
               STATUS      current
               DESCRIPTION
                   "The user name (supplicant identity) carried in the most
                    recently received Response Identity EAPOL frame for
                    EAPOL-based authentication, and the source MAC address
                    from the most recently received frame from a new client
                    for MAC-based authentication."
               ::= {     lcsNASSwitchStatusEntry 5 }

    lcsNASSwitchStatusQoSClass OBJECT-TYPE
               SYNTAX      DisplayString
               MAX-ACCESS  read-only
               STATUS      current
               DESCRIPTION
                   "QoS Class assigned to the port by the RADIUS server
                    if enabled."
               ::= {     lcsNASSwitchStatusEntry 6 }

    lcsNASSwitchStatusPortVLANID OBJECT-TYPE
               SYNTAX      DisplayString
               MAX-ACCESS  read-only
               STATUS      current
               DESCRIPTION
                   "The VLAN ID that NAS has put the port in."
               ::= {     lcsNASSwitchStatusEntry 7 }

--lcsNASPortCounterTable

    lcsNASPortCounterTable OBJECT-TYPE
               SYNTAX      SEQUENCE OF     LCSNASPortCounterEntry
               MAX-ACCESS  not-accessible
               STATUS      current
               DESCRIPTION
                   "The NAS Port Counter Table.
                    INDEX for this table is ifIndex which is
                    equivalent to the panel port number."
               ::= {     lcsNASStatus 2 }

    lcsNASPortCounterEntry OBJECT-TYPE
               SYNTAX          LCSNASPortCounterEntry
               MAX-ACCESS  not-accessible
               STATUS      current
               DESCRIPTION
                   "The NAS Port Counter Entry."
               INDEX    {    ifIndex  }
               ::= {     lcsNASPortCounterTable 1 }

    LCSNASPortCounterEntry             ::= SEQUENCE {
                 lcsNASReceiveEAPOLTotal          Integer32,
                 lcsNASReceiveEAPOLResponseID     Integer32,
                 lcsNASReceiveEAPOLResponses      Integer32,
                 lcsNASReceiveEAPOLStart          Integer32,
                 lcsNASReceiveEAPOLLogoff         Integer32,
                 lcsNASReceiveEAPOLInvalidType    Integer32,
                 lcsNASReceiveEAPOLInvalidLength  Integer32,
                 lcsNASTransmitEAPOLTotal         Integer32,
                 lcsNASTransmitEAPOLRequestID     Integer32,
                 lcsNASTransmitEAPOLRequests      Integer32,
                 lcsNASPortReceiveBackendServerAccessChallenges    Integer32,
                 lcsNASPortReceiveBackendServerOtherRequests       Integer32,
                 lcsNASPortReceiveBackendServerAuthSuccesses       Integer32,
                 lcsNASPortReceiveBackendServerAuthFailures        Integer32,
                 lcsNASPortTransmitBackendServerResponses          Integer32,
                 lcsNASSupplicantInfoMAC          DisplayString,
                 lcsNASSupplicantInfoVlanID       Integer32,
                 lcsNASSupplicantInfoVersion      Integer32,
                 lcsNASSupplicantInfoIdentity     DisplayString,
                 lcsNASPortCounterClearCmd        ActivateCmd
                 }

    lcsNASReceiveEAPOLTotal OBJECT-TYPE
               SYNTAX      Integer32(-1..1000000)
               MAX-ACCESS  read-only
               STATUS      current
               DESCRIPTION
                   "The number of valid EAPOL frames of any type that have
                    been received by the switch.
                    -1: no support."
               ::= {     lcsNASPortCounterEntry 2 }

    lcsNASReceiveEAPOLResponseID OBJECT-TYPE
               SYNTAX      Integer32(-1..1000000)
               MAX-ACCESS  read-only
               STATUS      current
               DESCRIPTION
                   "The number of valid EAPOL Response Identity frames that
                    have been received by the switch.
                    -1: no support."
               ::= {     lcsNASPortCounterEntry 3 }

    lcsNASReceiveEAPOLResponses OBJECT-TYPE
               SYNTAX      Integer32(-1..1000000)
               MAX-ACCESS  read-only
               STATUS      current
               DESCRIPTION
                   "The number of valid EAPOL response frames (other than
                    Response Identity frames) that have been received by
                    the switch.
                    -1: no support."
               ::= {     lcsNASPortCounterEntry 4 }

    lcsNASReceiveEAPOLStart OBJECT-TYPE
               SYNTAX      Integer32(-1..1000000)
               MAX-ACCESS  read-only
               STATUS      current
               DESCRIPTION
                   "The number of EAPOL Start frames that have been received
                    by the switch.
                    -1: no support."
               ::= {     lcsNASPortCounterEntry 5 }

    lcsNASReceiveEAPOLLogoff OBJECT-TYPE
               SYNTAX      Integer32(-1..1000000)
               MAX-ACCESS  read-only
               STATUS      current
               DESCRIPTION
                   "The number of valid EAPOL Logoff frames that have been
                    received by the switch.
                    -1: no support."
               ::= {     lcsNASPortCounterEntry 6 }

    lcsNASReceiveEAPOLInvalidType OBJECT-TYPE
               SYNTAX      Integer32(-1..1000000)
               MAX-ACCESS  read-only
               STATUS      current
               DESCRIPTION
                   "The number of EAPOL frames that have been received by
                    the switch in which the frame type is not recognized.
                    -1: no support."
               ::= {     lcsNASPortCounterEntry 7 }

    lcsNASReceiveEAPOLInvalidLength OBJECT-TYPE
               SYNTAX      Integer32(-1..1000000)
               MAX-ACCESS  read-only
               STATUS      current
               DESCRIPTION
                   "The number of EAPOL frames that have been received
                    by the switch in which the Packet Body Length field
                    is invalid.
                    -1: no support."
               ::= {     lcsNASPortCounterEntry 8 }

    lcsNASTransmitEAPOLTotal OBJECT-TYPE
               SYNTAX      Integer32(-1..1000000)
               MAX-ACCESS  read-only
               STATUS      current
               DESCRIPTION
                   "The number of EAPOL frames of any type that have been
                    transmitted by the switch.
                    -1: no support."
               ::= {     lcsNASPortCounterEntry 9 }

    lcsNASTransmitEAPOLRequestID OBJECT-TYPE
               SYNTAX      Integer32(-1..1000000)
               MAX-ACCESS  read-only
               STATUS      current
               DESCRIPTION
                   "The number of EAPOL Request Identity frames that have
                    been transmitted by the switch.
                    -1: no support."
               ::= {     lcsNASPortCounterEntry 10 }

    lcsNASTransmitEAPOLRequests OBJECT-TYPE
               SYNTAX      Integer32(-1..1000000)
               MAX-ACCESS  read-only
               STATUS      current
               DESCRIPTION
                   "The number of valid EAPOL Request frames (other than
                    Request Identity frames) that have been transmitted
                    by the switch.
                    -1: no support."
               ::= {     lcsNASPortCounterEntry 11 }

    lcsNASPortReceiveBackendServerAccessChallenges OBJECT-TYPE
               SYNTAX      Integer32(-1..1000000)
               MAX-ACCESS  read-only
               STATUS      current
               DESCRIPTION
                   "802.1X-based: Counts the number of times that the switch
                    receives the first request from the backend server following
                    the first response from the supplicant. Indicates that the
                    backend server has communication with the switch.
                    MAC-based:Counts all Access Challenges received from the
                    backend server for this port (left-most table).
                    -1: no support."
               ::= {     lcsNASPortCounterEntry 12 }

    lcsNASPortReceiveBackendServerOtherRequests OBJECT-TYPE
               SYNTAX      Integer32(-1..1000000)
               MAX-ACCESS  read-only
               STATUS      current
               DESCRIPTION
                   "802.1X-based: Counts the number of times that the switch
                    sends an EAP Request packet following the first to the
                    supplicant. Indicates that the backend server chose an
                    EAP-method.
                    MAC-based: Not applicable.
                    -1: no support."
               ::= {     lcsNASPortCounterEntry 13 }

    lcsNASPortReceiveBackendServerAuthSuccesses OBJECT-TYPE
               SYNTAX      Integer32(-1..1000000)
               MAX-ACCESS  read-only
               STATUS      current
               DESCRIPTION
                   "802.1X- and MAC-based: Counts the number of times that
                    the switch receives a success indication.Indicates that
                    the supplicant has successfully authenticated to
                    the backend server.
                    -1: no support."
               ::= {     lcsNASPortCounterEntry 14 }

    lcsNASPortReceiveBackendServerAuthFailures OBJECT-TYPE
               SYNTAX      Integer32(-1..1000000)
               MAX-ACCESS  read-only
               STATUS      current
               DESCRIPTION
                   "802.1X- and MAC-based:Counts the number of times that the
                    switch receives a failure message.This indicates that the
                    supplicant has not authenticated to the backend
                    server.
                    -1: no support."
               ::= {     lcsNASPortCounterEntry 15 }

    lcsNASPortTransmitBackendServerResponses OBJECT-TYPE
               SYNTAX      Integer32(-1..1000000)
               MAX-ACCESS  read-only
               STATUS      current
               DESCRIPTION
                   "802.1X-based:Counts the number of times that the switch
                    attempts to send a supplicant's first response packet to
                    the backend server. Indicates the switch attempted
                    communication with the backend server. Possible
                    retransmissions are not counted.
                    MAC-based: Counts all the backend server packets sent from
                    the switch towards the backend server for a given port
                    (left-most table). Possible retransmissions are not
                    counted.
                    -1: no support."
               ::= {     lcsNASPortCounterEntry 16 }

    lcsNASSupplicantInfoMAC OBJECT-TYPE
               SYNTAX      DisplayString
               MAX-ACCESS  read-only
               STATUS      current
               DESCRIPTION
                   "The MAC address of the last supplicant. "
               ::= {     lcsNASPortCounterEntry 17 }

    lcsNASSupplicantInfoVlanID OBJECT-TYPE
               SYNTAX      Integer32(-1..1000000)
               MAX-ACCESS  read-only
               STATUS      current
               DESCRIPTION
                   "The VLAN ID on which the last frame from the last
                    supplicant was received.
                    -1: no support."
               ::= {     lcsNASPortCounterEntry 18 }

    lcsNASSupplicantInfoVersion OBJECT-TYPE
               SYNTAX      Integer32(-1..1000000)
               MAX-ACCESS  read-only
               STATUS      current
               DESCRIPTION
                   "802.1X-based:The protocol version number carried in
                    the most recently received EAPOL frame.
                    MAC-based: Not applicable.
                    -1: no support."
               ::= {     lcsNASPortCounterEntry 19 }

    lcsNASSupplicantInfoIdentity OBJECT-TYPE
               SYNTAX      DisplayString
               MAX-ACCESS  read-only
               STATUS      current
               DESCRIPTION
                   "802.1X-based:The user name (supplicant identity) carried
                    in the most recently received Response Identity EAPOL frame.
                    MAC-based: Not applicable. "
               ::= {     lcsNASPortCounterEntry 20 }

    lcsNASPortCounterClearCmd OBJECT-TYPE
               SYNTAX      ActivateCmd
               MAX-ACCESS  read-write
               STATUS      current
               DESCRIPTION
                   "Clear the counters for the selected port."
               ::= {     lcsNASPortCounterEntry 21 }


-- =======================================================================================================================
lcsMACConf                      OBJECT IDENTIFIER ::= { lcsConfiguration 17 }

    lcsMAC                                                    OBJECT IDENTIFIER   ::= { lcsMACConf 1 }

--
-- =======================================================================================================================
-- Start lcsMAC group
-- =======================================================================================================================
    lcsMACDisableAutomaticAging   OBJECT-TYPE
               SYNTAX       AdminMode
               MAX-ACCESS   read-write
               STATUS       current
               DESCRIPTION
                   "Disable the automatic aging of dynamic entries."
                ::= {     lcsMAC 1 }

    lcsMACAgingTime  OBJECT-TYPE
               SYNTAX       Integer32 (-1 | 10..1000000)
               MAX-ACCESS   read-write
               STATUS       current
               DESCRIPTION
                   "Configure aging time by entering a value here in seconds.
                   range: 10-1000000 seconds.
                   -1: Automatic Aging is disable."
                ::= {     lcsMAC 2 }

--lcsMACLearningTable
    lcsMACLearningTable OBJECT-TYPE
               SYNTAX      SEQUENCE OF     LCSMACLearningEntry
               MAX-ACCESS  not-accessible
               STATUS      current
               DESCRIPTION
                   "The mac learning table.
                    INDEX for this table is ifIndex which is
                    equivalent to the panel port number."
               ::= {     lcsMAC 3 }

    lcsMACLearningEntry OBJECT-TYPE
               SYNTAX          LCSMACLearningEntry
               MAX-ACCESS  not-accessible
               STATUS      current
               DESCRIPTION
                   "The mac learning entry."
               INDEX    {     ifIndex  }
               ::= {     lcsMACLearningTable 1 }

    LCSMACLearningEntry             ::= SEQUENCE {
                lcsMACTableLearning     INTEGER
                }

    lcsMACTableLearning OBJECT-TYPE
               SYNTAX      INTEGER{ auto(0), disable(1), secure(2)}
               MAX-ACCESS  read-write
               STATUS      current
               DESCRIPTION
                   "auto(0)   : Learning is done automatically as soon as a
                                frame with unknown SMAC is received.
                    disable(1): Disable, No learning is done.
                    secure(2) : Secure, Only static MAC entries are learned,
                                all other frames are dropped."
               ::= {     lcsMACLearningEntry 2 }

    lcsLearningDisabledVLANs OBJECT-TYPE
               SYNTAX      DisplayString
               MAX-ACCESS  read-write
               STATUS      current
               DESCRIPTION
                   "The Learning Disabled VLANs"
               ::= {     lcsMAC 4 }            
               
--lcsMACStaticConfigTable
    lcsMACStaticConfigTable OBJECT-TYPE
               SYNTAX      SEQUENCE OF     LCSMACStaticConfigEntry
               MAX-ACCESS  not-accessible
               STATUS      current
               DESCRIPTION
                   "The static Mac config table."
               ::= {     lcsMAC 5 }

    lcsMACStaticConfigEntry OBJECT-TYPE
               SYNTAX          LCSMACStaticConfigEntry
               MAX-ACCESS  not-accessible
               STATUS      current
               DESCRIPTION
                   "The static Mac config entry."
               INDEX    {     lcsMACStaticConfigIndex  }
               ::= {     lcsMACStaticConfigTable 1 }

    LCSMACStaticConfigEntry             ::= SEQUENCE {
                lcsMACStaticConfigSwitchIndex Integer32,
                lcsMACStaticConfigIndex       Integer32,
                lcsMACStaticConfigVID         Integer32,
                lcsMACStaticConfigMACaddress  DisplayString,
                lcsMACStaticConfigPortList    DisplayString,
                lcsMACStaticConfigRowStatus   RowStatus
                }

    lcsMACStaticConfigSwitchIndex OBJECT-TYPE
               SYNTAX      Integer32(1..16)
               MAX-ACCESS  not-accessible
               STATUS      current
               DESCRIPTION
                   "Switch Index."
               ::= {     lcsMACStaticConfigEntry 1 }



    lcsMACStaticConfigIndex OBJECT-TYPE
               SYNTAX      Integer32(1..64)
               MAX-ACCESS  not-accessible
               STATUS      current
               DESCRIPTION
                   "The static entries in the MAC table are shown in this table.
                    The static MAC table can contain 64 entries."
               ::= {     lcsMACStaticConfigEntry 2 }

    lcsMACStaticConfigVID OBJECT-TYPE
               SYNTAX      Integer32(1..4094)
               MAX-ACCESS  read-create
               STATUS      current
               DESCRIPTION
                   "The VLAN ID of the entry.
                    range: 1-4094."
               ::= {     lcsMACStaticConfigEntry 3 }

    lcsMACStaticConfigMACaddress OBJECT-TYPE
               SYNTAX      DisplayString
               MAX-ACCESS  read-create
               STATUS      current
               DESCRIPTION
                   "The MAC address of the entry."
               ::= {     lcsMACStaticConfigEntry 4 }

    lcsMACStaticConfigPortList OBJECT-TYPE
               SYNTAX      DisplayString
               MAX-ACCESS  read-create
               STATUS      current
               DESCRIPTION
                   "Checkmarks indicate which ports are members of the entry.
                    Check or uncheck as needed to
                    modify the entry."
               ::= {     lcsMACStaticConfigEntry 5 }

    lcsMACStaticConfigRowStatus OBJECT-TYPE
               SYNTAX      RowStatus
               MAX-ACCESS  read-create
               STATUS      current
               DESCRIPTION
                   "This object indicates the status of this entry,
                    and is used to create/delete entries. Any
                    object in an entry of this table may be modified
                    while the value of the corresponding instance
                    of this object is active(1).
                    createAndGo, notReady not supported."
               ::= {     lcsMACStaticConfigEntry 6 }


-- =======================================================================================================================
lcsSpanningTree                         OBJECT IDENTIFIER ::= { lcsConfiguration 18 }

lcsBridgeSettings                     OBJECT IDENTIFIER ::= { lcsSpanningTree 1 }

lcsSTPProtocolVersion    OBJECT-TYPE
               SYNTAX      Integer32
               MAX-ACCESS  read-write
               STATUS      current
               DESCRIPTION
                   "0:STP
                    2:RSTP
                    3:MSTP"
               ::= {     lcsBridgeSettings 1 }

lcsBridgePriority    OBJECT-TYPE
               SYNTAX      Integer32
               MAX-ACCESS  read-write
               STATUS      current
               DESCRIPTION
                   "Bridge Priority, range: 0-61440, multiple of 4096."
               ::= {     lcsBridgeSettings 2 }

lcsBridgeForwardDelay    OBJECT-TYPE
               SYNTAX      Integer32
               MAX-ACCESS  read-write
               STATUS      current
               DESCRIPTION
                   "Bridge Forward Delay, range: 4-30 seconds."
               ::= {     lcsBridgeSettings 3 }

lcsBridgeMaxAge    OBJECT-TYPE
               SYNTAX      Integer32
               MAX-ACCESS  read-write
               STATUS      current
               DESCRIPTION
                   "Bridge MaxAge, range:6-40 seconds."
               ::= {     lcsBridgeSettings 4 }

lcsBridgeMaxHops    OBJECT-TYPE
               SYNTAX      Integer32
               MAX-ACCESS  read-write
               STATUS      current
               DESCRIPTION
                   "Bridge Max Hops, range:6-40 hops."
               ::= {     lcsBridgeSettings 5 }

lcsBridgetxHoldCount    OBJECT-TYPE
               SYNTAX      Integer32
               MAX-ACCESS  read-write
               STATUS      current
               DESCRIPTION
                   "Bridge Transmit Hold Count,range: 1-10 bpdu's per second. "
               ::= {     lcsBridgeSettings 6 }

lcsBridgeBPDUFilter    OBJECT-TYPE
               SYNTAX      Integer32
               MAX-ACCESS  read-write
               STATUS      current
               DESCRIPTION
                   "Bridge BPD UFilter
                    0:disable
                    1:enable                    "
               ::= {     lcsBridgeSettings 7 }

lcsBridgeBPDUGuard    OBJECT-TYPE
               SYNTAX      Integer32
               MAX-ACCESS  read-write
               STATUS      current
               DESCRIPTION
                   "Bridge BPDU Guard
                    0:disable
                    1:enable                       "
               ::= {     lcsBridgeSettings 8 }

lcsBridgeerrorRecoveryDelay    OBJECT-TYPE
               SYNTAX      Integer32
               MAX-ACCESS  read-write
               STATUS      current
               DESCRIPTION
                   "Bridge error Recovery Delay
                   range:30-86400 seconds
                   0:disable
                   "
               ::= {     lcsBridgeSettings 9 }

lcsBridgeHelloTime    OBJECT-TYPE
               SYNTAX      Integer32
               MAX-ACCESS  read-write
               STATUS      current
               DESCRIPTION
                   "The interval between sending STP BPDU's. Valid values are in the range 1 to 10 seconds, 
                   default:2 seconds."
               ::= {     lcsBridgeSettings 10 }            

lcsMSTIMapping                        OBJECT IDENTIFIER ::= { lcsSpanningTree 2 }
lcsConfigName    OBJECT-TYPE
               SYNTAX      DisplayString
               MAX-ACCESS  read-write
               STATUS      current
               DESCRIPTION
                   "Configuration Name, identify the VLAN to MSTI mapping"
               ::= {     lcsMSTIMapping 1 }

lcsConfigRevision    OBJECT-TYPE
               SYNTAX      Integer32
               MAX-ACCESS  read-write
               STATUS      current
               DESCRIPTION
                   "Configuration Revision. range:0-65535 "
               ::= {     lcsMSTIMapping 2 }

lcsMSTIMappingVLAN                    OBJECT IDENTIFIER ::= { lcsSpanningTree 3 }
lcsConfigMstiName1    OBJECT-TYPE
               SYNTAX      DisplayString
               MAX-ACCESS  read-write
               STATUS      current
               DESCRIPTION
                   "The list of VLANs mapped to the MSTI1.
                    The VLANs can be given as a single (xx, xx being between 1 and 4094) VLAN, or a range (xx-yy), each of which must be separated with comma and/or space. "
               ::= {     lcsMSTIMappingVLAN 1 }

lcsConfigMstiName2    OBJECT-TYPE
               SYNTAX      DisplayString
               MAX-ACCESS  read-write
               STATUS      current
               DESCRIPTION
                   "The list of VLANs mapped to the MSTI2.
                    The VLANs can be given as a single (xx, xx being between 1 and 4094) VLAN, or a range (xx-yy), each of which must be separated with comma and/or space.  "
               ::= {     lcsMSTIMappingVLAN 2 }

lcsConfigMstiName3    OBJECT-TYPE
               SYNTAX      DisplayString
               MAX-ACCESS  read-write
               STATUS      current
               DESCRIPTION
                   "The list of VLANs mapped to the MSTI3.
                    The VLANs can be given as a single (xx, xx being between 1 and 4094) VLAN, or a range (xx-yy), each of which must be separated with comma and/or space. "
               ::= {     lcsMSTIMappingVLAN 3 }

lcsConfigMstiName4    OBJECT-TYPE
               SYNTAX      DisplayString
               MAX-ACCESS  read-write
               STATUS      current
               DESCRIPTION
                   "The list of VLANs mapped to the MSTI4.
                    The VLANs can be given as a single (xx, xx being between 1 and 4094) VLAN, or a range (xx-yy), each of which must be separated with comma and/or space. "
               ::= {     lcsMSTIMappingVLAN 4 }

lcsConfigMstiName5    OBJECT-TYPE
               SYNTAX      DisplayString
               MAX-ACCESS  read-write
               STATUS      current
               DESCRIPTION
                   "The list of VLANs mapped to the MSTI5.
                    The VLANs can be given as a single (xx, xx being between 1 and 4094) VLAN, or a range (xx-yy), each of which must be separated with comma and/or space. "
               ::= {     lcsMSTIMappingVLAN 5 }

lcsConfigMstiName6    OBJECT-TYPE
               SYNTAX      DisplayString
               MAX-ACCESS  read-write
               STATUS      current
               DESCRIPTION
                   "The list of VLANs mapped to the MSTI6.
                    The VLANs can be given as a single (xx, xx being between 1 and 4094) VLAN, or a range (xx-yy), each of which must be separated with comma and/or space. "
               ::= {     lcsMSTIMappingVLAN 6 }

lcsConfigMstiName7    OBJECT-TYPE
               SYNTAX      DisplayString
               MAX-ACCESS  read-write
               STATUS      current
               DESCRIPTION
                   "The list of VLANs mapped to the MSTI7.
                    The VLANs can be given as a single (xx, xx being between 1 and 4094) VLAN, or a range (xx-yy), each of which must be separated with comma and/or space. "
               ::= {     lcsMSTIMappingVLAN 7 }

lcsMSTIPriorities                     OBJECT IDENTIFIER ::= { lcsSpanningTree 4 }

lcsCSTIPriority   OBJECT-TYPE
               SYNTAX      Integer32
               MAX-ACCESS  read-write
               STATUS      current
               DESCRIPTION
                   "CSTI Priority. range: 0-61440, multiple of 4096. Lower numeric values have better priority."
               ::= {     lcsMSTIPriorities 1 }

lcsMSTI1Priority   OBJECT-TYPE
               SYNTAX      Integer32
               MAX-ACCESS  read-write
               STATUS      current
               DESCRIPTION
                   "MSTI1 Priority. range: 0-61440, multiple of 4096. Lower numeric values have better priority."
               ::= {     lcsMSTIPriorities 2 }

lcsMSTI2Priority   OBJECT-TYPE
               SYNTAX      Integer32
               MAX-ACCESS  read-write
               STATUS      current
               DESCRIPTION
                   "MSTI2 Priority. range: 0-61440, multiple of 4096. Lower numeric values have better priority."
               ::= {     lcsMSTIPriorities 3 }

lcsMSTI3Priority   OBJECT-TYPE
               SYNTAX      Integer32
               MAX-ACCESS  read-write
               STATUS      current
               DESCRIPTION
                   "MSTI3 Priority. range: 0-61440, multiple of 4096. Lower numeric values have better priority."
               ::= {     lcsMSTIPriorities 4 }
lcsMSTI4Priority   OBJECT-TYPE
               SYNTAX      Integer32
               MAX-ACCESS  read-write
               STATUS      current
               DESCRIPTION
                   "MSTI4 Priority. range: 0-61440, multiple of 4096. Lower numeric values have better priority."
               ::= {     lcsMSTIPriorities 5 }
lcsMSTI5Priority   OBJECT-TYPE
               SYNTAX      Integer32
               MAX-ACCESS  read-write
               STATUS      current
               DESCRIPTION
                   "MSTI5 Priority. range: 0-61440, multiple of 4096. Lower numeric values have better priority."
               ::= {     lcsMSTIPriorities 6 }

lcsMSTI6Priority   OBJECT-TYPE
               SYNTAX      Integer32
               MAX-ACCESS  read-write
               STATUS      current
               DESCRIPTION
                   "MSTI6 Priority. range: 0-61440, multiple of 4096. Lower numeric values have better priority."
               ::= {     lcsMSTIPriorities 7 }
lcsMSTI7Priority   OBJECT-TYPE
               SYNTAX      Integer32
               MAX-ACCESS  read-write
               STATUS      current
               DESCRIPTION
                   "MSTI7 Priority. range: 0-61440, multiple of 4096. Lower numeric values have better priority."
               ::= {     lcsMSTIPriorities 8 }


lcsCISTPorts                          OBJECT IDENTIFIER ::= { lcsSpanningTree 5 }

lcsCISTAggregatedEnable   OBJECT-TYPE
               SYNTAX      Integer32 (0|1)
               MAX-ACCESS  read-write
               STATUS      current
               DESCRIPTION
                   "CIST Port Enable. range: 0-1.
                   0:disable
                   1:enable."
               ::= {     lcsCISTPorts 1 }

lcsCISTAggregatedPathCost   OBJECT-TYPE
               SYNTAX      Integer32 (0..200000000)
               MAX-ACCESS  read-write
               STATUS      current
               DESCRIPTION
                   "CIST Port Path Cost. range: 0-200000000. 0 is Auto."
               ::= {     lcsCISTPorts 2 }

lcsCISTAggregatedPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     lcsCISTPorts 3 }

lcsCISTAggregatedAdminEdge   OBJECT-TYPE
               SYNTAX      Integer32 (0|1)
               MAX-ACCESS  read-write
               STATUS      current
               DESCRIPTION
                   "CIST Port Admin Edge. range: 0-1.
                   0:Non-Edge
                   1:Edge."
               ::= {     lcsCISTPorts 4 }

lcsCISTAggregatedAutoEdge   OBJECT-TYPE
               SYNTAX      Integer32 (0|1)
               MAX-ACCESS  read-write
               STATUS      current
               DESCRIPTION
                   "CIST Port Auto Edge. range: 0-1.
                   0:disable
                   1:enable."
               ::= {     lcsCISTPorts 5 }

lcsCISTAggregatedrestrictedRole   OBJECT-TYPE
               SYNTAX      Integer32 (0|1)
               MAX-ACCESS  read-write
               STATUS      current
               DESCRIPTION
                   "CIST Port restricted Role. range: 0-1.
                   0:disable
                   1:enable."
               ::= {     lcsCISTPorts 6 }

lcsCISTAggregatedrestrictedTcn   OBJECT-TYPE
               SYNTAX      Integer32 (0|1)
               MAX-ACCESS  read-write
               STATUS      current
               DESCRIPTION
                   "CIST Port restricted Tcn. range: 0-1.
                   0:disable
                   1:enable."
               ::= {     lcsCISTPorts 7 }

lcsCISTAggregatedbpduGuard   OBJECT-TYPE
               SYNTAX      Integer32 (0|1)
               MAX-ACCESS  read-write
               STATUS      current
               DESCRIPTION
                   "CIST Port bpdu Guard. range: 0-1.
                   0:disable
                   1:enable."
               ::= {     lcsCISTPorts 8 }

lcsCISTAggregatedPointToPoint   OBJECT-TYPE
               SYNTAX      Integer32 (0..2)
               MAX-ACCESS  read-write
               STATUS      current
               DESCRIPTION
                   "CIST Port Point To Point. range: 0-2.
                   0:Forced True
                   1:Forced False.
                   2:Auto"
               ::= {     lcsCISTPorts 9 }


lcsCISTPortsTable OBJECT-TYPE
   SYNTAX      SEQUENCE OF LCSCISTPortsEntry
   MAX-ACCESS  not-accessible
   STATUS      current
   DESCRIPTION
        "CIST port table."
    ::= { lcsCISTPorts 10 }

lcsCISTPortsEntry OBJECT-TYPE
    SYNTAX        LCSCISTPortsEntry
    MAX-ACCESS    not-accessible
    STATUS        current
    DESCRIPTION
        "An entry in the CIST Ports Table."
    INDEX        { lcsCISTPortIndex }
    ::= { lcsCISTPortsTable 1 }

LCSCISTPortsEntry ::=
    SEQUENCE {
        lcsCISTPortIndex                 Integer32,
        lcsCISTPortEnable                Integer32,
        lcsCISTPortPathCost              Integer32,
        lcsCISTPortPortPriority          Integer32,
        lcsCISTPortAdminEdge             Integer32,
        lcsCISTPortAutoEdge              Integer32,
        lcsCISTPortrestrictedRole        Integer32,
        lcsCISTPortrestrictedTcn         Integer32,
        lcsCISTPortbpduGuard             Integer32,
        lcsCISTPortPointToPoint          Integer32,
        lcsCISTPortRootGuard             Integer32
    }

lcsCISTPortIndex   OBJECT-TYPE
               SYNTAX      Integer32 (1..53)
               MAX-ACCESS  not-accessible
               STATUS      current
               DESCRIPTION
                   "CIST Port Index. range: 1-53. 53 is Aggregated Port Configuration."
               ::= {     lcsCISTPortsEntry 1 }

lcsCISTPortEnable   OBJECT-TYPE
               SYNTAX      Integer32 (0|1)
               MAX-ACCESS  read-write
               STATUS      current
               DESCRIPTION
                   "CIST Port Enable. range: 0-1.
                   0:disable
                   1:enable."
               ::= {     lcsCISTPortsEntry 2 }

lcsCISTPortPathCost   OBJECT-TYPE
               SYNTAX      Integer32 (0..200000000)
               MAX-ACCESS  read-write
               STATUS      current
               DESCRIPTION
                   "CIST Port Path Cost. range: 0-200000000. 0 is Auto."
               ::= {     lcsCISTPortsEntry 3 }

lcsCISTPortPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     lcsCISTPortsEntry 4 }

lcsCISTPortAdminEdge   OBJECT-TYPE
               SYNTAX      Integer32 (0|1)
               MAX-ACCESS  read-write
               STATUS      current
               DESCRIPTION
                   "CIST Port Admin Edge. range: 0-1.
                   0:Non-Edge
                   1:Edge."
               ::= {     lcsCISTPortsEntry 5 }

lcsCISTPortAutoEdge   OBJECT-TYPE
               SYNTAX      Integer32 (0|1)
               MAX-ACCESS  read-write
               STATUS      current
               DESCRIPTION
                   "CIST Port Auto Edge. range: 0-1.
                   0:disable
                   1:enable."
               ::= {     lcsCISTPortsEntry 6 }

lcsCISTPortrestrictedRole   OBJECT-TYPE
               SYNTAX      Integer32 (0|1)
               MAX-ACCESS  read-write
               STATUS      current
               DESCRIPTION
                   "CIST Port restricted Role. range: 0-1.
                   0:disable
                   1:enable."
               ::= {     lcsCISTPortsEntry 7 }

lcsCISTPortrestrictedTcn   OBJECT-TYPE
               SYNTAX      Integer32 (0|1)
               MAX-ACCESS  read-write
               STATUS      current
               DESCRIPTION
                   "CIST Port restricted Tcn. range: 0-1.
                   0:disable
                   1:enable."
               ::= {     lcsCISTPortsEntry 8 }

lcsCISTPortbpduGuard   OBJECT-TYPE
               SYNTAX      Integer32 (0|1)
               MAX-ACCESS  read-write
               STATUS      current
               DESCRIPTION
                   "CIST Port bpdu Guard. range: 0-1.
                   0:disable
                   1:enable."
               ::= {     lcsCISTPortsEntry 9 }

lcsCISTPortPointToPoint   OBJECT-TYPE
               SYNTAX      Integer32 (0..2)
               MAX-ACCESS  read-write
               STATUS      current
               DESCRIPTION
                   "CIST Port Point To Point. range: 0-2.
                   0:Forced True
                   1:Forced False.
                   2:Auto"
               ::= {     lcsCISTPortsEntry 10 }

lcsCISTPortRootGuard   OBJECT-TYPE
               SYNTAX      Integer32 (0|1)
               MAX-ACCESS  read-write
               STATUS      current
               DESCRIPTION
                   "CIST Port root guard. range: 0-1.
                   0:disable
                   1:enable."
               ::= {     lcsCISTPortsEntry 11 }
               
lcsMSTIPorts                          OBJECT IDENTIFIER ::= { lcsSpanningTree 6 }


lcsMSTIAggregatedPortsTable OBJECT-TYPE
   SYNTAX      SEQUENCE OF LCSMSTIAggregatedPortsEntry
   MAX-ACCESS  not-accessible
   STATUS      current
   DESCRIPTION
       "A table of MSTI ports."
    ::= { lcsMSTIPorts 1 }

lcsMSTIAggregatedPortsEntry OBJECT-TYPE
    SYNTAX        LCSMSTIAggregatedPortsEntry
    MAX-ACCESS    not-accessible
    STATUS        current
    DESCRIPTION
        "An entry in the MSTI ports Table."
    INDEX        { lcsMSTIAggregatedPortsMSTIndex }
    ::= { lcsMSTIAggregatedPortsTable 1 }

LCSMSTIAggregatedPortsEntry ::=
    SEQUENCE {
        lcsMSTIAggregatedPortsMSTIndex                        Integer32,
        lcsMSTIAggregatedPortsPathCost                        Integer32,
        lcsMSTIAggregatedPortsPortPriority                    Integer32
    }

lcsMSTIAggregatedPortsMSTIndex OBJECT-TYPE
   SYNTAX      Integer32 (1..7)
   MAX-ACCESS  not-accessible
   STATUS      current
   DESCRIPTION
       "MST index, range:1-7"
   ::= {lcsMSTIAggregatedPortsEntry 1 }

lcsMSTIAggregatedPortsPathCost   OBJECT-TYPE
   SYNTAX      Integer32 (0..200000000)
   MAX-ACCESS  read-write
   STATUS      current
   DESCRIPTION
       "MST Path Cost. range: 0-200000000. 0 is Auto."
   ::= {lcsMSTIAggregatedPortsEntry 3 }

lcsMSTIAggregatedPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {lcsMSTIAggregatedPortsEntry 4 }


lcsMSTIPortsTable OBJECT-TYPE
   SYNTAX      SEQUENCE OF LCSMSTIPortsEntry
   MAX-ACCESS  not-accessible
   STATUS      current
   DESCRIPTION
       "A table of MSTI ports."
    ::= { lcsMSTIPorts 2 }

lcsMSTIPortsEntry OBJECT-TYPE
    SYNTAX        LCSMSTIPortsEntry
    MAX-ACCESS    not-accessible
    STATUS        current
    DESCRIPTION
        "An entry in the MSTI ports Table."
    INDEX        { lcsMSTIPortsMSTIndex, lcsMSTIPortsPortIndex }
    ::= { lcsMSTIPortsTable 1 }

LCSMSTIPortsEntry ::=
    SEQUENCE {
        lcsMSTIPortsMSTIndex                        Integer32,
        lcsMSTIPortsPortIndex                       Integer32,
        lcsMSTIPortsPathCost                        Integer32,
        lcsMSTIPortsPortPriority                    Integer32
    }

lcsMSTIPortsMSTIndex OBJECT-TYPE
   SYNTAX      Integer32 (1..7)
   MAX-ACCESS  not-accessible
   STATUS      current
   DESCRIPTION
       "MST index, range:1-7"
   ::= {lcsMSTIPortsEntry 1 }

lcsMSTIPortsPortIndex OBJECT-TYPE
   SYNTAX      Integer32 (1..53)
   MAX-ACCESS  not-accessible
   STATUS      current
   DESCRIPTION
       "Port index, range 1-53, 53 is Aggregated Ports Configuration."
   ::= {lcsMSTIPortsEntry 2 }

lcsMSTIPortsPathCost   OBJECT-TYPE
   SYNTAX      Integer32 (0..200000000)
   MAX-ACCESS  read-write
   STATUS      current
   DESCRIPTION
       "MST Path Cost. range: 0-200000000. 0 is Auto."
   ::= {lcsMSTIPortsEntry 3 }

lcsMSTIPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {lcsMSTIPortsEntry 4 }

-- =======================================================================================================================
lcsPrivateVLANs                         OBJECT IDENTIFIER ::= { lcsConfiguration 19 }

lcsPVLANMembershipTable  OBJECT-TYPE
   SYNTAX      SEQUENCE OF LCSPVLANMembershipEntry
   MAX-ACCESS  not-accessible
   STATUS      current
   DESCRIPTION
       "A table of Private VLAN Membership."
 ::= { lcsPrivateVLANs 1 }

lcsPVLANMembershipEntry OBJECT-TYPE
    SYNTAX        LCSPVLANMembershipEntry
    MAX-ACCESS    not-accessible
    STATUS        current
    DESCRIPTION
        "An entry in the private VLAN table."
    INDEX        { lcsPVLANMembershipIndex }
    ::= { lcsPVLANMembershipTable 1 }

LCSPVLANMembershipEntry ::=
    SEQUENCE {
        lcsPVLANMembershipIndex                    Integer32,
        lcsPVLANID                                 Integer32,
        lcsPVLANMembers                            DisplayString,
        lcsPVLANRowStatus                          RowStatus
    }

lcsPVLANMembershipIndex OBJECT-TYPE
   SYNTAX      Integer32 (1..28)
   MAX-ACCESS  not-accessible
   STATUS      current
   DESCRIPTION
       "PVLAN membership index. Range:1-28."
   ::= {lcsPVLANMembershipEntry 1 }

lcsPVLANID OBJECT-TYPE
   SYNTAX      Integer32 (1..28)
   MAX-ACCESS  read-create
   STATUS      current
   DESCRIPTION
       "PVLAN ID. Range:1-28."
   ::= {lcsPVLANMembershipEntry 2 }

lcsPVLANMembers OBJECT-TYPE
   SYNTAX      DisplayString
   MAX-ACCESS  read-create
   STATUS      current
   DESCRIPTION
       "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
   ::= {lcsPVLANMembershipEntry 3 }

lcsPVLANRowStatus OBJECT-TYPE
   SYNTAX      RowStatus
   MAX-ACCESS  read-create
   STATUS      current
   DESCRIPTION
       "PVLAN Row Status."
   ::= {lcsPVLANMembershipEntry 4 }

lcsPVLANPortIsolationTable  OBJECT-TYPE
   SYNTAX      SEQUENCE OF LCSPVLANPortIsolationEntry
   MAX-ACCESS  not-accessible
   STATUS      current
   DESCRIPTION
       "A table of Private VLAN Port Isolation."
 ::= { lcsPrivateVLANs 2 }

lcsPVLANPortIsolationEntry OBJECT-TYPE
    SYNTAX        LCSPVLANPortIsolationEntry
    MAX-ACCESS    not-accessible
    STATUS        current
    DESCRIPTION
        "An entry in the private VLAN table."
    INDEX        { lcsPVLANPortIsolationIndex }
    ::= { lcsPVLANPortIsolationTable 1 }

LCSPVLANPortIsolationEntry ::=
    SEQUENCE {
        lcsPVLANPortIsolationIndex                 Integer32,
        lcsPVLANPortIsolationPortMembers           Integer32
    }

lcsPVLANPortIsolationIndex OBJECT-TYPE
   SYNTAX      Integer32 (1..28)
   MAX-ACCESS  not-accessible
   STATUS      current
   DESCRIPTION
       "PVLAN Port Isolation Index. Range:1-28."
   ::= {lcsPVLANPortIsolationEntry 1 }

lcsPVLANPortIsolationPortMembers OBJECT-TYPE
   SYNTAX      Integer32 (0|1)
   MAX-ACCESS  read-write
   STATUS      current
   DESCRIPTION
       "PVLAN Port Isolation Port Members enable/disable. Range:0-1.
       1:Port Isolation enable  on that port.
       0:Port Isolation disable on that port."
   ::= {lcsPVLANPortIsolationEntry 2 }

-- =======================================================================================================================


lcssFlow                        OBJECT IDENTIFIER ::= { lcsConfiguration 20 }

      lcssFlowVersion OBJECT-TYPE
              SYNTAX      SnmpAdminString
              MAX-ACCESS  read-only
              STATUS      current
              DESCRIPTION "Uniquely identifies the version and implementation of this MIB. The version string must have the following structure: <MIB Version>;<Organization>;<Software Revision> where: <MIB Version>  must be '1.3', the version of this MIB.
                    <Organization> the name of the organization responsible for the agent implementation. <Revision>     the specific software build of this agent.
                 As an example, the string '1.3;InMon Corp.;2.1.1' indicates that this agent implements version '1.2' of the SFLOW MIB, that
                 it was developed by 'InMon Corp.' and that the software build is '2.1.1'.
                 The MIB Version will change with each revision of the SFLOW MIB.
                 Management entities must check the MIB Version and not attempt to manage agents with MIB Versions greater than that for which
                 they were designed.
                 Note: The sFlow Datagram Format has an independent version number which may change independently from <MIB Version>.
                       <MIB Version> applies to the structure and semantics of the SFLOW MIB only." DEFVAL { "1.3;;" }
              ::= { lcssFlow 1 }

      lcssFlowAgentAddressType OBJECT-TYPE
              SYNTAX      InetAddressType
              MAX-ACCESS  read-only
              STATUS      current
              DESCRIPTION "The address type of the address associated with this agent. Only ipv4 and ipv6 types are supported. ipv4:1, ipv6:2."
              ::= { lcssFlow 2 }

      lcssFlowAgentAddress OBJECT-TYPE
              SYNTAX      IpAddress
              MAX-ACCESS  read-write
              STATUS      current
              DESCRIPTION "The IP address associated with this agent. In the case of a multi-homed agent, this should be the loopback address of the
                 agent. The sFlowAgent address must provide SNMP connectivity to the agent. The address should be an invariant that does not
                 change as interfaces are reconfigured, enabled, disabled, added or removed. A manager should be able to use the
                 sFlowAgentAddress as a unique key that will identify this agent over extended periods of time so that a history can
                 be maintained."
              ::= { lcssFlow 3 }
      --
      -- Receiver Table
      --
      lcssFlowRcvrTable OBJECT-TYPE
              SYNTAX      SEQUENCE OF LCSSFlowRcvrEntry
              MAX-ACCESS  not-accessible
              STATUS      current
              DESCRIPTION "A table of the receivers of sFlow information."
              ::= { lcssFlow 4 }

      lcssFlowRcvrEntry OBJECT-TYPE
              SYNTAX LCSSFlowRcvrEntry
              MAX-ACCESS  not-accessible
              STATUS      current
              DESCRIPTION "Attributes of an sFlow Receiver."
              INDEX { lcssFlowRcvrIndex }
              ::= { lcssFlowRcvrTable 1 }

      LCSSFlowRcvrEntry ::= SEQUENCE {
              lcssFlowRcvrIndex                    Integer32,
              lcssFlowRcvrOwner                    OwnerString,
              lcssFlowRcvrTimeout                  Integer32,
              lcssFlowRcvrMaximumDatagramSize      Integer32,
              lcssFlowRcvrAddressType              InetAddressType,
              lcssFlowRcvrAddress                  IpAddress,
              lcssFlowRcvrPort                     Integer32,
              lcssFlowRcvrDatagramVersion          Integer32,
              lcssFlowRcvrMode                     Integer32
              }

      lcssFlowRcvrIndex OBJECT-TYPE
              SYNTAX      Integer32 (1..65535)
              MAX-ACCESS  not-accessible
              STATUS      current
              DESCRIPTION "Index into sFlowReceiverTable."
              ::= { lcssFlowRcvrEntry 1 }

      lcssFlowRcvrOwner OBJECT-TYPE
              SYNTAX      OwnerString
              MAX-ACCESS  read-write
              STATUS      current
              DESCRIPTION "The entity making use of this sFlowRcvrTable entry. The empty string indicates that the entry is currently unclaimed.
                 An entity wishing to claim an sFlowRcvrTable entry must ensure that the entry is unclaimed before trying to claim it.
                 The entry is claimed by setting the owner string. The entry must be claimed before any changes can be made to other sampler
                 objects.
                 In order to avoid a race condition, the entity taking control of the sampler must set both the owner and a value for
                 sFlowRcvrTimeout in the same SNMP set request.
                 When a management entity is finished using the sampler, it should set the value of sFlowRcvrOwner back to unclaimed.
                 The agent must restore all other entities this row to their default values when the owner is set to unclaimed. It must
                 also free all other resources associated with this sFlowRcvrTable entry.
                 This mechanism provides no enforcement and relies on the cooperation of management entities in order to ensure that
                 competition for a receiver entry is fairly resolved." DEFVAL { "" }
              ::= { lcssFlowRcvrEntry 2 }

      lcssFlowRcvrTimeout OBJECT-TYPE
              SYNTAX      Integer32
              MAX-ACCESS  read-write
              STATUS      current
              DESCRIPTION "The time (in seconds) remaining before the sampler is released and stops sampling. When set, the owner establishes control
                 for the specified period. When read, the remaining time in the interval is returned.
                 A management entity wanting to maintain control of the sampler is responsible for setting a new value before the old one
                 expires.
                 When the interval expires, the agent is responsible for restoring all other entities in this row to their default
                 values. It must also free all other resources associated with this sFlowRcvrTable entry." DEFVAL { 0 }
              ::= { lcssFlowRcvrEntry 3 }

      lcssFlowRcvrMaximumDatagramSize OBJECT-TYPE
              SYNTAX      Integer32
              MAX-ACCESS  read-write
              STATUS      current
              DESCRIPTION "The maximum number of data bytes that can be sent in a single sample datagram. The manager should set this value to avoid fragmentation of the sFlow datagrams." DEFVAL { 1400 }
              ::= { lcssFlowRcvrEntry 4 }

      lcssFlowRcvrAddressType OBJECT-TYPE
              SYNTAX      InetAddressType
              MAX-ACCESS  read-write
              STATUS      current
              DESCRIPTION "The type of sFlowRcvrCollectorAddress." DEFVAL { ipv4 }
              ::= { lcssFlowRcvrEntry 5 }

      lcssFlowRcvrAddress OBJECT-TYPE
              SYNTAX      IpAddress
              MAX-ACCESS  read-write
              STATUS      current
              DESCRIPTION "The IP address of the sFlow collector. If set to 0.0.0.0 not sFlow datagrams will be sent." DEFVAL { '00000000'h }  -- 0.0.0.0
              ::= { lcssFlowRcvrEntry 6 }

      lcssFlowRcvrPort OBJECT-TYPE
              SYNTAX      Integer32
              MAX-ACCESS  read-write
              STATUS      current
              DESCRIPTION "The destination port for sFlow datagrams." DEFVAL { 6343 }
              ::= { lcssFlowRcvrEntry 7 }

      lcssFlowRcvrDatagramVersion OBJECT-TYPE
              SYNTAX      Integer32
              MAX-ACCESS  read-write
              STATUS      current
              DESCRIPTION "The version of sFlow datagrams that should be sent.
                 When set to a value not support by the agent, the agent should adjust the value to the highest supported value less than the
                 requested value, or return an SNMP bad value error if no such value exists." DEFVAL { 5 }
              ::= { lcssFlowRcvrEntry 8 }

      lcssFlowRcvrMode OBJECT-TYPE
              SYNTAX      Integer32
              MAX-ACCESS  read-write
              STATUS      current
              DESCRIPTION "sFlow mode.
                          0:Disable
                          1:Enable" DEFVAL { 0 }
              ::= { lcssFlowRcvrEntry 9 } 

      --
      -- Flow Sampling Table
      --
      lcssFlowFsTable OBJECT-TYPE
              SYNTAX      SEQUENCE OF LCSSFlowFsEntry
              MAX-ACCESS  not-accessible
              STATUS      current
              DESCRIPTION "A table of the flow samplers within a device."
              ::= { lcssFlow 5 }

      lcssFlowFsEntry OBJECT-TYPE
              SYNTAX      LCSSFlowFsEntry
              MAX-ACCESS  not-accessible
              STATUS      current
              DESCRIPTION "Attributes of a flow sampler."
              INDEX { lcssFlowFsDataSource, lcssFlowFsInstance }
              ::= { lcssFlowFsTable 1 }

      LCSSFlowFsEntry ::= SEQUENCE {
              lcssFlowFsDataSource               Integer32,
              lcssFlowFsInstance                 Integer32,
              lcssFlowFsReceiver                 Integer32,
              lcssFlowFsPacketSamplingRate       Integer32,
              lcssFlowFsMaximumHeaderSize        Integer32,
              lcssFlowFsType                     Integer32
              }

      lcssFlowFsDataSource OBJECT-TYPE
              SYNTAX      Integer32 (1..65535)
              MAX-ACCESS  not-accessible
              STATUS      current
              DESCRIPTION "sFlowDataSource for this flow sampler."
              ::= { lcssFlowFsEntry 1 }

      lcssFlowFsInstance OBJECT-TYPE
              SYNTAX      Integer32 (1..65535)
              MAX-ACCESS  not-accessible
              STATUS      current
              DESCRIPTION "The sFlow instance for this flow sampler."
              ::= { lcssFlowFsEntry 2 }

      lcssFlowFsReceiver OBJECT-TYPE
              SYNTAX      Integer32
              MAX-ACCESS  read-write
              STATUS      current
              DESCRIPTION "The SFlowReceiver for this flow sampler." DEFVAL { 0 }
              ::= { lcssFlowFsEntry 3 }

      lcssFlowFsPacketSamplingRate OBJECT-TYPE
              SYNTAX      Integer32
              MAX-ACCESS  read-write
              STATUS      current
              DESCRIPTION "The statistical sampling rate for packet sampling from this source.
                 Set to N to sample 1/Nth of the packets in the monitored flows. An agent should choose its own algorithm to introduce variance
                 into the sampling so that exactly every Nth packet is not counted. A sampling rate of 1 counts all packets. A sampling
                 rate of 0 disables sampling.
                 The agent is permitted to have minimum and maximum allowable values for the sampling rate. A minimum rate lets the agent
                 designer set an upper bound on the overhead associated with sampling, and a maximum rate may be the result of hardware
                 restrictions (such as counter size). In addition not all values between the maximum and minimum may be realizable as the
                 sampling rate (again because of implementation considerations).
                 When the sampling rate is set the agent is free to adjust the value so that it lies between the maximum and minimum values
                 and has the closest achievable value.
                 When read, the agent must return the actual sampling rate it will be using (after the adjustments previously described). The
                 sampling algorithm must converge so that over time the number of packets sampled approaches 1/Nth of the total number of
                 packets in the monitored flows." DEFVAL { 0 }
              ::= { lcssFlowFsEntry 4 }

      lcssFlowFsMaximumHeaderSize OBJECT-TYPE
              SYNTAX      Integer32
              MAX-ACCESS  read-write
              STATUS      current
              DESCRIPTION "The maximum number of bytes that should be copied from a sampled packet. The agent may have an internal maximum and
                 minimum permissible sizes. If an attempt is made to set this value outside the permissible range then the agent should
                 adjust the value to the closest permissible value." DEFVAL { 128 }
              ::= { lcssFlowFsEntry 5 }

      lcssFlowFsType OBJECT-TYPE
              SYNTAX      Integer32
              MAX-ACCESS  read-write
              STATUS      current
              DESCRIPTION "Flow Sample Type.
              1:Rx
              2:Tx
              3:All."
              DEFVAL { 2 }
              ::= { lcssFlowFsEntry 6 }
      --
      -- Counter Polling Table
      --
      lcssFlowCpTable OBJECT-TYPE
              SYNTAX      SEQUENCE OF LCSSFlowCpEntry
              MAX-ACCESS  not-accessible
              STATUS      current
              DESCRIPTION "A table of the counter pollers within a device."
              ::= { lcssFlow 6 }

      lcssFlowCpEntry OBJECT-TYPE
              SYNTAX      LCSSFlowCpEntry
              MAX-ACCESS  not-accessible
              STATUS      current
              DESCRIPTION "Attributes of a counter poller."
              INDEX { lcssFlowCpDataSource, lcssFlowCpInstance }
              ::= { lcssFlowCpTable 1 }

      LCSSFlowCpEntry ::= SEQUENCE {
              lcssFlowCpDataSource               Integer32,
              lcssFlowCpInstance                 Integer32,
              lcssFlowCpReceiver                 Integer32,
              lcssFlowCpInterval                 Integer32
              }

      lcssFlowCpDataSource OBJECT-TYPE
              SYNTAX      Integer32 (1..65535)
              MAX-ACCESS  not-accessible
              STATUS      current
              DESCRIPTION "Identifies the source of the data for the counter poller."
              ::= { lcssFlowCpEntry 1 }

      lcssFlowCpInstance OBJECT-TYPE
              SYNTAX      Integer32 (1..65535)
              MAX-ACCESS  not-accessible
              STATUS      current
              DESCRIPTION "The sFlowInstance for this counter poller."
              ::= { lcssFlowCpEntry 2 }

      lcssFlowCpReceiver OBJECT-TYPE
              SYNTAX      Integer32
              MAX-ACCESS  read-write
              STATUS      current
              DESCRIPTION "The SFlowReciever associated with this counter poller." DEFVAL { 0 }
              ::= { lcssFlowCpEntry 3 }

      lcssFlowCpInterval OBJECT-TYPE
              SYNTAX      Integer32
              MAX-ACCESS  read-write
              STATUS      current
              DESCRIPTION "The maximum number of seconds between successive samples of the counters associated with this data source. A sampling interval
                 of 0 disables counter sampling.
                 The agent is permitted to have minimum and maximum allowable values for the counter polling interval. A minimum interval
                 lets the agent designer set an upper bound on the overhead associated with polling, and a maximum interval may be the
                 result of implementation restrictions (such as counter size). In addition not all values between the maximum and minimum may
                 be realizable as the sampling interval (again because of implementation considerations).
                 When the sampling rate is set the agent is free to adjust the value so that it lies between the maximum and minimum values
                 and has the closest achievable value.
                 When read, the agent must return the actual sampling interval it will be using (after the adjustments previously described).
                 The sampling algorithm must converge so that over time the number of packets sampled approaches 1/Nth of the total number
                 of packets in the monitored flows." DEFVAL { 0 }
              ::= { lcssFlowCpEntry 4 }

lcsLLDP                  OBJECT IDENTIFIER ::= { lcsConfiguration 21 }

    lcsLLDPConfTable OBJECT-TYPE
               SYNTAX      SEQUENCE OF     LCSLLDPConfEntry
               MAX-ACCESS  not-accessible
               STATUS      current
               DESCRIPTION
                   " "
               ::= {     lcsLLDP 1 }

    lcsLLDPConfEntry OBJECT-TYPE
               SYNTAX          LCSLLDPConfEntry
               MAX-ACCESS  not-accessible
               STATUS      current
               DESCRIPTION
                   " "
               INDEX    {    lcsLLDPIndex  }
               ::= {     lcsLLDPConfTable 1 }

    LCSLLDPConfEntry             ::= SEQUENCE {
         lcsLLDPIndex        Integer32,
         lcsLLDPMode         Integer32,
         lcsLLDPCDPAware     Integer32,
         lcsLLDPTrap         Integer32,
         lcsLLDPPortDescr    Integer32,
         lcsLLDPSysName      Integer32,
         lcsLLDPSysDescr     Integer32,
         lcsLLDPSysCapa      Integer32,
         lcsLLDPMgmtAddr     Integer32
    }

    lcsLLDPIndex OBJECT-TYPE
               SYNTAX      Integer32 (1..65535)
               MAX-ACCESS  read-write
               STATUS      current
               DESCRIPTION
                   "LLDP configuration index."
               ::= {     lcsLLDPConfEntry 1 }

    lcsLLDPMode OBJECT-TYPE
               SYNTAX      Integer32
               MAX-ACCESS  read-write
               STATUS      current
               DESCRIPTION
                   "0:Disable
           1:Tx only
           2:Rx only
           3:Enabled"
               ::= {     lcsLLDPConfEntry 2 }

    lcsLLDPCDPAware OBJECT-TYPE
               SYNTAX      Integer32
               MAX-ACCESS  read-write
               STATUS      current
               DESCRIPTION
                   "0:Disable
           1:Enable"
               ::= {     lcsLLDPConfEntry 3 }
               
    lcsLLDPTrap OBJECT-TYPE
               SYNTAX      Integer32
               MAX-ACCESS  read-write
               STATUS      current
               DESCRIPTION
               "0:Disable
                1:Enable"
               ::= {     lcsLLDPConfEntry 4 }               

    lcsLLDPPortDescr OBJECT-TYPE
               SYNTAX      Integer32
               MAX-ACCESS  read-write
               STATUS      current
               DESCRIPTION
                   "0:Disable
           1:Enable"
               ::= {     lcsLLDPConfEntry 5 }

    lcsLLDPSysName OBJECT-TYPE
               SYNTAX      Integer32
               MAX-ACCESS  read-write
               STATUS      current
               DESCRIPTION
                   "0:Disable
           1:Enable"
               ::= {     lcsLLDPConfEntry 6 }

    lcsLLDPSysDescr OBJECT-TYPE
               SYNTAX      Integer32
               MAX-ACCESS  read-write
               STATUS      current
               DESCRIPTION
                   "0:Disable
           1:Enable"
               ::= {     lcsLLDPConfEntry 7 }

    lcsLLDPSysCapa OBJECT-TYPE
               SYNTAX      Integer32
               MAX-ACCESS  read-write
               STATUS      current
               DESCRIPTION
                   "0:Disable
           1:Enable"
               ::= {     lcsLLDPConfEntry 8 }

    lcsLLDPMgmtAddr OBJECT-TYPE
               SYNTAX      Integer32
               MAX-ACCESS  read-write
               STATUS      current
               DESCRIPTION
                   "0:Disable
           1:Enable"
               ::= {     lcsLLDPConfEntry 9 }

lcsLLDPMEDCoordinatesLocation                          OBJECT IDENTIFIER ::= { lcsLLDP 2 }   
               
lcsLLDPMEDLatitude   OBJECT-TYPE
   SYNTAX      DisplayString
   MAX-ACCESS  read-write
   STATUS      current
   DESCRIPTION
       "Latitude SHOULD be normalized to within 0-90 degrees with a maximum of 4 digits."
   ::= { lcsLLDPMEDCoordinatesLocation 2 }
               
lcsLLDPMEDLatitudeDirection OBJECT-TYPE
   SYNTAX      Integer32(0|1)
   MAX-ACCESS  read-write
   STATUS      current
   DESCRIPTION
       "0:North 
        1:South"
   ::= { lcsLLDPMEDCoordinatesLocation 3 }
              
lcsLLDPMEDLongitude   OBJECT-TYPE
   SYNTAX      DisplayString
   MAX-ACCESS  read-write
   STATUS      current
   DESCRIPTION
       "Longitude SHOULD be normalized to within 0-180 degrees with a maximum of 4 digits."
   ::= { lcsLLDPMEDCoordinatesLocation 4 }
               
lcsLLDPMEDLongitudeDirection OBJECT-TYPE
   SYNTAX      Integer32(0|1)
   MAX-ACCESS  read-write
   STATUS      current
   DESCRIPTION
       "0:East 
        1:West"
   ::= { lcsLLDPMEDCoordinatesLocation 5 }
              
lcsLLDPMEDAltitude   OBJECT-TYPE
   SYNTAX      DisplayString
   MAX-ACCESS  read-write
   STATUS      current
   DESCRIPTION
       "Altitude SHOULD be normalized to within -2097151.9 to 2097151.9 with a maximum of 1 digits."
   ::= { lcsLLDPMEDCoordinatesLocation 6 }
               
lcsLLDPMEDAltitudeType OBJECT-TYPE
   SYNTAX      Integer32(1|2)
   MAX-ACCESS  read-write
   STATUS      current
   DESCRIPTION
       "1:Meters 
        2:Floors"
   ::= { lcsLLDPMEDCoordinatesLocation 7 } 
   
lcsLLDPMEDMapDatum OBJECT-TYPE
   SYNTAX      Integer32(0..2)
   MAX-ACCESS  read-write
   STATUS      current
   DESCRIPTION
       "The Map Datum is used for the coordinates given in these options:
        1:WGS84
        2:NAD83/NAVD88 
        3:NAD83/MLLW
        "
   ::= { lcsLLDPMEDCoordinatesLocation 8 }    
   
lcsLLDPMEDCivicAddressLocation                          OBJECT IDENTIFIER ::= { lcsLLDP 4 }   

lcsLLDPMEDCivicAddressLocationCountryCode   OBJECT-TYPE
   SYNTAX      DisplayString
   MAX-ACCESS  read-write
   STATUS      current
   DESCRIPTION
       " "
   ::= { lcsLLDPMEDCivicAddressLocation 2 }

lcsLLDPMEDCivicAddressLocationStateProvince   OBJECT-TYPE
   SYNTAX      DisplayString
   MAX-ACCESS  read-write
   STATUS      current
   DESCRIPTION
       " "
   ::= { lcsLLDPMEDCivicAddressLocation 3 }
    
lcsLLDPMEDCivicAddressLocationCounty   OBJECT-TYPE
   SYNTAX      DisplayString
   MAX-ACCESS  read-write
   STATUS      current
   DESCRIPTION
       " "
   ::= { lcsLLDPMEDCivicAddressLocation 4 }
   
lcsLLDPMEDCivicAddressLocationCity   OBJECT-TYPE
   SYNTAX      DisplayString
   MAX-ACCESS  read-write
   STATUS      current
   DESCRIPTION
       " "
   ::= { lcsLLDPMEDCivicAddressLocation 5 }
   
lcsLLDPMEDCivicAddressLocationCityDistrict   OBJECT-TYPE
   SYNTAX      DisplayString
   MAX-ACCESS  read-write
   STATUS      current
   DESCRIPTION
       " "
   ::= { lcsLLDPMEDCivicAddressLocation 6 }
   
lcsLLDPMEDCivicAddressLocationBlockNeighborhood   OBJECT-TYPE
   SYNTAX      DisplayString
   MAX-ACCESS  read-write
   STATUS      current
   DESCRIPTION
       " "
   ::= { lcsLLDPMEDCivicAddressLocation 7 }
   
lcsLLDPMEDCivicAddressLocationStreet   OBJECT-TYPE
   SYNTAX      DisplayString
   MAX-ACCESS  read-write
   STATUS      current
   DESCRIPTION
       " "
   ::= { lcsLLDPMEDCivicAddressLocation 8 }
   
lcsLLDPMEDCivicAddressLocationLeadingStreetDirection   OBJECT-TYPE
   SYNTAX      DisplayString
   MAX-ACCESS  read-write
   STATUS      current
   DESCRIPTION
       " "
   ::= { lcsLLDPMEDCivicAddressLocation 9 }
   
lcsLLDPMEDCivicAddressLocationTrailingStreetSuffix   OBJECT-TYPE
   SYNTAX      DisplayString
   MAX-ACCESS  read-write
   STATUS      current
   DESCRIPTION
       " "
   ::= { lcsLLDPMEDCivicAddressLocation 10 }
   
lcsLLDPMEDCivicAddressLocationStreetSuffix   OBJECT-TYPE
   SYNTAX      DisplayString
   MAX-ACCESS  read-write
   STATUS      current
   DESCRIPTION
       " "
   ::= { lcsLLDPMEDCivicAddressLocation 11 }
   
lcsLLDPMEDCivicAddressLocationHouseNo   OBJECT-TYPE
   SYNTAX      DisplayString
   MAX-ACCESS  read-write
   STATUS      current
   DESCRIPTION
       " "
   ::= { lcsLLDPMEDCivicAddressLocation 12 }
    
lcsLLDPMEDCivicAddressLocationHouseNoSuffix   OBJECT-TYPE
   SYNTAX      DisplayString
   MAX-ACCESS  read-write
   STATUS      current
   DESCRIPTION
       " "
   ::= { lcsLLDPMEDCivicAddressLocation 13 }
    
lcsLLDPMEDCivicAddressLocationLandmark   OBJECT-TYPE
   SYNTAX      DisplayString
   MAX-ACCESS  read-write
   STATUS      current
   DESCRIPTION
       " "
   ::= { lcsLLDPMEDCivicAddressLocation 14 }
   
lcsLLDPMEDCivicAddressLocationAdditionalLocationInfo   OBJECT-TYPE
   SYNTAX      DisplayString
   MAX-ACCESS  read-write
   STATUS      current
   DESCRIPTION
       " "
   ::= { lcsLLDPMEDCivicAddressLocation 15 }
   
lcsLLDPMEDCivicAddressLocationName   OBJECT-TYPE
   SYNTAX      DisplayString
   MAX-ACCESS  read-write
   STATUS      current
   DESCRIPTION
       " "
   ::= { lcsLLDPMEDCivicAddressLocation 16 }
   
lcsLLDPMEDCivicAddressLocationZipCode   OBJECT-TYPE
   SYNTAX      DisplayString
   MAX-ACCESS  read-write
   STATUS      current
   DESCRIPTION
       " "
   ::= { lcsLLDPMEDCivicAddressLocation 17 }
    
lcsLLDPMEDCivicAddressLocationBuilding   OBJECT-TYPE
   SYNTAX      DisplayString
   MAX-ACCESS  read-write
   STATUS      current
   DESCRIPTION
       " "
   ::= { lcsLLDPMEDCivicAddressLocation 18 }
   
lcsLLDPMEDCivicAddressLocationApartment   OBJECT-TYPE
   SYNTAX      DisplayString
   MAX-ACCESS  read-write
   STATUS      current
   DESCRIPTION
       " "
   ::= { lcsLLDPMEDCivicAddressLocation 19 }   
   
lcsLLDPMEDCivicAddressLocationFloor   OBJECT-TYPE
   SYNTAX      DisplayString
   MAX-ACCESS  read-write
   STATUS      current
   DESCRIPTION
       " "
   ::= { lcsLLDPMEDCivicAddressLocation 20 } 
   
lcsLLDPMEDCivicAddressLocationRoomNo   OBJECT-TYPE
   SYNTAX      DisplayString
   MAX-ACCESS  read-write
   STATUS      current
   DESCRIPTION
       " "
   ::= { lcsLLDPMEDCivicAddressLocation 21 }    
   
lcsLLDPMEDCivicAddressLocationPlaceType   OBJECT-TYPE
   SYNTAX      DisplayString
   MAX-ACCESS  read-write
   STATUS      current
   DESCRIPTION
       " "
   ::= { lcsLLDPMEDCivicAddressLocation 22 }     
   
lcsLLDPMEDCivicAddressLocationPostalCommunityName   OBJECT-TYPE
   SYNTAX      DisplayString
   MAX-ACCESS  read-write
   STATUS      current
   DESCRIPTION
       " "
   ::= { lcsLLDPMEDCivicAddressLocation 23 }    

lcsLLDPMEDCivicAddressLocationPOBox   OBJECT-TYPE
   SYNTAX      DisplayString
   MAX-ACCESS  read-write
   STATUS      current
   DESCRIPTION
       " "
   ::= { lcsLLDPMEDCivicAddressLocation 24 }     
   
lcsLLDPMEDCivicAddressLocationAdditionalCode   OBJECT-TYPE
   SYNTAX      DisplayString
   MAX-ACCESS  read-write
   STATUS      current
   DESCRIPTION
       " "
   ::= { lcsLLDPMEDCivicAddressLocation 25 }

   
lcsLLDPMEDPoliciesTable OBJECT-TYPE
   SYNTAX      SEQUENCE OF LCSLLDPMEDPoliciesEntry
   MAX-ACCESS  not-accessible
   STATUS      current
   DESCRIPTION
       " "
   ::= { lcsLLDP 5 }

lcsLLDPMEDPoliciesEntry OBJECT-TYPE
   SYNTAX      LCSLLDPMEDPoliciesEntry
   MAX-ACCESS  not-accessible
   STATUS      current
   DESCRIPTION
       " "
   INDEX    { lcsLLDPMEDPoliciesIndex  }
   ::= { lcsLLDPMEDPoliciesTable 1 }
  
LCSLLDPMEDPoliciesEntry ::= SEQUENCE {
   lcsLLDPMEDPoliciesIndex            Integer32,
   lcsLLDPMEDPoliciesPolicyID         Integer32,
   lcsLLDPMEDPoliciesApplicationType  Integer32,
   lcsLLDPMEDPoliciesTag              Integer32,
   lcsLLDPMEDPoliciesVLANID           Integer32,
   lcsLLDPMEDPoliciesL2Priority       Integer32,
   lcsLLDPMEDPoliciesDSCP             Integer32,
   lcsLLDPMEDPoliciesRowStatus        RowStatus
}

lcsLLDPMEDPoliciesIndex OBJECT-TYPE
   SYNTAX      Integer32 (1..65535)
   MAX-ACCESS  not-accessible
   STATUS      current
   DESCRIPTION
       "Index"
   ::= { lcsLLDPMEDPoliciesEntry 1 }

lcsLLDPMEDPoliciesPolicyID OBJECT-TYPE
   SYNTAX      Integer32
   MAX-ACCESS  read-only
   STATUS      current
   DESCRIPTION
       " "
   ::= { lcsLLDPMEDPoliciesEntry 2 }
               
lcsLLDPMEDPoliciesApplicationType OBJECT-TYPE
   SYNTAX      Integer32 (1..8)
   MAX-ACCESS  read-write
   STATUS      current
   DESCRIPTION
       "1:Voice
        2:Voice Signalling
        3:Guest Voice
        4:Guest Voice Signalling
        5:Softphone Voice
        6:Video Conferencing
        7:Streaming Video 
        8:Video Signalling"
   ::= { lcsLLDPMEDPoliciesEntry 3 }
   
lcsLLDPMEDPoliciesTag OBJECT-TYPE
   SYNTAX      Integer32 (0|1)
   MAX-ACCESS  read-write
   STATUS      current
   DESCRIPTION
       "0:Untagged
        1:Tagged"
   ::= { lcsLLDPMEDPoliciesEntry 4 }
   
lcsLLDPMEDPoliciesVLANID OBJECT-TYPE
   SYNTAX      Integer32 (1..4094)
   MAX-ACCESS  read-write
   STATUS      current
   DESCRIPTION
       "Range:1-4094"
   ::= { lcsLLDPMEDPoliciesEntry 5 }

lcsLLDPMEDPoliciesL2Priority OBJECT-TYPE
   SYNTAX      Integer32 (0..7)
   MAX-ACCESS  read-write
   STATUS      current
   DESCRIPTION
       "Range:0-7"
   ::= { lcsLLDPMEDPoliciesEntry 6 }
   
lcsLLDPMEDPoliciesDSCP OBJECT-TYPE
   SYNTAX      Integer32 (0..63)
   MAX-ACCESS  read-write
   STATUS      current
   DESCRIPTION
       "Range:0-63"
   ::= { lcsLLDPMEDPoliciesEntry 7 }    
   
lcsLLDPMEDPoliciesRowStatus OBJECT-TYPE
   SYNTAX      RowStatus
   MAX-ACCESS  read-create
   STATUS      current
   DESCRIPTION
       "Row Status."
   ::= { lcsLLDPMEDPoliciesEntry 8 }
    
lcsLLDPMEDPolicyPortConfTable OBJECT-TYPE
   SYNTAX      SEQUENCE OF LCSLLDPMEDPolicyPortConfEntry
   MAX-ACCESS  not-accessible
   STATUS      current
   DESCRIPTION
       " "
   ::= { lcsLLDP 6 }

lcsLLDPMEDPolicyPortConfEntry OBJECT-TYPE
   SYNTAX      LCSLLDPMEDPolicyPortConfEntry
   MAX-ACCESS  not-accessible
   STATUS      current
   DESCRIPTION
       " "
   INDEX    { lcsLLDPMEDPolicyPortConfPort  }
   ::= { lcsLLDPMEDPolicyPortConfTable 1 }

LCSLLDPMEDPolicyPortConfEntry ::= SEQUENCE {
   lcsLLDPMEDPolicyPortConfPort        Integer32,
   lcsLLDPMEDPolicyPortConf            Integer32
}
    
lcsLLDPMEDPolicyPortConfPort OBJECT-TYPE
   SYNTAX      Integer32 (1..65535)
   MAX-ACCESS  not-accessible
   STATUS      current
   DESCRIPTION
       "Index"
   ::= { lcsLLDPMEDPolicyPortConfEntry 1 }

lcsLLDPMEDPolicyPortConf OBJECT-TYPE
   SYNTAX      Integer32 (0|1)
   MAX-ACCESS  read-write
   STATUS      current
   DESCRIPTION
       "0:Disable
        1:Enable"
   ::= { lcsLLDPMEDPolicyPortConfEntry 2 }
    
lcsLLDPMEDFastStartRepeatCount OBJECT-TYPE
   SYNTAX      Integer32 (1..10)
   MAX-ACCESS  read-write
   STATUS      current
   DESCRIPTION
       "Range:1-10"
   ::= { lcsLLDP 7 }
    
lcsLLDPMEDEmergencyCallService OBJECT-TYPE
   SYNTAX      DisplayString
   MAX-ACCESS  read-write
   STATUS      current
   DESCRIPTION
       " "
   ::= { lcsLLDP 8 }
               
lcsUDLD    OBJECT IDENTIFIER ::= { lcsConfiguration 22 }

lcsUDLDPortConfigTable OBJECT-TYPE
   SYNTAX      SEQUENCE OF LCSUDLDPortConfigEntry
   MAX-ACCESS  not-accessible
   STATUS      current
   DESCRIPTION
       " "
   ::= { lcsUDLD 1 }

lcsUDLDPortConfigEntry OBJECT-TYPE
   SYNTAX      LCSUDLDPortConfigEntry
   MAX-ACCESS  not-accessible
   STATUS      current
   DESCRIPTION
       " "
   INDEX    { lcsUDLDPort  }
   ::= { lcsUDLDPortConfigTable 1 }

LCSUDLDPortConfigEntry ::= SEQUENCE {
   lcsUDLDPort                       Integer32,
   lcsUDLDPortMode                   Integer32,
   lcsUDLDPortMessageInterval        Integer32
}

lcsUDLDPort OBJECT-TYPE
   SYNTAX      Integer32 (1..65535)
   MAX-ACCESS  not-accessible
   STATUS      current
   DESCRIPTION
       " "
   ::= { lcsUDLDPortConfigEntry 1 }

lcsUDLDPortMode OBJECT-TYPE
   SYNTAX      Integer32 (0|1|2)
   MAX-ACCESS  read-write
   STATUS      current
   DESCRIPTION
       "default: 0
       0: disable
       1: Normal
       2: Aggressive"
   ::= { lcsUDLDPortConfigEntry 2 }

lcsUDLDPortMessageInterval OBJECT-TYPE
   SYNTAX      Integer32(7..90)
   MAX-ACCESS  read-write
   STATUS      current
   DESCRIPTION
       "default: 7, range: 7-90"
   ::= { lcsUDLDPortConfigEntry 3 }


lcsUDLDPortStatusTable OBJECT-TYPE
   SYNTAX      SEQUENCE OF LCSUDLDPortStatusEntry
   MAX-ACCESS  not-accessible
   STATUS      current
   DESCRIPTION
       " "
   ::= { lcsUDLD 2 }

lcsUDLDPortStatusEntry OBJECT-TYPE
   SYNTAX      LCSUDLDPortStatusEntry
   MAX-ACCESS  not-accessible
   STATUS      current
   DESCRIPTION
       " "
   INDEX    { lcsUDLDPortStatusPort  }
   ::= { lcsUDLDPortStatusTable 1 }

LCSUDLDPortStatusEntry ::= SEQUENCE {
   lcsUDLDPortStatusPort                   Integer32,
   lcsUDLDStatusAdminState                 Integer32,
   lcsUDLDStatusDeviceIDLocal          DisplayString,
   lcsUDLDStatusDeviceNameLocal        DisplayString,
   lcsUDLDStatusBidirectionalState     DisplayString
}

lcsUDLDPortStatusPort OBJECT-TYPE
   SYNTAX      Integer32 (1..65535)
   MAX-ACCESS  not-accessible
   STATUS      current
   DESCRIPTION
       "Port index"
   ::= { lcsUDLDPortStatusEntry 1 }

lcsUDLDStatusAdminState OBJECT-TYPE
   SYNTAX      Integer32
   MAX-ACCESS  read-only
   STATUS      current
   DESCRIPTION
       "0:disable
       1:enable"
   ::= { lcsUDLDPortStatusEntry 2 }

lcsUDLDStatusDeviceIDLocal OBJECT-TYPE
   SYNTAX      DisplayString
   MAX-ACCESS  read-only
   STATUS      current
   DESCRIPTION
       " "
   ::= { lcsUDLDPortStatusEntry 3 }

lcsUDLDStatusDeviceNameLocal OBJECT-TYPE
   SYNTAX      DisplayString
   MAX-ACCESS  read-only
   STATUS      current
   DESCRIPTION
       " "
   ::= { lcsUDLDPortStatusEntry 4 }

lcsUDLDStatusBidirectionalState OBJECT-TYPE
   SYNTAX      DisplayString
   MAX-ACCESS  read-only
   STATUS      current
   DESCRIPTION
       " "
   ::= { lcsUDLDPortStatusEntry 5 }


lcsUDLDStatusPort OBJECT-TYPE
   SYNTAX      Integer32
   MAX-ACCESS  read-write
   STATUS      current
   DESCRIPTION
       "Specify port number for check neighbour status"
   ::= { lcsUDLD 3 }

lcsUDLDPortNeighbourStatusTable OBJECT-TYPE
   SYNTAX      SEQUENCE OF LCSUDLDPortNeighbourStatusEntry
   MAX-ACCESS  not-accessible
   STATUS      current
   DESCRIPTION
       " "
   ::= { lcsUDLD 4 }

lcsUDLDPortNeighbourStatusEntry OBJECT-TYPE
   SYNTAX      LCSUDLDPortNeighbourStatusEntry
   MAX-ACCESS  not-accessible
   STATUS      current
   DESCRIPTION
       " "
   INDEX    { lcsUDLDNeighbourPort  }
   ::= { lcsUDLDPortNeighbourStatusTable 1 }

LCSUDLDPortNeighbourStatusEntry ::= SEQUENCE {
   lcsUDLDNeighbourPort                 Integer32,
   lcsUDLDNeighbourStatusPort           DisplayString,
   lcsUDLDNeighbourStatusDeviceId       DisplayString,
   lcsUDLDNeighbourStatusLinkStatus     DisplayString,
   lcsUDLDNeighbourStatusDeviceName     DisplayString
}

lcsUDLDNeighbourPort OBJECT-TYPE
   SYNTAX      Integer32 (1..65535)
   MAX-ACCESS  not-accessible
   STATUS      current
   DESCRIPTION
       "Index"
   ::= { lcsUDLDPortNeighbourStatusEntry 1 }

lcsUDLDNeighbourStatusPort OBJECT-TYPE
   SYNTAX      DisplayString
   MAX-ACCESS  read-only
   STATUS      current
   DESCRIPTION
       " "
   ::= { lcsUDLDPortNeighbourStatusEntry 2 }

lcsUDLDNeighbourStatusDeviceId OBJECT-TYPE
   SYNTAX      DisplayString
   MAX-ACCESS  read-only
   STATUS      current
   DESCRIPTION
       " "
   ::= { lcsUDLDPortNeighbourStatusEntry 3 }

lcsUDLDNeighbourStatusLinkStatus OBJECT-TYPE
   SYNTAX      DisplayString
   MAX-ACCESS  read-only
   STATUS      current
   DESCRIPTION
       " "
   ::= { lcsUDLDPortNeighbourStatusEntry 4 }

lcsUDLDNeighbourStatusDeviceName OBJECT-TYPE
   SYNTAX      DisplayString
   MAX-ACCESS  read-only
   STATUS      current
   DESCRIPTION
       " "
   ::= { lcsUDLDPortNeighbourStatusEntry 5 }
-- =======================================================================================================================
lcsEPS    OBJECT IDENTIFIER ::= { lcsConfiguration 23 }

lcsEPSTable  OBJECT-TYPE
   SYNTAX      SEQUENCE OF LCSEPSEntry
   MAX-ACCESS  not-accessible
   STATUS      current
   DESCRIPTION
       "A table of EPS."
 ::= { lcsEPS 1 }

lcsEPSEntry OBJECT-TYPE
    SYNTAX        LCSEPSEntry
    MAX-ACCESS    not-accessible
    STATUS        current
    DESCRIPTION
        ""
    INDEX        { lcsEPSIndex }
    ::= { lcsEPSTable 1 }

LCSEPSEntry ::=
    SEQUENCE {
        lcsEPSIndex                                Integer32,
        lcsEpsID                                   Integer32,
        lcsEpsDomain                               Integer32,
        lcsEpsArchitecture                         Integer32,
        lcsEpsWFlow                                Integer32,
        lcsEpsPFlow                                Integer32,   
        lcsEpsWSFMEP                               Integer32,       
        lcsEpsPSFMEP                               Integer32,       
        lcsEpsAPSMEP                               Integer32,       
        lcsEpsAlarm                                Integer32,       
        lcsEpsRowStatus                            RowStatus
    }

lcsEPSIndex OBJECT-TYPE
   SYNTAX      Integer32 (1..65535)
   MAX-ACCESS  not-accessible
   STATUS      current
   DESCRIPTION
       "Index"
   ::= { lcsEPSEntry 1 }

lcsEpsID OBJECT-TYPE
   SYNTAX      Integer32 (1..100)
   MAX-ACCESS  read-create
   STATUS      current
   DESCRIPTION
       "EPS ID. Range:1-100."
   ::= {lcsEPSEntry 2 }

lcsEpsDomain OBJECT-TYPE
   SYNTAX      Integer32
   MAX-ACCESS  read-create
   STATUS      current
   DESCRIPTION
       "EPS Domain. Range:0.
       0:Domain is Port"
   ::= {lcsEPSEntry 3 }   
   
lcsEpsArchitecture OBJECT-TYPE
   SYNTAX      Integer32
   MAX-ACCESS  read-create
   STATUS      current
   DESCRIPTION
       "EPS Architecture. Range:0-1.
       0:Architecture is 1+1
       1:Architecture is 1:1"
   ::= {lcsEPSEntry 4 }   
   
lcsEpsWFlow OBJECT-TYPE
   SYNTAX      Integer32
   MAX-ACCESS  read-create
   STATUS      current
   DESCRIPTION
       "The working flow for the EPS."
   ::= {lcsEPSEntry 5 }  

lcsEpsPFlow OBJECT-TYPE
   SYNTAX      Integer32
   MAX-ACCESS  read-create
   STATUS      current
   DESCRIPTION
       "The protecting flow for the EPS"
   ::= {lcsEPSEntry 6 }    
   
lcsEpsWSFMEP OBJECT-TYPE
   SYNTAX      Integer32
   MAX-ACCESS  read-create
   STATUS      current
   DESCRIPTION
       "The working Signal Fail reporting MEP."
   ::= {lcsEPSEntry 7 }     
   
lcsEpsPSFMEP OBJECT-TYPE
   SYNTAX      Integer32
   MAX-ACCESS  read-create
   STATUS      current
   DESCRIPTION
       "The protecting Signal Fail reporting MEP."
   ::= {lcsEPSEntry 8 }        
   
lcsEpsAPSMEP OBJECT-TYPE
   SYNTAX      Integer32
   MAX-ACCESS  read-create
   STATUS      current
   DESCRIPTION
       "The APS PDU handling MEP."
   ::= {lcsEPSEntry 9 }
   
lcsEpsAlarm OBJECT-TYPE
   SYNTAX      Integer32
   MAX-ACCESS  read-only
   STATUS      current
   DESCRIPTION
       "There is an active alarm on the EPS."
   ::= {lcsEPSEntry 10 }  
   
lcsEpsRowStatus OBJECT-TYPE
   SYNTAX      RowStatus
   MAX-ACCESS  read-create
   STATUS      current
   DESCRIPTION
       "EPS Row Status."
   ::= {lcsEPSEntry 11 }
   
lcsEpsConfigInstanceEpsID   OBJECT-TYPE
   SYNTAX      Integer32
   MAX-ACCESS  read-write
   STATUS      current
   DESCRIPTION
       "Specify EPS ID for table uesd."
   ::= {lcsEPS 2 }
   
   
lcsEPSConfigInstanceEntry    OBJECT IDENTIFIER ::= { lcsEPS 3 } 

lcsEpsConfigInstanceProtectionType OBJECT-TYPE
   SYNTAX      Integer32
   MAX-ACCESS  read-write
   STATUS      current
   DESCRIPTION
       "Range:0-1.
       0:Unidirectional: EPS in the two ends can select traffic from different working/protecting flow. This is only possible in case of 1+1.
       1:Bidirectional: EPS in the two ends is selecting traffic from the same working/protecting flow. This requires APS enabled. This is mandatory for 1:1"
   ::= { lcsEPSConfigInstanceEntry 2 }

lcsEpsConfigInstanceAPS OBJECT-TYPE
   SYNTAX      Integer32
   MAX-ACCESS  read-write
   STATUS      current
   DESCRIPTION
       "Range:0-1.
        0:disable
        1:enable
        The Automatic Protection Switching protocol can be enabled/disabled. This is mandatory for 1:1."
   ::= { lcsEPSConfigInstanceEntry 3 }

lcsEpsConfigInstanceRevertive OBJECT-TYPE
   SYNTAX      Integer32
   MAX-ACCESS  read-write
   STATUS      current
   DESCRIPTION
       "Range:0-1.
        0:disable
        1:enable
        The revertive switching to working flow can be enabled/disabled.
        "
   ::= { lcsEPSConfigInstanceEntry 4 }   
   
lcsEpsConfigInstanceWTRTime OBJECT-TYPE
   SYNTAX      Integer32
   MAX-ACCESS  read-write
   STATUS      current
   DESCRIPTION
       "The Wait To Restore timing value to be used in revertive switching. Range is 1 to 720 seconds.
        "
   ::= { lcsEPSConfigInstanceEntry 5 }      
   
lcsEpsConfigInstanceHoldOffTime OBJECT-TYPE
   SYNTAX      Integer32
   MAX-ACCESS  read-write
   STATUS      current
   DESCRIPTION
       "The timing value to be used to make persistent check on Signal Fail before switching. This is in 100 ms. and the max value is 100 (10 sec)."
   ::= { lcsEPSConfigInstanceEntry 6 }     
   
lcsEpsConfigInstanceCommand OBJECT-TYPE
   SYNTAX      Integer32
   MAX-ACCESS  read-write
   STATUS      current
   DESCRIPTION
       "0:None
        1:Clear
        2:Lock Out
        3:Forced switch
        4:Manual switch P
        5:Manual switch W
        6:Exercise
        7:Freeze
        8:Lock Out Local
       "
   ::= { lcsEPSConfigInstanceEntry 7 }     

lcsEpsStatusProtectionState OBJECT-TYPE
   SYNTAX      DisplayString
   MAX-ACCESS  read-only
   STATUS      current
   DESCRIPTION
       "EPS state according to State Transition Tables in G.8031.
       "
   ::= { lcsEPSConfigInstanceEntry 8 }
   
lcsEpsStatusWorkingFlowState OBJECT-TYPE
   SYNTAX      DisplayString
   MAX-ACCESS  read-only
   STATUS      current
   DESCRIPTION
       "OK: State of working flow is ok
        SF: State of working flow is Signal Fail
        SD: State of working flow is Signal Degrade (for future use)
       "
   ::= { lcsEPSConfigInstanceEntry 9 }   
   
lcsEpsStatusProtectingFlowState OBJECT-TYPE
   SYNTAX      DisplayString
   MAX-ACCESS  read-only
   STATUS      current
   DESCRIPTION
       "OK: State of protecting flow is ok
        SF: State of protecting flow is Signal Fail
        SD: State of protecting flow is Signal Degrade (for future use)
       "
   ::= { lcsEPSConfigInstanceEntry 10 }     
   
lcsEpsStatusTransmittedApsRequest OBJECT-TYPE
   SYNTAX      DisplayString
   MAX-ACCESS  read-only
   STATUS      current
   DESCRIPTION
       "The transmitted APS according to State Transition Tables in G.8031.
       "
   ::= { lcsEPSConfigInstanceEntry 11 }     
   
lcsEpsStatusTransmittedApsReSignal OBJECT-TYPE
   SYNTAX      Integer32
   MAX-ACCESS  read-only
   STATUS      current
   DESCRIPTION
       "The transmitted APS according to State Transition Tables in G.8031.
       "
   ::= { lcsEPSConfigInstanceEntry 12 }    
   
lcsEpsStatusTransmittedApsBrSignal OBJECT-TYPE
   SYNTAX      Integer32
   MAX-ACCESS  read-only
   STATUS      current
   DESCRIPTION
       "The transmitted APS according to State Transition Tables in G.8031.
       "
   ::= { lcsEPSConfigInstanceEntry 13 }
   
lcsEpsStatusReceivedApsRequest OBJECT-TYPE
   SYNTAX      DisplayString
   MAX-ACCESS  read-only
   STATUS      current
   DESCRIPTION
       "The received APS according to State Transition Tables in G.8031.
       "
   ::= { lcsEPSConfigInstanceEntry 14 }   
   
lcsEpsStatusReceivedApsReSignal OBJECT-TYPE
   SYNTAX      Integer32
   MAX-ACCESS  read-only
   STATUS      current
   DESCRIPTION
       "The received APS according to State Transition Tables in G.8031.
       "
   ::= { lcsEPSConfigInstanceEntry 15 }      
   
lcsEpsStatusReceivedApsBrSignal OBJECT-TYPE
   SYNTAX      Integer32
   MAX-ACCESS  read-only
   STATUS      current
   DESCRIPTION
       "The received APS according to State Transition Tables in G.8031.
       "
   ::= { lcsEPSConfigInstanceEntry 16 }    

lcsEpsStatusArchitectureMismatch OBJECT-TYPE
   SYNTAX      DisplayString
   MAX-ACCESS  read-only
   STATUS      current
   DESCRIPTION
       "The architecture indicated in the received APS does not match the locally configured.
       "
   ::= { lcsEPSConfigInstanceEntry 17 }    

lcsEpsStatusAPSOnWorking OBJECT-TYPE
   SYNTAX      DisplayString
   MAX-ACCESS  read-only
   STATUS      current
   DESCRIPTION
       "APS is received on the working flow.
       "
   ::= { lcsEPSConfigInstanceEntry 18 }     
   
lcsEpsStatusSwitchingIncomplete OBJECT-TYPE
   SYNTAX      DisplayString
   MAX-ACCESS  read-only
   STATUS      current
   DESCRIPTION
       "Traffic is not selected from the same flow instance in the two ends.
       "
   ::= { lcsEPSConfigInstanceEntry 19 }     
   
lcsEpsStatusNoApsReceived OBJECT-TYPE
   SYNTAX      DisplayString
   MAX-ACCESS  read-only
   STATUS      current
   DESCRIPTION
       "APS PDU is not received from the other end.
       "
   ::= { lcsEPSConfigInstanceEntry 20 }      
   
-- =======================================================================================================================
 
lcsERPS    OBJECT IDENTIFIER ::= { lcsConfiguration 24 }

lcsERPSTable  OBJECT-TYPE
   SYNTAX      SEQUENCE OF LCSERPSEntry
   MAX-ACCESS  not-accessible
   STATUS      current
   DESCRIPTION
       "A table of ERPS."
 ::= { lcsERPS 1 }

lcsERPSEntry OBJECT-TYPE
    SYNTAX        LCSERPSEntry
    MAX-ACCESS    not-accessible
    STATUS        current
    DESCRIPTION
        ""
    INDEX        { lcsErpsIndex }
    ::= { lcsERPSTable 1 }

LCSERPSEntry ::=
    SEQUENCE {
        lcsErpsIndex                                Integer32,
        lcsErpsID                                   Integer32,
        lcsErpsPort0                                Integer32,
        lcsErpsPort1                                Integer32,
        lcsErpsPort0APSMEP                          Integer32,      
        lcsErpsPort1APSMEP                          Integer32,
        lcsErpsPort0SFMEP                           Integer32,
        lcsErpsPort1SFMEP                           Integer32,  
        lcsErpsRingType                             Integer32,      
        lcsErpsInterconnectedNode                   Integer32,      
        lcsErpsVirtualChannel                       Integer32,      
        lcsErpsMajorRingID                          Integer32,  
        lcsErpsAlarm                                  Integer32,
        lcsErpsRowStatus                            RowStatus
    }

lcsErpsIndex OBJECT-TYPE
   SYNTAX      Integer32 (1..65535)
   MAX-ACCESS  not-accessible
   STATUS      current
   DESCRIPTION
       "Index"
   ::= { lcsERPSEntry 1 }

lcsErpsID OBJECT-TYPE
   SYNTAX      Integer32 (1..64)
   MAX-ACCESS  read-create
   STATUS      current
   DESCRIPTION
       "ERPS ID. Range:1-64."
   ::= {lcsERPSEntry 2 }

lcsErpsPort0 OBJECT-TYPE
   SYNTAX      Integer32
   MAX-ACCESS  read-create
   STATUS      current
   DESCRIPTION
       "This will create a Port 0 of the switch in the ring."
   ::= {lcsERPSEntry 3 }   
   
lcsErpsPort1 OBJECT-TYPE
   SYNTAX      Integer32
   MAX-ACCESS  read-create
   STATUS      current
   DESCRIPTION
       "This will create Port 1 of the switch in the Ring. 
       As interconnected sub-ring will have only one ring port, Port 1 is configured as 0 for interconnected sub-ring.
       0 in this field indicates that no Port 1 is associated with this instance"
   ::= {lcsERPSEntry 4 }   
   
lcsErpsPort0APSMEP OBJECT-TYPE
   SYNTAX      Integer32
   MAX-ACCESS  read-create
   STATUS      current
   DESCRIPTION
       "The Port 0 APS PDU handling MEP.
       Range: 1-100."
   ::= {lcsERPSEntry 5 }  
   
lcsErpsPort1APSMEP OBJECT-TYPE
   SYNTAX      Integer32
   MAX-ACCESS  read-create
   STATUS      current
   DESCRIPTION
       "The Port 1 APS PDU handling MEP.
       Range: 1-100."
   ::= {lcsERPSEntry 6 }     

lcsErpsPort0SFMEP OBJECT-TYPE
   SYNTAX      Integer32
   MAX-ACCESS  read-create
   STATUS      current
   DESCRIPTION
       "The Port 0 Signal Fail reporting MEP.
       Range: 1-100."
   ::= {lcsERPSEntry 7 }      
   
 lcsErpsPort1SFMEP OBJECT-TYPE
   SYNTAX      Integer32
   MAX-ACCESS  read-create
   STATUS      current
   DESCRIPTION
       "The Port 1 Signal Fail reporting MEP.
       Range: 1-100."
   ::= {lcsERPSEntry 8 }      
   
lcsErpsRingType OBJECT-TYPE
   SYNTAX      Integer32
   MAX-ACCESS  read-create
   STATUS      current
   DESCRIPTION
       "Type of Protecting ring. It can be either major ring or sub-ring.
       0:Major
       1:Sub"
   ::= {lcsERPSEntry 9 }
   
lcsErpsInterconnectedNode OBJECT-TYPE
   SYNTAX      Integer32
   MAX-ACCESS  read-create
   STATUS      current
   DESCRIPTION
       "Interconnected Node indicates that the ring instance is interconnected. 
       0: not interconnected
       1: interconnected"
   ::= {lcsERPSEntry 10 }  
   
lcsErpsVirtualChannel OBJECT-TYPE
   SYNTAX      Integer32
   MAX-ACCESS  read-create
   STATUS      current
   DESCRIPTION
       "1: indicates it is a sub-ring with virtual channel. 
        0: indicates, sub-ring doesn't have virtual channel."
   ::= {lcsERPSEntry 11 }
   
lcsErpsMajorRingID OBJECT-TYPE
   SYNTAX      Integer32
   MAX-ACCESS  read-create
   STATUS      current
   DESCRIPTION
       "Major ring group ID for the interconnected sub-ring.
       Range:1-64"
   ::= {lcsERPSEntry 12 }   

lcsErpsAlarm OBJECT-TYPE
   SYNTAX      Integer32
   MAX-ACCESS  read-create
   STATUS      current
   DESCRIPTION
       "There is an active alarm on the ERPS."
   ::= {lcsERPSEntry 13 }  
   
lcsErpsRowStatus OBJECT-TYPE
   SYNTAX      RowStatus
   MAX-ACCESS  read-create
   STATUS      current
   DESCRIPTION
       "ERPS Row Status."
   ::= {lcsERPSEntry 14 }      
  
   
lcsErpsConfigInstanceErpsID   OBJECT-TYPE
   SYNTAX      Integer32
   MAX-ACCESS  read-write
   STATUS      current
   DESCRIPTION
       "Specify ERPS ID for ERPSConfigInstanceEntry and ErpsConfigInstanceVLANConfigTable uesd."
   ::= {lcsERPS 2 }
   

lcsERPSConfigInstanceEntry    OBJECT IDENTIFIER ::= { lcsERPS 3 } 

lcsErpsConfigInstanceConfigured OBJECT-TYPE
   SYNTAX      DisplayString
   MAX-ACCESS  read-only
   STATUS      current
   DESCRIPTION
       "Down: This ERPS is only created and has not yet been configured - is not active.
        Up: This ERPS is configured - is active."
   ::= { lcsERPSConfigInstanceEntry 2 }

lcsErpsConfigInstanceGuardTime OBJECT-TYPE
   SYNTAX      Integer32
   MAX-ACCESS  read-write
   STATUS      current
   DESCRIPTION
       "The period of the guard timer can be configured in 10 ms steps between 10 ms and 2 seconds, with a default value of 500 ms.
        Guard timeout value to be used to prevent ring nodes from receiving outdated R-APS messages."
   ::= { lcsERPSConfigInstanceEntry 3 }

lcsErpsConfigInstanceWTRTime OBJECT-TYPE
   SYNTAX      Integer32
   MAX-ACCESS  read-write
   STATUS      current
   DESCRIPTION
       "The Wait To Restore timing value to be used in revertive switching.
        The period of the WTR time can be configured by the operator in 1 minute steps between 5 and 12 minutes with a default value of 5 minutes.
        "
   ::= { lcsERPSConfigInstanceEntry 4 }   
   
lcsErpsConfigInstanceHoldOffTime OBJECT-TYPE
   SYNTAX      Integer32
   MAX-ACCESS  read-write
   STATUS      current
   DESCRIPTION
       "The timing value to be used to make persistent check on Signal Fail before switching.
        The range of the hold off timer is 0 to 10 seconds in steps of 100 ms
        "
   ::= { lcsERPSConfigInstanceEntry 5 }      
   
lcsErpsConfigInstanceVersion OBJECT-TYPE
   SYNTAX      Integer32
   MAX-ACCESS  read-write
   STATUS      current
   DESCRIPTION
       "ERPS Protocol Version - v1 or v2
       1:v1
       2:v2"
   ::= { lcsERPSConfigInstanceEntry 6 }     
   
lcsErpsConfigInstanceRevertive OBJECT-TYPE
   SYNTAX      Integer32
   MAX-ACCESS  read-write
   STATUS      current
   DESCRIPTION
       "1:Revertive mode
        0:Non-Revertive mode"
   ::= { lcsERPSConfigInstanceEntry 7 }     

lcsErpsConfigInstanceRPLRole OBJECT-TYPE
   SYNTAX      Integer32
   MAX-ACCESS  read-write
   STATUS      current
   DESCRIPTION
       "It can be either RPL owner or RPL Neighbor.
       0:None 
       1:RPL owner
       2:RPL Neighbor
       Please set RPLPort first.
       "
   ::= { lcsERPSConfigInstanceEntry 8 }
   
lcsErpsConfigInstanceRPLPort OBJECT-TYPE
   SYNTAX      Integer32
   MAX-ACCESS  read-write
   STATUS      current
   DESCRIPTION
       "This allows to select the east port or west port as the RPL block.
       0:None
       1:Port0
       2:Port1
       Please set RPLRole after specify RPLPort.
       "
   ::= { lcsERPSConfigInstanceEntry 9 }   
   
lcsErpsConfigInstanceClear OBJECT-TYPE
   SYNTAX      Integer32
   MAX-ACCESS  read-write
   STATUS      current
   DESCRIPTION
       "If the owner has to be changed, then the clear check box allows to clear the RPL owner for that ERPS ring.
       0: no clear
       1: clear
       "
   ::= { lcsERPSConfigInstanceEntry 10 }     
   
lcsErpsConfigInstanceTopologyChange OBJECT-TYPE
   SYNTAX      Integer32
   MAX-ACCESS  read-write
   STATUS      current
   DESCRIPTION
       "1: indicates that the topology changes in the sub-ring are propagated in the major ring.
        0: indicates that the topology changes in the sub-ring are not propagated in the major ring.
       "
   ::= { lcsERPSConfigInstanceEntry 11 }     
 
lcsErpsConfigInstanceCommand OBJECT-TYPE
   SYNTAX      Integer32
   MAX-ACCESS  read-write
   STATUS      current
   DESCRIPTION
       "0:None
        1:Manual Switch
        2:Forced Switch
        3:Clear
        Please set InstancePort first.
       "
   ::= { lcsERPSConfigInstanceEntry 12 }  
 
lcsErpsConfigInstancePort OBJECT-TYPE
   SYNTAX      Integer32
   MAX-ACCESS  read-write
   STATUS      current
   DESCRIPTION
       "0:None
       1:Port0
       2:Port1
       Please set InstanceCommand after specify InstancePort.
       "
   ::= { lcsERPSConfigInstanceEntry 13 }     
   
lcsErpsStatusProtectionState OBJECT-TYPE
   SYNTAX      DisplayString
   MAX-ACCESS  read-only
   STATUS      current
   DESCRIPTION
       "ERPS state according to State Transition Tables in G.8032.
       "
   ::= { lcsERPSConfigInstanceEntry 14 }        
   
lcsErpsStatusPort0 OBJECT-TYPE
   SYNTAX      DisplayString
   MAX-ACCESS  read-only
   STATUS      current
   DESCRIPTION
       "OK: State of East port is ok
        SF: State of East port is Signal Fail
       "
   ::= { lcsERPSConfigInstanceEntry 15 }        
   
lcsErpsStatusPort1 OBJECT-TYPE
   SYNTAX      DisplayString
   MAX-ACCESS  read-only
   STATUS      current
   DESCRIPTION
       "OK: State of West port is ok
        SF: State of West port is Signal Fail
       "
   ::= { lcsERPSConfigInstanceEntry 16 }    
   
lcsErpsStatusTransmitAPS OBJECT-TYPE
   SYNTAX      DisplayString
   MAX-ACCESS  read-only
   STATUS      current
   DESCRIPTION
       "The transmitted APS according to State Transition Tables in G.8032.
       "
   ::= { lcsERPSConfigInstanceEntry 17 }    

lcsErpsStatusPort0ReceiveAPS OBJECT-TYPE
   SYNTAX      DisplayString
   MAX-ACCESS  read-only
   STATUS      current
   DESCRIPTION
       "The received APS on Port 0 according to State Transition Tables in G.8032.
       "
   ::= { lcsERPSConfigInstanceEntry 18 } 

lcsErpsStatusPort1ReceiveAPS OBJECT-TYPE
   SYNTAX      DisplayString
   MAX-ACCESS  read-only
   STATUS      current
   DESCRIPTION
       "The received APS on Port 1 according to State Transition Tables in G.8032.
       "
   ::= { lcsERPSConfigInstanceEntry 19 }    
   
lcsErpsStatusWTRRemaining OBJECT-TYPE
   SYNTAX      Integer32
   MAX-ACCESS  read-only
   STATUS      current
   DESCRIPTION
       "Remaining WTR timeout in milliseconds.
       "
   ::= { lcsERPSConfigInstanceEntry 20 }   
   
lcsErpsStatusRPLUnblocked OBJECT-TYPE
   SYNTAX      DisplayString
   MAX-ACCESS  read-only
   STATUS      current
   DESCRIPTION
       "APS is received on the working flow.
       "
   ::= { lcsERPSConfigInstanceEntry 21 }      
   
lcsErpsStatusNoAPSReceived OBJECT-TYPE
   SYNTAX      DisplayString
   MAX-ACCESS  read-only
   STATUS      current
   DESCRIPTION
       "RAPS PDU is not received from the other end.
       "
   ::= { lcsERPSConfigInstanceEntry 22 }   
   
lcsErpsStatusPort0BlockStatus OBJECT-TYPE
   SYNTAX      DisplayString
   MAX-ACCESS  read-only
   STATUS      current
   DESCRIPTION
       "Block status for Port 0 (Both traffic and R-APS block status). R-APS channel is never blocked on sub-rings without virtual channel.
       "
   ::= { lcsERPSConfigInstanceEntry 23 }      
   
lcsErpsStatusPort1BlockStatus OBJECT-TYPE
   SYNTAX      DisplayString
   MAX-ACCESS  read-only
   STATUS      current
   DESCRIPTION
       "Block status for Port 1 (Both traffic and R-APS block status). R-APS channel is never blocked on sub-rings without virtual channel.
       "
   ::= { lcsERPSConfigInstanceEntry 24 }       
   
lcsErpsStatusFOPAlarm OBJECT-TYPE
   SYNTAX      DisplayString
   MAX-ACCESS  read-only
   STATUS      current
   DESCRIPTION
       "Failure of Protocol Defect(FOP) status:
       FOP is not detected
       FOP is detected
       "
   ::= { lcsERPSConfigInstanceEntry 25 }      
   
lcsErpsConfigInstanceVLANConfigTable  OBJECT-TYPE
   SYNTAX      SEQUENCE OF LCSErpsConfigInstanceVLANConfigEntry
   MAX-ACCESS  not-accessible
   STATUS      current
   DESCRIPTION
       "A table of ERPS VLANConfig."
 ::= { lcsERPS 4 }

lcsErpsConfigInstanceVLANConfigEntry OBJECT-TYPE
    SYNTAX        LCSErpsConfigInstanceVLANConfigEntry
    MAX-ACCESS    not-accessible
    STATUS        current
    DESCRIPTION
        ""
    INDEX        { lcsErpsConfigInstanceVLANConfigIndex }
    ::= { lcsErpsConfigInstanceVLANConfigTable 1 }

LCSErpsConfigInstanceVLANConfigEntry ::=
    SEQUENCE {
        lcsErpsConfigInstanceVLANConfigIndex            Integer32,
        lcsErpsConfigInstanceVLANConfigVLANID           Integer32,
        lcsErpsConfigInstanceVLANConfigRowStatus        RowStatus
    }

lcsErpsConfigInstanceVLANConfigIndex OBJECT-TYPE
   SYNTAX      Integer32 (1..65535)
   MAX-ACCESS  not-accessible
   STATUS      current
   DESCRIPTION
       "Index"
   ::= { lcsErpsConfigInstanceVLANConfigEntry 1 }

lcsErpsConfigInstanceVLANConfigVLANID OBJECT-TYPE
   SYNTAX      Integer32 (1..4094)
   MAX-ACCESS  read-create
   STATUS      current
   DESCRIPTION
       "ERPS VLAN Config ID. Range:1-4094."
   ::= {lcsErpsConfigInstanceVLANConfigEntry 2 }

lcsErpsConfigInstanceVLANConfigRowStatus OBJECT-TYPE
   SYNTAX      RowStatus
   MAX-ACCESS  read-create
   STATUS      current
   DESCRIPTION
       "ERPS VLAN Config Row Status."
   ::= {lcsErpsConfigInstanceVLANConfigEntry 3 }   
-- =======================================================================================================================

lcsVLANTranslation    OBJECT IDENTIFIER ::= { lcsConfiguration 25 }

lcsVLANTranslationPortTable  OBJECT-TYPE
   SYNTAX      SEQUENCE OF LCSVLANTranslationPortEntry
   MAX-ACCESS  not-accessible
   STATUS      current
   DESCRIPTION
       "A table of VLANTranslationPort."
 ::= { lcsVLANTranslation 1 }

lcsVLANTranslationPortEntry OBJECT-TYPE
    SYNTAX        LCSVLANTranslationPortEntry
    MAX-ACCESS    not-accessible
    STATUS        current
    DESCRIPTION
        "An entry in the VLANTranslationPort table."
    INDEX        { lcsVLANTranslationPortIndex }
    ::= { lcsVLANTranslationPortTable 1 }

LCSVLANTranslationPortEntry ::=
    SEQUENCE {
        lcsVLANTranslationPortIndex                Integer32,
        lcsVLANTranslationPortDefault              Integer32,
        lcsVLANTranslationPortGroupID              Integer32
    }

lcsVLANTranslationPortIndex OBJECT-TYPE
   SYNTAX      Integer32 (1..65535)
   MAX-ACCESS  not-accessible
   STATUS      current
   DESCRIPTION
       "VLANTranslationPort index."
   ::= {lcsVLANTranslationPortEntry 1 }

lcsVLANTranslationPortDefault OBJECT-TYPE
   SYNTAX      Integer32
   MAX-ACCESS  read-write
   STATUS      current
   DESCRIPTION
       "Set the switch port to use the default VLAN Translation Group.
       1:set
       0:not set"
   ::= {lcsVLANTranslationPortEntry 2 }

lcsVLANTranslationPortGroupID OBJECT-TYPE
   SYNTAX      Integer32
   MAX-ACCESS  read-write
   STATUS      current
   DESCRIPTION
       "The VLAN Translation mappings are organized into Groups, identified by the Group ID."
   ::= {lcsVLANTranslationPortEntry 3 }
   
   
   
lcsVLANTranslationMappingTable  OBJECT-TYPE
   SYNTAX      SEQUENCE OF LCSVLANTranslationMappingEntry
   MAX-ACCESS  not-accessible
   STATUS      current
   DESCRIPTION
       "A table of VLANTranslationMapping."
 ::= { lcsVLANTranslation 2 }

lcsVLANTranslationMappingEntry OBJECT-TYPE
    SYNTAX        LCSVLANTranslationMappingEntry
    MAX-ACCESS    not-accessible
    STATUS        current
    DESCRIPTION
        "An entry in the VLANTranslationMapping table."
    INDEX        { lcsVLANTranslationMappingIndex }
    ::= { lcsVLANTranslationMappingTable 1 }

LCSVLANTranslationMappingEntry ::=
    SEQUENCE {
        lcsVLANTranslationMappingIndex                Integer32,
        lcsVLANTranslationMappingGroupID              Integer32,
        lcsVLANTranslationMappingVID                  Integer32,
        lcsVLANTranslationMappingTVID                 Integer32,
        lcsVLANTranslationMappingRowStatus            RowStatus
    }

lcsVLANTranslationMappingIndex OBJECT-TYPE
   SYNTAX      Integer32 (1..65535)
   MAX-ACCESS  not-accessible
   STATUS      current
   DESCRIPTION
       "VLANTranslationMapping index."
   ::= {lcsVLANTranslationMappingEntry 1 }

lcsVLANTranslationMappingGroupID OBJECT-TYPE
   SYNTAX      Integer32
   MAX-ACCESS  read-create
   STATUS      current
   DESCRIPTION
       "The VLAN Translation mappings are organized into Groups, identified by the Group ID."
   ::= {lcsVLANTranslationMappingEntry 2 }

lcsVLANTranslationMappingVID OBJECT-TYPE
   SYNTAX      Integer32
   MAX-ACCESS  read-create
   STATUS      current
   DESCRIPTION
       "Range:1-4094"
   ::= {lcsVLANTranslationMappingEntry 3 }

lcsVLANTranslationMappingTVID OBJECT-TYPE
   SYNTAX      Integer32
   MAX-ACCESS  read-create
   STATUS      current
   DESCRIPTION
       "Range:1-4094"
   ::= {lcsVLANTranslationMappingEntry 4 }   
   
lcsVLANTranslationMappingRowStatus OBJECT-TYPE
   SYNTAX      RowStatus
   MAX-ACCESS  read-create
   STATUS      current
   DESCRIPTION
       "VLANTranslationMapping Row Status."
   ::= {lcsVLANTranslationMappingEntry 5 }
-- ========================================================================================================   
lcsMEP    OBJECT IDENTIFIER ::= { lcsConfiguration 26 }    

lcsMEPTable  OBJECT-TYPE
   SYNTAX      SEQUENCE OF LCSMEPEntry
   MAX-ACCESS  not-accessible
   STATUS      current
   DESCRIPTION
       "A table of MEP."
 ::= { lcsMEP 1 }

lcsMEPEntry OBJECT-TYPE
    SYNTAX        LCSMEPEntry
    MAX-ACCESS    not-accessible
    STATUS        current
    DESCRIPTION
        "An entry in the MEP table."
    INDEX        { lcsMEPIndex }
    ::= { lcsMEPTable 1 }

LCSMEPEntry ::=
    SEQUENCE {
        lcsMEPIndex                         Integer32,
        lcsMepInstance                      Integer32,
        lcsMepDomain                        Integer32,
        lcsMepMode                          Integer32,
        lcsMepDirection                     Integer32,
        lcsMepResidencePort                 Integer32,
        lcsMepLevel                         Integer32,
        lcsMepFlowInstance                  Integer32,
        lcsMepTaggedVID                     Integer32,
        lcsMepEPSInstance                   DisplayString,
        lcsMepThisMAC                       DisplayString,
        lcsMepAlarm                         DisplayString,
        lcsMepRowStatus                     RowStatus
    }

lcsMEPIndex OBJECT-TYPE
   SYNTAX      Integer32 (1..65535)
   MAX-ACCESS  not-accessible
   STATUS      current
   DESCRIPTION
       "MEP Table index."
   ::= {lcsMEPEntry 1 }

lcsMepInstance OBJECT-TYPE
   SYNTAX      Integer32
   MAX-ACCESS  read-create
   STATUS      current
   DESCRIPTION
       ""
   ::= {lcsMEPEntry 2 }

lcsMepDomain OBJECT-TYPE
   SYNTAX      Integer32
   MAX-ACCESS  read-create
   STATUS      current
   DESCRIPTION
       ""
   ::= {lcsMEPEntry 3 }  
   
lcsMepMode OBJECT-TYPE
   SYNTAX      Integer32
   MAX-ACCESS  read-create
   STATUS      current
   DESCRIPTION
       ""
   ::= {lcsMEPEntry 4 }    

lcsMepDirection OBJECT-TYPE
   SYNTAX      Integer32
   MAX-ACCESS  read-create
   STATUS      current
   DESCRIPTION
       ""
   ::= {lcsMEPEntry 5 }  

lcsMepResidencePort OBJECT-TYPE
   SYNTAX      Integer32
   MAX-ACCESS  read-create
   STATUS      current
   DESCRIPTION
       ""
   ::= {lcsMEPEntry 6 }  

lcsMepLevel OBJECT-TYPE
   SYNTAX      Integer32
   MAX-ACCESS  read-create
   STATUS      current
   DESCRIPTION
       ""
   ::= {lcsMEPEntry 7 }  

lcsMepFlowInstance OBJECT-TYPE
   SYNTAX      Integer32
   MAX-ACCESS  read-create
   STATUS      current
   DESCRIPTION
       ""
   ::= {lcsMEPEntry 8 }  

lcsMepTaggedVID OBJECT-TYPE
   SYNTAX      Integer32
   MAX-ACCESS  read-create
   STATUS      current
   DESCRIPTION
       ""
   ::= {lcsMEPEntry 9 }    

lcsMepEPSInstance OBJECT-TYPE
   SYNTAX      DisplayString
   MAX-ACCESS  read-only
   STATUS      current
   DESCRIPTION
       ""
   ::= {lcsMEPEntry 10 }     
   
lcsMepThisMAC OBJECT-TYPE
   SYNTAX      DisplayString
   MAX-ACCESS  read-only
   STATUS      current
   DESCRIPTION
       ""
   ::= {lcsMEPEntry 11 }

lcsMepAlarm OBJECT-TYPE
   SYNTAX      DisplayString
   MAX-ACCESS  read-only
   STATUS      current
   DESCRIPTION
       ""
   ::= {lcsMEPEntry 12 }  
   
lcsMepRowStatus OBJECT-TYPE
   SYNTAX      RowStatus
   MAX-ACCESS  read-create
   STATUS      current
   DESCRIPTION
       "MEP Row Status."
   ::= {lcsMEPEntry 13 }
 
lcsMepInstanceID   OBJECT-TYPE
   SYNTAX      Integer32
   MAX-ACCESS  read-write
   STATUS      current
   DESCRIPTION
       "Specify MEP Instance ID for the following item and table uesd."
   ::= {lcsMEP 2 } 
 

lcsMepInstanceConfEntry    OBJECT IDENTIFIER ::= { lcsMEP 3 }

lcsMepInstanceConfLevel OBJECT-TYPE
   SYNTAX      Integer32
   MAX-ACCESS  read-write
   STATUS      current
   DESCRIPTION
       ""
   ::= {lcsMepInstanceConfEntry 2 }  

lcsMepInstanceConfFormat OBJECT-TYPE
   SYNTAX      Integer32
   MAX-ACCESS  read-write
   STATUS      current
   DESCRIPTION
       ""
   ::= {lcsMepInstanceConfEntry 3 }  

lcsMepInstanceConfDomainName OBJECT-TYPE
   SYNTAX      DisplayString
   MAX-ACCESS  read-write
   STATUS      current
   DESCRIPTION
       ""
   ::= {lcsMepInstanceConfEntry 4 }  

lcsMepInstanceConfMEGid OBJECT-TYPE
   SYNTAX      DisplayString
   MAX-ACCESS  read-write
   STATUS      current
   DESCRIPTION
       ""
   ::= {lcsMepInstanceConfEntry 5 } 

lcsMepInstanceConfMEPid OBJECT-TYPE
   SYNTAX      Integer32
   MAX-ACCESS  read-write
   STATUS      current
   DESCRIPTION
       ""
   ::= {lcsMepInstanceConfEntry 6 }   

lcsMepInstanceConfTaggedVID OBJECT-TYPE
   SYNTAX      Integer32
   MAX-ACCESS  read-write
   STATUS      current
   DESCRIPTION
       ""
   ::= {lcsMepInstanceConfEntry 7 }      
  
lcsMepInstanceConfSyslog OBJECT-TYPE
   SYNTAX      Integer32
   MAX-ACCESS  read-write
   STATUS      current
   DESCRIPTION
       ""
   ::= {lcsMepInstanceConfEntry 8 }  
  
lcsMepInstanceConfcLevel OBJECT-TYPE
   SYNTAX      DisplayString
   MAX-ACCESS  read-only
   STATUS      current
   DESCRIPTION
       ""
   ::= {lcsMepInstanceConfEntry 9 }  
 
lcsMepInstanceConfcMEG OBJECT-TYPE
   SYNTAX      DisplayString
   MAX-ACCESS  read-only
   STATUS      current
   DESCRIPTION
       ""
   ::= {lcsMepInstanceConfEntry 10 }   
 
lcsMepInstanceConfcMEP OBJECT-TYPE
   SYNTAX      DisplayString
   MAX-ACCESS  read-only
   STATUS      current
   DESCRIPTION
       ""
   ::= {lcsMepInstanceConfEntry 11 }   
 
lcsMepInstanceConfcAIS OBJECT-TYPE
   SYNTAX      DisplayString
   MAX-ACCESS  read-only
   STATUS      current
   DESCRIPTION
       ""
   ::= {lcsMepInstanceConfEntry 12 }   
   
lcsMepInstanceConfcLCK OBJECT-TYPE
   SYNTAX      DisplayString
   MAX-ACCESS  read-only
   STATUS      current
   DESCRIPTION
       ""
   ::= {lcsMepInstanceConfEntry 13 }   
 
lcsMepInstanceConfcLoop OBJECT-TYPE
   SYNTAX      DisplayString
   MAX-ACCESS  read-only
   STATUS      current
   DESCRIPTION
       ""
   ::= {lcsMepInstanceConfEntry 14 }  

lcsMepInstanceConfcConfig OBJECT-TYPE
   SYNTAX      DisplayString
   MAX-ACCESS  read-only
   STATUS      current
   DESCRIPTION
       ""
   ::= {lcsMepInstanceConfEntry 15 }  

lcsMepInstanceConfcDEG OBJECT-TYPE
   SYNTAX      DisplayString
   MAX-ACCESS  read-only
   STATUS      current
   DESCRIPTION
       ""
   ::= {lcsMepInstanceConfEntry 16 }  

lcsMepInstanceConfcSSF OBJECT-TYPE
   SYNTAX      DisplayString
   MAX-ACCESS  read-only
   STATUS      current
   DESCRIPTION
       ""
   ::= {lcsMepInstanceConfEntry 17 }  

lcsMepInstanceConfaBLK OBJECT-TYPE
   SYNTAX      DisplayString
   MAX-ACCESS  read-only
   STATUS      current
   DESCRIPTION
       ""
   ::= {lcsMepInstanceConfEntry 18 }  

lcsMepInstanceConfaTSD OBJECT-TYPE
   SYNTAX      DisplayString
   MAX-ACCESS  read-only
   STATUS      current
   DESCRIPTION
       ""
   ::= {lcsMepInstanceConfEntry 19 }  

lcsMepInstanceConfaTSF OBJECT-TYPE
   SYNTAX      DisplayString
   MAX-ACCESS  read-only
   STATUS      current
   DESCRIPTION
       ""
   ::= {lcsMepInstanceConfEntry 20 }     
 
 
lcsPeerMepConfTable  OBJECT-TYPE
   SYNTAX      SEQUENCE OF LCSPeerMepConfEntry
   MAX-ACCESS  not-accessible
   STATUS      current
   DESCRIPTION
       "A table of MEP."
 ::= { lcsMEP 4 }

lcsPeerMepConfEntry OBJECT-TYPE
    SYNTAX        LCSPeerMepConfEntry
    MAX-ACCESS    not-accessible
    STATUS        current
    DESCRIPTION
        ""
    INDEX        { lcsPeerMepConfIndex }
    ::= { lcsPeerMepConfTable 1 }

LCSPeerMepConfEntry ::=
    SEQUENCE {
        lcsPeerMepConfIndex                       Integer32,
        lcsPeerMepConfPeerMEPID                   Integer32,
        lcsPeerMepConfUnicastPeerMAC              DisplayString,
        lcsPeerMepConfcLOC                        DisplayString,
        lcsPeerMepConfcRDI                        DisplayString,
        lcsPeerMepConfcPeriod                     DisplayString,    
        lcsPeerMepConfcPriority                   DisplayString,            
        lcsPeerMepConfRowStatus                   RowStatus
    }

lcsPeerMepConfIndex OBJECT-TYPE
   SYNTAX      Integer32 (1..65535)
   MAX-ACCESS  not-accessible
   STATUS      current
   DESCRIPTION
       "Index"
   ::= { lcsPeerMepConfEntry 1 }

lcsPeerMepConfPeerMEPID OBJECT-TYPE
   SYNTAX      Integer32 
   MAX-ACCESS  read-create
   STATUS      current
   DESCRIPTION
       "Peer MEP ID"
   ::= {lcsPeerMepConfEntry 2 }

lcsPeerMepConfUnicastPeerMAC OBJECT-TYPE
   SYNTAX      DisplayString
   MAX-ACCESS  read-create
   STATUS      current
   DESCRIPTION
       ""
   ::= {lcsPeerMepConfEntry 3 }   
   
lcsPeerMepConfcLOC OBJECT-TYPE
   SYNTAX      DisplayString
   MAX-ACCESS  read-create
   STATUS      current
   DESCRIPTION
       ""
   ::= {lcsPeerMepConfEntry 4 }      
   
lcsPeerMepConfcRDI OBJECT-TYPE
   SYNTAX      DisplayString
   MAX-ACCESS  read-create
   STATUS      current
   DESCRIPTION
       ""
   ::= {lcsPeerMepConfEntry 5 }    
   
lcsPeerMepConfcPeriod OBJECT-TYPE
   SYNTAX      DisplayString
   MAX-ACCESS  read-create
   STATUS      current
   DESCRIPTION
       ""
   ::= {lcsPeerMepConfEntry 6 }  

lcsPeerMepConfcPriority OBJECT-TYPE
   SYNTAX      DisplayString
   MAX-ACCESS  read-create
   STATUS      current
   DESCRIPTION
       ""
   ::= {lcsPeerMepConfEntry 7 }  
   
lcsPeerMepConfRowStatus OBJECT-TYPE
   SYNTAX      RowStatus
   MAX-ACCESS  read-create
   STATUS      current
   DESCRIPTION
       "Peer Mep Conf Row Status."
   ::= {lcsPeerMepConfEntry 8 }
   
lcsFunctionalConf    OBJECT IDENTIFIER ::= { lcsMEP 5 }

lcsFunctionalConfContinuityCheckEnable OBJECT-TYPE
   SYNTAX      Integer32
   MAX-ACCESS  read-write
   STATUS      current
   DESCRIPTION
       "0:disable
       1:enable"
   ::= {lcsFunctionalConf 2 } 
   
lcsFunctionalConfContinuityCheckPriority OBJECT-TYPE
   SYNTAX      Integer32
   MAX-ACCESS  read-write
   STATUS      current
   DESCRIPTION
       "range:0-7"
   ::= {lcsFunctionalConf 3 } 
   
lcsFunctionalConfContinuityCheckFrameRate OBJECT-TYPE
   SYNTAX      Integer32
   MAX-ACCESS  read-write
   STATUS      current
   DESCRIPTION
       "range:1-7
       1: 300 f/sec
       2: 100 f/sec
       3: 10 f/sec
       4: 1 f/sec
       5: 6 f/min
       6: 1 f/min
       7: 6 f/hour"
   ::= {lcsFunctionalConf 4 }    

lcsFunctionalConfContinuityCheckTLV OBJECT-TYPE
   SYNTAX      Integer32
   MAX-ACCESS  read-write
   STATUS      current
   DESCRIPTION
       "0:disable
       1:enable"
   ::= {lcsFunctionalConf 5 } 

lcsFunctionalConfAPSProtocolEnable OBJECT-TYPE
   SYNTAX      Integer32
   MAX-ACCESS  read-write
   STATUS      current
   DESCRIPTION
       "0:disable
       1:enable"
   ::= {lcsFunctionalConf 6 }   

lcsFunctionalConfAPSProtocolPriority OBJECT-TYPE
   SYNTAX      Integer32
   MAX-ACCESS  read-write
   STATUS      current
   DESCRIPTION
       "range:0-7"
   ::= {lcsFunctionalConf 7 }   
   
lcsFunctionalConfAPSProtocolCast OBJECT-TYPE
   SYNTAX      Integer32
   MAX-ACCESS  read-write
   STATUS      current
   DESCRIPTION
       "0: Unicast destination address
       1: Multicast destination address"
   ::= {lcsFunctionalConf 8 }     

lcsFunctionalConfAPSProtocolType OBJECT-TYPE
   SYNTAX      Integer32
   MAX-ACCESS  read-write
   STATUS      current
   DESCRIPTION
       "1: Linear protection APS
       2: Ring protection APS"
   ::= {lcsFunctionalConf 9 }  

lcsFunctionalConfAPSProtocolLastOctet OBJECT-TYPE
   SYNTAX      Integer32
   MAX-ACCESS  read-write
   STATUS      current
   DESCRIPTION
       "range:0-255"
   ::= {lcsFunctionalConf 10 }    
   
lcsTLVConf    OBJECT IDENTIFIER ::= { lcsMEP 6 }   

lcsTLVConfOUIFirst OBJECT-TYPE
   SYNTAX      Integer32
   MAX-ACCESS  read-write
   STATUS      current
   DESCRIPTION
       "range:0-255"
   ::= {lcsTLVConf 2 } 
   
lcsTLVConfOUISecond OBJECT-TYPE
   SYNTAX      Integer32
   MAX-ACCESS  read-write
   STATUS      current
   DESCRIPTION
       "range:0-255"
   ::= {lcsTLVConf 3 } 
   
lcsTLVConfOUIThird OBJECT-TYPE
   SYNTAX      Integer32
   MAX-ACCESS  read-write
   STATUS      current
   DESCRIPTION
       "range:0-255"
   ::= {lcsTLVConf 4 } 
   
lcsTLVConfSubType OBJECT-TYPE
   SYNTAX      Integer32
   MAX-ACCESS  read-write
   STATUS      current
   DESCRIPTION
       "range:0-255"
   ::= {lcsTLVConf 5 }    
   
lcsTLVConfValue OBJECT-TYPE
   SYNTAX      Integer32
   MAX-ACCESS  read-write
   STATUS      current
   DESCRIPTION
       "range:0-255"
   ::= {lcsTLVConf 6 }  


lcsTLVConfStateTable OBJECT-TYPE
   SYNTAX      SEQUENCE OF LCSTLVConfStateEntry
   MAX-ACCESS  not-accessible
   STATUS      current
   DESCRIPTION
       "TLV Conf State Table"
   ::= { lcsMEP 7 }

lcsTLVConfStateEntry OBJECT-TYPE
   SYNTAX      LCSTLVConfStateEntry
   MAX-ACCESS  not-accessible
   STATUS      current
   DESCRIPTION
       "TLV Conf State Entry"
   INDEX    { lcsTLVConfStateIndex  }
   ::= { lcsTLVConfStateTable 1 }

LCSTLVConfStateEntry ::= SEQUENCE {
   lcsTLVConfStateIndex                                Integer32,
   lcsTLVConfStatePeerMEPID                            Integer32,
   lcsTLVConfStateCCOrganizationSpecificOUIFirst       Integer32,
   lcsTLVConfStateCCOrganizationSpecificOUISecond      Integer32,
   lcsTLVConfStateCCOrganizationSpecificOUIThird       Integer32,  
   lcsTLVConfStateCCOrganizationSpecificSubType        Integer32,  
   lcsTLVConfStateCCOrganizationSpecificValue          Integer32,  
   lcsTLVConfStateCCOrganizationSpecificLastRX         DisplayString, 
   lcsTLVConfStateCCPortStatusValue                    Integer32,
   lcsTLVConfStateCCPortStatusLastRX                   DisplayString, 
   lcsTLVConfStateCCInterfaceStatusValue               Integer32,
   lcsTLVConfStateCCInterfaceStatusLastRX              DisplayString
}

lcsTLVConfStateIndex OBJECT-TYPE
   SYNTAX      Integer32 (1..65535)
   MAX-ACCESS  not-accessible
   STATUS      current
   DESCRIPTION
       "Index"
   ::= { lcsTLVConfStateEntry 1 }
   
lcsTLVConfStatePeerMEPID OBJECT-TYPE
   SYNTAX      Integer32
   MAX-ACCESS  read-only
   STATUS      current
   DESCRIPTION
       "Peer MEP ID"
   ::= { lcsTLVConfStateEntry 2 }   
   
lcsTLVConfStateCCOrganizationSpecificOUIFirst OBJECT-TYPE
   SYNTAX      Integer32
   MAX-ACCESS  read-only
   STATUS      current
   DESCRIPTION
       "The last received first value in the OUI field."
   ::= { lcsTLVConfStateEntry 3 }      
   
lcsTLVConfStateCCOrganizationSpecificOUISecond OBJECT-TYPE
   SYNTAX      Integer32
   MAX-ACCESS  read-only
   STATUS      current
   DESCRIPTION
       "The last received second value in the OS TLV OUI field."
   ::= { lcsTLVConfStateEntry 4 }    
   
lcsTLVConfStateCCOrganizationSpecificOUIThird OBJECT-TYPE
   SYNTAX      Integer32
   MAX-ACCESS  read-only
   STATUS      current
   DESCRIPTION
       "The last received third value in the OS TLV OUI field."
   ::= { lcsTLVConfStateEntry 5 }  
   
lcsTLVConfStateCCOrganizationSpecificSubType OBJECT-TYPE
   SYNTAX      Integer32
   MAX-ACCESS  read-only
   STATUS      current
   DESCRIPTION
       "The last received value in the OS TLV Sub-Type field."
   ::= { lcsTLVConfStateEntry 6 }   

lcsTLVConfStateCCOrganizationSpecificValue OBJECT-TYPE
   SYNTAX      Integer32
   MAX-ACCESS  read-only
   STATUS      current
   DESCRIPTION
       "The last received value in the OS TLV Value field."
   ::= { lcsTLVConfStateEntry 7 }  

lcsTLVConfStateCCOrganizationSpecificLastRX OBJECT-TYPE
   SYNTAX      DisplayString
   MAX-ACCESS  read-only
   STATUS      current
   DESCRIPTION
       "OS TLV was received in the last received CCM PDU."
   ::= { lcsTLVConfStateEntry 8 }  

lcsTLVConfStateCCPortStatusValue OBJECT-TYPE
   SYNTAX      Integer32
   MAX-ACCESS  read-only
   STATUS      current
   DESCRIPTION
       "The last received value in the PS TLV Value field."
   ::= { lcsTLVConfStateEntry 9 }

lcsTLVConfStateCCPortStatusLastRX OBJECT-TYPE
   SYNTAX      DisplayString
   MAX-ACCESS  read-only
   STATUS      current
   DESCRIPTION
       "PS TLV was received in the last received CCM PDU."
   ::= { lcsTLVConfStateEntry 10 }  
   
lcsTLVConfStateCCInterfaceStatusValue OBJECT-TYPE
   SYNTAX      Integer32
   MAX-ACCESS  read-only
   STATUS      current
   DESCRIPTION
       "The last received value in the IS TLV Value field."
   ::= { lcsTLVConfStateEntry 11 }   
   
lcsTLVConfStateCCInterfaceStatusLastRX OBJECT-TYPE
   SYNTAX      DisplayString
   MAX-ACCESS  read-only
   STATUS      current
   DESCRIPTION
       "IS TLV was received in the last received CCM PDU."
   ::= { lcsTLVConfStateEntry 12 } 

lcsLinkStateTracking OBJECT-TYPE
   SYNTAX      Integer32
   MAX-ACCESS  read-write
   STATUS      current
   DESCRIPTION
       "0:disable
       1:enable"
   ::= { lcsMEP 8 } 

   
lcsFaultManagement    OBJECT IDENTIFIER ::= { lcsMEP 9 }   

lcsFaultMgmtLoopBackConfEnable OBJECT-TYPE
   SYNTAX      Integer32
   MAX-ACCESS  read-write
   STATUS      current
   DESCRIPTION
       "0:disable
       1:enable"
   ::= { lcsFaultManagement 2 } 

lcsFaultMgmtLoopBackConfDEI OBJECT-TYPE
   SYNTAX      Integer32
   MAX-ACCESS  read-write
   STATUS      current
   DESCRIPTION
       "0:disable
       1:enable"
   ::= { lcsFaultManagement 3 } 
   
lcsFaultMgmtLoopBackConfPriority OBJECT-TYPE
   SYNTAX      Integer32
   MAX-ACCESS  read-write
   STATUS      current
   DESCRIPTION
       "range:0-7"
   ::= { lcsFaultManagement 4 } 
 
lcsFaultMgmtLoopBackConfCast OBJECT-TYPE
   SYNTAX      Integer32
   MAX-ACCESS  read-write
   STATUS      current
   DESCRIPTION
       "0:Unicast destination address
       1:Multicast destination address"
   ::= { lcsFaultManagement 5 }  
 
lcsFaultMgmtLoopBackConfPeerMEP OBJECT-TYPE
   SYNTAX      Integer32
   MAX-ACCESS  read-write
   STATUS      current
   DESCRIPTION
       "This is only used if the 'Unicast MAC' is configured to all zero. 
       The LBM unicast MAC will be taken from the 'Unicast Peer MAC' configuration of this peer."
   ::= { lcsFaultManagement 6 }  
 
lcsFaultMgmtLoopBackConfUnicastMAC OBJECT-TYPE
   SYNTAX      DisplayString
   MAX-ACCESS  read-write
   STATUS      current
   DESCRIPTION
       "This is only used if NOT configured to all zero. 
       This will be used as the LBM PDU unicast MAC. 
       This is the only way to configure Loop Back to-wards a MIP. "
   ::= { lcsFaultManagement 7 }  
   
lcsFaultMgmtLoopBackConfToSend OBJECT-TYPE
   SYNTAX      Integer32
   MAX-ACCESS  read-write
   STATUS      current
   DESCRIPTION
       "The number of LBM PDU to send in one loop test. 
       The value 0 indicate infinite transmission (test behaviour). 
       This is HW based LBM/LBR and Requires VOE."
   ::= { lcsFaultManagement 8 } 
   
lcsFaultMgmtLoopBackConfSize OBJECT-TYPE
   SYNTAX      Integer32
   MAX-ACCESS  read-write
   STATUS      current
   DESCRIPTION
       "The LBM frame size."
   ::= { lcsFaultManagement 9 } 
   
lcsFaultMgmtLoopBackConfInterval OBJECT-TYPE
   SYNTAX      Integer32
   MAX-ACCESS  read-write
   STATUS      current
   DESCRIPTION
       "The interval between transmitting LBM PDU."
   ::= { lcsFaultManagement 10 } 
   
   
lcsFaultManagementState    OBJECT IDENTIFIER ::= { lcsMEP 10 }  
   
   
lcsFaultMgmtStateTransactionID OBJECT-TYPE
   SYNTAX      Integer32
   MAX-ACCESS  read-only
   STATUS      current
   DESCRIPTION
       "The transaction id of the first LBM transmitted. 
       For each LBM transmitted the transaction id in the PDU is incremented."
   ::= { lcsFaultManagementState 1 } 
   

lcsFaultMgmtStateTransmitted OBJECT-TYPE
   SYNTAX      Integer32
   MAX-ACCESS  read-only
   STATUS      current
   DESCRIPTION
       "The total number of LBM PDU transmitted."
   ::= { lcsFaultManagementState 2 } 
   
   
lcsFaultMgmtStateTable OBJECT-TYPE
   SYNTAX      SEQUENCE OF LCSFaultMgmtStateEntry
   MAX-ACCESS  not-accessible
   STATUS      current
   DESCRIPTION
       " "
   ::= { lcsFaultManagementState 3 }

lcsFaultMgmtStateEntry OBJECT-TYPE
   SYNTAX      LCSFaultMgmtStateEntry
   MAX-ACCESS  not-accessible
   STATUS      current
   DESCRIPTION
       " "
   INDEX    { lcsFaultMgmtStateIndex  }
   ::= { lcsFaultMgmtStateTable 1 }

LCSFaultMgmtStateEntry ::= SEQUENCE {
   lcsFaultMgmtStateIndex               Integer32,
   lcsFaultMgmtStateReplyMAC            DisplayString,
   lcsFaultMgmtStateReceived            Integer32,
   lcsFaultMgmtStateOutOfOrder          Integer32
}

lcsFaultMgmtStateIndex OBJECT-TYPE
   SYNTAX      Integer32 (1..65535)
   MAX-ACCESS  not-accessible
   STATUS      current
   DESCRIPTION
       "Index"
   ::= { lcsFaultMgmtStateEntry 1 }

lcsFaultMgmtStateReplyMAC OBJECT-TYPE
   SYNTAX      DisplayString
   MAX-ACCESS  read-only
   STATUS      current
   DESCRIPTION
       "The MAC of the replying MEP/MIP. 
       In case of multi-cast LBM, replies can be received from all peer MEP in the group. 
       This MAC is not shown in case of 'To Send' == 0."
   ::= { lcsFaultMgmtStateEntry 2 }

lcsFaultMgmtStateReceived OBJECT-TYPE
   SYNTAX      Integer32
   MAX-ACCESS  read-only
   STATUS      current
   DESCRIPTION
       "The total number of LBR PDU received from this 'Reply MAC'."
   ::= { lcsFaultMgmtStateEntry 3 }   
   
lcsFaultMgmtStateOutOfOrder OBJECT-TYPE
   SYNTAX      Integer32
   MAX-ACCESS  read-only
   STATUS      current
   DESCRIPTION
       "The number of LBR PDU received from this 'Reply MAC' with incorrect 'Transaction ID'."
   ::= { lcsFaultMgmtStateEntry 4 }  
   
lcsFaultMgmtTestSignal    OBJECT IDENTIFIER ::= { lcsMEP 11 }  

lcsFaultMgmtTestSignalTx OBJECT-TYPE
   SYNTAX      Integer32
   MAX-ACCESS  read-write
   STATUS      current
   DESCRIPTION
       "Test Signal based on transmitting TST PDU can be enabled/disabled.
       0:disable
       1:enable"
   ::= { lcsFaultMgmtTestSignal 2 }  
   
lcsFaultMgmtTestSignalRx OBJECT-TYPE
   SYNTAX      Integer32
   MAX-ACCESS  read-write
   STATUS      current
   DESCRIPTION
       "Test Signal based on transmitting TST PDU can be enabled/disabled.
       0:disable
       1:enable"
   ::= { lcsFaultMgmtTestSignal 3 }  
   
lcsFaultMgmtTestSignalDEI OBJECT-TYPE
   SYNTAX      Integer32
   MAX-ACCESS  read-write
   STATUS      current
   DESCRIPTION
       "The DEI to be inserted as PCP bits in TAG (if any).
       0:disable
       1:enable"
   ::= { lcsFaultMgmtTestSignal 4 }  

lcsFaultMgmtTestSignalPriority OBJECT-TYPE
   SYNTAX      Integer32
   MAX-ACCESS  read-write
   STATUS      current
   DESCRIPTION
       "The priority to be inserted as PCP bits in TAG (if any).
       Range:0-7"
   ::= { lcsFaultMgmtTestSignal 5 }    
   
lcsFaultMgmtTestSignalPeerMEP OBJECT-TYPE
   SYNTAX      Integer32
   MAX-ACCESS  read-write
   STATUS      current
   DESCRIPTION
       "The TST frame destination MAC will be taken from the 'Unicast Peer MAC' configuration of this peer."
   ::= { lcsFaultMgmtTestSignal 6 }    
   
lcsFaultMgmtTestSignalRate OBJECT-TYPE
   SYNTAX      Integer32
   MAX-ACCESS  read-write
   STATUS      current
   DESCRIPTION
       "The TST frame transmission bit rate - in Mega bits pr. second. 
       Limit is 400 Mbps. This is the bit rate of a standard frame without any encapsulation. 
       If 1 Mbps rate is selected in a EVC MEP, the added tag will give a higher bitrate on the wire."
   ::= { lcsFaultMgmtTestSignal 7 }  
   
lcsFaultMgmtTestSignalSize OBJECT-TYPE
   SYNTAX      Integer32
   MAX-ACCESS  read-write
   STATUS      current
   DESCRIPTION
       "The TST frame size. This is entered as the wanted size (in bytes) of a un-tagged frame containing TST OAM PDU - including CRC (four bytes)."
   ::= { lcsFaultMgmtTestSignal 8 }  
   
lcsFaultMgmtTestSignalPattern OBJECT-TYPE
   SYNTAX      Integer32
   MAX-ACCESS  read-write
   STATUS      current
   DESCRIPTION
       "The 'empty' TST PDU has the size of 12 bytes. 
       In order to achieve the configured frame size a data TLV will be added with a pattern.
       0:All Zero
       1:All One
       2:10101010"
   ::= { lcsFaultMgmtTestSignal 9 }  
   
lcsFaultMgmtTestSignalSequenceNumber OBJECT-TYPE
   SYNTAX      Integer32
   MAX-ACCESS  read-write
   STATUS      current
   DESCRIPTION
       "0:disable
       1:enable"
   ::= { lcsFaultMgmtTestSignal 10 }  
   
lcsFaultMgmtTestSignalState    OBJECT IDENTIFIER ::= { lcsMEP 12 }  
   
lcsFaultMgmtTestSignalStateTXFrameCount OBJECT-TYPE
   SYNTAX      Integer32
   MAX-ACCESS  read-only
   STATUS      current
   DESCRIPTION
       "The number of transmitted TST frames since last 'Clear'."
   ::= { lcsFaultMgmtTestSignalState 2 }  
   
lcsFaultMgmtTestSignalStateRXFrameCount OBJECT-TYPE
   SYNTAX      Integer32
   MAX-ACCESS  read-only
   STATUS      current
   DESCRIPTION
       "The number of received TST frames since last 'Clear'."
   ::= { lcsFaultMgmtTestSignalState 3 }  
   
lcsFaultMgmtTestSignalStateRXRate OBJECT-TYPE
   SYNTAX      Integer32
   MAX-ACCESS  read-only
   STATUS      current
   DESCRIPTION
       "The current received TST frame bit rate in Kbps. 
       This is calculated on a 1 s. basis, starting when first TST frame is received after 'Clear'. 
       The frame size used for this calculation is the first received after 'Clear'"
   ::= { lcsFaultMgmtTestSignalState 4 }  
   
lcsFaultMgmtTestSignalStateTestTime OBJECT-TYPE
   SYNTAX      Integer32
   MAX-ACCESS  read-only
   STATUS      current
   DESCRIPTION
       "The number of seconds passed since first TST frame received after last 'Clear'."
   ::= { lcsFaultMgmtTestSignalState 5 }  
   
   
lcsFaultMgmtTestSignalStateClear OBJECT-TYPE
   SYNTAX      Integer32
   MAX-ACCESS  read-write
   STATUS      current
   DESCRIPTION
       "This will clear all Test Signal State. 
       Transmission of TST frame will be restarted. 
       Calculation of 'Rx frame count', 'RX rate' and 'Test time' will be started when receiving first TST frame."
   ::= { lcsFaultMgmtTestSignalState 6 }     
   
   
lcsFaultMgmtClientConfigFlow    OBJECT IDENTIFIER ::= { lcsMEP 13 }  

lcsFaultMgmtClientConfigFlowTable OBJECT-TYPE
   SYNTAX      SEQUENCE OF LCSFaultMgmtClientConfigFlowEntry
   MAX-ACCESS  not-accessible
   STATUS      current
   DESCRIPTION
       " "
   ::= { lcsFaultMgmtClientConfigFlow 1 }

lcsFaultMgmtClientConfigFlowEntry OBJECT-TYPE
   SYNTAX      LCSFaultMgmtClientConfigFlowEntry
   MAX-ACCESS  not-accessible
   STATUS      current
   DESCRIPTION
       " "
   INDEX    { lcsFaultMgmtClientConfigFlowIndex  }
   ::= { lcsFaultMgmtClientConfigFlowTable 1 }

LCSFaultMgmtClientConfigFlowEntry ::= SEQUENCE {
   lcsFaultMgmtClientConfigFlowIndex     Integer32,
   lcsFaultMgmtClientConfigFlowDomain    Integer32,
   lcsFaultMgmtClientConfigFlowInstance  Integer32,
   lcsFaultMgmtClientConfigFlowLevel     Integer32,
   lcsFaultMgmtClientConfigFlowAISprio   Integer32,
   lcsFaultMgmtClientConfigFlowLCKprio   Integer32,
   lcsFaultMgmtClientConfigFlowRowStatus RowStatus
}

lcsFaultMgmtClientConfigFlowIndex OBJECT-TYPE
   SYNTAX      Integer32 (1..65535)
   MAX-ACCESS  not-accessible
   STATUS      current
   DESCRIPTION
       "Index"
   ::= { lcsFaultMgmtClientConfigFlowEntry 1 }

lcsFaultMgmtClientConfigFlowDomain OBJECT-TYPE
   SYNTAX      Integer32
   MAX-ACCESS  read-create
   STATUS      current
   DESCRIPTION
       "The domain of the client layer flow.
       Ranfew:0-6
       0:Port
       1:EVC
       2:VLAN
       3:MPLS_LINK
       4:MPLS_TUNNEL
       5:MPLS_PW
       6:MPLS_LSP"
   ::= { lcsFaultMgmtClientConfigFlowEntry 2 }  

lcsFaultMgmtClientConfigFlowInstance OBJECT-TYPE
   SYNTAX      Integer32
   MAX-ACCESS  read-create
   STATUS      current
   DESCRIPTION
       "Client layer flow instance numbers."
   ::= { lcsFaultMgmtClientConfigFlowEntry 3 }  
   
lcsFaultMgmtClientConfigFlowLevel OBJECT-TYPE
   SYNTAX      Integer32
   MAX-ACCESS  read-create
   STATUS      current
   DESCRIPTION
       "Client layer level - AIS and LCK PDU transmitted in this client layer flow will be on this level."
   ::= { lcsFaultMgmtClientConfigFlowEntry 4 }  
   
lcsFaultMgmtClientConfigFlowAISprio OBJECT-TYPE
   SYNTAX      Integer32
   MAX-ACCESS  read-create
   STATUS      current
   DESCRIPTION
       "The priority to be used when transmitting AIS in each client flow. 
       Priority resulting in highest possible PCP can be selected.
       Range:0-7. 255 indicate highest possible is requested"
   ::= { lcsFaultMgmtClientConfigFlowEntry 5 }  
   
lcsFaultMgmtClientConfigFlowLCKprio OBJECT-TYPE
   SYNTAX      Integer32
   MAX-ACCESS  read-create
   STATUS      current
   DESCRIPTION
       "The priority to be used when transmitting LCK in each client flow. 
       Priority resulting in highest possible PCP can be selected.
       Range:0-7. 255 indicate highest possible is requested"
   ::= { lcsFaultMgmtClientConfigFlowEntry 6 }  
   
lcsFaultMgmtClientConfigFlowRowStatus OBJECT-TYPE
   SYNTAX      RowStatus
   MAX-ACCESS  read-create
   STATUS      current
   DESCRIPTION
       "FaultMgmtClientConfigFlow Row Status."
   ::= {lcsFaultMgmtClientConfigFlowEntry 7 }
   
   
lcsFaultMgmtAISLOCK    OBJECT IDENTIFIER ::= { lcsMEP 14 }  
   
lcsFaultMgmtAISEnable OBJECT-TYPE
   SYNTAX      Integer32
   MAX-ACCESS  read-write
   STATUS      current
   DESCRIPTION
       "Insertion of AIS signal (AIS PDU transmission) in client layer flows, can be enable/disabled.
       0:disable
       1:enable"
   ::= { lcsFaultMgmtAISLOCK 2 }  
   
lcsFaultMgmtAISFrameRate OBJECT-TYPE
   SYNTAX      Integer32
   MAX-ACCESS  read-write
   STATUS      current
   DESCRIPTION
       "Selecting the frame rate of AIS PDU. 
       This is the inverse of transmission period as described in Y.1731.
       1: 300 frames per second
       2: 100 frames per second
       3: 10 frames per second
       4: 1 frames per second
       5: 6 frames per minute
       6: 1 frames per minute
       7: 6 frames per hour"
   ::= { lcsFaultMgmtAISLOCK 3 }  
   
lcsFaultMgmtAISProtection OBJECT-TYPE
   SYNTAX      Integer32
   MAX-ACCESS  read-write
   STATUS      current
   DESCRIPTION
       "Selecting this means that the first 3 AIS PDU is transmitted as fast as possible - in case of using this for protection in the end point.
       0:disable
       1:enable"
   ::= { lcsFaultMgmtAISLOCK 4 }     
   
   
lcsFaultMgmtLOCKEnable OBJECT-TYPE
   SYNTAX      Integer32
   MAX-ACCESS  read-write
   STATUS      current
   DESCRIPTION
       "Insertion of LOCK signal (LCK PDU transmission) in client layer flows, can be enable/disabled.
       0:disable
       1:enable"
   ::= { lcsFaultMgmtAISLOCK 5 }   
   
lcsFaultMgmtLOCKFrameRate OBJECT-TYPE
   SYNTAX      Integer32
   MAX-ACCESS  read-write
   STATUS      current
   DESCRIPTION
       "Selecting the frame rate of LCK PDU. This is the inverse of transmission period as described in Y.1731.
       1: 300 frames per second
       2: 100 frames per second
       3: 10 frames per second
       4: 1 frames per second
       5: 6 frames per minute
       6: 1 frames per minute
       7: 6 frames per hour"
   ::= { lcsFaultMgmtAISLOCK 6 }  

lcsPerformanceMonitor  OBJECT IDENTIFIER ::= { lcsMEP 15 }  

lcsDataSetEnable OBJECT-TYPE
   SYNTAX      Integer32
   MAX-ACCESS  read-write
   STATUS      current
   DESCRIPTION
       "
       When enabled this MEP instance will contribute to the 'PM Data Set' gathered by the PM Session.
       0:disable
       1:enable"
   ::= { lcsPerformanceMonitor 2 }   
   
lcsLossMeasurementEnable OBJECT-TYPE
   SYNTAX      Integer32
   MAX-ACCESS  read-write
   STATUS      current
   DESCRIPTION
       "
       Loss Measurement based on transmitting/receiving CCM or LMM/LMR PDU can be enabled/disabled - see 'Ended'. 
       This is only valid with one Peer MEP configured.
       0:disable
       1:enable"
   ::= { lcsPerformanceMonitor 3 }     
   
lcsLossMeasurementPriority OBJECT-TYPE
   SYNTAX      Integer32
   MAX-ACCESS  read-write
   STATUS      current
   DESCRIPTION
       "
       The priority to be inserted as PCP bits in TAG (if any). 
       In case of enable of Continuity Check and Loss Measurement both implemented on SW based CCM, 'Priority' has to be the same.
       range:0-7"
   ::= { lcsPerformanceMonitor 4 } 
   
lcsLossMeasurementFrameRate OBJECT-TYPE
   SYNTAX      Integer32
   MAX-ACCESS  read-write
   STATUS      current
   DESCRIPTION
       "
       1: 300 frames per second
       2: 100 frames per second
       3: 10 frames per second
       4: 1 frames per second
       5: 6 frames per minute
       6: 1 frames per minute
       7: 6 frames per hour"
   ::= { lcsPerformanceMonitor 5 }   
   
lcsLossMeasurementCast OBJECT-TYPE
   SYNTAX      Integer32
   MAX-ACCESS  read-write
   STATUS      current
   DESCRIPTION
       "
       0: Unicast destination address
       1: Multicast destination address 
       "
   ::= { lcsPerformanceMonitor 6 }  
   
lcsLossMeasurementEnded OBJECT-TYPE
   SYNTAX      Integer32
   MAX-ACCESS  read-write
   STATUS      current
   DESCRIPTION
       "
       0: Single ended LM based on LMM/LMR or DM based on DMM/DMR 
       1: Dual ended LM based on CCM or DM based on 1DM
       "
   ::= { lcsPerformanceMonitor 7 }  
   
lcsLossMeasurementFLRInterval OBJECT-TYPE
   SYNTAX      Integer32
   MAX-ACCESS  read-write
   STATUS      current
   DESCRIPTION
       "
       This is the interval in seconds where the Frame Loss Ratio is calculated.
       "
   ::= { lcsPerformanceMonitor 8 }  
   
lcsLossMeasurementLossThreshold OBJECT-TYPE
   SYNTAX      Integer32
   MAX-ACCESS  read-write
   STATUS      current
   DESCRIPTION
       "
       Far end loss threshold count is incremented if a loss measurement is above this threshold.
       "
   ::= { lcsPerformanceMonitor 9 }   
    
lcsLossMeasurementStateTx OBJECT-TYPE
   SYNTAX      Integer32
   MAX-ACCESS  read-only
   STATUS      current
   DESCRIPTION
       "
       "
   ::= { lcsPerformanceMonitor 10 }     
    
lcsLossMeasurementStateRx OBJECT-TYPE
   SYNTAX      Integer32
   MAX-ACCESS  read-only
   STATUS      current
   DESCRIPTION
       "
       "
   ::= { lcsPerformanceMonitor 11 }
   
lcsLossMeasurementStateNearEndLossCount OBJECT-TYPE
   SYNTAX      Integer32
   MAX-ACCESS  read-only
   STATUS      current
   DESCRIPTION
       "The accumulated near end frame loss count - since last 'clear'.
       "
   ::= { lcsPerformanceMonitor 12 }
   
lcsLossMeasurementStateFarEndLossCount OBJECT-TYPE
   SYNTAX      Integer32
   MAX-ACCESS  read-only
   STATUS      current
   DESCRIPTION
       "The accumulated far end frame loss count - since last 'clear'.
       "
   ::= { lcsPerformanceMonitor 13 }
   
lcsLossMeasurementStateNearEndLossRatio OBJECT-TYPE
   SYNTAX      Integer32
   MAX-ACCESS  read-only
   STATUS      current
   DESCRIPTION
       "The near end frame loss ratio calculated based on the near end frame loss count and far end frame transmitted - in the latest 'FLR Interval'. 
       The result is given in percent.
       "
   ::= { lcsPerformanceMonitor 14 }
   
lcsLossMeasurementStateFarEndLossRatio OBJECT-TYPE
   SYNTAX      Integer32
   MAX-ACCESS  read-only
   STATUS      current
   DESCRIPTION
       "The far end frame loss ratio calculated based on the far end frame loss count and near end frame transmitted - in the latest 'FLR Interval'. 
       The result is given in percent.
       "
   ::= { lcsPerformanceMonitor 15 }
   
lcsLossMeasurementStateClear OBJECT-TYPE
   SYNTAX      Integer32
   MAX-ACCESS  read-write
   STATUS      current
   DESCRIPTION
       "Set of this check and save will clear the accumulated counters and restart ratio calculation.
       "
   ::= { lcsPerformanceMonitor 16 }
   
lcsLossMeasurementAvailabilityEnable OBJECT-TYPE
   SYNTAX      Integer32
   MAX-ACCESS  read-write
   STATUS      current
   DESCRIPTION
       "Enable/disable of loss measurement availability.
       0:disable
       1:enable    
       "
   ::= { lcsPerformanceMonitor 17 }
   
lcsLossMeasurementAvailabilityInterval OBJECT-TYPE
   SYNTAX      Integer32
   MAX-ACCESS  read-write
   STATUS      current
   DESCRIPTION
       "Availability interval - number of measurements with same availability in order to change availability state.
       
       "
   ::= { lcsPerformanceMonitor 18 }
   
lcsLossMeasurementAvailabilityFLRThreshold OBJECT-TYPE
   SYNTAX      Integer32
   MAX-ACCESS  read-write
   STATUS      current
   DESCRIPTION
       "Availability frame loss ratio threshold in per mille.
       "
   ::= { lcsPerformanceMonitor 19 }
   
lcsLossMeasurementAvailabilityMaintenance OBJECT-TYPE
   SYNTAX      Integer32
   MAX-ACCESS  read-write
   STATUS      current
   DESCRIPTION
       "Enable/disable of loss measurement availability maintenance.
       "
   ::= { lcsPerformanceMonitor 20 }  
   
   
lcsLossMeasurementAvailabilityStateNearAvailabilityCount OBJECT-TYPE
   SYNTAX      Integer32
   MAX-ACCESS  read-only
   STATUS      current
   DESCRIPTION
       "Near end availability count.
       "
   ::= { lcsPerformanceMonitor 21 }     
   
lcsLossMeasurementAvailabilityStateFarAvailabilityCount OBJECT-TYPE
   SYNTAX      Integer32
   MAX-ACCESS  read-only
   STATUS      current
   DESCRIPTION
       "Far end availability count.
       "
   ::= { lcsPerformanceMonitor 22 }  
   
lcsLossMeasurementAvailabilityStateNearUnavailabilityCount OBJECT-TYPE
   SYNTAX      Integer32
   MAX-ACCESS  read-only
   STATUS      current
   DESCRIPTION
       "Near end unavailability count.
       "
   ::= { lcsPerformanceMonitor 23 }  
   
lcsLossMeasurementAvailabilityStateFarUnavailabilityCount OBJECT-TYPE
   SYNTAX      Integer32
   MAX-ACCESS  read-only
   STATUS      current
   DESCRIPTION
       "Far end unavailability count.
       "
   ::= { lcsPerformanceMonitor 24 }  
   
lcsLossMeasurementAvailabilityStateNearState OBJECT-TYPE
   SYNTAX      Integer32
   MAX-ACCESS  read-only
   STATUS      current
   DESCRIPTION
       "Near end availability state.
       "
   ::= { lcsPerformanceMonitor 25 }  
   
lcsLossMeasurementAvailabilityStateFarState OBJECT-TYPE
   SYNTAX      Integer32
   MAX-ACCESS  read-only
   STATUS      current
   DESCRIPTION
       "Far end availability state.
       "
   ::= { lcsPerformanceMonitor 26 }  
   
lcsLossMeasurementHighLossIntervalEnable OBJECT-TYPE
   SYNTAX      Integer32
   MAX-ACCESS  read-write
   STATUS      current
   DESCRIPTION
       "Enable/disable of loss measurement high loss interval.
       0:disable
       1:enable  
       "
   ::= { lcsPerformanceMonitor 27 }  
   
lcsLossMeasurementHighLossIntervalFLRThreshold OBJECT-TYPE
   SYNTAX      Integer32
   MAX-ACCESS  read-write
   STATUS      current
   DESCRIPTION
       "High Loss Interval frame loss ratio threshold in per mille.
       "
   ::= { lcsPerformanceMonitor 28 }  
   
lcsLossMeasurementHighLossIntervalConsecutiveInterval OBJECT-TYPE
   SYNTAX      Integer32
   MAX-ACCESS  read-write
   STATUS      current
   DESCRIPTION
       "High Loss Interval consecutive interval (number of measurements).
       "
   ::= { lcsPerformanceMonitor 29 }   
   
lcsLossMeasurementHighLossIntervalStateNearCount OBJECT-TYPE
   SYNTAX      Integer32
   MAX-ACCESS  read-only
   STATUS      current
   DESCRIPTION
       "Near end high loss interval count (number of measurements where availability state is available and FLR is above high loss interval FLR threshold.
       "
   ::= { lcsPerformanceMonitor 30 }   
   
lcsLossMeasurementHighLossIntervalStateFarCount OBJECT-TYPE
   SYNTAX      Integer32
   MAX-ACCESS  read-only
   STATUS      current
   DESCRIPTION
       "Far end high loss interval count (number of measurements where availability state is available and FLR is above high loss interval FLR threshold.
       "
   ::= { lcsPerformanceMonitor 31 }  
   
lcsLossMeasurementHighLossIntervalStateNearConsecutiveCount OBJECT-TYPE
   SYNTAX      Integer32
   MAX-ACCESS  read-only
   STATUS      current
   DESCRIPTION
       "Near end high loss interval consecutive count.
       "
   ::= { lcsPerformanceMonitor 32 }  
   
lcsLossMeasurementHighLossIntervalStateFarConsecutiveCount OBJECT-TYPE
   SYNTAX      Integer32
   MAX-ACCESS  read-only
   STATUS      current
   DESCRIPTION
       "Far end high loss interval consecutive count.
       "
   ::= { lcsPerformanceMonitor 33 } 
   
lcsLossMeasurementSignalDegradeEnable OBJECT-TYPE
   SYNTAX      Integer32
   MAX-ACCESS  read-write
   STATUS      current
   DESCRIPTION
       "Enable/disable of loss measurement signal degrade.
       0:disable
       1:enable        
       "
   ::= { lcsPerformanceMonitor 34 } 
   
lcsLossMeasurementSignalDegradeTXMinimum OBJECT-TYPE
   SYNTAX      Integer32
   MAX-ACCESS  read-write
   STATUS      current
   DESCRIPTION
       "Minimum number of frames that must be transmitted in a measurement before frame loss ratio is tested against loss ratio threshold.
       
       "
   ::= { lcsPerformanceMonitor 35 } 
   
lcsLossMeasurementSignalDegradeFLRThreshold OBJECT-TYPE
   SYNTAX      Integer32
   MAX-ACCESS  read-write
   STATUS      current
   DESCRIPTION
       "Signal Degraded frame loss ratio threshold in per mille.
       "
   ::= { lcsPerformanceMonitor 36 } 
   
lcsLossMeasurementSignalDegradeBadThreshold OBJECT-TYPE
   SYNTAX      Integer32
   MAX-ACCESS  read-write
   STATUS      current
   DESCRIPTION
       "Number of consecutive bad interval measurements required to set degrade state.
       "
   ::= { lcsPerformanceMonitor 37 }    
   
lcsLossMeasurementSignalDegradeGoodThreshold OBJECT-TYPE
   SYNTAX      Integer32
   MAX-ACCESS  read-write
   STATUS      current
   DESCRIPTION
       "Number of consecutive good interval measurements required to clear degrade state.
       "
   ::= { lcsPerformanceMonitor 38 } 
   
lcsDelayMeasurementEnable OBJECT-TYPE
   SYNTAX      Integer32
   MAX-ACCESS  read-write
   STATUS      current
   DESCRIPTION
       "Delay Measurement based on transmitting 1DM/DMM PDU can be enabled/disabled. 
       Delay Measurement based on receiving and handling 1DM/DMR PDU is always enabled.
       0:disable
       1:enable        
       "
   ::= { lcsPerformanceMonitor 39 } 
   
lcsDelayMeasurementPriority OBJECT-TYPE
   SYNTAX      Integer32
   MAX-ACCESS  read-write
   STATUS      current
   DESCRIPTION
       "The priority to be inserted as PCP bits in TAG (if any).
       Range:0-7       
       "
   ::= { lcsPerformanceMonitor 40 }  
   
lcsDelayMeasurementCast OBJECT-TYPE
   SYNTAX      Integer32
   MAX-ACCESS  read-write
   STATUS      current
   DESCRIPTION
       "Selection of 1DM/DMM PDU transmitted unicast or multicast. 
       The unicast MAC will be configured through 'Peer MEP'.   
       0: Unicast destination address
       1: Multicast destination address        
       "
   ::= { lcsPerformanceMonitor 41 } 
   
lcsDelayMeasurementPeerMEP OBJECT-TYPE
   SYNTAX      Integer32
   MAX-ACCESS  read-write
   STATUS      current
   DESCRIPTION
       "This is only used if the 'Cast' is configured to Uni. 
       The 1DM/DMR unicast MAC will be taken from the 'Unicast Peer MAC' configuration of this peer. 
       "
   ::= { lcsPerformanceMonitor 42 } 
   
lcsDelayMeasurementEnded OBJECT-TYPE
   SYNTAX      Integer32
   MAX-ACCESS  read-write
   STATUS      current
   DESCRIPTION
       "0:One-Way: One-Way Delay Measurement implemented on 1DM.
        1:Two-Way: Two-Way Delay Measurement implemented on DMM/DMR.
       "
   ::= { lcsPerformanceMonitor 43 } 
   
lcsDelayMeasurementTxMode OBJECT-TYPE
   SYNTAX      Integer32
   MAX-ACCESS  read-write
   STATUS      current
   DESCRIPTION
       "0:Standardize: Y.1731 standardize way to transmit 1DM/DMR.
        1:Proprietary: Vitesse proprietary way with follow-up packets to transmit 1DM/DMR.
       "
   ::= { lcsPerformanceMonitor 44 } 
   
lcsDelayMeasurementCalc OBJECT-TYPE
   SYNTAX      Integer32
   MAX-ACCESS  read-write
   STATUS      current
   DESCRIPTION
       "This is only used if the 'Way' is configured to Two-way.
        0:Round trip: The frame delay calculated by the transmitting and receiving timestamps of initiators. 
            Frame Delay = RxTimeb-TxTimeStampf
        1:Flow: The frame delay calculated by the transmitting and receiving timestamps of initiators and remotes. 
            Frame Delay = (RxTimeb-TxTimeStampf)-(TxTimeStampb-RxTimeStampf)
       "
   ::= { lcsPerformanceMonitor 45 } 
   
lcsDelayMeasurementGap OBJECT-TYPE
   SYNTAX      Integer32
   MAX-ACCESS  read-write
   STATUS      current
   DESCRIPTION
       "The gap between transmitting 1DM/DMM PDU in 10ms. The range is 10 to 65535.
       "
   ::= { lcsPerformanceMonitor 46 } 

lcsDelayMeasurementCount OBJECT-TYPE
   SYNTAX      Integer32
   MAX-ACCESS  read-write
   STATUS      current
   DESCRIPTION
       "The number of last records to calculate. The range is 10 to 2000.
       "
   ::= { lcsPerformanceMonitor 47 } 
   
lcsDelayMeasurementUnit OBJECT-TYPE
   SYNTAX      Integer32
   MAX-ACCESS  read-write
   STATUS      current
   DESCRIPTION
       "The time resolution.
       0:us
       1:ns
       "
   ::= { lcsPerformanceMonitor 48 }  
   
lcsDelayMeasurementD2forD1 OBJECT-TYPE
   SYNTAX      Integer32
   MAX-ACCESS  read-write
   STATUS      current
   DESCRIPTION
       "Enable to use DMM/DMR packet to calculate one-way DM.
       0:disable
       1:enable 
       "
   ::= { lcsPerformanceMonitor 49 }  
   
lcsDelayMeasurementCounterOverflowAction OBJECT-TYPE
   SYNTAX      Integer32
   MAX-ACCESS  read-write
   STATUS      current
   DESCRIPTION
       "The action to counter when overflow happens.
       0: Keep:When internal total delay counter overflow, DM is disabled automatically
       1: Reset:When internal total delay counter overflow, counter is reset and DM continues running
       "
   ::= { lcsPerformanceMonitor 50 }  
   
lcsDelayMeasurementStateOnewayTx OBJECT-TYPE
   SYNTAX      DisplayString
   MAX-ACCESS  read-only
   STATUS      current
   DESCRIPTION
       "The accumulated transmit count - since last 'clear'.
       "
   ::= { lcsPerformanceMonitor 51 } 
   
lcsDelayMeasurementStateOnewayRx OBJECT-TYPE
   SYNTAX      DisplayString
   MAX-ACCESS  read-only
   STATUS      current
   DESCRIPTION
       "The accumulated receive count - since last 'clear'.
       "
   ::= { lcsPerformanceMonitor 52 } 
   
lcsDelayMeasurementStateOnewayRxTimeout OBJECT-TYPE
   SYNTAX      DisplayString
   MAX-ACCESS  read-only
   STATUS      current
   DESCRIPTION
       "The accumulated receive timeout count for two-way only - since last 'clear'.
       "
   ::= { lcsPerformanceMonitor 53 } 
   
lcsDelayMeasurementStateOnewayRxError OBJECT-TYPE
   SYNTAX      DisplayString
   MAX-ACCESS  read-only
   STATUS      current
   DESCRIPTION
       "The accumulated receive error count - since last 'clear'. 
       This is counting if the frame delay is larger than 1 second or if far end residence time is larger than the round trip time.
       "
   ::= { lcsPerformanceMonitor 54 }
   
lcsDelayMeasurementStateOnewayAvDelayTot OBJECT-TYPE
   SYNTAX      DisplayString
   MAX-ACCESS  read-only
   STATUS      current
   DESCRIPTION
       "The average total delay - since last 'clear'.
       "
   ::= { lcsPerformanceMonitor 55 }
   
lcsDelayMeasurementStateOnewayAvDelaylastN OBJECT-TYPE
   SYNTAX      DisplayString
   MAX-ACCESS  read-only
   STATUS      current
   DESCRIPTION
       "The average delay of the last n packets - since last 'clear'.
       "
   ::= { lcsPerformanceMonitor 56 }
   
lcsDelayMeasurementStateOnewayDelayMin OBJECT-TYPE
   SYNTAX      DisplayString
   MAX-ACCESS  read-only
   STATUS      current
   DESCRIPTION
       "The minimum delay - since last 'clear'.
       "
   ::= { lcsPerformanceMonitor 57 }
   
lcsDelayMeasurementStateOnewayDelayMax OBJECT-TYPE
   SYNTAX      DisplayString
   MAX-ACCESS  read-only
   STATUS      current
   DESCRIPTION
       "The maximum delay - since last 'clear'.
       "
   ::= { lcsPerformanceMonitor 58 }
   
lcsDelayMeasurementStateOnewayAvDelayVarTot OBJECT-TYPE
   SYNTAX      DisplayString
   MAX-ACCESS  read-only
   STATUS      current
   DESCRIPTION
       "The average total delay variation - since last 'clear'.
       "
   ::= { lcsPerformanceMonitor 59 }
   
lcsDelayMeasurementStateOnewayAvDelayVarlastN OBJECT-TYPE
   SYNTAX      DisplayString
   MAX-ACCESS  read-only
   STATUS      current
   DESCRIPTION
       "The average delay variation of the last n packets - since last 'clear'.
       "
   ::= { lcsPerformanceMonitor 60 }
   
lcsDelayMeasurementStateOnewayDelayVarMin OBJECT-TYPE
   SYNTAX      DisplayString
   MAX-ACCESS  read-only
   STATUS      current
   DESCRIPTION
       "The minimum delay variation - since last 'clear'.
       "
   ::= { lcsPerformanceMonitor 61 }
   
lcsDelayMeasurementStateOnewayDelayVarMax OBJECT-TYPE
   SYNTAX      DisplayString
   MAX-ACCESS  read-only
   STATUS      current
   DESCRIPTION
       "The maximum delay variation - since last 'clear'.
       "
   ::= { lcsPerformanceMonitor 62 }
   
lcsDelayMeasurementStateOnewayOverflow OBJECT-TYPE
   SYNTAX      DisplayString
   MAX-ACCESS  read-only
   STATUS      current
   DESCRIPTION
       "The number of counter overflow - since last 'clear'.
       "
   ::= { lcsPerformanceMonitor 63 }
   
lcsDelayMeasurementStateFtoNTx OBJECT-TYPE
   SYNTAX      Integer32
   MAX-ACCESS  read-only
   STATUS      current
   DESCRIPTION
       "The accumulated transmit count - since last 'clear'.
       "
   ::= { lcsPerformanceMonitor 64 } 
   
lcsDelayMeasurementStateFtoNRx OBJECT-TYPE
   SYNTAX      Integer32
   MAX-ACCESS  read-only
   STATUS      current
   DESCRIPTION
       "The accumulated receive count - since last 'clear'.
       "
   ::= { lcsPerformanceMonitor 65 } 
   
lcsDelayMeasurementStateFtoNRxTimeout OBJECT-TYPE
   SYNTAX      Integer32
   MAX-ACCESS  read-only
   STATUS      current
   DESCRIPTION
       "The accumulated receive timeout count for two-way only - since last 'clear'.
       "
   ::= { lcsPerformanceMonitor 66 } 
   
lcsDelayMeasurementStateFtoNRxError OBJECT-TYPE
   SYNTAX      Integer32
   MAX-ACCESS  read-only
   STATUS      current
   DESCRIPTION
       "The accumulated receive error count - since last 'clear'. 
       This is counting if the frame delay is larger than 1 second or if far end residence time is larger than the round trip time.
       "
   ::= { lcsPerformanceMonitor 67 }
   
lcsDelayMeasurementStateFtoNAvDelayTot OBJECT-TYPE
   SYNTAX      Integer32
   MAX-ACCESS  read-only
   STATUS      current
   DESCRIPTION
       "The average total delay - since last 'clear'.
       "
   ::= { lcsPerformanceMonitor 68 }
   
lcsDelayMeasurementStateFtoNAvDelaylastN OBJECT-TYPE
   SYNTAX      Integer32
   MAX-ACCESS  read-only
   STATUS      current
   DESCRIPTION
       "The average delay of the last n packets - since last 'clear'.
       "
   ::= { lcsPerformanceMonitor 69 }
   
lcsDelayMeasurementStateFtoNDelayMin OBJECT-TYPE
   SYNTAX      Integer32
   MAX-ACCESS  read-only
   STATUS      current
   DESCRIPTION
       "The minimum delay - since last 'clear'.
       "
   ::= { lcsPerformanceMonitor 70 }
   
lcsDelayMeasurementStateFtoNDelayMax OBJECT-TYPE
   SYNTAX      Integer32
   MAX-ACCESS  read-only
   STATUS      current
   DESCRIPTION
       "The maximum delay - since last 'clear'.
       "
   ::= { lcsPerformanceMonitor 71 }
   
lcsDelayMeasurementStateFtoNAvDelayVarTot OBJECT-TYPE
   SYNTAX      Integer32
   MAX-ACCESS  read-only
   STATUS      current
   DESCRIPTION
       "The average total delay variation - since last 'clear'.
       "
   ::= { lcsPerformanceMonitor 72 }
   
lcsDelayMeasurementStateFtoNAvDelayVarlastN OBJECT-TYPE
   SYNTAX      Integer32
   MAX-ACCESS  read-only
   STATUS      current
   DESCRIPTION
       "The average delay variation of the last n packets - since last 'clear'.
       "
   ::= { lcsPerformanceMonitor 73 }
   
lcsDelayMeasurementStateFtoNDelayVarMin OBJECT-TYPE
   SYNTAX      Integer32
   MAX-ACCESS  read-only
   STATUS      current
   DESCRIPTION
       "The minimum delay variation - since last 'clear'.
       "
   ::= { lcsPerformanceMonitor 74 }
   
lcsDelayMeasurementStateFtoNDelayVarMax OBJECT-TYPE
   SYNTAX      Integer32
   MAX-ACCESS  read-only
   STATUS      current
   DESCRIPTION
       "The maximum delay variation - since last 'clear'.
       "
   ::= { lcsPerformanceMonitor 75 }
   
lcsDelayMeasurementStateFtoNOverflow OBJECT-TYPE
   SYNTAX      Integer32
   MAX-ACCESS  read-only
   STATUS      current
   DESCRIPTION
       "The number of counter overflow - since last 'clear'.
       "
   ::= { lcsPerformanceMonitor 76 }
   
lcsDelayMeasurementStateNtoFTx OBJECT-TYPE
   SYNTAX      Integer32
   MAX-ACCESS  read-only
   STATUS      current
   DESCRIPTION
       "The accumulated transmit count - since last 'clear'.
       "
   ::= { lcsPerformanceMonitor 77 } 
   
lcsDelayMeasurementStateNtoFRx OBJECT-TYPE
   SYNTAX      Integer32
   MAX-ACCESS  read-only
   STATUS      current
   DESCRIPTION
       "The accumulated receive count - since last 'clear'.
       "
   ::= { lcsPerformanceMonitor 78 } 
   
lcsDelayMeasurementStateNtoFRxTimeout OBJECT-TYPE
   SYNTAX      Integer32
   MAX-ACCESS  read-only
   STATUS      current
   DESCRIPTION
       "The accumulated receive timeout count for two-way only - since last 'clear'.
       "
   ::= { lcsPerformanceMonitor 79 } 
   
lcsDelayMeasurementStateNtoFRxError OBJECT-TYPE
   SYNTAX      Integer32
   MAX-ACCESS  read-only
   STATUS      current
   DESCRIPTION
       "The accumulated receive error count - since last 'clear'. 
       This is counting if the frame delay is larger than 1 second or if far end residence time is larger than the round trip time.
       "
   ::= { lcsPerformanceMonitor 80 }
   
lcsDelayMeasurementStateNtoFAvDelayTot OBJECT-TYPE
   SYNTAX      Integer32
   MAX-ACCESS  read-only
   STATUS      current
   DESCRIPTION
       "The average total delay - since last 'clear'.
       "
   ::= { lcsPerformanceMonitor 81 }
   
lcsDelayMeasurementStateNtoFAvDelaylastN OBJECT-TYPE
   SYNTAX      Integer32
   MAX-ACCESS  read-only
   STATUS      current
   DESCRIPTION
       "The average delay of the last n packets - since last 'clear'.
       "
   ::= { lcsPerformanceMonitor 82 }
   
lcsDelayMeasurementStateNtoFDelayMin OBJECT-TYPE
   SYNTAX      Integer32
   MAX-ACCESS  read-only
   STATUS      current
   DESCRIPTION
       "The minimum delay - since last 'clear'.
       "
   ::= { lcsPerformanceMonitor 83 }
   
lcsDelayMeasurementStateNtoFDelayMax OBJECT-TYPE
   SYNTAX      Integer32
   MAX-ACCESS  read-only
   STATUS      current
   DESCRIPTION
       "The maximum delay - since last 'clear'.
       "
   ::= { lcsPerformanceMonitor 84 }
   
lcsDelayMeasurementStateNtoFAvDelayVarTot OBJECT-TYPE
   SYNTAX      Integer32
   MAX-ACCESS  read-only
   STATUS      current
   DESCRIPTION
       "The average total delay variation - since last 'clear'.
       "
   ::= { lcsPerformanceMonitor 85 }
   
lcsDelayMeasurementStateNtoFAvDelayVarlastN OBJECT-TYPE
   SYNTAX      Integer32
   MAX-ACCESS  read-only
   STATUS      current
   DESCRIPTION
       "The average delay variation of the last n packets - since last 'clear'.
       "
   ::= { lcsPerformanceMonitor 86 }
   
lcsDelayMeasurementStateNtoFDelayVarMin OBJECT-TYPE
   SYNTAX      Integer32
   MAX-ACCESS  read-only
   STATUS      current
   DESCRIPTION
       "The minimum delay variation - since last 'clear'.
       "
   ::= { lcsPerformanceMonitor 87 }
   
lcsDelayMeasurementStateNtoFDelayVarMax OBJECT-TYPE
   SYNTAX      Integer32
   MAX-ACCESS  read-only
   STATUS      current
   DESCRIPTION
       "The maximum delay variation - since last 'clear'.
       "
   ::= { lcsPerformanceMonitor 88 }
   
lcsDelayMeasurementStateNtoFOverflow OBJECT-TYPE
   SYNTAX      Integer32
   MAX-ACCESS  read-only
   STATUS      current
   DESCRIPTION
       "The number of counter overflow - since last 'clear'.
       "
   ::= { lcsPerformanceMonitor 89 }
   
lcsDelayMeasurementStateTwowayTx OBJECT-TYPE
   SYNTAX      Integer32
   MAX-ACCESS  read-only
   STATUS      current
   DESCRIPTION
       "The accumulated transmit count - since last 'clear'.
       "
   ::= { lcsPerformanceMonitor 90 } 
   
lcsDelayMeasurementStateTwowayRx OBJECT-TYPE
   SYNTAX      Integer32
   MAX-ACCESS  read-only
   STATUS      current
   DESCRIPTION
       "The accumulated receive count - since last 'clear'.
       "
   ::= { lcsPerformanceMonitor 91 } 
   
lcsDelayMeasurementStateTwowayRxTimeout OBJECT-TYPE
   SYNTAX      Integer32
   MAX-ACCESS  read-only
   STATUS      current
   DESCRIPTION
       "The accumulated receive timeout count for two-way only - since last 'clear'.
       "
   ::= { lcsPerformanceMonitor 92 } 
   
lcsDelayMeasurementStateTwowayRxError OBJECT-TYPE
   SYNTAX      Integer32
   MAX-ACCESS  read-only
   STATUS      current
   DESCRIPTION
       "The accumulated receive error count - since last 'clear'. 
       This is counting if the frame delay is larger than 1 second or if far end residence time is larger than the round trip time.
       "
   ::= { lcsPerformanceMonitor 93 }
   
lcsDelayMeasurementStateTwowayAvDelayTot OBJECT-TYPE
   SYNTAX      Integer32
   MAX-ACCESS  read-only
   STATUS      current
   DESCRIPTION
       "The average total delay - since last 'clear'.
       "
   ::= { lcsPerformanceMonitor 94 }
   
lcsDelayMeasurementStateTwowayAvDelaylastN OBJECT-TYPE
   SYNTAX      Integer32
   MAX-ACCESS  read-only
   STATUS      current
   DESCRIPTION
       "The average delay of the last n packets - since last 'clear'.
       "
   ::= { lcsPerformanceMonitor 95 }
   
lcsDelayMeasurementStateTwowayDelayMin OBJECT-TYPE
   SYNTAX      Integer32
   MAX-ACCESS  read-only
   STATUS      current
   DESCRIPTION
       "The minimum delay - since last 'clear'.
       "
   ::= { lcsPerformanceMonitor 96 }
   
lcsDelayMeasurementStateTwowayDelayMax OBJECT-TYPE
   SYNTAX      Integer32
   MAX-ACCESS  read-only
   STATUS      current
   DESCRIPTION
       "The maximum delay - since last 'clear'.
       "
   ::= { lcsPerformanceMonitor 97 }
   
lcsDelayMeasurementStateTwowayAvDelayVarTot OBJECT-TYPE
   SYNTAX      Integer32
   MAX-ACCESS  read-only
   STATUS      current
   DESCRIPTION
       "The average total delay variation - since last 'clear'.
       "
   ::= { lcsPerformanceMonitor 98 }
   
lcsDelayMeasurementStateTwowayAvDelayVarlastN OBJECT-TYPE
   SYNTAX      Integer32
   MAX-ACCESS  read-only
   STATUS      current
   DESCRIPTION
       "The average delay variation of the last n packets - since last 'clear'.
       "
   ::= { lcsPerformanceMonitor 99 }
   
lcsDelayMeasurementStateTwowayDelayVarMin OBJECT-TYPE
   SYNTAX      Integer32
   MAX-ACCESS  read-only
   STATUS      current
   DESCRIPTION
       "The minimum delay variation - since last 'clear'.
       "
   ::= { lcsPerformanceMonitor 100 }
   
lcsDelayMeasurementStateTwowayDelayVarMax OBJECT-TYPE
   SYNTAX      Integer32
   MAX-ACCESS  read-only
   STATUS      current
   DESCRIPTION
       "The maximum delay variation - since last 'clear'.
       "
   ::= { lcsPerformanceMonitor 101 }
   
lcsDelayMeasurementStateTwowayOverflow OBJECT-TYPE
   SYNTAX      Integer32
   MAX-ACCESS  read-only
   STATUS      current
   DESCRIPTION
       "The number of counter overflow - since last 'clear'.
       "
   ::= { lcsPerformanceMonitor 102 }
   
lcsDelayMeasurementStateClear OBJECT-TYPE
   SYNTAX      Integer32
   MAX-ACCESS  read-write
   STATUS      current
   DESCRIPTION
       "Set of this check and save will clear the accumulated counters.
       1:clear
       "
   ::= { lcsPerformanceMonitor 103 }
   
lcsDelayMeasurementBinsMeasurementBinsforFD OBJECT-TYPE
   SYNTAX      Integer32
   MAX-ACCESS  read-write
   STATUS      current
   DESCRIPTION
       "Configurable number of Frame Delay Measurement Bins per Measurement Interval.
       range: 2-10
       "
   ::= { lcsPerformanceMonitor 104 }
   
lcsDelayMeasurementBinsMeasurementBinsforIFDV OBJECT-TYPE
   SYNTAX      Integer32
   MAX-ACCESS  read-write
   STATUS      current
   DESCRIPTION
       "Configurable number of Inter-Frame Delay Variation Measurement Bins per Measurement Interval.
       range: 2-10
       "
   ::= { lcsPerformanceMonitor 105 }
   
lcsDelayMeasurementBinsMeasurementThreshold OBJECT-TYPE
   SYNTAX      Integer32
   MAX-ACCESS  read-write
   STATUS      current
   DESCRIPTION
       "Configurable the Measurement Threshold for each Measurement Bin.
       "
   ::= { lcsPerformanceMonitor 106 }
   
   
   
   
lcsPerformanceMonitorDelayMeasurementBinsforFDTable OBJECT-TYPE
   SYNTAX      SEQUENCE OF LCSPerformanceMonitorDelayMeasurementBinsforFDEntry
   MAX-ACCESS  not-accessible
   STATUS      current
   DESCRIPTION
       " "
   ::= { lcsMEP 16 }

lcsPerformanceMonitorDelayMeasurementBinsforFDEntry OBJECT-TYPE
   SYNTAX      LCSPerformanceMonitorDelayMeasurementBinsforFDEntry
   MAX-ACCESS  not-accessible
   STATUS      current
   DESCRIPTION
       " "
   INDEX    { lcsPerformanceMonitorDelayMeasurementBinsforFDIndex  }
   ::= { lcsPerformanceMonitorDelayMeasurementBinsforFDTable 1 }

LCSPerformanceMonitorDelayMeasurementBinsforFDEntry ::= SEQUENCE {
   lcsPerformanceMonitorDelayMeasurementBinsforFDIndex    Integer32,
   lcsPerformanceMonitorDelayMeasurementBinsforFDOneway   Integer32,
   lcsPerformanceMonitorDelayMeasurementBinsforFDFtoN     Integer32,
   lcsPerformanceMonitorDelayMeasurementBinsforFDNtoF     Integer32,
   lcsPerformanceMonitorDelayMeasurementBinsforFDTwoway   Integer32
   
}

lcsPerformanceMonitorDelayMeasurementBinsforFDIndex OBJECT-TYPE
   SYNTAX      Integer32 (1..65535)
   MAX-ACCESS  not-accessible
   STATUS      current
   DESCRIPTION
       "Index"
   ::= { lcsPerformanceMonitorDelayMeasurementBinsforFDEntry 1 }

lcsPerformanceMonitorDelayMeasurementBinsforFDOneway OBJECT-TYPE
   SYNTAX      Integer32
   MAX-ACCESS  read-only
   STATUS      current
   DESCRIPTION
       " "
   ::= { lcsPerformanceMonitorDelayMeasurementBinsforFDEntry 2 }

lcsPerformanceMonitorDelayMeasurementBinsforFDFtoN OBJECT-TYPE
   SYNTAX      Integer32
   MAX-ACCESS  read-only
   STATUS      current
   DESCRIPTION
       " "
   ::= { lcsPerformanceMonitorDelayMeasurementBinsforFDEntry 3 }
   
lcsPerformanceMonitorDelayMeasurementBinsforFDNtoF OBJECT-TYPE
   SYNTAX      Integer32
   MAX-ACCESS  read-only
   STATUS      current
   DESCRIPTION
       " "
   ::= { lcsPerformanceMonitorDelayMeasurementBinsforFDEntry 4 }  
   
lcsPerformanceMonitorDelayMeasurementBinsforFDTwoway OBJECT-TYPE
   SYNTAX      Integer32
   MAX-ACCESS  read-only
   STATUS      current
   DESCRIPTION
       " "
   ::= { lcsPerformanceMonitorDelayMeasurementBinsforFDEntry 5 } 
   
   
   
   
lcsPerformanceMonitorDelayMeasurementBinsforIFDVTable OBJECT-TYPE
   SYNTAX      SEQUENCE OF LCSPerformanceMonitorDelayMeasurementBinsforIFDVEntry
   MAX-ACCESS  not-accessible
   STATUS      current
   DESCRIPTION
       " "
   ::= { lcsMEP 17 }

lcsPerformanceMonitorDelayMeasurementBinsforIFDVEntry OBJECT-TYPE
   SYNTAX      LCSPerformanceMonitorDelayMeasurementBinsforIFDVEntry
   MAX-ACCESS  not-accessible
   STATUS      current
   DESCRIPTION
       " "
   INDEX    { lcsPerformanceMonitorDelayMeasurementBinsforIFDVIndex  }
   ::= { lcsPerformanceMonitorDelayMeasurementBinsforIFDVTable 1 }

LCSPerformanceMonitorDelayMeasurementBinsforIFDVEntry ::= SEQUENCE {
   lcsPerformanceMonitorDelayMeasurementBinsforIFDVIndex    Integer32,
   lcsPerformanceMonitorDelayMeasurementBinsforIFDVOneway   Integer32,
   lcsPerformanceMonitorDelayMeasurementBinsforIFDVFtoN     Integer32,
   lcsPerformanceMonitorDelayMeasurementBinsforIFDVNtoF     Integer32,
   lcsPerformanceMonitorDelayMeasurementBinsforIFDVTwoway   Integer32
   
}

lcsPerformanceMonitorDelayMeasurementBinsforIFDVIndex OBJECT-TYPE
   SYNTAX      Integer32 (1..65535)
   MAX-ACCESS  not-accessible
   STATUS      current
   DESCRIPTION
       "Index"
   ::= { lcsPerformanceMonitorDelayMeasurementBinsforIFDVEntry 1 }

lcsPerformanceMonitorDelayMeasurementBinsforIFDVOneway OBJECT-TYPE
   SYNTAX      Integer32
   MAX-ACCESS  read-only
   STATUS      current
   DESCRIPTION
       " "
   ::= { lcsPerformanceMonitorDelayMeasurementBinsforIFDVEntry 2 }

lcsPerformanceMonitorDelayMeasurementBinsforIFDVFtoN OBJECT-TYPE
   SYNTAX      Integer32
   MAX-ACCESS  read-only
   STATUS      current
   DESCRIPTION
       " "
   ::= { lcsPerformanceMonitorDelayMeasurementBinsforIFDVEntry 3 }
   
lcsPerformanceMonitorDelayMeasurementBinsforIFDVNtoF OBJECT-TYPE
   SYNTAX      Integer32
   MAX-ACCESS  read-only
   STATUS      current
   DESCRIPTION
       " "
   ::= { lcsPerformanceMonitorDelayMeasurementBinsforIFDVEntry 4 }  
   
lcsPerformanceMonitorDelayMeasurementBinsforIFDVTwoway OBJECT-TYPE
   SYNTAX      Integer32
   MAX-ACCESS  read-only
   STATUS      current
   DESCRIPTION
       " "
   ::= { lcsPerformanceMonitorDelayMeasurementBinsforIFDVEntry 5 } 
-- =============================================================================================================   
lcsPTP    OBJECT IDENTIFIER ::= { lcsConfiguration 28 }   
   
lcsPTPExternalEnable OBJECT-TYPE
   SYNTAX      Integer32
   MAX-ACCESS  read-write
   STATUS      current
   DESCRIPTION
       "This Selection box will allow you to configure the External Clock output.
        The following values are possible:
        1. True : Enable the external clock output
        0. False : Disable the external clock output
        "
   ::= { lcsPTP 1 }   
   
lcsPTPAdjustMethod OBJECT-TYPE
   SYNTAX      Integer32
   MAX-ACCESS  read-write
   STATUS      current
   DESCRIPTION
       "This Selection box will allow you to configure the Frequency adjustment configuration.
        0: LTC frequency : Select Local Time Counter (LTC) frequency control
        1: SyncE-DPLL : Select SyncE DPLL frequency control, if allowed by SyncE
        2: Oscillator : Select an oscillator independent of SyncE for frequency control, if supported by the HW
        3: LTC phase : Select Local Time Counter (LTC) phase control (assumes that the frequency is locked by means of SyncE)
        "
   ::= { lcsPTP 2 }      
   
lcsPTPClockFrequency OBJECT-TYPE
   SYNTAX      Integer32
   MAX-ACCESS  read-write
   STATUS      current
   DESCRIPTION
       "This will allow to set the Clock Frequency.
        The possible range of values are 1 - 25000000 (1 - 25MHz)
       "
   ::= { lcsPTP 3 }   
   


lcsPTPClockConfTable  OBJECT-TYPE
   SYNTAX      SEQUENCE OF LCSPTPClockConfEntry
   MAX-ACCESS  not-accessible
   STATUS      current
   DESCRIPTION
       "A table of PTP Clock Conf."
 ::= { lcsPTP 5 }

lcsPTPClockConfEntry OBJECT-TYPE
    SYNTAX        LCSPTPClockConfEntry
    MAX-ACCESS    not-accessible
    STATUS        current
    DESCRIPTION
        "An entry in the PTP Clock Conf table."
    INDEX        { lcsPTPClockConfIndex }
    ::= { lcsPTPClockConfTable 1 }

LCSPTPClockConfEntry ::=
    SEQUENCE {
        lcsPTPClockConfIndex                    Integer32,
        lcsPTPClockConfClockInstance            Integer32,
        lcsPTPClockConfDeviceType               Integer32,
        lcsPTPClockConfProfile                  Integer32,
        lcsPTPClockConfRowStatus                RowStatus
    }

lcsPTPClockConfIndex OBJECT-TYPE
   SYNTAX      Integer32 (1..65535)
   MAX-ACCESS  not-accessible
   STATUS      current
   DESCRIPTION
       "PTP Clock Conf index."
   ::= {lcsPTPClockConfEntry 1 }

lcsPTPClockConfClockInstance OBJECT-TYPE
   SYNTAX      Integer32
   MAX-ACCESS  read-create
   STATUS      current
   DESCRIPTION
       "Indicates the Instance of a particular Clock Instance [0..3]."
   ::= {lcsPTPClockConfEntry 2 }

lcsPTPClockConfDeviceType OBJECT-TYPE
   SYNTAX      Integer32
   MAX-ACCESS  read-create
   STATUS      current
   DESCRIPTION
       "Indicates the Type of the Clock Instance. There are five Device Types.
        0: Inactive - passive clock instance
        1: Ord-Bound - clock's Device Type is Ordinary-Boundary Clock.
        2: P2p Transp - clock's Device Type is Peer to Peer Transparent Clock.
        3: E2e Transp - clock's Device Type is End to End Transparent Clock.
        4: Master Only - clock's Device Type is Master Only.
        5: Slave Only - clock's Device Type is Slave Only.
        6: Boundary Clock frontend clock instance, only 1-step, 1-way is supported."
   ::= {lcsPTPClockConfEntry 3 }
   
lcsPTPClockConfProfile OBJECT-TYPE
   SYNTAX      Integer32
   MAX-ACCESS  read-create
   STATUS      current
   DESCRIPTION
       "0:No profile
       1:1588
       2:G8265.1
       3:G8275.1
       "
   ::= {lcsPTPClockConfEntry 4 }   
   
lcsPTPClockConfRowStatus OBJECT-TYPE
   SYNTAX      RowStatus
   MAX-ACCESS  read-create
   STATUS      current
   DESCRIPTION
       "PTP Clock Conf Row Status."
   ::= {lcsPTPClockConfEntry 5 }
   
lcsPTPClockInstance OBJECT-TYPE
   SYNTAX      Integer32
   MAX-ACCESS  read-write
   STATUS      current
   DESCRIPTION
       "Specify the PTP clock instance for the following item used [0..3]."
   ::= {lcsPTP 6 }
   
   
lcsPTPClockConfAndStatus    OBJECT IDENTIFIER ::= { lcsPTP 7 }

lcsPTPClockConfEntryClockInstance OBJECT-TYPE
   SYNTAX      Integer32
   MAX-ACCESS  read-only
   STATUS      current
   DESCRIPTION
       ""
   ::= {lcsPTPClockConfAndStatus 2 }

lcsPTPClockConfEntryDeviceType OBJECT-TYPE
   SYNTAX      DisplayString
   MAX-ACCESS  read-only
   STATUS      current
   DESCRIPTION
       ""
   ::= {lcsPTPClockConfAndStatus 3 }   
   
lcsPTPClockConfEntryProfile OBJECT-TYPE
   SYNTAX      DisplayString
   MAX-ACCESS  read-only
   STATUS      current
   DESCRIPTION
       ""
   ::= {lcsPTPClockConfAndStatus 4 }    

lcsPTPClockConfEntryApplyProfileDefaults OBJECT-TYPE
   SYNTAX      Integer32
   MAX-ACCESS  read-write
   STATUS      current
   DESCRIPTION
       "-1:n/a
       0:normal state
       1:apply profile default"
   ::= {lcsPTPClockConfAndStatus 5 }   
   
lcsPTPClockConfEntryPTPTime OBJECT-TYPE
   SYNTAX      DisplayString
   MAX-ACCESS  read-only
   STATUS      current
   DESCRIPTION
       "Shows the actual PTP time with nanosecond resolution."
   ::= {lcsPTPClockConfAndStatus 6 }    
   
lcsPTPClockConfEntryClockAdjustmentMethod OBJECT-TYPE
   SYNTAX      DisplayString
   MAX-ACCESS  read-only
   STATUS      current
   DESCRIPTION
       "Shows the actual clock adjustment method. The method depends on the available hardware."
   ::= {lcsPTPClockConfAndStatus 7 }     
   
lcsPTPClockConfEntrySynchronizeToSystemClock OBJECT-TYPE
   SYNTAX      Integer32
   MAX-ACCESS  read-write
   STATUS      current
   DESCRIPTION
       "Activate this button to synchronize the System Clock to PTP Time.
       1:Synchronize to system clock."
   ::= {lcsPTPClockConfAndStatus 8 }    

lcsPTPClockConfEntryClockCurrentDataSetstpRm OBJECT-TYPE
   SYNTAX      Integer32
   MAX-ACCESS  read-only
   STATUS      current
   DESCRIPTION
       "Steps Removed : It is the number of PTP clocks traversed from the grandmaster to the local slave clock."
   ::= {lcsPTPClockConfAndStatus 9 }   
   
lcsPTPClockConfEntryClockCurrentDataSetOffsetFromMaster OBJECT-TYPE
   SYNTAX      DisplayString
   MAX-ACCESS  read-only
   STATUS      current
   DESCRIPTION
       "Time difference between the master clock and the local slave clock, measured in ns."
   ::= {lcsPTPClockConfAndStatus 10 }      
  
lcsPTPClockConfEntryClockCurrentDataSetMeanPathDelay OBJECT-TYPE
   SYNTAX      DisplayString
   MAX-ACCESS  read-only
   STATUS      current
   DESCRIPTION
       "The mean propagation time for the link between the master and the local slave."
   ::= {lcsPTPClockConfAndStatus 11 }   
   
lcsPTPClockConfEntryClockCurrentDataSetSlavePort OBJECT-TYPE
   SYNTAX      Integer32
   MAX-ACCESS  read-only
   STATUS      current
   DESCRIPTION
       "Shows which port is in slave mode. The value is 0 if no ports are in slave mode."
   ::= {lcsPTPClockConfAndStatus 12 }  
   
lcsPTPClockConfEntryClockCurrentDataSetSlaveState OBJECT-TYPE
   SYNTAX      DisplayString
   MAX-ACCESS  read-only
   STATUS      current
   DESCRIPTION
       "Shows synchronization state of the slave."
   ::= {lcsPTPClockConfAndStatus 13 }  
   
lcsPTPClockConfEntryClockCurrentDataSetHoldover OBJECT-TYPE
   SYNTAX      DisplayString
   MAX-ACCESS  read-only
   STATUS      current
   DESCRIPTION
       "After the slave has been in Locked mode during the stabilization period, 
       this value shows the actual clock offset between the freerun and the actual holdover frequency, 
       the value is shown in parts pr billion (ppb). 
       During the stabilization period, the value is shown as N.A. 
       The stabilization period is 60 sec as default, it can be changed from the CLI interface."
   ::= {lcsPTPClockConfAndStatus 14 } 

lcsPTPClockConfEntryClockParentDataSetParentPortID OBJECT-TYPE
   SYNTAX      DisplayString
   MAX-ACCESS  read-only
   STATUS      current
   DESCRIPTION
       "Clock identity for the parent clock, if the local clock is not a slave, the value is the clocks own id."
   ::= {lcsPTPClockConfAndStatus 15 }     
  
lcsPTPClockConfEntryClockParentDataSetPort OBJECT-TYPE
   SYNTAX      Integer32
   MAX-ACCESS  read-only
   STATUS      current
   DESCRIPTION
       "Port Id for the parent master port"
   ::= {lcsPTPClockConfAndStatus 16 }

lcsPTPClockConfEntryClockParentDataSetPStat OBJECT-TYPE
   SYNTAX      DisplayString
   MAX-ACCESS  read-only
   STATUS      current
   DESCRIPTION
       "Parents Stats (always false)."
   ::= {lcsPTPClockConfAndStatus 17 }     
   
lcsPTPClockConfEntryClockParentDataSetVar OBJECT-TYPE
   SYNTAX      Integer32
   MAX-ACCESS  read-only
   STATUS      current
   DESCRIPTION
       "It is observed parent offset scaled log variance"
   ::= {lcsPTPClockConfAndStatus 18 }    
   
lcsPTPClockConfEntryClockParentDataSetRate OBJECT-TYPE
   SYNTAX      Integer32
   MAX-ACCESS  read-only
   STATUS      current
   DESCRIPTION
       "Observed Parent Clock Phase Change Rate. i.e. the slave clocks rate offset compared to the master. 
       (unit = ns per s)."
   ::= {lcsPTPClockConfAndStatus 19 }  

lcsPTPClockConfEntryClockParentDataSetGrandMasterID OBJECT-TYPE
   SYNTAX      DisplayString
   MAX-ACCESS  read-only
   STATUS      current
   DESCRIPTION
       "Clock identity for the grand master clock, if the local clock is not a slave, the value is the clocks own id."
   ::= {lcsPTPClockConfAndStatus 20 }   

lcsPTPClockConfEntryClockParentDataSetGrandMasterClockQuality OBJECT-TYPE
   SYNTAX      DisplayString
   MAX-ACCESS  read-only
   STATUS      current
   DESCRIPTION
       "The clock quality announced by the grand master (See description of Clock Default DataSet:Clock Quality)"
   ::= {lcsPTPClockConfAndStatus 21 }     
   
lcsPTPClockConfEntryClockParentDataSetPri1 OBJECT-TYPE
   SYNTAX      Integer32
   MAX-ACCESS  read-only
   STATUS      current
   DESCRIPTION
       "Clock priority 1 announced by the grand master"
   ::= {lcsPTPClockConfAndStatus 22 }   

lcsPTPClockConfEntryClockParentDataSetPri2 OBJECT-TYPE
   SYNTAX      Integer32
   MAX-ACCESS  read-only
   STATUS      current
   DESCRIPTION
       "Clock priority 2 announced by the grand master."
   ::= {lcsPTPClockConfAndStatus 23 }      
   
lcsPTPClockConfEntryClockDefaultDataSetClockID OBJECT-TYPE
   SYNTAX      Integer32
   MAX-ACCESS  read-only
   STATUS      current
   DESCRIPTION
       "An internal instance id (0..3)"
   ::= {lcsPTPClockConfAndStatus 24 }     
   
lcsPTPClockConfEntryClockDefaultDataSetDeviceType OBJECT-TYPE
   SYNTAX      DisplayString
   MAX-ACCESS  read-only
   STATUS      current
   DESCRIPTION
       "Indicates the Type of the Clock Instance. There are five Device Types.
        1. Ord-Bound - Clock's Device Type is Ordinary-Boundary Clock.
        2. P2p Transp - Clock's Device Type is Peer to Peer Transparent Clock.
        3. E2e Transp - Clock's Device Type is End to End Transparent Clock.
        4. Master Only - Clock's Device Type is Master Only.
        5. Slave Only - Clock's Device Type is Slave Only."
   ::= {lcsPTPClockConfAndStatus 25 }    

lcsPTPClockConfEntryClockDefaultDataSet2StepFlag OBJECT-TYPE
   SYNTAX      Integer32
   MAX-ACCESS  read-write
   STATUS      current
   DESCRIPTION
       "True if two-step Sync events and Pdelay_Resp events are used
       0:false
       1:true"
   ::= {lcsPTPClockConfAndStatus 26 }   
   
lcsPTPClockConfEntryClockDefaultDataSetPorts OBJECT-TYPE
   SYNTAX      Integer32
   MAX-ACCESS  read-only
   STATUS      current
   DESCRIPTION
       "The total number of physical ports in the node"
   ::= {lcsPTPClockConfAndStatus 27 }     
   
lcsPTPClockConfEntryClockDefaultDataSetClockIdentity OBJECT-TYPE
   SYNTAX      DisplayString
   MAX-ACCESS  read-only
   STATUS      current
   DESCRIPTION
       "It shows unique clock identifier"
   ::= {lcsPTPClockConfAndStatus 28 }    

lcsPTPClockConfEntryClockDefaultDataSetDom OBJECT-TYPE
   SYNTAX      Integer32
   MAX-ACCESS  read-write
   STATUS      current
   DESCRIPTION
       "Clock domain [0..127]."
   ::= {lcsPTPClockConfAndStatus 29 }     
   
lcsPTPClockConfEntryClockDefaultDataSetClockQuality OBJECT-TYPE
   SYNTAX      DisplayString
   MAX-ACCESS  read-only
   STATUS      current
   DESCRIPTION
       "The clock quality is determined by the system, and holds 3 parts: Clock Class, Clock Accuracy and OffsetScaledLog Variance as defined in IEEE1588.
The Clock Accuracy values are defined in IEEE1588 table 6 (Currently the clock Accuracy is set to 'Unknown' as default)."
   ::= {lcsPTPClockConfAndStatus 30 }  
   
lcsPTPClockConfEntryClockDefaultDataSetPri1 OBJECT-TYPE
   SYNTAX      Integer32
   MAX-ACCESS  read-write
   STATUS      current
   DESCRIPTION
       "Clock priority 1 [0..255] used by the BMC master select algorithm."
   ::= {lcsPTPClockConfAndStatus 31 }
   
lcsPTPClockConfEntryClockDefaultDataSetPri2 OBJECT-TYPE
   SYNTAX      Integer32
   MAX-ACCESS  read-write
   STATUS      current
   DESCRIPTION
       "Clock priority 2 [0..255] used by the BMC master select algorithm."
   ::= {lcsPTPClockConfAndStatus 32 }   
   
lcsPTPClockConfEntryClockDefaultDataSetProtocol OBJECT-TYPE
   SYNTAX      Integer32
   MAX-ACCESS  read-write
   STATUS      current
   DESCRIPTION
       "0:Ethernet
       1:Ethernet Mixed
       2:IP4Multi
       3:IP4Mixed
       4:IP4Uni
	   5:OAM"
   ::= {lcsPTPClockConfAndStatus 33 }     
   
lcsPTPClockConfEntryClockDefaultDataSetOneWay OBJECT-TYPE
   SYNTAX      Integer32
   MAX-ACCESS  read-write
   STATUS      current
   DESCRIPTION
       "If true, one way measurements are used. 
       This parameter applies only to a slave. 
       In one-way mode no delay measurements are performed, i.e. this is applicable only if frequency synchronization is needed. 
       The master always responds to delay requests.
       0:false
       1:true"
   ::= {lcsPTPClockConfAndStatus 34 }     
   
lcsPTPClockConfEntryClockDefaultDataSetVLANTagEnable OBJECT-TYPE
   SYNTAX      Integer32
   MAX-ACCESS  read-write
   STATUS      current
   DESCRIPTION
       "The VLAN Tag Enable parameter is ignored, because the tagging is controlled by the VLAN configuration.
       0:false
       1:true"
   ::= {lcsPTPClockConfAndStatus 35 }   

lcsPTPClockConfEntryClockDefaultDataSetVID OBJECT-TYPE
   SYNTAX      Integer32
   MAX-ACCESS  read-write
   STATUS      current
   DESCRIPTION
       "TVLAN Identifier used for tagging the VLAN packets.
       range:1-4094"
   ::= {lcsPTPClockConfAndStatus 36 }    

lcsPTPClockConfEntryClockDefaultDataSetPCP OBJECT-TYPE
   SYNTAX      Integer32
   MAX-ACCESS  read-write
   STATUS      current
   DESCRIPTION
       "Priority Code Point value used for PTP frames. range:0-7"
   ::= {lcsPTPClockConfAndStatus 37 }     
   
lcsPTPClockConfEntryClockDefaultDataSetDSCP OBJECT-TYPE
   SYNTAX      Integer32
   MAX-ACCESS  read-write
   STATUS      current
   DESCRIPTION
       ""
   ::= {lcsPTPClockConfAndStatus 38 }  
   
lcsPTPClockConfEntryClockTimePropertiesDataSetUtcOffset OBJECT-TYPE
   SYNTAX      Integer32
   MAX-ACCESS  read-write
   STATUS      current
   DESCRIPTION
       "range: 0-10000"
   ::= {lcsPTPClockConfAndStatus 39 }     
 
lcsPTPClockConfEntryClockTimePropertiesDataSetValid OBJECT-TYPE
   SYNTAX      Integer32
   MAX-ACCESS  read-write
   STATUS      current
   DESCRIPTION
       "0:false
       1:true"
   ::= {lcsPTPClockConfAndStatus 40 }     
   
lcsPTPClockConfEntryClockTimePropertiesDataSetLeap59 OBJECT-TYPE
   SYNTAX      Integer32
   MAX-ACCESS  read-write
   STATUS      current
   DESCRIPTION
       "0:false
       1:true"
   ::= {lcsPTPClockConfAndStatus 41 }   
   
lcsPTPClockConfEntryClockTimePropertiesDataSetLeap61 OBJECT-TYPE
   SYNTAX      Integer32
   MAX-ACCESS  read-write
   STATUS      current
   DESCRIPTION
       "0:false
       1:true"
   ::= {lcsPTPClockConfAndStatus 42 }    
   
lcsPTPClockConfEntryClockTimePropertiesDataSetTimeTrac OBJECT-TYPE
   SYNTAX      Integer32
   MAX-ACCESS  read-write
   STATUS      current
   DESCRIPTION
       "0:false
       1:true"
   ::= {lcsPTPClockConfAndStatus 43 }           
   
lcsPTPClockConfEntryClockTimePropertiesDataSetFreqTrac OBJECT-TYPE
   SYNTAX      Integer32
   MAX-ACCESS  read-write
   STATUS      current
   DESCRIPTION
       "0:false
       1:true"
   ::= {lcsPTPClockConfAndStatus 44 }    
   
lcsPTPClockConfEntryClockTimePropertiesDataSetPTPTimeScale OBJECT-TYPE
   SYNTAX      Integer32
   MAX-ACCESS  read-write
   STATUS      current
   DESCRIPTION
       "0:false
       1:true"
   ::= {lcsPTPClockConfAndStatus 45 }    
   
lcsPTPClockConfEntryClockTimePropertiesDataSetTimeSource OBJECT-TYPE
   SYNTAX      Integer32
   MAX-ACCESS  read-write
   STATUS      current
   DESCRIPTION
       "range: 0-255"
   ::= {lcsPTPClockConfAndStatus 46 }      
   
lcsPTPClockConfEntryFilterParametersFilterType OBJECT-TYPE
   SYNTAX      Integer32
   MAX-ACCESS  read-write
   STATUS      current
   DESCRIPTION
       "Shows the filter type used which can be either the basic filter or an advanced filter that can be configured to use only a fraction of the packets received 
       (i.e. the packets that have experienced the least latency).
       0:BASIC"
   ::= {lcsPTPClockConfAndStatus 47 }  
   
lcsPTPClockConfEntryFilterParametersDelayFilter OBJECT-TYPE
   SYNTAX      Integer32
   MAX-ACCESS  read-write
   STATUS      current
   DESCRIPTION
       "range:0-6"
   ::= {lcsPTPClockConfAndStatus 48 }   
   
lcsPTPClockConfEntryFilterParametersPeriod OBJECT-TYPE
   SYNTAX      Integer32
   MAX-ACCESS  read-write
   STATUS      current
   DESCRIPTION
       "range:1-10000"
   ::= {lcsPTPClockConfAndStatus 49 }    

lcsPTPClockConfEntryFilterParametersDist OBJECT-TYPE
   SYNTAX      Integer32
   MAX-ACCESS  read-write
   STATUS      current
   DESCRIPTION
       "range:1-10"
   ::= {lcsPTPClockConfAndStatus 50 }     

lcsPTPClockConfEntryServoParametersDisplay OBJECT-TYPE
   SYNTAX      Integer32
   MAX-ACCESS  read-write
   STATUS      current
   DESCRIPTION
       "If true then Offset From Master, MeanPathDelay and clockAdjustment are logged on the debug terminal
       0:false
       1:true"
   ::= {lcsPTPClockConfAndStatus 51 }    

lcsPTPClockConfEntryServoParametersPEnable OBJECT-TYPE
   SYNTAX      Integer32
   MAX-ACCESS  read-write
   STATUS      current
   DESCRIPTION
       "If true the P part of the algorithm is included
       0:false
       1:true"
   ::= {lcsPTPClockConfAndStatus 52 }    
   
lcsPTPClockConfEntryServoParametersIEnable OBJECT-TYPE
   SYNTAX      Integer32
   MAX-ACCESS  read-write
   STATUS      current
   DESCRIPTION
       "If true the I part of the algorithm is included
       0:false
       1:true"
   ::= {lcsPTPClockConfAndStatus 53 }       
   
lcsPTPClockConfEntryServoParametersDEnable OBJECT-TYPE
   SYNTAX      Integer32
   MAX-ACCESS  read-write
   STATUS      current
   DESCRIPTION
       "If true the D part of the algorithm is included
       0:false
       1:true"
   ::= {lcsPTPClockConfAndStatus 54 }          
   
lcsPTPClockConfEntryServoParametersPConstant OBJECT-TYPE
   SYNTAX      Integer32
   MAX-ACCESS  read-write
   STATUS      current
   DESCRIPTION
       "range:0-1000"
   ::= {lcsPTPClockConfAndStatus 55 }      
   
lcsPTPClockConfEntryServoParametersIConstant OBJECT-TYPE
   SYNTAX      Integer32
   MAX-ACCESS  read-write
   STATUS      current
   DESCRIPTION
       "range:0-10000"
   ::= {lcsPTPClockConfAndStatus 56 }     

lcsPTPClockConfEntryServoParametersDConstant OBJECT-TYPE
   SYNTAX      Integer32
   MAX-ACCESS  read-write
   STATUS      current
   DESCRIPTION
       "range:0-1000"
   ::= {lcsPTPClockConfAndStatus 57 }     

   
lcsPTPClockPortDataSetConfTable OBJECT-TYPE
   SYNTAX      SEQUENCE OF LCSPTPClockPortDataSetConfEntry
   MAX-ACCESS  not-accessible
   STATUS      current
   DESCRIPTION
       " "
   ::= { lcsPTP 8 }

lcsPTPClockPortDataSetConfEntry OBJECT-TYPE
   SYNTAX      LCSPTPClockPortDataSetConfEntry
   MAX-ACCESS  not-accessible
   STATUS      current
   DESCRIPTION
       " "
   INDEX    { lcsPTPClockPortDataSetConfPort  }
   ::= { lcsPTPClockPortDataSetConfTable 1 }

LCSPTPClockPortDataSetConfEntry ::= SEQUENCE {
   lcsPTPClockPortDataSetConfPort               Integer32,
   lcsPTPClockConfEntryPortConfEnable           Integer32,
   lcsPTPClockConfEntryPortConfStat             DisplayString,
   lcsPTPClockConfEntryPortConfMDR              Integer32,
   lcsPTPClockConfEntryPortConfPeerMeanPathDel  DisplayString,
   lcsPTPClockConfEntryPortConfAnv              Integer32,
   lcsPTPClockConfEntryPortConfATo              Integer32,
   lcsPTPClockConfEntryPortConfSyv              Integer32,
   lcsPTPClockConfEntryPortConfDlm              Integer32,
   lcsPTPClockConfEntryPortConfMPR              Integer32,
   lcsPTPClockConfEntryPortConfDelayAsymmetry   Integer32,
   lcsPTPClockConfEntryPortConfIngressLatency   Integer32,
   lcsPTPClockConfEntryPortConfEgressLatency    Integer32,
   lcsPTPClockConfEntryPortConfVersion          Integer32
}

lcsPTPClockPortDataSetConfPort OBJECT-TYPE
   SYNTAX      Integer32 (1..65535)
   MAX-ACCESS  not-accessible
   STATUS      current
   DESCRIPTION
       "Index"
   ::= { lcsPTPClockPortDataSetConfEntry 1 }

lcsPTPClockConfEntryPortConfEnable OBJECT-TYPE
   SYNTAX      Integer32
   MAX-ACCESS  read-write
   STATUS      current
   DESCRIPTION
       "0:false
       1:true"
   ::= { lcsPTPClockPortDataSetConfEntry 2 }
   
lcsPTPClockConfEntryPortConfStat OBJECT-TYPE
   SYNTAX      DisplayString
   MAX-ACCESS  read-only
   STATUS      current
   DESCRIPTION
       "Dynamic member portState: Current state of the port."
   ::= { lcsPTPClockPortDataSetConfEntry 3 }   
   
lcsPTPClockConfEntryPortConfMDR OBJECT-TYPE
   SYNTAX      Integer32
   MAX-ACCESS  read-only
   STATUS      current
   DESCRIPTION
       "Dynamic member log Min Delay Req Interval: The delay request interval announced by the master."
   ::= { lcsPTPClockPortDataSetConfEntry 4 }      

lcsPTPClockConfEntryPortConfPeerMeanPathDel OBJECT-TYPE
   SYNTAX      DisplayString
   MAX-ACCESS  read-only
   STATUS      current
   DESCRIPTION
       "The path delay measured by the port in P2P mode. In E2E mode this value is 0"
   ::= { lcsPTPClockPortDataSetConfEntry 5 }  
   

   
lcsPTPClockConfEntryPortConfAnv OBJECT-TYPE
   SYNTAX      Integer32
   MAX-ACCESS  read-write
   STATUS      current
   DESCRIPTION
       "The interval for issuing announce messages in master state. Range is -3 to 4."
   ::= { lcsPTPClockPortDataSetConfEntry 6 }     
   
lcsPTPClockConfEntryPortConfATo OBJECT-TYPE
   SYNTAX      Integer32
   MAX-ACCESS  read-write
   STATUS      current
   DESCRIPTION
       "The timeout for receiving announce messages on the port. Range is 1 to 10."
   ::= { lcsPTPClockPortDataSetConfEntry 7 }    
   
lcsPTPClockConfEntryPortConfSyv OBJECT-TYPE
   SYNTAX      Integer32
   MAX-ACCESS  read-write
   STATUS      current
   DESCRIPTION
       "The interval for issuing sync messages in master. Range is -7 to 4."
   ::= { lcsPTPClockPortDataSetConfEntry 8 }     

lcsPTPClockConfEntryPortConfDlm OBJECT-TYPE
   SYNTAX      Integer32
   MAX-ACCESS  read-write
   STATUS      current
   DESCRIPTION
       "Configurable member delayMechanism: The delay mechanism used for the port:
        e2e End to end delay measurement
        p2p Peer to peer delay measurement.
        Can be defined per port in an Ordinary/Boundary clock.
        In a transparent clock all ports use the same delay mechanism, determined by the clock type.
        1:e2e
        2:p2p"
   ::= { lcsPTPClockPortDataSetConfEntry 9 }    

lcsPTPClockConfEntryPortConfMPR OBJECT-TYPE
   SYNTAX      Integer32
   MAX-ACCESS  read-write
   STATUS      current
   DESCRIPTION
       "The interval for issuing Delay_Req messages for the port in E2e mode. This value is announced from the master to the slave in an announce message. The value is reflected in the MDR field in the Slave
The interval for issuing Pdelay_Req messages for the port in P2P mode
Note: The interpretation of this parameter has changed from release 2.40. In earlier versions the value was interpreted relative to the Sync interval, this was a violation of the standard, so now the value is interpreted as an interval. I.e. MPR = 0 => 1 Delay_Req pr sec, independent of the Sync rate.
Range is -7 to 5."
   ::= { lcsPTPClockPortDataSetConfEntry 10 }    

lcsPTPClockConfEntryPortConfDelayAsymmetry OBJECT-TYPE
   SYNTAX      Integer32
   MAX-ACCESS  read-write
   STATUS      current
   DESCRIPTION
       "If the transmission delay for a link in not symmetric, the asymmetry can be configured here, see IEEE 1588 Section 7.4.2 Communication path asymmetry
Range is -100000 to 100000."
   ::= { lcsPTPClockPortDataSetConfEntry 11 }    
   
lcsPTPClockConfEntryPortConfIngressLatency OBJECT-TYPE
   SYNTAX      Integer32
   MAX-ACCESS  read-write
   STATUS      current
   DESCRIPTION
       "Ingress latency measured in ns, as defined in IEEE 1588 Section 7.3.4.2.
Range is -100000 to 100000."
   ::= { lcsPTPClockPortDataSetConfEntry 12 }     
   
lcsPTPClockConfEntryPortConfEgressLatency OBJECT-TYPE
   SYNTAX      Integer32
   MAX-ACCESS  read-write
   STATUS      current
   DESCRIPTION
       "Egress latency measured in ns, as defined in IEEE 1588 Section 7.3.4.2.
Range is -100000 to 100000."
   ::= { lcsPTPClockPortDataSetConfEntry 13 }     
   
lcsPTPClockConfEntryPortConfVersion OBJECT-TYPE
   SYNTAX      Integer32
   MAX-ACCESS  read-only
   STATUS      current
   DESCRIPTION
       "The current implementation only supports PTP version 2"
   ::= { lcsPTPClockPortDataSetConfEntry 14 }    
   
  
lcsPTPClockUnicastSlaveConfTable OBJECT-TYPE
   SYNTAX      SEQUENCE OF LCSPTPClockUnicastSlaveConfEntry
   MAX-ACCESS  not-accessible
   STATUS      current
   DESCRIPTION
       " "
   ::= { lcsPTP 9 }

lcsPTPClockUnicastSlaveConfEntry OBJECT-TYPE
   SYNTAX      LCSPTPClockUnicastSlaveConfEntry
   MAX-ACCESS  not-accessible
   STATUS      current
   DESCRIPTION
       " "
   INDEX    { lcsPTPClockConfEntryUnicastSlaveConfIndex  }
   ::= { lcsPTPClockUnicastSlaveConfTable 1 }

LCSPTPClockUnicastSlaveConfEntry ::= SEQUENCE {
   lcsPTPClockConfEntryUnicastSlaveConfIndex              Integer32,
   lcsPTPClockConfEntryUnicastSlaveConfDuration           Integer32,
   lcsPTPClockConfEntryUnicastSlaveConfIPAddress          IpAddress,
   lcsPTPClockConfEntryUnicastSlaveConfGrant              Integer32,
   lcsPTPClockConfEntryUnicastSlaveConfCommState          DisplayString
}

lcsPTPClockConfEntryUnicastSlaveConfIndex OBJECT-TYPE
   SYNTAX      Integer32 (1..65535)
   MAX-ACCESS  not-accessible
   STATUS      current
   DESCRIPTION
       "Index"
   ::= { lcsPTPClockUnicastSlaveConfEntry 1 }

lcsPTPClockConfEntryUnicastSlaveConfDuration OBJECT-TYPE
   SYNTAX      Integer32
   MAX-ACCESS  read-write
   STATUS      current
   DESCRIPTION
       "The number of seconds a master is requested to send Announce/Sync messages. 
       The request is repeated from the slave each Duration/4 seconds.
       range:10-1000"
   ::= { lcsPTPClockUnicastSlaveConfEntry 2 }
      
lcsPTPClockConfEntryUnicastSlaveConfIPAddress OBJECT-TYPE
   SYNTAX      IpAddress
   MAX-ACCESS  read-write
   STATUS      current
   DESCRIPTION
       "IPv4 Address of the Master clock"
   ::= { lcsPTPClockUnicastSlaveConfEntry 3 }
   
lcsPTPClockConfEntryUnicastSlaveConfGrant OBJECT-TYPE
   SYNTAX      Integer32
   MAX-ACCESS  read-only
   STATUS      current
   DESCRIPTION
       "The granted repetition period for the sync message"
   ::= { lcsPTPClockUnicastSlaveConfEntry 4 }   
   
lcsPTPClockConfEntryUnicastSlaveConfCommState OBJECT-TYPE
   SYNTAX      DisplayString
   MAX-ACCESS  read-only
   STATUS      current
   DESCRIPTION
       "The state of the communication with the master, possible values are:
        IDLE : The entry is not in use.
        INIT : Announce is sent to the master (Waiting for a response).
        CONN : The master has responded.
        SELL : The assigned master is selected as current master.
        SYNC : The master is sending Sync messages."
   ::= { lcsPTPClockUnicastSlaveConfEntry 5 }   
-- =======================================================================================================================
lcsETHLINKOAM    OBJECT IDENTIFIER ::= { lcsConfiguration 29 } 

lcsEthLinkOAMPortConfTable OBJECT-TYPE
   SYNTAX      SEQUENCE OF LCSEthLinkOAMPortConfEntry
   MAX-ACCESS  not-accessible
   STATUS      current
   DESCRIPTION
       " "
   ::= { lcsETHLINKOAM 1 }

lcsEthLinkOAMPortConfEntry OBJECT-TYPE
   SYNTAX      LCSEthLinkOAMPortConfEntry
   MAX-ACCESS  not-accessible
   STATUS      current
   DESCRIPTION
       " "
   INDEX    { lcsEthLinkOAMPortConfIndex  }
   ::= { lcsEthLinkOAMPortConfTable 1 }

LCSEthLinkOAMPortConfEntry ::= SEQUENCE {
   lcsEthLinkOAMPortConfIndex               Integer32,
   lcsEthLinkOAMPortConfOAMEnable           Integer32,
   lcsEthLinkOAMPortConfOAMMode             Integer32,
   lcsEthLinkOAMPortConfLoopbackSupport     Integer32,
   lcsEthLinkOAMPortConfLinkMonitorSupport  Integer32,
   lcsEthLinkOAMPortConfMIBRetrievalSupport Integer32,
   lcsEthLinkOAMPortConfLoopbackOperation   Integer32
}

lcsEthLinkOAMPortConfIndex OBJECT-TYPE
   SYNTAX      Integer32 (1..65535)
   MAX-ACCESS  not-accessible
   STATUS      current
   DESCRIPTION
       "Index"
   ::= { lcsEthLinkOAMPortConfEntry 1 }

lcsEthLinkOAMPortConfOAMEnable OBJECT-TYPE
   SYNTAX      Integer32
   MAX-ACCESS  read-write
   STATUS      current
   DESCRIPTION
       "Controls whether Link OAM is enabled on this switch port. 
       Enabling Link OAM provides the network operators the ability to monitor the health of the network and 
       quickly determine the location of failing links or fault conditions.
       0:disable
       1:enable"
   ::= { lcsEthLinkOAMPortConfEntry 2 }
   
lcsEthLinkOAMPortConfOAMMode OBJECT-TYPE
   SYNTAX      Integer32
   MAX-ACCESS  read-write
   STATUS      current
   DESCRIPTION
       "Configures the OAM Mode as Active or Passive. The default mode is Passive.
       0:Passive mode
       1:Active mode"
   ::= { lcsEthLinkOAMPortConfEntry 3 }   
   
lcsEthLinkOAMPortConfLoopbackSupport OBJECT-TYPE
   SYNTAX      Integer32
   MAX-ACCESS  read-write
   STATUS      current
   DESCRIPTION
       "Controls whether the loopback support is enabled for the switch port. 
       0:disable
       1:enable"
   ::= { lcsEthLinkOAMPortConfEntry 4 }     
   
lcsEthLinkOAMPortConfLinkMonitorSupport OBJECT-TYPE
   SYNTAX      Integer32
   MAX-ACCESS  read-write
   STATUS      current
   DESCRIPTION
       "Controls whether the Link Monitor support is enabled for the switch port.
       0:disable
       1:enable"
   ::= { lcsEthLinkOAMPortConfEntry 5 }

lcsEthLinkOAMPortConfMIBRetrievalSupport OBJECT-TYPE
   SYNTAX      Integer32
   MAX-ACCESS  read-write
   STATUS      current
   DESCRIPTION
       "Controls whether the MIB Retrieval Support is enabled for the switch port. 
       0:disable
       1:enable"
   ::= { lcsEthLinkOAMPortConfEntry 6 }    
   
lcsEthLinkOAMPortConfLoopbackOperation OBJECT-TYPE
   SYNTAX      Integer32
   MAX-ACCESS  read-write
   STATUS      current
   DESCRIPTION
       "If the Loopback support is enabled, enabling this field will start a loopback operation for the port.
       0:disable
       1:enable"
   ::= { lcsEthLinkOAMPortConfEntry 7 }       
   
   
   
lcsEthLinkOAMPortDetailStatusTable OBJECT-TYPE
   SYNTAX      SEQUENCE OF LCSEthLinkOAMPortDetailStatusEntry
   MAX-ACCESS  not-accessible
   STATUS      current
   DESCRIPTION
       "Eth Link OAM Port Detail Status table"
   ::= { lcsETHLINKOAM 2 }

lcsEthLinkOAMPortDetailStatusEntry OBJECT-TYPE
   SYNTAX      LCSEthLinkOAMPortDetailStatusEntry
   MAX-ACCESS  not-accessible
   STATUS      current
   DESCRIPTION
       "Eth Link OAM Port Detail Status entry"
   INDEX    { lcsEthLinkOAMPortDetailStatusIndex  }
   ::= { lcsEthLinkOAMPortDetailStatusTable 1 }

LCSEthLinkOAMPortDetailStatusEntry ::= SEQUENCE {
   lcsEthLinkOAMPortDetailStatusIndex                       Integer32,
   lcsEthLinkOAMPortPDUPermission                           DisplayString,
   lcsEthLinkOAMPortDiscoveryState                          DisplayString,
   lcsEthLinkOAMPortPeerMACAddress                          DisplayString,
   lcsEthLinkOAMPortLocalMode                               DisplayString,
   lcsEthLinkOAMPortLocalUnidirectionalOperationSupport     DisplayString,
   lcsEthLinkOAMPortLocalRemoteLoopbackSupport              DisplayString,
   lcsEthLinkOAMPortLocalLinkMonitoringSupport              DisplayString,
   lcsEthLinkOAMPortLocalMIBRetrievalSupport                DisplayString,
   lcsEthLinkOAMPortLocalMTUSize                            Integer32,  
   lcsEthLinkOAMPortLocalMultiplexerState                   DisplayString,  
   lcsEthLinkOAMPortLocalParserState                        DisplayString,  
   lcsEthLinkOAMPortLocalOrganizationalUniqueIdentification DisplayString,  
   lcsEthLinkOAMPortLocalPDURevision                        Integer32,  
   lcsEthLinkOAMPortPeerMode                                DisplayString,  
   lcsEthLinkOAMPortPeerUnidirectionalOperationSupport      DisplayString,  
   lcsEthLinkOAMPortPeerRemoteLoopbackSupport               DisplayString,  
   lcsEthLinkOAMPortPeerLinkMonitoringSupport               DisplayString,  
   lcsEthLinkOAMPortPeerMIBRetrievalSupport                 DisplayString,  
   lcsEthLinkOAMPortPeerMTUSize                             DisplayString,  
   lcsEthLinkOAMPortPeerMultiplexerState                    DisplayString,  
   lcsEthLinkOAMPortPeerParserState                         DisplayString,  
   lcsEthLinkOAMPortPeerOrganizationalUniqueIdentification  DisplayString,  
   lcsEthLinkOAMPortPDURevision                             DisplayString     
}

lcsEthLinkOAMPortDetailStatusIndex OBJECT-TYPE
   SYNTAX      Integer32 (1..65535)
   MAX-ACCESS  not-accessible
   STATUS      current
   DESCRIPTION
       "Index"
   ::= { lcsEthLinkOAMPortDetailStatusEntry 1 }

lcsEthLinkOAMPortPDUPermission OBJECT-TYPE
   SYNTAX      DisplayString
   MAX-ACCESS  read-only
   STATUS      current
   DESCRIPTION
       "This field is available only for the Local DTE. 
       It displays the current permission rules set for the local DTE. 
       Possible values are Link fault, Receive only, Information exchange only, ANY."
   ::= { lcsEthLinkOAMPortDetailStatusEntry 2 }
   
lcsEthLinkOAMPortDiscoveryState OBJECT-TYPE
   SYNTAX      DisplayString
   MAX-ACCESS  read-only
   STATUS      current
   DESCRIPTION
       "Displays the current state of the discovery process. 
       Possible states are Fault state, Active state, Passive state, 
       SEND_LOCAL_REMOTE_STATE, SEND_LOCAL_REMOTE_OK_STATE, SEND_ANY_STATE."
   ::= { lcsEthLinkOAMPortDetailStatusEntry 3 }   
   
lcsEthLinkOAMPortPeerMACAddress OBJECT-TYPE
   SYNTAX      DisplayString
   MAX-ACCESS  read-only
   STATUS      current
   DESCRIPTION
       " "
   ::= { lcsEthLinkOAMPortDetailStatusEntry 4 }     
   
lcsEthLinkOAMPortLocalMode OBJECT-TYPE
   SYNTAX      DisplayString
   MAX-ACCESS  read-only
   STATUS      current
   DESCRIPTION
       "The Mode in which the Link OAM is operating, Active or Passive."
   ::= { lcsEthLinkOAMPortDetailStatusEntry 5 }

lcsEthLinkOAMPortLocalUnidirectionalOperationSupport OBJECT-TYPE
   SYNTAX      DisplayString
   MAX-ACCESS  read-only
   STATUS      current
   DESCRIPTION
       "This feature is not available to be configured by the user. The status of this configuration is retrieved from the PHY."
   ::= { lcsEthLinkOAMPortDetailStatusEntry 6 }    
   
lcsEthLinkOAMPortLocalRemoteLoopbackSupport OBJECT-TYPE
   SYNTAX      DisplayString
   MAX-ACCESS  read-only
   STATUS      current
   DESCRIPTION
       "If status is enabled, DTE is capable of OAM remote loopback mode."
   ::= { lcsEthLinkOAMPortDetailStatusEntry 7 }       
   
lcsEthLinkOAMPortLocalLinkMonitoringSupport OBJECT-TYPE
   SYNTAX      DisplayString
   MAX-ACCESS  read-only
   STATUS      current
   DESCRIPTION
       "If status is enabled, DTE supports interpreting Link Events."
   ::= { lcsEthLinkOAMPortDetailStatusEntry 8 }   

lcsEthLinkOAMPortLocalMIBRetrievalSupport OBJECT-TYPE
   SYNTAX      DisplayString
   MAX-ACCESS  read-only
   STATUS      current
   DESCRIPTION
       "If status ie enabled DTE supports sending Variable Response OAMPDUs."
   ::= { lcsEthLinkOAMPortDetailStatusEntry 9 }   

lcsEthLinkOAMPortLocalMTUSize OBJECT-TYPE
   SYNTAX      Integer32
   MAX-ACCESS  read-only
   STATUS      current
   DESCRIPTION
       "It represents the largest OAMPDU, in octets, supported by the DTE. 
       This value is compared to the remotes Maximum PDU Size and the smaller of the two is used."
   ::= { lcsEthLinkOAMPortDetailStatusEntry 10 }   
   
lcsEthLinkOAMPortLocalMultiplexerState OBJECT-TYPE
   SYNTAX      DisplayString
   MAX-ACCESS  read-only
   STATUS      current
   DESCRIPTION
       "When in forwarding state, the Device is forwarding non-OAMPDUs to the lower sublayer. 
       Incase of discarding, the device discards all the non-OAMPDU's."
   ::= { lcsEthLinkOAMPortDetailStatusEntry 11 }  
   
lcsEthLinkOAMPortLocalParserState OBJECT-TYPE
   SYNTAX      DisplayString
   MAX-ACCESS  read-only
   STATUS      current
   DESCRIPTION
       "When in forwarding state, Device is forwarding non-OAMPDUs to higher sublayer. 
       When in loopback, Device is looping back non-OAMPDUs to the lower sublayer. 
       When in discarding state, Device is discarding non-OAMPDUs."
   ::= { lcsEthLinkOAMPortDetailStatusEntry 12 }  
   
lcsEthLinkOAMPortLocalOrganizationalUniqueIdentification OBJECT-TYPE
   SYNTAX      DisplayString
   MAX-ACCESS  read-only
   STATUS      current
   DESCRIPTION
       "24-bit Organizationally Unique Identifier of the vendor."
   ::= { lcsEthLinkOAMPortDetailStatusEntry 13 }   
   
lcsEthLinkOAMPortLocalPDURevision OBJECT-TYPE
   SYNTAX      Integer32
   MAX-ACCESS  read-only
   STATUS      current
   DESCRIPTION
       "It indicates the current revision of the Information TLV. 
       The value of this field shall start at zero and be incremented each time something in the Information TLV changes. 
       Upon reception of an Information TLV from a peer, an OAM client may use this field to decide if it needs to be processed 
       (an Information TLV that is identical to the previous Information TLV doesn't need to be parsed as nothing in it has changed)."
   ::= { lcsEthLinkOAMPortDetailStatusEntry 14 } 
   
lcsEthLinkOAMPortPeerMode OBJECT-TYPE
   SYNTAX      DisplayString
   MAX-ACCESS  read-only
   STATUS      current
   DESCRIPTION
       "The Mode in which the Link OAM is operating, Active or Passive."
   ::= { lcsEthLinkOAMPortDetailStatusEntry 15 }  
   
lcsEthLinkOAMPortPeerUnidirectionalOperationSupport OBJECT-TYPE
   SYNTAX      DisplayString
   MAX-ACCESS  read-only
   STATUS      current
   DESCRIPTION
       "This feature is not available to be configured by the user. 
       The status of this configuration is retrieved from the PHY."
   ::= { lcsEthLinkOAMPortDetailStatusEntry 16 } 
   
lcsEthLinkOAMPortPeerRemoteLoopbackSupport OBJECT-TYPE
   SYNTAX      DisplayString
   MAX-ACCESS  read-only
   STATUS      current
   DESCRIPTION
       "If status is enabled, DTE is capable of OAM remote loopback mode."
   ::= { lcsEthLinkOAMPortDetailStatusEntry 17 } 
   
lcsEthLinkOAMPortPeerLinkMonitoringSupport OBJECT-TYPE
   SYNTAX      DisplayString
   MAX-ACCESS  read-only
   STATUS      current
   DESCRIPTION
       "If status is enabled, DTE supports interpreting Link Events."
   ::= { lcsEthLinkOAMPortDetailStatusEntry 18 } 
   
lcsEthLinkOAMPortPeerMIBRetrievalSupport OBJECT-TYPE
   SYNTAX      DisplayString
   MAX-ACCESS  read-only
   STATUS      current
   DESCRIPTION
       "If status ie enabled DTE supports sending Variable Response OAMPDUs."
   ::= { lcsEthLinkOAMPortDetailStatusEntry 19 } 
   
lcsEthLinkOAMPortPeerMTUSize OBJECT-TYPE
   SYNTAX      DisplayString
   MAX-ACCESS  read-only
   STATUS      current
   DESCRIPTION
       "It represents the largest OAMPDU, in octets, supported by the DTE. 
       This value is compared to the remotes Maximum PDU Size and the smaller of the two is used."
   ::= { lcsEthLinkOAMPortDetailStatusEntry 20 } 
   
lcsEthLinkOAMPortPeerMultiplexerState OBJECT-TYPE
   SYNTAX      DisplayString
   MAX-ACCESS  read-only
   STATUS      current
   DESCRIPTION
       "When in forwarding state, the Device is forwarding non-OAMPDUs to the lower sublayer. 
       Incase of discarding, the device discards all the non-OAMPDU's."
   ::= { lcsEthLinkOAMPortDetailStatusEntry 21 } 
   
lcsEthLinkOAMPortPeerParserState OBJECT-TYPE
   SYNTAX      DisplayString
   MAX-ACCESS  read-only
   STATUS      current
   DESCRIPTION
       "When in forwarding state, Device is forwarding non-OAMPDUs to higher sublayer. 
       When in loopback, Device is looping back non-OAMPDUs to the lower sublayer. 
       When in discarding state, Device is discarding non-OAMPDUs."
   ::= { lcsEthLinkOAMPortDetailStatusEntry 22 } 
   
lcsEthLinkOAMPortPeerOrganizationalUniqueIdentification OBJECT-TYPE
   SYNTAX      DisplayString
   MAX-ACCESS  read-only
   STATUS      current
   DESCRIPTION
       "24-bit Organizationally Unique Identifier of the vendor."
   ::= { lcsEthLinkOAMPortDetailStatusEntry 23 }      
   
lcsEthLinkOAMPortPDURevision                              OBJECT-TYPE
   SYNTAX      DisplayString
   MAX-ACCESS  read-only
   STATUS      current
   DESCRIPTION
       "It indicates the current revision of the Information TLV. 
       The value of this field shall start at zero and be incremented each time something in the Information TLV changes. 
       Upon reception of an Information TLV from a peer, an OAM client may use this field to decide if it needs to be processed 
       (an Information TLV that is identical to the previous Information TLV doesn't need to be parsed as nothing in it has changed)."
   ::= { lcsEthLinkOAMPortDetailStatusEntry 24 }   


lcsEthLinkOAMPortLinkEventConfTable OBJECT-TYPE
   SYNTAX      SEQUENCE OF LCSEthLinkOAMPortLinkEventConfEntry
   MAX-ACCESS  not-accessible
   STATUS      current
   DESCRIPTION
       "Eth Link OAM Port Link Event Conf Table"
   ::= { lcsETHLINKOAM 3 }

lcsEthLinkOAMPortLinkEventConfEntry OBJECT-TYPE
   SYNTAX      LCSEthLinkOAMPortLinkEventConfEntry
   MAX-ACCESS  not-accessible
   STATUS      current
   DESCRIPTION
       "Eth Link OAM Port Link Event Conf Entry"
   INDEX    { lcsPortLinkEventConfIndex  }
   ::= { lcsEthLinkOAMPortLinkEventConfTable 1 }

LCSEthLinkOAMPortLinkEventConfEntry ::= SEQUENCE {
   lcsPortLinkEventConfIndex                                 Integer32,
   lcsPortLinkEventConfErrorFrameEventErrorWindow            Integer32,
   lcsPortLinkEventConfErrorFrameEventErrorThreshold         Integer32,
   lcsPortLinkEventConfSymbolPeriodErrorEventErrorWindow     Integer32,
   lcsPortLinkEventConfSymbolPeriodErrorEventErrorThreshold  Integer32,
   lcsPortLinkEventConfSecondsSummaryEventErrorWindow        Integer32,
   lcsPortLinkEventConfSecondsSummaryEventErrorThreshold     Integer32
}

lcsPortLinkEventConfIndex OBJECT-TYPE
   SYNTAX      Integer32 (1..65535)
   MAX-ACCESS  not-accessible
   STATUS      current
   DESCRIPTION
       "Index"
   ::= { lcsEthLinkOAMPortLinkEventConfEntry 1 }

lcsPortLinkEventConfErrorFrameEventErrorWindow OBJECT-TYPE
   SYNTAX      Integer32
   MAX-ACCESS  read-write
   STATUS      current
   DESCRIPTION
       "The Errored Frame Event counts the number of errored frames detected during the specified period. 
       Represents the window period in the order of 1 sec for the observation of various link events.
       range: 1-60"
   ::= { lcsEthLinkOAMPortLinkEventConfEntry 2 }
   
lcsPortLinkEventConfErrorFrameEventErrorThreshold OBJECT-TYPE
   SYNTAX      Integer32
   MAX-ACCESS  read-write
   STATUS      current
   DESCRIPTION
       "The Errored Frame Event counts the number of errored frames detected during the specified period. 
       Represents the threshold value for the window period for the appropriate Link event so as to notify the peer of this error.
       range:0-0xffffffff"
   ::= { lcsEthLinkOAMPortLinkEventConfEntry 3 }
   
lcsPortLinkEventConfSymbolPeriodErrorEventErrorWindow OBJECT-TYPE
   SYNTAX      Integer32
   MAX-ACCESS  read-write
   STATUS      current
   DESCRIPTION
       "The Errored Symbol Period Event counts the number of symbol errors that occurred during the specified period.
       Represents the window period in the order of 1 sec for the observation of various link events.
       range: 1-60"
   ::= { lcsEthLinkOAMPortLinkEventConfEntry 4 }

lcsPortLinkEventConfSymbolPeriodErrorEventErrorThreshold OBJECT-TYPE
   SYNTAX      Integer32
   MAX-ACCESS  read-write
   STATUS      current
   DESCRIPTION
       "The Errored Symbol Period Event counts the number of symbol errors that occurred during the specified period.
       Represents the threshold value for the window period for the appropriate Link event so as to notify the peer of this error.
       range:0-0xffffffff"
   ::= { lcsEthLinkOAMPortLinkEventConfEntry 5 }

lcsPortLinkEventConfSecondsSummaryEventErrorWindow OBJECT-TYPE
   SYNTAX      Integer32
   MAX-ACCESS  read-write
   STATUS      current
   DESCRIPTION
       "The Errored Frame Seconds Summary Event TLV counts the number of errored frame seconds that occurred during the specified period. 
       Represents the window period in the order of 1 sec for the observation of various link events.
       range: 10-900"
   ::= { lcsEthLinkOAMPortLinkEventConfEntry 6 }   
   
lcsPortLinkEventConfSecondsSummaryEventErrorThreshold OBJECT-TYPE
   SYNTAX      Integer32
   MAX-ACCESS  read-write
   STATUS      current
   DESCRIPTION
       "The Errored Frame Seconds Summary Event TLV counts the number of errored frame seconds that occurred during the specified period. 
       Represents the threshold value for the window period for the appropriate Link event so as to notify the peer of this error.
       range:0-0xffff"
   ::= { lcsEthLinkOAMPortLinkEventConfEntry 7 } 




lcsEthLinkOAMPortDetailedStatisticsTable OBJECT-TYPE
   SYNTAX      SEQUENCE OF LCSEthLinkOAMPortDetailedStatisticsEntry
   MAX-ACCESS  not-accessible
   STATUS      current
   DESCRIPTION
       "Eth Link OAM Port Detailed Statistics Table"
   ::= { lcsETHLINKOAM 4 }

lcsEthLinkOAMPortDetailedStatisticsEntry OBJECT-TYPE
   SYNTAX      LCSEthLinkOAMPortDetailedStatisticsEntry
   MAX-ACCESS  not-accessible
   STATUS      current
   DESCRIPTION
       "Eth Link OAM Port Detailed Statistics Entry"
   INDEX    { lcsPortDetailedStatisticsIndex  }
   ::= { lcsEthLinkOAMPortDetailedStatisticsTable 1 }

LCSEthLinkOAMPortDetailedStatisticsEntry ::= SEQUENCE {
   lcsPortDetailedStatisticsIndex                             Integer32,
   lcsPortDetailedStatisticsRxOAMInformationPDUs              Integer32,
   lcsPortDetailedStatisticsRxUniqueErrorEventNotification    Integer32,
   lcsPortDetailedStatisticsRxDuplicateErrorEventNotification Integer32,
   lcsPortDetailedStatisticsRxLoopbackControl                 Integer32,
   lcsPortDetailedStatisticsRxVariableRequest                 Integer32,
   lcsPortDetailedStatisticsRxVariableResponse                Integer32,
   lcsPortDetailedStatisticsRxOrgSpecificPDUs                 Integer32,
   lcsPortDetailedStatisticsRxUnsupportedCodes                Integer32,
   lcsPortDetailedStatisticsRxLinkFaultPDUs                   Integer32,
   lcsPortDetailedStatisticsRxDyingGasp                       Integer32,
   lcsPortDetailedStatisticsRxCriticalEventPDUs               Integer32,
   lcsPortDetailedStatisticsTxOAMInformationPDUs              Integer32,
   lcsPortDetailedStatisticsTxUniqueErrorEventNotification    Integer32,
   lcsPortDetailedStatisticsTxDuplicateErrorEventNotification Integer32,
   lcsPortDetailedStatisticsTxLoopbackControl                 Integer32,
   lcsPortDetailedStatisticsTxVariableRequest                 Integer32,
   lcsPortDetailedStatisticsTxVariableResponse                Integer32,
   lcsPortDetailedStatisticsTxOrgSpecificPDUs                 Integer32,
   lcsPortDetailedStatisticsTxUnsupportedCodes                Integer32,
   lcsPortDetailedStatisticsTxLinkFaultPDUs                   Integer32,
   lcsPortDetailedStatisticsTxDyingGasp                       Integer32,
   lcsPortDetailedStatisticsTxCriticalEventPDUs               Integer32,
   lcsPortDetailedStatisticsClear                             Integer32
}

lcsPortDetailedStatisticsIndex OBJECT-TYPE
   SYNTAX      Integer32 (1..65535)
   MAX-ACCESS  not-accessible
   STATUS      current
   DESCRIPTION
       "Index"
   ::= { lcsEthLinkOAMPortDetailedStatisticsEntry 1 }

lcsPortDetailedStatisticsRxOAMInformationPDUs OBJECT-TYPE
   SYNTAX      Integer32
   MAX-ACCESS  read-only
   STATUS      current
   DESCRIPTION
       "The number of received and transmitted OAM Information PDU's. 
       Discontinuities of this counter can occur at re-initialization of the management system."
   ::= { lcsEthLinkOAMPortDetailedStatisticsEntry 2 }
   
lcsPortDetailedStatisticsRxUniqueErrorEventNotification OBJECT-TYPE
   SYNTAX      Integer32
   MAX-ACCESS  read-only
   STATUS      current
   DESCRIPTION
       "A count of the number of unique Event OAMPDUs received and transmitted on this interface. 
       Event Notifications may be sent in duplicate to increase the probability of successfully being received, 
       given the possibility that a frame may be lost in transit. 
       Duplicate Event Notification transmissions are counted by 
       Duplicate Event Notification counters for Tx and Rx respectively. 
       A unique Event Notification OAMPDU is indicated as an Event Notification OAMPDU with
       a Sequence Number field that is distinct from the previously transmitted Event Notification OAMPDU Sequence Number."
   ::= { lcsEthLinkOAMPortDetailedStatisticsEntry 3 }
   
lcsPortDetailedStatisticsRxDuplicateErrorEventNotification OBJECT-TYPE
   SYNTAX      Integer32
   MAX-ACCESS  read-only
   STATUS      current
   DESCRIPTION
       "A count of the number of duplicate Event OAMPDUs received and transmitted on this interface. 
       Event Notification OAMPDUs may be sent in duplicate to increase the probability of successfully being received, 
       given the possibility that a frame may be lost in transit. 
       A duplicate Event Notification OAMPDU is indicated as an Event Notification OAMPDU with
       a Sequence Number field that is identical to the previously transmitted Event Notification OAMPDU Sequence Number."
   ::= { lcsEthLinkOAMPortDetailedStatisticsEntry 4 }
   
lcsPortDetailedStatisticsRxLoopbackControl OBJECT-TYPE
   SYNTAX      Integer32
   MAX-ACCESS  read-only
   STATUS      current
   DESCRIPTION
       "A count of the number of Loopback Control OAMPDUs received and transmitted on this interface."
   ::= { lcsEthLinkOAMPortDetailedStatisticsEntry 5 }
   
lcsPortDetailedStatisticsRxVariableRequest OBJECT-TYPE
   SYNTAX      Integer32
   MAX-ACCESS  read-only
   STATUS      current
   DESCRIPTION
       "A count of the number of Variable Request OAMPDUs received and transmitted on this interface."
   ::= { lcsEthLinkOAMPortDetailedStatisticsEntry 6 }
   
lcsPortDetailedStatisticsRxVariableResponse OBJECT-TYPE
   SYNTAX      Integer32
   MAX-ACCESS  read-only
   STATUS      current
   DESCRIPTION
       "A count of the number of Variable Response OAMPDUs received and transmitted on this interface."
   ::= { lcsEthLinkOAMPortDetailedStatisticsEntry 7 }
   
lcsPortDetailedStatisticsRxOrgSpecificPDUs OBJECT-TYPE
   SYNTAX      Integer32
   MAX-ACCESS  read-only
   STATUS      current
   DESCRIPTION
       "A count of the number of Organization Specific OAMPDUs transmitted on this interface."
   ::= { lcsEthLinkOAMPortDetailedStatisticsEntry 8 }
   
lcsPortDetailedStatisticsRxUnsupportedCodes OBJECT-TYPE
   SYNTAX      Integer32
   MAX-ACCESS  read-only
   STATUS      current
   DESCRIPTION
       "A count of the number of OAMPDUs transmitted on this interface with an unsupported op-code."
   ::= { lcsEthLinkOAMPortDetailedStatisticsEntry 9 }
   
lcsPortDetailedStatisticsRxLinkFaultPDUs OBJECT-TYPE
   SYNTAX      Integer32
   MAX-ACCESS  read-only
   STATUS      current
   DESCRIPTION
       "A count of the number of Link fault PDU's received and transmitted on this interface."
   ::= { lcsEthLinkOAMPortDetailedStatisticsEntry 10 }
   
lcsPortDetailedStatisticsRxDyingGasp OBJECT-TYPE
   SYNTAX      Integer32
   MAX-ACCESS  read-only
   STATUS      current
   DESCRIPTION
       "A count of the number of Dying Gasp events received and transmitted on this interface."
   ::= { lcsEthLinkOAMPortDetailedStatisticsEntry 11 }
   
lcsPortDetailedStatisticsRxCriticalEventPDUs OBJECT-TYPE
   SYNTAX      Integer32
   MAX-ACCESS  read-only
   STATUS      current
   DESCRIPTION
       "A count of the number of Critical event PDU's received and transmitted on this interface."
   ::= { lcsEthLinkOAMPortDetailedStatisticsEntry 12 }
   
lcsPortDetailedStatisticsTxOAMInformationPDUs OBJECT-TYPE
   SYNTAX      Integer32
   MAX-ACCESS  read-only
   STATUS      current
   DESCRIPTION
       "The number of received and transmitted OAM Information PDU's. 
       Discontinuities of this counter can occur at re-initialization of the management system."
   ::= { lcsEthLinkOAMPortDetailedStatisticsEntry 13 }
   
lcsPortDetailedStatisticsTxUniqueErrorEventNotification OBJECT-TYPE
   SYNTAX      Integer32
   MAX-ACCESS  read-only
   STATUS      current
   DESCRIPTION
       "A count of the number of unique Event OAMPDUs received and transmitted on this interface. 
       Event Notifications may be sent in duplicate to increase the probability of successfully being received, 
       given the possibility that a frame may be lost in transit. 
       Duplicate Event Notification transmissions are counted by 
       Duplicate Event Notification counters for Tx and Rx respectively. 
       A unique Event Notification OAMPDU is indicated as an Event Notification OAMPDU with
       a Sequence Number field that is distinct from the previously transmitted Event Notification OAMPDU Sequence Number."
   ::= { lcsEthLinkOAMPortDetailedStatisticsEntry 14 }
   
lcsPortDetailedStatisticsTxDuplicateErrorEventNotification OBJECT-TYPE
   SYNTAX      Integer32
   MAX-ACCESS  read-only
   STATUS      current
   DESCRIPTION
       "A count of the number of duplicate Event OAMPDUs received and transmitted on this interface. 
       Event Notification OAMPDUs may be sent in duplicate to increase the probability of successfully being received, 
       given the possibility that a frame may be lost in transit. 
       A duplicate Event Notification OAMPDU is indicated as an Event Notification OAMPDU with
       a Sequence Number field that is identical to the previously transmitted Event Notification OAMPDU Sequence Number."
   ::= { lcsEthLinkOAMPortDetailedStatisticsEntry 15 }
   
lcsPortDetailedStatisticsTxLoopbackControl OBJECT-TYPE
   SYNTAX      Integer32
   MAX-ACCESS  read-only
   STATUS      current
   DESCRIPTION
       "A count of the number of Loopback Control OAMPDUs received and transmitted on this interface."
   ::= { lcsEthLinkOAMPortDetailedStatisticsEntry 16 }
   
lcsPortDetailedStatisticsTxVariableRequest OBJECT-TYPE
   SYNTAX      Integer32
   MAX-ACCESS  read-only
   STATUS      current
   DESCRIPTION
       "A count of the number of Variable Request OAMPDUs received and transmitted on this interface."
   ::= { lcsEthLinkOAMPortDetailedStatisticsEntry 17 }
   
lcsPortDetailedStatisticsTxVariableResponse OBJECT-TYPE
   SYNTAX      Integer32
   MAX-ACCESS  read-only
   STATUS      current
   DESCRIPTION
       "A count of the number of Variable Response OAMPDUs received and transmitted on this interface."
   ::= { lcsEthLinkOAMPortDetailedStatisticsEntry 18 }
   
lcsPortDetailedStatisticsTxOrgSpecificPDUs OBJECT-TYPE
   SYNTAX      Integer32
   MAX-ACCESS  read-only
   STATUS      current
   DESCRIPTION
       "A count of the number of Organization Specific OAMPDUs transmitted on this interface."
   ::= { lcsEthLinkOAMPortDetailedStatisticsEntry 19 }
   
lcsPortDetailedStatisticsTxUnsupportedCodes OBJECT-TYPE
   SYNTAX      Integer32
   MAX-ACCESS  read-only
   STATUS      current
   DESCRIPTION
       "A count of the number of OAMPDUs transmitted on this interface with an unsupported op-code."
   ::= { lcsEthLinkOAMPortDetailedStatisticsEntry 20 }
   
lcsPortDetailedStatisticsTxLinkFaultPDUs OBJECT-TYPE
   SYNTAX      Integer32
   MAX-ACCESS  read-only
   STATUS      current
   DESCRIPTION
       "A count of the number of Link fault PDU's received and transmitted on this interface."
   ::= { lcsEthLinkOAMPortDetailedStatisticsEntry 21 }
   
lcsPortDetailedStatisticsTxDyingGasp OBJECT-TYPE
   SYNTAX      Integer32
   MAX-ACCESS  read-only
   STATUS      current
   DESCRIPTION
       "A count of the number of Dying Gasp events received and transmitted on this interface."
   ::= { lcsEthLinkOAMPortDetailedStatisticsEntry 22 }
   
lcsPortDetailedStatisticsTxCriticalEventPDUs OBJECT-TYPE
   SYNTAX      Integer32
   MAX-ACCESS  read-only
   STATUS      current
   DESCRIPTION
       "A count of the number of Critical event PDU's received and transmitted on this interface."
   ::= { lcsEthLinkOAMPortDetailedStatisticsEntry 23 }
   
lcsPortDetailedStatisticsClear OBJECT-TYPE
   SYNTAX      Integer32
   MAX-ACCESS  read-write
   STATUS      current
   DESCRIPTION
       "Clears the counters for the selected port."
   ::= { lcsEthLinkOAMPortDetailedStatisticsEntry 24 }
   
   
lcsEthLinkOAMPortEventDetailedStatisticsTable OBJECT-TYPE
   SYNTAX      SEQUENCE OF LCSEthLinkOAMPortEventDetailedStatisticsEntry
   MAX-ACCESS  not-accessible
   STATUS      current
   DESCRIPTION
       "Eth Link OAM Port Event Detailed Statistics Table"
   ::= { lcsETHLINKOAM 5 }

lcsEthLinkOAMPortEventDetailedStatisticsEntry OBJECT-TYPE
   SYNTAX      LCSEthLinkOAMPortEventDetailedStatisticsEntry
   MAX-ACCESS  not-accessible
   STATUS      current
   DESCRIPTION
       "Eth Link OAM Port Event Detailed Statistics Entry"
   INDEX    { lcsDetailedStatisticsIndex  }
   ::= { lcsEthLinkOAMPortEventDetailedStatisticsTable 1 }

LCSEthLinkOAMPortEventDetailedStatisticsEntry ::= SEQUENCE {
   lcsDetailedStatisticsIndex                                  Integer32,
   lcsDetailedStatisticsLocalSequenceNumber                    Integer32,
   lcsDetailedStatisticsLocalFrameErrorEventTimestamp          Integer32,
   lcsDetailedStatisticsLocalFrameErrorEventWindow             Integer32,
   lcsDetailedStatisticsLocalFrameErrorEventThreshold          Integer32,
   lcsDetailedStatisticsLocalFrameErrors                       Integer32,
   lcsDetailedStatisticsLocalTotalFrameErrors                  Counter64,
   lcsDetailedStatisticsLocalTotalFrameErrorEvents             Integer32,
   lcsDetailedStatisticsLocalFramePeriodErrorEventTimestamp    Integer32,
   lcsDetailedStatisticsLocalFramePeriodErrorEventWindow       Integer32,
   lcsDetailedStatisticsLocalFramePeriodErrorEventThreshold    Integer32,
   lcsDetailedStatisticsLocalFramePeriodErrors                 Integer32,
   lcsDetailedStatisticsLocalTotalFramePeriodErrors            Counter64,
   lcsDetailedStatisticsLocalTotalFramePeriodErrorEvents       Integer32,
   lcsDetailedStatisticsLocalSymbolPeriodErrorEventTimestamp   Integer32,
   lcsDetailedStatisticsLocalSymbolPeriodErrorEventWindow      Counter64,
   lcsDetailedStatisticsLocalSymbolPeriodErrorEventThreshold   Counter64,
   lcsDetailedStatisticsLocalSymbolPeriodErrors                Counter64,
   lcsDetailedStatisticsLocalSymbolFramePeriodErrors           Counter64,
   lcsDetailedStatisticsLocalSymbolFramePeriodErrorEvents      Integer32,
   lcsDetailedStatisticsLocalEventSecondsSummaryTimeStamp      Integer32,
   lcsDetailedStatisticsLocalEventSecondsSummaryWindow         Integer32,
   lcsDetailedStatisticsLocalEventSecondsSummaryThreshold      Integer32,
   lcsDetailedStatisticsLocalEventSecondsSummaryEvents         Integer32,
   lcsDetailedStatisticsLocalEventSecondsSummaryErrorTotal     Integer32,
   lcsDetailedStatisticsLocalEventSecondsSummaryEventTotal     Integer32,
   lcsDetailedStatisticsRemoteFrameErrorEventTimestamp         Integer32,
   lcsDetailedStatisticsRemoteFrameErrorEventWindow            Integer32,
   lcsDetailedStatisticsRemoteFrameErrorEventThreshold         Integer32,
   lcsDetailedStatisticsRemoteFrameErrors                      Integer32,
   lcsDetailedStatisticsRemoteTotalFrameErrors                 Counter64,
   lcsDetailedStatisticsRemoteTotalFrameErrorEvents            Integer32,
   lcsDetailedStatisticsRemoteFramePeriodErrorEventTimestamp   Integer32,
   lcsDetailedStatisticsRemoteFramePeriodErrorEventWindow      Integer32,
   lcsDetailedStatisticsRemoteFramePeriodErrorEventThreshold   Integer32,
   lcsDetailedStatisticsRemoteFramePeriodErrors                Integer32,
   lcsDetailedStatisticsRemoteTotalFramePeriodErrors           Counter64,
   lcsDetailedStatisticsRemoteTotalFramePeriodErrorEvents      Integer32,
   lcsDetailedStatisticsRemoteSymbolPeriodErrorEventTimestamp  Integer32,
   lcsDetailedStatisticsRemoteSymbolPeriodErrorEventWindow     Counter64,
   lcsDetailedStatisticsRemoteSymbolPeriodErrorEventThreshold  Counter64,
   lcsDetailedStatisticsRemoteSymbolPeriodErrors               Counter64,
   lcsDetailedStatisticsRemoteSymbolFramePeriodErrors          Counter64,
   lcsDetailedStatisticsRemoteSymbolFramePeriodErrorEvents     Integer32,
   lcsDetailedStatisticsRemoteEventSecondsSummaryTimeStamp     Integer32,
   lcsDetailedStatisticsRemoteEventSecondsSummaryWindow        Integer32,
   lcsDetailedStatisticsRemoteEventSecondsSummaryThreshold     Integer32,   
   lcsDetailedStatisticsRemoteEventSecondsSummaryEvents        Integer32,
   lcsDetailedStatisticsRemoteEventSecondsSummaryErrorTotal    Integer32,
   lcsDetailedStatisticsRemoteEventSecondsSummaryEventTotal    Integer32   
}

lcsDetailedStatisticsIndex OBJECT-TYPE
   SYNTAX      Integer32 (1..65535)
   MAX-ACCESS  not-accessible
   STATUS      current
   DESCRIPTION
       "Index"
   ::= { lcsEthLinkOAMPortEventDetailedStatisticsEntry 1 }

lcsDetailedStatisticsLocalSequenceNumber OBJECT-TYPE
   SYNTAX      Integer32
   MAX-ACCESS  read-only
   STATUS      current
   DESCRIPTION
       "This two-octet field indicates the total number of events occurred at the remote end."   
   ::= { lcsEthLinkOAMPortEventDetailedStatisticsEntry 2 }
   
lcsDetailedStatisticsLocalFrameErrorEventTimestamp OBJECT-TYPE
   SYNTAX      Integer32
   MAX-ACCESS  read-only
   STATUS      current
   DESCRIPTION
       "This two-octet field indicates the time reference when the event was generated, in terms of 100 ms intervals."   
   ::= { lcsEthLinkOAMPortEventDetailedStatisticsEntry 3 }

lcsDetailedStatisticsLocalFrameErrorEventWindow OBJECT-TYPE
   SYNTAX      Integer32
   MAX-ACCESS  read-only
   STATUS      current
   DESCRIPTION
       "This two-octet field indicates the duration of the period in terms of 100 ms intervals. 1) 
       The default value is one second. 2) The lower bound is one second. 3) 
       The upper bound is one minute."   
   ::= { lcsEthLinkOAMPortEventDetailedStatisticsEntry 4 }

lcsDetailedStatisticsLocalFrameErrorEventThreshold OBJECT-TYPE
   SYNTAX      Integer32
   MAX-ACCESS  read-only
   STATUS      current
   DESCRIPTION
       "This four-octet field indicates the number of detected errored frames in the period is required
       to be equal to or greater than in order for the event to be generated. 1) 
       The default value is one frame error. 2) 
       The lower bound is zero frame errors. 3) 
       The upper bound is unspecified."   
   ::= { lcsEthLinkOAMPortEventDetailedStatisticsEntry 5 }

lcsDetailedStatisticsLocalFrameErrors OBJECT-TYPE
   SYNTAX      Integer32
   MAX-ACCESS  read-only
   STATUS      current
   DESCRIPTION
       "This four-octet field indicates the number of detected errored frames in the period."   
   ::= { lcsEthLinkOAMPortEventDetailedStatisticsEntry 6 }

lcsDetailedStatisticsLocalTotalFrameErrors OBJECT-TYPE
   SYNTAX      Counter64
   MAX-ACCESS  read-only
   STATUS      current
   DESCRIPTION
       "This eight-octet field indicates the sum of errored frames that have been detected since the OAM sublayer was reset."   
   ::= { lcsEthLinkOAMPortEventDetailedStatisticsEntry 7 }

lcsDetailedStatisticsLocalTotalFrameErrorEvents OBJECT-TYPE
   SYNTAX      Integer32
   MAX-ACCESS  read-only
   STATUS      current
   DESCRIPTION
       "This four-octet field indicates the number of Errored Frame Event TLVs that 
       have been generated since the OAM sublayer was reset."   
   ::= { lcsEthLinkOAMPortEventDetailedStatisticsEntry 8 }

lcsDetailedStatisticsLocalFramePeriodErrorEventTimestamp OBJECT-TYPE
   SYNTAX      Integer32
   MAX-ACCESS  read-only
   STATUS      current
   DESCRIPTION
       "This two-octet field indicates the time reference when the event was generated, in terms of 100 ms intervals."   
   ::= { lcsEthLinkOAMPortEventDetailedStatisticsEntry 9 }

lcsDetailedStatisticsLocalFramePeriodErrorEventWindow OBJECT-TYPE
   SYNTAX      Integer32
   MAX-ACCESS  read-only
   STATUS      current
   DESCRIPTION
       "This four-octet field indicates the duration of period in terms of frames."   
   ::= { lcsEthLinkOAMPortEventDetailedStatisticsEntry 10 }

lcsDetailedStatisticsLocalFramePeriodErrorEventThreshold OBJECT-TYPE
   SYNTAX      Integer32
   MAX-ACCESS  read-only
   STATUS      current
   DESCRIPTION
       "This four-octet field indicates the number of errored frames in the period is required
       to be equal to or greater than in order for the event to be generated."   
   ::= { lcsEthLinkOAMPortEventDetailedStatisticsEntry 11 }

lcsDetailedStatisticsLocalFramePeriodErrors OBJECT-TYPE
   SYNTAX      Integer32
   MAX-ACCESS  read-only
   STATUS      current
   DESCRIPTION
       "This four-octet field indicates the number of frame errors in the period."   
   ::= { lcsEthLinkOAMPortEventDetailedStatisticsEntry 12 }

lcsDetailedStatisticsLocalTotalFramePeriodErrors OBJECT-TYPE
   SYNTAX      Counter64
   MAX-ACCESS  read-only
   STATUS      current
   DESCRIPTION
       "This eight-octet field indicates the sum of frame errors that have been detected since the OAM sublayer was reset."   
   ::= { lcsEthLinkOAMPortEventDetailedStatisticsEntry 13 }

lcsDetailedStatisticsLocalTotalFramePeriodErrorEvents OBJECT-TYPE
   SYNTAX      Integer32
   MAX-ACCESS  read-only
   STATUS      current
   DESCRIPTION
       "This four-octet field indicates the number of Errored Frame Period Event TLVs 
       that have been generated since the OAM sublayer was reset."   
   ::= { lcsEthLinkOAMPortEventDetailedStatisticsEntry 14 }

lcsDetailedStatisticsLocalSymbolPeriodErrorEventTimestamp OBJECT-TYPE
   SYNTAX      Integer32
   MAX-ACCESS  read-only
   STATUS      current
   DESCRIPTION
       "This two-octet field indicates the time reference when the event was generated, in terms of 100 ms intervals."   
   ::= { lcsEthLinkOAMPortEventDetailedStatisticsEntry 15 }

lcsDetailedStatisticsLocalSymbolPeriodErrorEventWindow OBJECT-TYPE
   SYNTAX      Counter64
   MAX-ACCESS  read-only
   STATUS      current
   DESCRIPTION
       "This eight-octet field indicates the number of symbols in the period."   
   ::= { lcsEthLinkOAMPortEventDetailedStatisticsEntry 16 }

lcsDetailedStatisticsLocalSymbolPeriodErrorEventThreshold OBJECT-TYPE
   SYNTAX      Counter64
   MAX-ACCESS  read-only
   STATUS      current
   DESCRIPTION
       "This eight-octet field indicates the number of errored symbols in the period is required to
       be equal to or greater than in order for the event to be generated."   
   ::= { lcsEthLinkOAMPortEventDetailedStatisticsEntry 17 }

lcsDetailedStatisticsLocalSymbolPeriodErrors OBJECT-TYPE
   SYNTAX      Counter64
   MAX-ACCESS  read-only
   STATUS      current
   DESCRIPTION
       "This eight-octet field indicates the number of symbol errors in the period."   
   ::= { lcsEthLinkOAMPortEventDetailedStatisticsEntry 18 }

lcsDetailedStatisticsLocalSymbolFramePeriodErrors OBJECT-TYPE
   SYNTAX      Counter64
   MAX-ACCESS  read-only
   STATUS      current
   DESCRIPTION
       "This eight-octet field indicates the sum of symbol errors since the OAM sublayer was reset."   
   ::= { lcsEthLinkOAMPortEventDetailedStatisticsEntry 19 }

lcsDetailedStatisticsLocalSymbolFramePeriodErrorEvents OBJECT-TYPE
   SYNTAX      Integer32
   MAX-ACCESS  read-only
   STATUS      current
   DESCRIPTION
       "This four-octet field indicates the number of Errored Symbol Period Event TLVs that
       have been generated since the OAM sublayer was reset."   
   ::= { lcsEthLinkOAMPortEventDetailedStatisticsEntry 20 }

lcsDetailedStatisticsLocalEventSecondsSummaryTimeStamp OBJECT-TYPE
   SYNTAX      Integer32
   MAX-ACCESS  read-only
   STATUS      current
   DESCRIPTION
       "This two-octet field indicates the time reference when the event was generated, 
       in terms of 100 ms intervals, encoded as a 16-bit unsigned integer."   
   ::= { lcsEthLinkOAMPortEventDetailedStatisticsEntry 21 }

lcsDetailedStatisticsLocalEventSecondsSummaryWindow OBJECT-TYPE
   SYNTAX      Integer32
   MAX-ACCESS  read-only
   STATUS      current
   DESCRIPTION
       "This two-octet field indicates the duration of the period in terms of 100 ms intervals, encoded as a 16-bit unsigned integer."   
   ::= { lcsEthLinkOAMPortEventDetailedStatisticsEntry 22 }

lcsDetailedStatisticsLocalEventSecondsSummaryThreshold OBJECT-TYPE
   SYNTAX      Integer32
   MAX-ACCESS  read-only
   STATUS      current
   DESCRIPTION
       "This two-octet field indicates the number of errored frame seconds in the period is required
       to be equal to or greater than in order for the event to be generated, encoded as a 16-bit unsigned integer."   
   ::= { lcsEthLinkOAMPortEventDetailedStatisticsEntry 23 }

lcsDetailedStatisticsLocalEventSecondsSummaryEvents OBJECT-TYPE
   SYNTAX      Integer32
   MAX-ACCESS  read-only
   STATUS      current
   DESCRIPTION
       "This two-octet field indicates the number of errored frame seconds in the period, encoded as a 16-bit unsigned integer."   
   ::= { lcsEthLinkOAMPortEventDetailedStatisticsEntry 24 }

lcsDetailedStatisticsLocalEventSecondsSummaryErrorTotal OBJECT-TYPE
   SYNTAX      Integer32
   MAX-ACCESS  read-only
   STATUS      current
   DESCRIPTION
       "This four-octet field indicates the sum of errored frame seconds that have been detected since the OAM sublayer was reset."   
   ::= { lcsEthLinkOAMPortEventDetailedStatisticsEntry 25 }

lcsDetailedStatisticsLocalEventSecondsSummaryEventTotal OBJECT-TYPE
   SYNTAX      Integer32
   MAX-ACCESS  read-only
   STATUS      current
   DESCRIPTION
       "This four-octet field indicates the number of Errored Frame Seconds Summary Event TLVs that 
       have been generated since the OAM sublayer was reset, encoded as a 32bit unsigned integer."   
   ::= { lcsEthLinkOAMPortEventDetailedStatisticsEntry 26 }

lcsDetailedStatisticsRemoteFrameErrorEventTimestamp OBJECT-TYPE
   SYNTAX      Integer32
   MAX-ACCESS  read-only
   STATUS      current
   DESCRIPTION
       "This two-octet field indicates the time reference when the event was generated, in terms of 100 ms intervals."   
   ::= { lcsEthLinkOAMPortEventDetailedStatisticsEntry 27 }
   
lcsDetailedStatisticsRemoteFrameErrorEventWindow OBJECT-TYPE
   SYNTAX      Integer32
   MAX-ACCESS  read-only
   STATUS      current
   DESCRIPTION
       "This two-octet field indicates the duration of the period in terms of 100 ms intervals. 1) 
       The default value is one second. 2) The lower bound is one second. 3) 
       The upper bound is one minute."   
   ::= { lcsEthLinkOAMPortEventDetailedStatisticsEntry 28 }   
   
lcsDetailedStatisticsRemoteFrameErrorEventThreshold OBJECT-TYPE
   SYNTAX      Integer32
   MAX-ACCESS  read-only
   STATUS      current
   DESCRIPTION
       "This four-octet field indicates the number of detected errored frames in the period is required
       to be equal to or greater than in order for the event to be generated. 1) 
       The default value is one frame error. 2) 
       The lower bound is zero frame errors. 3) 
       The upper bound is unspecified."   
   ::= { lcsEthLinkOAMPortEventDetailedStatisticsEntry 29 }

lcsDetailedStatisticsRemoteFrameErrors OBJECT-TYPE
   SYNTAX      Integer32
   MAX-ACCESS  read-only
   STATUS      current
   DESCRIPTION
       "This four-octet field indicates the number of detected errored frames in the period."   
   ::= { lcsEthLinkOAMPortEventDetailedStatisticsEntry 30 }
   
lcsDetailedStatisticsRemoteTotalFrameErrors OBJECT-TYPE
   SYNTAX      Counter64
   MAX-ACCESS  read-only
   STATUS      current
   DESCRIPTION
       "This eight-octet field indicates the sum of errored frames that have been detected since the OAM sublayer was reset."   
   ::= { lcsEthLinkOAMPortEventDetailedStatisticsEntry 31 }
   
lcsDetailedStatisticsRemoteTotalFrameErrorEvents OBJECT-TYPE
   SYNTAX      Integer32
   MAX-ACCESS  read-only
   STATUS      current
   DESCRIPTION
       "This four-octet field indicates the number of Errored Frame Event TLVs that 
       have been generated since the OAM sublayer was reset."   
   ::= { lcsEthLinkOAMPortEventDetailedStatisticsEntry 32 }
   
lcsDetailedStatisticsRemoteFramePeriodErrorEventTimestamp OBJECT-TYPE
   SYNTAX      Integer32
   MAX-ACCESS  read-only
   STATUS      current
   DESCRIPTION
       "This two-octet field indicates the time reference when the event was generated, in terms of 100 ms intervals."   
   ::= { lcsEthLinkOAMPortEventDetailedStatisticsEntry 33 }
   
lcsDetailedStatisticsRemoteFramePeriodErrorEventWindow OBJECT-TYPE
   SYNTAX      Integer32
   MAX-ACCESS  read-only
   STATUS      current
   DESCRIPTION
       "This four-octet field indicates the duration of period in terms of frames."   
   ::= { lcsEthLinkOAMPortEventDetailedStatisticsEntry 34 }
   
lcsDetailedStatisticsRemoteFramePeriodErrorEventThreshold OBJECT-TYPE
   SYNTAX      Integer32
   MAX-ACCESS  read-only
   STATUS      current
   DESCRIPTION
       "This four-octet field indicates the number of errored frames in the period is required
       to be equal to or greater than in order for the event to be generated."   
   ::= { lcsEthLinkOAMPortEventDetailedStatisticsEntry 35 }
   
lcsDetailedStatisticsRemoteFramePeriodErrors OBJECT-TYPE
   SYNTAX      Integer32
   MAX-ACCESS  read-only
   STATUS      current
   DESCRIPTION
       "This four-octet field indicates the number of frame errors in the period."   
   ::= { lcsEthLinkOAMPortEventDetailedStatisticsEntry 36 }
   
lcsDetailedStatisticsRemoteTotalFramePeriodErrors OBJECT-TYPE
   SYNTAX      Counter64
   MAX-ACCESS  read-only
   STATUS      current
   DESCRIPTION
       "This eight-octet field indicates the sum of frame errors that have been detected since the OAM sublayer was reset."   
   ::= { lcsEthLinkOAMPortEventDetailedStatisticsEntry 37 }
   
lcsDetailedStatisticsRemoteTotalFramePeriodErrorEvents OBJECT-TYPE
   SYNTAX      Integer32
   MAX-ACCESS  read-only
   STATUS      current
   DESCRIPTION
       "This four-octet field indicates the number of Errored Frame Period Event TLVs 
       that have been generated since the OAM sublayer was reset."   
   ::= { lcsEthLinkOAMPortEventDetailedStatisticsEntry 38 }
   
lcsDetailedStatisticsRemoteSymbolPeriodErrorEventTimestamp OBJECT-TYPE
   SYNTAX      Integer32
   MAX-ACCESS  read-only
   STATUS      current
   DESCRIPTION
       "This two-octet field indicates the time reference when the event was generated, in terms of 100 ms intervals."   
   ::= { lcsEthLinkOAMPortEventDetailedStatisticsEntry 39 }
   
lcsDetailedStatisticsRemoteSymbolPeriodErrorEventWindow OBJECT-TYPE
   SYNTAX      Counter64
   MAX-ACCESS  read-only
   STATUS      current
   DESCRIPTION
       "This eight-octet field indicates the number of symbols in the period."   
   ::= { lcsEthLinkOAMPortEventDetailedStatisticsEntry 40 }
   
lcsDetailedStatisticsRemoteSymbolPeriodErrorEventThreshold OBJECT-TYPE
   SYNTAX      Counter64
   MAX-ACCESS  read-only
   STATUS      current
   DESCRIPTION
       "This eight-octet field indicates the number of errored symbols in the period is required to
       be equal to or greater than in order for the event to be generated."   
   ::= { lcsEthLinkOAMPortEventDetailedStatisticsEntry 41 }
   
lcsDetailedStatisticsRemoteSymbolPeriodErrors OBJECT-TYPE
   SYNTAX      Counter64
   MAX-ACCESS  read-only
   STATUS      current
   DESCRIPTION
       "This eight-octet field indicates the number of symbol errors in the period."   
   ::= { lcsEthLinkOAMPortEventDetailedStatisticsEntry 42 }
   
lcsDetailedStatisticsRemoteSymbolFramePeriodErrors OBJECT-TYPE
   SYNTAX      Counter64
   MAX-ACCESS  read-only
   STATUS      current
   DESCRIPTION
       "This eight-octet field indicates the sum of symbol errors since the OAM sublayer was reset."   
   ::= { lcsEthLinkOAMPortEventDetailedStatisticsEntry 43 }
   
lcsDetailedStatisticsRemoteSymbolFramePeriodErrorEvents OBJECT-TYPE
   SYNTAX      Integer32
   MAX-ACCESS  read-only
   STATUS      current
   DESCRIPTION
       "This four-octet field indicates the number of Errored Symbol Period Event TLVs that
       have been generated since the OAM sublayer was reset."   
   ::= { lcsEthLinkOAMPortEventDetailedStatisticsEntry 44 }
   
lcsDetailedStatisticsRemoteEventSecondsSummaryTimeStamp OBJECT-TYPE
   SYNTAX      Integer32
   MAX-ACCESS  read-only
   STATUS      current
   DESCRIPTION
       "This two-octet field indicates the time reference when the event was generated, 
       in terms of 100 ms intervals, encoded as a 16-bit unsigned integer."   
   ::= { lcsEthLinkOAMPortEventDetailedStatisticsEntry 45 }
   
lcsDetailedStatisticsRemoteEventSecondsSummaryWindow OBJECT-TYPE
   SYNTAX      Integer32
   MAX-ACCESS  read-only
   STATUS      current
   DESCRIPTION
       "This two-octet field indicates the duration of the period in terms of 100 ms intervals, encoded as a 16-bit unsigned integer."   
   ::= { lcsEthLinkOAMPortEventDetailedStatisticsEntry 46 }
   
lcsDetailedStatisticsRemoteEventSecondsSummaryThreshold OBJECT-TYPE
   SYNTAX      Integer32
   MAX-ACCESS  read-only
   STATUS      current
   DESCRIPTION
       "This two-octet field indicates the number of errored frame seconds in the period is required
       to be equal to or greater than in order for the event to be generated, encoded as a 16-bit unsigned integer."   
   ::= { lcsEthLinkOAMPortEventDetailedStatisticsEntry 47 }
   
lcsDetailedStatisticsRemoteEventSecondsSummaryEvents OBJECT-TYPE
   SYNTAX      Integer32
   MAX-ACCESS  read-only
   STATUS      current
   DESCRIPTION
       "This two-octet field indicates the number of errored frame seconds in the period, encoded as a 16-bit unsigned integer."   
   ::= { lcsEthLinkOAMPortEventDetailedStatisticsEntry 48 }
   
lcsDetailedStatisticsRemoteEventSecondsSummaryErrorTotal OBJECT-TYPE
   SYNTAX      Integer32
   MAX-ACCESS  read-only
   STATUS      current
   DESCRIPTION
       "This four-octet field indicates the sum of errored frame seconds that have been detected since the OAM sublayer was reset."   
   ::= { lcsEthLinkOAMPortEventDetailedStatisticsEntry 49 }
   
lcsDetailedStatisticsRemoteEventSecondsSummaryEventTotal OBJECT-TYPE
   SYNTAX      Integer32
   MAX-ACCESS  read-only
   STATUS      current
   DESCRIPTION
       "This four-octet field indicates the number of Errored Frame Seconds Summary Event TLVs that 
       have been generated since the OAM sublayer was reset, encoded as a 32bit unsigned integer."   
   ::= { lcsEthLinkOAMPortEventDetailedStatisticsEntry 50 }
   
 
lcsIPMC    OBJECT IDENTIFIER ::= { lcsConfiguration 32 }

lcsIGMPSnooping    OBJECT IDENTIFIER ::= { lcsIPMC 1 }

lcsIGMPSnoopingBasicConfigSnoopingEnabled OBJECT-TYPE
   SYNTAX      Integer32(0|1)
   MAX-ACCESS  read-write
   STATUS      current
   DESCRIPTION
       "Snooping Enabled
       0:Disable
       1:Enable"
   ::= {     lcsIGMPSnooping 2 }
   
lcsIGMPSnoopingBasicConfigUnregisteredIPMCv4FloodingEnabled OBJECT-TYPE
   SYNTAX      Integer32(0|1)
   MAX-ACCESS  read-write
   STATUS      current
   DESCRIPTION
       "Unregistered IPMCv4 Flooding Enabled
       0:Disable
       1:Enable"
   ::= {     lcsIGMPSnooping 3 }
   
lcsIGMPSnoopingBasicConfigIGMPSSMRange OBJECT-TYPE
   SYNTAX      IpAddress
   MAX-ACCESS  read-write
   STATUS      current
   DESCRIPTION
       "IGMP SSM Range
        IPv4 multicast address."
   ::= {     lcsIGMPSnooping 4 }   

lcsIGMPSnoopingBasicConfigIGMPSSMRangeLength OBJECT-TYPE
   SYNTAX      Integer32(4..32)
   MAX-ACCESS  read-write
   STATUS      current
   DESCRIPTION
       "IGMP SSM Range prefix. "
   ::= {     lcsIGMPSnooping 5 }

lcsIGMPSnoopingBasicConfigLeaveProxyEnabled OBJECT-TYPE
   SYNTAX      Integer32(0|1)
   MAX-ACCESS  read-write
   STATUS      current
   DESCRIPTION
       "Leave Proxy Enabled
       0:Disable
       1:Enable"
   ::= {     lcsIGMPSnooping 6 }
   
lcsIGMPSnoopingBasicConfigProxyEnabled OBJECT-TYPE
   SYNTAX      Integer32(0|1)
   MAX-ACCESS  read-write
   STATUS      current
   DESCRIPTION
       "Proxy Enabled
       0:Disable
       1:Enable"
   ::= {     lcsIGMPSnooping 7 }   


   
lcsIGMPSnoopingPortRelatedTable OBJECT-TYPE
   SYNTAX      SEQUENCE OF LCSIGMPSnoopingPortRelatedEntry
   MAX-ACCESS  not-accessible
   STATUS      current
   DESCRIPTION
       " "
   ::= { lcsIGMPSnooping 8 }

lcsIGMPSnoopingPortRelatedEntry OBJECT-TYPE
   SYNTAX      LCSIGMPSnoopingPortRelatedEntry
   MAX-ACCESS  not-accessible
   STATUS      current
   DESCRIPTION
       " "
   INDEX    { lcsIGMPSnoopingPortRelatedPort  }
   ::= { lcsIGMPSnoopingPortRelatedTable 1 }

LCSIGMPSnoopingPortRelatedEntry ::= SEQUENCE {
   lcsIGMPSnoopingPortRelatedPort       Integer32,
   lcsIGMPSnoopingPortRouterPort        Integer32,
   lcsIGMPSnoopingPortFastLeave         Integer32,
   lcsIGMPSnoopingPortThrottling        Integer32,
   lcsIGMPSnoopingPortFilteringProfile  DisplayString
}

lcsIGMPSnoopingPortRelatedPort OBJECT-TYPE
   SYNTAX      Integer32 (1..65535)
   MAX-ACCESS  not-accessible
   STATUS      current
   DESCRIPTION
       "Index"
   ::= {     lcsIGMPSnoopingPortRelatedEntry 1 }

lcsIGMPSnoopingPortRouterPort OBJECT-TYPE
   SYNTAX      Integer32(0|1)
   MAX-ACCESS  read-write
   STATUS      current
   DESCRIPTION
       "Router Port
       0:Disable
       1:Enable"
   ::= {     lcsIGMPSnoopingPortRelatedEntry 2 }   

lcsIGMPSnoopingPortFastLeave OBJECT-TYPE
   SYNTAX      Integer32(0|1)
   MAX-ACCESS  read-write
   STATUS      current
   DESCRIPTION
       "Fast Leave
       0:Disable
       1:Enable"
   ::= {     lcsIGMPSnoopingPortRelatedEntry 3 }  
   
lcsIGMPSnoopingPortThrottling OBJECT-TYPE
   SYNTAX      Integer32(0..10)
   MAX-ACCESS  read-write
   STATUS      current
   DESCRIPTION
       "Throttling.
       Range: 0:unlimited, 1-10"
   ::= {     lcsIGMPSnoopingPortRelatedEntry 4 }  
   
lcsIGMPSnoopingPortFilteringProfile OBJECT-TYPE
   SYNTAX      DisplayString
   MAX-ACCESS  read-write
   STATUS      current
   DESCRIPTION
       "Filtering Profile"
   ::= {     lcsIGMPSnoopingPortRelatedEntry 5 }

lcsIGMPSnoopingVLANConfigTable OBJECT-TYPE
   SYNTAX      SEQUENCE OF LCSIGMPSnoopingVLANConfigEntry
   MAX-ACCESS  not-accessible
   STATUS      current
   DESCRIPTION
       " "
   ::= { lcsIGMPSnooping 9 }

lcsIGMPSnoopingVLANConfigEntry OBJECT-TYPE
   SYNTAX      LCSIGMPSnoopingVLANConfigEntry
   MAX-ACCESS  not-accessible
   STATUS      current
   DESCRIPTION
       " "
   INDEX    { lcsIGMPSnoopingVLANConfigIndex  }
   ::= { lcsIGMPSnoopingVLANConfigTable 1 }

LCSIGMPSnoopingVLANConfigEntry ::= SEQUENCE {
   lcsIGMPSnoopingVLANConfigIndex            Integer32,
   lcsIGMPSnoopingVLANConfigVLANID           Integer32,
   lcsIGMPSnoopingVLANConfigSnoopingEnabled  Integer32,
   lcsIGMPSnoopingVLANConfigQuerierElection  Integer32,
   lcsIGMPSnoopingVLANConfigQuerierAddress   IpAddress,
   lcsIGMPSnoopingVLANConfigCompatibility    Integer32,
   lcsIGMPSnoopingVLANConfigPRI              Integer32,
   lcsIGMPSnoopingVLANConfigRV               Integer32,
   lcsIGMPSnoopingVLANConfigQI               Integer32,  
   lcsIGMPSnoopingVLANConfigQRI              Integer32,   
   lcsIGMPSnoopingVLANConfigLLQI             Integer32,   
   lcsIGMPSnoopingVLANConfigURI              Integer32 
}

lcsIGMPSnoopingVLANConfigIndex OBJECT-TYPE
   SYNTAX      Integer32 (1..65535)
   MAX-ACCESS  not-accessible
   STATUS      current
   DESCRIPTION
       "Index"
   ::= {     lcsIGMPSnoopingVLANConfigEntry 1 }

lcsIGMPSnoopingVLANConfigVLANID OBJECT-TYPE
   SYNTAX      Integer32
   MAX-ACCESS  read-only
   STATUS      current
   DESCRIPTION
       "VLAN ID"
   ::= {     lcsIGMPSnoopingVLANConfigEntry 2 }   

lcsIGMPSnoopingVLANConfigSnoopingEnabled OBJECT-TYPE
   SYNTAX      Integer32(0|1)
   MAX-ACCESS  read-write
   STATUS      current
   DESCRIPTION
       "IGMP Snooping Enabled
       0:Disable
       1:Enable"
   ::= {     lcsIGMPSnoopingVLANConfigEntry 3 }  
   
lcsIGMPSnoopingVLANConfigQuerierElection OBJECT-TYPE
   SYNTAX      Integer32(0|1)
   MAX-ACCESS  read-write
   STATUS      current
   DESCRIPTION
       "Querier Election
       0:Disable
       1:Enable"
   ::= {     lcsIGMPSnoopingVLANConfigEntry 4 }  
   
lcsIGMPSnoopingVLANConfigQuerierAddress OBJECT-TYPE
   SYNTAX      IpAddress
   MAX-ACCESS  read-write
   STATUS      current
   DESCRIPTION
       "Querier Address"
   ::= {     lcsIGMPSnoopingVLANConfigEntry 5 }

lcsIGMPSnoopingVLANConfigCompatibility OBJECT-TYPE
   SYNTAX      Integer32(0..3)
   MAX-ACCESS  read-write
   STATUS      current
   DESCRIPTION
       "Compatibility
       0:IGMP-Auto
       1:Forced IGMPv1
       2:Forced IGMPv2
       3:Forced IGMPv3"
   ::= {     lcsIGMPSnoopingVLANConfigEntry 6 }  
   
lcsIGMPSnoopingVLANConfigPRI OBJECT-TYPE
   SYNTAX      Integer32(0..7)
   MAX-ACCESS  read-write
   STATUS      current
   DESCRIPTION
       "Priority of Interface.
       "
   ::= {     lcsIGMPSnoopingVLANConfigEntry 7 }  
   
lcsIGMPSnoopingVLANConfigRV OBJECT-TYPE
   SYNTAX      Integer32(1..255)
   MAX-ACCESS  read-write
   STATUS      current
   DESCRIPTION
       "Robustness Variable."
   ::= {     lcsIGMPSnoopingVLANConfigEntry 8 }  
   
lcsIGMPSnoopingVLANConfigQI OBJECT-TYPE
   SYNTAX      Integer32(1..31744)
   MAX-ACCESS  read-write
   STATUS      current
   DESCRIPTION
       "Query Interval."
   ::= {     lcsIGMPSnoopingVLANConfigEntry 9 }  
   
lcsIGMPSnoopingVLANConfigQRI OBJECT-TYPE
   SYNTAX      Integer32(0..31744)
   MAX-ACCESS  read-write
   STATUS      current
   DESCRIPTION
       "Query Response Interval."
   ::= {     lcsIGMPSnoopingVLANConfigEntry 10 }  
   
lcsIGMPSnoopingVLANConfigLLQI OBJECT-TYPE
   SYNTAX      Integer32(0..31744)
   MAX-ACCESS  read-write
   STATUS      current
   DESCRIPTION
       "Last Member Query Interval."
   ::= {     lcsIGMPSnoopingVLANConfigEntry 11 }  
   
lcsIGMPSnoopingVLANConfigURI OBJECT-TYPE
   SYNTAX      Integer32(0..31744)
   MAX-ACCESS  read-write
   STATUS      current
   DESCRIPTION
       "Unsolicited Report Interval."
   ::= {     lcsIGMPSnoopingVLANConfigEntry 12 }  


lcsIGMPSnoopingStatusClear OBJECT-TYPE
   SYNTAX      Integer32(0|1)
   MAX-ACCESS  read-write
   STATUS      current
   DESCRIPTION
       "Clears all Statistics counters."
   ::= { lcsIGMPSnooping 10 }


lcsIGMPSnoopingStatusTable OBJECT-TYPE
   SYNTAX      SEQUENCE OF LCSIGMPSnoopingStatusEntry
   MAX-ACCESS  not-accessible
   STATUS      current
   DESCRIPTION
       " "
   ::= { lcsIGMPSnooping 11 }

lcsIGMPSnoopingStatusEntry OBJECT-TYPE
   SYNTAX      LCSIGMPSnoopingStatusEntry
   MAX-ACCESS  not-accessible
   STATUS      current
   DESCRIPTION
       " "
   INDEX    { lcsIGMPSnoopingStatusIndex  }
   ::= { lcsIGMPSnoopingStatusTable 1 }

LCSIGMPSnoopingStatusEntry ::= SEQUENCE {
   lcsIGMPSnoopingStatusIndex               Integer32,
   lcsIGMPSnoopingStatusVLANID              Integer32,
   lcsIGMPSnoopingStatusQuerierVersion      DisplayString,
   lcsIGMPSnoopingStatusHostVersion         DisplayString,
   lcsIGMPSnoopingStatusQuerierStatus       Integer32,
   lcsIGMPSnoopingStatusQueriesTransmitted  Integer32,
   lcsIGMPSnoopingStatusQueriesReceived     Integer32,
   lcsIGMPSnoopingStatusV1ReportsReceived   Integer32,
   lcsIGMPSnoopingStatusV2ReportsReceived   Integer32,
   lcsIGMPSnoopingStatusV3ReportsReceived   Integer32,  
   lcsIGMPSnoopingStatusV2LeavesReceived    Integer32
}

lcsIGMPSnoopingStatusIndex OBJECT-TYPE
   SYNTAX      Integer32 (1..65535)
   MAX-ACCESS  not-accessible
   STATUS      current
   DESCRIPTION
       "Index"
   ::= {     lcsIGMPSnoopingStatusEntry 1 }

lcsIGMPSnoopingStatusVLANID OBJECT-TYPE
   SYNTAX      Integer32
   MAX-ACCESS  read-only
   STATUS      current
   DESCRIPTION
       "VLAN ID"
   ::= {     lcsIGMPSnoopingStatusEntry 2 }   

lcsIGMPSnoopingStatusQuerierVersion OBJECT-TYPE
   SYNTAX      DisplayString
   MAX-ACCESS  read-only
   STATUS      current
   DESCRIPTION
       "Querier Version"
   ::= {     lcsIGMPSnoopingStatusEntry 3 }  
   
lcsIGMPSnoopingStatusHostVersion OBJECT-TYPE
   SYNTAX      DisplayString
   MAX-ACCESS  read-only
   STATUS      current
   DESCRIPTION
       "Host Version"
   ::= {     lcsIGMPSnoopingStatusEntry 4 }  
   
lcsIGMPSnoopingStatusQuerierStatus OBJECT-TYPE
   SYNTAX      Integer32
   MAX-ACCESS  read-only
   STATUS      current
   DESCRIPTION
       "Querier Status.
       0:Init
       1:Idle
       2:Active"
   ::= {     lcsIGMPSnoopingStatusEntry 5 }

lcsIGMPSnoopingStatusQueriesTransmitted OBJECT-TYPE
   SYNTAX      Integer32
   MAX-ACCESS  read-only
   STATUS      current
   DESCRIPTION
       "Queries Transmitted."
   ::= {     lcsIGMPSnoopingStatusEntry 6 }  
   
lcsIGMPSnoopingStatusQueriesReceived OBJECT-TYPE
   SYNTAX      Integer32
   MAX-ACCESS  read-only
   STATUS      current
   DESCRIPTION
       "Queries Received."
   ::= {     lcsIGMPSnoopingStatusEntry 7 }  
   
lcsIGMPSnoopingStatusV1ReportsReceived OBJECT-TYPE
   SYNTAX      Integer32
   MAX-ACCESS  read-only
   STATUS      current
   DESCRIPTION
       "V1 Reports Received"
   ::= {     lcsIGMPSnoopingStatusEntry 8 }  
   
lcsIGMPSnoopingStatusV2ReportsReceived OBJECT-TYPE
   SYNTAX      Integer32
   MAX-ACCESS  read-only
   STATUS      current
   DESCRIPTION
       "V2 Reports Received"
   ::= {     lcsIGMPSnoopingStatusEntry 9 }  
   
lcsIGMPSnoopingStatusV3ReportsReceived OBJECT-TYPE
   SYNTAX      Integer32
   MAX-ACCESS  read-only
   STATUS      current
   DESCRIPTION
       "V3 Reports Received"
   ::= {     lcsIGMPSnoopingStatusEntry 10 }  
   
lcsIGMPSnoopingStatusV2LeavesReceived OBJECT-TYPE
   SYNTAX      Integer32
   MAX-ACCESS  read-only
   STATUS      current
   DESCRIPTION
       "V2 Leaves Received"
   ::= {     lcsIGMPSnoopingStatusEntry 11 }  
   
lcsIGMPSnoopingStatusRouterPortTable OBJECT-TYPE
   SYNTAX      SEQUENCE OF LCSIGMPSnoopingStatusRouterPortEntry
   MAX-ACCESS  not-accessible
   STATUS      current
   DESCRIPTION
       " "
   ::= { lcsIGMPSnooping 12 }

lcsIGMPSnoopingStatusRouterPortEntry OBJECT-TYPE
   SYNTAX      LCSIGMPSnoopingStatusRouterPortEntry
   MAX-ACCESS  not-accessible
   STATUS      current
   DESCRIPTION
       " "
   INDEX    { lcsIGMPSnoopingStatusRouterPortIndex  }
   ::= { lcsIGMPSnoopingStatusRouterPortTable 1 }

LCSIGMPSnoopingStatusRouterPortEntry ::= SEQUENCE {
   lcsIGMPSnoopingStatusRouterPortIndex    Integer32,
   lcsIGMPSnoopingStatusRouterPortPort     Integer32
}

lcsIGMPSnoopingStatusRouterPortIndex OBJECT-TYPE
   SYNTAX      Integer32 (1..65535)
   MAX-ACCESS  not-accessible
   STATUS      current
   DESCRIPTION
       "Index"
   ::= {     lcsIGMPSnoopingStatusRouterPortEntry 1 }

lcsIGMPSnoopingStatusRouterPortPort OBJECT-TYPE
   SYNTAX      Integer32
   MAX-ACCESS  read-only
   STATUS      current
   DESCRIPTION
       "Switch port number.
       0:DISABLE
       1:IDLE
       2:ACTIVE"
   ::= {     lcsIGMPSnoopingStatusRouterPortEntry 2 }   



lcsIGMPSnoopingGroupInfoTable OBJECT-TYPE
   SYNTAX      SEQUENCE OF LCSIGMPSnoopingGroupInfoEntry
   MAX-ACCESS  not-accessible
   STATUS      current
   DESCRIPTION
       " "
   ::= { lcsIGMPSnooping 13 }

lcsIGMPSnoopingGroupInfoEntry OBJECT-TYPE
   SYNTAX      LCSIGMPSnoopingGroupInfoEntry
   MAX-ACCESS  not-accessible
   STATUS      current
   DESCRIPTION
       " "
   INDEX    { lcsIGMPSnoopingGroupInfoIndex  }
   ::= { lcsIGMPSnoopingGroupInfoTable 1 }

LCSIGMPSnoopingGroupInfoEntry ::= SEQUENCE {
   lcsIGMPSnoopingGroupInfoIndex       Integer32,
   lcsIGMPSnoopingGroupInfoVLANID      Integer32,
   lcsIGMPSnoopingGroupInfoGroups      IpAddress,
   lcsIGMPSnoopingGroupInfoPortMembers DisplayString
}

lcsIGMPSnoopingGroupInfoIndex OBJECT-TYPE
   SYNTAX      Integer32 (1..65535)
   MAX-ACCESS  not-accessible
   STATUS      current
   DESCRIPTION
       "Index"
   ::= {     lcsIGMPSnoopingGroupInfoEntry 1 }

lcsIGMPSnoopingGroupInfoVLANID OBJECT-TYPE
   SYNTAX      Integer32
   MAX-ACCESS  read-only
   STATUS      current
   DESCRIPTION
       "VLAN ID"
   ::= {     lcsIGMPSnoopingGroupInfoEntry 2 }   

lcsIGMPSnoopingGroupInfoGroups OBJECT-TYPE
   SYNTAX      IpAddress
   MAX-ACCESS  read-only
   STATUS      current
   DESCRIPTION
       "Groups"
   ::= {     lcsIGMPSnoopingGroupInfoEntry 3 } 
   
lcsIGMPSnoopingGroupInfoPortMembers OBJECT-TYPE
   SYNTAX      DisplayString
   MAX-ACCESS  read-only
   STATUS      current
   DESCRIPTION
       "Port Members"
   ::= {     lcsIGMPSnoopingGroupInfoEntry 4 }    
   


lcsIGMPSFMInfoTable OBJECT-TYPE
   SYNTAX      SEQUENCE OF LCSIGMPSFMInfoEntry
   MAX-ACCESS  not-accessible
   STATUS      current
   DESCRIPTION
       " "
   ::= { lcsIGMPSnooping 14 }

lcsIGMPSFMInfoEntry OBJECT-TYPE
   SYNTAX      LCSIGMPSFMInfoEntry
   MAX-ACCESS  not-accessible
   STATUS      current
   DESCRIPTION
       " "
   INDEX    { lcsIGMPSFMInfoIndex  }
   ::= { lcsIGMPSFMInfoTable 1 }

LCSIGMPSFMInfoEntry ::= SEQUENCE {
   lcsIGMPSFMInfoIndex                Integer32,
   lcsIGMPSFMInfoVLANID               Integer32,
   lcsIGMPSFMInfoGroup                IpAddress,
   lcsIGMPSFMInfoPort                 Integer32,
   lcsIGMPSFMInfoMode                 Integer32,
   lcsIGMPSFMInfoSourceAddress        DisplayString,
   lcsIGMPSFMInfoType                 Integer32,
   lcsIGMPSFMInfoHardwareFilterSwitch Integer32
   
}

lcsIGMPSFMInfoIndex OBJECT-TYPE
   SYNTAX      Integer32 (1..65535)
   MAX-ACCESS  not-accessible
   STATUS      current
   DESCRIPTION
       "Index"
   ::= {     lcsIGMPSFMInfoEntry 1 }

lcsIGMPSFMInfoVLANID OBJECT-TYPE
   SYNTAX      Integer32
   MAX-ACCESS  read-only
   STATUS      current
   DESCRIPTION
       "VLAN ID"
   ::= {     lcsIGMPSFMInfoEntry 2 }   

lcsIGMPSFMInfoGroup OBJECT-TYPE
   SYNTAX      IpAddress
   MAX-ACCESS  read-only
   STATUS      current
   DESCRIPTION
       "Group"
   ::= {     lcsIGMPSFMInfoEntry 3 } 
   
lcsIGMPSFMInfoPort OBJECT-TYPE
   SYNTAX      Integer32
   MAX-ACCESS  read-only
   STATUS      current
   DESCRIPTION
       "Port"
   ::= {     lcsIGMPSFMInfoEntry 4 }  
   
lcsIGMPSFMInfoMode OBJECT-TYPE
   SYNTAX      Integer32
   MAX-ACCESS  read-only
   STATUS      current
   DESCRIPTION
       "Mode
       0:Exclude.
       1:Include"
   ::= {     lcsIGMPSFMInfoEntry 5 }  

lcsIGMPSFMInfoSourceAddress OBJECT-TYPE
   SYNTAX      DisplayString
   MAX-ACCESS  read-only
   STATUS      current
   DESCRIPTION
       "Source Address"
   ::= {     lcsIGMPSFMInfoEntry 6 } 
   
lcsIGMPSFMInfoType OBJECT-TYPE
   SYNTAX      Integer32
   MAX-ACCESS  read-only
   STATUS      current
   DESCRIPTION
       "Type
       0:Deny
       1:Allow"
   ::= {     lcsIGMPSFMInfoEntry 7 }  
   
lcsIGMPSFMInfoHardwareFilterSwitch OBJECT-TYPE
   SYNTAX      Integer32
   MAX-ACCESS  read-only
   STATUS      current
   DESCRIPTION
       "Hardware Filter\Switch
       0:No
       1:Yes"
   ::= {     lcsIGMPSFMInfoEntry 8 }     

lcsMLDSnooping    OBJECT IDENTIFIER ::= { lcsIPMC 2 }

lcsMLDSnoopingBasicConfigSnoopingEnabled OBJECT-TYPE
   SYNTAX      Integer32(0|1)
   MAX-ACCESS  read-write
   STATUS      current
   DESCRIPTION
       "Snooping Enabled
       0:Disable
       1:Enable"
   ::= {     lcsMLDSnooping 2 }
   
lcsMLDSnoopingBasicConfigUnregisteredIPMCv6FloodingEnabled OBJECT-TYPE
   SYNTAX      Integer32(0|1)
   MAX-ACCESS  read-write
   STATUS      current
   DESCRIPTION
       "Unregistered IPMCv6 Flooding Enabled
       0:Disable
       1:Enable"
   ::= {     lcsMLDSnooping 3 }
   
lcsMLDSnoopingBasicConfigMLDSSMRange OBJECT-TYPE
   SYNTAX      DisplayString
   MAX-ACCESS  read-write
   STATUS      current
   DESCRIPTION
       "MLD SSM Range
        IPv6 multicast address."
   ::= {     lcsMLDSnooping 4 }   

lcsMLDSnoopingBasicConfigMLDSSMRangeLength OBJECT-TYPE
   SYNTAX      Integer32(8..128)
   MAX-ACCESS  read-write
   STATUS      current
   DESCRIPTION
       "MLD SSM Range prefix. "
   ::= {     lcsMLDSnooping 5 }

lcsMLDSnoopingBasicConfigLeaveProxyEnabled OBJECT-TYPE
   SYNTAX      Integer32(0|1)
   MAX-ACCESS  read-write
   STATUS      current
   DESCRIPTION
       "Leave Proxy Enabled
       0:Disable
       1:Enable"
   ::= {     lcsMLDSnooping 6 }
   
lcsMLDSnoopingBasicConfigProxyEnabled OBJECT-TYPE
   SYNTAX      Integer32(0|1)
   MAX-ACCESS  read-write
   STATUS      current
   DESCRIPTION
       "Proxy Enabled
       0:Disable
       1:Enable"
   ::= {     lcsMLDSnooping 7 }   


   
lcsMLDSnoopingPortRelatedTable OBJECT-TYPE
   SYNTAX      SEQUENCE OF LCSMLDSnoopingPortRelatedEntry
   MAX-ACCESS  not-accessible
   STATUS      current
   DESCRIPTION
       " "
   ::= { lcsMLDSnooping 8 }

lcsMLDSnoopingPortRelatedEntry OBJECT-TYPE
   SYNTAX      LCSMLDSnoopingPortRelatedEntry
   MAX-ACCESS  not-accessible
   STATUS      current
   DESCRIPTION
       " "
   INDEX    { lcsMLDSnoopingPortRelatedPort  }
   ::= { lcsMLDSnoopingPortRelatedTable 1 }

LCSMLDSnoopingPortRelatedEntry ::= SEQUENCE {
   lcsMLDSnoopingPortRelatedPort       Integer32,
   lcsMLDSnoopingPortRouterPort        Integer32,
   lcsMLDSnoopingPortFastLeave         Integer32,
   lcsMLDSnoopingPortThrottling        Integer32,
   lcsMLDSnoopingPortFilteringProfile  DisplayString
}

lcsMLDSnoopingPortRelatedPort OBJECT-TYPE
   SYNTAX      Integer32 (1..65535)
   MAX-ACCESS  not-accessible
   STATUS      current
   DESCRIPTION
       "Index"
   ::= {     lcsMLDSnoopingPortRelatedEntry 1 }

lcsMLDSnoopingPortRouterPort OBJECT-TYPE
   SYNTAX      Integer32(0|1)
   MAX-ACCESS  read-write
   STATUS      current
   DESCRIPTION
       "Router Port
       0:Disable
       1:Enable"
   ::= {     lcsMLDSnoopingPortRelatedEntry 2 }   

lcsMLDSnoopingPortFastLeave OBJECT-TYPE
   SYNTAX      Integer32(0|1)
   MAX-ACCESS  read-write
   STATUS      current
   DESCRIPTION
       "Fast Leave
       0:Disable
       1:Enable"
   ::= {     lcsMLDSnoopingPortRelatedEntry 3 }  
   
lcsMLDSnoopingPortThrottling OBJECT-TYPE
   SYNTAX      Integer32(0..10)
   MAX-ACCESS  read-write
   STATUS      current
   DESCRIPTION
       "Throttling.
       Range: 0:unlimited, 1-10"
   ::= {     lcsMLDSnoopingPortRelatedEntry 4 }  
   
lcsMLDSnoopingPortFilteringProfile OBJECT-TYPE
   SYNTAX      DisplayString
   MAX-ACCESS  read-write
   STATUS      current
   DESCRIPTION
       "Filtering Profile"
   ::= {     lcsMLDSnoopingPortRelatedEntry 5 }


lcsMLDSnoopingVLANConfigTable OBJECT-TYPE
   SYNTAX      SEQUENCE OF LCSMLDSnoopingVLANConfigEntry
   MAX-ACCESS  not-accessible
   STATUS      current
   DESCRIPTION
       " "
   ::= { lcsMLDSnooping 9 }

lcsMLDSnoopingVLANConfigEntry OBJECT-TYPE
   SYNTAX      LCSMLDSnoopingVLANConfigEntry
   MAX-ACCESS  not-accessible
   STATUS      current
   DESCRIPTION
       " "
   INDEX    { lcsMLDSnoopingVLANConfigIndex  }
   ::= { lcsMLDSnoopingVLANConfigTable 1 }

LCSMLDSnoopingVLANConfigEntry ::= SEQUENCE {
   lcsMLDSnoopingVLANConfigIndex            Integer32,
   lcsMLDSnoopingVLANConfigVLANID           Integer32,
   lcsMLDSnoopingVLANConfigSnoopingEnabled  Integer32,
   lcsMLDSnoopingVLANConfigQuerierElection  Integer32,
   lcsMLDSnoopingVLANConfigCompatibility    Integer32,
   lcsMLDSnoopingVLANConfigPRI              Integer32,
   lcsMLDSnoopingVLANConfigRV               Integer32,
   lcsMLDSnoopingVLANConfigQI               Integer32,  
   lcsMLDSnoopingVLANConfigQRI              Integer32,   
   lcsMLDSnoopingVLANConfigLLQI             Integer32,   
   lcsMLDSnoopingVLANConfigURI              Integer32 
}

lcsMLDSnoopingVLANConfigIndex OBJECT-TYPE
   SYNTAX      Integer32 (1..65535)
   MAX-ACCESS  not-accessible
   STATUS      current
   DESCRIPTION
       "Index"
   ::= {     lcsMLDSnoopingVLANConfigEntry 1 }

lcsMLDSnoopingVLANConfigVLANID OBJECT-TYPE
   SYNTAX      Integer32
   MAX-ACCESS  read-only
   STATUS      current
   DESCRIPTION
       "VLAN ID"
   ::= {     lcsMLDSnoopingVLANConfigEntry 2 }   

lcsMLDSnoopingVLANConfigSnoopingEnabled OBJECT-TYPE
   SYNTAX      Integer32(0|1)
   MAX-ACCESS  read-write
   STATUS      current
   DESCRIPTION
       "IGMP Snooping Enabled
       0:Disable
       1:Enable"
   ::= {     lcsMLDSnoopingVLANConfigEntry 3 }  
   
lcsMLDSnoopingVLANConfigQuerierElection OBJECT-TYPE
   SYNTAX      Integer32(0|1)
   MAX-ACCESS  read-write
   STATUS      current
   DESCRIPTION
       "Querier Election
       0:Disable
       1:Enable"
   ::= {     lcsMLDSnoopingVLANConfigEntry 4 }  

lcsMLDSnoopingVLANConfigCompatibility OBJECT-TYPE
   SYNTAX      Integer32(0..2)
   MAX-ACCESS  read-write
   STATUS      current
   DESCRIPTION
       "Compatibility
       0:MLD-Auto
       1:Forced MLDv1
       2:Forced MLDv2"
   ::= {     lcsMLDSnoopingVLANConfigEntry 6 }  
   
lcsMLDSnoopingVLANConfigPRI OBJECT-TYPE
   SYNTAX      Integer32(0..7)
   MAX-ACCESS  read-write
   STATUS      current
   DESCRIPTION
       "Priority of Interface.
       "
   ::= {     lcsMLDSnoopingVLANConfigEntry 7 }  
   
lcsMLDSnoopingVLANConfigRV OBJECT-TYPE
   SYNTAX      Integer32(1..255)
   MAX-ACCESS  read-write
   STATUS      current
   DESCRIPTION
       "Robustness Variable."
   ::= {     lcsMLDSnoopingVLANConfigEntry 8 }  
   
lcsMLDSnoopingVLANConfigQI OBJECT-TYPE
   SYNTAX      Integer32(1..31744)
   MAX-ACCESS  read-write
   STATUS      current
   DESCRIPTION
       "Query Interval."
   ::= {     lcsMLDSnoopingVLANConfigEntry 9 }  
   
lcsMLDSnoopingVLANConfigQRI OBJECT-TYPE
   SYNTAX      Integer32(0..31744)
   MAX-ACCESS  read-write
   STATUS      current
   DESCRIPTION
       "Query Response Interval."
   ::= {     lcsMLDSnoopingVLANConfigEntry 10 }  
   
lcsMLDSnoopingVLANConfigLLQI OBJECT-TYPE
   SYNTAX      Integer32(0..31744)
   MAX-ACCESS  read-write
   STATUS      current
   DESCRIPTION
       "Last Member Query Interval."
   ::= {     lcsMLDSnoopingVLANConfigEntry 11 }  
   
lcsMLDSnoopingVLANConfigURI OBJECT-TYPE
   SYNTAX      Integer32(0..31744)
   MAX-ACCESS  read-write
   STATUS      current
   DESCRIPTION
       "Unsolicited Report Interval."
   ::= {     lcsMLDSnoopingVLANConfigEntry 12 }  


lcsMLDSnoopingStatusClear OBJECT-TYPE
   SYNTAX      Integer32(0|1)
   MAX-ACCESS  read-write
   STATUS      current
   DESCRIPTION
       "Clears all Statistics counters."
   ::= { lcsMLDSnooping 10 }


lcsMLDSnoopingStatusTable OBJECT-TYPE
   SYNTAX      SEQUENCE OF LCSMLDSnoopingStatusEntry
   MAX-ACCESS  not-accessible
   STATUS      current
   DESCRIPTION
       " "
   ::= { lcsMLDSnooping 11 }

lcsMLDSnoopingStatusEntry OBJECT-TYPE
   SYNTAX      LCSMLDSnoopingStatusEntry
   MAX-ACCESS  not-accessible
   STATUS      current
   DESCRIPTION
       " "
   INDEX    { lcsMLDSnoopingStatusIndex  }
   ::= { lcsMLDSnoopingStatusTable 1 }

LCSMLDSnoopingStatusEntry ::= SEQUENCE {
   lcsMLDSnoopingStatusIndex               Integer32,
   lcsMLDSnoopingStatusVLANID              Integer32,
   lcsMLDSnoopingStatusQuerierVersion      DisplayString,
   lcsMLDSnoopingStatusHostVersion         DisplayString,
   lcsMLDSnoopingStatusQuerierStatus       Integer32,
   lcsMLDSnoopingStatusQueriesTransmitted  Integer32,
   lcsMLDSnoopingStatusQueriesReceived     Integer32,
   lcsMLDSnoopingStatusV1ReportsReceived   Integer32,
   lcsMLDSnoopingStatusV2ReportsReceived   Integer32,
   lcsMLDSnoopingStatusV1LeavesReceived    Integer32
}

lcsMLDSnoopingStatusIndex OBJECT-TYPE
   SYNTAX      Integer32 (1..65535)
   MAX-ACCESS  not-accessible
   STATUS      current
   DESCRIPTION
       "Index"
   ::= {     lcsMLDSnoopingStatusEntry 1 }

lcsMLDSnoopingStatusVLANID OBJECT-TYPE
   SYNTAX      Integer32
   MAX-ACCESS  read-only
   STATUS      current
   DESCRIPTION
       "VLAN ID"
   ::= {     lcsMLDSnoopingStatusEntry 2 }   

lcsMLDSnoopingStatusQuerierVersion OBJECT-TYPE
   SYNTAX      DisplayString
   MAX-ACCESS  read-only
   STATUS      current
   DESCRIPTION
       "Querier Version"
   ::= {     lcsMLDSnoopingStatusEntry 3 }  
   
lcsMLDSnoopingStatusHostVersion OBJECT-TYPE
   SYNTAX      DisplayString
   MAX-ACCESS  read-only
   STATUS      current
   DESCRIPTION
       "Host Version"
   ::= {     lcsMLDSnoopingStatusEntry 4 }  
   
lcsMLDSnoopingStatusQuerierStatus OBJECT-TYPE
   SYNTAX      Integer32
   MAX-ACCESS  read-only
   STATUS      current
   DESCRIPTION
       "Querier Status.
       0:Init
       1:Idle
       2:Active"
   ::= {     lcsMLDSnoopingStatusEntry 5 }

lcsMLDSnoopingStatusQueriesTransmitted OBJECT-TYPE
   SYNTAX      Integer32
   MAX-ACCESS  read-only
   STATUS      current
   DESCRIPTION
       "Queries Transmitted."
   ::= {     lcsMLDSnoopingStatusEntry 6 }  
   
lcsMLDSnoopingStatusQueriesReceived OBJECT-TYPE
   SYNTAX      Integer32
   MAX-ACCESS  read-only
   STATUS      current
   DESCRIPTION
       "Queries Received."
   ::= {     lcsMLDSnoopingStatusEntry 7 }  
   
lcsMLDSnoopingStatusV1ReportsReceived OBJECT-TYPE
   SYNTAX      Integer32
   MAX-ACCESS  read-only
   STATUS      current
   DESCRIPTION
       "V1 Reports Received"
   ::= {     lcsMLDSnoopingStatusEntry 8 }  
   
lcsMLDSnoopingStatusV2ReportsReceived OBJECT-TYPE
   SYNTAX      Integer32
   MAX-ACCESS  read-only
   STATUS      current
   DESCRIPTION
       "V2 Reports Received"
   ::= {     lcsMLDSnoopingStatusEntry 9 }  
   
lcsMLDSnoopingStatusV1LeavesReceived OBJECT-TYPE
   SYNTAX      Integer32
   MAX-ACCESS  read-only
   STATUS      current
   DESCRIPTION
       "V1 Leaves Received"
   ::= {     lcsMLDSnoopingStatusEntry 11 }  
   
lcsMLDSnoopingStatusRouterPortTable OBJECT-TYPE
   SYNTAX      SEQUENCE OF LCSMLDSnoopingStatusRouterPortEntry
   MAX-ACCESS  not-accessible
   STATUS      current
   DESCRIPTION
       " "
   ::= { lcsMLDSnooping 12 }

lcsMLDSnoopingStatusRouterPortEntry OBJECT-TYPE
   SYNTAX      LCSMLDSnoopingStatusRouterPortEntry
   MAX-ACCESS  not-accessible
   STATUS      current
   DESCRIPTION
       " "
   INDEX    { lcsMLDSnoopingStatusRouterPortIndex  }
   ::= { lcsMLDSnoopingStatusRouterPortTable 1 }

LCSMLDSnoopingStatusRouterPortEntry ::= SEQUENCE {
   lcsMLDSnoopingStatusRouterPortIndex    Integer32,
   lcsMLDSnoopingStatusRouterPortPort     Integer32
}

lcsMLDSnoopingStatusRouterPortIndex OBJECT-TYPE
   SYNTAX      Integer32 (1..65535)
   MAX-ACCESS  not-accessible
   STATUS      current
   DESCRIPTION
       "Index"
   ::= {     lcsMLDSnoopingStatusRouterPortEntry 1 }

lcsMLDSnoopingStatusRouterPortPort OBJECT-TYPE
   SYNTAX      Integer32
   MAX-ACCESS  read-only
   STATUS      current
   DESCRIPTION
       "Switch port number.
       0:DISABLE
       1:IDLE
       2:ACTIVE"
   ::= {     lcsMLDSnoopingStatusRouterPortEntry 2 }  
   
   
lcsMLDSnoopingGroupInfoTable OBJECT-TYPE
   SYNTAX      SEQUENCE OF LCSMLDSnoopingGroupInfoEntry
   MAX-ACCESS  not-accessible
   STATUS      current
   DESCRIPTION
       " "
   ::= { lcsMLDSnooping 13 }

lcsMLDSnoopingGroupInfoEntry OBJECT-TYPE
   SYNTAX      LCSMLDSnoopingGroupInfoEntry
   MAX-ACCESS  not-accessible
   STATUS      current
   DESCRIPTION
       " "
   INDEX    { lcsMLDSnoopingGroupInfoIndex  }
   ::= { lcsMLDSnoopingGroupInfoTable 1 }

LCSMLDSnoopingGroupInfoEntry ::= SEQUENCE {
   lcsMLDSnoopingGroupInfoIndex       Integer32,
   lcsMLDSnoopingGroupInfoVLANID      Integer32,
   lcsMLDSnoopingGroupInfoGroups      IpAddress,
   lcsMLDSnoopingGroupInfoPortMembers DisplayString
}

lcsMLDSnoopingGroupInfoIndex OBJECT-TYPE
   SYNTAX      Integer32 (1..65535)
   MAX-ACCESS  not-accessible
   STATUS      current
   DESCRIPTION
       "Index"
   ::= {     lcsMLDSnoopingGroupInfoEntry 1 }

lcsMLDSnoopingGroupInfoVLANID OBJECT-TYPE
   SYNTAX      Integer32
   MAX-ACCESS  read-only
   STATUS      current
   DESCRIPTION
       "VLAN ID"
   ::= {     lcsMLDSnoopingGroupInfoEntry 2 }   

lcsMLDSnoopingGroupInfoGroups OBJECT-TYPE
   SYNTAX      IpAddress
   MAX-ACCESS  read-only
   STATUS      current
   DESCRIPTION
       "Groups"
   ::= {     lcsMLDSnoopingGroupInfoEntry 3 } 
   
lcsMLDSnoopingGroupInfoPortMembers OBJECT-TYPE
   SYNTAX      DisplayString
   MAX-ACCESS  read-only
   STATUS      current
   DESCRIPTION
       "Port Members"
   ::= {     lcsMLDSnoopingGroupInfoEntry 4 }    
   


lcsMLDSFMInfoTable OBJECT-TYPE
   SYNTAX      SEQUENCE OF LCSMLDSFMInfoEntry
   MAX-ACCESS  not-accessible
   STATUS      current
   DESCRIPTION
       " "
   ::= { lcsMLDSnooping 14 }

lcsMLDSFMInfoEntry OBJECT-TYPE
   SYNTAX      LCSMLDSFMInfoEntry
   MAX-ACCESS  not-accessible
   STATUS      current
   DESCRIPTION
       " "
   INDEX    { lcsMLDSFMInfoIndex  }
   ::= { lcsMLDSFMInfoTable 1 }

LCSMLDSFMInfoEntry ::= SEQUENCE {
   lcsMLDSFMInfoIndex                Integer32,
   lcsMLDSFMInfoVLANID               Integer32,
   lcsMLDSFMInfoGroup                IpAddress,
   lcsMLDSFMInfoPort                 Integer32,
   lcsMLDSFMInfoMode                 Integer32,
   lcsMLDSFMInfoSourceAddress        DisplayString,
   lcsMLDSFMInfoType                 Integer32,
   lcsMLDSFMInfoHardwareFilterSwitch Integer32
   
}

lcsMLDSFMInfoIndex OBJECT-TYPE
   SYNTAX      Integer32 (1..65535)
   MAX-ACCESS  not-accessible
   STATUS      current
   DESCRIPTION
       "Index"
   ::= {     lcsMLDSFMInfoEntry 1 }

lcsMLDSFMInfoVLANID OBJECT-TYPE
   SYNTAX      Integer32
   MAX-ACCESS  read-only
   STATUS      current
   DESCRIPTION
       "VLAN ID"
   ::= {     lcsMLDSFMInfoEntry 2 }   

lcsMLDSFMInfoGroup OBJECT-TYPE
   SYNTAX      IpAddress
   MAX-ACCESS  read-only
   STATUS      current
   DESCRIPTION
       "Group"
   ::= {     lcsMLDSFMInfoEntry 3 } 
   
lcsMLDSFMInfoPort OBJECT-TYPE
   SYNTAX      Integer32
   MAX-ACCESS  read-only
   STATUS      current
   DESCRIPTION
       "Port"
   ::= {     lcsMLDSFMInfoEntry 4 }  
   
lcsMLDSFMInfoMode OBJECT-TYPE
   SYNTAX      Integer32
   MAX-ACCESS  read-only
   STATUS      current
   DESCRIPTION
       "Mode
       0:Exclude.
       1:Include"
   ::= {     lcsMLDSFMInfoEntry 5 }  

lcsMLDSFMInfoSourceAddress OBJECT-TYPE
   SYNTAX      DisplayString
   MAX-ACCESS  read-only
   STATUS      current
   DESCRIPTION
       "Source Address"
   ::= {     lcsMLDSFMInfoEntry 6 } 
   
lcsMLDSFMInfoType OBJECT-TYPE
   SYNTAX      Integer32
   MAX-ACCESS  read-only
   STATUS      current
   DESCRIPTION
       "Type
       0:Deny
       1:Allow"
   ::= {     lcsMLDSFMInfoEntry 7 }  
   
lcsMLDSFMInfoHardwareFilterSwitch OBJECT-TYPE
   SYNTAX      Integer32
   MAX-ACCESS  read-only
   STATUS      current
   DESCRIPTION
       "Hardware Filter\Switch
       0:No
       1:Yes"
   ::= {     lcsMLDSFMInfoEntry 8 }   

lcsMVR    OBJECT IDENTIFIER ::= { lcsConfiguration 33 }

lcsMVRConfig    OBJECT IDENTIFIER ::= { lcsMVR 1 }

lcsMVRConfigMVRMode OBJECT-TYPE
   SYNTAX      Integer32
   MAX-ACCESS  read-write
   STATUS      current
   DESCRIPTION
       "MVR Mode
       0:Disable
       1:Enable"
   ::= { lcsMVRConfig 2 } 


lcsVLANInterfaceSettingTable  OBJECT-TYPE
   SYNTAX      SEQUENCE OF LCSVLANInterfaceSettingEntry
   MAX-ACCESS  not-accessible
   STATUS      current
   DESCRIPTION
       "MVR Config table"
 ::= { lcsMVRConfig 3 }

lcsVLANInterfaceSettingEntry OBJECT-TYPE
    SYNTAX        LCSVLANInterfaceSettingEntry
    MAX-ACCESS    not-accessible
    STATUS        current
    DESCRIPTION
        "MVR Config table"
    INDEX        { lcsVLANInterfaceSettingIndex }
    ::= { lcsVLANInterfaceSettingTable 1 }

LCSVLANInterfaceSettingEntry ::=
    SEQUENCE {
        lcsVLANInterfaceSettingIndex                    Integer32,
        lcsVLANInterfaceSettingMVRVID                   Integer32,
        lcsVLANInterfaceSettingMVRName                  DisplayString,
        lcsVLANInterfaceSettingIGMPAddress              IpAddress,
        lcsVLANInterfaceSettingMode                     Integer32,
        lcsVLANInterfaceSettingTagging                  Integer32,
        lcsVLANInterfaceSettingPriority                 Integer32,
        lcsVLANInterfaceSettingLLQI                     Integer32,
        lcsVLANInterfaceSettingInterfaceChannelProfile  DisplayString,      
        lcsVLANInterfaceSettingRowStatus                RowStatus
    }
    
lcsVLANInterfaceSettingIndex OBJECT-TYPE
   SYNTAX      Integer32 (1..65535)
   MAX-ACCESS  not-accessible
   STATUS      current
   DESCRIPTION
       "MVR Config index."
   ::= {lcsVLANInterfaceSettingEntry 1 }    
    
lcsVLANInterfaceSettingMVRVID OBJECT-TYPE
   SYNTAX      Integer32
   MAX-ACCESS  read-create
   STATUS      current
   DESCRIPTION
       "MVR VLAN ID"
   ::= {lcsVLANInterfaceSettingEntry 2 }    
    
lcsVLANInterfaceSettingMVRName OBJECT-TYPE
   SYNTAX      DisplayString
   MAX-ACCESS  read-create
   STATUS      current
   DESCRIPTION
       "MVR Name. Length:0-16"
   ::= {lcsVLANInterfaceSettingEntry 3 }    
    
lcsVLANInterfaceSettingIGMPAddress OBJECT-TYPE
   SYNTAX      IpAddress
   MAX-ACCESS  read-create
   STATUS      current
   DESCRIPTION
       "IPv4 IGMP Address"
   ::= {lcsVLANInterfaceSettingEntry 4 }

lcsVLANInterfaceSettingMode OBJECT-TYPE
   SYNTAX      Integer32
   MAX-ACCESS  read-create
   STATUS      current
   DESCRIPTION
      "Mode.
       0:Dynamic
       1:Compatible"
   ::= {lcsVLANInterfaceSettingEntry 5 }
   
lcsVLANInterfaceSettingTagging OBJECT-TYPE
   SYNTAX      Integer32
   MAX-ACCESS  read-create
   STATUS      current
   DESCRIPTION
      "Tagging.
       0:Untagged
       1:Tagged"
   ::= {lcsVLANInterfaceSettingEntry 6 }   
   
lcsVLANInterfaceSettingPriority OBJECT-TYPE
   SYNTAX      Integer32(0..7)
   MAX-ACCESS  read-create
   STATUS      current
   DESCRIPTION
      "Priority"
   ::= {lcsVLANInterfaceSettingEntry 7 }   

lcsVLANInterfaceSettingLLQI OBJECT-TYPE
   SYNTAX      Integer32(0..31744)
   MAX-ACCESS  read-create
   STATUS      current
   DESCRIPTION
      "LLQI"
   ::= {lcsVLANInterfaceSettingEntry 8 }     
   
lcsVLANInterfaceSettingInterfaceChannelProfile OBJECT-TYPE
   SYNTAX      DisplayString
   MAX-ACCESS  read-create
   STATUS      current
   DESCRIPTION
      "Interface Channel Profile."
   ::= {lcsVLANInterfaceSettingEntry 9 }     
   

lcsVLANInterfaceSettingRowStatus OBJECT-TYPE
   SYNTAX      RowStatus
   MAX-ACCESS  read-create
   STATUS      current
   DESCRIPTION
       "Row Status."
   ::= {lcsVLANInterfaceSettingEntry 10 }     

lcsMVRVIDIndex OBJECT-TYPE
   SYNTAX      Integer32
   MAX-ACCESS  read-write
   STATUS      current
   DESCRIPTION
       "Set VIDIndex before use VLANInterfaceSettingPortRoleTable table."
   ::= { lcsMVRConfig 4 } 
   
lcsVLANInterfaceSettingPortRoleTable  OBJECT-TYPE
   SYNTAX      SEQUENCE OF LCSVLANInterfaceSettingPortRoleEntry
   MAX-ACCESS  not-accessible
   STATUS      current
   DESCRIPTION
       "VLAN Interface Setting Port Role table"
 ::= { lcsMVRConfig 5 }

lcsVLANInterfaceSettingPortRoleEntry OBJECT-TYPE
    SYNTAX        LCSVLANInterfaceSettingPortRoleEntry
    MAX-ACCESS    not-accessible
    STATUS        current
    DESCRIPTION
        "VLAN Interface Setting Port Role table"
    INDEX        { lcsVLANInterfaceSettingPortRoleIndex }
    ::= { lcsVLANInterfaceSettingPortRoleTable 1 }

LCSVLANInterfaceSettingPortRoleEntry ::=
    SEQUENCE {
        lcsVLANInterfaceSettingPortRoleIndex   Integer32,
        lcsVLANInterfaceSettingPortRolePort    Integer32
    }
    
lcsVLANInterfaceSettingPortRoleIndex OBJECT-TYPE
   SYNTAX      Integer32 (1..65535)
   MAX-ACCESS  not-accessible
   STATUS      current
   DESCRIPTION
       "VLAN Interface Setting Port Role index."
   ::= {lcsVLANInterfaceSettingPortRoleEntry 1 }    
    
lcsVLANInterfaceSettingPortRolePort OBJECT-TYPE
   SYNTAX      Integer32(0..2)
   MAX-ACCESS  read-write
   STATUS      current
   DESCRIPTION
       "Port Role.
       0:Inactive 
       1:Source 
       2:Receiver"
   ::= {lcsVLANInterfaceSettingPortRoleEntry 2 }    

   
   
lcsImmediateLeaveSettingTable  OBJECT-TYPE
   SYNTAX      SEQUENCE OF LCSImmediateLeaveSettingEntry
   MAX-ACCESS  not-accessible
   STATUS      current
   DESCRIPTION
       "Immediate Leave Setting table"
 ::= { lcsMVRConfig 6 }

lcsImmediateLeaveSettingEntry OBJECT-TYPE
    SYNTAX        LCSImmediateLeaveSettingEntry
    MAX-ACCESS    not-accessible
    STATUS        current
    DESCRIPTION
        "Immediate Leave Setting table"
    INDEX        { lcsImmediateLeaveSettingPort }
    ::= { lcsImmediateLeaveSettingTable 1 }

LCSImmediateLeaveSettingEntry ::=
    SEQUENCE {
        lcsImmediateLeaveSettingPort            Integer32,
        lcsImmediateLeaveSettingImmediateLeave  Integer32
    }
    
lcsImmediateLeaveSettingPort OBJECT-TYPE
   SYNTAX      Integer32 (1..65535)
   MAX-ACCESS  not-accessible
   STATUS      current
   DESCRIPTION
       "Immediate Leave Setting index."
   ::= {lcsImmediateLeaveSettingEntry 1 }    
    
lcsImmediateLeaveSettingImmediateLeave OBJECT-TYPE
   SYNTAX      Integer32(0|1)
   MAX-ACCESS  read-write
   STATUS      current
   DESCRIPTION
      "Immediate Leave
       0:Disable
       1:Enable"
   ::= {lcsImmediateLeaveSettingEntry 2 }     
   
   
lcsStatistics    OBJECT IDENTIFIER ::= { lcsMVR 2 }

lcsMVRStatisticsClear OBJECT-TYPE
   SYNTAX      Integer32
   MAX-ACCESS  read-write
   STATUS      current
   DESCRIPTION
       "Statistics Clear.
       1:Clear"
   ::= { lcsStatistics 2 } 

lcsMVRStatisticsTable OBJECT-TYPE
   SYNTAX      SEQUENCE OF LCSMVRStatisticsEntry
   MAX-ACCESS  not-accessible
   STATUS      current
   DESCRIPTION
       " "
   ::= { lcsStatistics 3 }

lcsMVRStatisticsEntry OBJECT-TYPE
   SYNTAX      LCSMVRStatisticsEntry
   MAX-ACCESS  not-accessible
   STATUS      current
   DESCRIPTION
       " "
   INDEX    { lcsMVRStatisticsIndex  }
   ::= { lcsMVRStatisticsTable 1 }

LCSMVRStatisticsEntry ::= SEQUENCE {
   lcsMVRStatisticsIndex                       Integer32,
   lcsMVRStatisticsVLANID                      Integer32,
   lcsMVRStatisticsIGMPMLDQueriesReceived      DisplayString,
   lcsMVRStatisticsIGMPMLDQueriesTransmitted   DisplayString,
   lcsMVRStatisticsIGMPv1JoinsReceived         DisplayString,
   lcsMVRStatisticsIGMPv2MLDv1ReportsReceived  DisplayString,
   lcsMVRStatisticsIGMPv3MLDv2ReportsReceived  DisplayString,
   lcsMVRStatisticsIGMPv2MLDv1LeavesReceived   DisplayString
}

lcsMVRStatisticsIndex OBJECT-TYPE
   SYNTAX      Integer32 (1..65535)
   MAX-ACCESS  not-accessible
   STATUS      current
   DESCRIPTION
       "Index"
   ::= {     lcsMVRStatisticsEntry 1 }

lcsMVRStatisticsVLANID OBJECT-TYPE
   SYNTAX      Integer32
   MAX-ACCESS  read-only
   STATUS      current
   DESCRIPTION
       "VLAN ID"
   ::= {     lcsMVRStatisticsEntry 2 }   
   
lcsMVRStatisticsIGMPMLDQueriesReceived OBJECT-TYPE
   SYNTAX      DisplayString
   MAX-ACCESS  read-only
   STATUS      current
   DESCRIPTION
       "IGMP/MLD Queries Received"
   ::= {     lcsMVRStatisticsEntry 3 }

lcsMVRStatisticsIGMPMLDQueriesTransmitted OBJECT-TYPE
   SYNTAX      DisplayString
   MAX-ACCESS  read-only
   STATUS      current
   DESCRIPTION
       "IGMP/MLD Queries Transmitted"
   ::= {     lcsMVRStatisticsEntry 4 }  
   
lcsMVRStatisticsIGMPv1JoinsReceived OBJECT-TYPE
   SYNTAX      DisplayString
   MAX-ACCESS  read-only
   STATUS      current
   DESCRIPTION
       "IGMPv1 Joins Received"
   ::= {     lcsMVRStatisticsEntry 5 }  
   
lcsMVRStatisticsIGMPv2MLDv1ReportsReceived OBJECT-TYPE
   SYNTAX      DisplayString
   MAX-ACCESS  read-only
   STATUS      current
   DESCRIPTION
       "IGMPv2/MLDv1 Reports Received"
   ::= {     lcsMVRStatisticsEntry 6 }  
   
lcsMVRStatisticsIGMPv3MLDv2ReportsReceived OBJECT-TYPE
   SYNTAX      DisplayString
   MAX-ACCESS  read-only
   STATUS      current
   DESCRIPTION
       "IGMPv3/MLDv2 Reports Received"
   ::= {     lcsMVRStatisticsEntry 7 }  
   
lcsMVRStatisticsIGMPv2MLDv1LeavesReceived OBJECT-TYPE
   SYNTAX      DisplayString
   MAX-ACCESS  read-only
   STATUS      current
   DESCRIPTION
       "IGMPv2/MLDv1 Leaves Received"
   ::= {     lcsMVRStatisticsEntry 8 }  


lcsGroupInformation  OBJECT IDENTIFIER ::= { lcsMVR 3 }

lcsMVRGroupInfoTable OBJECT-TYPE
   SYNTAX      SEQUENCE OF LCSMVRGroupInfoEntry
   MAX-ACCESS  not-accessible
   STATUS      current
   DESCRIPTION
       " "
   ::= { lcsGroupInformation 1 }

lcsMVRGroupInfoEntry OBJECT-TYPE
   SYNTAX      LCSMVRGroupInfoEntry
   MAX-ACCESS  not-accessible
   STATUS      current
   DESCRIPTION
       " "
   INDEX    { lcsMVRGroupInfoIndex  }
   ::= { lcsMVRGroupInfoTable 1 }

LCSMVRGroupInfoEntry ::= SEQUENCE {
   lcsMVRGroupInfoIndex       Integer32,
   lcsMVRGroupInfoVLANID      Integer32,
   lcsMVRGroupInfoGroups      DisplayString,
   lcsMVRGroupInfoPortMembers DisplayString
}

lcsMVRGroupInfoIndex OBJECT-TYPE
   SYNTAX      Integer32 (1..65535)
   MAX-ACCESS  not-accessible
   STATUS      current
   DESCRIPTION
       "Index"
   ::= {     lcsMVRGroupInfoEntry 1 }

lcsMVRGroupInfoVLANID OBJECT-TYPE
   SYNTAX      Integer32
   MAX-ACCESS  read-only
   STATUS      current
   DESCRIPTION
       "VLAN ID"
   ::= {     lcsMVRGroupInfoEntry 2 }   

lcsMVRGroupInfoGroups OBJECT-TYPE
   SYNTAX      DisplayString
   MAX-ACCESS  read-only
   STATUS      current
   DESCRIPTION
       "Groups"
   ::= {     lcsMVRGroupInfoEntry 3 } 
   
lcsMVRGroupInfoPortMembers OBJECT-TYPE
   SYNTAX      DisplayString
   MAX-ACCESS  read-only
   STATUS      current
   DESCRIPTION
       "Port Members"
   ::= {     lcsMVRGroupInfoEntry 4 }    
   
lcsMVRSFMInformation  OBJECT IDENTIFIER ::= { lcsMVR 4 }   

lcsMVRSFMInfoTable OBJECT-TYPE
   SYNTAX      SEQUENCE OF LCSMVRSFMInfoEntry
   MAX-ACCESS  not-accessible
   STATUS      current
   DESCRIPTION
       " "
   ::= { lcsMVRSFMInformation 2 }

lcsMVRSFMInfoEntry OBJECT-TYPE
   SYNTAX      LCSMVRSFMInfoEntry
   MAX-ACCESS  not-accessible
   STATUS      current
   DESCRIPTION
       " "
   INDEX    { lcsMVRSFMInfoIndex  }
   ::= { lcsMVRSFMInfoTable 1 }

LCSMVRSFMInfoEntry ::= SEQUENCE {
   lcsMVRSFMInfoIndex                Integer32,
   lcsMVRSFMInfoVLANID               Integer32,
   lcsMVRSFMInfoGroup                DisplayString,
   lcsMVRSFMInfoPort                 Integer32,
   lcsMVRSFMInfoMode                 Integer32,
   lcsMVRSFMInfoSourceAddress        DisplayString,
   lcsMVRSFMInfoType                 Integer32,
   lcsMVRSFMInfoHardwareFilterSwitch Integer32
   
}

lcsMVRSFMInfoIndex OBJECT-TYPE
   SYNTAX      Integer32 (1..65535)
   MAX-ACCESS  not-accessible
   STATUS      current
   DESCRIPTION
       "Index"
   ::= {     lcsMVRSFMInfoEntry 1 }

lcsMVRSFMInfoVLANID OBJECT-TYPE
   SYNTAX      Integer32
   MAX-ACCESS  read-only
   STATUS      current
   DESCRIPTION
       "VLAN ID"
   ::= {     lcsMVRSFMInfoEntry 2 }   

lcsMVRSFMInfoGroup OBJECT-TYPE
   SYNTAX      DisplayString
   MAX-ACCESS  read-only
   STATUS      current
   DESCRIPTION
       "Group"
   ::= {     lcsMVRSFMInfoEntry 3 } 
   
lcsMVRSFMInfoPort OBJECT-TYPE
   SYNTAX      Integer32
   MAX-ACCESS  read-only
   STATUS      current
   DESCRIPTION
       "Port"
   ::= {     lcsMVRSFMInfoEntry 4 }  
   
lcsMVRSFMInfoMode OBJECT-TYPE
   SYNTAX      Integer32
   MAX-ACCESS  read-only
   STATUS      current
   DESCRIPTION
       "Mode
       0:Exclude.
       1:Include"
   ::= {     lcsMVRSFMInfoEntry 5 }  

lcsMVRSFMInfoSourceAddress OBJECT-TYPE
   SYNTAX      DisplayString
   MAX-ACCESS  read-only
   STATUS      current
   DESCRIPTION
       "Source Address"
   ::= {     lcsMVRSFMInfoEntry 6 } 
   
lcsMVRSFMInfoType OBJECT-TYPE
   SYNTAX      Integer32
   MAX-ACCESS  read-only
   STATUS      current
   DESCRIPTION
       "Type
       0:Deny
       1:Allow"
   ::= {     lcsMVRSFMInfoEntry 7 }  
   
lcsMVRSFMInfoHardwareFilterSwitch OBJECT-TYPE
   SYNTAX      Integer32
   MAX-ACCESS  read-only
   STATUS      current
   DESCRIPTION
       "Hardware Filter\Switch
       0:No
       1:Yes"
   ::= {     lcsMVRSFMInfoEntry 8 }     


lcsIPMCLIB    OBJECT IDENTIFIER ::= { lcsConfiguration 34 }

lcsMulticastFilteringProfileMode OBJECT-TYPE
   SYNTAX      Integer32
   MAX-ACCESS  read-write
   STATUS      current
   DESCRIPTION
       "Multicast Filtering Profile Mode.
       0:Disable
       1:Enable"
   ::= {     lcsIPMCLIB 1 } 
   

lcsMulticastFilteringProfileSettingTable  OBJECT-TYPE
   SYNTAX      SEQUENCE OF LCSMulticastFilteringProfileSettingEntry
   MAX-ACCESS  not-accessible
   STATUS      current
   DESCRIPTION
       "Multicast Filtering Profile Setting table"
 ::= { lcsIPMCLIB 2 }

lcsMulticastFilteringProfileSettingEntry OBJECT-TYPE
    SYNTAX        LCSMulticastFilteringProfileSettingEntry
    MAX-ACCESS    not-accessible
    STATUS        current
    DESCRIPTION
        "Multicast Filtering Profile Setting table."
    INDEX        { lcsMulticastFilteringProfileSettingIndex }
    ::= { lcsMulticastFilteringProfileSettingTable 1 }

LCSMulticastFilteringProfileSettingEntry ::=
    SEQUENCE {
        lcsMulticastFilteringProfileSettingIndex               Integer32,
        lcsMulticastFilteringProfileSettingProfileName         DisplayString,
        lcsMulticastFilteringProfileSettingProfileDescription  DisplayString,
        lcsMulticastFilteringProfileSettingRowStatus           RowStatus
    }
    
lcsMulticastFilteringProfileSettingIndex OBJECT-TYPE
   SYNTAX      Integer32 (1..65535)
   MAX-ACCESS  not-accessible
   STATUS      current
   DESCRIPTION
       "Multicast Filtering Profile Setting index."
   ::= {lcsMulticastFilteringProfileSettingEntry 1 }    
    

lcsMulticastFilteringProfileSettingProfileName OBJECT-TYPE
   SYNTAX      DisplayString
   MAX-ACCESS  read-create
   STATUS      current
   DESCRIPTION
       "Profile Name. Length:1-16"
   ::= {lcsMulticastFilteringProfileSettingEntry 2 } 
   
lcsMulticastFilteringProfileSettingProfileDescription OBJECT-TYPE
   SYNTAX      DisplayString
   MAX-ACCESS  read-create
   STATUS      current
   DESCRIPTION
       "Profile Description. Length:0-64"
   ::= {lcsMulticastFilteringProfileSettingEntry 3 }    

lcsMulticastFilteringProfileSettingRowStatus OBJECT-TYPE
   SYNTAX      RowStatus
   MAX-ACCESS  read-create
   STATUS      current
   DESCRIPTION
       "Row Status."
   ::= {lcsMulticastFilteringProfileSettingEntry 4 }    
               
               
               
lcsMulticastFilteringProfileRuleSettingsProfileNameIndex OBJECT-TYPE
   SYNTAX      DisplayString
   MAX-ACCESS  read-write
   STATUS      current
   DESCRIPTION
       "Set this Profile Name value before use MulticastFilteringProfileRuleSettingsTable table"
   ::= {     lcsIPMCLIB 3 } 
               
               
               
lcsMulticastFilteringProfileRuleSettingsTable  OBJECT-TYPE
   SYNTAX      SEQUENCE OF LCSMulticastFilteringProfileRuleSettingsEntry
   MAX-ACCESS  not-accessible
   STATUS      current
   DESCRIPTION
       "Multicast Filtering Profile Rule Setting table"
 ::= { lcsIPMCLIB 4 }

lcsMulticastFilteringProfileRuleSettingsEntry OBJECT-TYPE
    SYNTAX        LCSMulticastFilteringProfileRuleSettingsEntry
    MAX-ACCESS    not-accessible
    STATUS        current
    DESCRIPTION
        "Multicast Filtering Profile Rule Setting table."
    INDEX        { lcsMulticastFilteringProfileRuleSettingsIndex }
    ::= { lcsMulticastFilteringProfileRuleSettingsTable 1 }

LCSMulticastFilteringProfileRuleSettingsEntry ::=
    SEQUENCE {
        lcsMulticastFilteringProfileRuleSettingsTableIndex          Integer32,
        lcsMulticastFilteringProfileRuleSettingsProfileName         DisplayString,
        lcsMulticastFilteringProfileRuleSettingsIndex               Integer32,
        lcsMulticastFilteringProfileRuleSettingsEntryName           DisplayString,  
        lcsMulticastFilteringProfileRuleSettingsAddressRange        DisplayString,
        lcsMulticastFilteringProfileRuleSettingsAction              Integer32,
        lcsMulticastFilteringProfileRuleSettingsLog                 Integer32,
        lcsMulticastFilteringProfileRuleSettingsRowStatus           RowStatus
    }
    
lcsMulticastFilteringProfileRuleSettingsTableIndex OBJECT-TYPE
   SYNTAX      Integer32
   MAX-ACCESS  not-accessible
   STATUS      current
   DESCRIPTION
       "Multicast Filtering Profile Rule Setting index."
   ::= {lcsMulticastFilteringProfileRuleSettingsEntry 1 }    
    

lcsMulticastFilteringProfileRuleSettingsProfileName OBJECT-TYPE
   SYNTAX      DisplayString
   MAX-ACCESS  read-only
   STATUS      current
   DESCRIPTION
       "Profile Name"
   ::= {lcsMulticastFilteringProfileRuleSettingsEntry 2 } 
   
lcsMulticastFilteringProfileRuleSettingsIndex OBJECT-TYPE
   SYNTAX      Integer32 (1..65535)
   MAX-ACCESS  read-only
   STATUS      current
   DESCRIPTION
       "Index"
   ::= {lcsMulticastFilteringProfileRuleSettingsEntry 3 } 
   
lcsMulticastFilteringProfileRuleSettingsEntryName OBJECT-TYPE
   SYNTAX      DisplayString
   MAX-ACCESS  read-create
   STATUS      current
   DESCRIPTION
       "Entry Name, Length: 1-16"
   ::= {lcsMulticastFilteringProfileRuleSettingsEntry 4 } 
   
lcsMulticastFilteringProfileRuleSettingsAddressRange OBJECT-TYPE
   SYNTAX      DisplayString
   MAX-ACCESS  read-only
   STATUS      current
   DESCRIPTION
       "Address Range"
   ::= {lcsMulticastFilteringProfileRuleSettingsEntry 5 } 
   
   
lcsMulticastFilteringProfileRuleSettingsAction OBJECT-TYPE
   SYNTAX      Integer32
   MAX-ACCESS  read-create
   STATUS      current
   DESCRIPTION
       "0:Deny
        1:Permit"
   ::= {lcsMulticastFilteringProfileRuleSettingsEntry 6 } 

lcsMulticastFilteringProfileRuleSettingsLog OBJECT-TYPE
   SYNTAX      Integer32
   MAX-ACCESS  read-create
   STATUS      current
   DESCRIPTION
       "0:Disable
        1:Enable"
   ::= {lcsMulticastFilteringProfileRuleSettingsEntry 7 } 


lcsMulticastFilteringProfileRuleSettingsRowStatus OBJECT-TYPE
   SYNTAX      RowStatus
   MAX-ACCESS  read-create
   STATUS      current
   DESCRIPTION
       "Row Status."
   ::= {lcsMulticastFilteringProfileRuleSettingsEntry 8 }    


lcsMulticastFilteringProfileAddressConfigTable  OBJECT-TYPE
   SYNTAX      SEQUENCE OF LCSMulticastFilteringProfileAddressConfigEntry
   MAX-ACCESS  not-accessible
   STATUS      current
   DESCRIPTION
       "Multicast Filtering Profile Address Config table"
 ::= { lcsIPMCLIB 5 }

lcsMulticastFilteringProfileAddressConfigEntry OBJECT-TYPE
    SYNTAX        LCSMulticastFilteringProfileAddressConfigEntry
    MAX-ACCESS    not-accessible
    STATUS        current
    DESCRIPTION
        "Multicast Filtering Profile Address Config table."
    INDEX        { lcsMulticastFilteringProfileAddressConfigTableIndex }
    ::= { lcsMulticastFilteringProfileAddressConfigTable 1 }

LCSMulticastFilteringProfileAddressConfigEntry ::=
    SEQUENCE {
        lcsMulticastFilteringProfileAddressConfigTableIndex     Integer32,
        lcsMulticastFilteringProfileAddressConfigEntryName      DisplayString,
        lcsMulticastFilteringProfileAddressConfigStartAddress   DisplayString,  
        lcsMulticastFilteringProfileAddressConfigEndAddress     DisplayString,
        lcsMulticastFilteringProfileAddressConfigRowStatus      RowStatus
    }
    
lcsMulticastFilteringProfileAddressConfigTableIndex OBJECT-TYPE
   SYNTAX      Integer32 (1..65535)
   MAX-ACCESS  not-accessible
   STATUS      current
   DESCRIPTION
       "Multicast Filtering Profile Address Config index."
   ::= {lcsMulticastFilteringProfileAddressConfigEntry 1 }    
    

lcsMulticastFilteringProfileAddressConfigEntryName OBJECT-TYPE
   SYNTAX      DisplayString
   MAX-ACCESS  read-create
   STATUS      current
   DESCRIPTION
       "Entry Name, Length: 1-16"
   ::= {lcsMulticastFilteringProfileAddressConfigEntry 2 } 
   
lcsMulticastFilteringProfileAddressConfigStartAddress OBJECT-TYPE
   SYNTAX      DisplayString
   MAX-ACCESS  read-create
   STATUS      current
   DESCRIPTION
       "IPv4/IPv6 Multicast Group Address"
   ::= {lcsMulticastFilteringProfileAddressConfigEntry 3 } 
   
lcsMulticastFilteringProfileAddressConfigEndAddress OBJECT-TYPE
   SYNTAX      DisplayString
   MAX-ACCESS  read-create
   STATUS      current
   DESCRIPTION
       "IPv4/IPv6 Multicast Group Address"
   ::= {lcsMulticastFilteringProfileAddressConfigEntry 4 } 

lcsMulticastFilteringProfileAddressConfigRowStatus OBJECT-TYPE
   SYNTAX      RowStatus
   MAX-ACCESS  read-create
   STATUS      current
   DESCRIPTION
       "Row Status."
   ::= {lcsMulticastFilteringProfileAddressConfigEntry 5 }    

lcsEEE    OBJECT IDENTIFIER ::= { lcsConfiguration 35 }

lcsPortPowerSavings   OBJECT IDENTIFIER ::= { lcsEEE 1 }

lcsEnergyEfficientEthernetConfigTable OBJECT-TYPE
   SYNTAX      SEQUENCE OF LCSEnergyEfficientEthernetConfigEntry
   MAX-ACCESS  not-accessible
   STATUS      current
   DESCRIPTION
       " "
   ::= { lcsPortPowerSavings 2 }

lcsEnergyEfficientEthernetConfigEntry OBJECT-TYPE
   SYNTAX      LCSEnergyEfficientEthernetConfigEntry
   MAX-ACCESS  not-accessible
   STATUS      current
   DESCRIPTION
       " "
   INDEX    { lcsEnergyEfficientEthernetConfigPort  }
   ::= { lcsEnergyEfficientEthernetConfigTable 1 }

LCSEnergyEfficientEthernetConfigEntry ::= SEQUENCE {
   lcsEnergyEfficientEthernetConfigPort           Integer32,
   lcsEnergyEfficientEthernetConfigPortConfig     Integer32
}

lcsEnergyEfficientEthernetConfigPort OBJECT-TYPE
   SYNTAX      Integer32 (1..4094)
   MAX-ACCESS  not-accessible
   STATUS      current
   DESCRIPTION
       "Index"
   ::= { lcsEnergyEfficientEthernetConfigEntry 1 }

lcsEnergyEfficientEthernetConfigPortConfig OBJECT-TYPE
   SYNTAX      Integer32
   MAX-ACCESS  read-write
   STATUS      current
   DESCRIPTION
       "Controls whether EEE is enabled for this port. 
       0:Disable
       1:Enable"
   ::= { lcsEnergyEfficientEthernetConfigEntry 2 }

-- =======================================================================================================================

lcsAggregation    OBJECT IDENTIFIER ::= { lcsConfiguration 36 } 
    
lcsAggregationStatic    OBJECT IDENTIFIER ::= { lcsAggregation 1 } 

lcsAggrSourceMACAddress   OBJECT-TYPE
               SYNTAX      Integer32 (0|1)
               MAX-ACCESS  read-write
               STATUS      current
               DESCRIPTION
                   "Source MAC Address"
               ::= { lcsAggregationStatic 2 }

lcsAggrDestinationMACAddress   OBJECT-TYPE
               SYNTAX      Integer32 (0|1)
               MAX-ACCESS  read-write
               STATUS      current
               DESCRIPTION
                   "Destination MAC Address"
               ::= { lcsAggregationStatic 3 }
               
lcsAggrIPAddress   OBJECT-TYPE
               SYNTAX      Integer32 (0|1)
               MAX-ACCESS  read-write
               STATUS      current
               DESCRIPTION
                   "IP Address"
               ::= { lcsAggregationStatic 4 }

lcsAggrTCPUDPPortNumber   OBJECT-TYPE
               SYNTAX      Integer32 (0|1)
               MAX-ACCESS  read-write
               STATUS      current
               DESCRIPTION
                   "TCP/UDP Port Number"
               ::= { lcsAggregationStatic 5 }
               
               
lcsAggrGroupConfigTable OBJECT-TYPE
   SYNTAX      SEQUENCE OF LCSAggrGroupConfigEntry
   MAX-ACCESS  not-accessible
   STATUS      current
   DESCRIPTION
       " "
   ::= { lcsAggregationStatic 6 }

lcsAggrGroupConfigEntry OBJECT-TYPE
   SYNTAX      LCSAggrGroupConfigEntry
   MAX-ACCESS  not-accessible
   STATUS      current
   DESCRIPTION
       " "
   INDEX    { lcsAggrGroupConfigPort  }
   ::= { lcsAggrGroupConfigTable 1 }

LCSAggrGroupConfigEntry ::= SEQUENCE {
   lcsAggrGroupConfigPort                 Integer32,
   lcsAggrGroupConfigGroup                Integer32,
   lcsAggrGroupConfig                     Integer32
}

lcsAggrGroupConfigPort OBJECT-TYPE
   SYNTAX      Integer32 (1..4094)
   MAX-ACCESS  not-accessible
   STATUS      current
   DESCRIPTION
       "port index"
   ::= { lcsAggrGroupConfigEntry 1 }
      
lcsAggrGroupConfigGroup OBJECT-TYPE
   SYNTAX      Integer32
   MAX-ACCESS  not-accessible
   STATUS      current
   DESCRIPTION
       "group index"
   ::= { lcsAggrGroupConfigEntry 2 }   

lcsAggrGroupConfig OBJECT-TYPE
   SYNTAX      Integer32 (0|1)
   MAX-ACCESS  read-write
   STATUS      current
   DESCRIPTION
       "Aggregation Group Configuration"
   ::= { lcsAggrGroupConfigEntry 3 }
   
lcsLACPConfiguration    OBJECT IDENTIFIER ::= { lcsAggregation 2 } 

lcsLACPPortConfigTable OBJECT-TYPE
   SYNTAX      SEQUENCE OF LCSLACPPortConfigEntry
   MAX-ACCESS  not-accessible
   STATUS      current
   DESCRIPTION
       " "
   ::= { lcsLACPConfiguration 1 }

lcsLACPPortConfigEntry OBJECT-TYPE
   SYNTAX      LCSLACPPortConfigEntry
   MAX-ACCESS  not-accessible
   STATUS      current
   DESCRIPTION
       " "
   INDEX    { lcsLACPPortConfigPort  }
   ::= { lcsLACPPortConfigTable 1 }

LCSLACPPortConfigEntry ::= SEQUENCE {
   lcsLACPPortConfigPort                  Integer32,
   lcsLACPPortConfigEnabled               Integer32,
   lcsLACPPortConfigKey                   Integer32,
   lcsLACPPortConfigRole                  Integer32,
   lcsLACPPortConfigTimeout               Integer32,
   lcsLACPPortConfigPrio                  Integer32   
}

lcsLACPPortConfigPort OBJECT-TYPE
   SYNTAX      Integer32 (1..4094)
   MAX-ACCESS  not-accessible
   STATUS      current
   DESCRIPTION
       "port index"
   ::= { lcsLACPPortConfigEntry 1 }
      
lcsLACPPortConfigEnabled OBJECT-TYPE
   SYNTAX      Integer32 (0|1)
   MAX-ACCESS  read-write
   STATUS      current
   DESCRIPTION
       "Controls whether LACP is enabled on this switch port.
       0:Disable
       1:Enable"
   ::= { lcsLACPPortConfigEntry 2 }   

lcsLACPPortConfigKey OBJECT-TYPE
   SYNTAX      Integer32
   MAX-ACCESS  read-write
   STATUS      current
   DESCRIPTION
       "The Key value incurred by the port, range 1-Number of link aggregations."
   ::= { lcsLACPPortConfigEntry 3 }
   
lcsLACPPortConfigRole OBJECT-TYPE
   SYNTAX      Integer32 (0|1)
   MAX-ACCESS  read-write
   STATUS      current
   DESCRIPTION
       "The Role shows the LACP activity status.
       0:Passive
       1:Active"
   ::= { lcsLACPPortConfigEntry 4 }

lcsLACPPortConfigTimeout OBJECT-TYPE
   SYNTAX      Integer32 (0|1)
   MAX-ACCESS  read-write
   STATUS      current
   DESCRIPTION
       "The Timeout controls the period between BPDU transmissions.
       0:Slow
       1:Fast"
   ::= { lcsLACPPortConfigEntry 5 }

lcsLACPPortConfigPrio OBJECT-TYPE
   SYNTAX      Integer32 (1..65535)
   MAX-ACCESS  read-write
   STATUS      current
   DESCRIPTION
       "The Prio controls the priority of the port."
   ::= { lcsLACPPortConfigEntry 6 }


lcsLacpSystemStatus    OBJECT IDENTIFIER ::= { lcsAggregation 3 } 

lcsLacpSystemStatusTable OBJECT-TYPE
   SYNTAX      SEQUENCE OF LCSLacpSystemStatusEntry
   MAX-ACCESS  not-accessible
   STATUS      current
   DESCRIPTION
       " "
   ::= { lcsLacpSystemStatus 1 }

lcsLacpSystemStatusEntry OBJECT-TYPE
   SYNTAX      LCSLacpSystemStatusEntry
   MAX-ACCESS  not-accessible
   STATUS      current
   DESCRIPTION
       " "
   INDEX    { lcsLacpSystemStatusIndex  }
   ::= { lcsLacpSystemStatusTable 1 }

LCSLacpSystemStatusEntry ::= SEQUENCE {
   lcsLacpSystemStatusIndex              Integer32,
   lcsLacpSystemStatusAggrID             DisplayString,
   lcsLacpSystemStatusPartnerSystemID    DisplayString,
   lcsLacpSystemStatusPartnerKey         DisplayString,
   lcsLacpSystemStatusPartnerPrio        DisplayString,
   lcsLacpSystemStatusLastChanged        DisplayString,
   lcsLacpSystemStatusLocalPorts         DisplayString
}                                  

lcsLacpSystemStatusIndex OBJECT-TYPE
   SYNTAX      Integer32 (1..65536)
   MAX-ACCESS  not-accessible
   STATUS      current
   DESCRIPTION
       "index"
   ::= { lcsLacpSystemStatusEntry 1 }
      
lcsLacpSystemStatusAggrID OBJECT-TYPE
   SYNTAX      DisplayString
   MAX-ACCESS  read-only
   STATUS      current
   DESCRIPTION
       "The Aggregation ID associated with this aggregation instance."
   ::= { lcsLacpSystemStatusEntry 2 }   

lcsLacpSystemStatusPartnerSystemID OBJECT-TYPE
   SYNTAX      DisplayString
   MAX-ACCESS  read-only
   STATUS      current
   DESCRIPTION
       "The system ID (MAC address) of the aggregation partner."
   ::= { lcsLacpSystemStatusEntry 3 }
   
lcsLacpSystemStatusPartnerKey OBJECT-TYPE
   SYNTAX      DisplayString
   MAX-ACCESS  read-only
   STATUS      current
   DESCRIPTION
       "The Key that the partner has assigned to this aggregation ID."
   ::= { lcsLacpSystemStatusEntry 4 }

lcsLacpSystemStatusPartnerPrio OBJECT-TYPE
   SYNTAX      DisplayString
   MAX-ACCESS  read-only
   STATUS      current
   DESCRIPTION
       "The priority that the partner has assigned to this aggregation ID."
   ::= { lcsLacpSystemStatusEntry 5 }

lcsLacpSystemStatusLastChanged OBJECT-TYPE
   SYNTAX      DisplayString
   MAX-ACCESS  read-only
   STATUS      current
   DESCRIPTION
       "The time since this aggregation changed."
   ::= { lcsLacpSystemStatusEntry 6 }

lcsLacpSystemStatusLocalPorts OBJECT-TYPE
   SYNTAX      DisplayString
   MAX-ACCESS  read-only
   STATUS      current
   DESCRIPTION
       "Shows which ports are a part of this aggregation for this switch."
   ::= { lcsLacpSystemStatusEntry 7 }

lcsLACPInternalPortStatus    OBJECT IDENTIFIER ::= { lcsAggregation 4 } 

lcsLACPInternalPortStatusTable OBJECT-TYPE
   SYNTAX      SEQUENCE OF LCSLACPInternalPortStatusEntry
   MAX-ACCESS  not-accessible
   STATUS      current
   DESCRIPTION
       " "
   ::= { lcsLACPInternalPortStatus 1 }

lcsLACPInternalPortStatusEntry OBJECT-TYPE
   SYNTAX      LCSLACPInternalPortStatusEntry
   MAX-ACCESS  not-accessible
   STATUS      current
   DESCRIPTION
       " "
   INDEX    { lcsLACPInternalPortStatusIndex  }
   ::= { lcsLACPInternalPortStatusTable 1 }

LCSLACPInternalPortStatusEntry ::= SEQUENCE {
   lcsLACPInternalPortStatusIndex              Integer32,
   lcsLACPInternalPortStatusPort               DisplayString,
   lcsLACPInternalPortStatusState              DisplayString,
   lcsLACPInternalPortStatusKey                DisplayString,
   lcsLACPInternalPortStatusPriority           DisplayString,
   lcsLACPInternalPortStatusActivity           DisplayString,
   lcsLACPInternalPortStatusTimeout            DisplayString,
   lcsLACPInternalPortStatusAggregation        DisplayString,
   lcsLACPInternalPortStatusSynchronization    DisplayString,
   lcsLACPInternalPortStatusCollecting         DisplayString,
   lcsLACPInternalPortStatusDistributing       DisplayString,
   lcsLACPInternalPortStatusDefaulted          DisplayString,
   lcsLACPInternalPortStatusExpired            DisplayString   
}                                  

lcsLACPInternalPortStatusIndex OBJECT-TYPE
   SYNTAX      Integer32 (1..4094)
   MAX-ACCESS  not-accessible
   STATUS      current
   DESCRIPTION
       "index"
   ::= { lcsLACPInternalPortStatusEntry 1 }
      
lcsLACPInternalPortStatusPort OBJECT-TYPE
   SYNTAX      DisplayString
   MAX-ACCESS  read-only
   STATUS      current
   DESCRIPTION
       "The switch port number."
   ::= { lcsLACPInternalPortStatusEntry 2 }   

lcsLACPInternalPortStatusState OBJECT-TYPE
   SYNTAX      DisplayString
   MAX-ACCESS  read-only
   STATUS      current
   DESCRIPTION
       "The current port state:
        Down: The port is not active.
        Active: The port is in active state.
        Standby: The port is in standby state."
   ::= { lcsLACPInternalPortStatusEntry 3 }
   
lcsLACPInternalPortStatusKey OBJECT-TYPE
   SYNTAX      DisplayString
   MAX-ACCESS  read-only
   STATUS      current
   DESCRIPTION
       "The key assigned to this port. Only ports with the same key can aggregate together."
   ::= { lcsLACPInternalPortStatusEntry 4 }

lcsLACPInternalPortStatusPriority OBJECT-TYPE
   SYNTAX      DisplayString
   MAX-ACCESS  read-only
   STATUS      current
   DESCRIPTION
       "The priority assigned to this aggregation group."
   ::= { lcsLACPInternalPortStatusEntry 5 }

lcsLACPInternalPortStatusActivity OBJECT-TYPE
   SYNTAX      DisplayString
   MAX-ACCESS  read-only
   STATUS      current
   DESCRIPTION
       "The LACP mode of the group (Active or Passive)."
   ::= { lcsLACPInternalPortStatusEntry 6 }

lcsLACPInternalPortStatusTimeout OBJECT-TYPE
   SYNTAX      DisplayString
   MAX-ACCESS  read-only
   STATUS      current
   DESCRIPTION
       "The timeout mode configured for the port (Fast or Slow)."
   ::= { lcsLACPInternalPortStatusEntry 7 }

lcsLACPInternalPortStatusAggregation OBJECT-TYPE
   SYNTAX      DisplayString
   MAX-ACCESS  read-only
   STATUS      current
   DESCRIPTION
       "Show whether the system considers this link to be aggregateable. i.e., a potential candidate for aggregation."
   ::= { lcsLACPInternalPortStatusEntry 8 }
   
lcsLACPInternalPortStatusSynchronization OBJECT-TYPE
   SYNTAX      DisplayString
   MAX-ACCESS  read-only
   STATUS      current
   DESCRIPTION
       "Show whether the system considers this link to be IN_SYNC."
   ::= { lcsLACPInternalPortStatusEntry 9 }

lcsLACPInternalPortStatusCollecting OBJECT-TYPE
   SYNTAX      DisplayString
   MAX-ACCESS  read-only
   STATUS      current
   DESCRIPTION
       "Show if collection of incoming frames on this link is enabled."
   ::= { lcsLACPInternalPortStatusEntry 10 }

lcsLACPInternalPortStatusDistributing OBJECT-TYPE
   SYNTAX      DisplayString
   MAX-ACCESS  read-only
   STATUS      current
   DESCRIPTION
       "Show if distribution of outgoing frames on this link is enabled."
   ::= { lcsLACPInternalPortStatusEntry 11 }

lcsLACPInternalPortStatusDefaulted OBJECT-TYPE
   SYNTAX      DisplayString
   MAX-ACCESS  read-only
   STATUS      current
   DESCRIPTION
       "Show if the Actor's Receive machine is using Defaulted operational Partner information."
   ::= { lcsLACPInternalPortStatusEntry 12 }

lcsLACPInternalPortStatusExpired OBJECT-TYPE
   SYNTAX      DisplayString
   MAX-ACCESS  read-only
   STATUS      current
   DESCRIPTION
       "Show if that the Actor's Receive machine is in the EXPIRED state."
   ::= { lcsLACPInternalPortStatusEntry 13 }


lcsLACPNeighborPortStatus    OBJECT IDENTIFIER ::= { lcsAggregation 5 } 

lcsLACPNeighborPortStatusTable OBJECT-TYPE
   SYNTAX      SEQUENCE OF LCSLACPNeighborPortStatusEntry
   MAX-ACCESS  not-accessible
   STATUS      current
   DESCRIPTION
       " "
   ::= { lcsLACPNeighborPortStatus 1 }

lcsLACPNeighborPortStatusEntry OBJECT-TYPE
   SYNTAX      LCSLACPNeighborPortStatusEntry
   MAX-ACCESS  not-accessible
   STATUS      current
   DESCRIPTION
       " "
   INDEX    { lcsLACPNeighborPortStatusIndex  }
   ::= { lcsLACPNeighborPortStatusTable 1 }

LCSLACPNeighborPortStatusEntry ::= SEQUENCE {
   lcsLACPNeighborPortStatusIndex              Integer32,
   lcsLACPNeighborPortStatusPort               DisplayString,
   lcsLACPNeighborPortStatusState              DisplayString,
   lcsLACPNeighborPortStatusAggrID             DisplayString,   
   lcsLACPNeighborPortStatusPartnerKey         DisplayString,
   lcsLACPNeighborPortStatusPartnerPort        DisplayString,   
   lcsLACPNeighborPortStatusPartnerPortPrio    DisplayString,
   lcsLACPNeighborPortStatusActivity           DisplayString,
   lcsLACPNeighborPortStatusTimeout            DisplayString,
   lcsLACPNeighborPortStatusAggregation        DisplayString,
   lcsLACPNeighborPortStatusSynchronization    DisplayString,
   lcsLACPNeighborPortStatusCollecting         DisplayString,
   lcsLACPNeighborPortStatusDistributing       DisplayString,
   lcsLACPNeighborPortStatusDefaulted          DisplayString,
   lcsLACPNeighborPortStatusExpired            DisplayString   
}                                  

lcsLACPNeighborPortStatusIndex OBJECT-TYPE
   SYNTAX      Integer32 (1..4094)
   MAX-ACCESS  not-accessible
   STATUS      current
   DESCRIPTION
       "index"
   ::= { lcsLACPNeighborPortStatusEntry 1 }
      
lcsLACPNeighborPortStatusPort OBJECT-TYPE
   SYNTAX      DisplayString
   MAX-ACCESS  read-only
   STATUS      current
   DESCRIPTION
       "The switch port number."
   ::= { lcsLACPNeighborPortStatusEntry 2 }   

lcsLACPNeighborPortStatusState OBJECT-TYPE
   SYNTAX      DisplayString
   MAX-ACCESS  read-only
   STATUS      current
   DESCRIPTION
       "The current port state:
        Down: The port is not active.
        Active: The port is in active state.
        Standby: The port is in standby state."
   ::= { lcsLACPNeighborPortStatusEntry 3 }
   
lcsLACPNeighborPortStatusAggrID OBJECT-TYPE
   SYNTAX      DisplayString
   MAX-ACCESS  read-only
   STATUS      current
   DESCRIPTION
       "The aggregation group ID which the port is assigned to."
   ::= { lcsLACPNeighborPortStatusEntry 4 }

lcsLACPNeighborPortStatusPartnerKey OBJECT-TYPE
   SYNTAX      DisplayString
   MAX-ACCESS  read-only
   STATUS      current
   DESCRIPTION
       "The key assigned to this port by the partner."
   ::= { lcsLACPNeighborPortStatusEntry 5 }

lcsLACPNeighborPortStatusPartnerPort OBJECT-TYPE
   SYNTAX      DisplayString
   MAX-ACCESS  read-only
   STATUS      current
   DESCRIPTION
       "The partner port number associated with this link."
   ::= { lcsLACPNeighborPortStatusEntry 6 }

lcsLACPNeighborPortStatusPartnerPortPrio OBJECT-TYPE
   SYNTAX      DisplayString
   MAX-ACCESS  read-only
   STATUS      current
   DESCRIPTION
       "The priority assigned to this partner port ."
   ::= { lcsLACPNeighborPortStatusEntry 7 }

lcsLACPNeighborPortStatusActivity OBJECT-TYPE
   SYNTAX      DisplayString
   MAX-ACCESS  read-only
   STATUS      current
   DESCRIPTION
       "The LACP mode of the group (Active or Passive)."
   ::= { lcsLACPNeighborPortStatusEntry 8 }
   
lcsLACPNeighborPortStatusTimeout OBJECT-TYPE
   SYNTAX      DisplayString
   MAX-ACCESS  read-only
   STATUS      current
   DESCRIPTION
       "The timeout mode configured for the partner port (Fast or Slow)."
   ::= { lcsLACPNeighborPortStatusEntry 9 }

lcsLACPNeighborPortStatusAggregation OBJECT-TYPE
   SYNTAX      DisplayString
   MAX-ACCESS  read-only
   STATUS      current
   DESCRIPTION
       "Show whether the partner considers this link to be aggregateable."
   ::= { lcsLACPNeighborPortStatusEntry 10 }

lcsLACPNeighborPortStatusSynchronization OBJECT-TYPE
   SYNTAX      DisplayString
   MAX-ACCESS  read-only
   STATUS      current
   DESCRIPTION
       "Show whether the partner considers this link to be IN_SYNC"
   ::= { lcsLACPNeighborPortStatusEntry 11 }

lcsLACPNeighborPortStatusCollecting OBJECT-TYPE
   SYNTAX      DisplayString
   MAX-ACCESS  read-only
   STATUS      current
   DESCRIPTION
       "Show if collection of incoming frames on this link is enabled."
   ::= { lcsLACPNeighborPortStatusEntry 12 }

lcsLACPNeighborPortStatusDistributing OBJECT-TYPE
   SYNTAX      DisplayString
   MAX-ACCESS  read-only
   STATUS      current
   DESCRIPTION
       "Show if distribution of outgoing frames on this link is enabled."
   ::= { lcsLACPNeighborPortStatusEntry 13 }

lcsLACPNeighborPortStatusDefaulted OBJECT-TYPE
   SYNTAX      DisplayString
   MAX-ACCESS  read-only
   STATUS      current
   DESCRIPTION
       "Show if the partners Receive machine is using Defaulted operational Partner information."
   ::= { lcsLACPNeighborPortStatusEntry 14 }
   
lcsLACPNeighborPortStatusExpired OBJECT-TYPE
   SYNTAX      DisplayString
   MAX-ACCESS  read-only
   STATUS      current
   DESCRIPTION
       "Show if that the partners Receive machine is in the EXPIRED state."
   ::= { lcsLACPNeighborPortStatusEntry 15 }   


lcsLACPStatus    OBJECT IDENTIFIER ::= { lcsAggregation 6 } 

lcsLACPStatusTable OBJECT-TYPE
   SYNTAX      SEQUENCE OF LCSLACPStatusEntry
   MAX-ACCESS  not-accessible
   STATUS      current
   DESCRIPTION
       " "
   ::= { lcsLACPStatus 1 }

lcsLACPStatusEntry OBJECT-TYPE
   SYNTAX      LCSLACPStatusEntry
   MAX-ACCESS  not-accessible
   STATUS      current
   DESCRIPTION
       " "
   INDEX    { lcsLACPStatusPort  }
   ::= { lcsLACPStatusTable 1 }

LCSLACPStatusEntry ::= SEQUENCE {
   lcsLACPStatusPort               Integer32,
   lcsLACPStatusLACP               DisplayString,
   lcsLACPStatusKey                DisplayString,
   lcsLACPStatusAggrID             DisplayString,   
   lcsLACPStatusPartnerSystemID    DisplayString,
   lcsLACPStatusPartnerPort        DisplayString,   
   lcsLACPStatusPartnerPrio        DisplayString
}                                  

lcsLACPStatusPort OBJECT-TYPE
   SYNTAX      Integer32 (1..4094)
   MAX-ACCESS  not-accessible
   STATUS      current
   DESCRIPTION
       "index"
   ::= { lcsLACPStatusEntry 1 }
      
lcsLACPStatusLACP OBJECT-TYPE
   SYNTAX      DisplayString
   MAX-ACCESS  read-only
   STATUS      current
   DESCRIPTION
       "Yes: means that LACP is enabled and the port link is up. 
       No: means that LACP is not enabled or that the port link is down. 
       Backup: means that the port could not join the aggregation group but will join if other port leaves. Meanwhile it's LACP status is disabled."
   ::= { lcsLACPStatusEntry 2 }   

lcsLACPStatusKey OBJECT-TYPE
   SYNTAX      DisplayString
   MAX-ACCESS  read-only
   STATUS      current
   DESCRIPTION
       "The key assigned to this port. Only ports with the same key can aggregate together."
   ::= { lcsLACPStatusEntry 3 }
   
lcsLACPStatusAggrID OBJECT-TYPE
   SYNTAX      DisplayString
   MAX-ACCESS  read-only
   STATUS      current
   DESCRIPTION
       "The Aggregation ID assigned to this aggregation group."
   ::= { lcsLACPStatusEntry 4 }

lcsLACPStatusPartnerSystemID OBJECT-TYPE
   SYNTAX      DisplayString
   MAX-ACCESS  read-only
   STATUS      current
   DESCRIPTION
       "The partner's System ID (MAC address)."
   ::= { lcsLACPStatusEntry 5 }

lcsLACPStatusPartnerPort OBJECT-TYPE
   SYNTAX      DisplayString
   MAX-ACCESS  read-only
   STATUS      current
   DESCRIPTION
       "The partner's port number connected to this port."
   ::= { lcsLACPStatusEntry 6 }

lcsLACPStatusPartnerPrio OBJECT-TYPE
   SYNTAX      DisplayString
   MAX-ACCESS  read-only
   STATUS      current
   DESCRIPTION
       "The partner's port priority."
   ::= { lcsLACPStatusEntry 7 }

-- =======================================================================================================================
lcsLMC                                                   OBJECT IDENTIFIER ::= { lcsConfiguration 1500 } 

lcsLMCOperating OBJECT-TYPE
   SYNTAX      Integer32
   MAX-ACCESS  read-write
   STATUS      current
   DESCRIPTION
       "LMC Operating Switch 
       0:Disable
       1:Enable
       2:Try"
   ::= { lcsLMC 1 }

lcsLMCConfigViaDHCP OBJECT-TYPE
   SYNTAX      Integer32
   MAX-ACCESS  read-write
   STATUS      current
   DESCRIPTION
       "Enables LMC configuration via DHCP option 43
       0:Disable
       1:Enable"
   ::= { lcsLMC 2 }

lcsLMCDomain OBJECT-TYPE
   SYNTAX      DisplayString
   MAX-ACCESS  read-write
   STATUS      current
   DESCRIPTION
       "LMC Domain for example cloud.lancom.de"
   ::= { lcsLMC 3 }

lcsLMCAutoRenew OBJECT-TYPE
   SYNTAX      Integer32
   MAX-ACCESS  read-write
   STATUS      current
   DESCRIPTION
      "Renew DHCP lease early when connection to LMC is not possible
       0:Disabled
       1:Enabled"
   ::= { lcsLMC 4 }

lcsLMCRolloutProjectID OBJECT-TYPE
   SYNTAX      DisplayString
   MAX-ACCESS  read-write
   STATUS      current
   DESCRIPTION
       "LMC Project rollout information string"
   ::= { lcsLMC 5 }

lcsLMCRolloutLocationID OBJECT-TYPE
   SYNTAX      DisplayString
   MAX-ACCESS  read-write
   STATUS      current
   DESCRIPTION
       "LMC Location rollout information string"
   ::= { lcsLMC 6 }

lcsLMCRolloutRole OBJECT-TYPE
   SYNTAX      DisplayString
   MAX-ACCESS  read-write
   STATUS      current
   DESCRIPTION
       "LMC Role rollout information string"
   ::= { lcsLMC 7 }


lcsLMCZeroTouchSupport OBJECT-TYPE
   SYNTAX      Integer32
   MAX-ACCESS  read-only
   STATUS      current
   DESCRIPTION
      "Support for Zero Touch
      0:No
       1:Yes"
   ::= { lcsLMC 50 }

lcsLMCPairingTokenPresent OBJECT-TYPE
   SYNTAX      Integer32
   MAX-ACCESS  read-only
   STATUS      current
   DESCRIPTION
      "Paring Token present
       0:No
       1:Yes"
   ::= { lcsLMC 51 }


lcsLMCManagementStatus OBJECT-TYPE
   SYNTAX      Integer32
   MAX-ACCESS  read-only
   STATUS      current
   DESCRIPTION
        "0:Unpaired
        1:Paired
        2:Disabled
        3:DisabledByWLC
        4:Operating
        5:HTTPProtocolError
        6:HTTPConnectionError
        7:DNSError
        8:MemoryError
        9:NotYet
       10:Redirect
       11:AuthenticationError
       12:Error
       13:CertificateStorageError
       14:PairedAndClaimed
       15:CertificateError
       16:DeactivatedNoActivationCode"
   ::= { lcsLMC 53 }

lcsLMCControlStatus OBJECT-TYPE
   SYNTAX      Integer32
   MAX-ACCESS  read-only
   STATUS      current
   DESCRIPTION
        "0:Unpaired
        1:Paired
        2:Disabled
        3:DisabledByWLC
        4:Operating
        5:HTTPProtocolError
        6:HTTPConnectionError
        7:DNSError
        8:MemoryError
        9:NotYet
       10:Redirect
       11:AuthenticationError
       12:Error
       13:CertificateStorageError
       14:PairedAndClaimed
       15:CertificateError
       16:DeactivatedNoActivationCode"

   ::= { lcsLMC 54 }

lcsLMCMonitoringStatus OBJECT-TYPE
   SYNTAX      Integer32
   MAX-ACCESS  read-only
   STATUS      current
   DESCRIPTION
        "0:Unpaired
        1:Paired
        2:Disabled
        3:DisabledByWLC
        4:Operating
        5:HTTPProtocolError
        6:HTTPConnectionError
        7:DNSError
        8:MemoryError
        9:NotYet
       10:Redirect
       11:AuthenticationError
       12:Error
       13:CertificateStorageError
       14:PairedAndClaimed
       15:CertificateError
       16:DeactivatedNoActivationCode"
   ::= { lcsLMC 55 }


lcsLMCConfigModified OBJECT-TYPE
   SYNTAX      Integer32
   MAX-ACCESS  read-only
   STATUS      current
   DESCRIPTION
       "Configuration modified by LMC
       0:No
       1:Yes"
   ::= { lcsLMC 57 }
   
lcsLMCDeviceID OBJECT-TYPE
   SYNTAX      DisplayString
   MAX-ACCESS  read-only
   STATUS      current
   DESCRIPTION
       "Device ID"
   ::= { lcsLMC 58 }
   
lcsLMCStatusRTT OBJECT-TYPE
   SYNTAX      Integer32
   MAX-ACCESS  read-only
   STATUS      current
   DESCRIPTION
       "Heartbeat round trip time"
   ::= { lcsLMC 100 }
   
   
--lcsLMCTransportStatusTable

    lcsLMCTransportStatusTable OBJECT-TYPE
               SYNTAX      SEQUENCE OF     LCSLMCTransportStatusTableEntry
               MAX-ACCESS  not-accessible
               STATUS      current
               DESCRIPTION
                   "Transport status"
               ::= {     lcsLMC 101 }

    lcsLMCTransportStatusTableEntry OBJECT-TYPE
               SYNTAX          LCSLMCTransportStatusTableEntry
               MAX-ACCESS  not-accessible
               STATUS      current
               DESCRIPTION
                       "Transport number"
               INDEX    {     lcsLMCTransportStatusTransportNumberIndex  }
               ::= {     lcsLMCTransportStatusTable 1 }

    LCSLMCTransportStatusTableEntry             ::= SEQUENCE {
                lcsLMCTransportStatusTransportNumberIndex  Integer32,
                lcsLMCTransportStatusServiceName           DisplayString,
                lcsLMCTransportStatusHttpRequests          Counter64,
                lcsLMCTransportStatusHttpRequestsErrors    Counter64,
                lcsLMCTransportStatusTXBytes               Counter64,
                lcsLMCTransportStatusRXBytes               Counter64
                }
   
       lcsLMCTransportStatusTransportNumberIndex OBJECT-TYPE
               SYNTAX      Integer32
               MAX-ACCESS  not-accessible
               STATUS      current
               DESCRIPTION
                   ""
               ::= {     lcsLMCTransportStatusTableEntry 1 }

       lcsLMCTransportStatusServiceName OBJECT-TYPE
               SYNTAX      DisplayString
               MAX-ACCESS  read-only
               STATUS      current
               DESCRIPTION
                   "Service name"
               ::= {     lcsLMCTransportStatusTableEntry 2 }
   
       lcsLMCTransportStatusHttpRequests OBJECT-TYPE
               SYNTAX      Counter64
               MAX-ACCESS  read-only
               STATUS      current
               DESCRIPTION
                   "Number of Http requests"
               ::= {     lcsLMCTransportStatusTableEntry 3 }
   
       lcsLMCTransportStatusHttpRequestsErrors OBJECT-TYPE
               SYNTAX      Counter64
               MAX-ACCESS  read-only
               STATUS      current
               DESCRIPTION
                   "Number of Http request errors"
               ::= {     lcsLMCTransportStatusTableEntry 4 }
               
       lcsLMCTransportStatusTXBytes OBJECT-TYPE
               SYNTAX      Counter64
               MAX-ACCESS  read-only
               STATUS      current
               DESCRIPTION
                   "Number of transmitted bytes"
               ::= {     lcsLMCTransportStatusTableEntry 5 }
               
       lcsLMCTransportStatusRXBytes OBJECT-TYPE
               SYNTAX      Counter64
               MAX-ACCESS  read-only
               STATUS      current
               DESCRIPTION
                   "Number of received bytes"
               ::= {     lcsLMCTransportStatusTableEntry 7 }

-- =======================================================================================================================
lcsRolloutAgent                                          OBJECT IDENTIFIER ::= { lcsConfiguration 1501 }

lcsRolloutAgentOperating OBJECT-TYPE
   SYNTAX      Integer32
   MAX-ACCESS  read-write
   STATUS      current
   DESCRIPTION
       "Rollout Agent Operating Switch
       0:Disable
       1:Enable
       2:Only-Unconfigured"
   ::= { lcsRolloutAgent 1 }

lcsRolloutAgentActive OBJECT-TYPE
   SYNTAX      Integer32
   MAX-ACCESS  read-only
   STATUS      current
   DESCRIPTION
       "Rollout Agent Active
       0:No
       1:Yes
       2:Deactivated"
   ::= { lcsRolloutAgent 100 }

lcsRolloutAgentLastRequestStatus OBJECT-TYPE
   SYNTAX      Integer32
   MAX-ACCESS  read-only
   STATUS      current
   DESCRIPTION
       "Rollout Agent Last Request Status
        0:NoError,
        1:DnsError,
        2:ProtocolError,
        3:ConnectionError,
        4:MissingOrInvalidConfig"
   ::= { lcsRolloutAgent 101 }

lcsRolloutAgentLastRequestTimestamp OBJECT-TYPE
   SYNTAX      Counter64
   MAX-ACCESS  read-only
   STATUS      current
   DESCRIPTION
       "Rollout Agent Last Request Timestamp"
   ::= { lcsRolloutAgent 102 }

lcsRolloutAgentActiveHeartbeatUrl OBJECT-TYPE
   SYNTAX      DisplayString
   MAX-ACCESS  read-only
   STATUS      current
   DESCRIPTION
       "Active Heartbeat Url"
   ::= { lcsRolloutAgent 103 }

lcsRolloutAgentActiveProjectId OBJECT-TYPE
   SYNTAX      DisplayString
   MAX-ACCESS  read-only
   STATUS      current
   DESCRIPTION
       "Rollout Agent Active Project ID"
   ::= { lcsRolloutAgent 104 }

lcsRolloutAgentActiveLocationId OBJECT-TYPE
   SYNTAX      DisplayString
   MAX-ACCESS  read-only
   STATUS      current
   DESCRIPTION
       "Rollout Agent Active Location ID"
   ::= { lcsRolloutAgent 105 }

lcsRolloutAgentActiveTan OBJECT-TYPE
   SYNTAX      DisplayString
   MAX-ACCESS  read-only
   STATUS      current
   DESCRIPTION
       "Rollout Agent Active TAN"
   ::= { lcsRolloutAgent 106 }

-- =======================================================================================================================
lcsSecurity                                              OBJECT IDENTIFIER ::= { lcosSX 3 }

lcsIPSourceGuard                                         OBJECT IDENTIFIER ::= { lcsSecurity 1 }

lcsIPSourceGuardConf                                     OBJECT IDENTIFIER ::= { lcsIPSourceGuard 1 }

-- RowStatus Info:  createAndGo, notReady not supported.
-- =======================================================================================================================
-- Textual Conventions for the LCS IP Source Guard Mib
-- =======================================================================================================================
--
--    lcsIPSourceGuard        OBJECT IDENTIFIER  ::= { lcsIPSourceGuardMIB 1 }
--    lcsIPSourceGuardConf    OBJECT IDENTIFIER  ::= { lcsIPSourceGuard 1 }

--
-- =======================================================================================================================
-- Start lcsIPSourceGuard group
-- =======================================================================================================================
--lcsIPSourceGuardConf

    lcsIPSourceGuardMode OBJECT-TYPE
               SYNTAX      AdminMode
               MAX-ACCESS  read-write
               STATUS      current
               DESCRIPTION
                   "Enable the Global IP Source Guard or disable the
                    Global IP Source Guard."
               ::= {     lcsIPSourceGuardConf 1 }

    lcsIPSourceGuardDynamicToStaticCmd OBJECT-TYPE
               SYNTAX      ActivateCmd
               MAX-ACCESS  read-write
               STATUS      current
               DESCRIPTION
                   "Translate all dynamic entries to static entries."
               DEFVAL  { noAction }
               ::= {     lcsIPSourceGuardConf 2 }

--lcsIPSourceGuardPortConfigTable

    lcsIPSourceGuardPortConfigTable OBJECT-TYPE
               SYNTAX      SEQUENCE OF     LCSIPSourceGuardPortConfigEntry
               MAX-ACCESS  not-accessible
               STATUS      current
               DESCRIPTION
                   "The IP Source Guard Port Configuration Table.
                    INDEX for this table is ifIndex which is
                    equivalent to the panel port number."
               ::= {     lcsIPSourceGuardConf 3 }

    lcsIPSourceGuardPortConfigEntry OBJECT-TYPE
               SYNTAX          LCSIPSourceGuardPortConfigEntry
               MAX-ACCESS  not-accessible
               STATUS      current
               DESCRIPTION
                   "The IP Source Guard Port Configuration Entry."
               INDEX    {    ifIndex  }
               ::= {     lcsIPSourceGuardPortConfigTable 1 }

    LCSIPSourceGuardPortConfigEntry             ::= SEQUENCE {
                 lcsIPSourceGuardPortConfigMode            AdminMode,
                 lcsIPSourceGuardPortMaxDynamicClients     Integer32
                 }

    lcsIPSourceGuardPortConfigMode OBJECT-TYPE
               SYNTAX      AdminMode
               MAX-ACCESS  read-write
               STATUS      current
               DESCRIPTION
                   "Specify IP Source Guard is enabled on which ports."
               ::= {     lcsIPSourceGuardPortConfigEntry 2 }

    lcsIPSourceGuardPortMaxDynamicClients OBJECT-TYPE
               SYNTAX      Integer32(0..2|99)
               MAX-ACCESS  read-write
               STATUS      current
               DESCRIPTION
                   "Specify the maximum number of dynamic clients that can
                    be learned on given port.
                    default: 99
                    0~2: Max Dynamic clients
                    99:Unlimited "
               ::= {     lcsIPSourceGuardPortConfigEntry 3 }

--lcsIPSourceGuardStaticTable

    lcsIPSourceGuardStaticTable OBJECT-TYPE
               SYNTAX      SEQUENCE OF     LCSIPSourceGuardStaticEntry
               MAX-ACCESS  not-accessible
               STATUS      current
               DESCRIPTION
                   "The IP Source Guard Static Table."
               ::= {     lcsIPSourceGuard 2 }

    lcsIPSourceGuardStaticEntry OBJECT-TYPE
               SYNTAX          LCSIPSourceGuardStaticEntry
               MAX-ACCESS  not-accessible
               STATUS      current
               DESCRIPTION
                   "The IP Source Guard Static Entry."
               INDEX    {    lcsIPSourceGuardStaticIndex  }
               ::= {     lcsIPSourceGuardStaticTable 1 }

    LCSIPSourceGuardStaticEntry             ::= SEQUENCE {
                 lcsIPSourceGuardStaticSwitchIndex   Integer32,
                 lcsIPSourceGuardStaticIndex         Integer32,
                 lcsIPSourceGuardStaticPort          Integer32,
                 lcsIPSourceGuardStaticVLANId        Integer32,
                 lcsIPSourceGuardStaticIPAddress     IpAddress,
--                 lcsIPSourceGuardStaticIPMask        IpAddress,
                 lcsIPSourceGuardStaticMACAddress    DisplayString,
                 lcsIPSourceGuardStaticRowStatus     RowStatus
                 }

    lcsIPSourceGuardStaticSwitchIndex OBJECT-TYPE
               SYNTAX      Integer32(1..16)
               MAX-ACCESS  not-accessible
               STATUS      current
               DESCRIPTION
                   "Switch Index."
               ::= {     lcsIPSourceGuardStaticEntry 1 }

    lcsIPSourceGuardStaticIndex OBJECT-TYPE
               SYNTAX      Integer32(1..28)
               MAX-ACCESS  not-accessible
               STATUS      current
               DESCRIPTION
                   "The entry of table."
               ::= {     lcsIPSourceGuardStaticEntry 2 }

    lcsIPSourceGuardStaticPort OBJECT-TYPE
               SYNTAX      Integer32(1..255)
               MAX-ACCESS  read-create
               STATUS      current
               DESCRIPTION
                   "The port number of table.
                    range: 1 - port number."
               ::= {     lcsIPSourceGuardStaticEntry 3 }

    lcsIPSourceGuardStaticVLANId OBJECT-TYPE
               SYNTAX      Integer32(1..4094)
               MAX-ACCESS  read-create
               STATUS      current
               DESCRIPTION
                   "VLAN ID, range: 1 - 4094."
               ::= {     lcsIPSourceGuardStaticEntry 4 }

    lcsIPSourceGuardStaticIPAddress OBJECT-TYPE
               SYNTAX      IpAddress
               MAX-ACCESS  read-create
               STATUS      current
               DESCRIPTION
                   "IP address allowed for doing IP source guard."
               ::= {     lcsIPSourceGuardStaticEntry 5 }

--    lcsIPSourceGuardStaticIPMask OBJECT-TYPE
--               SYNTAX      IpAddress
--               MAX-ACCESS  read-create
--               STATUS      current
--               DESCRIPTION
--                   "IP Mask allowed for doing IP source guard."
--               ::= {     lcsIPSourceGuardStaticEntry 6 }

    lcsIPSourceGuardStaticMACAddress OBJECT-TYPE
               SYNTAX      DisplayString
               MAX-ACCESS  read-create
               STATUS      current
               DESCRIPTION
                   "Allowed Source MAC address, format: 0a 1b 2c 3d 4e 5f."
               ::= {     lcsIPSourceGuardStaticEntry 7 }

    lcsIPSourceGuardStaticRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     lcsIPSourceGuardStaticEntry 8 }

--lcsIPSourceGuardDynamicTable

    lcsIPSourceGuardDynamicTable OBJECT-TYPE
               SYNTAX      SEQUENCE OF     LCSIPSourceGuardDynamicEntry
               MAX-ACCESS  not-accessible
               STATUS      current
               DESCRIPTION
                   "The IP Source Guard Dynamic Table."
               ::= {     lcsIPSourceGuard 3 }

    lcsIPSourceGuardDynamicEntry OBJECT-TYPE
               SYNTAX          LCSIPSourceGuardDynamicEntry
               MAX-ACCESS  not-accessible
               STATUS      current
               DESCRIPTION
                   "The IP Source Guard Dynamic Entry."
               INDEX    {    lcsIPSourceGuardDynamicIndex  }
               ::= {     lcsIPSourceGuardDynamicTable 1 }

    LCSIPSourceGuardDynamicEntry             ::= SEQUENCE {
                 lcsIPSourceGuardDynamicSwitchIndex    Integer32,
                 lcsIPSourceGuardDynamicIndex          Integer32,
                 lcsIPSourceGuardDynamicPort           Integer32,
                 lcsIPSourceGuardDynamicVLANId         Integer32,
                 lcsIPSourceGuardDynamicIPAddress      IpAddress,
                 lcsIPSourceGuardDynamicMACAddress     DisplayString
                 }

    lcsIPSourceGuardDynamicSwitchIndex OBJECT-TYPE
               SYNTAX      Integer32(1..16)
               MAX-ACCESS  not-accessible
               STATUS      current
               DESCRIPTION
                   "Switch Index."
               ::= {     lcsIPSourceGuardDynamicEntry 1 }

    lcsIPSourceGuardDynamicIndex OBJECT-TYPE
               SYNTAX      Integer32(1..4094)
               MAX-ACCESS  not-accessible
               STATUS      current
               DESCRIPTION
                   "The entry of table."
               ::= {     lcsIPSourceGuardDynamicEntry 2 }

    lcsIPSourceGuardDynamicPort OBJECT-TYPE
               SYNTAX      Integer32(1..255)
               MAX-ACCESS  read-only
               STATUS      current
               DESCRIPTION
                   "The logical port for the settings."
               ::= {     lcsIPSourceGuardDynamicEntry 3 }

    lcsIPSourceGuardDynamicVLANId OBJECT-TYPE
               SYNTAX      Integer32(1..4094)
               MAX-ACCESS  read-only
               STATUS      current
               DESCRIPTION
                   "The vlan id for the settings."
               ::= {     lcsIPSourceGuardDynamicEntry 4 }

    lcsIPSourceGuardDynamicIPAddress OBJECT-TYPE
               SYNTAX      IpAddress
               MAX-ACCESS  read-only
               STATUS      current
               DESCRIPTION
                   "Allowed Source IP address."
               ::= {     lcsIPSourceGuardDynamicEntry 5 }

    lcsIPSourceGuardDynamicMACAddress OBJECT-TYPE
               SYNTAX      DisplayString
               MAX-ACCESS  read-only
               STATUS      current
               DESCRIPTION
                   "Allowed Source MAC address."
               ::= {     lcsIPSourceGuardDynamicEntry 6 }
-- =======================================================================================================================
lcsARPInspection                                          OBJECT IDENTIFIER ::= { lcsSecurity 2 }
-- RowStatus Info:  createAndGo, notReady not supported.
-- =======================================================================================================================
-- Textual Conventions for the lcs Arp Mib
-- =======================================================================================================================
--
    lcsARP                  OBJECT IDENTIFIER  ::= { lcsARPInspection 1 }
    lcsARPConfig            OBJECT IDENTIFIER  ::= { lcsARP 1 }

--
-- =======================================================================================================================
-- Start lcsARP group
-- =======================================================================================================================
--lcsARPConfig

    lcsARPConfMode OBJECT-TYPE
               SYNTAX      AdminMode
               MAX-ACCESS  read-write
               STATUS      current
               DESCRIPTION
                   "Enable the Global ARP Inspection or disable the Global
                    ARP Inspection."
               ::= {     lcsARPConfig 1 }

--lcsARPPortConfTable

    lcsARPPortConfTable OBJECT-TYPE
               SYNTAX      SEQUENCE OF     LCSARPPortConfEntry
               MAX-ACCESS  not-accessible
               STATUS      current
               DESCRIPTION
                   "The ARP Port Configuration Table."
               ::= {     lcsARPConfig 3 }

    lcsARPPortConfEntry OBJECT-TYPE
               SYNTAX          LCSARPPortConfEntry
               MAX-ACCESS  not-accessible
               STATUS      current
               DESCRIPTION
                   "The ARP Port Configuration Entry."
               INDEX    {    lcsARPPortConfPort  }
               ::= {     lcsARPPortConfTable 1 }

    LCSARPPortConfEntry             ::= SEQUENCE {
                 lcsARPPortConfPort            Integer32,
                 lcsARPPortConfMode            AdminMode,
                 lcsARPPortConfCheckVLAN       AdminMode,
                 lcsARPPortConfLogType         INTEGER
                 }

    lcsARPPortConfPort OBJECT-TYPE
               SYNTAX      Integer32(1..255)
               MAX-ACCESS  not-accessible
               STATUS      current
               DESCRIPTION
                   "The port number for which the configuration below applies.
                    range: 1 - port number."
               ::= {     lcsARPPortConfEntry 1 }

    lcsARPPortConfMode OBJECT-TYPE
               SYNTAX      AdminMode
               MAX-ACCESS  read-write
               STATUS      current
               DESCRIPTION
                   "Specify ARP Inspection is enabled on which ports."
               ::= {     lcsARPPortConfEntry 2 }

    lcsARPPortConfCheckVLAN OBJECT-TYPE
               SYNTAX      AdminMode
               MAX-ACCESS  read-write
               STATUS      current
               DESCRIPTION
                   "When the setting of 'Check VLAN' is disabled, the log
                   type of ARP Inspection will refer to the port setting.
                   And the setting of 'Check VLAN' is enabled, the log type
                   of ARP Inspection will refer to the VLAN setting."
               ::= {     lcsARPPortConfEntry 3 }

    lcsARPPortConfLogType OBJECT-TYPE
               SYNTAX      INTEGER{none(0),deny(1),permit(2),all(3)}
               MAX-ACCESS  read-write
               STATUS      current
               DESCRIPTION
                   "The log type of ARP Inspection will refer to the
                    port setting.
                    0: none,
                    1: deny,
                    2: permit,
                    3: all,
                    range: 0-3."
               ::= {     lcsARPPortConfEntry 4 }

--lcsARPVlanConfig

    lcsARPVlanConfigTable OBJECT-TYPE
               SYNTAX      SEQUENCE OF     LCSARPVlanConfigEntry
               MAX-ACCESS  not-accessible
               STATUS      current
               DESCRIPTION
                   "The ARP Vlan Configuration Table."
               ::= {     lcsARP 2 }

    lcsARPVlanConfigEntry OBJECT-TYPE
               SYNTAX          LCSARPVlanConfigEntry
               MAX-ACCESS  not-accessible
               STATUS      current
               DESCRIPTION
                   "The ARP Vlan Configuration Entry."
               INDEX    {    lcsARPVlanConfigVlan  }
               ::= {     lcsARPVlanConfigTable 1 }

    LCSARPVlanConfigEntry             ::= SEQUENCE {
                 lcsARPPortConfigIndex      Integer32,      
                 lcsARPVlanConfigVlan       Integer32,
                 lcsARPVlanConfigLogType    INTEGER,
                 lcsARPVlanConfigRowStatus  RowStatus
                 }

    lcsARPPortConfigIndex OBJECT-TYPE
               SYNTAX      Integer32(1..4094)
               MAX-ACCESS  not-accessible
               STATUS      current
               DESCRIPTION
                   "The Index of Vlan config Table"
               ::= {     lcsARPVlanConfigEntry 1 }                               
                 
    lcsARPVlanConfigVlan OBJECT-TYPE
               SYNTAX      Integer32(1..4094)
               MAX-ACCESS  read-create
               STATUS      current
               DESCRIPTION
                   "Specify ARP Inspection is enabled on which VLANs.
                    range: 1 - 4094."
               ::= {     lcsARPVlanConfigEntry 2 }

    lcsARPVlanConfigLogType OBJECT-TYPE
               SYNTAX      INTEGER{none(0),deny(1),permit(2),all(3)}
               MAX-ACCESS  read-create
               STATUS      current
               DESCRIPTION
                   "The log type also can be configured on per VLAN setting.
                    0: none,
                    1: deny,
                    2: permit,
                    3: all,
                    range: 0-3."
               ::= {     lcsARPVlanConfigEntry 3 }

    lcsARPVlanConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     lcsARPVlanConfigEntry 4 }

--lcsARPStaticTable

    lcsARPStaticTable OBJECT-TYPE
               SYNTAX      SEQUENCE OF     LCSARPStaticEntry
               MAX-ACCESS  not-accessible
               STATUS      current
               DESCRIPTION
                   "The ARP Static Table."
               ::= {     lcsARP 3 }

    lcsARPStaticEntry OBJECT-TYPE
               SYNTAX          LCSARPStaticEntry
               MAX-ACCESS  not-accessible
               STATUS      current
               DESCRIPTION
                   "The ARP Static Entry."
               INDEX    {    lcsARPStaticIndex  }
               ::= {     lcsARPStaticTable 1 }

    LCSARPStaticEntry             ::= SEQUENCE {
                 lcsARPStaticSwitchIndex   Integer32,
                 lcsARPStaticIndex         Integer32,
                 lcsARPStaticPort          Integer32,
                 lcsARPStaticVlanID        Integer32,
                 lcsARPStaticMACAddress    DisplayString,
                 lcsARPStaticIPAddress     IpAddress,
                 lcsARPStaticRowStatus     RowStatus
                 }


    lcsARPStaticSwitchIndex OBJECT-TYPE
               SYNTAX      Integer32(1..16)
               MAX-ACCESS  not-accessible
               STATUS      current
               DESCRIPTION
                   "Switch Index."
               ::= {     lcsARPStaticEntry 1 }

    lcsARPStaticIndex OBJECT-TYPE
               SYNTAX      Integer32(1..255)
               MAX-ACCESS  not-accessible
               STATUS      current
               DESCRIPTION
                   "The entry of table."
               ::= {     lcsARPStaticEntry 2 }

    lcsARPStaticPort OBJECT-TYPE
               SYNTAX      Integer32(1..255)
               MAX-ACCESS  read-create
               STATUS      current
               DESCRIPTION
                   "The logical port for the settings.
                    range: 1 - port number."
               ::= {     lcsARPStaticEntry 3 }

    lcsARPStaticVlanID OBJECT-TYPE
               SYNTAX      Integer32(1..4094)
               MAX-ACCESS  read-create
               STATUS      current
               DESCRIPTION
                   "The vlan id for the settings.
                    range: 1-4094."
               ::= {     lcsARPStaticEntry 4 }

    lcsARPStaticMACAddress OBJECT-TYPE
               SYNTAX      DisplayString
               MAX-ACCESS  read-create
               STATUS      current
               DESCRIPTION
                   "Allowed Source MAC address in ARP request packets."
               ::= {     lcsARPStaticEntry 5 }

    lcsARPStaticIPAddress OBJECT-TYPE
               SYNTAX      IpAddress
               MAX-ACCESS  read-create
               STATUS      current
               DESCRIPTION
                   "Allowed Source IP address in ARP request packets."
               ::= {     lcsARPStaticEntry 6 }

    lcsARPStaticRowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     lcsARPStaticEntry 7 }

--lcsARPDynamicTable

    lcsARPDynamicTable OBJECT-TYPE
               SYNTAX      SEQUENCE OF     LCSARPDynamicEntry
               MAX-ACCESS  not-accessible
               STATUS      current
               DESCRIPTION
                   "The ARP Dynamic Table."
               ::= {    lcsARP 4 }

    lcsARPDynamicEntry OBJECT-TYPE
               SYNTAX          LCSARPDynamicEntry
               MAX-ACCESS  not-accessible
               STATUS      current
               DESCRIPTION
                   "The ARP Dynamic Entry."
               INDEX    {   lcsARPDynamicIndex  }
               ::= {    lcsARPDynamicTable 1 }

    LCSARPDynamicEntry             ::= SEQUENCE {
                 lcsARPDynamicIndex          Integer32,
                 lcsARPDynamicPort           Integer32,
                 lcsARPDynamicVLANId         Integer32,
                 lcsARPDynamicMACAddress     MacAddress,
                 lcsARPDynamicIPAddress      IpAddress,
                 lcsARPDynamicToStaticCmd    INTEGER
                 }

    lcsARPDynamicIndex OBJECT-TYPE
               SYNTAX      Integer32(1..4094)
               MAX-ACCESS  not-accessible
               STATUS      current
               DESCRIPTION
                   "The entry of table."
               ::= {    lcsARPDynamicEntry 1 }

    lcsARPDynamicPort OBJECT-TYPE
               SYNTAX      Integer32(1..255)
               MAX-ACCESS  read-only
               STATUS      current
               DESCRIPTION
                   "Switch Port Number for which the entries are displayed."
               ::= {    lcsARPDynamicEntry 2 }

    lcsARPDynamicVLANId OBJECT-TYPE
               SYNTAX      Integer32(1..4094)
               MAX-ACCESS  read-only
               STATUS      current
               DESCRIPTION
                   "VLAN-ID in which the ARP traffic is permitted."
               ::= {    lcsARPDynamicEntry 3 }

    lcsARPDynamicMACAddress OBJECT-TYPE
               SYNTAX      MacAddress
               MAX-ACCESS  read-only
               STATUS      current
               DESCRIPTION
                   "User MAC address of the entry."
               ::= {    lcsARPDynamicEntry 4 }

    lcsARPDynamicIPAddress OBJECT-TYPE
               SYNTAX      IpAddress
               MAX-ACCESS  read-only
               STATUS      current
               DESCRIPTION
                   "User IP address of the entry."
               ::= {    lcsARPDynamicEntry 5 }

    lcsARPDynamicToStaticCmd OBJECT-TYPE
               SYNTAX      ActivateCmd
               MAX-ACCESS  read-write
               STATUS      current
               DESCRIPTION
                   "Enable the Global ARP Inspection or disable the Global
                    ARP Inspection."
               ::= {     lcsARPDynamicEntry 6 }


-- =======================================================================================================================
-- lcsARPConformance
-- =======================================================================================================================
lcsARPConformance OBJECT IDENTIFIER ::= { lcsARPInspection 200 }

lcsARPCompliances OBJECT IDENTIFIER ::= { lcsARPConformance 1 }

lcsARPGroups      OBJECT IDENTIFIER ::= { lcsARPConformance 2 }

lcsARPGroup OBJECT-GROUP
    OBJECTS {
                -- lcsARPConfig
                lcsARPConfMode,

                --lcsARPPortConfTable
                lcsARPPortConfMode,
                lcsARPPortConfCheckVLAN,
                lcsARPPortConfLogType,

                --lcsARPVlanConfig
                lcsARPVlanConfigLogType,
                lcsARPVlanConfigRowStatus,

                --lcsARPStaticTable
                lcsARPStaticPort,
                lcsARPStaticVlanID,
                lcsARPStaticMACAddress,
                lcsARPStaticIPAddress,
                lcsARPStaticRowStatus,

                --lcsARPDynamicTable
                lcsARPDynamicPort,
                lcsARPDynamicVLANId,
                lcsARPDynamicMACAddress,
                lcsARPDynamicIPAddress,
                lcsARPDynamicToStaticCmd
            }
     STATUS  current
     DESCRIPTION
            "The collection of objects which are used to indicate
            lcs ARP information."
    ::= { lcsARPGroups 1 }

-- =======================================================================================================================
lcsDHCPSnooping                                          OBJECT IDENTIFIER ::= { lcsSecurity 3 }

lcsDHCPSnoopingConf                                          OBJECT IDENTIFIER ::= { lcsDHCPSnooping 1 }

lcsDHCPSnoopingMode OBJECT-TYPE
   SYNTAX      Integer32(0|1)
   MAX-ACCESS  read-write
   STATUS      current
   DESCRIPTION
       "default: 0
       0: disable
       1: enable"
   ::= { lcsDHCPSnoopingConf 1 }

lcsDHCPSnoopingPortModeConfigurationTable OBJECT-TYPE
   SYNTAX      SEQUENCE OF LCSDHCPSnoopingPortModeConfigurationEntry
   MAX-ACCESS  not-accessible
   STATUS      current
   DESCRIPTION
       " "
   ::= { lcsDHCPSnoopingConf 2 }

lcsDHCPSnoopingPortModeConfigurationEntry OBJECT-TYPE
   SYNTAX      LCSDHCPSnoopingPortModeConfigurationEntry
   MAX-ACCESS  not-accessible
   STATUS      current
   DESCRIPTION
       " "
   INDEX    { lcsDHCPSnoopingPortModeConfigurationPort  }
   ::= { lcsDHCPSnoopingPortModeConfigurationTable 1 }

LCSDHCPSnoopingPortModeConfigurationEntry ::= SEQUENCE {
   lcsDHCPSnoopingPortModeConfigurationPort Integer32,
   lcsDHCPSnoopingPortModeConfigurationMode Integer32
}

lcsDHCPSnoopingPortModeConfigurationPort OBJECT-TYPE
   SYNTAX      Integer32(1..4094)
   MAX-ACCESS  not-accessible
   STATUS      current
   DESCRIPTION
       " "
   ::= { lcsDHCPSnoopingPortModeConfigurationEntry 1 }

lcsDHCPSnoopingPortModeConfigurationMode OBJECT-TYPE
   SYNTAX      Integer32 (0|1)
   MAX-ACCESS  read-write
   STATUS      current
   DESCRIPTION
       "default: 1
       0: trust port mode
       1: untrust port mode"
   ::= { lcsDHCPSnoopingPortModeConfigurationEntry 2 }

lcsDHCPSnoopingStatisticsTable OBJECT-TYPE
   SYNTAX      SEQUENCE OF LCSDHCPSnoopingStatisticsEntry
   MAX-ACCESS  not-accessible
   STATUS      current
   DESCRIPTION
       " "
   ::= { lcsDHCPSnooping 2 }

lcsDHCPSnoopingStatisticsEntry OBJECT-TYPE
   SYNTAX      LCSDHCPSnoopingStatisticsEntry
   MAX-ACCESS  not-accessible
   STATUS      current
   DESCRIPTION
       " "
   INDEX    { lcsDHCPSnoopingStatisticsPort  }
   ::= { lcsDHCPSnoopingStatisticsTable 1 }

LCSDHCPSnoopingStatisticsEntry ::= SEQUENCE {
   lcsDHCPSnoopingStatisticsPort         Integer32,
   lcsDHCPSnoopingStatisticsClear        Integer32,
   lcsDHCPSnoopingRxDiscover             Counter32,
   lcsDHCPSnoopingRxOffer                Counter32,
   lcsDHCPSnoopingRxRequest              Counter32,
   lcsDHCPSnoopingRxDecline              Counter32,
   lcsDHCPSnoopingRxACK                  Counter32,
   lcsDHCPSnoopingRxNAK                  Counter32,
   lcsDHCPSnoopingRxRelease              Counter32,
   lcsDHCPSnoopingRxInform               Counter32,
   lcsDHCPSnoopingRxLeaseQuery           Counter32,
   lcsDHCPSnoopingRxLeaseUnassigned      Counter32,
   lcsDHCPSnoopingRxLeaseUnknown         Counter32,
   lcsDHCPSnoopingRxLeaseActive          Counter32,
   lcsDHCPSnoopingTxDiscover             Counter32,
   lcsDHCPSnoopingTxOffer                Counter32,
   lcsDHCPSnoopingTxRequest              Counter32,
   lcsDHCPSnoopingTxDecline              Counter32,
   lcsDHCPSnoopingTxACK                  Counter32,
   lcsDHCPSnoopingTxNAK                  Counter32,
   lcsDHCPSnoopingTxRelease              Counter32,
   lcsDHCPSnoopingTxInform               Counter32,
   lcsDHCPSnoopingTxLeaseQuery           Counter32,
   lcsDHCPSnoopingTxLeaseUnassigned      Counter32,
   lcsDHCPSnoopingTxLeaseUnknown         Counter32,
   lcsDHCPSnoopingTxLeaseActive          Counter32,
   lcsDHCPSnoopingRxDiscardedChecksumError  Counter32,
   lcsDHCPSnoopingRxDiscardedFromUntrusted  Counter32
}

lcsDHCPSnoopingStatisticsPort OBJECT-TYPE
   SYNTAX      Integer32(1..4094)
   MAX-ACCESS  not-accessible
   STATUS      current
   DESCRIPTION
       " "
   ::= { lcsDHCPSnoopingStatisticsEntry 1 }

lcsDHCPSnoopingStatisticsClear OBJECT-TYPE
   SYNTAX      Integer32 (0|1)
   MAX-ACCESS  read-write
   STATUS      current
   DESCRIPTION
       "default: 0
       0: none
       1: clear"
   ::= { lcsDHCPSnoopingStatisticsEntry 2 }

lcsDHCPSnoopingRxDiscover OBJECT-TYPE
   SYNTAX      Counter32
   MAX-ACCESS  read-only
   STATUS      current
   DESCRIPTION
       " "
   ::= { lcsDHCPSnoopingStatisticsEntry 3 }

lcsDHCPSnoopingRxOffer OBJECT-TYPE
   SYNTAX      Counter32
   MAX-ACCESS  read-only
   STATUS      current
   DESCRIPTION
       " "
   ::= { lcsDHCPSnoopingStatisticsEntry 4 }

lcsDHCPSnoopingRxRequest OBJECT-TYPE
   SYNTAX      Counter32
   MAX-ACCESS  read-only
   STATUS      current
   DESCRIPTION
       " "
   ::= { lcsDHCPSnoopingStatisticsEntry 5 }

lcsDHCPSnoopingRxDecline OBJECT-TYPE
   SYNTAX      Counter32
   MAX-ACCESS  read-only
   STATUS      current
   DESCRIPTION
       " "
   ::= { lcsDHCPSnoopingStatisticsEntry 6 }

lcsDHCPSnoopingRxACK OBJECT-TYPE
   SYNTAX      Counter32
   MAX-ACCESS  read-only
   STATUS      current
   DESCRIPTION
       " "
   ::= { lcsDHCPSnoopingStatisticsEntry 7 }

lcsDHCPSnoopingRxNAK OBJECT-TYPE
   SYNTAX      Counter32
   MAX-ACCESS  read-only
   STATUS      current
   DESCRIPTION
       " "
   ::= { lcsDHCPSnoopingStatisticsEntry 8 }

lcsDHCPSnoopingRxRelease OBJECT-TYPE
   SYNTAX      Counter32
   MAX-ACCESS  read-only
   STATUS      current
   DESCRIPTION
       " "
   ::= { lcsDHCPSnoopingStatisticsEntry 9 }

lcsDHCPSnoopingRxInform OBJECT-TYPE
   SYNTAX      Counter32
   MAX-ACCESS  read-only
   STATUS      current
   DESCRIPTION
       " "
   ::= { lcsDHCPSnoopingStatisticsEntry 10 }

lcsDHCPSnoopingRxLeaseQuery OBJECT-TYPE
   SYNTAX      Counter32
   MAX-ACCESS  read-only
   STATUS      current
   DESCRIPTION
       " "
   ::= { lcsDHCPSnoopingStatisticsEntry 11 }

lcsDHCPSnoopingRxLeaseUnassigned OBJECT-TYPE
   SYNTAX      Counter32
   MAX-ACCESS  read-only
   STATUS      current
   DESCRIPTION
       " "
   ::= { lcsDHCPSnoopingStatisticsEntry 12 }

lcsDHCPSnoopingRxLeaseUnknown OBJECT-TYPE
   SYNTAX      Counter32
   MAX-ACCESS  read-only
   STATUS      current
   DESCRIPTION
       " "
   ::= { lcsDHCPSnoopingStatisticsEntry 13 }

lcsDHCPSnoopingRxLeaseActive OBJECT-TYPE
   SYNTAX      Counter32
   MAX-ACCESS  read-only
   STATUS      current
   DESCRIPTION
       " "
   ::= { lcsDHCPSnoopingStatisticsEntry 14 }

lcsDHCPSnoopingTxDiscover OBJECT-TYPE
   SYNTAX      Counter32
   MAX-ACCESS  read-only
   STATUS      current
   DESCRIPTION
       " "
   ::= { lcsDHCPSnoopingStatisticsEntry 15 }

lcsDHCPSnoopingTxOffer OBJECT-TYPE
   SYNTAX      Counter32
   MAX-ACCESS  read-only
   STATUS      current
   DESCRIPTION
       " "
   ::= { lcsDHCPSnoopingStatisticsEntry 16 }

lcsDHCPSnoopingTxRequest OBJECT-TYPE
   SYNTAX      Counter32
   MAX-ACCESS  read-only
   STATUS      current
   DESCRIPTION
       " "
   ::= { lcsDHCPSnoopingStatisticsEntry 17 }

lcsDHCPSnoopingTxDecline OBJECT-TYPE
   SYNTAX      Counter32
   MAX-ACCESS  read-only
   STATUS      current
   DESCRIPTION
       " "
   ::= { lcsDHCPSnoopingStatisticsEntry 18 }

lcsDHCPSnoopingTxACK OBJECT-TYPE
   SYNTAX      Counter32
   MAX-ACCESS  read-only
   STATUS      current
   DESCRIPTION
       " "
   ::= { lcsDHCPSnoopingStatisticsEntry 19 }

lcsDHCPSnoopingTxNAK OBJECT-TYPE
   SYNTAX      Counter32
   MAX-ACCESS  read-only
   STATUS      current
   DESCRIPTION
       " "
   ::= { lcsDHCPSnoopingStatisticsEntry 20 }

lcsDHCPSnoopingTxRelease OBJECT-TYPE
   SYNTAX      Counter32
   MAX-ACCESS  read-only
   STATUS      current
   DESCRIPTION
       " "
   ::= { lcsDHCPSnoopingStatisticsEntry 21 }

lcsDHCPSnoopingTxInform OBJECT-TYPE
   SYNTAX      Counter32
   MAX-ACCESS  read-only
   STATUS      current
   DESCRIPTION
       " "
   ::= { lcsDHCPSnoopingStatisticsEntry 22 }

lcsDHCPSnoopingTxLeaseQuery OBJECT-TYPE
   SYNTAX      Counter32
   MAX-ACCESS  read-only
   STATUS      current
   DESCRIPTION
       " "
   ::= { lcsDHCPSnoopingStatisticsEntry 23 }

lcsDHCPSnoopingTxLeaseUnassigned OBJECT-TYPE
   SYNTAX      Counter32
   MAX-ACCESS  read-only
   STATUS      current
   DESCRIPTION
       " "
   ::= { lcsDHCPSnoopingStatisticsEntry 24 }

lcsDHCPSnoopingTxLeaseUnknown OBJECT-TYPE
   SYNTAX      Counter32
   MAX-ACCESS  read-only
   STATUS      current
   DESCRIPTION
       " "
   ::= { lcsDHCPSnoopingStatisticsEntry 25 }

lcsDHCPSnoopingTxLeaseActive OBJECT-TYPE
   SYNTAX      Counter32
   MAX-ACCESS  read-only
   STATUS      current
   DESCRIPTION
       " "
   ::= { lcsDHCPSnoopingStatisticsEntry 26 }

lcsDHCPSnoopingRxDiscardedChecksumError OBJECT-TYPE
   SYNTAX      Counter32
   MAX-ACCESS  read-only
   STATUS      current
   DESCRIPTION
       " "
   ::= { lcsDHCPSnoopingStatisticsEntry 27 }

lcsDHCPSnoopingRxDiscardedFromUntrusted OBJECT-TYPE
   SYNTAX      Counter32
   MAX-ACCESS  read-only
   STATUS      current
   DESCRIPTION
       " "
   ::= { lcsDHCPSnoopingStatisticsEntry 28 }

lcsDHCPRelay                                             OBJECT IDENTIFIER ::= { lcsSecurity 4 }

lcsDHCPRelayConfiguration                                         OBJECT IDENTIFIER ::= { lcsDHCPRelay 1 }

lcsDHCPRelayMode OBJECT-TYPE
   SYNTAX      Integer32(0|1)
   MAX-ACCESS  read-write
   STATUS      current
   DESCRIPTION
       "default: 0
       0: disable
       1: enable
       We need at least one server"
   ::= { lcsDHCPRelayConfiguration 1 }

lcsDHCPRelayServer OBJECT-TYPE
   SYNTAX      IpAddress
   MAX-ACCESS  read-write
   STATUS      current
   DESCRIPTION
       " "
   ::= { lcsDHCPRelayConfiguration 2 }

lcsDHCPRelayInformationMode OBJECT-TYPE
   SYNTAX      Integer32(0|1)
   MAX-ACCESS  read-write
   STATUS      current
   DESCRIPTION
       "default: 0
       0: disable
       1: enable "
   ::= { lcsDHCPRelayConfiguration 3 }

lcsDHCPRelayInformationPolicy OBJECT-TYPE
   SYNTAX      Integer32(0..2)
   MAX-ACCESS  read-write
   STATUS      current
   DESCRIPTION
       "default: 0
       0: replace
       1: keep
       2: drop "
   ::= { lcsDHCPRelayConfiguration 4 }

lcsDHCPRelayStatistics                                   OBJECT IDENTIFIER ::= { lcsDHCPRelay 2 }

lcsDHCPRelayServerStatistics                                   OBJECT IDENTIFIER ::= { lcsDHCPRelayStatistics 1 }

lcsServerStatTransmitToServer OBJECT-TYPE
   SYNTAX      Counter32
   MAX-ACCESS  read-only
   STATUS      current
   DESCRIPTION
       " "
   ::= { lcsDHCPRelayServerStatistics 1 }

lcsServerStatTransmitError OBJECT-TYPE
   SYNTAX      Counter32
   MAX-ACCESS  read-only
   STATUS      current
   DESCRIPTION
       " "
   ::= { lcsDHCPRelayServerStatistics 2 }

lcsServerStatReceiveFromServer OBJECT-TYPE
   SYNTAX      Counter32
   MAX-ACCESS  read-only
   STATUS      current
   DESCRIPTION
       " "
   ::= { lcsDHCPRelayServerStatistics 3 }

lcsServerStatReceiveMissingAgentOption OBJECT-TYPE
   SYNTAX      Counter32
   MAX-ACCESS  read-only
   STATUS      current
   DESCRIPTION
       " "
   ::= { lcsDHCPRelayServerStatistics 4 }

lcsServerStatReceiveMissingCircuitID OBJECT-TYPE
   SYNTAX      Counter32
   MAX-ACCESS  read-only
   STATUS      current
   DESCRIPTION
       " "
   ::= { lcsDHCPRelayServerStatistics 5 }

lcsServerStatReceiveMissingRemoteID OBJECT-TYPE
   SYNTAX      Counter32
   MAX-ACCESS  read-only
   STATUS      current
   DESCRIPTION
       " "
   ::= { lcsDHCPRelayServerStatistics 6 }

lcsServerStatReceiveBadCircuitID OBJECT-TYPE
   SYNTAX      Counter32
   MAX-ACCESS  read-only
   STATUS      current
   DESCRIPTION
       " "
   ::= { lcsDHCPRelayServerStatistics 7 }

lcsServerStatReceiveBadRemoteID OBJECT-TYPE
   SYNTAX      Counter32
   MAX-ACCESS  read-only
   STATUS      current
   DESCRIPTION
       " "
   ::= { lcsDHCPRelayServerStatistics 8 }

lcsDHCPRelayClientStatistics                                   OBJECT IDENTIFIER ::= { lcsDHCPRelayStatistics 2 }

lcsClientStatTransmitToClient OBJECT-TYPE
   SYNTAX      Counter32
   MAX-ACCESS  read-only
   STATUS      current
   DESCRIPTION
       " "
   ::= { lcsDHCPRelayClientStatistics 1 }

lcsClientStatTransmitError OBJECT-TYPE
   SYNTAX      Counter32
   MAX-ACCESS  read-only
   STATUS      current
   DESCRIPTION
       " "
   ::= { lcsDHCPRelayClientStatistics 2 }

lcsClientStatReceivefromClient OBJECT-TYPE
   SYNTAX      Counter32
   MAX-ACCESS  read-only
   STATUS      current
   DESCRIPTION
       " "
   ::= { lcsDHCPRelayClientStatistics 3 }

lcsClientStatReceiveAgentOption OBJECT-TYPE
   SYNTAX      Counter32
   MAX-ACCESS  read-only
   STATUS      current
   DESCRIPTION
       " "
   ::= { lcsDHCPRelayClientStatistics 4 }

lcsClientStatReplaceAgentOption OBJECT-TYPE
   SYNTAX      Counter32
   MAX-ACCESS  read-only
   STATUS      current
   DESCRIPTION
       " "
   ::= { lcsDHCPRelayClientStatistics 5 }

lcsClientStatKeepAgentOption OBJECT-TYPE
   SYNTAX      Counter32
   MAX-ACCESS  read-only
   STATUS      current
   DESCRIPTION
       " "
   ::= { lcsDHCPRelayClientStatistics 6 }

lcsClientStatDropAgentOption OBJECT-TYPE
   SYNTAX      Counter32
   MAX-ACCESS  read-only
   STATUS      current
   DESCRIPTION
       " "
   ::= { lcsDHCPRelayClientStatistics 7 }

lcsPortSecurity                                          OBJECT IDENTIFIER ::= { lcsSecurity 5 }

lcsPortSecLimitCtrl                                      OBJECT IDENTIFIER ::= { lcsPortSecurity 1 }

lcsPortSecLimitCtrlSystemConf                                      OBJECT IDENTIFIER ::= { lcsPortSecLimitCtrl 1 }

-- lcsPortSecurityMode OBJECT-TYPE
--   SYNTAX      Integer32(0|1)
--   MAX-ACCESS  read-write
--   STATUS      current
--   DESCRIPTION
--       "default: 0
--       0: disable
--       1: enable "
--   ::= { lcsPortSecLimitCtrlSystemConf 1 }

lcsPortSecurityAging OBJECT-TYPE
   SYNTAX      Integer32(0|1)
   MAX-ACCESS  read-write
   STATUS      current
   DESCRIPTION
       "default: 0
       0: disable
       1: enable "
   ::= { lcsPortSecLimitCtrlSystemConf 1 }

lcsPortSecurityAgingPeriod OBJECT-TYPE
   SYNTAX      Integer32(10..10000000)
   MAX-ACCESS  read-write
   STATUS      current
   DESCRIPTION
       "default: 3600, range: 10-10000000 "
   ::= { lcsPortSecLimitCtrlSystemConf 2 }

lcsPortSecurityHoldTime OBJECT-TYPE
   SYNTAX      Integer32(10..10000000)
   MAX-ACCESS  read-write
   STATUS      current
   DESCRIPTION
       "default: 300, range: 10-10000000 "
   ::= { lcsPortSecLimitCtrlSystemConf 3 }

lcsPortSecLimitCtrlTable OBJECT-TYPE
   SYNTAX      SEQUENCE OF LCSPortSecLimitCtrlEntry
   MAX-ACCESS  not-accessible
   STATUS      current
   DESCRIPTION
       " "
   ::= { lcsPortSecLimitCtrl 2 }

lcsPortSecLimitCtrlEntry OBJECT-TYPE
   SYNTAX      LCSPortSecLimitCtrlEntry
   MAX-ACCESS  not-accessible
   STATUS      current
   DESCRIPTION
       " "
   INDEX    { lcsPortSecLimitCtrlPort  }
   ::= { lcsPortSecLimitCtrlTable 1 }

LCSPortSecLimitCtrlEntry ::= SEQUENCE {
   lcsPortSecLimitCtrlPort                Integer32,
   lcsPortSecLimitCtrlPortMode            Integer32,
   lcsPortSecLimitCtrlPortLimit           Integer32,
   lcsPortSecLimitCtrlPortViolationmMode  Integer32,
   lcsPortSecLimitCtrlPortViolationmLimit Integer32,
   lcsPortSecLimitCtrlPortState           DisplayString,
   lcsPortSecLimitCtrlPortReOpen          Integer32,
   lcsPortSecLimitCtrlPortSticky          Integer32,
   lcsPortSecLimitCtrlPortClear           Integer32 
}

lcsPortSecLimitCtrlPort OBJECT-TYPE
   SYNTAX      Integer32 (1..65535)
   MAX-ACCESS  not-accessible
   STATUS      current
   DESCRIPTION
       " "
   ::= { lcsPortSecLimitCtrlEntry 1 }

lcsPortSecLimitCtrlPortMode OBJECT-TYPE
   SYNTAX      Integer32 (0|1)
   MAX-ACCESS  read-write
   STATUS      current
   DESCRIPTION
       "default: 0
       0: disable
       1: enable"
   ::= { lcsPortSecLimitCtrlEntry 2 }

lcsPortSecLimitCtrlPortLimit OBJECT-TYPE
   SYNTAX      Integer32(1..1024)
   MAX-ACCESS  read-write
   STATUS      current
   DESCRIPTION
       "default: 4, range: 1-1024"
   ::= { lcsPortSecLimitCtrlEntry 3 }

lcsPortSecLimitCtrlPortViolationmMode OBJECT-TYPE
   SYNTAX      Integer32(0..2)
   MAX-ACCESS  read-write
   STATUS      current
   DESCRIPTION
       "default: 0
       0: Protect
       1: Restrict
       2: Shutdown"
   ::= { lcsPortSecLimitCtrlEntry 4 }

lcsPortSecLimitCtrlPortViolationmLimit OBJECT-TYPE
   SYNTAX      Integer32(1..1024)
   MAX-ACCESS  read-write
   STATUS      current
   DESCRIPTION
       "default: 4, range: 1-1024"
   ::= { lcsPortSecLimitCtrlEntry 5 }
   
   
lcsPortSecLimitCtrlPortState OBJECT-TYPE
   SYNTAX      DisplayString
   MAX-ACCESS  read-only
   STATUS      current
   DESCRIPTION
       " "
   ::= { lcsPortSecLimitCtrlEntry 6 }

lcsPortSecLimitCtrlPortReOpen OBJECT-TYPE
   SYNTAX      Integer32 (0|1)
   MAX-ACCESS  read-write
   STATUS      current
   DESCRIPTION
       "default: 0
       0: none
       1: reopen"
   ::= { lcsPortSecLimitCtrlEntry 7 }  
   
lcsPortSecLimitCtrlPortSticky OBJECT-TYPE
   SYNTAX      Integer32 (0|1)
   MAX-ACCESS  read-write
   STATUS      current
   DESCRIPTION
       "default: 0
       0: disable
       1: enable"
   ::= { lcsPortSecLimitCtrlEntry 8 }

lcsPortSecLimitCtrlPortClear OBJECT-TYPE
   SYNTAX      Integer32 (0|1)
   MAX-ACCESS  read-write
   STATUS      current
   DESCRIPTION
       "default: 0
       1: clear"
   ::= { lcsPortSecLimitCtrlEntry 9 }   
   
   
lcsPortSecSwitchStatusTable OBJECT-TYPE
   SYNTAX      SEQUENCE OF LCSPortSecSwitchStatusEntry
   MAX-ACCESS  not-accessible
   STATUS      current
   DESCRIPTION
       " "
   ::= { lcsPortSecurity 2 }

lcsPortSecSwitchStatusEntry OBJECT-TYPE
   SYNTAX      LCSPortSecSwitchStatusEntry
   MAX-ACCESS  not-accessible
   STATUS      current
   DESCRIPTION
       " "
   INDEX    { lcsPortSecSwitchStatusPort  }
   ::= { lcsPortSecSwitchStatusTable 1 }

LCSPortSecSwitchStatusEntry ::= SEQUENCE {
   lcsPortSecSwitchStatusPort                Integer32,
--   lcsPortSecSwitchStatusUsers               DisplayString,
   lcsPortSecSwitchStatusViolationmMode      DisplayString,
   lcsPortSecSwitchStatusState               DisplayString,
   lcsPortSecSwitchStatusMACCountCurrent     Integer32,
   lcsPortSecSwitchStatusMACCountViolating   Integer32, 
   lcsPortSecSwitchStatusMACCountLimit       Integer32,
   lcsPortSecSwitchStatusClear               Integer32
}

lcsPortSecSwitchStatusPort OBJECT-TYPE
   SYNTAX      Integer32 (1..65535)
   MAX-ACCESS  not-accessible
   STATUS      current
   DESCRIPTION
       " "
   ::= { lcsPortSecSwitchStatusEntry 1 }

-- lcsPortSecSwitchStatusUsers OBJECT-TYPE
--   SYNTAX      DisplayString
--   MAX-ACCESS  read-only
--   STATUS      current
--   DESCRIPTION
--       " Users Abbr: L = Limit Control, 8 = 802.1X, D = DHCP Snooping, V = Voice VLAN,
--         '-' means that the corresponding user module is not enabled. "
--   ::= { lcsPortSecSwitchStatusEntry 2 }
   
lcsPortSecSwitchStatusViolationmMode OBJECT-TYPE
   SYNTAX      DisplayString
   MAX-ACCESS  read-only
   STATUS      current
   DESCRIPTION
       "Shows the configured Violation Mode of the port."
   ::= { lcsPortSecSwitchStatusEntry 3 }

lcsPortSecSwitchStatusState OBJECT-TYPE
   SYNTAX      DisplayString
   MAX-ACCESS  read-only
   STATUS      current
   DESCRIPTION
       " Shows the current state of the port : Disabled, Ready, Limit Reached, Shutdown. "
   ::= { lcsPortSecSwitchStatusEntry 4 }

lcsPortSecSwitchStatusMACCountCurrent OBJECT-TYPE
   SYNTAX      Integer32
   MAX-ACCESS  read-only
   STATUS      current
   DESCRIPTION
       " "
   ::= { lcsPortSecSwitchStatusEntry 5 }
   
lcsPortSecSwitchStatusMACCountViolating OBJECT-TYPE
   SYNTAX      Integer32
   MAX-ACCESS  read-only
   STATUS      current
   DESCRIPTION
       " "
   ::= { lcsPortSecSwitchStatusEntry 6 }   

lcsPortSecSwitchStatusMACCountLimit OBJECT-TYPE
   SYNTAX      Integer32
   MAX-ACCESS  read-only
   STATUS      current
   DESCRIPTION
       " "
   ::= { lcsPortSecSwitchStatusEntry 7 }
   
lcsPortSecSwitchStatusClear OBJECT-TYPE
   SYNTAX      Integer32 (0|1)
   MAX-ACCESS  read-write
   STATUS      current
   DESCRIPTION
       "Remove all MAC addresses on all VLANs on this port."
   ::= { lcsPortSecSwitchStatusEntry 8 }   

lcsPortSecPortStatus                                      OBJECT IDENTIFIER ::= { lcsPortSecurity 3 }

lcsPortSecPortStatusPort OBJECT-TYPE
   SYNTAX       Integer32
   MAX-ACCESS   read-write
   STATUS       current
   DESCRIPTION
       "port number
        default: 1
        range: 1 - port number."
   ::= { lcsPortSecPortStatus 1 }

lcsPortSecPortStatusTable OBJECT-TYPE
   SYNTAX      SEQUENCE OF LCSPortSecPortStatusEntry
   MAX-ACCESS  not-accessible
   STATUS      current
   DESCRIPTION
      " "
   ::= { lcsPortSecPortStatus 2 }

lcsPortSecPortStatusEntry OBJECT-TYPE
   SYNTAX      LCSPortSecPortStatusEntry
   MAX-ACCESS  not-accessible
   STATUS      current
   DESCRIPTION
       " "
   INDEX    { lcsPortSecPortStatusIndex  }
   ::= { lcsPortSecPortStatusTable 1 }

LCSPortSecPortStatusEntry ::= SEQUENCE {
   lcsPortSecPortStatusIndex              Integer32,
   lcsPortSecPortStatusMACAddress         DisplayString,
   lcsPortSecPortStatusVLANId             Integer32,
   lcsPortSecPortStatusState              DisplayString,
   lcsPortSecPortStatusAgeAndHold         DisplayString,
   lcsPortSecPortStatusClear              Integer32
}

lcsPortSecPortStatusIndex OBJECT-TYPE
   SYNTAX      Integer32 (1..65535)
   MAX-ACCESS  not-accessible
   STATUS      current
   DESCRIPTION
       " "
   ::= { lcsPortSecPortStatusEntry 1 }

lcsPortSecPortStatusMACAddress OBJECT-TYPE
   SYNTAX      DisplayString
   MAX-ACCESS  read-only
   STATUS      current
   DESCRIPTION
       "MAC address that is seen on this port."
   ::= { lcsPortSecPortStatusEntry 2 }

lcsPortSecPortStatusVLANId OBJECT-TYPE
   SYNTAX      Integer32(1..4094)
   MAX-ACCESS  read-only
   STATUS      current
   DESCRIPTION
       "VLAN ID that is seen on this port"
   ::= { lcsPortSecPortStatusEntry 3 }

lcsPortSecPortStatusState OBJECT-TYPE
   SYNTAX      DisplayString
   MAX-ACCESS  read-only
   STATUS      current
   DESCRIPTION
       "Indicates whether the corresponding MAC address is violating
       (administrative user has configured the interface in Restrict mode and the MAC address is blocked), 
       blocked, or forwarding."
   ::= { lcsPortSecPortStatusEntry 4 }

lcsPortSecPortStatusAgeAndHold OBJECT-TYPE
   SYNTAX      DisplayString
   MAX-ACCESS  read-only
   STATUS      current
   DESCRIPTION
       " "
   ::= { lcsPortSecPortStatusEntry 5 }

lcsPortSecPortStatusClear OBJECT-TYPE
   SYNTAX      Integer32(0|1)
   MAX-ACCESS  read-write
   STATUS      current
   DESCRIPTION
       "Remove particular MAC addresses from MAC table
       1:clear"
   ::= { lcsPortSecPortStatusEntry 6 }
   
lcsAccessManagement                                      OBJECT IDENTIFIER ::= { lcsSecurity 6 }

lcsAccessMgmtConf                                         OBJECT IDENTIFIER ::= { lcsAccessManagement 1 }

lcsAccessMgmtStatistics                                   OBJECT IDENTIFIER ::= { lcsAccessManagement 2 }
--
-- =======================================================================================================================
-- Start lcsAccessManagement group
-- =======================================================================================================================
--lcsAccessMgmtConf

    lcsAccessMgmtConfMode OBJECT-TYPE
               SYNTAX      AdminMode
               MAX-ACCESS  read-write
               STATUS      current
               DESCRIPTION
                   "Indicates the access management mode operation."
               DEFVAL  { disable }
               ::= {     lcsAccessMgmtConf 1 }

--lcsAccessMgmtConfTable

    lcsAccessMgmtConfTable OBJECT-TYPE
               SYNTAX      SEQUENCE OF     LCSAccessMgmtConfEntry
               MAX-ACCESS  not-accessible
               STATUS      current
               DESCRIPTION
                   "The Access Mgmt Conf Table. "
               ::= {     lcsAccessMgmtConf 2 }

    lcsAccessMgmtConfEntry OBJECT-TYPE
               SYNTAX          LCSAccessMgmtConfEntry
               MAX-ACCESS  not-accessible
               STATUS      current
               DESCRIPTION
                   "The Access Mgmt Conf Entry "
               INDEX    {    lcsAccessMgmtIndex  }
               ::= {     lcsAccessMgmtConfTable 1 }

    LCSAccessMgmtConfEntry             ::= SEQUENCE {
                 lcsAccessMgmtIndex            Integer32,
                 lcsAccessMgmtVlanID           Integer32,
                 lcsAccessMgmtStartIpAddress   IpAddress,
                 lcsAccessMgmtEndIpAddress     IpAddress,
                 lcsAccessMgmtHttpHttps        AdminMode,
                 lcsAccessMgmtSNMP             AdminMode,
                 lcsAccessMgmtTelnetSSH        AdminMode,
                 lcsAccessMgmtRowStatus        RowStatus
                 }

    lcsAccessMgmtIndex OBJECT-TYPE
               SYNTAX      Integer32(1..16)
               MAX-ACCESS  not-accessible
               STATUS      current
               DESCRIPTION
                   "The Access Management config index.
                    range : 1-16."
               ::= {     lcsAccessMgmtConfEntry 1 }

    lcsAccessMgmtVlanID OBJECT-TYPE
               SYNTAX      Integer32 (1..4094)
               MAX-ACCESS  read-create
               STATUS      current
               DESCRIPTION
                   "The VLAN ID for the access management entry.
                    range: 1-4094."
               ::= {     lcsAccessMgmtConfEntry 2 }

    lcsAccessMgmtStartIpAddress OBJECT-TYPE
               SYNTAX      IpAddress
               MAX-ACCESS  read-create
               STATUS      current
               DESCRIPTION
                   "The start IP address for the access management
                    entry."
               ::= {     lcsAccessMgmtConfEntry 3 }

    lcsAccessMgmtEndIpAddress OBJECT-TYPE
               SYNTAX      IpAddress
               MAX-ACCESS  read-create
               STATUS      current
               DESCRIPTION
                   "The end IP address for the access management
                    entry. "
               ::= {     lcsAccessMgmtConfEntry 4 }

    lcsAccessMgmtHttpHttps OBJECT-TYPE
               SYNTAX      AdminMode
               MAX-ACCESS  read-create
               STATUS      current
               DESCRIPTION
                   "Indicates that the host can access the switch from
                    HTTP/HTTPS interface if the host IP address matches the IP
                    address range provided in the entry."
               DEFVAL  { disable }
               ::= {     lcsAccessMgmtConfEntry 5 }

    lcsAccessMgmtSNMP OBJECT-TYPE
               SYNTAX      AdminMode
               MAX-ACCESS  read-create
               STATUS      current
               DESCRIPTION
                   "Indicates that the host can access the switch from SNMP
                    interface if the host IP address matches the IP address
                    range provided in the entry."
               DEFVAL  { disable }
               ::= {     lcsAccessMgmtConfEntry 6 }

    lcsAccessMgmtTelnetSSH OBJECT-TYPE
               SYNTAX      AdminMode
               MAX-ACCESS  read-create
               STATUS      current
               DESCRIPTION
                   "Indicates that the host can access the switch from
                    TELNET/SSH interface if the host IP address matches
                    the IP address range provided in the entry."
               DEFVAL  { disable }
               ::= {     lcsAccessMgmtConfEntry 7 }

    lcsAccessMgmtRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     lcsAccessMgmtConfEntry 8 }

--lcsAccessMgmtStatistics

    lcsAccessMgmtStatisticsClear OBJECT-TYPE
               SYNTAX      ActivateCmd
               MAX-ACCESS  read-write
               STATUS      current
               DESCRIPTION
                   "Clear all statistics."
               ::= {     lcsAccessMgmtStatistics 1 }

--lcsAccessMgmtStatisticsTable

    lcsAccessMgmtStatisticsTable OBJECT-TYPE
               SYNTAX      SEQUENCE OF     LCSAccessMgmtStatisticsEntry
               MAX-ACCESS  not-accessible
               STATUS      current
               DESCRIPTION
                   "The Access Mgmt Statistics Table. "
               ::= {     lcsAccessMgmtStatistics 2 }

    lcsAccessMgmtStatisticsEntry OBJECT-TYPE
               SYNTAX          LCSAccessMgmtStatisticsEntry
               MAX-ACCESS  not-accessible
               STATUS      current
               DESCRIPTION
                   "The Access Mgmt Statistics Entry. "
               INDEX    {    lcsAccessMgmtStatisticsInterface  }
               ::= {     lcsAccessMgmtStatisticsTable 1 }

    LCSAccessMgmtStatisticsEntry ::= SEQUENCE {
                 lcsAccessMgmtStatisticsInterface         INTEGER,
                 lcsAccessMgmtStatisticsReceivedPackets   Integer32,
                 lcsAccessMgmtStatisticsAllowedPackets    Integer32,
                 lcsAccessMgmtStatisticsDiscardedPackets  Integer32
                 }

    lcsAccessMgmtStatisticsInterface OBJECT-TYPE
               SYNTAX      INTEGER { http(1), https(2), snmp(3), telnet(4), ssh (5) }
               MAX-ACCESS  not-accessible
               STATUS      current
               DESCRIPTION
                   "The interface type through which the remote host can
                    access the switch.
                    1: HTTP,
                    2: HTTPs,
                    3: SNMP,
                    4: TELNET,
                    5: SSH"
               ::= {     lcsAccessMgmtStatisticsEntry 1 }

    lcsAccessMgmtStatisticsReceivedPackets OBJECT-TYPE
               SYNTAX      Integer32(1..10000000)
               MAX-ACCESS  read-only
               STATUS      current
               DESCRIPTION
                   "Number of received packets from the interface when
                    access management mode is enabled. "
               ::= {     lcsAccessMgmtStatisticsEntry 2 }

    lcsAccessMgmtStatisticsAllowedPackets OBJECT-TYPE
               SYNTAX      Integer32(1..10000000)
               MAX-ACCESS  read-only
               STATUS      current
               DESCRIPTION
                   "Number of allowed packets from the interface when
                    access management mode is enabled. "
               ::= {     lcsAccessMgmtStatisticsEntry 3 }

    lcsAccessMgmtStatisticsDiscardedPackets OBJECT-TYPE
               SYNTAX      Integer32(1..10000000)
               MAX-ACCESS  read-only
               STATUS      current
               DESCRIPTION
                   "Number of discarded packets from the interface when
                    access management mode is enabled. "
               ::= {     lcsAccessMgmtStatisticsEntry 4 }

-- =======================================================================================================================

--lcsSSH                                                   OBJECT IDENTIFIER ::= { lcsSecurity 7 }
--
--lcsSSHMode OBJECT-TYPE
--   SYNTAX      Integer32(0|1)
--   MAX-ACCESS  read-write
--   STATUS      current
--   DESCRIPTION
--       "default: 1
--        0: disable
--        1: enable"
--   ::= { lcsSSH 1 }

--lcsSSHPort OBJECT-TYPE
--   SYNTAX      Integer32(1..65535)
--   MAX-ACCESS  read-write
--   STATUS      current
--   DESCRIPTION
--       "SSH service port number.
--        range : 1-65535, default : 22."
--   ::= { lcsSSH 2 }

lcsHTTPS                                                 OBJECT IDENTIFIER ::= { lcsSecurity 8 }
--
--lcsHTTPSMode OBJECT-TYPE
--   SYNTAX      Integer32(0|1)
--   MAX-ACCESS  read-write
--   STATUS      current
--   DESCRIPTION
--       "default: 1
--        0: disable
--        1: enable"
--   ::= { lcsHTTPS 1 }
--
--lcsHTTPSAutoRedirect OBJECT-TYPE
--   SYNTAX      Integer32(0|1)
--   MAX-ACCESS  read-write
--   STATUS      current
--   DESCRIPTION
--       "default: 0
--        0: disable
--        1: enable"
--   ::= { lcsHTTPS 2 }
--
--lcsHTTPSPort OBJECT-TYPE
--   SYNTAX      Integer32(1..65535)
--   MAX-ACCESS  read-write
--   STATUS      current
--   DESCRIPTION
--       "HTTPS service port number.
--        range : 1-65535, default : 443."
--   ::= { lcsHTTPS 3 }
--
lcsHTTPSCertificateMaintain OBJECT-TYPE
   SYNTAX      Integer32(2..3)
   MAX-ACCESS  read-write
   STATUS      current
   DESCRIPTION
       "2: Upload
        3: Generate"
   ::= { lcsHTTPS 4 }

lcsHTTPSCertificatePassPhrase OBJECT-TYPE
   SYNTAX      DisplayString
   MAX-ACCESS  read-write
   STATUS      current
   DESCRIPTION
       "Enter the pass phrase in this field if your uploading certificate is protected by a specific passphrase."
   ::= { lcsHTTPS 5 }
   
lcsHTTPSCertificateUpload OBJECT-TYPE
   SYNTAX      Integer32(0|1)
   MAX-ACCESS  read-write
   STATUS      current
   DESCRIPTION
       "default: 0
        0: TFTP
        1: URL"
   ::= { lcsHTTPS 6 }
   
lcsHTTPSFileUploadFileURL OBJECT-TYPE
   SYNTAX      DisplayString
   MAX-ACCESS  read-write
   STATUS      current
   DESCRIPTION
       "TFTP: filename
        URL: URL"
   ::= { lcsHTTPS 7 }
   
lcsHTTPSFileUploadTFTPServer OBJECT-TYPE
   SYNTAX       IpAddress
   MAX-ACCESS   read-write
   STATUS       current
   DESCRIPTION
        "TFTP server IP address"
   ::= { lcsHTTPS 8 }
   
lcsHTTPSApply OBJECT-TYPE
   SYNTAX      Integer32(0|1)
   MAX-ACCESS  read-write
   STATUS      current
   DESCRIPTION
       "1: apply the above https settings"
   ::= { lcsHTTPS 9 }
   
lcsHTTPSCertificateStatus OBJECT-TYPE
   SYNTAX      DisplayString
   MAX-ACCESS  read-only
   STATUS      current
   DESCRIPTION
       "Display the current status of certificate on the switch."
   ::= { lcsHTTPS 10 }   
   
lcsAuthMethod                                            OBJECT IDENTIFIER ::= { lcsSecurity 9 }

--
-- =======================================================================================================================
-- Start lcsAuthMethodConfig group
-- =======================================================================================================================
--lcsAuthMethodConfigTable

    lcsAuthMethodConfigTable OBJECT-TYPE
               SYNTAX      SEQUENCE OF     LCSAuthMethodConfigEntry
               MAX-ACCESS  not-accessible
               STATUS      current
               DESCRIPTION
                   "The Auth Method Config Table."
               ::= {     lcsAuthMethod 1 }

    lcsAuthMethodConfigEntry OBJECT-TYPE
               SYNTAX          LCSAuthMethodConfigEntry
               MAX-ACCESS  not-accessible
               STATUS      current
               DESCRIPTION
                   "The Auth Method Config Entry."
               INDEX    {    lcsAuthMethodConfigClient  }
               ::= {     lcsAuthMethodConfigTable 1 }

    LCSAuthMethodConfigEntry             ::= SEQUENCE {
                 lcsAuthMethodConfigClient        INTEGER,
                 lcsAuthMethodConfigMethod1       INTEGER,
                 lcsAuthMethodConfigMethod2       INTEGER,
                 lcsAuthMethodConfigMethod3       INTEGER,
                 lcsAuthMethodConfigMethod4       INTEGER,
                 lcsAuthMethodConfigServicePort   Integer32
                 }

    lcsAuthMethodConfigClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     lcsAuthMethodConfigEntry 1 }

    lcsAuthMethodConfigMethod1 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     lcsAuthMethodConfigEntry 2 }

    lcsAuthMethodConfigMethod2 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     lcsAuthMethodConfigEntry 3 }

    lcsAuthMethodConfigMethod3 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     lcsAuthMethodConfigEntry 4 }
               
    lcsAuthMethodConfigMethod4 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     lcsAuthMethodConfigEntry 5 }

    lcsAuthMethodConfigServicePort OBJECT-TYPE
               SYNTAX      Integer32 (1..65535)
               MAX-ACCESS  read-write
               STATUS      current
               DESCRIPTION
                   "The network port number this client bound to provide service."
               ::= {     lcsAuthMethodConfigEntry 6 }               
               
    lcsCommandAuthorizationMethodTable OBJECT-TYPE
               SYNTAX      SEQUENCE OF     LCSCommandAuthorizationMethodEntry
               MAX-ACCESS  not-accessible
               STATUS      current
               DESCRIPTION
                   "The Command Authorized Method Config Table."
               ::= {     lcsAuthMethod 2 }

    lcsCommandAuthorizationMethodEntry OBJECT-TYPE
               SYNTAX          LCSCommandAuthorizationMethodEntry
               MAX-ACCESS  not-accessible
               STATUS      current
               DESCRIPTION
                   "The Command Authorized Method Config Entry."
               INDEX    {    lcsCommandAuthorizationMethodClient  }
               ::= {     lcsCommandAuthorizationMethodTable 1 }

    LCSCommandAuthorizationMethodEntry             ::= SEQUENCE {
                 lcsCommandAuthorizationMethodClient       INTEGER,
                 lcsCommandAuthorizationMethodMethod       Integer32,
                 lcsCommandAuthorizationMethodCmdLvl       Integer32,
                 lcsCommandAuthorizationMethodCfgCmd       Integer32
                 }

    lcsCommandAuthorizationMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     lcsCommandAuthorizationMethodEntry 1 }

    lcsCommandAuthorizationMethodMethod OBJECT-TYPE
               SYNTAX      Integer32
               MAX-ACCESS  read-write
               STATUS      current
               DESCRIPTION
                   "Method can be set to one of the following values:
                    0:no: Command authorization is disabled. 
                      User is granted access to CLI commands according to his privilege level.
                    4:tacacs: Use remote TACACS+ server(s) for command authorization. 
                      If all remote servers are offline, the user is granted access to CLI commands
                      according to his privilege level."
               ::= {     lcsCommandAuthorizationMethodEntry 2 }

    lcsCommandAuthorizationMethodCmdLvl OBJECT-TYPE
               SYNTAX      Integer32
               MAX-ACCESS  read-write
               STATUS      current
               DESCRIPTION
                   "Authorize all commands with a privilege level higher than or equal to this level.
                    Valid values are in the range 0 to 15."
               ::= {     lcsCommandAuthorizationMethodEntry 3 }

    lcsCommandAuthorizationMethodCfgCmd OBJECT-TYPE
               SYNTAX      Integer32
               MAX-ACCESS  read-write
               STATUS      current
               DESCRIPTION
                   "Also authorize configuration commands.
                   0:Disable
                   1:Enable"
               ::= {     lcsCommandAuthorizationMethodEntry 4 }

               
    lcsAccountingMethodTable OBJECT-TYPE
               SYNTAX      SEQUENCE OF     LCSAccountingMethodEntry
               MAX-ACCESS  not-accessible
               STATUS      current
               DESCRIPTION
                   "The Accounting Method Config Table."
               ::= {     lcsAuthMethod 3 }

    lcsAccountingMethodEntry OBJECT-TYPE
               SYNTAX          LCSAccountingMethodEntry
               MAX-ACCESS  not-accessible
               STATUS      current
               DESCRIPTION
                   "The Accounting Method Config Entry."
               INDEX    {    lcsAccountingMethodClient  }
               ::= {     lcsAccountingMethodTable 1 }

    LCSAccountingMethodEntry             ::= SEQUENCE {
                 lcsAccountingMethodClient       INTEGER,
                 lcsAccountingMethodMethod       Integer32,
                 lcsAccountingMethodCmdLvl       Integer32,
                 lcsAccountingMethodCfgCmd       Integer32
                 }

    lcsAccountingMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     lcsAccountingMethodEntry 1 }

    lcsAccountingMethodMethod OBJECT-TYPE
               SYNTAX      Integer32
               MAX-ACCESS  read-write
               STATUS      current
               DESCRIPTION
                   "Method can be set to one of the following values:
                    0:no: Accounting is disabled.
                    4:tacacs: Use remote TACACS+ server(s) for accounting."
               ::= {     lcsAccountingMethodEntry 2 }

    lcsAccountingMethodCmdLvl OBJECT-TYPE
               SYNTAX      Integer32
               MAX-ACCESS  read-write
               STATUS      current
               DESCRIPTION
                   "Enable accounting of all commands with a privilege level higher than or equal to this level.
                    Valid values are in the range 0 to 15. Leave the field empty to disable command accounting."
               ::= {     lcsAccountingMethodEntry 3 }

    lcsAccountingMethodCfgCmd OBJECT-TYPE
               SYNTAX      Integer32
               MAX-ACCESS  read-write
               STATUS      current
               DESCRIPTION
                   "Enable exec (login) accounting.
                   0:Disable
                   1:Enable"
               ::= {     lcsAccountingMethodEntry 4 }              
               
-- lcsTELNET                                                 OBJECT IDENTIFIER ::= { lcsSecurity 10 }

-- lcsTELNETPort OBJECT-TYPE
--   SYNTAX      Integer32(1..65535)
--   MAX-ACCESS  read-write
--   STATUS      current
--   DESCRIPTION
--       "TELNET service port number.
--        range : 1-65535, default : 23."
--   ::= { lcsTELNET 1 }

lcsDot1xSupplicant OBJECT IDENTIFIER ::= { lcsSecurity 1500 }

lcsDot1xSupplicantSystemMode OBJECT-TYPE
    SYNTAX      INTEGER { disable(0), enable(1) }
    MAX-ACCESS  read-write
    STATUS      current
    DESCRIPTION
        "Global 802.1X Supplicant Enable / Disable Mode"
    ::= { lcsDot1xSupplicant 1 }

lcsDot1xSupplicantSystemEapMethods OBJECT-TYPE
    SYNTAX      BITS { lcsDot1xSupplicantSystemEapMethodsAll(0), -- All supported Methods
                       lcsDot1xSupplicantSystemEapMethodsMD5(1), -- EAP-MD5
                       lcsDot1xSupplicantSystemEapMethodsPSK(2), -- EAP-PSK
                       lcsDot1xSupplicantSystemEapMethodsPWD(3)  -- EAP-PWD
                     }
    MAX-ACCESS  read-write
    STATUS      current
    DESCRIPTION
        "EAP Methods which will be support in communication with the EAP Authenticator."
    ::= { lcsDot1xSupplicant 2 }

lcsDot1xSupplicantTable OBJECT-TYPE
    SYNTAX      SEQUENCE OF LCSDot1xSupplicantEntry
    MAX-ACCESS  not-accessible
    STATUS      current
    DESCRIPTION
        "Table of all available supplicants and their configuration and status"
    ::= { lcsDot1xSupplicant 3 }

lcsDot1xSupplicantEntry OBJECT-TYPE
    SYNTAX      LCSDot1xSupplicantEntry
    MAX-ACCESS  not-accessible
    STATUS      current
    DESCRIPTION
        "Configuration and status for a supplicant"
    INDEX       { lcsDot1xSupplicantIndex }
    ::= { lcsDot1xSupplicantTable 1 }

LCSDot1xSupplicantEntry ::=
    SEQUENCE {
        lcsDot1xSupplicantIndex             Integer32,
        lcsDot1xSupplicantPortNumber        Integer32,
        lcsDot1xSupplicantConfigMode        INTEGER,
        lcsDot1xSupplicantConfigUsername    DisplayString,
        lcsDot1xSupplicantConfigPassword    DisplayString,
        lcsDot1xSupplicantStatusActive      INTEGER,
        lcsDot1xSupplicantStatusAuthorized  INTEGER,
        lcsDot1xSupplicantStatusLink        INTEGER,
        lcsDot1xSupplicantStatusLogoff      INTEGER,
        lcsDot1xSupplicantStatusString      DisplayString,
        lcsDot1xSupplicantStatusResult      INTEGER
    }

lcsDot1xSupplicantIndex OBJECT-TYPE
    SYNTAX      Integer32(1..5)
    MAX-ACCESS  not-accessible
    STATUS      current
    DESCRIPTION
        "Index of the supplicant, 1-5"
    ::= { lcsDot1xSupplicantEntry 1 }

lcsDot1xSupplicantPortNumber OBJECT-TYPE
    SYNTAX      Integer32(0..52)
    MAX-ACCESS  read-write
    STATUS      current
    DESCRIPTION
        "Port on which the supplicant operates.
         Port 0 is equivalent to lcsDot1xSupplicantConfigMode disable."
    ::= { lcsDot1xSupplicantEntry 2 }

lcsDot1xSupplicantConfigMode OBJECT-TYPE
    SYNTAX      INTEGER { disable(0), enable(1) }
    MAX-ACCESS  read-write
    STATUS      current
    DESCRIPTION
        "Configured mode of the supplicant"
    ::= { lcsDot1xSupplicantEntry 3 }

lcsDot1xSupplicantConfigUsername OBJECT-TYPE
    SYNTAX      DisplayString
    MAX-ACCESS  read-write
    STATUS      current
    DESCRIPTION
        "Username the supplicant should use for authentication"
    ::= { lcsDot1xSupplicantEntry 4 }

lcsDot1xSupplicantConfigPassword OBJECT-TYPE
    SYNTAX      DisplayString
    MAX-ACCESS  read-write
    STATUS      current
    DESCRIPTION
        "Password the supplicant should use for authentication.
         Only reads '********' for a set password and '' (empty)
         for unset password."
    ::= { lcsDot1xSupplicantEntry 5 }

lcsDot1xSupplicantStatusActive OBJECT-TYPE
    SYNTAX      INTEGER { inactive(0), active(1) }
    MAX-ACCESS  read-only
    STATUS      current
    DESCRIPTION
        "Operating status of the supplicant"
    ::= { lcsDot1xSupplicantEntry 6 }

lcsDot1xSupplicantStatusAuthorized OBJECT-TYPE
    SYNTAX      INTEGER { unauthorized(0), authorized(1) }
    MAX-ACCESS  read-only
    STATUS      current
    DESCRIPTION
        "Authorized status of the supplicant"
    ::= { lcsDot1xSupplicantEntry 7 }

lcsDot1xSupplicantStatusLink OBJECT-TYPE
    SYNTAX      INTEGER { down(0), up(1) }
    MAX-ACCESS  read-only
    STATUS      current
    DESCRIPTION
        "Link status of port of the supplicant"
    ::= { lcsDot1xSupplicantEntry 8 }

lcsDot1xSupplicantStatusLogoff OBJECT-TYPE
    SYNTAX      INTEGER { no(0), yes(1) }
    MAX-ACCESS  read-only
    STATUS      current
    DESCRIPTION
        "If the supplicant did logoff from the authenticator"
    ::= { lcsDot1xSupplicantEntry 9 }

lcsDot1xSupplicantStatusString OBJECT-TYPE
    SYNTAX      DisplayString
    MAX-ACCESS  read-only
    STATUS      current
    DESCRIPTION
        "Last status message of the supplicant"
    ::= { lcsDot1xSupplicantEntry 10 }

lcsDot1xSupplicantStatusResult OBJECT-TYPE
    SYNTAX      INTEGER { unknown(0), failure(1), success(2), expectedFailure(3) }
    MAX-ACCESS  read-only
    STATUS      current
    DESCRIPTION
        "Result from the supplicant, unknown if authentication was not yet completed"
    ::= { lcsDot1xSupplicantEntry 11 }

lcsDot1xSupplicantSystemMacMode OBJECT-TYPE
    SYNTAX      INTEGER { port(0), system(1) }
    MAX-ACCESS  read-write
    STATUS      current
    DESCRIPTION
        "Use the system mac or separate port mac during authentication"
    ::= { lcsDot1xSupplicant 4 }


-- =======================================================================================================================
lcsMaintenance                                           OBJECT IDENTIFIER ::= { lcosSX 4 }

lcsSoftware                      OBJECT IDENTIFIER   ::= {  lcsMaintenance 3 }
lcsConfig                        OBJECT IDENTIFIER   ::= {  lcsMaintenance 4 }

--
-- =======================================================================================================================
-- Objects in the lcsMaintenance Group
-- =======================================================================================================================
    lcsRestartDevice OBJECT-TYPE
               SYNTAX      ActivateCmd
               MAX-ACCESS  read-write
               STATUS      current
               DESCRIPTION
                   "Command to restart the device."
               DEFVAL  { noAction }
               ::= {     lcsMaintenance 1 }

    lcsFactoryDefaults OBJECT-TYPE
               SYNTAX      ActivateCmd
               MAX-ACCESS  read-write
               STATUS      current
               DESCRIPTION
                   "Reset the configuration to Factory Defaults keep-ip."
               DEFVAL  { noAction }
               ::= {     lcsMaintenance 2 }

--lcsSoftware

    lcsSoftwareUsername OBJECT-TYPE
               SYNTAX       DisplayString
               MAX-ACCESS   read-write
               STATUS       current
               DESCRIPTION
                    "Get/Set the username for 'tftp' firmware upgrading."
               ::= {     lcsSoftware 1 }

    lcsSoftwarePassword OBJECT-TYPE
               SYNTAX       DisplayString
               MAX-ACCESS   read-write
               STATUS       current
               DESCRIPTION
                    "Get/Set the password for 'tftp' firmware upgrading."
               ::= {     lcsSoftware 2 }

    lcsSoftwareIpAddress OBJECT-TYPE
               SYNTAX       IpAddress
               MAX-ACCESS   read-write
               STATUS       current
               DESCRIPTION
                    "Get/Set the firmware tftp server."
               ::= {     lcsSoftware 3 }

    lcsSoftwareFileName OBJECT-TYPE
               SYNTAX       DisplayString
               MAX-ACCESS   read-write
               STATUS       current
               DESCRIPTION
                    "Get/Set the path and filename for firmware upgrading."
               ::= {     lcsSoftware 4 }

    lcsSoftwareUpgradeCmd OBJECT-TYPE
               SYNTAX       INTEGER  {  noAction ( 0 ),
                                        tftpUpgrade ( 1 ),
                                        ftpUpgrade ( 2 )
                                     }
               MAX-ACCESS   read-write
               STATUS       current
               DESCRIPTION
                    "Firmware upgrade command.
                     noAction(0 )- do nothing   (read only).
                     tftpUpgrade (1) - activate 'tftp' firmware upgrade"

               DEFVAL  { noAction }
               ::= {     lcsSoftware 5 }

    lcsSoftwareImageSelectionCmd OBJECT-TYPE
               SYNTAX       ActivateCmd
               MAX-ACCESS   read-write
               STATUS       current
               DESCRIPTION
                    "Activate firmware image selection.
                     noAction(0) - do nothing - returned upon get.
                     activate(1) - activate firmware image selection."
               DEFVAL  { noAction }
               ::= {     lcsSoftware 6 }

    lcsSaveStartCmd OBJECT-TYPE
               SYNTAX      ActivateCmd
               MAX-ACCESS  read-write
               STATUS      current
               DESCRIPTION
                   "This copies running-config to startup-config,
                   thereby ensuring that the currently active
                   configuration will be used at the next reboot. "
               DEFVAL  { noAction }
               ::= {     lcsConfig 1 }

    lcsConfigUsername OBJECT-TYPE
               SYNTAX       DisplayString
               MAX-ACCESS   read-write
               STATUS       current
               DESCRIPTION
                    "Get/Set the username for 'tftp' 'upload config' or 'download config'."
               ::= {     lcsConfig 2 }

    lcsConfigPassword OBJECT-TYPE
               SYNTAX       DisplayString
               MAX-ACCESS   read-write
               STATUS       current
               DESCRIPTION
                    "Get/Set the password for 'tftp' 'upload config' or 'download config'."
               ::= {     lcsConfig 3 }

    lcsConfigIpAddress OBJECT-TYPE
               SYNTAX       IpAddress
               MAX-ACCESS   read-write
               STATUS       current
               DESCRIPTION
                    "Get/Set the IP address for 'tftp' 'upload config'
                    or 'download config'."
               ::= {     lcsConfig 4 }

    lcsConfigFilename OBJECT-TYPE
               SYNTAX       DisplayString
               MAX-ACCESS   read-write
               STATUS       current
               DESCRIPTION
                    "Get/Set the filename in switch for 'tftp'
                    'upload config' or 'download config'."
               ::= {     lcsConfig 5 }

    lcsConfigFileTable OBJECT-TYPE
               SYNTAX      SEQUENCE OF     LCSConfigFileEntry
               MAX-ACCESS  not-accessible
               STATUS      current
               DESCRIPTION
                   "The config file tabe."
               ::= {     lcsConfig 6 }

    lcsConfigFileEntry OBJECT-TYPE
               SYNTAX          LCSConfigFileEntry
               MAX-ACCESS  not-accessible
               STATUS      current
               DESCRIPTION
                   "an entry in the config file tabe."
               INDEX    {     lcsConfigFileIndex }
               ::= {     lcsConfigFileTable 1 }

    LCSConfigFileEntry             ::= SEQUENCE {
                lcsConfigFileIndex         Integer32,
                lcsShowConfigFileName      DisplayString,
                lcsActivateConfigCmd       ActivateCmd,
                lcsDeleteConfigCmd         ActivateCmd,
                lcsUploadConfigCmd         INTEGER,
                lcsDownloadConfigCmd       INTEGER
                }

    lcsConfigFileIndex OBJECT-TYPE
               SYNTAX      Integer32(1..255)
               MAX-ACCESS  not-accessible
               STATUS      current
               DESCRIPTION
                   "The config file index."
               ::= {     lcsConfigFileEntry 1 }

    lcsShowConfigFileName OBJECT-TYPE
               SYNTAX      DisplayString
               MAX-ACCESS  read-write
               STATUS      current
               DESCRIPTION
                   "Shows the config file name. Without config filename:'NewConfig'
                   is temp file when 'activate download
                   config' can 'create new file' and 'change create filename'."
               ::= {     lcsConfigFileEntry 2 }

    lcsActivateConfigCmd OBJECT-TYPE
               SYNTAX       ActivateCmd
               MAX-ACCESS   read-write
               STATUS       current
               DESCRIPTION
                    "Activate config command.
                     noAction(0) : do nothing  (read only).
                     activate(1) : activate the config"
               DEFVAL  { noAction }
               ::= {     lcsConfigFileEntry 3 }

    lcsDeleteConfigCmd OBJECT-TYPE
               SYNTAX       ActivateCmd
               MAX-ACCESS   read-write
               STATUS       current
               DESCRIPTION
                    "Delete config command.
                     noAction(0) : do nothing  (read only).
                     activate(1) : delete the config"
               DEFVAL  { noAction }
               ::= {     lcsConfigFileEntry 4 }

    lcsDownloadConfigCmd OBJECT-TYPE
               SYNTAX       INTEGER  {  noAction ( 0 ),
                                        tftpUpload ( 1 )
                                        --ftpUpload ( 2 )
                                     }
               MAX-ACCESS   read-write
               STATUS       current
               DESCRIPTION
                    "Download config command.
                     noAction   (0) - do nothing   (read only).
                     tftpUpload (1) - activate 'tftp' config download."
               DEFVAL  { noAction }
               ::= {     lcsConfigFileEntry 5 }

    lcsUploadConfigCmd OBJECT-TYPE
               SYNTAX       INTEGER  {  noAction ( 0 ),
                                        tftpDownload ( 1 )
                                        --ftpDownload ( 2 )
                                     }
               MAX-ACCESS   read-write
               STATUS       current
               DESCRIPTION
                    "Upload config command.
                     noAction   (0) - do nothing   (read only).
                     tftpDownload (1) - activate 'tftp' config upload.
                     For merge/replace running-config:
                     1:merge
                     3:replace"                  
               DEFVAL  { noAction }
               ::= {     lcsConfigFileEntry 6 }

-- =======================================================================================================================
lcsDiagnostics                                           OBJECT IDENTIFIER ::= { lcsMaintenance 5 }

lcsPingIpAddress OBJECT-TYPE
   SYNTAX      IpAddress
   MAX-ACCESS  read-write
   STATUS      current
   DESCRIPTION
       " The destination IP Address. "
   ::= { lcsDiagnostics 1 }

lcsPingSize OBJECT-TYPE
   SYNTAX      Integer32(60..1400)
   MAX-ACCESS  read-write
   STATUS      current
   DESCRIPTION
       " Size of ICMP echo packet.
         range : 60-1400, default : 64. "
   ::= { lcsDiagnostics 2 }

lcsDoPingConfig OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { lcsDiagnostics 3 }

lcsPingResult OBJECT-TYPE
   SYNTAX      DisplayString
   MAX-ACCESS  read-only
   STATUS      current
   DESCRIPTION
       " Show ping result. "
   ::= { lcsDiagnostics 4 }

lcsPing6IpAddress OBJECT-TYPE
   SYNTAX      DisplayString
   MAX-ACCESS  read-write
   STATUS      current
   DESCRIPTION
       " The destination IPv6 Address. "
   ::= { lcsDiagnostics 5 }

lcsPing6Size OBJECT-TYPE
   SYNTAX      Integer32(60..1400)
   MAX-ACCESS  read-write
   STATUS      current
   DESCRIPTION
       " Size of ICMP echo packet.
         range : 60-1400. "
   ::= { lcsDiagnostics 6 }

lcsPing6EgressInterface OBJECT-TYPE
   SYNTAX      Integer32(1..4094)
   MAX-ACCESS  read-write
   STATUS      current
   DESCRIPTION
       "The VLAN ID (VID) of the specific egress IPv6 interface which ICMP packet goes."
   ::= { lcsDiagnostics 7 }
   
lcsDoPing6Config OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { lcsDiagnostics 8 }

lcsPing6Result OBJECT-TYPE
   SYNTAX      DisplayString
   MAX-ACCESS  read-only
   STATUS      current
   DESCRIPTION
       " Show ping result. "
   ::= { lcsDiagnostics 9 }

lcstracerouteIpAddress OBJECT-TYPE
   SYNTAX      IpAddress
   MAX-ACCESS  read-write
   STATUS      current
   DESCRIPTION
       " The destination IP Address. "
   ::= { lcsDiagnostics 10 }

--lcstracerouteProtocol OBJECT-TYPE
--   SYNTAX      Integer32(0..2)
--   MAX-ACCESS  read-write
--   STATUS      current
--   DESCRIPTION
--       " Specify protocol including icmp=0, udp=1 and tcp=2.
--         range : 0-2, default : 0. "
--   ::= { lcsDiagnostics 11 }

lcstracerouteWaittime OBJECT-TYPE
   SYNTAX      Integer32(1..60)
   MAX-ACCESS  read-write
   STATUS      current
   DESCRIPTION
       " Specify wait time for waiting probe packets come back.
         range : 1-60(sec), default : 5(sec). "
   ::= { lcsDiagnostics 12 }

lcstracerouteMaxTTL OBJECT-TYPE
   SYNTAX      Integer32(1..255)
   MAX-ACCESS  read-write
   STATUS      current
   DESCRIPTION
       " Specify max TTL.
         range : 1-255, default : 30. "
   ::= { lcsDiagnostics 13 }

lcstracerouteNqueries OBJECT-TYPE
   SYNTAX      Integer32(1..10)
   MAX-ACCESS  read-write
   STATUS      current
   DESCRIPTION
       " Specify number of probe packets.
         range : 1-10, default : 3. "
   ::= { lcsDiagnostics 14 }

lcsDotracerouteConfig OBJECT-TYPE
   SYNTAX      Integer32(1)
   MAX-ACCESS  read-write
   STATUS      current
   DESCRIPTION
       "Do traceroute-config.
         Get this OID always return zero.
         1 - ping. Uses the traceroute program to get
         ip address of the middle gateway. "
   ::= { lcsDiagnostics 15 }

lcstracerouteResult OBJECT-TYPE
   SYNTAX      DisplayString
   MAX-ACCESS  read-only
   STATUS      current
   DESCRIPTION
       " Show traceroute result. "
   ::= { lcsDiagnostics 16 }

lcsCableDiagnostics                                           OBJECT IDENTIFIER ::= { lcsDiagnostics 17 }

lcsCableDiagnosticsTest OBJECT-TYPE
   SYNTAX      Integer32
   MAX-ACCESS  read-write
   STATUS      current
   DESCRIPTION
       "Run Cable Diagnostics.
        port, range : 1 - port number."
   ::= { lcsCableDiagnostics 1 }

lcsCableDiagnosticsTable OBJECT-TYPE
   SYNTAX      SEQUENCE OF LCSCableDiagnosticsEntry
   MAX-ACCESS  not-accessible
   STATUS      current
   DESCRIPTION
       " "
   ::= { lcsCableDiagnostics 2 }

lcsCableDiagnosticsEntry OBJECT-TYPE
   SYNTAX      LCSCableDiagnosticsEntry
   MAX-ACCESS  not-accessible
   STATUS      current
   DESCRIPTION
       " "
   INDEX    { lcsCableDiagnosticsPort  }
   ::= { lcsCableDiagnosticsTable 1 }

LCSCableDiagnosticsEntry ::= SEQUENCE {
   lcsCableDiagnosticsPort        Integer32,
   lcsCableDiagnosticsLinkStatus  DisplayString,
   lcsCableDiagnosticsTestResult  DisplayString,
   lcsCableDiagnosticsLength      DisplayString
}

lcsCableDiagnosticsPort OBJECT-TYPE
   SYNTAX      Integer32 (1..52)
   MAX-ACCESS  not-accessible
   STATUS      current
   DESCRIPTION
       "port index"
   ::= { lcsCableDiagnosticsEntry 1 }

lcsCableDiagnosticsLinkStatus OBJECT-TYPE
   SYNTAX      DisplayString
   MAX-ACCESS  read-only
   STATUS      current
   DESCRIPTION
       "The status of the cable."
   ::= { lcsCableDiagnosticsEntry 2 }

lcsCableDiagnosticsTestResult OBJECT-TYPE
   SYNTAX      DisplayString
   MAX-ACCESS  read-only
   STATUS      current
   DESCRIPTION
       "Test Result of the cable."
   ::= { lcsCableDiagnosticsEntry 3 }

lcsCableDiagnosticsLength OBJECT-TYPE
   SYNTAX      DisplayString
   MAX-ACCESS  read-only
   STATUS      current
   DESCRIPTION
       "The length (in meters) of the cable."
   ::= { lcsCableDiagnosticsEntry 4 }

lcsSwitchRebootSchedule OBJECT IDENTIFIER ::= { lcsMaintenance 6 }   

lcsSwitchRebootMode OBJECT-TYPE
   SYNTAX      Integer32
   MAX-ACCESS  read-write
   STATUS      current
   DESCRIPTION
       "Switch Reboot Mode.
        0:disable
        1:enable"
   ::= { lcsSwitchRebootSchedule 1 }

lcsSwitchRebootTimeTable OBJECT-TYPE
   SYNTAX      SEQUENCE OF LCSSwitchRebootTimeEntry
   MAX-ACCESS  not-accessible
   STATUS      current
   DESCRIPTION
       " Configure the Switch reboot time. "
   ::= { lcsSwitchRebootSchedule 2 }

lcsSwitchRebootTimeEntry OBJECT-TYPE
   SYNTAX      LCSSwitchRebootTimeEntry
   MAX-ACCESS  not-accessible
   STATUS      current
   DESCRIPTION
       " "
   INDEX    { lcsSwitchRebootWeekIndex  }
   ::= { lcsSwitchRebootTimeTable 1 }

LCSSwitchRebootTimeEntry ::= SEQUENCE {
   lcsSwitchRebootWeekIndex        Integer32,
   lcsSwitchRebootTimeHour           Integer32,
   lcsSwitchRebootTimeMinute         Integer32
}

lcsSwitchRebootWeekIndex OBJECT-TYPE
   SYNTAX      Integer32 (1..7)
   MAX-ACCESS  not-accessible
   STATUS      current
   DESCRIPTION
       "Switch reboot week index.
       1: Sun, 2: Mon, 3:Tue, 4: Wed, 5: Thu, 6: Fri, 7: Sat"
   ::= { lcsSwitchRebootTimeEntry 1 }

lcsSwitchRebootTimeHour OBJECT-TYPE
   SYNTAX      Integer32 (-1..23)
   MAX-ACCESS  read-write
   STATUS      current
   DESCRIPTION
       "Switch Reboot Time (Hour). Range: 0-23. 
       -1:disable"
   ::= { lcsSwitchRebootTimeEntry 2 }

lcsSwitchRebootTimeMinute OBJECT-TYPE
   SYNTAX      Integer32 (-1..55)
   MAX-ACCESS  read-write
   STATUS      current
   DESCRIPTION
       "Switch Reboot Time (Minute). Range:0,5,10,...,55. 
       -1:disable"
   ::= { lcsSwitchRebootTimeEntry 3 }    

lcsiPerf OBJECT IDENTIFIER ::= { lcsMaintenance 7 }   

lcsiPerfMethod OBJECT-TYPE
   SYNTAX      Integer32
   MAX-ACCESS  read-write
   STATUS      current
   DESCRIPTION
       "The measuring method of iPerf.
        2:iPerf version 2
        3:iPerf version 3"
   ::= { lcsiPerf 2 }   
   
lcsiPerfHost OBJECT-TYPE
   SYNTAX      IpAddress
   MAX-ACCESS  read-write
   STATUS      current
   DESCRIPTION
       "The address of iPerf server. "
   ::= { lcsiPerf 3 }
   
lcsiPerfPort OBJECT-TYPE
   SYNTAX      Integer32
   MAX-ACCESS  read-write
   STATUS      current
   DESCRIPTION
       "The listen port of iPerf server. The default value is 5001 for iPerf, 5201 for iPerf3. "
   ::= { lcsiPerf 4 }  

lcsiPerfTime OBJECT-TYPE
   SYNTAX      Integer32
   MAX-ACCESS  read-write
   STATUS      current
   DESCRIPTION
       "The time in seconds to transmit for (default 10 secs). "
   ::= { lcsiPerf 5 }     
  
lcsiPerfInterval OBJECT-TYPE
   SYNTAX      Integer32
   MAX-ACCESS  read-write
   STATUS      current
   DESCRIPTION
       "The time in seconds between periodic bandwidth reports (default no periodic reports). "
   ::= { lcsiPerf 6 }    
   
lcsiPerfTTL OBJECT-TYPE
   SYNTAX      Integer32
   MAX-ACCESS  read-write
   STATUS      current
   DESCRIPTION
       "The time-to-live, for multicast (default 1). "
   ::= { lcsiPerf 7 }       
   
lcsiPerfStart OBJECT-TYPE
   SYNTAX      Integer32
   MAX-ACCESS  read-write
   STATUS      current
   DESCRIPTION
       "Start iPerf
       1:Start."
   ::= { lcsiPerf 8 } 
   
lcsiPerfResult OBJECT-TYPE
   SYNTAX      DisplayString
   MAX-ACCESS  read-only
   STATUS      current
   DESCRIPTION
       "Test result of iPerf"
   ::= { lcsiPerf 9 }
   
-- =======================================================================================================================
lcsTrap                                                  OBJECT IDENTIFIER ::= { lcosSX 5 }

lcsTrapEvent                                             OBJECT IDENTIFIER ::= { lcsTrap 1 }

lcsEmergency NOTIFICATION-TYPE
  OBJECTS   { lcsInformation }
  STATUS        current
    DESCRIPTION
        "The severity level is Emergency. Emergency conditions."
    ::= { lcsTrapEvent 1 }

lcsAlert NOTIFICATION-TYPE
  OBJECTS   { lcsInformation }
  STATUS        current
    DESCRIPTION
        "The severity level is Alert. Alert conditions."
    ::= { lcsTrapEvent 2 }

lcsCritical NOTIFICATION-TYPE
  OBJECTS   { lcsInformation }
  STATUS        current
    DESCRIPTION
        "The severity level is Critical. Critical conditions."
    ::= { lcsTrapEvent 3 }

lcsError NOTIFICATION-TYPE
  OBJECTS   { lcsInformation }
  STATUS        current
    DESCRIPTION
        "The severity level is Error. Error conditions."
    ::= { lcsTrapEvent 4 }

lcsWarning NOTIFICATION-TYPE
  OBJECTS   { lcsInformation }
  STATUS        current
    DESCRIPTION
        "The severity level is Warning. Warning conditions."
    ::= { lcsTrapEvent 5 }

lcsNotice NOTIFICATION-TYPE
  OBJECTS   { lcsInformation }
  STATUS        current
    DESCRIPTION
        "The severity level is Notice. Notice conditions."
    ::= { lcsTrapEvent 6 }

lcsInformational NOTIFICATION-TYPE
  OBJECTS   { lcsInformation }
  STATUS        current
    DESCRIPTION
        "The severity level is Informational. Informational conditions."
    ::= { lcsTrapEvent 7 }

lcsDebug NOTIFICATION-TYPE
  OBJECTS   { lcsInformation }
  STATUS        current
    DESCRIPTION
        "The severity level is Debug. Debug conditions."
    ::= { lcsTrapEvent 8 }

lcsTrapVariable                                          OBJECT IDENTIFIER ::= { lcsTrap 2 }

lcsInformation OBJECT-TYPE
    SYNTAX      DisplayString
    MAX-ACCESS  read-only
    STATUS      current
    DESCRIPTION
        "Trap information."
    ::= { lcsTrapVariable 1 }

lcsMacTrap                  OBJECT IDENTIFIER ::= { lcsTrap 100 }

lcsMacTrapEvent             OBJECT IDENTIFIER ::= { lcsMacTrap 1 }

lcsMacTrapAddNotification NOTIFICATION-TYPE
    OBJECTS     { dot1qTpFdbAddress,
                  dot1qFdbId,
                  dot1qTpFdbPort
                }
    STATUS      current
    DESCRIPTION
        "Event generated for a new learned mac address.
         dot1qTpFdbAddress: The mac address.
         dot1qFdbId: The VLAN ID.
         dot1qTpFdbPort: The port the mac address was learned on."
    ::= { lcsMacTrapEvent 1 }

lcsMacTrapDelNotification NOTIFICATION-TYPE
    OBJECTS     { dot1qTpFdbAddress,
                  dot1qFdbId,
                  dot1qTpFdbPort,
                  lcsMacTrapVarDelReason
                }
    STATUS      current
    DESCRIPTION
        "Event generated for a deleted mac address.
         dot1qTpFdbAddress: The mac address.
         dot1qFdbId: The VLAN ID.
         dot1qTpFdbPort: The port the mac address was known on."
    ::= { lcsMacTrapEvent 2 }

lcsMacTrapVars              OBJECT IDENTIFIER ::= { lcsMacTrap 2 }

lcsMacTrapVarDelReason OBJECT-TYPE
    SYNTAX      DisplayString
    MAX-ACCESS  accessible-for-notify
    STATUS      current
    DESCRIPTION
        "The textual reason for deletion of a mac address."
    ::= { lcsMacTrapVars 1 }

--
-- =======================================================================================================================
-- Objects in the lcsProducts Group
-- =======================================================================================================================
-- Each device type has a unique OID with which it can be identified.
-- The OID has to be in the sysObjectID to identify the device type!
-- =======================================================================================================================

-- {NODE} 1.3.6.1.4.1.2356.14.8
lcsProducts                                                    OBJECT IDENTIFIER ::= { lcosSX 8 }

-- =======================================================================================================================
-- List of OIDs used in the sysObjectID to identify the device type
-- =======================================================================================================================
-- {NODE} 1.3.6.1.4.1.2356.14.8.3152
lcsProductsGS3152X        OBJECT IDENTIFIER ::= { lcsProducts 3152 }

-- {NODE} 1.3.6.1.4.1.2356.14.8.3153
lcsProductsGS3152XP       OBJECT IDENTIFIER ::= { lcsProducts 3153 }

-- {NODE} 1.3.6.1.4.1.2356.14.8.3154
lcsProductsGS3152XSP      OBJECT IDENTIFIER ::= { lcsProducts 3154 }

-- {NODE} 1.3.6.1.4.1.2356.14.8.3155
lcsProductsGS3152P       OBJECT IDENTIFIER ::= { lcsProducts 3155 }

-- {NODE} 1.3.6.1.4.1.2356.14.8.3528
lcsProductsGS3528XSP      OBJECT IDENTIFIER ::= { lcsProducts 3528 }

-- {NODE} 1.3.6.1.4.1.2356.14.8.3128
lcsProductsGS3128X 	  OBJECT IDENTIFIER ::= { lcsProducts 3128 }

-- {NODE} 1.3.6.1.4.1.2356.14.8.3129
lcsProductsGS3128XP 	  OBJECT IDENTIFIER ::= { lcsProducts 3129 }

-- {NODE} 1.3.6.1.4.1.2356.14.8.3529
lcsProductsGS3528XP       OBJECT IDENTIFIER ::= { lcsProducts 3529 }

-- {NODE} 1.3.6.1.4.1.2356.14.8.3530
lcsProductsGS3528X        OBJECT IDENTIFIER ::= { lcsProducts 3530 }

-- {NODE} 1.3.6.1.4.1.2356.14.8.3126
lcsProductsGS3126X    OBJECT IDENTIFIER ::= { lcsProducts 3126 }

-- {NODE} 1.3.6.1.4.1.2356.14.8.3127
lcsProductsGS3126XP     OBJECT IDENTIFIER ::= { lcsProducts 3127 }

-- {NODE} 1.3.6.1.4.1.2356.14.8.3510
lcsProductsGS3510XP     OBJECT IDENTIFIER ::= { lcsProducts 3510 }

-- {NODE} 1.3.6.1.4.1.2356.14.8.3511
lcsProductsGS3510X    OBJECT IDENTIFIER ::= { lcsProducts 3511 }

-- {NODE} 1.3.6.1.4.1.2356.14.8.3531
lcsProductsGS3528XUP     OBJECT IDENTIFIER ::= { lcsProducts 3531 }

-- In the future, enter the OID of a new device type here.

END
