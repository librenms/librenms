APM-MIB DEFINITIONS ::= BEGIN

-- Title:      RADWARE
-- Version:    0.1
-- Date:       11/1/2004
-- By:         RMA (Radware MIB Authority)
-- E-mail:     US:            support@radware.com
--             International: support_int@radware.com
--
IMPORTS
       NetworkAddress,
       IpAddress,
       Counter,
       Gauge,
       enterprises
              FROM RFC1155-SMI
       Integer32,        
       OBJECT-TYPE,
       Counter64
              FROM SNMPv2-SMI
        
       DisplayString,
       ipAddrEntry
              FROM RFC1213-MIB
       TRAP-TYPE
                    FROM RFC-1215
       rsAPM,
       rndErrorDesc,
       rndErrorSeverity
                    FROM RADWARE-MIB
        MacAddress,
        TEXTUAL-CONVENTION
				    FROM SNMPv2-TC;

    Bool ::= INTEGER {
         true (1),
         false (2)
    }
    RowStatus ::= INTEGER {
        active(1),
        notInService(2),
        notReady(3),
        createAndGo(4),
        createAndWait(5),
        destroy(6)
    }
  
    LogSeverity ::= INTEGER {
      none(1),
      emergency(2),
      alert(3),   
      critical(4),
      error(5),  
      warning(6),
      notice(7),
      info(8), 
      debug(9)
    }  


    SamplingAlgorithm ::= INTEGER {
      deterministic(1),
      nonDeterministic(2)
    }

    L4Protocol ::= INTEGER {
          tcp(1),
          udp(2)
    }

    L7Protocol ::= INTEGER {
          generic(1),
          http(2),
          smtp(3),
          pop3(4),
          imap4(5),
          https(6)
    }


    DataItemSetNumber ::= INTEGER {
        currentInterval (1),
        previousInterval (2),
        peakSubIntervalValuePerCurrentInterval (3),
        peakSubIntervalValuePerPreviousInterval (4),
        currentSubinterval (5),
        previousSubinterval (6)
    }


-- Bits designating which data items need to be collected

 CollectItems ::= BITS {
    numberOfServerTcpResponses(0),
    numberOfIncompleteServerTcpResponses(1),
    numberOfClientTcpResponses(2),
    numberOfIncompleteClientTcpResponses(3),
    numberOfAlternateClientTcpResponses(4),
    numberOfIncompleteAlternateClientTcpResponses(5),
    numberOfServerFullSslHandshakeResponses(6),
    numberOfIncompleteServerFullSslHandshakeResponses(7),
    numberOfServerResumedSslHandshakeResponses(8),
    numberOfIncompleteServerResumedSslHandshakeResponses(9),
    numberOfServerTransactionResponses(10),
    numberOfIncompleteServerTransactionResponses(11),
    numberOfServerTransactionCompletedBytes(12),
    numberOfNewSessions(13),
    numberOfNewTransactions(14),
    numberOfConcurrentSessions(15),
    numberOfTransactionFailures(16),
    numberOfReceivedRequestPackets(17),
    numberOfReceivedResponsePackets(18),
    numberOfTransmittedRequestPackets(19),
    numberOfTransmittedResponsePackets(20),
    numberOfReceivedRetransmittedRequestPackets(21),
    numberOfReceivedRetransmittedResponsePackets(22),
    numberOfNewDelayedBindingSessions(23),
    numberOfSkippedSessions(24),
    numberOfUnsampledSessions(25),
    numberOfSkippedTransactions(26),
    totalServerTcpResponseTime(27),
    totalClientTcpResponseTime(28),
    totalAlternateClientTcpResponseTime(29),
    totalServerFullSslHandshakeResponseTime(30),
    totalServerResumedSslHandshakeResponseTime(31),
    totalServerTransactionResponseTime(32),
    totalServerTransactionCompletedResponseTime(33),
    numberOfReceivedRequestBytes(34),
    numberOfReceivedResponseBytes(35),
    numberOfTransmittedRequestBytes(36),
    numberOfTransmittedResponseBytes(37),
    averageServerTcpResponseTime(38),
    averageEffectiveServerTcpResponseTime(39),
    averageClientTcpResponseTime(40),
    averageEffectiveClientTcpResponseTime(41),
    averageAlternateClientTcpResponseTime(42),
    averageEffectiveAlternateClientTcpResponseTime(43),
    averageAllClientTcpResponseTime(44),
    averageEffectiveAllClientTcpResponseTime(45),
    averageServerFullSslHandshakeResponseTime(46),
    averageEffectiveServerFullSslHandshakeResponseTime(47),
    averageServerResumedSslHandshakeResponseTime(48),
    averageEffectiveServerResumedSslHandshakeResponseTime(49),
    averageServerTransactionResponseTime(50),
    averageEffectiveServerTransactionResponseTime(51),
    averageServerTransactionCompletedResponseTimePerByte(52),
    averageEffectiveServerTransactionCompletedResponseTimePerByte(53),
    averageNumberOfConcurrentSessions(54)

}    

-- Floats are scaled appropriately such that they can be treated as integers
   Float ::= INTEGER

--    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsAPMPolicyTable OBJECT-TYPE
    SYNTAX SEQUENCE OF RsAPMPolicyEntry
    MAX-ACCESS not-accessible
    STATUS  current
    DESCRIPTION
      "Table containing the list of APM policies."
    ::=  { rsAPM 1 }

rsAPMPolicyEntry OBJECT-TYPE
    SYNTAX RsAPMPolicyEntry
    MAX-ACCESS not-accessible
    STATUS  current
    DESCRIPTION
       "The row definition for the APM policies table."
    INDEX { rsAPMPolicyID }
    ::=  { rsAPMPolicyTable 1 }

RsAPMPolicyEntry ::= SEQUENCE {
    rsAPMPolicyID INTEGER,
    rsAPMPolicyRowStatus RowStatus,
    rsAPMPolicyName DisplayString,
    rsAPMPolicyEnabledStatus INTEGER,
    rsAPMPolicyDescription DisplayString,
    rsAPMPolicyDestination DisplayString,
    rsAPMPolicySource DisplayString,
    rsAPMPolicyFilter DisplayString,
    rsAPMPolicyFilterType INTEGER,
    rsAPMPolicyPhysicalPortGroup DisplayString,
    rsAPMPolicyVLANTagGroup DisplayString,
    rsAPMPolicyL4Protocol L4Protocol,
    rsAPMPolicyL7Protocol L7Protocol,
    rsAPMPolicyReportInterval INTEGER,
    rsAPMPolicyReportSubInterval INTEGER,
    rsAPMPolicyNextReportIntervalID INTEGER,
    rsAPMPolicyRemainingTimeTillNextReportIntervalStart INTEGER,
    rsAPMPolicyReportViaSrp Bool,
    rsAPMPolicyInsiteInfo DisplayString
}

rsAPMPolicyID OBJECT-TYPE
    SYNTAX INTEGER
    MAX-ACCESS  read-write
    STATUS  current
    DESCRIPTION
       "This variable indicates the administrative ID of a policy. APM policies
       have no order semantics, so this ID is used for identification purposes only."
    ::=  { rsAPMPolicyEntry 1 }

rsAPMPolicyRowStatus OBJECT-TYPE
    SYNTAX RowStatus
    MAX-ACCESS  read-write
    STATUS  current
    DESCRIPTION
       "This variable indicates the administrative status of this entry.
        Used to delete an entry of this table."
    ::=  { rsAPMPolicyEntry 2 }

rsAPMPolicyName OBJECT-TYPE
    SYNTAX DisplayString (SIZE(0..32))
    MAX-ACCESS  read-write
    STATUS  current
    DESCRIPTION
      "The name for the APM policy. Must be unique."
    ::=  { rsAPMPolicyEntry 3 }


rsAPMPolicyEnabledStatus OBJECT-TYPE
    SYNTAX INTEGER {
        enabled (1),
        disabled (2)
    }
    MAX-ACCESS  read-write
    STATUS  current
    DESCRIPTION
       "This variable indicates if the policy is monitoring traffic at the moment
       or not. Policies in the modified policy table are not monitoring traffic
       by definition."
    ::= { rsAPMPolicyEntry 4 }

rsAPMPolicyDescription OBJECT-TYPE
    SYNTAX DisplayString (SIZE(0..64))
    MAX-ACCESS  read-write
    STATUS  current
    DESCRIPTION
      "Description."
    ::=  { rsAPMPolicyEntry 5 }

rsAPMPolicyDestination OBJECT-TYPE
    SYNTAX DisplayString (SIZE(0..32))
    MAX-ACCESS  read-write
    STATUS  current
    DESCRIPTION
      "The destination address / range of addresses for monitored sessions. The destination
      is defined as the server side, i.e., the side sending response packets. The
      name is defined in the classifier networks table or can be an IP address."
    ::=  { rsAPMPolicyEntry 6 }

rsAPMPolicySource OBJECT-TYPE
    SYNTAX DisplayString (SIZE(0..32))
    MAX-ACCESS  read-write
    STATUS  current
    DESCRIPTION
      "The source address / range of addresses for monitored sessions. The source
      is defined as the client side, i.e., the side sending request packets. The
      name is defined in the classifier networks table or can be an IP address."
    ::=  { rsAPMPolicyEntry 7 }

rsAPMPolicyFilter OBJECT-TYPE
    SYNTAX DisplayString (SIZE(0..32))
    MAX-ACCESS  read-write
    STATUS  current
    DESCRIPTION
       "The name of the filter, defined in the classifier filter table, for the APM policy."
    ::=  { rsAPMPolicyEntry 8 }

rsAPMPolicyFilterType OBJECT-TYPE
    SYNTAX INTEGER {
        basic (1),
        advanced (2),
        group (3)
    }
    MAX-ACCESS  read-write
    STATUS  current
    DESCRIPTION
       "The Type OF Filter."
    DEFVAL  { basic }
    ::=  { rsAPMPolicyEntry 9 }

rsAPMPolicyPhysicalPortGroup OBJECT-TYPE
    SYNTAX DisplayString (SIZE(0..32))
    MAX-ACCESS  read-write
    STATUS  current
    DESCRIPTION
       "The name of the physical port group, defined by the classifier, for the policy."
    ::=  { rsAPMPolicyEntry 10 }

rsAPMPolicyVLANTagGroup OBJECT-TYPE
    SYNTAX DisplayString (SIZE(0..32))
    MAX-ACCESS  read-write
    STATUS  current
    DESCRIPTION
        "The name of the VLAN tag group, defined by the classifier, for this rule."
    ::= { rsAPMPolicyEntry 11 }

rsAPMPolicyL4Protocol OBJECT-TYPE
    SYNTAX L4Protocol
    MAX-ACCESS  read-write
    STATUS  current
    DESCRIPTION
       "The L4 protocol monitored by the policy."
    ::=  { rsAPMPolicyEntry 12 }

rsAPMPolicyL7Protocol OBJECT-TYPE
    SYNTAX L7Protocol
    MAX-ACCESS  read-write
    STATUS  current
    DESCRIPTION
       "The L7 protocol monitored by the policy."
    DEFVAL  { generic }
    ::=  { rsAPMPolicyEntry 13 }

rsAPMPolicyReportInterval OBJECT-TYPE
    SYNTAX INTEGER 
    MAX-ACCESS  read-write
    STATUS  current
    DESCRIPTION
       "The reporting interval to Insite. Specified in seconds."
    ::=  { rsAPMPolicyEntry 14 }

rsAPMPolicyReportSubInterval OBJECT-TYPE
    SYNTAX INTEGER 
    MAX-ACCESS  read-write
    STATUS  current
    DESCRIPTION
       "The reporting sub interval. Specified in seconds."
    ::=  { rsAPMPolicyEntry 15 }

rsAPMPolicyNextReportIntervalID OBJECT-TYPE
    SYNTAX INTEGER 
    MAX-ACCESS  read-write
    STATUS  current
    DESCRIPTION
       "The ID of the next report interval."
    DEFVAL  { 0 }
    ::=  { rsAPMPolicyEntry 16 }

rsAPMPolicyRemainingTimeTillNextReportIntervalStart OBJECT-TYPE
    SYNTAX INTEGER 
    MAX-ACCESS  read-write
    STATUS  current
    DESCRIPTION
       "Specifies the remaining time, in msec, until the start of the next report interval."
    ::=  { rsAPMPolicyEntry 17 }

rsAPMPolicyReportViaSrp OBJECT-TYPE
    SYNTAX Bool
    MAX-ACCESS  read-write
    STATUS  current
    DESCRIPTION
       "Specifies whether the monitored data items for this policy should
       be reported via SRP or not."
    ::=  { rsAPMPolicyEntry 18 }

rsAPMPolicyInsiteInfo OBJECT-TYPE
    SYNTAX DisplayString (SIZE(0..64))
    MAX-ACCESS  read-write
    STATUS  current
    DESCRIPTION
       "64 Bytes that insite can use to store insite related information"
    ::=  { rsAPMPolicyEntry 19 }

rsAPMMonitorTable OBJECT-TYPE
    SYNTAX SEQUENCE OF RsAPMMonitorEntry
    MAX-ACCESS not-accessible
    STATUS  current
    DESCRIPTION
      "Table containing the list of APM monitors."
    ::=  { rsAPM 2 }

rsAPMMonitorEntry OBJECT-TYPE
    SYNTAX RsAPMMonitorEntry
    MAX-ACCESS not-accessible
    STATUS  current
    DESCRIPTION
       "The row definition for the APM policies table."
    INDEX { rsAPMMonitorPolicyID, rsAPMMonitorID }
    ::=  { rsAPMMonitorTable 1 }

RsAPMMonitorEntry ::= SEQUENCE {
    rsAPMMonitorPolicyID INTEGER,
    rsAPMMonitorID INTEGER,
    rsAPMMonitorRowStatus RowStatus,
    rsAPMMonitorType INTEGER,
    rsAPMMonitorFarmID DisplayString,
    rsAPMMonitorDirectionOrientation INTEGER,
    rsAPMMonitorItemsToCollect CollectItems
}

rsAPMMonitorPolicyID OBJECT-TYPE
    SYNTAX INTEGER
    MAX-ACCESS  read-write
    STATUS  current
    DESCRIPTION
       "This variable indicates the administrative ID of the APM policy this monitor belongs to."
    ::=  { rsAPMMonitorEntry 1 }

rsAPMMonitorID OBJECT-TYPE
    SYNTAX INTEGER
    MAX-ACCESS  read-write
    STATUS  current
    DESCRIPTION
       "This variable indicates the administrative ID of a monitor. This ID is used for identification purposes only."
    ::=  { rsAPMMonitorEntry 2 }

rsAPMMonitorRowStatus OBJECT-TYPE
    SYNTAX RowStatus
    MAX-ACCESS  read-write
    STATUS  current
    DESCRIPTION
       "This variable indicates the administrative status of this entry.
        Used to delete an entry of this table."
    ::=  { rsAPMMonitorEntry 3 }

rsAPMMonitorType OBJECT-TYPE
    SYNTAX INTEGER {
        device (1),
        farm (2)
    }
    MAX-ACCESS  read-write
    STATUS  current
    DESCRIPTION
       "The monitor type."
    ::= { rsAPMMonitorEntry 4 }

rsAPMMonitorFarmID OBJECT-TYPE
    SYNTAX DisplayString (SIZE(0..32))
    MAX-ACCESS  read-write
    STATUS  current
    DESCRIPTION
       "The farm ID of the farm that is being monitored. Not relevant for device monitors."
    ::=  { rsAPMMonitorEntry 5 }

rsAPMMonitorDirectionOrientation OBJECT-TYPE
    SYNTAX INTEGER { 
        source (1),
        destination (2)
    }
    MAX-ACCESS  read-write
    STATUS  current
    DESCRIPTION
       "Specifies the direction orientation of the monitor. Monitors with 'source'
       direction orientation will have packets associated to them according to
       the farm from which request packets arrived and the farm to which response packets
       were sent. Monitors with 'destination' direction orientation will have packets
       associated to them according to the farm to which request packets were sent and the
       farm from which response packets arrived."
    ::=  { rsAPMMonitorEntry 6 }

rsAPMMonitorItemsToCollect OBJECT-TYPE
    SYNTAX CollectItems
    MAX-ACCESS  read-write
    STATUS  current
    DESCRIPTION
       "Specifies which items need to be collected."
    ::=  { rsAPMMonitorEntry 7 }

rsAPMLegFarmTable OBJECT-TYPE
    SYNTAX SEQUENCE OF RsAPMLegFarmEntry 
    MAX-ACCESS not-accessible
    STATUS  current
    DESCRIPTION
      "Table listing all the leg farms that will be encountered by a policy, per policy.
      Any farm encountered by a policy that is not listed in this table will be considered
      to be an edge farm."
    ::=  { rsAPM 3 }

rsAPMLegFarmEntry OBJECT-TYPE
    SYNTAX RsAPMLegFarmEntry
    MAX-ACCESS not-accessible
    STATUS  current
    DESCRIPTION
       "The row definition for the APM leg farm table."
    INDEX { rsAPMLegFarmPolicyID,rsAPMLegFarmIndex }
    ::=  { rsAPMLegFarmTable 1 }

RsAPMLegFarmEntry ::= SEQUENCE {
    rsAPMLegFarmPolicyID INTEGER,
    rsAPMLegFarmIndex    INTEGER,
    rsAPMLegFarmFarmID DisplayString,
    rsAPMLegFarmRowStatus RowStatus
}

rsAPMLegFarmPolicyID  OBJECT-TYPE
    SYNTAX INTEGER
    MAX-ACCESS  read-write
    STATUS  current
    DESCRIPTION
       "This variable indicates the administrative ID of the APM policy this leg farm belongs to."
    ::=  { rsAPMLegFarmEntry 1 }

rsAPMLegFarmIndex  OBJECT-TYPE
    SYNTAX INTEGER
    MAX-ACCESS  read-write
    STATUS  current
    DESCRIPTION
       "Index of the leg farm."
    ::=  { rsAPMLegFarmEntry 2 }

    
rsAPMLegFarmFarmID  OBJECT-TYPE
    SYNTAX DisplayString (SIZE(0..32))
    MAX-ACCESS  read-write
    STATUS  current
    DESCRIPTION
       "This variable indicates the ID of this leg farm."
    ::=  { rsAPMLegFarmEntry  3 }
    
rsAPMLegFarmRowStatus OBJECT-TYPE
   SYNTAX RowStatus
    MAX-ACCESS  read-write
    STATUS  current
    DESCRIPTION
       "This variable indicates the administrative status of this entry.
        Used to delete an entry of this table."
    ::=  { rsAPMLegFarmEntry  4 }


rsAPMMonitorDataItemTable OBJECT-TYPE
    SYNTAX SEQUENCE OF RsAPMMonitorDataItemEntry 
    MAX-ACCESS not-accessible
    STATUS  current
    DESCRIPTION
      "Table providing read-only access to all Monitor data items. Access to
      the Monitor data items is given per policy, farm monitor, farm element
      monitor (if applicable), farm element element monitor (if applicable),
      current or previous data item and Monitor data item type. The available
      types are: interval, subinterval, peak subinterval value per interval. Not
      all these types are available for each Monitor data item. See the APM
      documentation for full details."
    ::=  { rsAPM 4 }

rsAPMMonitorDataItemEntry OBJECT-TYPE
    SYNTAX RsAPMMonitorDataItemEntry
    MAX-ACCESS not-accessible
    STATUS  current
    DESCRIPTION
       "The row definition for the APM Monitor data item table."
    INDEX { rsAPMMonitorDataItemPolicyID,
            rsAPMMonitorDataItemFarmMonitorID,
            rsAPMMonitorDataItemFarmElementMonitorID,
            rsAPMMonitorDataItemSetNumber }
    ::=  { rsAPMMonitorDataItemTable 1 }



RsAPMMonitorDataItemEntry ::= SEQUENCE {
    rsAPMMonitorDataItemPolicyID INTEGER,
    rsAPMMonitorDataItemFarmMonitorID INTEGER,
    rsAPMMonitorDataItemFarmElementMonitorID INTEGER,
    rsAPMMonitorDataItemSetNumber DataItemSetNumber,
    rsAPMMonitorDataItemFarmID DisplayString,
    rsAPMMonitorDataItemNumberOfServerTcpResponses INTEGER,
    rsAPMMonitorDataItemNumberOfIncompleteServerTcpResponses INTEGER,
    rsAPMMonitorDataItemNumberOfClientTcpResponses INTEGER,
    rsAPMMonitorDataItemNumberOfIncompleteClientTcpResponses INTEGER,
    rsAPMMonitorDataItemNumberOfAlternateClientTcpResponses INTEGER,
    rsAPMMonitorDataItemNumberOfIncompleteAlternateClientTcpResponses INTEGER,
    rsAPMMonitorDataItemNumberOfServerFullSslHandshakeResponses INTEGER,
    rsAPMMonitorDataItemNumberOfIncompleteServerFullSslHandshakeResponses INTEGER,
    rsAPMMonitorDataItemNumberOfServerResumedSslHandshakeResponses INTEGER,
    rsAPMMonitorDataItemNumberOfIncompleteServerResumedSslHandshakeResponses INTEGER,
    rsAPMMonitorDataItemNumberOfServerTransactionResponses INTEGER,
    rsAPMMonitorDataItemNumberOfIncompleteServerTransactionResponses INTEGER,
    rsAPMMonitorDataItemNumberOfServerTransactionCompletedBytes INTEGER,
    rsAPMMonitorDataItemNumberOfNewSessions INTEGER,
    rsAPMMonitorDataItemNumberOfNewTransactions INTEGER,
    rsAPMMonitorDataItemNumberOfConcurrentSessions INTEGER,
    rsAPMMonitorDataItemNumberOfTransactionFailures INTEGER,
    rsAPMMonitorDataItemNumberOfReceivedRequestPackets INTEGER,
    rsAPMMonitorDataItemNumberOfReceivedResponsePackets INTEGER,
    rsAPMMonitorDataItemNumberOfTransmittedRequestPackets INTEGER,
    rsAPMMonitorDataItemNumberOfTransmittedResponsePackets INTEGER,
    rsAPMMonitorDataItemNumberOfReceivedRetransmittedRequestPackets INTEGER,
    rsAPMMonitorDataItemNumberOfReceivedRetransmittedResponsePackets INTEGER,
    rsAPMMonitorDataItemNumberOfNewDelayedBindingSessions INTEGER,
    rsAPMMonitorDataItemNumberOfSkippedSessions INTEGER,
    rsAPMMonitorDataItemNumberOfUnsampledSessions INTEGER,
    rsAPMMonitorDataItemNumberOfSkippedTransactions INTEGER,
    rsAPMMonitorDataItemTotalServerTcpResponseTime Counter64,
    rsAPMMonitorDataItemTotalClientTcpResponseTime Counter64,
    rsAPMMonitorDataItemTotalAlternateClientTcpResponseTime Counter64,
    rsAPMMonitorDataItemTotalServerFullSslHandshakeResponseTime Counter64,
    rsAPMMonitorDataItemTotalServerResumedSslHandshakeResponseTime Counter64,
    rsAPMMonitorDataItemTotalServerTransactionResponseTime Counter64,
    rsAPMMonitorDataItemTotalServerTransactionCompletedResponseTime Counter64,
    rsAPMMonitorDataItemNumberOfReceivedRequestBytes Counter64,
    rsAPMMonitorDataItemNumberOfReceivedResponseBytes Counter64,
    rsAPMMonitorDataItemNumberOfTransmittedRequestBytes Counter64,
    rsAPMMonitorDataItemNumberOfTransmittedResponseBytes Counter64,
    rsAPMMonitorDataItemAverageServerTcpResponseTime Float,
    rsAPMMonitorDataItemAverageEffectiveServerTcpResponseTime Float,
    rsAPMMonitorDataItemAverageClientTcpResponseTime Float,
    rsAPMMonitorDataItemAverageEffectiveClientTcpResponseTime Float,
    rsAPMMonitorDataItemAverageAlternateClientTcpResponseTime Float,
    rsAPMMonitorDataItemAverageEffectiveAlternateClientTcpResponseTime Float,
    rsAPMMonitorDataItemAverageAllClientTcpResponseTime Float,
    rsAPMMonitorDataItemAverageEffectiveAllClientTcpResponseTime Float,
    rsAPMMonitorDataItemAverageServerFullSslHandshakeResponseTime Float,
    rsAPMMonitorDataItemAverageEffectiveServerFullSslHandshakeResponseTime Float,
    rsAPMMonitorDataItemAverageServerResumedSslHandshakeResponseTime Float,
    rsAPMMonitorDataItemAverageEffectiveServerResumedSslHandshakeResponseTime Float,
    rsAPMMonitorDataItemAverageServerTransactionResponseTime Float,
    rsAPMMonitorDataItemAverageEffectiveServerTransactionResponseTime Float,
    rsAPMMonitorDataItemAverageServerTransactionCompletedResponseTimePerByte Float,
    rsAPMMonitorDataItemAverageEffectiveServerTransactionCompletedResponseTimePerByte Float,
    rsAPMMonitorDataItemAverageNumberOfConcurrentSessions Float,
    rsAPMMonitorDataItemIntervalId INTEGER,
    rsAPMMonitorDataItemSamplingAlgorithm SamplingAlgorithm,
    rsAPMMonitorDataItemSamplingRate INTEGER,
    rsAPMMonitorDataItemUsePreciseSampling Bool
        
}


rsAPMMonitorDataItemPolicyID  OBJECT-TYPE
	SYNTAX INTEGER
	MAX-ACCESS  read-only
	STATUS  current
	DESCRIPTION
		""
	::=  { rsAPMMonitorDataItemEntry 1 }


rsAPMMonitorDataItemFarmMonitorID  OBJECT-TYPE
	SYNTAX INTEGER
	MAX-ACCESS  read-only
	STATUS  current
	DESCRIPTION
		""
	::=  { rsAPMMonitorDataItemEntry 2 }


rsAPMMonitorDataItemFarmElementMonitorID  OBJECT-TYPE
	SYNTAX INTEGER
	MAX-ACCESS  read-only
	STATUS  current
	DESCRIPTION
		""
	::=  { rsAPMMonitorDataItemEntry 3 }


rsAPMMonitorDataItemSetNumber  OBJECT-TYPE
	SYNTAX DataItemSetNumber
	MAX-ACCESS  read-only
	STATUS  current
	DESCRIPTION
		""
	::=  { rsAPMMonitorDataItemEntry 4 }


rsAPMMonitorDataItemFarmID  OBJECT-TYPE
	SYNTAX DisplayString
	MAX-ACCESS  read-only
	STATUS  current
	DESCRIPTION
		""
	::=  { rsAPMMonitorDataItemEntry 5 }


rsAPMMonitorDataItemNumberOfServerTcpResponses  OBJECT-TYPE
	SYNTAX INTEGER
	MAX-ACCESS  read-only
	STATUS  current
	DESCRIPTION
		""
	::=  { rsAPMMonitorDataItemEntry 6 }


rsAPMMonitorDataItemNumberOfIncompleteServerTcpResponses  OBJECT-TYPE
	SYNTAX INTEGER
	MAX-ACCESS  read-only
	STATUS  current
	DESCRIPTION
		""
	::=  { rsAPMMonitorDataItemEntry 7 }


rsAPMMonitorDataItemNumberOfClientTcpResponses  OBJECT-TYPE
	SYNTAX INTEGER
	MAX-ACCESS  read-only
	STATUS  current
	DESCRIPTION
		""
	::=  { rsAPMMonitorDataItemEntry 8 }


rsAPMMonitorDataItemNumberOfIncompleteClientTcpResponses  OBJECT-TYPE
	SYNTAX INTEGER
	MAX-ACCESS  read-only
	STATUS  current
	DESCRIPTION
		""
	::=  { rsAPMMonitorDataItemEntry 9 }


rsAPMMonitorDataItemNumberOfAlternateClientTcpResponses  OBJECT-TYPE
	SYNTAX INTEGER
	MAX-ACCESS  read-only
	STATUS  current
	DESCRIPTION
		""
	::=  { rsAPMMonitorDataItemEntry 10 }


rsAPMMonitorDataItemNumberOfIncompleteAlternateClientTcpResponses  OBJECT-TYPE
	SYNTAX INTEGER
	MAX-ACCESS  read-only
	STATUS  current
	DESCRIPTION
		""
	::=  { rsAPMMonitorDataItemEntry 11 }


rsAPMMonitorDataItemNumberOfServerFullSslHandshakeResponses  OBJECT-TYPE
	SYNTAX INTEGER
	MAX-ACCESS  read-only
	STATUS  current
	DESCRIPTION
		""
	::=  { rsAPMMonitorDataItemEntry 12 }


rsAPMMonitorDataItemNumberOfIncompleteServerFullSslHandshakeResponses  OBJECT-TYPE
	SYNTAX INTEGER
	MAX-ACCESS  read-only
	STATUS  current
	DESCRIPTION
		""
	::=  { rsAPMMonitorDataItemEntry 13 }


rsAPMMonitorDataItemNumberOfServerResumedSslHandshakeResponses  OBJECT-TYPE
	SYNTAX INTEGER
	MAX-ACCESS  read-only
	STATUS  current
	DESCRIPTION
		""
	::=  { rsAPMMonitorDataItemEntry 14 }


rsAPMMonitorDataItemNumberOfIncompleteServerResumedSslHandshakeResponses  OBJECT-TYPE
	SYNTAX INTEGER
	MAX-ACCESS  read-only
	STATUS  current
	DESCRIPTION
		""
	::=  { rsAPMMonitorDataItemEntry 15 }


rsAPMMonitorDataItemNumberOfServerTransactionResponses  OBJECT-TYPE
	SYNTAX INTEGER
	MAX-ACCESS  read-only
	STATUS  current
	DESCRIPTION
		""
	::=  { rsAPMMonitorDataItemEntry 16 }


rsAPMMonitorDataItemNumberOfIncompleteServerTransactionResponses  OBJECT-TYPE
	SYNTAX INTEGER
	MAX-ACCESS  read-only
	STATUS  current
	DESCRIPTION
		""
	::=  { rsAPMMonitorDataItemEntry 17 }


rsAPMMonitorDataItemNumberOfServerTransactionCompletedBytes  OBJECT-TYPE
	SYNTAX INTEGER
	MAX-ACCESS  read-only
	STATUS  current
	DESCRIPTION
		""
	::=  { rsAPMMonitorDataItemEntry 18 }


rsAPMMonitorDataItemNumberOfNewSessions  OBJECT-TYPE
	SYNTAX INTEGER
	MAX-ACCESS  read-only
	STATUS  current
	DESCRIPTION
		""
	::=  { rsAPMMonitorDataItemEntry 19 }


rsAPMMonitorDataItemNumberOfNewTransactions  OBJECT-TYPE
	SYNTAX INTEGER
	MAX-ACCESS  read-only
	STATUS  current
	DESCRIPTION
		""
	::=  { rsAPMMonitorDataItemEntry 20 }


rsAPMMonitorDataItemNumberOfConcurrentSessions  OBJECT-TYPE
	SYNTAX INTEGER
	MAX-ACCESS  read-only
	STATUS  current
	DESCRIPTION
		""
	::=  { rsAPMMonitorDataItemEntry 21 }


rsAPMMonitorDataItemNumberOfTransactionFailures  OBJECT-TYPE
	SYNTAX INTEGER
	MAX-ACCESS  read-only
	STATUS  current
	DESCRIPTION
		""
	::=  { rsAPMMonitorDataItemEntry 22 }


rsAPMMonitorDataItemNumberOfReceivedRequestPackets  OBJECT-TYPE
	SYNTAX INTEGER
	MAX-ACCESS  read-only
	STATUS  current
	DESCRIPTION
		""
	::=  { rsAPMMonitorDataItemEntry 23 }


rsAPMMonitorDataItemNumberOfReceivedResponsePackets  OBJECT-TYPE
	SYNTAX INTEGER
	MAX-ACCESS  read-only
	STATUS  current
	DESCRIPTION
		""
	::=  { rsAPMMonitorDataItemEntry 24 }


rsAPMMonitorDataItemNumberOfTransmittedRequestPackets  OBJECT-TYPE
	SYNTAX INTEGER
	MAX-ACCESS  read-only
	STATUS  current
	DESCRIPTION
		""
	::=  { rsAPMMonitorDataItemEntry 25 }


rsAPMMonitorDataItemNumberOfTransmittedResponsePackets  OBJECT-TYPE
	SYNTAX INTEGER
	MAX-ACCESS  read-only
	STATUS  current
	DESCRIPTION
		""
	::=  { rsAPMMonitorDataItemEntry 26 }


rsAPMMonitorDataItemNumberOfReceivedRetransmittedRequestPackets  OBJECT-TYPE
	SYNTAX INTEGER
	MAX-ACCESS  read-only
	STATUS  current
	DESCRIPTION
		""
	::=  { rsAPMMonitorDataItemEntry 27 }


rsAPMMonitorDataItemNumberOfReceivedRetransmittedResponsePackets  OBJECT-TYPE
	SYNTAX INTEGER
	MAX-ACCESS  read-only
	STATUS  current
	DESCRIPTION
		""
	::=  { rsAPMMonitorDataItemEntry 28 }


rsAPMMonitorDataItemNumberOfNewDelayedBindingSessions  OBJECT-TYPE
	SYNTAX INTEGER
	MAX-ACCESS  read-only
	STATUS  current
	DESCRIPTION
		""
	::=  { rsAPMMonitorDataItemEntry 29 }


rsAPMMonitorDataItemNumberOfSkippedSessions  OBJECT-TYPE
	SYNTAX INTEGER
	MAX-ACCESS  read-only
	STATUS  current
	DESCRIPTION
		""
	::=  { rsAPMMonitorDataItemEntry 30 }


rsAPMMonitorDataItemNumberOfUnsampledSessions  OBJECT-TYPE
	SYNTAX INTEGER
	MAX-ACCESS  read-only
	STATUS  current
	DESCRIPTION
		""
	::=  { rsAPMMonitorDataItemEntry 31 }


rsAPMMonitorDataItemNumberOfSkippedTransactions  OBJECT-TYPE
	SYNTAX INTEGER
	MAX-ACCESS  read-only
	STATUS  current
	DESCRIPTION
		""
	::=  { rsAPMMonitorDataItemEntry 32 }


rsAPMMonitorDataItemTotalServerTcpResponseTime  OBJECT-TYPE
	SYNTAX Counter64
	MAX-ACCESS  read-only
	STATUS  current
	DESCRIPTION
		""
	::=  { rsAPMMonitorDataItemEntry 33 }


rsAPMMonitorDataItemTotalClientTcpResponseTime  OBJECT-TYPE
	SYNTAX Counter64
	MAX-ACCESS  read-only
	STATUS  current
	DESCRIPTION
		""
	::=  { rsAPMMonitorDataItemEntry 34 }


rsAPMMonitorDataItemTotalAlternateClientTcpResponseTime  OBJECT-TYPE
	SYNTAX Counter64
	MAX-ACCESS  read-only
	STATUS  current
	DESCRIPTION
		""
	::=  { rsAPMMonitorDataItemEntry 35 }


rsAPMMonitorDataItemTotalServerFullSslHandshakeResponseTime  OBJECT-TYPE
	SYNTAX Counter64
	MAX-ACCESS  read-only
	STATUS  current
	DESCRIPTION
		""
	::=  { rsAPMMonitorDataItemEntry 36 }


rsAPMMonitorDataItemTotalServerResumedSslHandshakeResponseTime  OBJECT-TYPE
	SYNTAX Counter64
	MAX-ACCESS  read-only
	STATUS  current
	DESCRIPTION
		""
	::=  { rsAPMMonitorDataItemEntry 37 }


rsAPMMonitorDataItemTotalServerTransactionResponseTime  OBJECT-TYPE
	SYNTAX Counter64
	MAX-ACCESS  read-only
	STATUS  current
	DESCRIPTION
		""
	::=  { rsAPMMonitorDataItemEntry 38 }


rsAPMMonitorDataItemTotalServerTransactionCompletedResponseTime  OBJECT-TYPE
	SYNTAX Counter64
	MAX-ACCESS  read-only
	STATUS  current
	DESCRIPTION
		""
	::=  { rsAPMMonitorDataItemEntry 39 }


rsAPMMonitorDataItemNumberOfReceivedRequestBytes  OBJECT-TYPE
	SYNTAX Counter64
	MAX-ACCESS  read-only
	STATUS  current
	DESCRIPTION
		""
	::=  { rsAPMMonitorDataItemEntry 40 }


rsAPMMonitorDataItemNumberOfReceivedResponseBytes  OBJECT-TYPE
	SYNTAX Counter64
	MAX-ACCESS  read-only
	STATUS  current
	DESCRIPTION
		""
	::=  { rsAPMMonitorDataItemEntry 41 }


rsAPMMonitorDataItemNumberOfTransmittedRequestBytes  OBJECT-TYPE
	SYNTAX Counter64
	MAX-ACCESS  read-only
	STATUS  current
	DESCRIPTION
		""
	::=  { rsAPMMonitorDataItemEntry 42 }


rsAPMMonitorDataItemNumberOfTransmittedResponseBytes  OBJECT-TYPE
	SYNTAX Counter64
	MAX-ACCESS  read-only
	STATUS  current
	DESCRIPTION
		""
	::=  { rsAPMMonitorDataItemEntry 43 }


rsAPMMonitorDataItemAverageServerTcpResponseTime  OBJECT-TYPE
	SYNTAX Float
	MAX-ACCESS  read-only
	STATUS  current
	DESCRIPTION
		""
	::=  { rsAPMMonitorDataItemEntry 44 }


rsAPMMonitorDataItemAverageEffectiveServerTcpResponseTime  OBJECT-TYPE
	SYNTAX Float
	MAX-ACCESS  read-only
	STATUS  current
	DESCRIPTION
		""
	::=  { rsAPMMonitorDataItemEntry 45 }


rsAPMMonitorDataItemAverageClientTcpResponseTime  OBJECT-TYPE
	SYNTAX Float
	MAX-ACCESS  read-only
	STATUS  current
	DESCRIPTION
		""
	::=  { rsAPMMonitorDataItemEntry 46 }


rsAPMMonitorDataItemAverageEffectiveClientTcpResponseTime  OBJECT-TYPE
	SYNTAX Float
	MAX-ACCESS  read-only
	STATUS  current
	DESCRIPTION
		""
	::=  { rsAPMMonitorDataItemEntry 47 }


rsAPMMonitorDataItemAverageAlternateClientTcpResponseTime  OBJECT-TYPE
	SYNTAX Float
	MAX-ACCESS  read-only
	STATUS  current
	DESCRIPTION
		""
	::=  { rsAPMMonitorDataItemEntry 48 }


rsAPMMonitorDataItemAverageEffectiveAlternateClientTcpResponseTime  OBJECT-TYPE
	SYNTAX Float
	MAX-ACCESS  read-only
	STATUS  current
	DESCRIPTION
		""
	::=  { rsAPMMonitorDataItemEntry 49 }


rsAPMMonitorDataItemAverageAllClientTcpResponseTime  OBJECT-TYPE
	SYNTAX Float
	MAX-ACCESS  read-only
	STATUS  current
	DESCRIPTION
		""
	::=  { rsAPMMonitorDataItemEntry 50 }


rsAPMMonitorDataItemAverageEffectiveAllClientTcpResponseTime  OBJECT-TYPE
	SYNTAX Float
	MAX-ACCESS  read-only
	STATUS  current
	DESCRIPTION
		""
	::=  { rsAPMMonitorDataItemEntry 51 }


rsAPMMonitorDataItemAverageServerFullSslHandshakeResponseTime  OBJECT-TYPE
	SYNTAX Float
	MAX-ACCESS  read-only
	STATUS  current
	DESCRIPTION
		""
	::=  { rsAPMMonitorDataItemEntry 52 }


rsAPMMonitorDataItemAverageEffectiveServerFullSslHandshakeResponseTime  OBJECT-TYPE
	SYNTAX Float
	MAX-ACCESS  read-only
	STATUS  current
	DESCRIPTION
		""
	::=  { rsAPMMonitorDataItemEntry 53 }


rsAPMMonitorDataItemAverageServerResumedSslHandshakeResponseTime  OBJECT-TYPE
	SYNTAX Float
	MAX-ACCESS  read-only
	STATUS  current
	DESCRIPTION
		""
	::=  { rsAPMMonitorDataItemEntry 54 }


rsAPMMonitorDataItemAverageEffectiveServerResumedSslHandshakeResponseTime  OBJECT-TYPE
	SYNTAX Float
	MAX-ACCESS  read-only
	STATUS  current
	DESCRIPTION
		""
	::=  { rsAPMMonitorDataItemEntry 55 }


rsAPMMonitorDataItemAverageServerTransactionResponseTime  OBJECT-TYPE
	SYNTAX Float
	MAX-ACCESS  read-only
	STATUS  current
	DESCRIPTION
		""
	::=  { rsAPMMonitorDataItemEntry 56 }


rsAPMMonitorDataItemAverageEffectiveServerTransactionResponseTime  OBJECT-TYPE
	SYNTAX Float
	MAX-ACCESS  read-only
	STATUS  current
	DESCRIPTION
		""
	::=  { rsAPMMonitorDataItemEntry 57 }


rsAPMMonitorDataItemAverageServerTransactionCompletedResponseTimePerByte  OBJECT-TYPE
	SYNTAX Float
	MAX-ACCESS  read-only
	STATUS  current
	DESCRIPTION
		""
	::=  { rsAPMMonitorDataItemEntry 58 }


rsAPMMonitorDataItemAverageEffectiveServerTransactionCompletedResponseTimePerByte  OBJECT-TYPE
	SYNTAX Float
	MAX-ACCESS  read-only
	STATUS  current
	DESCRIPTION
		""
	::=  { rsAPMMonitorDataItemEntry 59 }


rsAPMMonitorDataItemAverageNumberOfConcurrentSessions  OBJECT-TYPE
	SYNTAX Float
	MAX-ACCESS  read-only
	STATUS  current
	DESCRIPTION
		""
	::=  { rsAPMMonitorDataItemEntry 60 }

rsAPMMonitorDataItemIntervalId  OBJECT-TYPE
	SYNTAX INTEGER
	MAX-ACCESS  read-only
	STATUS  current
	DESCRIPTION
		""
	::=  { rsAPMMonitorDataItemEntry 61 }


rsAPMMonitorDataItemSamplingAlgorithm OBJECT-TYPE
    SYNTAX SamplingAlgorithm
    MAX-ACCESS  read-only
    STATUS  current
    DESCRIPTION
       "The sampling algorithm to be used"
    DEFVAL  { deterministic }
    ::=  { rsAPMMonitorDataItemEntry 62 }

rsAPMMonitorDataItemSamplingRate OBJECT-TYPE
    SYNTAX INTEGER
    MAX-ACCESS  read-only
    STATUS  current
    DESCRIPTION
       "The rate to be used. Specified in percentage. Valid range is 1-100."
    ::=  { rsAPMMonitorDataItemEntry 63 }


rsAPMMonitorDataItemUsePreciseSampling OBJECT-TYPE
    SYNTAX Bool
    MAX-ACCESS  read-only
    STATUS  current
    DESCRIPTION
       "The rate to be used"
    ::=  { rsAPMMonitorDataItemEntry 64 }


    
rsAPMAlertSpecTable OBJECT-TYPE
    SYNTAX SEQUENCE OF RsAPMAlertSpecEntry
    MAX-ACCESS not-accessible
    STATUS  current
    DESCRIPTION
      "Table containing the list of APM alert specs."
    ::=  { rsAPM 5 }

rsAPMAlertSpecEntry OBJECT-TYPE
    SYNTAX RsAPMAlertSpecEntry
    MAX-ACCESS not-accessible
    STATUS  current
    DESCRIPTION
       "The row definition for the APM alert spec table."
    INDEX { rsAPMAlertSpecID }
    ::=  { rsAPMAlertSpecTable 1 }

RsAPMAlertSpecEntry ::= SEQUENCE {
    rsAPMAlertSpecID INTEGER,
    rsAPMAlertSpecRowStatus RowStatus,
    rsAPMAlertSpecEnabledStatus INTEGER,
    rsAPMAlertSpecDescription DisplayString,
    rsAPMAlertSpecExpression DisplayString,
    rsAPMAlertSpecEvaluationInterval INTEGER,
    rsAPMAlertSpecReportedMonitorDataItemList DisplayString
}

rsAPMAlertSpecID OBJECT-TYPE
    SYNTAX INTEGER
    MAX-ACCESS  read-write
    STATUS  current
    DESCRIPTION
        "This variable indicates the administrative ID of the alert spec."
    ::=  { rsAPMAlertSpecEntry 1 }

rsAPMAlertSpecRowStatus OBJECT-TYPE
    SYNTAX RowStatus
    MAX-ACCESS  read-write
    STATUS  current
    DESCRIPTION
       "This variable indicates the administrative status of this entry.
        Used to delete an entry of this table."
    ::=  { rsAPMAlertSpecEntry 2 }
    
rsAPMAlertSpecEnabledStatus OBJECT-TYPE
    SYNTAX INTEGER {
        enabled (1),
        disabled (2)
    }
    MAX-ACCESS  read-write
    STATUS  current
    DESCRIPTION
        "This variable indicates whether the alert spec is enabled or not."
    ::=  { rsAPMAlertSpecEntry 3 }


rsAPMAlertSpecDescription OBJECT-TYPE
    SYNTAX DisplayString
    MAX-ACCESS  read-write
    STATUS  current
    DESCRIPTION
        "This variable holds the description for the alert spec."
    ::=  { rsAPMAlertSpecEntry 4 }
    
rsAPMAlertSpecExpression OBJECT-TYPE
    SYNTAX DisplayString (SIZE(0..32))
    MAX-ACCESS  read-write
    STATUS  current
    DESCRIPTION
        "This variable holds the alert spec expression. For the exact syntax
        of this expression, see the APM RDG document."
    ::=  { rsAPMAlertSpecEntry 5 }
    
rsAPMAlertSpecEvaluationInterval OBJECT-TYPE
    SYNTAX INTEGER
    MAX-ACCESS  read-write
    STATUS  current
    DESCRIPTION
        "The periodic interval, specified in seconds, in which the alert expression is evaluated."
    ::=  { rsAPMAlertSpecEntry 6 }
    
rsAPMAlertSpecReportedMonitorDataItemList OBJECT-TYPE
    SYNTAX DisplayString
    MAX-ACCESS  read-write
    STATUS  current
    DESCRIPTION
        "This variable defines the list of monitor data items that will be sent
        with the alert. The syntax for denoting the monitor data item list will
        be as follows (the syntax is specified using the augmented BNF rules defined
        in RFC 2616, section 2.1; the single quote character is used instead of
        the double quote character; definitions that are split over more than one
        line are meant to be concatenated):
        
        reportedMonitorDataItemList ::= #monitorDataItemIdentifier
        monitorDataItemIdentifier ::= PolicyID'.'(DeviceMonitorID|(FarmMonitorID
                                      ['.'FarmElement1MonitorID['.'FarmElement2MonitorID]])
                                      '.'DataItemSetNumber'.'DataItemNumber

        where the various policy and monitor IDs are those defined by the
        rsAPMMonitorDataItemTable, the data item set numbers are defined in
        the rsAPMMonitorDataItemSetNumber enumeration and the data item numbers are 
        defined by the enumeration used in the APM SRP reports (see the APM RDG doc).
        
        The alert will consist of an SNMP trap, which will contain a variable that
        will include the values of the monitors specified in the alert spec
        monitor data item list. The values will be given accordng to the following
        syntax (which follows the abovementioned syntax rules):
        
        alertMonitorDataItemValueList ::= #monitorDataItemValue
        monitorDataItemValue ::= <integer>

        The values of the monitor data items will be ordered according
        to the order of the reported monitor data item list in the alert spec."
    ::=  { rsAPMAlertSpecEntry 7 }
    

rsAPMAlertVariables  OBJECT IDENTIFIER ::= { rsAPM 6 }

rsAPMAlertVariableMonitorDataItemValueList OBJECT-TYPE
    SYNTAX DisplayString
    MAX-ACCESS  read-only
    STATUS  current
    DESCRIPTION
       "String containing the values of monitor data items as specified
       in the alert spec. See rsAPMAlertSpecReportedMonitorDataItemList
       for the exact syntax."
    ::= { rsAPMAlertVariables 1 }

rsAPMAlert TRAP-TYPE
        ENTERPRISE rsAPM
        VARIABLES  { rsAPMAlertVariableMonitorDataItemValueList }
        DESCRIPTION
             "This trap is sent to inform the user about an APM alert."
		::=  1


rsAPMTuning  OBJECT IDENTIFIER ::= { rsAPM 7 }

rsAPMNumberOfPolicies OBJECT-TYPE
    SYNTAX INTEGER
    MAX-ACCESS  read-only
    STATUS  current
    DESCRIPTION
      "Maximum number of policy entries."
    ::= { rsAPMTuning 1 }

rsAPMNumberOfPoliciesAfterReset OBJECT-TYPE
    SYNTAX INTEGER
    MAX-ACCESS  read-write
    STATUS  current
    DESCRIPTION
      "maximum number of policy entries after reset."
    ::=  { rsAPMTuning 2 }

rsAPMNumberOfFarmsPerPolicy OBJECT-TYPE
    SYNTAX INTEGER
    MAX-ACCESS  read-only
    STATUS  current
    DESCRIPTION
      "maximum average number of farms per policy."
    ::= { rsAPMTuning 3 }

rsAPMNumberOfFarmsPerPolicyAfterReset OBJECT-TYPE
    SYNTAX INTEGER
    MAX-ACCESS  read-write
    STATUS  current
    DESCRIPTION
      "maximum average number of farms per policy after reset."
    ::=  { rsAPMTuning 4 }


rsAPMNumberOfFarmElementsPerFarm OBJECT-TYPE
    SYNTAX INTEGER
    MAX-ACCESS  read-only
    STATUS  current
    DESCRIPTION
      "Maximum average number of farm elements per farm."
    ::= { rsAPMTuning 5 }

rsAPMNumberOfFarmElementsPerFarmAfterReset OBJECT-TYPE
    SYNTAX INTEGER
    MAX-ACCESS  read-write
    STATUS  current
    DESCRIPTION
      "Maximum average number of farm elements per farm after reset."
    ::=  { rsAPMTuning 6 }


rsAPMNumberOfLegFarmsPerPolicy OBJECT-TYPE
    SYNTAX INTEGER
    MAX-ACCESS  read-only
    STATUS  current
    DESCRIPTION
      "Maximum average number of leg farms per policy."
    ::= { rsAPMTuning 7 }

rsAPMNumberOfLegFarmsPerPolicyAfterReset OBJECT-TYPE
    SYNTAX INTEGER
    MAX-ACCESS  read-write
    STATUS  current
    DESCRIPTION
      "Maximum average number of leg farms per policy after reset."
    ::=  { rsAPMTuning 8 }

rsAPMNumberOfAlerts OBJECT-TYPE
    SYNTAX INTEGER
    MAX-ACCESS  read-only
    STATUS  current
    DESCRIPTION
      "Maximum number of alerts."
    ::= { rsAPMTuning 9 }

rsAPMNumberOfAlertsAfterReset OBJECT-TYPE
    SYNTAX INTEGER
    MAX-ACCESS  read-write
    STATUS  current
    DESCRIPTION
      "Maximum number of alerts after reset."
    ::=  { rsAPMTuning 10 }


rsAPMNumberOfApmSessions OBJECT-TYPE
    SYNTAX INTEGER
    MAX-ACCESS  read-only
    STATUS  current
    DESCRIPTION
      "Maximum number of apm sessions."
    ::= { rsAPMTuning 11 }

rsAPMNumberOfApmSessionsAfterReset OBJECT-TYPE
    SYNTAX INTEGER
    MAX-ACCESS  read-write
    STATUS  current
    DESCRIPTION
      "Maximum number of apm sessions after reset."
    ::=  { rsAPMTuning 12 }

rsAPMNumberOfPoliciesPerSession OBJECT-TYPE
    SYNTAX INTEGER
    MAX-ACCESS  read-only
    STATUS  current
    DESCRIPTION
      "Maximum average number of policies per session."
    ::= { rsAPMTuning 13 }

rsAPMNumberOfPoliciesPerSessionAfterReset OBJECT-TYPE
    SYNTAX INTEGER
    MAX-ACCESS  read-write
    STATUS  current
    DESCRIPTION
      "Maximum average number of policies per session after reset."
    ::=  { rsAPMTuning 14 }

rsAPMCurrentPolicyTable OBJECT-TYPE
    SYNTAX SEQUENCE OF RsAPMCurrentPolicyEntry
    MAX-ACCESS not-accessible
    STATUS  current
    DESCRIPTION
      "Table containing the list of APM policies."
    ::=  { rsAPM 8 }

rsAPMCurrentPolicyEntry OBJECT-TYPE
    SYNTAX RsAPMCurrentPolicyEntry
    MAX-ACCESS not-accessible
    STATUS  current
    DESCRIPTION
       "The row definition for the APM policies table."
    INDEX { rsAPMCurrentPolicyID }
    ::=  { rsAPMCurrentPolicyTable 1 }

RsAPMCurrentPolicyEntry ::= SEQUENCE {
    rsAPMCurrentPolicyID INTEGER,
    rsAPMCurrentPolicyRowStatus RowStatus,
    rsAPMCurrentPolicyName DisplayString,
    rsAPMCurrentPolicyEnabledStatus INTEGER,
    rsAPMCurrentPolicyDescription DisplayString,
    rsAPMCurrentPolicyDestination DisplayString,
    rsAPMCurrentPolicySource DisplayString,
    rsAPMCurrentPolicyFilter DisplayString,
    rsAPMCurrentPolicyFilterType INTEGER,
    rsAPMCurrentPolicyPhysicalPortGroup DisplayString,
    rsAPMCurrentPolicyVLANTagGroup DisplayString,
    rsAPMCurrentPolicyL4Protocol L4Protocol,
    rsAPMCurrentPolicyL7Protocol L7Protocol,
    rsAPMCurrentPolicyReportInterval INTEGER,
    rsAPMCurrentPolicyReportSubInterval INTEGER,
    rsAPMCurrentPolicyNextReportIntervalID INTEGER,
    rsAPMCurrentPolicyRemainingTimeTillNextReportIntervalStart INTEGER,
    rsAPMCurrentPolicyReportViaSrp Bool,
    rsAPMCurrentPolicyInsiteInfo DisplayString
}

rsAPMCurrentPolicyID OBJECT-TYPE
    SYNTAX INTEGER
    MAX-ACCESS  read-only
    STATUS  current
    DESCRIPTION
       "This variable indicates the administrative ID of a policy. APM policies
       have no order semantics, so this ID is used for identification purposes only."
    ::=  { rsAPMCurrentPolicyEntry 1 }

rsAPMCurrentPolicyRowStatus OBJECT-TYPE
    SYNTAX RowStatus
    MAX-ACCESS  read-write
    STATUS  current
    DESCRIPTION
       "This variable indicates the administrative status of this entry. Only here so 
        insite can update enable status. Must therefore be set only for modify."
    ::=  { rsAPMCurrentPolicyEntry 2 }


rsAPMCurrentPolicyName OBJECT-TYPE
    SYNTAX DisplayString (SIZE(0..32))
    MAX-ACCESS  read-only
    STATUS  current
    DESCRIPTION
      "The name for the APM policy. Must be unique."
    ::=  { rsAPMCurrentPolicyEntry 3 }


rsAPMCurrentPolicyEnabledStatus OBJECT-TYPE
    SYNTAX INTEGER {
        enabled (1),
        disabled (2)
    }
    MAX-ACCESS  read-write
    STATUS  current
    DESCRIPTION
       "This variable indicates if the policy is monitoring traffic at the moment
       or not. Policies in the modified policy table are not monitoring traffic
       by definition."
    ::= { rsAPMCurrentPolicyEntry 4 }

rsAPMCurrentPolicyDescription OBJECT-TYPE
    SYNTAX DisplayString (SIZE(0..64))
    MAX-ACCESS  read-only
    STATUS  current
    DESCRIPTION
      "Description."
    ::=  { rsAPMCurrentPolicyEntry 5 }

rsAPMCurrentPolicyDestination OBJECT-TYPE
    SYNTAX DisplayString (SIZE(0..20))
    MAX-ACCESS  read-only
    STATUS  current
    DESCRIPTION
      "The destination address / range of addresses for monitored sessions. The destination
      is defined as the server side, i.e., the side sending response packets. The
      name is defined in the classifier networks table or can be an IP address."
    ::=  { rsAPMCurrentPolicyEntry 6 }

rsAPMCurrentPolicySource OBJECT-TYPE
    SYNTAX DisplayString (SIZE(0..32))
    MAX-ACCESS  read-only
    STATUS  current
    DESCRIPTION
      "The source address / range of addresses for monitored sessions. The source
      is defined as the client side, i.e., the side sending request packets. The
      name is defined in the classifier networks table or can be an IP address."
    ::=  { rsAPMCurrentPolicyEntry 7 }

rsAPMCurrentPolicyFilter OBJECT-TYPE
    SYNTAX DisplayString (SIZE(0..32))
    MAX-ACCESS  read-only
    STATUS  current
    DESCRIPTION
       "The name of the filter, defined in the classifier filter table, for the APM policy."
    ::=  { rsAPMCurrentPolicyEntry 8 }

rsAPMCurrentPolicyFilterType OBJECT-TYPE
    SYNTAX INTEGER {
        basic (1),
        advanced (2),
        group (3)
    }
    MAX-ACCESS  read-only
    STATUS  current
    DESCRIPTION
       "The Type OF Filter."
    ::=  { rsAPMCurrentPolicyEntry 9 }


rsAPMCurrentPolicyPhysicalPortGroup OBJECT-TYPE
    SYNTAX DisplayString (SIZE(0..32))
    MAX-ACCESS  read-only
    STATUS  current
    DESCRIPTION
       "The name of the physical port group, defined by the classifier, for the policy."
    ::=  { rsAPMCurrentPolicyEntry 10 }

rsAPMCurrentPolicyVLANTagGroup OBJECT-TYPE
    SYNTAX DisplayString (SIZE(0..32))
    MAX-ACCESS  read-only
    STATUS  current
    DESCRIPTION
        "The name of the VLAN tag group, defined by the classifier, for this rule."
    ::= { rsAPMCurrentPolicyEntry 11 }

rsAPMCurrentPolicyL4Protocol OBJECT-TYPE
    SYNTAX L4Protocol
    MAX-ACCESS  read-only
    STATUS  current
    DESCRIPTION
       "The L4 protocol monitored by the policy."
    ::=  { rsAPMCurrentPolicyEntry 12 }

rsAPMCurrentPolicyL7Protocol OBJECT-TYPE
    SYNTAX L7Protocol
    MAX-ACCESS  read-only
    STATUS  current
    DESCRIPTION
       "The L7 protocol monitored by the policy."
    DEFVAL  { generic }
    ::=  { rsAPMCurrentPolicyEntry 13 }

rsAPMCurrentPolicyReportInterval OBJECT-TYPE
    SYNTAX INTEGER 
    MAX-ACCESS  read-only
    STATUS  current
    DESCRIPTION
       "The reporting interval to Insite. Specified in seconds."
    ::=  { rsAPMCurrentPolicyEntry 14 }

rsAPMCurrentPolicyReportSubInterval OBJECT-TYPE
    SYNTAX INTEGER 
    MAX-ACCESS  read-only
    STATUS  current
    DESCRIPTION
       "The reporting sub interval. Specified in seconds."
    ::=  { rsAPMCurrentPolicyEntry 15 }

rsAPMCurrentPolicyNextReportIntervalID OBJECT-TYPE
    SYNTAX INTEGER 
    MAX-ACCESS  read-write
    STATUS  current
    DESCRIPTION
       "The ID of the next report interval."
    DEFVAL  { 0 }
    ::=  { rsAPMCurrentPolicyEntry 16 }

rsAPMCurrentPolicyRemainingTimeTillNextReportIntervalStart OBJECT-TYPE
    SYNTAX INTEGER 
    MAX-ACCESS  read-write
    STATUS  current
    DESCRIPTION
       "Specifies the remaining time, in msec, until the start of the next report interval."
    ::=  { rsAPMCurrentPolicyEntry 17 }

rsAPMCurrentPolicyReportViaSrp OBJECT-TYPE
    SYNTAX Bool
    MAX-ACCESS  read-only
    STATUS  current
    DESCRIPTION
       "Specifies whether the monitored data items for this policy should
       be reported via SRP or not."
    ::=  { rsAPMCurrentPolicyEntry 18 }

rsAPMCurrentPolicyInsiteInfo OBJECT-TYPE
    SYNTAX DisplayString (SIZE(0..64))
    MAX-ACCESS  read-only
    STATUS  current
    DESCRIPTION
       "Generic 64 Bytes used by insite to store info in the policy."
    ::=  { rsAPMCurrentPolicyEntry 19 }


rsAPMCurrentMonitorTable OBJECT-TYPE
    SYNTAX SEQUENCE OF RsAPMCurrentMonitorEntry
    MAX-ACCESS not-accessible
    STATUS  current
    DESCRIPTION
      "Table containing the list of APM monitors."
    ::=  { rsAPM 9 }

rsAPMCurrentMonitorEntry OBJECT-TYPE
    SYNTAX RsAPMCurrentMonitorEntry
    MAX-ACCESS not-accessible
    STATUS  current
    DESCRIPTION
       "The row definition for the APM policies table."
    INDEX { rsAPMCurrentMonitorPolicyID, rsAPMCurrentMonitorID }
    ::=  { rsAPMCurrentMonitorTable 1 }

RsAPMCurrentMonitorEntry ::= SEQUENCE {
    rsAPMCurrentMonitorPolicyID INTEGER,
    rsAPMCurrentMonitorID INTEGER,
    rsAPMCurrentMonitorType INTEGER,
    rsAPMCurrentMonitorFarmID DisplayString,
    rsAPMCurrentMonitorDirectionOrientation INTEGER,
    rsAPMCurrentMonitorItemsToCollect CollectItems
}

rsAPMCurrentMonitorPolicyID OBJECT-TYPE
    SYNTAX INTEGER
    MAX-ACCESS  read-only
    STATUS  current
    DESCRIPTION
       "This variable indicates the administrative ID of the APM policy this monitor belongs to."
    ::=  { rsAPMCurrentMonitorEntry 1 }

rsAPMCurrentMonitorID OBJECT-TYPE
    SYNTAX INTEGER
    MAX-ACCESS  read-only
    STATUS  current
    DESCRIPTION
       "This variable indicates the administrative ID of a monitor. This ID is used for identification purposes only."
    ::=  { rsAPMCurrentMonitorEntry 2 }

rsAPMCurrentMonitorType OBJECT-TYPE
    SYNTAX INTEGER {
        device (1),
        farm (2)
    }
    MAX-ACCESS  read-only
    STATUS  current
    DESCRIPTION
       "The monitor type."
    ::= { rsAPMCurrentMonitorEntry 3 }

rsAPMCurrentMonitorFarmID OBJECT-TYPE
    SYNTAX DisplayString (SIZE(0..32))
    MAX-ACCESS  read-only
    STATUS  current
    DESCRIPTION
       "The farm ID of the farm that is being monitored. Not relevant for device monitors."
    ::=  { rsAPMCurrentMonitorEntry 4 }

rsAPMCurrentMonitorDirectionOrientation OBJECT-TYPE
    SYNTAX INTEGER { 
        source (1),
        destination (2)
    }
    MAX-ACCESS  read-only
    STATUS  current
    DESCRIPTION
       "Specifies the direction orientation of the monitor. Monitors with 'source'
       direction orientation will have packets associated to them according to
       the farm from which request packets arrived and the farm to which response packets
       were sent. Monitors with 'destination' direction orientation will have packets
       associated to them according to the farm to which request packets were sent and the
       farm from which response packets arrived."
    ::=  { rsAPMCurrentMonitorEntry 5 }


rsAPMCurrentMonitorItemsToCollect OBJECT-TYPE
    SYNTAX CollectItems
    MAX-ACCESS  read-only
    STATUS  current
    DESCRIPTION
       "The items to collect."
    ::=  { rsAPMCurrentMonitorEntry 6 }


rsAPMCurrentLegFarmTable OBJECT-TYPE
    SYNTAX SEQUENCE OF RsAPMCurrentLegFarmEntry 
    MAX-ACCESS not-accessible
    STATUS  current
    DESCRIPTION
      "Table listing all the leg farms that will be encountered by a policy, per policy.
      Any farm encountered by a policy that is not listed in this table will be considered
      to be an edge farm."
    ::=  { rsAPM 10 }

rsAPMCurrentLegFarmEntry OBJECT-TYPE
    SYNTAX RsAPMCurrentLegFarmEntry
    MAX-ACCESS not-accessible
    STATUS  current
    DESCRIPTION
       "The row definition for the APM leg farm table."
    INDEX { rsAPMCurrentLegFarmPolicyID,rsAPMCurrentLegFarmIndex}
    ::=  { rsAPMCurrentLegFarmTable 1 }

RsAPMCurrentLegFarmEntry ::= SEQUENCE {
    rsAPMCurrentLegFarmPolicyID INTEGER,
    rsAPMCurrentLegFarmIndex    INTEGER,
    rsAPMCurrentLegFarmFarmID DisplayString
}

rsAPMCurrentLegFarmPolicyID  OBJECT-TYPE
    SYNTAX INTEGER
    MAX-ACCESS  read-only
    STATUS  current
    DESCRIPTION
       "This variable indicates the administrative ID of the APM policy this leg farm belongs to."
    ::=  { rsAPMCurrentLegFarmEntry 1 }

rsAPMCurrentLegFarmIndex  OBJECT-TYPE
    SYNTAX INTEGER
    MAX-ACCESS  read-only
    STATUS  current
    DESCRIPTION
       "Index of the leg farm"
    ::=  { rsAPMCurrentLegFarmEntry 2 }

    
rsAPMCurrentLegFarmFarmID  OBJECT-TYPE
    SYNTAX DisplayString (SIZE(0..32))
    MAX-ACCESS  read-only
    STATUS  current
    DESCRIPTION
       "This variable indicates the ID of this leg farm."
    ::=  { rsAPMCurrentLegFarmEntry  3 }

rsAPMEnabledStatus OBJECT-TYPE
    SYNTAX INTEGER {
        enabled (1),
        disabled (2)
    }
    MAX-ACCESS  read-write
    STATUS  current
    DESCRIPTION
        "Enable/disable the apm - becomes valid after reboot. Get returns the current runtime value"
    ::=  {rsAPM 11}
    
rsAPMUpdateAllPolicies OBJECT-TYPE
    SYNTAX  INTEGER
    MAX-ACCESS  read-write
    STATUS  current
    DESCRIPTION
        "Updates all apm policies (temp becomes active). Any value is valid"
    DEFVAL  { 1 }
    ::=  {rsAPM 12}

rsAPMUpdatePolicy OBJECT-TYPE
    SYNTAX  INTEGER
    MAX-ACCESS  read-write
    STATUS  current
    DESCRIPTION
        "Updates a single apm policy (temp becomes active for specified policy)"
    DEFVAL  { 1 }
    ::=  {rsAPM 13}


rsAPMResetApm OBJECT-TYPE
    SYNTAX  INTEGER
    MAX-ACCESS  read-write
    STATUS  current
    DESCRIPTION
        "Reset Apm to an empty configuration. Any value is valid"
    DEFVAL  { 1 }
    ::=  {rsAPM 14}

rsAPMResetApmFromDatabase OBJECT-TYPE
    SYNTAX  INTEGER
    MAX-ACCESS  read-write
    STATUS  current
    DESCRIPTION
        "Resets the apm configuration from the database. Any value is valid"
    DEFVAL  { 1 }
    ::=  {rsAPM 15}


rsAPMGlobalParameters  OBJECT IDENTIFIER ::= { rsAPM 17 }

rsAPMSamplingAlgorithm OBJECT-TYPE
    SYNTAX SamplingAlgorithm
    MAX-ACCESS  read-write
    STATUS  current
    DESCRIPTION
       "The sampling algorithm to be used"
    DEFVAL  { deterministic }
    ::=  { rsAPMGlobalParameters 1 }

rsAPMSamplingRate OBJECT-TYPE
    SYNTAX INTEGER (1..100)
    MAX-ACCESS  read-write
    STATUS  current
    DESCRIPTION
       "The rate to be used. Specified in percentage. Valid range is 1-100."
    ::=  { rsAPMGlobalParameters 2 }


rsAPMUsePreciseSampling OBJECT-TYPE
    SYNTAX Bool
    MAX-ACCESS  read-write
    STATUS  current
    DESCRIPTION
       "Specifies whether te apm should use precise sampling"
    ::=  { rsAPMGlobalParameters 3 }

rsAPMTimerMode  OBJECT-TYPE
    SYNTAX INTEGER {
        automatic (1),
        manual (2)
    }
    MAX-ACCESS  read-write
    STATUS  current
    DESCRIPTION
        "Timer Mode for the APM"
    DEFVAL  { 1 }
    ::=  { rsAPMGlobalParameters 4 }

rsAPMInsiteConfigurationId OBJECT-TYPE
    SYNTAX INTEGER
    MAX-ACCESS  read-write
    STATUS  current
    DESCRIPTION
       "Id of the insite configuration - set/read by insite"
    ::=  { rsAPMGlobalParameters 5 }

END
