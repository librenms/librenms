-- ============================================================================
-- AT-LOG.MIB, Allied Telesis enterprise MIB:
-- Log MIB for the AlliedWare Plus(tm) operating system
-- 
-- Copyright (c) 2008 by Allied Telesis, Inc.
-- All rights reserved.
-- 
-- ============================================================================

	AT-LOG-MIB DEFINITIONS ::= BEGIN
 
		IMPORTS
			modules			
				FROM AT-SMI-MIB			
			Integer32, Unsigned32, OBJECT-TYPE, MODULE-IDENTITY			
				FROM SNMPv2-SMI;
	
	
		-- 1.3.6.1.4.1.207.8.4.4.4.601
		log MODULE-IDENTITY 
			LAST-UPDATED "200810080000Z"		-- October 08, 2008 at 00:00 GMT
			ORGANIZATION 
				"Allied Telesis Labs New Zealand"
			CONTACT-INFO 
				"http://www.alliedtelesis.com"
			DESCRIPTION 
				"The AT Log MIB, for listing log entries from the buffered and permament logs."
			REVISION "200810080000Z"		-- October 08, 2008 at 00:00 GMT
			DESCRIPTION 
				"Initial revision."
			::= { modules 601 }

		
	
	
--
-- Node definitions
--
	
-- ---------------------------------------------------------- --
-- The log table
-- ---------------------------------------------------------- --
		-- 1.3.6.1.4.1.207.8.4.4.4.601.1
		logTable OBJECT-TYPE
			SYNTAX SEQUENCE OF LogEntry
			MAX-ACCESS not-accessible
			STATUS current
			DESCRIPTION
				"A list of log entries from the source specified in the logSource object. The list is ordered
				from oldest entry to newest entry."
			::= { log 1 }

		
		-- 1.3.6.1.4.1.207.8.4.4.4.601.1.1
		logEntry OBJECT-TYPE
			SYNTAX LogEntry
			MAX-ACCESS not-accessible
			STATUS current
			DESCRIPTION
				"A log entry from the source specified in the logSource object."
			INDEX { logIndex }
			::= { logTable 1 }

		
		LogEntry ::=
			SEQUENCE { 
				logIndex
					Unsigned32,
				logDate
					OCTET STRING,
				logTime
					OCTET STRING,
				logFacility
					OCTET STRING,
				logSeverity
					OCTET STRING,
				logProgram
					OCTET STRING,
				logMessage
					OCTET STRING
			 }

		-- 1.3.6.1.4.1.207.8.4.4.4.601.1.1.1
		logIndex OBJECT-TYPE
			SYNTAX Unsigned32
			MAX-ACCESS read-only
			STATUS current
			DESCRIPTION
				"An index integer. This index is not directly tied to any specific log entry. Over time, the log
				will grow larger and eventually older entries will be removed from the log."
			::= { logEntry 1 }

		
		-- 1.3.6.1.4.1.207.8.4.4.4.601.1.1.2
		logDate OBJECT-TYPE
			SYNTAX OCTET STRING
			MAX-ACCESS read-only
			STATUS current
			DESCRIPTION
				"The date of the log entry, in the form YYYY MMM DD, eg: 2008 Oct  9."
			::= { logEntry 2 }

		
		-- 1.3.6.1.4.1.207.8.4.4.4.601.1.1.3
		logTime OBJECT-TYPE
			SYNTAX OCTET STRING
			MAX-ACCESS read-only
			STATUS current
			DESCRIPTION
				"The time of the log entry, in the form HH:MM:SS, eg: 07:15:04."
			::= { logEntry 3 }

		
		-- 1.3.6.1.4.1.207.8.4.4.4.601.1.1.4
		logFacility OBJECT-TYPE
			SYNTAX OCTET STRING
			MAX-ACCESS read-only
			STATUS current
			DESCRIPTION
				"The syslog facility that generated the log entry. See the reference manual for more 
				information."
			::= { logEntry 4 }

		
		-- 1.3.6.1.4.1.207.8.4.4.4.601.1.1.5
		logSeverity OBJECT-TYPE
			SYNTAX OCTET STRING
			MAX-ACCESS read-only
			STATUS current
			DESCRIPTION
				"The severity level of the log entry. Severities are given below:
				
				emerg     Emergency, system is unusable
				alert     Action must be taken immediately
				crit      Critical conditions
				err       Error conditions
				warning   Warning conditions
				notice    Normal, but significant, conditions
				info      Informational messages
				debug     Debug-level messages"
			::= { logEntry 5 }

		
		-- 1.3.6.1.4.1.207.8.4.4.4.601.1.1.6
		logProgram OBJECT-TYPE
			SYNTAX OCTET STRING
			MAX-ACCESS read-only
			STATUS current
			DESCRIPTION
				"The program that generated the log entry. See the reference manual for more information."
			::= { logEntry 6 }

		
		-- 1.3.6.1.4.1.207.8.4.4.4.601.1.1.7
		logMessage OBJECT-TYPE
			SYNTAX OCTET STRING
			MAX-ACCESS read-only
			STATUS current
			DESCRIPTION
				"The message of the log entry."
			::= { logEntry 7 }

		
-- ---------------------------------------------------------- --
-- The log options
-- ---------------------------------------------------------- --
		-- 1.3.6.1.4.1.207.8.4.4.4.601.2
		logOptions OBJECT IDENTIFIER::= { log 2 }

		
		-- 1.3.6.1.4.1.207.8.4.4.4.601.2.1
		logSource OBJECT-TYPE
			SYNTAX Integer32 (1..2)
			MAX-ACCESS read-write
			STATUS current
			DESCRIPTION
				"The source to retrieve the log entries from. The valid values are:
				1. Buffered log (default)
				2. Permanent log.
				
				This source is used when retrieving the logTable objects, and also specifies the log to
				be cleared when the clearLog object is set."
			DEFVAL { 1 }
			::= { logOptions 1 }

		
		-- 1.3.6.1.4.1.207.8.4.4.4.601.2.2
		logAll OBJECT-TYPE
			SYNTAX Integer32 (0..1)
			MAX-ACCESS read-write
			STATUS current
			DESCRIPTION
				"Whether to display all log entries in the logTable objects or not. The default is 0, which 
				will display the most recent log messages only. Set with 1 to show all available log entries.
				
				Note: Choosing to display all log entries may result in delays of several seconds when
				accessing the logTable objects."
			DEFVAL { 0 }
			::= { logOptions 2 }

		
		-- 1.3.6.1.4.1.207.8.4.4.4.601.2.3
		clearLog OBJECT-TYPE
			SYNTAX Integer32 (0..1)
			MAX-ACCESS read-write
			STATUS current
			DESCRIPTION
				"Set with a value of 1 to clear the log that is specified by the logSource object."
			::= { logOptions 3 }

		
	
	END

--
-- AT-LOG-MIB.mib
--
