SKYLONE-MIB DEFINITIONS ::= BEGIN

	-- Version: 1.0

	-- SUBTREE: 1.3.6.1.4.1.51009
	-- iso.org.dod.internet.private.enterprises.skylone
	  
	IMPORTS
		MODULE-IDENTITY, OBJECT-TYPE, Gauge32, Integer32, enterprises
			FROM SNMPv2-SMI
		TEXTUAL-CONVENTION, DisplayString, TimeStamp, DateAndTime
			FROM SNMPv2-TC;
	--	MODULE-COMPLIANCE, OBJECT-GROUP
	--		FROM SNMPv2-CONF;

	skylone MODULE-IDENTITY
		LAST-UPDATED
			"201811252137Z"
		ORGANIZATION
			"Skylone Technology Ltd."
		CONTACT-INFO
            		"Gokhan Poyraz
			Skylone Teknoloji Sanayi Ticaret ve Limited Sirketi
			Barbaros Mah. Kardelen Sk.
			Palladium Tower No:2 K10
			Istanbul, Atasehir 34746
			TR

			+90 (216) 687 0363
			gokhanp@skylone.com"
		DESCRIPTION
			"The MIB that supports Skylone products"

		REVISION
			"201811252137Z"
		DESCRIPTION
			"Initial revision"
	::= { enterprises 51009 }

	BufferSize ::= TEXTUAL-CONVENTION
		DISPLAY-HINT "d-2"
		STATUS  current
		DESCRIPTION
			"A buffer type definition which is two digit shifted value
			 in format secods.milliseconds"
		SYNTAX  Integer32 (0..10000)

	productInfo	OBJECT IDENTIFIER ::= { skylone 1 }

	-- skylone.productInfo subtree
	productName OBJECT-TYPE
		SYNTAX  DisplayString
		MAX-ACCESS  read-only
		STATUS  current
		DESCRIPTION
			"Product Name"
		::= {productInfo 1 }

	productVersion OBJECT-TYPE
		SYNTAX  DisplayString
		MAX-ACCESS  read-only
		STATUS  current
		DESCRIPTION
			"Version"
		::= {productInfo 2 }

	productBuild OBJECT-TYPE
		SYNTAX  DisplayString
		MAX-ACCESS  read-only
		STATUS  current
		DESCRIPTION
			"Build"
		::= {productInfo 3 }

	sysResource	OBJECT IDENTIFIER ::= { skylone 2 }

	-- skylone.sysResource subtree
	sysResourceCPU OBJECT-TYPE
		SYNTAX  Integer32
		MAX-ACCESS  read-only
		STATUS  current
		DESCRIPTION
			"CPU Usage"
		::= {sysResource 1 }

	sysResourceMEM OBJECT-TYPE
		SYNTAX  Integer32
		MAX-ACCESS  read-only
		STATUS  current
		DESCRIPTION
			"Memory Usage"
		::= {sysResource 2 }

	dbaseResource	OBJECT IDENTIFIER ::= { skylone 3 }

	-- skylone.dbaseResource subtree
	dbaseCache OBJECT-TYPE
		SYNTAX  Integer32
		MAX-ACCESS  read-only
		STATUS  current
		DESCRIPTION
			"Cache"
		::= {dbaseResource 1 }

	dbaseOpen OBJECT-TYPE
		SYNTAX  Integer32
		MAX-ACCESS  read-only
		STATUS  current
		DESCRIPTION
			"Open"
		::= {dbaseResource 2 }

	dbasePool OBJECT-TYPE
		SYNTAX  Integer32
		MAX-ACCESS  read-only
		STATUS  current
		DESCRIPTION
			"Pool"
		::= {dbaseResource 3 }

	dbaseLive OBJECT-TYPE
		SYNTAX  Integer32
		MAX-ACCESS  read-only
		STATUS  current
		DESCRIPTION
			"Live"
		::= {dbaseResource 4 }

	dbasePeak OBJECT-TYPE
		SYNTAX  Integer32
		MAX-ACCESS  read-only
		STATUS  current
		DESCRIPTION
			"Peak"
		::= {dbaseResource 5 }

	srvResource	OBJECT IDENTIFIER ::= { skylone 4 }

	-- skylone.srvResource subtree
	srvResourceUser OBJECT-TYPE
		SYNTAX  Integer32
		MAX-ACCESS  read-only
		STATUS  current
		DESCRIPTION
			"Number of User"
		::= {srvResource 1}

	srvResourceMaxUser OBJECT-TYPE
		SYNTAX  Integer32
		MAX-ACCESS  read-only
		STATUS  current
		DESCRIPTION
			"Maximum Number of User"
		::= {srvResource 2}

	srvResourceActiveUser OBJECT-TYPE
		SYNTAX  Integer32
		MAX-ACCESS  read-only
		STATUS  current
		DESCRIPTION
			"Number of Active User"
		::= {srvResource 3}

	srvResourceWaitingUser OBJECT-TYPE
		SYNTAX  Integer32
		MAX-ACCESS  read-only
		STATUS  current
		DESCRIPTION
			"Number of Waiting User"
		::= {srvResource 4}

	srvStatus	OBJECT IDENTIFIER ::= { skylone 5 }

	tpStatus	OBJECT IDENTIFIER ::= { skylone 6 }

	-- skylone.tpStatus subtree
	tpNumber OBJECT-TYPE
		SYNTAX  Integer32
		MAX-ACCESS  read-only
		STATUS  current
		DESCRIPTION
			"Number of Transponders"
		::= { tpStatus 1 }

	tpTable OBJECT-TYPE
		SYNTAX  SEQUENCE OF TpEntry
		MAX-ACCESS  not-accessible
		STATUS  current
		DESCRIPTION
			"List of Transponder entries"
		::= { tpStatus 2 }

	tpEntry OBJECT-TYPE
		SYNTAX  TpEntry
		MAX-ACCESS  not-accessible
		STATUS  current
		DESCRIPTION
			"A Transponder Entry"
		INDEX   { tpIndex }
		::= { tpTable 1 }

	TpEntry ::= SEQUENCE {
		tpIndex Integer32,
		tpName DisplayString,
		tpSignal DisplayString,
		tpSync DisplayString,
		tpLock DisplayString,
		tpStrength Integer32,
		tpSnr Integer32,
		tpBitrate Gauge32,
		tpInvalid Integer32,
		tpError Integer32,
		tpDiscont Integer32,
		tpNumConfig Integer32,
		tpNumService Integer32
	}
 
	tpIndex OBJECT-TYPE
		SYNTAX  Integer32 (1..2147483647)
		MAX-ACCESS  not-accessible
		STATUS  current
		DESCRIPTION
        		"A unique value for each Transponder"
		::= { tpEntry 1 }

	tpName OBJECT-TYPE
		SYNTAX  DisplayString
		MAX-ACCESS  read-only
		STATUS  current
		DESCRIPTION
        		"Name of the Transponder"
		::= { tpEntry 2 }

	tpSignal OBJECT-TYPE
		SYNTAX  DisplayString
		MAX-ACCESS  read-only
		STATUS  current
		DESCRIPTION
        		"Signal Status of the Transponder"
		::= { tpEntry 3 }

	tpSync OBJECT-TYPE
		SYNTAX  DisplayString
		MAX-ACCESS  read-only
		STATUS  current
		DESCRIPTION
        		"Sync Satus of the Transponder"
		::= { tpEntry 4 }

	tpLock OBJECT-TYPE
		SYNTAX  DisplayString
		MAX-ACCESS  read-only
		STATUS  current
		DESCRIPTION
        		"Lock Status of the Transponder"
		::= { tpEntry 5 }

	tpStrength OBJECT-TYPE
		SYNTAX  Integer32
		MAX-ACCESS  read-only
		STATUS  current
		DESCRIPTION
        		"Signal Strength of the Transponder"
		::= { tpEntry 6 }

	tpSnr OBJECT-TYPE
		SYNTAX  Integer32
		MAX-ACCESS  read-only
		STATUS  current
		DESCRIPTION
        		"SNR Level of the Transponder"
		::= { tpEntry 7 }

	tpBitrate OBJECT-TYPE
		SYNTAX  Gauge32
		MAX-ACCESS  read-only
		STATUS  current
		DESCRIPTION
        		"Bitrate of the Transponder"
		::= { tpEntry 8 }

	tpInvalid OBJECT-TYPE
		SYNTAX  Integer32
		MAX-ACCESS  read-only
		STATUS  current
		DESCRIPTION
        		"Number of Invalid packets of the Transponder"
		::= { tpEntry 9 }

	tpError OBJECT-TYPE
		SYNTAX  Integer32
		MAX-ACCESS  read-only
		STATUS  current
		DESCRIPTION
        		"Number of Errors of the Transponder"
		::= { tpEntry 10 }

	tpDiscont OBJECT-TYPE
		SYNTAX  Integer32
		MAX-ACCESS  read-only
		STATUS  current
		DESCRIPTION
        		"Number of Discontinues of the Transponder"
		::= { tpEntry 11 }

	tpNumConfig OBJECT-TYPE
		SYNTAX  Integer32
		MAX-ACCESS  read-only
		STATUS  current
		DESCRIPTION
        		"Number of configured services of the Transponder"
		::= { tpEntry 12 }

	tpNumService OBJECT-TYPE
		SYNTAX  Integer32
		MAX-ACCESS  read-only
		STATUS  current
		DESCRIPTION
        		"Total number of sevices available in the Transponder"
		::= { tpEntry 13 }

	mptStatus	OBJECT IDENTIFIER ::= { skylone 7 }

	-- skylone.mptStatus subtree
	mptNumber OBJECT-TYPE
		SYNTAX  Integer32
		MAX-ACCESS  read-only
		STATUS  current
		DESCRIPTION
			"Number of MPTS Inputs"
		::= { mptStatus 1 }

	mptTable OBJECT-TYPE
		SYNTAX  SEQUENCE OF MptEntry
		MAX-ACCESS  not-accessible
		STATUS  current
		DESCRIPTION
			"List of MPTS Input entries"
		::= { mptStatus 2 }

	mptEntry OBJECT-TYPE
		SYNTAX  MptEntry
		MAX-ACCESS  not-accessible
		STATUS  current
		DESCRIPTION
			"A MPTS Input Entry"
		INDEX   { mptIndex }
		::= { mptTable 1 }

	MptEntry ::= SEQUENCE {
		mptIndex Integer32,
		mptName DisplayString,
		mptLock DisplayString,
		mptBitrate Gauge32,
		mptInvalid Integer32,
		mptError Integer32,
		mptDiscont Integer32,
		mptNumConfig Integer32,
		mptNumService Integer32
	}
 
	mptIndex OBJECT-TYPE
		SYNTAX  Integer32 (1..2147483647)
		MAX-ACCESS  not-accessible
		STATUS  current
		DESCRIPTION
        		"A unique value for each MPTS Input"
		::= { mptEntry 1 }

	mptName OBJECT-TYPE
		SYNTAX  DisplayString
		MAX-ACCESS  read-only
		STATUS  current
		DESCRIPTION
        		"Name of the MPTS Input"
		::= { mptEntry 2 }

	mptLock OBJECT-TYPE
		SYNTAX  DisplayString
		MAX-ACCESS  read-only
		STATUS  current
		DESCRIPTION
        		"Lock Status of the MPTS Input"
		::= { mptEntry 3 }

	mptBitrate OBJECT-TYPE
		SYNTAX  Gauge32
		MAX-ACCESS  read-only
		STATUS  current
		DESCRIPTION
        		"Bitrate of the MPTS Input"
		::= { mptEntry 4 }

	mptInvalid OBJECT-TYPE
		SYNTAX  Integer32
		MAX-ACCESS  read-only
		STATUS  current
		DESCRIPTION
        		"Number of Invalid packets of the MPTS Input"
		::= { mptEntry 5 }

	mptError OBJECT-TYPE
		SYNTAX  Integer32
		MAX-ACCESS  read-only
		STATUS  current
		DESCRIPTION
        		"Number of Errors of the MPTS Input"
		::= { mptEntry 6 }

	mptDiscont OBJECT-TYPE
		SYNTAX  Integer32
		MAX-ACCESS  read-only
		STATUS  current
		DESCRIPTION
        		"Number of Discontinues of the MPTS Input"
		::= { mptEntry 7 }

	mptNumConfig OBJECT-TYPE
		SYNTAX  Integer32
		MAX-ACCESS  read-only
		STATUS  current
		DESCRIPTION
        		"Number of configured services of the MPTS Input"
		::= { mptEntry 8 }

	mptNumService OBJECT-TYPE
		SYNTAX  Integer32
		MAX-ACCESS  read-only
		STATUS  current
		DESCRIPTION
        		"Total number of sevices available in the MPTS Input"
		::= { mptEntry 9 }

	muxStatus	OBJECT IDENTIFIER ::= { skylone 8 }

	-- skylone.muxStatus subtree
	muxNumber OBJECT-TYPE
		SYNTAX  Integer32
		MAX-ACCESS  read-only
		STATUS  current
		DESCRIPTION
			"Number of Multiplexers"
		::= { muxStatus 1 }

	muxTable OBJECT-TYPE
		SYNTAX  SEQUENCE OF MuxEntry
		MAX-ACCESS  not-accessible
		STATUS  current
		DESCRIPTION
			"List of Multiplexer entries"
		::= { muxStatus 2 }

	muxEntry OBJECT-TYPE
		SYNTAX  MuxEntry
		MAX-ACCESS  not-accessible
		STATUS  current
		DESCRIPTION
			"A Multiplexer Entry"
		INDEX   { muxIndex }
		::= { muxTable 1 }

	MuxEntry ::= SEQUENCE {
		muxIndex Integer32,
		muxName DisplayString,
		muxLock DisplayString,
		muxBitrate Gauge32,
		muxInvalid Integer32,
		muxError Integer32,
		muxDiscont Integer32,
		muxNumActive Integer32,
		muxNumConfig Integer32
	}
 
	muxIndex OBJECT-TYPE
		SYNTAX  Integer32 (1..2147483647)
		MAX-ACCESS  not-accessible
		STATUS  current
		DESCRIPTION
        		"A unique value for each Multiplexer"
		::= { muxEntry 1 }

	muxName OBJECT-TYPE
		SYNTAX  DisplayString
		MAX-ACCESS  read-only
		STATUS  current
		DESCRIPTION
        		"Name of the Multiplexer"
		::= { muxEntry 2 }

	muxLock OBJECT-TYPE
		SYNTAX  DisplayString
		MAX-ACCESS  read-only
		STATUS  current
		DESCRIPTION
        		"Lock Status of the Multiplexer"
		::= { muxEntry 3 }

	muxBitrate OBJECT-TYPE
		SYNTAX  Gauge32
		MAX-ACCESS  read-only
		STATUS  current
		DESCRIPTION
        		"Bitrate of the Multiplexer"
		::= { muxEntry 4 }

	muxInvalid OBJECT-TYPE
		SYNTAX  Integer32
		MAX-ACCESS  read-only
		STATUS  current
		DESCRIPTION
        		"Number of Invalid packets of the Multiplexer"
		::= { muxEntry 5 }

	muxError OBJECT-TYPE
		SYNTAX  Integer32
		MAX-ACCESS  read-only
		STATUS  current
		DESCRIPTION
        		"Number of Errors of the Multiplexer"
		::= { muxEntry 6 }

	muxDiscont OBJECT-TYPE
		SYNTAX  Integer32
		MAX-ACCESS  read-only
		STATUS  current
		DESCRIPTION
        		"Number of Discontinues of the Multiplexer"
		::= { muxEntry 7 }

	muxNumActive OBJECT-TYPE
		SYNTAX  Integer32
		MAX-ACCESS  read-only
		STATUS  current
		DESCRIPTION
        		"Number of active services of Multiplexer"
		::= { muxEntry 8 }

	muxNumConfig OBJECT-TYPE
		SYNTAX  Integer32
		MAX-ACCESS  read-only
		STATUS  current
		DESCRIPTION
        		"Total number of configured sevices of Multiplexer"
		::= { muxEntry 9 }

	dvmStatus	OBJECT IDENTIFIER ::= { skylone 9 }

	-- skylone.dvmStatus subtree
	dvmNumber OBJECT-TYPE
		SYNTAX  Integer32
		MAX-ACCESS  read-only
		STATUS  current
		DESCRIPTION
			"Number of DV Modulator"
		::= { dvmStatus 1 }

	dvmTable OBJECT-TYPE
		SYNTAX  SEQUENCE OF DvmEntry
		MAX-ACCESS  not-accessible
		STATUS  current
		DESCRIPTION
			"List of DV Modulator entries"
		::= { dvmStatus 2 }

	dvmEntry OBJECT-TYPE
		SYNTAX  DvmEntry
		MAX-ACCESS  not-accessible
		STATUS  current
		DESCRIPTION
			"A DV Modulator Entry"
		INDEX   { dvmIndex }
		::= { dvmTable 1 }

	DvmEntry ::= SEQUENCE {
		dvmIndex Integer32,
		dvmName DisplayString,
		dvmType DisplayString,
		dvmLock DisplayString,
		dvmStart DateAndTime,
		dvmDuration TimeStamp,
		dvmBitrate Gauge32
	}
 
	dvmIndex OBJECT-TYPE
		SYNTAX  Integer32 (1..2147483647)
		MAX-ACCESS  not-accessible
		STATUS  current
		DESCRIPTION
        		"A unique value for each DV Modulator"
		::= { dvmEntry 1 }

	dvmName OBJECT-TYPE
		SYNTAX  DisplayString
		MAX-ACCESS  read-only
		STATUS  current
		DESCRIPTION
        		"Name of the DV Modulator"
		::= { dvmEntry 2 }

	dvmType OBJECT-TYPE
		SYNTAX  DisplayString
		MAX-ACCESS  read-only
		STATUS  current
		DESCRIPTION
        		"The Type of the DV Modulator"
		::= { dvmEntry 3 }

	dvmLock OBJECT-TYPE
		SYNTAX  DisplayString
		MAX-ACCESS  read-only
		STATUS  current
		DESCRIPTION
        		"Lock Status of the DV Modulator"
		::= { dvmEntry 4 }

	dvmStart OBJECT-TYPE
		SYNTAX  DateAndTime
		MAX-ACCESS  read-only
		STATUS  current
		DESCRIPTION
        		"Start Time of the DV Modulator"
		::= { dvmEntry 5 }

	dvmDuration OBJECT-TYPE
		SYNTAX  TimeStamp
		MAX-ACCESS  read-only
		STATUS  current
		DESCRIPTION
        		"Total Time of the DV Modulator"
		::= { dvmEntry 6 }

	dvmBitrate OBJECT-TYPE
		SYNTAX  Gauge32
		MAX-ACCESS  read-only
		STATUS  current
		DESCRIPTION
        		"Bitrate of the DV Modulator"
		::= { dvmEntry 7 }

	exmStatus	OBJECT IDENTIFIER ::= { skylone 10 }

	-- skylone.exmStatus subtree
	exmNumber OBJECT-TYPE
		SYNTAX  Integer32
		MAX-ACCESS  read-only
		STATUS  current
		DESCRIPTION
			"Number of External Module"
		::= { exmStatus 1 }

	exmTable OBJECT-TYPE
		SYNTAX  SEQUENCE OF ExmEntry
		MAX-ACCESS  not-accessible
		STATUS  current
		DESCRIPTION
			"List of External Module entries"
		::= { exmStatus 2 }

	exmEntry OBJECT-TYPE
		SYNTAX  ExmEntry
		MAX-ACCESS  not-accessible
		STATUS  current
		DESCRIPTION
			"A External Module Entry"
		INDEX   { exmIndex }
		::= { exmTable 1 }

	ExmEntry ::= SEQUENCE {
		exmIndex Integer32,
		exmName DisplayString,
		exmType DisplayString,
		exmLock DisplayString,
		exmDrop Integer32,
		exmDuration TimeStamp,
		exmBitrate Gauge32
	}
 
	exmIndex OBJECT-TYPE
		SYNTAX  Integer32 (1..2147483647)
		MAX-ACCESS  not-accessible
		STATUS  current
		DESCRIPTION
        		"A unique value for each External Module"
		::= { exmEntry 1 }

	exmName OBJECT-TYPE
		SYNTAX  DisplayString
		MAX-ACCESS  read-only
		STATUS  current
		DESCRIPTION
        		"Name of the External Module"
		::= { exmEntry 2 }

	exmType OBJECT-TYPE
		SYNTAX  DisplayString
		MAX-ACCESS  read-only
		STATUS  current
		DESCRIPTION
        		"The Type of the External Module"
		::= { exmEntry 3 }

	exmLock OBJECT-TYPE
		SYNTAX  DisplayString
		MAX-ACCESS  read-only
		STATUS  current
		DESCRIPTION
        		"Lock Status of the External Module"
		::= { exmEntry 4 }

	exmDrop OBJECT-TYPE
		SYNTAX  Integer32
		MAX-ACCESS  read-only
		STATUS  current
		DESCRIPTION
        		"Number of Drops of the External Module"
		::= { exmEntry 5 }

	exmDuration OBJECT-TYPE
		SYNTAX  TimeStamp
		MAX-ACCESS  read-only
		STATUS  current
		DESCRIPTION
        		"Total Time of the External Module"
		::= { exmEntry 6 }

	exmBitrate OBJECT-TYPE
		SYNTAX  Gauge32
		MAX-ACCESS  read-only
		STATUS  current
		DESCRIPTION
        		"Bitrate of the External Module"
		::= { exmEntry 7 }

	mulStatus	OBJECT IDENTIFIER ::= { skylone 11 }

	-- skylone.mulStatus subtree
	mulNumber OBJECT-TYPE
		SYNTAX  Integer32
		MAX-ACCESS  read-only
		STATUS  current
		DESCRIPTION
			"Number of Multicast Output"
		::= { mulStatus 1 }

	mulTable OBJECT-TYPE
		SYNTAX  SEQUENCE OF MulEntry
		MAX-ACCESS  not-accessible
		STATUS  current
		DESCRIPTION
			"List of Multicast Output entries"
		::= { mulStatus 2 }

	mulEntry OBJECT-TYPE
		SYNTAX  MulEntry
		MAX-ACCESS  not-accessible
		STATUS  current
		DESCRIPTION
			"A Multicast Output Entry"
		INDEX   { mulIndex }
		::= { mulTable 1 }

	MulEntry ::= SEQUENCE {
		mulIndex Integer32,
		mulName DisplayString,
		mulLock DisplayString,
		mulStart DateAndTime,
		mulDuration TimeStamp,
		mulBitrate Gauge32,
		mulBuffer BufferSize
	}
 
	mulIndex OBJECT-TYPE
		SYNTAX  Integer32 (1..2147483647)
		MAX-ACCESS  not-accessible
		STATUS  current
		DESCRIPTION
        		"A unique value for each Multicast Output"
		::= { mulEntry 1 }

	mulName OBJECT-TYPE
		SYNTAX  DisplayString
		MAX-ACCESS  read-only
		STATUS  current
		DESCRIPTION
        		"Name of the Multicast Output"
		::= { mulEntry 2 }

	mulLock OBJECT-TYPE
		SYNTAX  DisplayString
		MAX-ACCESS  read-only
		STATUS  current
		DESCRIPTION
        		"Lock Status of the Multicast Output"
		::= { mulEntry 3 }

	mulStart OBJECT-TYPE
		SYNTAX  DateAndTime
		MAX-ACCESS  read-only
		STATUS  current
		DESCRIPTION
        		"Start Time of the Multicast Output"
		::= { mulEntry 4 }

	mulDuration OBJECT-TYPE
		SYNTAX  TimeStamp
		MAX-ACCESS  read-only
		STATUS  current
		DESCRIPTION
        		"Total Time of the Multicast Output"
		::= { mulEntry 5 }

	mulBitrate OBJECT-TYPE
		SYNTAX  Gauge32
		MAX-ACCESS  read-only
		STATUS  current
		DESCRIPTION
        		"Bitrate of the Multicast Output"
		::= { mulEntry 6 }

	mulBuffer OBJECT-TYPE
		SYNTAX  BufferSize
		MAX-ACCESS  read-only
		STATUS  current
		DESCRIPTION
        		"Input buffer in seconds of the Multicast Output"
		::= { mulEntry 7 }

	lfStatus	OBJECT IDENTIFIER ::= { skylone 12 }

	-- skylone.lfStatus subtree
	lfNumber OBJECT-TYPE
		SYNTAX  Integer32
		MAX-ACCESS  read-only
		STATUS  current
		DESCRIPTION
			"Number of Local File"
		::= { lfStatus 1 }

	lfTable OBJECT-TYPE
		SYNTAX  SEQUENCE OF LfEntry
		MAX-ACCESS  not-accessible
		STATUS  current
		DESCRIPTION
			"List of Local File entries"
		::= { lfStatus 2 }

	lfEntry OBJECT-TYPE
		SYNTAX  LfEntry
		MAX-ACCESS  not-accessible
		STATUS  current
		DESCRIPTION
			"A Local File Entry"
		INDEX   { lfIndex }
		::= { lfTable 1 }

	LfEntry ::= SEQUENCE {
		lfIndex Integer32,
		lfName DisplayString,
		lfLock DisplayString,
		lfLoop DisplayString,
		lfLoopCount Integer32,
		lfPosition TimeStamp,
		lfBitrate Gauge32
	}
 
	lfIndex OBJECT-TYPE
		SYNTAX  Integer32 (1..2147483647)
		MAX-ACCESS  not-accessible
		STATUS  current
		DESCRIPTION
        		"A unique value for each Local File"
		::= { lfEntry 1 }

	lfName OBJECT-TYPE
		SYNTAX  DisplayString
		MAX-ACCESS  read-only
		STATUS  current
		DESCRIPTION
        		"Name of the Local File"
		::= { lfEntry 2 }

	lfLock OBJECT-TYPE
		SYNTAX  DisplayString
		MAX-ACCESS  read-only
		STATUS  current
		DESCRIPTION
        		"Lock Status of the Local File"
		::= { lfEntry 3 }

	lfLoop OBJECT-TYPE
		SYNTAX  DisplayString
		MAX-ACCESS  read-only
		STATUS  current
		DESCRIPTION
        		"Loop Status of the Local File"
		::= { lfEntry 4 }

	lfLoopCount OBJECT-TYPE
		SYNTAX  Integer32
		MAX-ACCESS  read-only
		STATUS  current
		DESCRIPTION
        		"Loop Count of the Local File"
		::= { lfEntry 5 }

	lfPosition OBJECT-TYPE
		SYNTAX  TimeStamp
		MAX-ACCESS  read-only
		STATUS  current
		DESCRIPTION
        		"Current playing position in seconds of Local File"
		::= { lfEntry 6 }

	lfBitrate OBJECT-TYPE
		SYNTAX  Gauge32
		MAX-ACCESS  read-only
		STATUS  current
		DESCRIPTION
        		"Bitrate of the Local File"
		::= { lfEntry 7 }

	inpStatus	OBJECT IDENTIFIER ::= { skylone 13 }

	-- skylone.inpStatus subtree
	inpNumber OBJECT-TYPE
		SYNTAX  Integer32
		MAX-ACCESS  read-only
		STATUS  current
		DESCRIPTION
			"Number of Input Stream"
		::= { inpStatus 1 }

	inpTable OBJECT-TYPE
		SYNTAX  SEQUENCE OF InpEntry
		MAX-ACCESS  not-accessible
		STATUS  current
		DESCRIPTION
			"List of Input Stream entries"
		::= { inpStatus 2 }

	inpEntry OBJECT-TYPE
		SYNTAX  InpEntry
		MAX-ACCESS  not-accessible
		STATUS  current
		DESCRIPTION
			"A Input Stream Entry"
		INDEX   { inpIndex }
		::= { inpTable 1 }

	InpEntry ::= SEQUENCE {
		inpIndex Integer32,
		inpName DisplayString,
		inpType DisplayString,
		inpLock DisplayString,
		inpStart DateAndTime,
		inpDuration TimeStamp,
		inpBitrate Gauge32,
		inpBuffer BufferSize
	}
 
	inpIndex OBJECT-TYPE
		SYNTAX  Integer32 (1..2147483647)
		MAX-ACCESS  not-accessible
		STATUS  current
		DESCRIPTION
        		"A unique value for each Input Stream"
		::= { inpEntry 1 }

	inpName OBJECT-TYPE
		SYNTAX  DisplayString
		MAX-ACCESS  read-only
		STATUS  current
		DESCRIPTION
        		"Name of the Input Stream"
		::= { inpEntry 2 }

	inpType OBJECT-TYPE
		SYNTAX  DisplayString
		MAX-ACCESS  read-only
		STATUS  current
		DESCRIPTION
        		"Lock Status of the Input Stream"
		::= { inpEntry 3 }

	inpLock OBJECT-TYPE
		SYNTAX  DisplayString
		MAX-ACCESS  read-only
		STATUS  current
		DESCRIPTION
        		"Lock Status of the Input Stream"
		::= { inpEntry 4 }

	inpStart OBJECT-TYPE
		SYNTAX  DateAndTime
		MAX-ACCESS  read-only
		STATUS  current
		DESCRIPTION
        		"Start Time of the Input Stream"
		::= { inpEntry 5 }

	inpDuration OBJECT-TYPE
		SYNTAX  TimeStamp
		MAX-ACCESS  read-only
		STATUS  current
		DESCRIPTION
        		"Total Time of the Input Stream"
		::= { inpEntry 6 }

	inpBitrate OBJECT-TYPE
		SYNTAX  Gauge32
		MAX-ACCESS  read-only
		STATUS  current
		DESCRIPTION
        		"Bitrate of the Input Stream"
		::= { inpEntry 7 }

	inpBuffer OBJECT-TYPE
		SYNTAX  BufferSize
		MAX-ACCESS  read-only
		STATUS  current
		DESCRIPTION
        		"Input buffer in seconds of the Input Stream"
		::= { inpEntry 8 }

	peerStatus	OBJECT IDENTIFIER ::= { skylone 14 }

	-- skylone.peerStatus subtree
	peerNumber OBJECT-TYPE
		SYNTAX  Integer32
		MAX-ACCESS  read-only
		STATUS  current
		DESCRIPTION
			"Number of Peer"
		::= { peerStatus 1 }

	peerTable OBJECT-TYPE
		SYNTAX  SEQUENCE OF PeerEntry
		MAX-ACCESS  not-accessible
		STATUS  current
		DESCRIPTION
			"List of Peer entries"
		::= { peerStatus 2 }

	peerEntry OBJECT-TYPE
		SYNTAX  PeerEntry
		MAX-ACCESS  not-accessible
		STATUS  current
		DESCRIPTION
			"A Peer Entry"
		INDEX   { peerIndex }
		::= { peerTable 1 }

	PeerEntry ::= SEQUENCE {
		peerIndex Integer32,
		peerName DisplayString,
		peerMacAddr DisplayString,
		peerIPAddr DisplayString,
		peerStart DateAndTime,
		peerDuration TimeStamp,
		peerBitrate Gauge32
	}
 
	peerIndex OBJECT-TYPE
		SYNTAX  Integer32 (1..2147483647)
		MAX-ACCESS  not-accessible
		STATUS  current
		DESCRIPTION
        		"A unique value for each Peer"
		::= { peerEntry 1 }

	peerName OBJECT-TYPE
		SYNTAX  DisplayString
		MAX-ACCESS  read-only
		STATUS  current
		DESCRIPTION
        		"Name of the Peer"
		::= { peerEntry 2 }

	peerMacAddr OBJECT-TYPE
		SYNTAX  DisplayString
		MAX-ACCESS  read-only
		STATUS  current
		DESCRIPTION
        		"Lock Status of the Peer"
		::= { peerEntry 3 }

	peerIPAddr OBJECT-TYPE
		SYNTAX  DisplayString
		MAX-ACCESS  read-only
		STATUS  current
		DESCRIPTION
        		"Lock Status of the Peer"
		::= { peerEntry 4 }

	peerStart OBJECT-TYPE
		SYNTAX  DateAndTime
		MAX-ACCESS  read-only
		STATUS  current
		DESCRIPTION
        		"Start Time of the Peer"
		::= { peerEntry 5 }

	peerDuration OBJECT-TYPE
		SYNTAX  TimeStamp
		MAX-ACCESS  read-only
		STATUS  current
		DESCRIPTION
        		"Total Time of the Peer"
		::= { peerEntry 6 }

	peerBitrate OBJECT-TYPE
		SYNTAX  Gauge32
		MAX-ACCESS  read-only
		STATUS  current
		DESCRIPTION
        		"Bitrate of the Peer"
		::= { peerEntry 7 }


END
