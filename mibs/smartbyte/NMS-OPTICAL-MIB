--
-- NMS-OPTICAL-MIB.my
-- MIB generated by MG-SOFT Visual MIB Builder Version 6.0  Build 88
-- Friday, December 08, 2023 at 11:37:56
--

	NMS-OPTICAL-MIB DEFINITIONS ::= BEGIN
        
		IMPORTS
			nmsModule			
				FROM NMS
			Integer32, OBJECT-TYPE			
				FROM SNMPv2-SMI;

		-- xx.8.1
		opticalModule MODULE-IDENTITY 
			LAST-UPDATED "202312081137Z"
			ORGANIZATION 
				""
			CONTACT-INFO 
				""
			DESCRIPTION 
				"Define the optical module nodes."
			REVISION "202312081137Z"
			DESCRIPTION 
				"init"
			::= { optical 1 }		
	
--                                                                                       
-- Node definitions
--
	
		-- xx.8
		optical OBJECT IDENTIFIER ::= { nmsModule 8 }

		
		-- xx.8.2
		opticalModuleInfoTable OBJECT-TYPE
			SYNTAX SEQUENCE OF OpticalModuleInfoEntry
			MAX-ACCESS not-accessible
			STATUS current
			DESCRIPTION
				"This table describes optical module information."
			::= { optical 2 }

		
		-- xx.8.2.1
		opticalModuleInfoEntry OBJECT-TYPE
			SYNTAX OpticalModuleInfoEntry
			MAX-ACCESS not-accessible
			STATUS current
			DESCRIPTION
				"An entry in the table of optical module properties for each optical module."
			INDEX { opticalPortIndex }
			::= { opticalModuleInfoTable 1 }

		
		OpticalModuleInfoEntry ::=
			SEQUENCE { 
				opticalPortIndex
					INTEGER,
				opticalTransceiverType
					OCTET STRING,
				opticalConnectType
					OCTET STRING,
				opticalWaveLength
					Integer32,
				opticalVendorName
					OCTET STRING,
				opticalSerialNumber
					OCTET STRING,
				opticalPartNumber
					OCTET STRING,
				opticalTransferDistance
					Integer32,
				opticalSupportDDM
					INTEGER,
				opticalTemperature
					Integer32,
				opticalVoltage
					Integer32,
				opticalBiasCurrent
					Integer32,
				opticalRxPower
					Integer32,
				opticalTxPower
					Integer32,
				opticalTempHiAlarm
					Integer32,
				opticalTempHiWarn
					Integer32,
				opticalTempLoWarn
					Integer32,
				opticalTempLoAlarm
					Integer32,
				opticalVoltHiAlarm
					Integer32,
				opticalVoltHiWarn
					Integer32,
				opticalVoltLoWarn
					Integer32,
				opticalVoltLoAlarm
					Integer32,
				opticalBiasHiAlarm
					Integer32,
				opticalBiasHiWarn
					Integer32,
				opticalBiasLoWarn
					Integer32,
				opticalBiasLoAlarm
					Integer32,
				opticalRxHiAlarm
					Integer32,
				opticalRxHiWarn
					Integer32,
				opticalRxLoWarn
					Integer32,
				opticalRxLoAlarm
					Integer32,
				opticalTxHiAlarm
					Integer32,
				opticalTxHiWarn
					Integer32,
				opticalTxLoWarn
					Integer32,
				opticalTxLoAlarm
					Integer32
			 }

		-- xx.8.2.1.1
		opticalPortIndex OBJECT-TYPE
			SYNTAX INTEGER (0..65535)
			MAX-ACCESS read-only
			STATUS current
			DESCRIPTION
				"Interface index(es) of port(s) present on the device."
			::= { opticalModuleInfoEntry 1 }

		
		-- xx.8.2.1.2
		opticalTransceiverType OBJECT-TYPE
			SYNTAX OCTET STRING (SIZE (0..32))
			MAX-ACCESS read-only
			STATUS current
			DESCRIPTION
				"Type of the optical module, such as SFP/XFP/GBIC."
			::= { opticalModuleInfoEntry 2 }

		
		-- xx.8.2.1.3
		opticalConnectType OBJECT-TYPE
			SYNTAX OCTET STRING (SIZE (0..16))
			MAX-ACCESS read-only
			STATUS current
			DESCRIPTION
				"The Connector Type of the optical module, such as LC."
			::= { opticalModuleInfoEntry 3 }

		
		-- xx.8.2.1.4
		opticalWaveLength OBJECT-TYPE
			SYNTAX Integer32
			MAX-ACCESS read-only
			STATUS current
			DESCRIPTION
				"Wave length of the interface, measured in nanometer."
			::= { opticalModuleInfoEntry 4 }

		
		-- xx.8.2.1.5
		opticalVendorName OBJECT-TYPE
			SYNTAX OCTET STRING (SIZE (0..64))
			MAX-ACCESS read-only
			STATUS current
			DESCRIPTION
				"Vendor name of the optical module."
			::= { opticalModuleInfoEntry 5 }

		
		-- xx.8.2.1.6
		opticalSerialNumber OBJECT-TYPE
			SYNTAX OCTET STRING (SIZE (0..32))
			MAX-ACCESS read-only
			STATUS current
			DESCRIPTION
				"Serial number of the optical module."
			::= { opticalModuleInfoEntry 6 }

		
		-- xx.8.2.1.7
		opticalPartNumber OBJECT-TYPE
			SYNTAX OCTET STRING (SIZE (0..32))
			MAX-ACCESS read-only
			STATUS current
			DESCRIPTION
				"Part number of the optical module."
			::= { opticalModuleInfoEntry 7 }

		
		-- xx.8.2.1.8
		opticalTransferDistance OBJECT-TYPE
			SYNTAX Integer32
			MAX-ACCESS read-only
			STATUS current
			DESCRIPTION
				"The maximum distance which the interface can transmit, measured in meter."
			::= { opticalModuleInfoEntry 8 }

		
		-- xx.8.2.1.9
		opticalSupportDDM OBJECT-TYPE
			SYNTAX INTEGER
				{
				support(1),
				notSupport(2)
				}
			MAX-ACCESS read-only
			STATUS current
			DESCRIPTION
				"Indicates whether the optical module supports DDM."
			::= { opticalModuleInfoEntry 9 }

		
		-- xx.8.2.1.10
		opticalTemperature OBJECT-TYPE
			SYNTAX Integer32
			MAX-ACCESS read-only
			STATUS current
			DESCRIPTION
				"Indicating the current temperature. The unit is degrees Celsius."
			::= { opticalModuleInfoEntry 10 }

		
		-- xx.8.2.1.11
		opticalVoltage OBJECT-TYPE
			SYNTAX Integer32
			MAX-ACCESS read-only
			STATUS current
			DESCRIPTION
				"Indicating the current voltage. The unit is in hundredths of V."
			::= { opticalModuleInfoEntry 11 }

		
		-- xx.8.2.1.12
		opticalBiasCurrent OBJECT-TYPE
			SYNTAX Integer32
			MAX-ACCESS read-only
			STATUS current
			DESCRIPTION
				"Indicating the current bias electric current. The unit is in hundredths of mA."
			::= { opticalModuleInfoEntry 12 }

		
		-- xx.8.2.1.13
		opticalRxPower OBJECT-TYPE
			SYNTAX Integer32
			MAX-ACCESS read-only
			STATUS current
			DESCRIPTION
				"Indicating the received power. The unit is in hundredths of dBM."
			::= { opticalModuleInfoEntry 13 }

		
		-- xx.8.2.1.14
		opticalTxPower OBJECT-TYPE
			SYNTAX Integer32
			MAX-ACCESS read-only
			STATUS current
			DESCRIPTION
				"Indicating the transmitted power. The unit is in hundredths of dBM."
			::= { opticalModuleInfoEntry 14 }

		
		-- xx.8.2.1.15
		opticalTempHiAlarm OBJECT-TYPE
			SYNTAX Integer32 (-255..255)
			MAX-ACCESS read-write
			STATUS current
			DESCRIPTION
				"Transceiver temperature too high alarm threshold limit in degrees Celsius."
			::= { opticalModuleInfoEntry 15 }

		
		-- xx.8.2.1.16
		opticalTempHiWarn OBJECT-TYPE
			SYNTAX Integer32 (-255..255)
			MAX-ACCESS read-write
			STATUS current
			DESCRIPTION
				"Transceiver temperature too high warning threshold limit in degrees Celsius."
			::= { opticalModuleInfoEntry 16 }

		
		-- xx.8.2.1.17
		opticalTempLoWarn OBJECT-TYPE
			SYNTAX Integer32 (-255..255)
			MAX-ACCESS read-write
			STATUS current
			DESCRIPTION
				"Transceiver temperature too low warning threshold limit in degrees Celsius."
			::= { opticalModuleInfoEntry 17 }

		
		-- xx.8.2.1.18
		opticalTempLoAlarm OBJECT-TYPE
			SYNTAX Integer32 (-255..255)
			MAX-ACCESS read-write
			STATUS current
			DESCRIPTION
				"Transceiver temperature too low alarm threshold limit in degrees Celsius."
			::= { opticalModuleInfoEntry 18 }

		
		-- xx.8.2.1.19
		opticalVoltHiAlarm OBJECT-TYPE
			SYNTAX Integer32 (0..500)
			MAX-ACCESS read-write
			STATUS current
			DESCRIPTION
				"Transceiver voltage too high alarm threshold limit in hundredths of V."
			::= { opticalModuleInfoEntry 19 }

		
		-- xx.8.2.1.20
		opticalVoltHiWarn OBJECT-TYPE
			SYNTAX Integer32 (0..500)
			MAX-ACCESS read-write
			STATUS current
			DESCRIPTION
				"Transceiver voltage too high warning threshold limit in hundredths of V."
			::= { opticalModuleInfoEntry 20 }

		
		-- xx.8.2.1.21
		opticalVoltLoWarn OBJECT-TYPE
			SYNTAX Integer32 (0..500)
			MAX-ACCESS read-write
			STATUS current
			DESCRIPTION
				"Transceiver voltage too low warning threshold limit in hundredths of V."
			::= { opticalModuleInfoEntry 21 }

		
		-- xx.8.2.1.22
		opticalVoltLoAlarm OBJECT-TYPE
			SYNTAX Integer32 (0..500)
			MAX-ACCESS read-write
			STATUS current
			DESCRIPTION
				"Transceiver voltage too low alarm threshold limit in hundredths of V."
			::= { opticalModuleInfoEntry 22 }

		
		-- xx.8.2.1.23
		opticalBiasHiAlarm OBJECT-TYPE
			SYNTAX Integer32 (0..50000)
			MAX-ACCESS read-write
			STATUS current
			DESCRIPTION
				"Transceiver bias too high alarm threshold limit in hundredths of mA."
			::= { opticalModuleInfoEntry 23 }

		
		-- xx.8.2.1.24
		opticalBiasHiWarn OBJECT-TYPE
			SYNTAX Integer32 (0..50000)
			MAX-ACCESS read-write
			STATUS current
			DESCRIPTION
				"Transceiver bias too high warning threshold limit in hundredths of mA."
			::= { opticalModuleInfoEntry 24 }

		
		-- xx.8.2.1.25
		opticalBiasLoWarn OBJECT-TYPE
			SYNTAX Integer32 (0..50000)
			MAX-ACCESS read-write
			STATUS current
			DESCRIPTION
				"Transceiver bias too low warning threshold limit in hundredths of mA."
			::= { opticalModuleInfoEntry 25 }

		
		-- xx.8.2.1.26
		opticalBiasLoAlarm OBJECT-TYPE
			SYNTAX Integer32 (0..50000)
			MAX-ACCESS read-write
			STATUS current
			DESCRIPTION
				"Transceiver bias too low alarm threshold limit in hundredths of mA."
			::= { opticalModuleInfoEntry 26 }

		
		-- xx.8.2.1.27
		opticalRxHiAlarm OBJECT-TYPE
			SYNTAX Integer32 (-4000..1000)
			MAX-ACCESS read-write
			STATUS current
			DESCRIPTION
				"Transceiver receive power too high alarm threshold limit in hundredths of dBM."
			::= { opticalModuleInfoEntry 27 }

		
		-- xx.8.2.1.28
		opticalRxHiWarn OBJECT-TYPE
			SYNTAX Integer32 (-4000..1000)
			MAX-ACCESS read-write
			STATUS current
			DESCRIPTION
				"Transceiver receive power too high warning threshold limit in hundredths of dBM."
			::= { opticalModuleInfoEntry 28 }

		
		-- xx.8.2.1.29
		opticalRxLoWarn OBJECT-TYPE
			SYNTAX Integer32 (-4000..1000)
			MAX-ACCESS read-write
			STATUS current
			DESCRIPTION
				"Transceiver receive power too low warning threshold limit in hundredths of dBM."
			::= { opticalModuleInfoEntry 29 }

		
		-- xx.8.2.1.30
		opticalRxLoAlarm OBJECT-TYPE
			SYNTAX Integer32 (-4000..1000)
			MAX-ACCESS read-write
			STATUS current
			DESCRIPTION
				"Transceiver receive power too low alarm threshold limit in hundredths of dBM."
			::= { opticalModuleInfoEntry 30 }

		
		-- xx.8.2.1.31
		opticalTxHiAlarm OBJECT-TYPE
			SYNTAX Integer32 (-4000..1000)
			MAX-ACCESS read-write
			STATUS current
			DESCRIPTION
				"Transceiver transmit power too high alarm threshold limit in hundredths of dBM."
			::= { opticalModuleInfoEntry 31 }

		
		-- xx.8.2.1.32
		opticalTxHiWarn OBJECT-TYPE
			SYNTAX Integer32 (-4000..1000)
			MAX-ACCESS read-write
			STATUS current
			DESCRIPTION
				"Transceiver transmit power too high warning threshold limit in hundredths of dBM."
			::= { opticalModuleInfoEntry 32 }

		
		-- xx.8.2.1.33
		opticalTxLoWarn OBJECT-TYPE
			SYNTAX Integer32 (-4000..1000)
			MAX-ACCESS read-write
			STATUS current
			DESCRIPTION
				"Transceiver transmit power too low warning threshold limit in hundredths of dBM."
			::= { opticalModuleInfoEntry 33 }

		
		-- xx.8.2.1.34
		opticalTxLoAlarm OBJECT-TYPE
			SYNTAX Integer32 (-4000..1000)
			MAX-ACCESS read-write
			STATUS current
			DESCRIPTION
				"Transceiver transmit power too low alarm threshold limit in hundredths of dBM."
			::= { opticalModuleInfoEntry 34 }

		
	
	END

--
-- NMS-OPTICAL-MIB.my
--
