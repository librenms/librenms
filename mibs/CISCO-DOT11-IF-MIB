-- *****************************************************************
-- CISCO-DOT11-IF-MIB.my: CISCO IEEE 802.11 INTERFACE MIB file
--
-- April 2002, Francis Pang 
--
-- Copyright (c) 2002-2007 by Cisco Systems, Inc.
-- All rights reserved.
-- *****************************************************************
--
CISCO-DOT11-IF-MIB DEFINITIONS ::= BEGIN

IMPORTS
        MODULE-IDENTITY,
        OBJECT-TYPE,
        NOTIFICATION-TYPE,
        Integer32,
        Unsigned32,
        Counter32
                FROM SNMPv2-SMI
        MODULE-COMPLIANCE,
        OBJECT-GROUP,
        NOTIFICATION-GROUP
                FROM SNMPv2-CONF
        TEXTUAL-CONVENTION,
        MacAddress,
        RowStatus,
        TruthValue
                FROM SNMPv2-TC
        SnmpAdminString 
                FROM SNMP-FRAMEWORK-MIB
        ifIndex
                FROM IF-MIB
        dot11AuthenticationAlgorithmsIndex,
        dot11SupportedDataRatesRxIndex
                FROM IEEE802dot11-MIB
        ciscoMgmt
                FROM CISCO-SMI;


-- ********************************************************************
-- *  MODULE IDENTITY
-- ********************************************************************

ciscoDot11IfMIB MODULE-IDENTITY
        LAST-UPDATED    "200612200000Z"
        ORGANIZATION    "Cisco System Inc."
        CONTACT-INFO
                "       Cisco Systems
                        Customer Service

                Postal: 170 West Tasman Drive,
                        San Jose CA 95134-1706.
                        USA

                   Tel: +1 800 553-NETS

                E-mail: cs-dot11@cisco.com"
        DESCRIPTION
                "This MIB module provides network management  
                support for Cisco IEEE 802.11 Wireless LAN
                type device (Access Point) radio interfaces.

                          ACRONYMS 
                AES 
                    Advanced Encryption Standard

                AP   
                    Access point 
                
                AID 
                    Association IDentifier for wireless stations.  

                BSS
                    IEEE 802.11 Basic Service Set.

                CCMP
                    Code Mode/CBC Mac Protocol

                CEPT
                    European Conference of Postal and 
                    Telecommunications Administrations.

                CRC 
                    Cyclic Redundancy Check.  

                DSSS    
                    Direct-Sequence Spread Spectrum.  
                
                EAP
                    Extensible Authentication Protocol.  

                ERP
                    Extended Rate PHY

                FHSS    
                    Frequency-Hopping Spread Spectrum.  
                
                IAPP
                    Inter-Access-Point Protocol.  
                
                ICV
                    Integrity Check Value.  

                ISM 
                    Industrial, Scientific, and Medical.

                MBSSID 
                    Multiple Broadcast SSID

                MIC
                    Message Integrity Check.  

                MMH
                    Multi-Modal Hashing.
                
                OFDM 
                    Orthogonal Frequency Division Multiplexing.  

                PHY
                    Physical Layer (Layer 1 in network model).

                PLCP
                    Physical Layer Convergence Procedure.  

                PMD
                    Physical Medium Dependent.  

                PSPF
                    Public Secure Packet Forwarding.

                RF
                    Radio Frequency.
 
                SS    
                    Spread-spectrum.
                
                SSID
                    Radio Service Set ID.  
                
                STA 
                    IEEE 802.11 wireless station.

                U-NII  
                    Unlicensed National information Infrastructure
                   
                VLAN 
                    Virtual LAN.
                
                WEP
                    Wired Equivalent Privacy.
                
                WGB
                    Work-group Bridge

                WPA 
                    WiFi Protected Access

                          GLOSSARY 

                Access point    
                    Transmitter/receiver (transceiver) device
                    that commonly connects and transports data 
                    between a wireless network and a wired network.
                
                Association
                    The service used to establish access point
                    or station mapping and enable STA invocation
                    of the distribution system services.
                    (Wireless clients attempt to connect to 
                    access points.)
                
                Basic Rate
                    A data rate that is mandatory for client
                    devices to support in order for them to achieve
                    successful association.

                Basic Service Set
                    The IEEE 802.11 BSS of an AP comprises of the 
                    stations directly associating with the AP.

                Bridge    
                    Device that connects two or more segments 
                    and reduces traffic by analyzing the 
                    destination address, filtering the frame,
                    and forwarding the frame to all connected 
                    segments.
                
                Bridge AP 
                    It is an AP that functions as a transparent 
                    bridge between 2 wired LAN segments.  

                Broadcast SSID 
                    Clients can send out Broadcast SSID Probe 
                    Requests to a nearby AP, and the AP will 
                    broadcast its own SSID within its beacons
                    to response to the clients. Clients can use
                    this Broadcast SSID to associate and 
                    communicate with the AP.  

                Cyclic Redundancy Check 
                    CRC is an error detect mechanism that applies 
                    to frame transmission.
                
                Direct-Sequence Spread Spectrum
                    DSSS combines a data signal at the sending 
                    station with a higher data rate bit sequence, 
                    which many refer to as a chipping code (also 
                    known as processing gain).  A high processing gain
                    increases the signals resistance to interference.  
                    DSSS sends a specific string of bits for each data
                    bit sent.

                ERP-CCK Modulation
                    This signal modulation technique is supported in
                    PHY implementing IEEE 802.11b/g Protocol.
                
                ERP-OFDM Modulation
                    This signal modulation technique is supported in
                    PHY implementing IEEE 802.11g Protocol.         

                Extensible Authentication Protocol
                    EAP acts as the interface between a wireless 
                    client and an authentication server, such as a 
                    RADIUS server, to which the access point 
                    communicates over the wired network.

                Extended Rate PHY
                    This PHY implements the IEEE 802.11g Protocol.

                Frequency-Hopping Spread Spectrum
                    In FHSS, a hopping code determines the frequencies 
                    the radio will transmit and in which order.  To 
                    properly receive the signal, the receiver must be 
                    set to same hopping code and listen to the 
                    incoming signal at the right time and correct 
                    frequency.  The code pattern maintains a single 
                    logical channel.
                
                IEEE 802.11    
                    Standard to encourage interoperability among 
                    wireless networking equipment.
                
                IEEE 802.11b    
                    High-rate wireless LAN standard for wireless 
                    data transfer at up to 11 Mbps.
                
                IEEE P802.11g 
                    Higher Speed Physical Layer (PHY) Extension to 
                    IEEE 802.11b, will boost wireless LAN speed to 54 
                    Mbps by using OFDM (orthogonal frequency division 
                    multiplexing).  The IEEE 802.11g specification is 
                    backward compatible with the widely deployed IEEE 
                    802.11b standard.

                Inter-Access-Point Protocol 
                    The IEEE 802.11 standard does not define how 
                    access points track moving users or how to 
                    negotiate a handoff from one access point to the
                    next, a process referred to as roaming.  IAPP is
                    a Cisco proprietary protocol to support roaming.  
                    However, IAPP does not address how the wireless 
                    system tracks users moving from one subnet to 
                    another.
                
                Independent network    
                    Network that provides peer-to-peer connectivity 
                    without relying on a complete network 
                    infrastructure.
                
                Integrity Check Value
                    The WEP ICV shall be a 32-bit value containing
                    the 32-bit cyclic redundancy code designed for 
                    verifying wireless data frame integrity.   

                Message Integrity Check 
                    A MIC can, optionally, be added to WEP-encrypted 
                    802.11 frames.  MIC prevents attacks on encrypted 
                    packets.  MIC, implemented on both the access point 
                    and all associated client devices, adds a few bytes
                    to each packet to make the packets tamper-proof.  
                
                Native VLAN ID
                    A switch port and/or AP can be configured with a 
                    'native VLAN ID'.  Untagged or priority-tagged 
                    frames are implicitly associated with the native 
                    VLAN ID.  The default native VLAN ID is '1' if 
                    VLAN tagging is enabled.  The native VLAN ID is '0' 
                    or 'no VLAN ID' if VLAN tagging is not enabled.
                
                Node    
                    Device on a network; has its own unique network 
                    address and name.
                
                Non-Root Bridge 
                    This wireless bridge does not connect to the main 
                    wired LAN segment.  It connects to a remote wired 
                    LAN segment and can associate with root bridges and 
                    other non-root bridges that accept client 
                    associations.  It also can accept associations from
                    other non-root bridges, repeater access points, 
                    and client devices.
                
                Physical Layer Convergence Procedure
                    In IEEE 802.11 wireless LANs, PLCP defines a method 
                    of mapping the IEEE 802.11 MAC sublayer protocol
                    data units into a framing format suitable for
                    sending and receiving user data and management
                    information between two or more wireless stations
                    using the associated PMD system.  

                Physical Medium Dependent
                    In IEEE 802.11 wireless LANs, a PMD system, whose
                    function defines the characteristics of, and method 
                    of transmitting and receiving data through, a 
                    wireless medium between two or more wireless 
                    stations each using the DSSS.

                Preamble
                    The radio preamble are data at the head of a 
                    packet that contains information access points 
                    and client devices required by IEEE 802.11 when 
                    sending and receiving packets.

                Primary LAN
                    In an AP, if the destinations of inbound unicast 
                    frames are unknown, the frames are sent toward 
                    the primary LAN defined on the device.
                
                Radio carrier    
                    Radio waves that deliver energy to a remote 
                    receiver; in other words, radio waves in a 
                    wireless LAN environment.
                
                Repeater    
                    Device that connects multiple segments, 
                    listening to each and regenerating the signal
                    on one to every other connected one; so that 
                    the signal can travel further.
                
                Repeater or Non-root Access Point    
                    The repeater access point is not connected 
                    to the wired LAN.  The Repeater is a wireless 
                    LAN transceiver that transfers data between 
                    a client and another access point, another 
                    repeater, or between two bridges.  The repeater 
                    is placed within radio range of an access point 
                    connected to the wired LAN, another repeater, or 
                    an non-root bridge to extend the range of the 
                    infrastructure.
                
                Radio Frequency 
                    Radio wave and modulation process or operation.
 
                Root Access Point    
                    This access point connects clients to the main 
                    wired LAN.
                
                Root (Wireless) Bridge    
                    This wireless bridge connects to the main wired 
                    LAN.  It can communicate with non-root wireless 
                    bridges, repeater access points, and client 
                    devices but not with another wireless root 
                    bridge.  Only one wireless bridge in a wireless 
                    LAN can be set as the wireless root bridge.  
                
                Spread-spectrum 
                    Wideband radio frequency technique that 
                    consumes more bandwidth than the narrow-band 
                    alternative but produces a signal that is louder 
                    and easier to detect.  There are two types of 
                    spread-spectrum radio: frequency hopping and 
                    direct sequence.
                
                Radio Service Set ID
                    SSID is a unique identifier that APs and clients 
                    use to identify with each other.  SSID is a simple 
                    means of access control and is not for security.  
                    The SSID can be any alphanumeric entry up to 32 
                    characters.
                
                Tag header
                    A 'tag header' is as defined in the IEEE 802.1Q
                    standard.  An 802.1Q tag header contains a 3-bit 
                    priority field and a 12-bit VLAN ID field.   
                    A 'priority tag' has a VLAN ID of 0, to indicate 
                    'no VLAN ID'.  A 'VLAN tag' has a non-zero 
                    VLAN ID.
                
                Virtual LAN
                    VLAN defined in the IEEE 802.1Q VLAN standard 
                    supports logically segmenting of LAN 
                    infrastructure into different subnets or 
                    workgroups so that packets are switched only 
                    between ports within the same VLAN.  
                
                VLAN ID
                    Each VLAN is identified by a 12-bit 'VLAN ID'.   
                    A VLAN ID of '0' is used to indicate 
                    'no VLAN ID'.  Valid VLAN IDs range from '1' to 
                    '4095'.  VLAN of ID '4095' is the default VLAN 
                    for Cisco VoIP Phones.
                
                Wired Equivalent Privacy
                    WEP is generally used to refer to 802.11 
                    encryption.

                Work-group Bridge
                    It is a client to APs or wireless root bridges.
                    The radio port of a WGB serves as the uplink to
                    the main network and the Ethernet port provides
                    network access for devices like PC or IP phone.

                Upgrade of Frequencies
                    As per the latest regulations proposed by the 
                    Japanese Government, the four channels 34
                    ( 5170 GHz ), 38 ( 5190 GHz), 42 ( 5210 ) and 
                    44 ( 5230 ) in the 5150-5250 MHz band has been
                    shifted by 10 MHz. Thus, the new channels in the
                    5150-5250 MHz band  are 36 ( 5180 ), 40 ( 5200 )
                    and 44 ( 5220 ) and 48 ( 5240 )." 

        REVISION        "200612200000Z"
        DESCRIPTION
                "- Added following objects in cd11IfStationConfigTable 
                   cd11IfMobileStationListIgnore 
                   cd11IfMobileStationScanChannel.
                - Added cd11Ifdot11MobileStationScanGroup OBJECT-GROUP
                - Added ciscoDot11IfComplianceRev4 MODULE-COMPLIANCE."
        REVISION        "200503100000Z"
        DESCRIPTION
                "Updated the cd11IfCurrentCarrierSet to define new 
                carrier types."
        REVISION        "200406060000Z"
        DESCRIPTION
                "Modified the cd11IfPhyNativePowerUseStandard to 
                read-write and updated cd11IfNativeTxPowerSupportTable
                and cd11IfRfNativePowerTable to add the object 
                cd11IfRadioModulationClass as indices." 
        REVISION        "200405060000Z"
        DESCRIPTION
                "Added cd11IfStationSwitchOverNotif and
                 cd11IfRogueApDetectedNotif notifications"
        REVISION        "200404170000Z"
        DESCRIPTION
                "Added cd11IfVlanPsPacketForwardEnable and 
                cd11IfPsPacketForwardEnable for PSPF support. 
                Added cd11IfMultipleBssidEnable for MBSSID support.
                Modified Cd11IfVlanEncryptKeyEntry to add objects 
                for WEP encryption support.  Added
                cd11IfRogueApDetectedTable for rogue AP detection
                information.  Added cd11IfFrequencyBandTable, 
                cd11IfRfNativePowerTable, and 
                cd11IfNativeTxPowerSupportTable to support per
                radio frequency band power configuration. Added 
                cd11IfDataRatesSensitivityTable for receive 
                sensitivity specifications of IEEE 802.11 radio."
        REVISION        "200402270000Z"
        DESCRIPTION
                "Updated the cd11IfStationRole object description.
                Modified CDot11IfCipherType textual convention to
                match the latest design.  Updated 
                cd11IfClientTxPowerTable power levels to allow
                negative dBm power.  Modified the 
                MODULE-COMPLIANCE for this MIB." 
        REVISION        "200311170000Z"
        DESCRIPTION
                "Added cd11IfWorldModeCountry, cd11IfWorldMode, and
                cd11IfMobileStationScanParent to
                cd11IfStationConfigEntry.  Added cd11IfPhyConcatenation
                to cd11IfPhyOperationEntry.  Added
                cd11IfVlanEncryptKeyTransmit to
                Cd11IfVlanEncryptKeyEntry.  Added
                cd11IfClientTxPowerTable, cd11IfOfdmTxPowerTable,
                cd11IfRadioMonitoringTable, and
                cd11IfVlanSecurityTable.  Modified the
                MODULE-COMPLIANCE for this MIB."
        REVISION        "200307130000Z"
        DESCRIPTION
                "Added cd11IfPhyBasicRateSet to identify if a rate
                in the dot11OperationalRateSet is a Basic Rate, added 
                cd11IfPhyMacSpecification to identify the IEEE 802.11 
                Standard being applied to the radio, modified the 
                cd11IfPhyDsssCurrentChannel and cd11IfChanSelectChannel 
                ranges to support 802.11A radio, and added new device 
                types to cd11IfStationRole.

                Added cd11IfAuxSsidAuthAlgEapMethod,                 
                cd11IfAuxSsidAuthAlgMacMethod, cd11IfAuthAlgEapMethod, 
                and cd11IfAuthAlgMacAddrMethod to specify the
                authentication method list." 
        REVISION        "200212290000Z"
        DESCRIPTION
                "Added a new cd11IfVlanEncryptKeyTable to support 
                per interface and VLAN encryption key and
                cd11IfDomainCapabilitySet to support the
                IEEE 802.11 dot11MultiDomainCapabilityTable."
        REVISION        "200208010000Z"
        DESCRIPTION
                "Corrected the description of roleBridge(2) of 
                the cd11IfStationRole object and changed the roleAP(1)
                to roleWgb(1)." 
        REVISION        "200207040000Z"
        DESCRIPTION
                "Changed cd11IfAuxSsidBroadcastSsid from read-only
                to read-write."
        REVISION        "200205100000Z"
        DESCRIPTION
                "The maximum value for cd11IfAuxiliarySsidLength is 
                changed to '4095'.  The new cd11IfAuxSsidIndex replaces
                cd11IfAuxSsid as the cd11IfAuxSsidTable index.  New  
                enumerate values are added to cd11IfStationRole.  New 
                MAC address authentication cd11IfAuthAlgRequireMacAddr 
                and cd11IfAuxSsidAuthAlgRequireMac objects are added to
                the authentication algorithm tables."
        REVISION        "200204110000Z"
        DESCRIPTION
                "This is the initial version of this MIB module."
        ::= { ciscoMgmt 272 }


ciscoDot11IfMIBNotifications OBJECT IDENTIFIER
        ::= { ciscoDot11IfMIB 0 }

ciscoDot11IfMIBObjects OBJECT IDENTIFIER 
        ::= { ciscoDot11IfMIB 1 }

cd11IfConfigurations   OBJECT IDENTIFIER 
        ::= { ciscoDot11IfMIBObjects 1 }

cd11IfStatistics       OBJECT IDENTIFIER 
        ::= { ciscoDot11IfMIBObjects 2 }

cd11IfManagement       OBJECT IDENTIFIER 
        ::= { cd11IfConfigurations 1 }

cd11IfPhyConfig        OBJECT IDENTIFIER 
        ::= { cd11IfConfigurations 2 }

cd11IfMacStatistics    OBJECT IDENTIFIER 
        ::= { cd11IfStatistics 1 }


-- Textual Conventions

CDot11IfVlanIdOrZero ::= TEXTUAL-CONVENTION
        STATUS     current
        DESCRIPTION
                "This is a 12-bit VLAN ID used in the VLAN Tag 
                header.  A value of '0' indicates NULL or no VLAN ID.
                and '4095' is the default VLAN for Cisco VoIP Phones.
                This textual convention differs from the VlanId
                textual convention, defined by the Q-BRIDGE-MIB
                in RFC-2674, because VlanId does not permit the 
                value '0' and '4095'."
        REFERENCE
                "RFC-2674, Bridge MIB Extensions, August 1999, 
                Q-BRIDGE-MIB, E. Bell."
        SYNTAX     Unsigned32 (0..4095)


WepKeyType128 ::= TEXTUAL-CONVENTION
        STATUS     current
        DESCRIPTION
                "WEP shared secret encryption key, 128-bits or 16 
                octets.  Only the first 13 octets are accessible to 
                users among the total 16 octets."
        REFERENCE  
                "IEEE Std 802.11-Jan 14 1999, Wireless LAN Medium 
                Access Control and Physical Layer Specifications, 
                LAN MAN Standards Committee of the IEEE Computer 
                Society, Section 8.3.2." 
        SYNTAX     OCTET STRING (SIZE (5..13))


CDot11IfMicAlgorithm ::= TEXTUAL-CONVENTION
        STATUS     current
        DESCRIPTION
                "Auxiliary MIC calculated on WEP-encoded packets 
                to validate that they have not been modified.   
                This is in addition to the standard 802.11 ICV.
                The two options are:
                    micNone(1)    - do not apply MIC, 
                    micMXX(2)     - apply MMH MIC,
                    micMichael(3) - Michael MIC."
        SYNTAX     INTEGER { 
                         micNone(1), 
                         micMXX(2),
                         micMichael(3)
                           }


CDot11IfWepKeyPermuteAlgorithm ::= TEXTUAL-CONVENTION
        STATUS     current
        DESCRIPTION
                "This defines the function through which the WEP 
                encryption key is permuted between key renewal 
                periods.
                    wepPermuteNone(1) - no WEP key permutation,
                    wepPermuteIV(2)   - WEP key permutation with
                                        initialization vector."
        SYNTAX     INTEGER { 
                         wepPermuteNone(1), 
                         wepPermuteIV(2) 
                           }


CDot11IfCipherType ::= TEXTUAL-CONVENTION
        STATUS     current
        DESCRIPTION
                "These are the frame encryption cipher types for 
                frames on IEEE 802.11 radio interfaces.
                    ckip        Cisco Per packet key hashing,
                    cmic        Cisco MMH MIC, 
                    tkip        WPA Temporal Key encryption,
                    wep40       40-bit WEP key,
                    wep128      128-bit WEP key,
                    aesccm      WPA AES CCMP encryption."
        SYNTAX     BITS { 
                           ckip(0),      
                           cmic(1),    
                           tkip(2),   
                           wep40(3),
                           wep128(4), 
                           aesccm(5)
                         }
         

CDot11RadioFrequencyBandType ::= TEXTUAL-CONVENTION
        STATUS     current
        DESCRIPTION
                "These are the radio frequency band names 
                the IEEE 802.11 radio is operating on:
                    ism24G(0)    - ISM 2.4 GHz band,
                    unii1(1)     - U-NII-1 band (5.15-5.25 GHz), 
                    unii2(2)     - U-NII-2 band (5.25-5.35 GHz),
                    unii3(3)     - U-NII-3 band (5.725-5.825 GHz),
                    cept(4)      - CEPT band B (5.47-5.725 GHz),
                    japan49G(5)  - Japan 4.9 band (4.9-5.0 GHz),
                    japan50G(6)  - Japan 5.0 band (5.03-5.091 GHz)."
        SYNTAX     BITS {
                        ism24G(0),
                        unii1(1),
                        unii2(2),
                        unii3(3),
                        cept(4),
                        japan49G(5),
                        japan50G(6)
                        }

CDot11RadioModulationClass ::= TEXTUAL-CONVENTION
        STATUS     current
        DESCRIPTION
                "These are classifications of radio modulation 
                techniques used by the various Physical Layers 
                of IEEE 802.11 radios:
                    dsss(1) - modulation schemes associated 
                              with DSSS type PHYs,
                    ofdm(2) - modulation schemes associated 
                              with OFDM type PHYs."
        SYNTAX     INTEGER {
                       dsss(1),
                       ofdm(2)
                           }

Cd11IfDot11UpgradeStatus ::= TEXTUAL-CONVENTION
        STATUS     current
        DESCRIPTION
                "These are the various status on the 
                 Radio Upgrade:
                    unknown(1)              - upgrade status unknown,
                    upgradeNotApplicable(2) - Regulatory domain upgrade
                                              is not applicable for 11b/g
                                              radios and 11a radios not in
                                              Japan regulatory domain,
                    upgradeNotDone(3)       - 11a radio is in Japan domain but 
                                              yet to be upgraded,
                    upgradeNotNeeded(4)     - 11a radio is already configured to 
                                              operate in the W52 domain and that 
                                              the upgrade is not needed,
                    upgradeDone(5)          - upgrade has been done from J52 to W52."
        SYNTAX     INTEGER {
                       unknown(1),
                       upgradeNotApplicable(2),
                       upgradeNotDone(3),
                       upgradeNotNeeded(4),
                       upgradeDone(5)
                           }                     

-- ********************************************************************
-- *  Cisco IEEE 802.11 Interface Extension 
-- ********************************************************************

-- Configuration Objects 

cd11IfStationConfigTable OBJECT-TYPE
        SYNTAX     SEQUENCE OF Cd11IfStationConfigEntry
        MAX-ACCESS not-accessible
        STATUS     current
        DESCRIPTION 
                "This table contains attributes to configure radio
                interfaces managed by this agent.  The attributes 
                are extensions to the configuration parameters in 
                the dot11StationConfigTable defined in the 
                IEEE802dot11-MIB.  This table configures the station
                role of the interface, proprietary extensions, 
                hierarchy, security option and parameters, and 
                communication settings.  This table has a sparse 
                dependent relationship on the ifTable.  
                For each entry in this table, there exists an entry
                in the ifTable of ifType ieee80211(71).
                Entries in this table cannot be created or deleted
                by the network management system.  All entries are
                created or deleted by the agent."
        REFERENCE  
                "IEEE Std 802.11-Jan 14 1999, Wireless LAN Medium 
                Access Control and Physical Layer Specifications, 
                LAN MAN Standards Committee of the IEEE Computer 
                Society, IEEE802dot11-MIB." 
        ::= { cd11IfManagement 1 }

cd11IfStationConfigEntry OBJECT-TYPE
        SYNTAX     Cd11IfStationConfigEntry
        MAX-ACCESS not-accessible
        STATUS     current
        DESCRIPTION 
                "A collection of configuration attributes for  
                an IEEE 802.11 radio interface. These attributes
                are supplements to attributes defined in the 
                dot11StationConfigTable in IEEE802dot11-MIB."
        REFERENCE  
                "IEEE Std 802.11-Jan 14 1999, Wireless LAN Medium 
                Access Control and Physical Layer Specifications, 
                LAN MAN Standards Committee of the IEEE Computer 
                Society, IEEE802dot11-MIB." 
        INDEX      { ifIndex }
        ::= { cd11IfStationConfigTable 1 }

Cd11IfStationConfigEntry ::= 
        SEQUENCE   {
            cd11IfStationRole               INTEGER,
            cd11IfCiscoExtensionsEnable     TruthValue,
            cd11IfAllowBroadcastSsidAssoc   TruthValue,
            cd11IfPrivacyOptionMaxRate      Integer32,
            cd11IfEthernetEncapsulDefault   INTEGER,
            cd11IfBridgeSpacing             Unsigned32,
            cd11IfDesiredSsidMaxAssocSta    Unsigned32,
            cd11IfAuxiliarySsidLength       Unsigned32,
            cd11IfVoipExtensionsEnable      TruthValue,
            cd11IfDesiredSsidMicAlgorithm   CDot11IfMicAlgorithm,
            cd11IfDesiredSsidWepPermuteAlg
                    CDot11IfWepKeyPermuteAlgorithm,
            cd11IfWorldMode                 INTEGER,
            cd11IfWorldModeCountry          OCTET STRING,
            cd11IfMobileStationScanParent   TruthValue, 
            cd11IfPsPacketForwardEnable     TruthValue,
            cd11IfMultipleBssidEnable       TruthValue,
            cd11IfMobileStationListIgnore   TruthValue,
            cd11IfMobileStationScanChannel  OCTET STRING
                   }

cd11IfStationRole OBJECT-TYPE
        SYNTAX     INTEGER {
                         roleWgb(1),
                         roleBridge(2),
                         roleClient(3),
                         roleRoot(4),
                         roleRepeater(5),
                         roleApBridge(6),
                         roleApRepeater(7),
                         roleIBSS(8),
                         roleNrBridge(9), 
                         roleApNrBridge(10), 
                         roleScanner(11) 
                           }
        MAX-ACCESS read-write
        STATUS     current
        DESCRIPTION
                "This defines the role of this station itself within
                the 802.11 BSS of which it is a member. The roles are:
                         roleWgb(1)         - infrastructure type WGB
                                              client,
                         roleBridge(2)      - root bridge,
                         roleClient(3)      - independent BBS type
                                              WGB client,
                         roleRoot(4)        - root access point,
                         roleRepeater(5)    - repeater,
                         roleApBridge(6)    - AP and root bridge,
                         roleApRepeater(7)  - AP and repeater,
                         roleIBSS(8)        - independent BSS,
                         roleNrBridge(9)    - non-root bridge,
                         roleApNrBridge(10) - AP and non-root bridge,
                         roleScanner(11)    - scanner for rogue APs
                                              and clients.
                The default role is roleRoot(4)."
        REFERENCE  
                "IEEE Std 802.11-Jan 14 1999, Wireless LAN Medium 
                Access Control and Physical Layer Specifications,
                LAN MAN Standards Committee of the IEEE Computer 
                Society, section 3."
        ::= { cd11IfStationConfigEntry 1 }

cd11IfCiscoExtensionsEnable OBJECT-TYPE
        SYNTAX     TruthValue
        MAX-ACCESS read-write
        STATUS     current
        DESCRIPTION 
                "Cisco Aironet extensions to the basic IEEE
                802.11 protocols are enabled if the value is
                'true'.  The extension enables better BSS 
                performance and faster roaming.  If the value 
                is 'false', only the basic IEEE 802.11 protocols 
                are used.  This ensures maximum compatibility 
                with non-Cisco equipment.  The default value is 
                'true'."
        ::= { cd11IfStationConfigEntry 2 }

cd11IfAllowBroadcastSsidAssoc OBJECT-TYPE
        SYNTAX     TruthValue
        MAX-ACCESS read-write
        STATUS     current
        DESCRIPTION 
                "If the value of cd11IfStationRole is either 
                'roleRoot' or 'roleRepeater', and if 
                cd11IfAllowBroadcastSsidAssoc is 'true', 
                the device radio driver will respond
                to Broadcast SSID Probe Requests and will 
                broadcast its own SSID within its beacons.  
                If cd11IfAllowBroadcastSsidAssoc is 'false', 
                the radio will not respond to the Broadcast 
                SSID and will not broadcast its SSID within 
                beacons.  The default value is 'true'."
        ::= { cd11IfStationConfigEntry 3 }

cd11IfPrivacyOptionMaxRate OBJECT-TYPE
        SYNTAX     Integer32 (2..127)
        UNITS      "500 Kb per second"
        MAX-ACCESS read-only
        STATUS     current
        DESCRIPTION
                "This object specifies the maximum transmit bit 
                rate supported by the radio when using, for example, 
                WEP encryption.  The rate is expressed in standard 
                IEEE 802.11 increments of 500Kb/sec."
        REFERENCE  
                "IEEE Std 802.11-Jan 14 1999, Wireless LAN Medium 
                Access Control and Physical Layer Specifications,
                LAN MAN Standards Committee of the IEEE Computer 
                Society, section 8.1.2." 
        ::= { cd11IfStationConfigEntry 4 }

cd11IfEthernetEncapsulDefault OBJECT-TYPE
        SYNTAX     INTEGER { 
                        encap802dot1H(1), 
                        encapRfc1042(2) 
                           }
        MAX-ACCESS read-write
        STATUS     current
        DESCRIPTION 
                "This object specifies the Ethernet encapsulation 
                transform type used within the BSS.  The encapsulations 
                allowed are either IEEE 802.1H type or RFC-1042 type.
                IEEE 802.1H designates the Subnetwork Access Protocol 
                (SNAP) mechanism as the Ethernet encapsulation protocol.
                Subsequently, other (non-IP) uses of the RFC-1042 
                mechanism.  RFC-1042 specifies a translation for 
                Ethernet frames, such that they can be exchanged with
                end stations on LANs that do not provide an Ethernet 
                service.  
                    encap802dot1H(1) - IEEE 802.1H SNAP encapsulation 
                    encapRfc1042(2)  - RFC-1042 encapsulation.
                The default encapsulation type is encap802dot1H(1)."
        REFERENCE
                "IEEE Std 802.1H-1997, Media Access Control 
                Bridging of Ethernet V2.0 in Local Area 
                Networks.  RFC-1042, February 1988, A Standard for 
                the Transmission of IP Datagrams over IEEE 802 
                Networks, J. Postel and J. Reynolds."
        ::= { cd11IfStationConfigEntry 5 }

cd11IfBridgeSpacing OBJECT-TYPE
        SYNTAX     Unsigned32 (0..38640)
        UNITS      "Kilometers" 
        MAX-ACCESS read-write
        STATUS     current
        DESCRIPTION 
                "If this device is a root wireless bridge,
                this value is the distance in kilometers 
                reported between this device and its 
                farthest non-root bridge client."
        ::= { cd11IfStationConfigEntry 6 }

cd11IfDesiredSsidMaxAssocSta OBJECT-TYPE
        SYNTAX     Unsigned32 (0..2007)
        MAX-ACCESS read-write
        STATUS     current
        DESCRIPTION 
                "This object defines the maximum number of IEEE 
                802.11 stations which may associate with this radio 
                interface through IEEE802dot11-MIB dot11DesiredSSID.  
                If this value is '0', the maximum number is limited
                only by the IEEE 802.11 standard and any hardware or
                radio firmware limitations of the access point.  The
                default value is '0'." 
        REFERENCE  
                "IEEE Std 802.11-Jan 14 1999, Wireless LAN Medium 
                Access Control and Physical Layer Specifications,
                LAN MAN Standards Committee of the IEEE Computer 
                Society, section 5.7." 
        ::= { cd11IfStationConfigEntry 7 }

cd11IfAuxiliarySsidLength OBJECT-TYPE
        SYNTAX     Unsigned32 (0..4095)
        MAX-ACCESS read-only
        STATUS     current
        DESCRIPTION 
                "This object specifies the maximum number of SSIDs
                allowed for a radio interface or the number of SSID 
                entries per radio interface in the cd11IfAuxSsidTable.
                The default value is '25'."
        ::= { cd11IfStationConfigEntry 8 }

cd11IfVoipExtensionsEnable OBJECT-TYPE
        SYNTAX     TruthValue
        MAX-ACCESS read-write
        STATUS     current
        DESCRIPTION 
                "This object enables the radio generate proprietary
                elements in its beacons and probe responses to support 
                Voice-over-IP (VoIP) phones.  The default value is 
                'true'."
        ::= { cd11IfStationConfigEntry 9 }

cd11IfDesiredSsidMicAlgorithm OBJECT-TYPE
        SYNTAX     CDot11IfMicAlgorithm
        MAX-ACCESS read-write
        STATUS     current
        DESCRIPTION 
                "This object defines the auxiliary MIC calculated 
                on WEP-encoded packets of stations associated with 
                this radio interface through IEEE802dot11-MIB 
                dot11DesiredSSID.  The default value is micNone(1)." 
        REFERENCE  
                "IEEE Std 802.11-Jan 14 1999, Wireless LAN Medium 
                Access Control and Physical Layer Specifications,
                LAN MAN Standards Committee of the IEEE Computer 
                Society, section 8.2.3."
        ::= { cd11IfStationConfigEntry 10 }

cd11IfDesiredSsidWepPermuteAlg OBJECT-TYPE
        SYNTAX     CDot11IfWepKeyPermuteAlgorithm
        MAX-ACCESS read-write
        STATUS     current
        DESCRIPTION 
                "This object defines the function through which 
                the WEP encryption key is permuted between key 
                renewal periods for stations associated with this 
                radio interface through IEEE802dot11-MIB 
                dot11DesiredSSID.  The default value is 
                wepPermuteNone(1)."
        REFERENCE  
                "IEEE Std 802.11-Jan 14 1999, Wireless LAN Medium 
                Access Control and Physical Layer Specifications,
                LAN MAN Standards Committee of the IEEE Computer 
                Society, section 8.2.3."
        ::= { cd11IfStationConfigEntry 11 }

cd11IfWorldMode OBJECT-TYPE
        SYNTAX     INTEGER { 
                              none(1),
                              legacy(2),
                              dot11d(3)
                           } 
        MAX-ACCESS read-write
        STATUS     current
        DESCRIPTION
                "This object sets the World-Mode function of the
                radio to allow it to function in countries other
                than it was manufactured for.
                    none(1)   - No world mode setting,
                    legacy(2) - compatible with legacy hardware,
                    dot11d(3) - use IEEE 802.11d mechanism."
        DEFVAL     { none } 
        ::= { cd11IfStationConfigEntry 12 }

cd11IfWorldModeCountry OBJECT-TYPE
        SYNTAX OCTET STRING (SIZE(3))
        MAX-ACCESS read-write
        STATUS     current
        DESCRIPTION
                "This object sets the dot11CountryString in the
                IEEE802dot11-MIB identifying the country in which 
                the radio is operating.  When cd11IfWorldMode is 
                either legacy(2) or dot11d(3), this object value
                will be sent in the radio management frame.
       
                The first two octets of this string is the two 
                character country code as described in document 
                ISO/IEC 3166-1.  The third octet shall be one of 
                the following:

                1. an ASCII space character, if the regulations under
                which the station is operating encompass all
                environments in the country,

                2. an ASCII 'O' character, if the regulations under
                which the station is operating are for an Outdoor
                environment only, or

                3. an ASCII 'I' character, if the regulations under
                which the station is operating are for an Indoor
                environment only."
        REFERENCE
                "IEEE Std 802.11-Jan 14 1999, Wireless LAN Medium 
                Access Control and Physical Layer Specifications,
                LAN MAN Standards Committee of the IEEE Computer 
                Society, IEEE802dot11-MIB." 
        ::= { cd11IfStationConfigEntry 13 }

cd11IfMobileStationScanParent OBJECT-TYPE
        SYNTAX     TruthValue
        MAX-ACCESS read-write
        STATUS     current
        DESCRIPTION
                "This object enables the radio to scan for a better
                parent when it is a mobile non-root device, for
                example, the value of cd11IfStationRole is roleWgb(1)."
        DEFVAL     { false }
        ::= { cd11IfStationConfigEntry 14 }

cd11IfPsPacketForwardEnable OBJECT-TYPE
        SYNTAX     TruthValue
        MAX-ACCESS read-write
        STATUS     current
        DESCRIPTION
                "If no VLAN is configured on the radio interface,
                this object configures the PSPF feature. Otherwise,
                cd11IfVlanPsPacketForwardEnable is used to configure
                the PSPF feature per VLAN.  If it is 'true', PSPF is
                on the radio interface and direct traffic between 
                wireless clients of the interface is not allowed.
                If it is 'false', PSPF is disabled on the VLAN and
                direct traffic between wireless clients of the 
                interface is allowed."
        DEFVAL     { false }
        ::= { cd11IfStationConfigEntry 15 }

cd11IfMultipleBssidEnable OBJECT-TYPE
        SYNTAX     TruthValue
        MAX-ACCESS read-write
        STATUS     current
        DESCRIPTION
                "If it is 'true', multiple broadcast SSID is 
                enabled on the radio.  To a wireless client, a 
                MBSSID AP appears to be several distinct co-located
                APs, and it transmits a beacon for each broadcast 
                SSID or SSID.  This allows all of the SSIDs visible 
                for passive scanning."
        DEFVAL     { false }
        ::= { cd11IfStationConfigEntry 16 }

cd11IfMobileStationListIgnore OBJECT-TYPE
        SYNTAX     TruthValue
        MAX-ACCESS read-write
        STATUS     current
        DESCRIPTION
                "This object indicates whether the radio should
                process the AP adjacency and Enhanced Neighbor
                List reports specified in the CCX Specification.
                AP adjacency and Enhanced Neighbor List provide
                information about the infrastructure wireless
                devices found in the near vicinity of this
                radio.
                
                This object is applicable only when the radio's
                role as represented by the object cd11IfStationRole
                is one of roleWgb(1), roleRepeater(5) or
                roleNrbridge(9). 
 
                Agent will populate a value of 'false', when the 
                radio's role as represented by cd11IfStationRole
                is one of roleRoot(4) ,roleBridge(2) or 
                roleApBridge(6), to indicate that the object is
                not applicable for the radio in these roles.  Set
                requests will be rejected when the radio is 
                configured to be in one of these roles.
 
                User can configure this object only when
                cd11IfMobileStationScanChannel is configured with
                a valid set of channels.  When
                cd11IfMobileStationScanChannel is configured with
                a value of 0, the agent will automatically 
                populate a value of 'false'. "
        DEFVAL     { false }
        ::= { cd11IfStationConfigEntry 17 }

cd11IfMobileStationScanChannel OBJECT-TYPE
        SYNTAX     OCTET STRING (SIZE(1..64))
        MAX-ACCESS read-write
        STATUS     current
        DESCRIPTION
                "This object specifies the channels to be used by
                the infractructure clients for scanning purposes.
                
                This object is applicable only when the radio's
                role as represented by the object cd11IfStationRole
                is one of roleWgb(1), roleRepeater(5) or
                roleNrbridge(9).   Agent will reject the request
                to set this object when the cd11IfStationRole doesn't
                populate one of the values mentioned above.
 
                Each octet carries the channel number.  To configure
                the radio to scan all the channels applicable to a
                particular regulatory domain,  this object should be
                configured with only one octet of value 0. "
        ::= { cd11IfStationConfigEntry 18 }


cd11IfAuthAlgorithmTable OBJECT-TYPE
        SYNTAX     SEQUENCE OF Cd11IfAuthAlgorithmEntry
        MAX-ACCESS not-accessible
        STATUS     current
        DESCRIPTION
                "This table contains attributes to configure 
                authentication algorithm parameters for associations 
                through the SSID defined by IEEE802dot11-MIB 
                dot11DesiredSSID object.  It defines attributes 
                additional to those defined in the IEEE802dot11-MIB
                dot11AuthenticationAlgorithmsTable.  An interface 
                may support multiple authentication algorithms.  

                This table has an expansion dependent relationship 
                on the ifTable.  For each entry in this table, 
                there exists at least an entry in the ifTable of 
                ifType ieee80211(71).  This table uses the 
                dot11AuthenticationAlgorithmsIndex of the
                dot11AuthenticationAlgorithmsTable defined in the 
                IEEE802dot11-MIB as the expansion index.  

                Entries in this table cannot be created or deleted
                by the network management system.  All entries are
                created or deleted by the agent."
        REFERENCE  
                "IEEE Std 802.11-Jan 14 1999, Wireless LAN Medium 
                Access Control and Physical Layer Specifications,
                LAN MAN Standards Committee of the IEEE Computer 
                Society, section 5.7.6 and IEEE802dot11-MIB." 
        ::= { cd11IfManagement 2 }

cd11IfAuthAlgorithmEntry OBJECT-TYPE
        SYNTAX     Cd11IfAuthAlgorithmEntry
        MAX-ACCESS not-accessible
        STATUS     current
        DESCRIPTION
                "Each entry specifies authentication algorithm
                configuration attributes of a VLAN for the 
                dot11DesiredSSID on a radio interface." 
        REFERENCE  
                "IEEE Std 802.11-Jan 14 1999, Wireless LAN Medium 
                Access Control and Physical Layer Specifications,
                LAN MAN Standards Committee of the IEEE Computer 
                Society, section 8.2 and IEEE802dot11-MIB." 
        INDEX      { 
                ifIndex,
                dot11AuthenticationAlgorithmsIndex 
                   }
        ::= { cd11IfAuthAlgorithmTable 1 }

Cd11IfAuthAlgorithmEntry ::= 
        SEQUENCE   {
            cd11IfAuthAlgRequireEap      TruthValue,
            cd11IfAuthAlgRequireMacAddr  TruthValue,
            cd11IfAuthAlgDefaultVlan     CDot11IfVlanIdOrZero,
            cd11IfAuthAlgEapMethod       SnmpAdminString,
            cd11IfAuthAlgMacAddrMethod   SnmpAdminString
                   }

cd11IfAuthAlgRequireEap OBJECT-TYPE
        SYNTAX     TruthValue
        MAX-ACCESS read-write
        STATUS     current
        DESCRIPTION 
                "If the value is 'true', stations authenticating 
                with the corresponding IEEE802dot11-MIB
                dot11AuthenticationAlgorithm must complete 
                network-level EAP authentication before their 
                association attempts will be unblocked.  If the 
                value is 'false', stations authenticating with 
                the corresponding dot11AuthenticationAlgorithm 
                will be unblocked as soon as they complete the 
                802.11 authentication.  The default value is 
                'true'."
        REFERENCE  
                "IEEE Std 802.11-Jan 14 1999, Wireless LAN Medium 
                Access Control and Physical Layer Specifications,
                LAN MAN Standards Committee of the IEEE Computer 
                Society, section 8.2 and IEEE802dot11-MIB." 
        ::= { cd11IfAuthAlgorithmEntry 1 }

cd11IfAuthAlgRequireMacAddr OBJECT-TYPE
        SYNTAX     TruthValue
        MAX-ACCESS read-write
        STATUS     current
        DESCRIPTION
                "If the value is 'true', stations authenticating
                with the corresponding IEEE802dot11-MIB
                dot11AuthenticationAlgorithm must complete
                additional MAC address authentication before their
                association attempts will be unblocked.  If the
                value is 'false', stations authenticating with
                the corresponding dot11AuthenticationAlgorithm
                will be unblocked as soon as they complete the
                802.11 authentication.  The default value is
                'true'."
        REFERENCE 
                "IEEE Std 802.11-Jan 14 1999, Wireless LAN Medium
                Access Control and Physical Layer Specifications,
                LAN MAN Standards Committee of the IEEE Computer
                Society, section 8.2 and IEEE802dot11-MIB."
        ::= { cd11IfAuthAlgorithmEntry 2 }

cd11IfAuthAlgDefaultVlan OBJECT-TYPE
        SYNTAX     CDot11IfVlanIdOrZero
        MAX-ACCESS read-write
        STATUS     current
        DESCRIPTION
                "This object defines the default VLAN identifier 
                for stations associated with this radio interface 
                with this authentication and through 
                IEEE802dot11-MIB dot11DesiredSSID.  If the value 
                of this object is '0', it indicates that either the
                default VLAN are not defined for this authentication 
                on this radio interface or the default VLAN is the 
                native VLAN ID.  The default value is '0'." 
        REFERENCE  
                "IEEE Std 802.11-Jan 14 1999, Wireless LAN Medium 
                Access Control and Physical Layer Specifications,
                LAN MAN Standards Committee of the IEEE Computer 
                Society, section 8.2 and IEEE802dot11-MIB." 
        ::= { cd11IfAuthAlgorithmEntry 3 }

cd11IfAuthAlgEapMethod OBJECT-TYPE       
        SYNTAX     SnmpAdminString
        MAX-ACCESS read-write
        STATUS     current
        DESCRIPTION 
                "If the value of cd11IfAuthAlgRequireEap is 'true'
                or dot11AuthenticationAlgorithm is Network-EAP, 
                this is the EAP method list to used for the EAP 
                authentication."
        REFERENCE  
                "IEEE Std 802.11-Jan 14 1999, Wireless LAN Medium 
                Access Control and Physical Layer Specifications,
                LAN MAN Standards Committee of the IEEE Computer 
                Society, IEEE802dot11-MIB." 
        ::= { cd11IfAuthAlgorithmEntry 4 }

cd11IfAuthAlgMacAddrMethod OBJECT-TYPE                  
        SYNTAX     SnmpAdminString
        MAX-ACCESS read-write
        STATUS     current
        DESCRIPTION
                "If the value of cd11IfAuthAlgRequireMacAddr 
                is 'true', this is the MAC address method list to 
                used for the MAC authentication."
        ::= { cd11IfAuthAlgorithmEntry 5 }


cd11IfWepDefaultKeysTable OBJECT-TYPE
        SYNTAX     SEQUENCE OF Cd11IfWepDefaultKeysEntry
        MAX-ACCESS not-accessible
        STATUS     current
        DESCRIPTION 
                "The dot11WEPDefaultKeysTable defined by the 
                IEEE802dot11-MIB allows only WEP keys of length 
                up to 40 bits.  This table overrides the the
                dot11WEPDefaultKeysTable and supports keys of 
                from 40 to 128 bits.  A maximum of four keys can
                associate with any IEEE 802.11 radio interface.  
                For devices implementing this table, they should
                not implement the dot11WEPDefaultKeysTable.  

                This table has an expansion dependent relationship 
                on the ifTable.  For each entry in this table, 
                there exists at least an entry in the ifTable of 
                ifType ieee80211(71).  Entries in this table 
                cannot be created or deleted by the network 
                management system.  All entries are created or 
                deleted by the agent."
        REFERENCE  
                "IEEE Std 802.11-Jan 14 1999, Wireless LAN Medium 
                Access Control and Physical Layer Specifications,
                LAN MAN Standards Committee of the IEEE Computer 
                Society, IEEE802dot11-MIB." 
        ::= { cd11IfManagement 3 }

cd11IfWepDefaultKeysEntry OBJECT-TYPE
        SYNTAX     Cd11IfWepDefaultKeysEntry
        MAX-ACCESS not-accessible
        STATUS     current
        DESCRIPTION 
                "A collection of attributes defining a WEP key for
                a radio interface." 
        INDEX      { 
                ifIndex, 
                cd11IfWepDefaultKeyIndex 
                   }
        ::= { cd11IfWepDefaultKeysTable 1 }

Cd11IfWepDefaultKeysEntry ::= 
        SEQUENCE   {
            cd11IfWepDefaultKeyIndex  Unsigned32, 
            cd11IfWepDefaultKeyLen    Unsigned32,
            cd11IfWepDefaultKeyValue  WepKeyType128 
                   }

cd11IfWepDefaultKeyIndex OBJECT-TYPE
        SYNTAX     Unsigned32 (1..4)
        MAX-ACCESS not-accessible 
        STATUS     current
        DESCRIPTION
                "This object identifies a WEP key instance for 
                a radio interface."
        ::= { cd11IfWepDefaultKeysEntry 1 }

cd11IfWepDefaultKeyLen OBJECT-TYPE
        SYNTAX     Unsigned32 (5..13)
        MAX-ACCESS read-write
        STATUS     current
        DESCRIPTION
                "This object specifies the length in octets of 
                the WEP key cd11IfWepDefaultKeyValue.  The 
                default key length is '13'."
        ::= { cd11IfWepDefaultKeysEntry 2 }

cd11IfWepDefaultKeyValue OBJECT-TYPE
        SYNTAX     WepKeyType128
        MAX-ACCESS read-write
        STATUS     current
        DESCRIPTION
                "This is the WEP default secret key value.  Any 
                attempt to read this object by the NMS will 
                result in return of a zero-length string.  The 
                default value is a NULL string."
        ::= { cd11IfWepDefaultKeysEntry 3 }


cd11IfDesiredBssTable OBJECT-TYPE
        SYNTAX     SEQUENCE OF Cd11IfDesiredBssEntry
        MAX-ACCESS not-accessible
        STATUS     current
        DESCRIPTION 
                "When the radio is not functioning as an access
                point (i.e., cd11IfStationRole is not 'roleRoot'), 
                and for example, this radio is a repeater or 
                bridge, this table will contain a list of preferred 
                access points with which the radio interface should 
                associate with.  This table has an expansion 
                dependent relationship on the ifTable.  For each 
                entry in this table, there exists at least an entry
                in the ifTable of ifType ieee80211(71).
                Entries in this table cannot be created or deleted
                by the network management system.  All entries are
                created or deleted by the agent."
        ::= { cd11IfManagement 5 }

cd11IfDesiredBssEntry OBJECT-TYPE
        SYNTAX     Cd11IfDesiredBssEntry
        MAX-ACCESS not-accessible
        STATUS     current
        DESCRIPTION 
                "Each entry provides the MAC address of a preferred
                access point.  A maximum of 4 BSS addresses can be
                configured to an interface."
        INDEX      { 
                ifIndex, 
                cd11IfDesiredBssIndex 
                   }
        ::= { cd11IfDesiredBssTable 1 }

Cd11IfDesiredBssEntry ::= 
        SEQUENCE   {
            cd11IfDesiredBssIndex  Unsigned32, 
            cd11IfDesiredBssAddr   MacAddress 
                   }

cd11IfDesiredBssIndex OBJECT-TYPE
        SYNTAX     Unsigned32 (1..4)
        MAX-ACCESS not-accessible 
        STATUS     current
        DESCRIPTION
                "This object defines the priority order in which 
                preferred access points should be probed.  Lower 
                index values indicate higher priority."
        ::= { cd11IfDesiredBssEntry 1 }

cd11IfDesiredBssAddr OBJECT-TYPE
        SYNTAX     MacAddress
        MAX-ACCESS read-write
        STATUS     current
        DESCRIPTION
                "This object defines the BSS identifier (MAC 
                address) of the access point with which the radio 
                should try to associate with.  The value of this 
                object is '00:00:00:00:00:00' if the BSS 
                identifier for this priority is not specified
                or configured.  The default value is 
                '000000000000'H."
        ::= { cd11IfDesiredBssEntry 2 }


cd11IfAuxSsidTable OBJECT-TYPE
        SYNTAX     SEQUENCE OF Cd11IfAuxSsidEntry
        MAX-ACCESS not-accessible
        STATUS     current
        DESCRIPTION 
                "When the radio is not functioning as a client 
                station (i.e., cd11IfStationRole is not 
                'roleClient'), and for example, this is a access 
                point or independent BSS, this table will contain 
                a list of SSIDs which stations must be used to 
                associate with this radio.  This table has an 
                expansion dependent relationship on the ifTable.  
                For each entry in this table, there exists at least
                an entry in the ifTable of ifType ieee80211(71).
                Entries in this table cannot be created or deleted
                by the network management system.  All entries are
                created or deleted by the agent."
        ::= { cd11IfManagement 6 }

cd11IfAuxSsidEntry OBJECT-TYPE
        SYNTAX     Cd11IfAuxSsidEntry
        MAX-ACCESS not-accessible
        STATUS     current
        DESCRIPTION 
                "A collection of attributes defining an auxiliary
                service set which client stations can associate on
                the specific interface.  An interface can have 
                multiple auxiliary service sets while IEEE 802.11 
                defines only one desired service set for each 
                interface. Each radio interface currently supports
                up to 25 SSIDs, and the cd11IfAuxiliarySsidLength 
                object specifies the configured maximum."
        INDEX      { 
                ifIndex, 
                cd11IfAuxSsidIndex 
                   }
        ::= { cd11IfAuxSsidTable 1 }

Cd11IfAuxSsidEntry ::= 
        SEQUENCE   {
            cd11IfAuxSsidIndex          Unsigned32,
            cd11IfAuxSsid               OCTET STRING,
            cd11IfAuxSsidBroadcastSsid  TruthValue, 
            cd11IfAuxSsidMaxAssocSta    Unsigned32,
            cd11IfAuxSsidMicAlgorithm   CDot11IfMicAlgorithm,
            cd11IfAuxSsidWepPermuteAlg
                    CDot11IfWepKeyPermuteAlgorithm
                   }

cd11IfAuxSsidIndex OBJECT-TYPE
        SYNTAX     Unsigned32 (1..4095)
        MAX-ACCESS not-accessible
        STATUS     current
        DESCRIPTION
                "This object identifies a SSID defined on a radio."
        ::= { cd11IfAuxSsidEntry 1 }

cd11IfAuxSsid OBJECT-TYPE
        SYNTAX     OCTET STRING (SIZE(0..32))
        MAX-ACCESS read-write
        STATUS     current
        DESCRIPTION
                "This object specifies a SSID recognized by this 
                radio interface.  The radio interface shall respond 
                to probe requests using this SSID, but it does not 
                advertise this SSID in its beacons."
        ::= { cd11IfAuxSsidEntry 2 }

cd11IfAuxSsidBroadcastSsid OBJECT-TYPE
        SYNTAX     TruthValue 
        MAX-ACCESS read-write
        STATUS     current
        DESCRIPTION
                "This object indicates if an auxiliary SSID 
                is the Broadcast SSID. There is only one Broadcast
                SSID per IEEE 802.11 radio interface." 
        REFERENCE  
                "IEEE Std 802.11-Jan 14 1999, Wireless LAN Medium 
                Access Control and Physical Layer Specifications,
                LAN MAN Standards Committee of the IEEE Computer 
                Society, section 7.3.2.1." 
        ::= { cd11IfAuxSsidEntry 3 }

cd11IfAuxSsidMaxAssocSta OBJECT-TYPE
        SYNTAX     Unsigned32 (0..2007)
        MAX-ACCESS read-write
        STATUS     current
        DESCRIPTION
                "This object defines the maximum number of IEEE
                802.11 stations which may associate with this radio 
                interface through the cd11IfAuxSsid.  If the value 
                is '0', the maximum number is limited only by the 
                IEEE 802.11 standard and any hardware or radio 
                firmware limitations of the access point.  The 
                default value is '0'."
        REFERENCE  
                "IEEE Std 802.11-Jan 14 1999, Wireless LAN Medium 
                Access Control and Physical Layer Specifications,
                LAN MAN Standards Committee of the IEEE Computer 
                Society, section 5.7." 
        ::= { cd11IfAuxSsidEntry 4 }

cd11IfAuxSsidMicAlgorithm OBJECT-TYPE
        SYNTAX     CDot11IfMicAlgorithm
        MAX-ACCESS read-write
        STATUS     current
        DESCRIPTION
                "This object defines the auxiliary MIC algorithm 
                applied to WEP-encoded packets of stations associated
                with this radio interface through the cd11IfAuxSsid.
                The default value is micNone(1)."
        ::= { cd11IfAuxSsidEntry 5 }

cd11IfAuxSsidWepPermuteAlg OBJECT-TYPE
        SYNTAX     CDot11IfWepKeyPermuteAlgorithm
        MAX-ACCESS read-write
        STATUS     current
        DESCRIPTION 
                "This object defines the function through which 
                the WEP encryption key is permuted between key renewal 
                periods for stations associated with this radio
                interface through the cd11IfAuxSsid.  The default value
                is wepPermuteNone(1)." 
        ::= { cd11IfAuxSsidEntry 6 }


cd11IfAuxSsidAuthAlgTable OBJECT-TYPE
        SYNTAX     SEQUENCE OF Cd11IfAuxSsidAuthAlgEntry
        MAX-ACCESS not-accessible
        STATUS     current
        DESCRIPTION
                "This table contains attributes to configure
                authentication algorithms for SSIDs listed in the 
                cd11IfAuxSsidTable.  This table extends the 
                IEEE802dot11-MIB dot11AuthenticationAlgorithmsTable 
                for multiple SSIDs support.  Multiple SSIDs 
                can associate with an interface and multiple 
                authentication algorithms can apply to an auxiliary
                SSID.  

                This table has an expansion dependent relationship 
                on the ifTable.  For each entry in this table, 
                there exists at least an entry in the ifTable of 
                ifType ieee80211(71).  Entries in this table cannot 
                be created or deleted by the network management 
                system.  All entries are created or deleted by 
                the agent."
        REFERENCE  
                "IEEE Std 802.11-Jan 14 1999, Wireless LAN Medium 
                Access Control and Physical Layer Specifications,
                LAN MAN Standards Committee of the IEEE Computer 
                Society, section 5.7.6."
        ::= { cd11IfManagement 7 }

cd11IfAuxSsidAuthAlgEntry OBJECT-TYPE
        SYNTAX     Cd11IfAuxSsidAuthAlgEntry
        MAX-ACCESS not-accessible
        STATUS     current
        DESCRIPTION
                "Each entry specifies authentication algorithm
                configuration attributes of a VLAN for an auxiliary
                SSID on a radio interface." 
        REFERENCE  
                "IEEE Std 802.11-Jan 14 1999, Wireless LAN Medium 
                Access Control and Physical Layer Specifications,
                LAN MAN Standards Committee of the IEEE Computer 
                Society, IEEE802dot11-MIB." 
        INDEX      { 
                ifIndex,
                cd11IfAuxSsidIndex,
                dot11AuthenticationAlgorithmsIndex 
                   }
        ::= { cd11IfAuxSsidAuthAlgTable 1 }

Cd11IfAuxSsidAuthAlgEntry ::= 
        SEQUENCE   {
            cd11IfAuxSsidAuthAlgEnable       TruthValue,
            cd11IfAuxSsidAuthAlgRequireEap   TruthValue,
            cd11IfAuxSsidAuthAlgRequireMac   TruthValue,
            cd11IfAuxSsidAuthAlgDefaultVlan  CDot11IfVlanIdOrZero,
            cd11IfAuxSsidAuthAlgEapMethod    SnmpAdminString,
            cd11IfAuxSsidAuthAlgMacMethod    SnmpAdminString
                   }

cd11IfAuxSsidAuthAlgEnable OBJECT-TYPE
        SYNTAX     TruthValue
        MAX-ACCESS read-write
        STATUS     current
        DESCRIPTION 
                "If the value is 'true', this device may 
                authenticate an association using SSID (specified 
                by cd11IfAuxiliarySSIDIndex) with the algorithm 
                identified by IEEE802dot11-MIB 
                dot11AuthenticationAlgorithmsIndex.  The default 
                value is 'true'."
        REFERENCE  
                "IEEE Std 802.11-Jan 14 1999, Wireless LAN Medium 
                Access Control and Physical Layer Specifications,
                LAN MAN Standards Committee of the IEEE Computer 
                Society, IEEE802dot11-MIB." 
        ::= { cd11IfAuxSsidAuthAlgEntry 1 }

cd11IfAuxSsidAuthAlgRequireEap OBJECT-TYPE
        SYNTAX     TruthValue
        MAX-ACCESS read-write
        STATUS     current
        DESCRIPTION 
                "If both the values of this object and 
                cd11IfAuxSsidAuthAlgEnable are 'true', the 
                association authentication must complete additional 
                network-level EAP authentication before client 
                stations will be unblocked from their association 
                attempts.  If the value of this object is 'false' 
                while cd11IfAuxSsidAuthAlgEnable is 'true', client 
                stations will be unblocked as soon as they 
                complete this enabled IEEE 802.11 authentication.
                The default value is 'true'."
        REFERENCE  
                "IEEE Std 802.11-Jan 14 1999, Wireless LAN Medium 
                Access Control and Physical Layer Specifications,
                LAN MAN Standards Committee of the IEEE Computer 
                Society, IEEE802dot11-MIB." 
        ::= { cd11IfAuxSsidAuthAlgEntry 2 }

cd11IfAuxSsidAuthAlgRequireMac OBJECT-TYPE
        SYNTAX     TruthValue
        MAX-ACCESS read-write
        STATUS     current
        DESCRIPTION
                "If both the values of this object and
                cd11IfAuxSsidAuthAlgEnable are 'true', the
                association authentication must complete additional
                MAC address authentication before client stations
                will be unblocked from their association
                attempts.  If the value of this object is 'false'
                while cd11IfAuxSsidAuthAlgEnable is 'true', client
                stations will be unblocked as soon as they
                complete this enabled IEEE 802.11 authentication.
                The default value is 'true'."
        REFERENCE 
                "IEEE Std 802.11-Jan 14 1999, Wireless LAN Medium
                Access Control and Physical Layer Specifications,
                LAN MAN Standards Committee of the IEEE Computer
                Society, IEEE802dot11-MIB."
        ::= { cd11IfAuxSsidAuthAlgEntry 3 }

cd11IfAuxSsidAuthAlgDefaultVlan OBJECT-TYPE
        SYNTAX     CDot11IfVlanIdOrZero
        MAX-ACCESS read-write
        STATUS     current
        DESCRIPTION
               "This object defines the default VLAN identifier
                for stations associated with this radio interface
                with the dot11AuthenticationAlgorithmsIndex 
                authentication defined in IEEE802dot11-MIB and 
                through the cd11IfAuxSsid.  If the value 
                of this object is '0', it indicates that either the
                default VLAN are not defined for that authentication 
                on this radio interface or the default VLAN is the 
                native VLAN ID.  The default value is '0'."
        ::= { cd11IfAuxSsidAuthAlgEntry 4 }

cd11IfAuxSsidAuthAlgEapMethod OBJECT-TYPE
        SYNTAX     SnmpAdminString
        MAX-ACCESS read-write
        STATUS     current
        DESCRIPTION 
                "If the value of cd11IfAuxSsidAuthAlgRequireEap 
                is 'true' or dot11AuthenticationAlgorithm is 
                Network-EAP, this is the EAP method list to used
                for the EAP authentication."
        REFERENCE  
                "IEEE Std 802.11-Jan 14 1999, Wireless LAN Medium 
                Access Control and Physical Layer Specifications,
                LAN MAN Standards Committee of the IEEE Computer 
                Society, IEEE802dot11-MIB." 
        ::= { cd11IfAuxSsidAuthAlgEntry 5 }

cd11IfAuxSsidAuthAlgMacMethod OBJECT-TYPE
        SYNTAX     SnmpAdminString  
        MAX-ACCESS read-write
        STATUS     current
        DESCRIPTION
                "If the value of cd11IfAuxSsidAuthAlgRequireMac 
                is 'true', this is the MAC address method list to 
                used for the MAC authentication."
        ::= { cd11IfAuxSsidAuthAlgEntry 6 }


cd11IfAssignedAidTable OBJECT-TYPE
        SYNTAX     SEQUENCE OF Cd11IfAssignedAidEntry
        MAX-ACCESS not-accessible
        STATUS     current
        DESCRIPTION 
                "When the radio is not functioning as a client 
                station (i.e., cd11IfStationRole is not 
                'roleClient'), this is the list of AIDs which this
                agent will assign to the clients associating with
                it.  An AID is assigned if the corresponding MAC 
                address matches that of the client.  This table has 
                an expansion dependent relationship on the ifTable.
                For each entry in this table, there exists at least
                an entry in the ifTable of ifType ieee80211(71).

                Entries in this table cannot be created or deleted
                by the network management system.  All entries are
                created or deleted by the agent."
        ::= { cd11IfManagement 8 }

cd11IfAssignedAidEntry OBJECT-TYPE
        SYNTAX     Cd11IfAssignedAidEntry
        MAX-ACCESS not-accessible
        STATUS     current
        DESCRIPTION 
                "Each entry associates an AID with a client MAC 
                address.  The relationship between AID and client 
                MAC address is one to one."
        INDEX      { 
                ifIndex, 
                cd11IfAssignedAid 
                   }
        ::= { cd11IfAssignedAidTable 1 }

Cd11IfAssignedAidEntry ::= 
        SEQUENCE   {
            cd11IfAssignedAid  Unsigned32, 
            cd11IfAssignedSta  MacAddress 
                   }

cd11IfAssignedAid OBJECT-TYPE
        SYNTAX     Unsigned32 (2..2007)
        MAX-ACCESS not-accessible 
        STATUS     current
        DESCRIPTION
                "This object specifies the AID for a client 
                station to the radio interface."
        ::= { cd11IfAssignedAidEntry 1 }

cd11IfAssignedSta OBJECT-TYPE
        SYNTAX     MacAddress
        MAX-ACCESS read-write
        STATUS     current
        DESCRIPTION
                "This object defines the client station MAC 
                address.  When a client associates with this 
                radio interface, it shall always be assigned with 
                the cd11IfAssignedAid as its IEEE 802.11 AID.
                The default value is '000000000000'H." 
        REFERENCE  
                "IEEE Std 802.11-Jan 14 1999, Wireless LAN Medium 
                Access Control and Physical Layer Specifications,
                LAN MAN Standards Committee of the IEEE Computer 
                Society, section 5.7.2." 
        ::= { cd11IfAssignedAidEntry 2 }


cd11IfVlanEncryptKeyTable OBJECT-TYPE
        SYNTAX     SEQUENCE OF Cd11IfVlanEncryptKeyEntry
        MAX-ACCESS not-accessible
        STATUS     current
        DESCRIPTION
                "This table contains shared WEP keys for all IEEE
                802.11 packets transmitted and received frames over
                a VLAN identified by the cwvlWlanVlanId if both VLAN
                and encryption are enabled (i.e., the 
                cwvlWlanEncryptionMode is wep(2) or aes(3)) on the
                radio interface.

                If WEP encryption is enabled for the transmitted 
                IEEE 802.11 frames, then the Default Shared WEP 
                key in the set is used to encrypt the transmitted 
                broadcast and multicast frames associated with
                the cwvlWlanVlanId.  Key '1' in the set is the 
                default key.  If an individual session key is not 
                defined for the target station address, then the 
                Default Shared WEP key will also be used to encrypt 
                or decrypt unicast frames associated with the
                cwvlWlanVlanId."
        REFERENCE  
                "CISCO-WLAN-VLAN-MIB, June 2002, Cisco Systems 
                Wireless Virtual LAN MIB."
        ::= { cd11IfManagement 9 }

cd11IfVlanEncryptKeyEntry OBJECT-TYPE
        SYNTAX     Cd11IfVlanEncryptKeyEntry
        MAX-ACCESS not-accessible
        STATUS     current
        DESCRIPTION 
                "Each entry contains the key index, key length, and 
                key value.  There is a maximum of 4 keys per VLAN or
                key set.  Each key set exists only if the 
                corresponding VLAN is enabled on the interface, and
                it is indexed by the VLAN ID."
        INDEX      { 
                ifIndex, 
                cd11IfVlanId, 
                cd11IfVlanEncryptKeyIndex 
                   }
        ::= { cd11IfVlanEncryptKeyTable 1 }

Cd11IfVlanEncryptKeyEntry 
        ::= SEQUENCE { 
            cd11IfVlanId                  CDot11IfVlanIdOrZero,
            cd11IfVlanEncryptKeyIndex     Unsigned32, 
            cd11IfVlanEncryptKeyLen       Unsigned32,
            cd11IfVlanEncryptKeyValue     WepKeyType128,
            cd11IfVlanEncryptKeyStatus    RowStatus, 
            cd11IfVlanEncryptKeyTransmit  TruthValue
                     }

cd11IfVlanId OBJECT-TYPE
        SYNTAX     CDot11IfVlanIdOrZero 
        MAX-ACCESS not-accessible
        STATUS     current
        DESCRIPTION
                "This object identifies the VLAN (1 to 4095) on 
                this radio interface.  The object value should 
                match the corresponding cwvlWlanVlanId in the 
                cwvlWlanVlanTable or cd11IfVlanSecurityVlanId 
                object in the cd11IfVlanSecurityTable.  When
                the value is '0', the encryption keys are applied
                to the non-VLAN configuration."
        REFERENCE  
                "CISCO-WLAN-VLAN-MIB, June 2002, Cisco Systems 
                Wireless Virtual LAN MIB."
        ::= { cd11IfVlanEncryptKeyEntry 1 }

cd11IfVlanEncryptKeyIndex OBJECT-TYPE
        SYNTAX     Unsigned32 (1..4)
        MAX-ACCESS not-accessible
        STATUS     current
        DESCRIPTION
                "This object is a representative of the 
                corresponding 802.11 WEP Key Index used when 
                transmitting or receiving frames with this key.  
                SNMP table indexing conventions require table 
                index to be non-zero.  Therefore, this object has
                to be one greater than the actual 802.11 WEP key 
                index.  A value of '1' for this object corresponds 
                to a value of '0' for the 802.11 WEP key index."
        ::= { cd11IfVlanEncryptKeyEntry 2 }

cd11IfVlanEncryptKeyLen OBJECT-TYPE
        SYNTAX     Unsigned32 (0..13)
        MAX-ACCESS read-create
        STATUS     current
        DESCRIPTION
                "This object specifies the length in octets of 
                cd11IfVlanEncryptKeyValue.  Common values are 5 for 
                40-bit WEP key and 13 for 128-bit WEP key.  A value 
                of '0' means that the key is not set but the VLAN
                is enabled." 
        DEFVAL     { 0 }
        ::= { cd11IfVlanEncryptKeyEntry 3 }

cd11IfVlanEncryptKeyValue OBJECT-TYPE
        SYNTAX     WepKeyType128
        MAX-ACCESS read-create
        STATUS     current
        DESCRIPTION
                "This is the WEP secret key value.  The agent
                always returns a zero-length string when this
                object is read for security reason."
        ::= { cd11IfVlanEncryptKeyEntry 4 }
               
cd11IfVlanEncryptKeyStatus OBJECT-TYPE
        SYNTAX     RowStatus
        MAX-ACCESS read-create
        STATUS     current
        DESCRIPTION
                "This object controls and reflects the status of 
                rows in this table.  

                When the row in 'active' state, the NMS can modify
                both key length and value.  To delete a row, set this 
                object value to 'destroy'."
        ::= { cd11IfVlanEncryptKeyEntry 5 }

cd11IfVlanEncryptKeyTransmit OBJECT-TYPE
        SYNTAX     TruthValue
        MAX-ACCESS read-create
        STATUS     current
        DESCRIPTION
                "Only one of the 4 keys of a VLAN can be the transmit
                key.  Setting any one of the 4 keys to 'true', the
                agent will automatically change the value of
                cd11IfVlanEncryptKeyTransmit of the other 3 keys to
                'false' if they exist." 
        ::= { cd11IfVlanEncryptKeyEntry 6 }



cd11IfVlanSecurityTable OBJECT-TYPE
        SYNTAX     SEQUENCE OF Cd11IfVlanSecurityEntry
        MAX-ACCESS not-accessible
        STATUS     current
        DESCRIPTION
                "This table contains encryption method and key
                rotation configurations for all VLANs on all 
                IEEE 802.11 radio interfaces.  This table has an
                expansion dependent relationship on the ifTable.  
                For each entry in this table, there exists at least
                an entry in the ifTable of ifType ieee80211(71).

                VLANs are identified by the cd11IfVlanSecurityVlanId,
                and the actual VLAN does not have to exist or be 
                enabled for the encryption configuration to exist."
        ::= { cd11IfManagement 10 }

cd11IfVlanSecurityEntry OBJECT-TYPE
        SYNTAX     Cd11IfVlanSecurityEntry
        MAX-ACCESS not-accessible
        STATUS     current
        DESCRIPTION
                "Each entry is a set of encryption configurations  
                for traffic on a VLAN of a IEEE 802.11 radio
                interface."
        INDEX      {
                ifIndex,
                cd11IfVlanSecurityVlanId        
                   }
        ::= { cd11IfVlanSecurityTable 1 }

Cd11IfVlanSecurityEntry 
        ::= SEQUENCE { 
            cd11IfVlanSecurityVlanId          CDot11IfVlanIdOrZero,
            cd11IfVlanSecurityVlanEnabled     TruthValue,
            cd11IfVlanBcastKeyChangeInterval  Unsigned32,
            cd11IfVlanBcastKeyCapabilChange   TruthValue, 
            cd11IfVlanBcastKeyClientLeave     TruthValue, 
            cd11IfVlanSecurityCiphers         CDot11IfCipherType, 
            cd11IfVlanSecurityRowStatus       RowStatus,
            cd11IfVlanEncryptionMode          INTEGER,
            cd11IfVlanWepEncryptOptions       INTEGER,
            cd11IfVlanWepEncryptMic           TruthValue,
            cd11IfVlanWepEncryptKeyHashing    TruthValue,
            cd11IfVlanPsPacketForwardEnable   TruthValue
                     }

cd11IfVlanSecurityVlanId OBJECT-TYPE
        SYNTAX     CDot11IfVlanIdOrZero 
        MAX-ACCESS not-accessible 
        STATUS     current
        DESCRIPTION 
                "This is the VLAN ID (1-4095) to which the 
                parameters in each conceptual row shall be 
                applied.  If the value is '0', these parameters 
                apply to the non-VLAN configuration." 
        ::= { cd11IfVlanSecurityEntry 1 }

cd11IfVlanSecurityVlanEnabled OBJECT-TYPE
        SYNTAX     TruthValue
        MAX-ACCESS read-create
        STATUS     current
        DESCRIPTION 
                "If the value is 'true', this VLAN sub-interface is 
                enabled on all trunk and hybrid ports.  If the value 
                is 'false', this VLAN is disabled on all ports.  For
                platforms supporting NMS to create VLAN sub-interfaces,
                setting this object to 'true' will create the
                corresponding VLAN sub-interfaces on all ports and
                'false' will remove the the corresponding VLAN."
        ::= { cd11IfVlanSecurityEntry 2 }

cd11IfVlanBcastKeyChangeInterval OBJECT-TYPE
        SYNTAX     Unsigned32 (0|10..10000000)
        MAX-ACCESS read-create
        STATUS     current
        DESCRIPTION 
                "This is the broadcast key rotation period.  If the 
                value is '0', there is no key rotation."
        ::= { cd11IfVlanSecurityEntry 3 }
             
cd11IfVlanBcastKeyCapabilChange OBJECT-TYPE
        SYNTAX     TruthValue
        MAX-ACCESS read-create
        STATUS     current
        DESCRIPTION 
                "If it is 'true', a new key will be used every time 
                when the common set of encryption capability among
                clients of this radio on this VLAN is changed."
        DEFVAL     { false }
        ::= { cd11IfVlanSecurityEntry 4 }

cd11IfVlanBcastKeyClientLeave OBJECT-TYPE
        SYNTAX     TruthValue
        MAX-ACCESS read-create
        STATUS     current
        DESCRIPTION
                "If it is 'true', a new key will be used every time 
                when a client of the radio on this VLAN disassociates."
        DEFVAL     { false }
        ::= { cd11IfVlanSecurityEntry 5 }

cd11IfVlanSecurityCiphers OBJECT-TYPE
        SYNTAX     CDot11IfCipherType 
        MAX-ACCESS read-create
        STATUS     current
        DESCRIPTION 
                "If cd11IfVlanEncryptionMode is cipher(1), these
                are all the possible cipher type combinations
                currently supported for data frame encryption from
                different IEEE 802.11 radio interface implementations.
                Some platform may support only a subset of the
                combinations.  Agent will not honor invalid
                combinations.  If none of the bits are set, no
                encryption will be done. 
                    aesccm      WPA AES CCMP encryption,
                    ckip        Cisco Per packet key hashing,
                    cmic        Cisco MMH MIC,
                    ckip|cmic   Cisco Per packet key hashing and MIC,
                    tkip        WPA Temporal Key encryption,
                    wep128      128-bit WEP key,
                    wep40       40-bit WEP key.
                    tkip|wep128 WPA Temporal Key and 128-bit WEP,
                    tkip|wep40  WPA Temporal Key and 40-bit WEP."
        ::= { cd11IfVlanSecurityEntry 6 }
             
cd11IfVlanSecurityRowStatus OBJECT-TYPE
        SYNTAX     RowStatus
        MAX-ACCESS read-create
        STATUS     current
        DESCRIPTION 
                "This is used to create a new row, modify or
                delete an existing VLAN encryption configuration
                in this table.

                Creation of rows must be done via 'createAndGo' and 
                cd11IfVlanSecurityVlanEnabled and 
                cd11IfVlanSecurityCiphers columns are mandatory. 
                This object will become 'active' if the NMS performs
                a multivarbind set including this object and 
                successfully creates the encryption configuration.

                Modification and deletion of rows can be done via
                'createAndGo' and 'delete' respectively when this 
                object is 'active'.  Any encryption configurations 
                of a VLAN should only be deleted when it is not 
                being used for any client association."
        ::= { cd11IfVlanSecurityEntry 7 }

cd11IfVlanEncryptionMode OBJECT-TYPE
        SYNTAX     INTEGER {
                          cipher(1),
                          wep(2)
                           }
        MAX-ACCESS read-create
        STATUS     current
        DESCRIPTION
                "Encryption mode this VLANs are:
                    cipher(1) - WPA and Cisco encryptions,
                    wep(2)    - WEP Only encryption"
        DEFVAL     { cipher }
        ::= { cd11IfVlanSecurityEntry 8 }

cd11IfVlanWepEncryptOptions OBJECT-TYPE
        SYNTAX     INTEGER {
                          mandatory(1),
                          optional(2)
                           }
        MAX-ACCESS read-create
        STATUS     current
        DESCRIPTION
                "If cd11IfVlanEncryptionMode is wep(2),
                    mandatory(1) - WEP encryption is mandatory,
                    optional(2)  - WEP encryption is option.
                for all data frames on this VLAN."
        DEFVAL     { mandatory }
        ::= { cd11IfVlanSecurityEntry 9 }

cd11IfVlanWepEncryptMic OBJECT-TYPE
        SYNTAX     TruthValue
        MAX-ACCESS read-create
        STATUS     current
        DESCRIPTION
                "If cd11IfVlanEncryptionMode is wep(2) and
                 this object is 'true', MIC will be performed
                 on all data frames on this VLAN. Otherwise,
                 no MIC will be done."
        DEFVAL     { false }
        ::= { cd11IfVlanSecurityEntry 10 }

cd11IfVlanWepEncryptKeyHashing OBJECT-TYPE
        SYNTAX     TruthValue
        MAX-ACCESS read-create
        STATUS     current
        DESCRIPTION
                "If cd11IfVlanEncryptionMode is wep(2) and
                 this object is 'true', key hashing will be
                 used for encryption. Otherwise, no key
                 hashing will be done."
        DEFVAL     { false }
        ::= { cd11IfVlanSecurityEntry 11 }

cd11IfVlanPsPacketForwardEnable OBJECT-TYPE
        SYNTAX     TruthValue
        MAX-ACCESS read-create
        STATUS     current
        DESCRIPTION
                "If both cd11IfVlanSecurityVlanEnabled and this 
                object are 'true', PSPF is enabled on VLAN 
                cd11IfVlanSecurityVlanId of this radio interface 
                and direct traffic between wireless clients of the
                VLAn is not allowed.  Otherwise, PSPF is disabled
                on the VLAN and direct traffic between wireless
                clients of the VLAN is allowed."
        DEFVAL     { false }
        ::= { cd11IfVlanSecurityEntry 12 }


cd11IfRadioMonitoringTable OBJECT-TYPE
        SYNTAX     SEQUENCE OF Cd11IfRadioMonitoringEntry
        MAX-ACCESS not-accessible
        STATUS     current
        DESCRIPTION
                "This table is for monitoring of remote active 
                IEEE 802.11 radio devices on the network.
                Each table entry shows an active radio being
                monitored by a hot standby radio on this 
                monitoring unit. 

                This table has a sparse dependent relationship 
                on the ifTable.  For each entry in this table, 
                there exists an entry in the ifTable of ifType 
                ieee80211(71).  Entries on this table can be 
                added, deleted, and modified by the NMS."
        ::= { cd11IfManagement 11 }

cd11IfRadioMonitoringEntry OBJECT-TYPE
        SYNTAX     Cd11IfRadioMonitoringEntry
        MAX-ACCESS not-accessible
        STATUS     current
        DESCRIPTION
                "Each entry specifies the MAC address of the remote
                radio and the monitoring configuration and status
                of the local radio.  Most platforms supporting this
                table only support one entry per ifIndex."
        INDEX      { 
                ifIndex,
                cd11IfRemoteRadioMacAddr 
                   }
        ::= { cd11IfRadioMonitoringTable 1 }

Cd11IfRadioMonitoringEntry 
        ::= SEQUENCE {
            cd11IfRemoteRadioMacAddr          MacAddress,     
            cd11IfRadioMonitorPollingFreq     Unsigned32, 
            cd11IfRadioMonitorPollingTimeOut  Unsigned32, 
            cd11IfLocalRadioMonitorStatus     INTEGER,
            cd11IfRadioMonitorRowStatus       RowStatus
                     }
  
cd11IfRemoteRadioMacAddr OBJECT-TYPE
        SYNTAX     MacAddress 
        MAX-ACCESS not-accessible 
        STATUS     current
        DESCRIPTION 
                "Mac address of the active IEEE 802.11 radio device 
                to be monitored by this hot standby monitoring radio.
                The cd11IfPhyMacSpecification of the local and remote
                radios must be the same in order for the monitoring to
                happen." 
        ::= { cd11IfRadioMonitoringEntry 1 }

cd11IfRadioMonitorPollingFreq OBJECT-TYPE   
        SYNTAX Unsigned32 (1..30) 
        UNITS "seconds"
        MAX-ACCESS read-create
        STATUS current
        DESCRIPTION
                "The frequency, in seconds, the remote active radio 
                specified by cd11IfRemoteRadioMacAddr is polled 
                for its health."
        DEFVAL { 5 }
        ::= { cd11IfRadioMonitoringEntry 2 }


cd11IfRadioMonitorPollingTimeOut OBJECT-TYPE 
        SYNTAX Unsigned32 (1..600) 
        UNITS "seconds"
        MAX-ACCESS read-create
        STATUS current
        DESCRIPTION
                "The total time, in seconds, this standby monitoring 
                radio unit can tolerate the failure of polling 
                of the active radio unit.  After this duration, one
                more failure of the polling will trigger this hot
                standby monitoring radio to take over and become an
                active radio.  It will then stop all monitoring 
                activity and set the instance of 
                cd11IfLocalRadioMonitorStatus indexed by the
                failed radio cd11IfRemoteRadioMacAddr to 'active'."
        DEFVAL { 5 }
        ::= { cd11IfRadioMonitoringEntry 3 }

cd11IfLocalRadioMonitorStatus OBJECT-TYPE
        SYNTAX     INTEGER {
                         active(1),
                         monitor(2),
                         inactive(3) 
                           }
        MAX-ACCESS read-create
        STATUS     current
        DESCRIPTION
                "NMS can only set this object to monitor(2).  In
                the monitor(2) state, this local radio will monitor
                the remote radio specified in the 
                cd11IfRemoteRadioMacAddr.  

                When the remote radio fails or goes down, this local 
                radio will takeover the functions and became active.
                The agent will set the instance of
                cd11IfLocalRadioMonitorStatus indexed by the
                failed radio cd11IfRemoteRadioMacAddr to 'active'.
 
                This local radio will not monitor any other radios
                when it is active, therefore, all other instances of
                cd11IfLocalRadioMonitorStatus indexed by the same
                ifIndex but different cd11IfRemoteRadioMacAddr
                will be set to 'inactive'."
        ::= { cd11IfRadioMonitoringEntry 4 }

cd11IfRadioMonitorRowStatus OBJECT-TYPE
        SYNTAX     RowStatus 
        MAX-ACCESS read-create
        STATUS     current
        DESCRIPTION
                "This object is used for creating, modifying, and
                deleting rows in this table.
 
                Creation of rows must be done via 'createAndGo'. 
                This object will become 'active' if the NMS performs
                a multivarbind set including this object. 

                Any object in a row can be modified any time when 
                the row is in the 'active' state via 'createAndGo'.

                Removal of a row can be done via setting this
                object to 'destroy'." 
        ::= { cd11IfRadioMonitoringEntry 5 }


cd11IfDot11UpgradeStatusTable OBJECT-TYPE
        SYNTAX     SEQUENCE OF Cd11IfDot11UpgradeStatusEntry
        MAX-ACCESS not-accessible
        STATUS     current
        DESCRIPTION
                "This table represents the status of upgrade of
                the radios to the newer frequencies of the 5150-5250
                MHz band.

                This table has a sparse dependent relationship on the
                ifTable.  For each entry in this table, there exists 
                an entry in the ifTable of ifType ieee80211(71).

                Entries in this table cannot be created or deleted
                by the network management system.  All entries are
                created or deleted by the agent. "
        ::= { cd11IfManagement 12 }

cd11IfDot11UpgradeStatusEntry OBJECT-TYPE
        SYNTAX      Cd11IfDot11UpgradeStatusEntry
        MAX-ACCESS not-accessible
        STATUS     current
        DESCRIPTION
                "Each entry corresponds to one conceptual row in
                 cd11IfDot11UpgradeStatusTable and represents the
                 status of upgrade of a dot11 radio interface. "
        INDEX      { ifIndex }
        ::= { cd11IfDot11UpgradeStatusTable 1 }

Cd11IfDot11UpgradeStatusEntry ::=
        SEQUENCE   {
                cd11IfDot11UpgradeStatus Cd11IfDot11UpgradeStatus
                   }

cd11IfDot11UpgradeStatus OBJECT-TYPE
        SYNTAX     Cd11IfDot11UpgradeStatus
        MAX-ACCESS read-only
        STATUS     current
        DESCRIPTION
                "This object represents the status of upgrade of
                 a dot11 radio interface. "
        ::= {cd11IfDot11UpgradeStatusEntry 1 }


cd11IfPhyOperationTable OBJECT-TYPE
        SYNTAX     SEQUENCE OF Cd11IfPhyOperationEntry
        MAX-ACCESS not-accessible
        STATUS     current
        DESCRIPTION 
                "This table contains the IEEE 802.11 Physical
                Layer operation configuration parameters for
                each radio interface.  This table has a sparse 
                dependent relationship on the ifTable.  
                For each entry in this table, there exists an 
                entry in the ifTable of ifType ieee80211(71).
                Entries in this table cannot be created or deleted
                by the network management system.  All entries are
                created or deleted by the agent."
        ::= { cd11IfPhyConfig 1 }

cd11IfPhyOperationEntry OBJECT-TYPE
        SYNTAX     Cd11IfPhyOperationEntry
        MAX-ACCESS not-accessible
        STATUS     current
        DESCRIPTION 
                "A collection of attributes defining the physical
                characteristics and behaviors of an IEEE 802.11 PHY."
        INDEX      { ifIndex }
        ::= { cd11IfPhyOperationTable 1 }

Cd11IfPhyOperationEntry ::= 
        SEQUENCE   {
            cd11IfCurrentCarrierSet    INTEGER,
            cd11IfModulationType       INTEGER,
            cd11IfPreambleType         INTEGER,
            cd11IfDomainCapabilitySet  Integer32,
            cd11IfPhyBasicRateSet      OCTET STRING,
            cd11IfPhyMacSpecification  INTEGER,
            cd11IfPhyConcatenation     Integer32, 
            cd11IfPhyNativePowerUseStandard   
                                       TruthValue  
                   }

cd11IfCurrentCarrierSet OBJECT-TYPE
        SYNTAX     INTEGER { 
                         usa(0), 
                         europe(1), 
                         japan(2), 
                         spain(3),
                         france(4), 
                         belgium(5), 
                         israel(6),
                         canada(7), 
                         australia(8), 
                         japanWide(9),
                         world(10),
                         usa5GHz(11),
                         europe5GHz(12),
                         japan5GHz(13),
                         singapore5GHz(14),
                         taiwan5GHz(15),
                         china(16),
                         northAmer5GHzUNI3(17),
                         chnIreAus5GHzUNI3(18),
                         hkNZ5GHzUNI3(19),
                         korea5GHzUNI3(20),
                         mexAusNZ5GHz(21),
                         china5GHz(22),
                         korea5GHzUNI123E(23),
                         japan5GHzUNI12(24),    
                         taiwan5GHzUNI23E(25),
                         israel5GhzUNI12(26),
                         usaFCC49PS(27),
                         japan5GHzUNI1(28)
                           } 
        MAX-ACCESS read-only
        STATUS     current
        DESCRIPTION 
                "This object defines the carrier set of the radio.  
                The carrier set implies a regulatory domain, but
                geographic-specific restrictions within a regulatory
                domain may necessitate several carrier sets within 
                the regulatory domain.
                         usa(0)         - ISM 2.4 GHz America 
                         europe(1)      - ISM 2.4 GHz Europe 
                         japan(2)       - ISM 2.4 GHz Japan 
                         spain(3)       - ISM 2.4 GHz Spain 
                         france(4)      - ISM 2.4 GHz France 
                         belgium(5)     - ISM 2.4 GHz Belgium 
                         israel(6)      - ISM 2.4 GHz Israel 
                         canada(7)      - ISM 2.4 GHz Canada 
                         australia(8)   - ISM 2.4 GHz Australia 
                         japanWide(9)   - ISM 2.4 GHz JapanWide  
                         world(10)      - ISM 2.4 GHz World
                         usa5GHz(11)       - OFDM UNII 2 America
                         europe5GHz(12)    - OFDM UNII 2 Europe
                         japan5GHz(13)     - OFDM UNII 2 Japan
                         singapore5GHz(14) - OFDM UNII 2 Singapore
                         taiwan5GHz(15)    - OFDM UNII 2 Taiwan
                         china(16)      - ISM 2.4 GHz China
                         northAmer5GHzUNI3(17) 
                             - OFDM UNII 3 North America
                         chnIreAus5GHzUNI3(18) 
                             - OFDM UNII 3 China, Ireland, Austrialia 
                         hkNZ5GHzUNI3(19)
                             - OFDM UNII 3 Hong Kong, New Zealand
                         korea5GHzUNI3(20)
                             - OFDM UNII 3 Korea
                         mexAusNZ5GHzUNI3(21)
                             - OFDM UNII 3 Mexical, Australia, 
                               New Zealand (North America without 
                               ETSI Channels)
                         china5GHzUNI2(22)     
                             - OFDM UNII 2 China
                         korea5GHzUNI123E(23)  
                             - OFDM UNII 1,2,3,ETSI Korea 
                         japan5GHzUNI12(24)    
                             - OFDM UNII 1,2 Japan
                         taiwan5GHzUNI23E(25)  
                             - OFDM UNII 2,3,ETSI Taiwan
                         israel5GhzUNI12(26)   
                             - OFDM UNII 1,2 Israel
                         usaFCC49PS(27)
                             - OFDM FCC49 USA Public Safety
                         japan5GHzUNI1(28)
                             - OFDM UNII 1 Japan"
        REFERENCE  
                "IEEE Std 802.11-Jan 14 1999, Wireless LAN Medium 
                Access Control and Physical Layer Specifications,
                LAN MAN Standards Committee of the IEEE Computer 
                Society, section 14.6.10." 
        ::= { cd11IfPhyOperationEntry 1 }

cd11IfModulationType OBJECT-TYPE
        SYNTAX     INTEGER { 
                         standard(1), 
                         mok(2) 
                           }
        MAX-ACCESS read-write
        STATUS     current
        DESCRIPTION 
                "This object specifies the RF modulation type of 
                the radio.
                    standard(1) - Standard, this is the default 
                                  setting currently defined in the 
                                  IEEE 802.11 standard.
                    mok(2)      - MOK, this modulation was used 
                                  before the IEEE finished the 
                                  high-speed 802.11 standard.
                The default modulation type is standard(1)." 
        REFERENCE  
                "IEEE Std 802.11-Jan 14 1999, Wireless LAN Medium 
                Access Control and Physical Layer Specifications,
                LAN MAN Standards Committee of the IEEE Computer 
                Society, section 14.6.10." 
        ::= { cd11IfPhyOperationEntry 2 }

cd11IfPreambleType OBJECT-TYPE
        SYNTAX     INTEGER { 
                         long(1), 
                         short(2) 
                           }
        MAX-ACCESS read-write
        STATUS     current
        DESCRIPTION 
                "This object specifies the current radio preamble 
                type in use by the station.  Possible values:
                        long(1)  - long preambles 
                        short(2) - short preambles.
                A long preamble ensures compatibility between 
                access point and all early models of Cisco 
                Aironet Wireless LAN adapters (client devices).  
                A short preamble improves throughput performance.
                The default preamble type is short(2)." 
        REFERENCE  
                "IEEE Std 802.11-Jan 14 1999, Wireless LAN Medium 
                Access Control and Physical Layer Specifications,
                LAN MAN Standards Committee of the IEEE Computer 
                Society, section 14.6.10." 
        ::= { cd11IfPhyOperationEntry 3 }

cd11IfDomainCapabilitySet OBJECT-TYPE
        SYNTAX     Integer32
        MAX-ACCESS read-write
        STATUS     current
        DESCRIPTION
                "This object specifies the current multi-domain
                capability setting of this radio.  This object
                takes one of the dot11MultiDomainCapabilityIndex
                values on the dot11MultiDomainCapabilityTable.  

                The setting controls the first working radio channel
                number, the number of working channels, and the 
                maximum transmit power level of the radio.  The 
                setting must match the corresponding value of the 
                cd11IfCurrentCarrierSet set for this radio.  This
                object is writable only if the IEEE 802.11 
                multi-domain capability option is implemented
                and enabled via dot11MultiDomainCapabilityImplemented
                and dot11MultiDomainCapabilityEnabled."
        REFERENCE
                "IEEE Std 802.11-Jan 14 1999, Wireless LAN Medium 
                Access Control and Physical Layer Specifications,
                LAN MAN Standards Committee of the IEEE Computer 
                Society, IEEE802dot11-MIB." 
        ::= { cd11IfPhyOperationEntry 4 }

cd11IfPhyBasicRateSet OBJECT-TYPE
        SYNTAX     OCTET STRING (SIZE(1..126))
        MAX-ACCESS read-write
        STATUS     current
        DESCRIPTION
                "This attribute specifies if a data rate in the 
                dot11OperationalRateSet of the IEEE802dot11-MIB  
                is a Basic Rate for this radio interface.
                If a data rate is a Basic Rate, the corresponding
                octet of this attribute will contain a value of
                128 (or the most significant bit is set). Otherwise,
                the corresponding octet of this attribute will
                be 0."
        REFERENCE
                "IEEE Std 802.11-Jan 14 1999, Wireless LAN Medium
                Access Control and Physical Layer Specifications,
                LAN MAN Standards Committee of the IEEE Computer
                Society, IEEE802dot11-MIB."
        ::= { cd11IfPhyOperationEntry 5 }

cd11IfPhyMacSpecification OBJECT-TYPE
        SYNTAX     INTEGER {
                         ieee802dot11a(1),
                         ieee802dot11b(2),
                         ieee802dot11g(3)
                           }
        MAX-ACCESS read-only
        STATUS     current
        DESCRIPTION
                "This object specifies which IEEE 802.11 Standard 
                applies to this radio interface.
                     ieee802dot11a(1) - IEEE 802.11a Standard,
                     ieee802dot11b(2) - IEEE 802.11b Standard,
                     ieee802dot11g(3) - IEEE 802.11g Standard."
        REFERENCE 
                "IEEE P802.11g (expected June 2003), Wireless LAN 
                Medium Access Control (MAC) and Physical Layer (PHY) 
                Specifications: Higher Speed Physical Layer (PHY) 
                Extension to IEEE 802.11b."
        ::= { cd11IfPhyOperationEntry 6 }

cd11IfPhyConcatenation OBJECT-TYPE
        SYNTAX     Integer32
        MAX-ACCESS read-write
        STATUS     current
        DESCRIPTION
                "If the value of cd11IfStationRole is 'roleBridge' 
                or 'roleNrBridge', this object sets the maximum 
                packet concatenation size in bytes for all 
                outbound packets.  For our current 5 GHz product,
                the maximum value range is from 1600 to 4000."
        ::= { cd11IfPhyOperationEntry 7 }

cd11IfPhyNativePowerUseStandard OBJECT-TYPE
        SYNTAX     TruthValue  
        MAX-ACCESS read-write
        STATUS     current
        DESCRIPTION
                "This object indicates if queries for current 
                transmit power and number of transmit power levels
                of the radio for the frequency band shall be via 
                the Standard IEEE802dot11-MIB dot11PhyTxPowerTable
                dot11CurrentTxPowerLevel and
                dot11NumberSupportedPowerLevels objects or
                corresponding cd11IfNativeCurrentPowerLevel 
                and cd11IfNativeNumberPowerLevels objects 
                in the cd11IfRfNativePowerTable. 

                If the value is 'true', the dot11CurrentTxPowerLevel
                is used to configure the current radio transmit
                power level.  If the value is 'false', the 
                cd11IfNativeCurrentPowerLevel object shall be used
                to configure the current radio transmit power level." 
        REFERENCE
                "IEEE Std 802.11-Jan 14 1999, Wireless LAN Medium
                Access Control and Physical Layer Specifications,
                LAN MAN Standards Committee of the IEEE Computer
                Society, IEEE802dot11-MIB."
        DEFVAL     { true }
        ::= { cd11IfPhyOperationEntry 8 }


cd11IfPhyFhssTable OBJECT-TYPE
        SYNTAX     SEQUENCE OF Cd11IfPhyFhssEntry
        MAX-ACCESS not-accessible
        STATUS     current
        DESCRIPTION
                "This table contains the Physical Layer
                Frequency Hopping Spread Spectrum configuration 
                parameters for each radio interface.  This table 
                has a sparse dependent relationship on the ifTable.
                For each entry in this table, there exists an 
                entry in the ifTable of ifType ieee80211(71).
                Entries in this table cannot be created or deleted
                by the network management system.  All entries are
                created or deleted by the agent."
        REFERENCE  
                "IEEE Std 802.11-Jan 14 1999, Wireless LAN Medium 
                Access Control and Physical Layer Specifications,
                LAN MAN Standards Committee of the IEEE Computer 
                Society, section 14.1.2." 
        ::= { cd11IfPhyConfig 4 }

cd11IfPhyFhssEntry OBJECT-TYPE
        SYNTAX     Cd11IfPhyFhssEntry
        MAX-ACCESS not-accessible
        STATUS     current
        DESCRIPTION
                "A collection of attributes defining the FHSS 
                configuration parameters of a radio interface."
        INDEX      { ifIndex }
        ::= {  cd11IfPhyFhssTable 1 }

Cd11IfPhyFhssEntry ::= 
        SEQUENCE   {
            cd11IfPhyFhssMaxCompatibleRate  Integer32 
                   }

cd11IfPhyFhssMaxCompatibleRate OBJECT-TYPE
        SYNTAX     Integer32 (2..127) 
        UNITS      "500 Kb per second"
        MAX-ACCESS read-write
        STATUS     current
        DESCRIPTION 
                "This object specifies the of maximum data 
                rate at which the station may transmit data.  
                The octet contains a value representing a rate.   
                The rate should be within the range from '2' to 
                '127', corresponding to data rates in increments
                of 500 kb/s from 1 Mb/s to 63.5 Mb/s.  It should be 
                one of the rates in the IEEE802dot11-MIB
                dot11OperationalRateSet.  The default value is 
                '127'."
        REFERENCE  
                "IEEE Std 802.11-Jan 14 1999, Wireless LAN Medium 
                Access Control and Physical Layer Specifications,
                LAN MAN Standards Committee of the IEEE Computer 
                Society, IEEE802dot11-MIB." 
        ::= { cd11IfPhyFhssEntry 1 }


cd11IfPhyDsssTable OBJECT-TYPE
        SYNTAX     SEQUENCE OF Cd11IfPhyDsssEntry
        MAX-ACCESS not-accessible
        STATUS     current
        DESCRIPTION 
                "This table contains the Physical Layer
                Direct Sequence Spread Spectrum configuration 
                parameters for each radio interface.  This table 
                has a sparse dependent relationship on the ifTable.
                For each entry in this table, there exists an 
                entry in the ifTable of ifType ieee80211(71).
                Entries in this table cannot be created or deleted
                by the network management system.  All entries are
                created or deleted by the agent."
        REFERENCE  
                "IEEE Std 802.11-Jan 14 1999, Wireless LAN Medium 
                Access Control and Physical Layer Specifications,
                LAN MAN Standards Committee of the IEEE Computer 
                Society, section 15.1." 
        ::= { cd11IfPhyConfig 5 }

cd11IfPhyDsssEntry OBJECT-TYPE
        SYNTAX     Cd11IfPhyDsssEntry
        MAX-ACCESS not-accessible
        STATUS     current
        DESCRIPTION 
                "A collection of attributes defining the DSSS 
                configuration parameters of a radio interface."
        INDEX      { ifIndex }
        ::= { cd11IfPhyDsssTable 1 }

Cd11IfPhyDsssEntry ::= 
        SEQUENCE   {
            cd11IfPhyDsssMaxCompatibleRate  Integer32,
            cd11IfPhyDsssChannelAutoEnable  TruthValue,
            cd11IfPhyDsssCurrentChannel     INTEGER 
                   }

cd11IfPhyDsssMaxCompatibleRate OBJECT-TYPE
        SYNTAX     Integer32 (2..127)
        UNITS      "500 Kb per second"
        MAX-ACCESS read-write
        STATUS     current
        DESCRIPTION 
                "This object specifies the of maximum data 
                rate at which the station may transmit data.  
                The octet contains a value representing a rate.   
                The rate should be within the range from '2' to
                '127', corresponding to data rates in increments 
                of 500 kb/s from 1 Mb/s to 63.5 Mb/s.  It should 
                be one of the rates in the IEEE802dot11-MIB
                dot11OperationalRateSet.  The default value is 
                '127'."
        REFERENCE  
                "IEEE Std 802.11-Jan 14 1999, Wireless LAN Medium 
                Access Control and Physical Layer Specifications,
                LAN MAN Standards Committee of the IEEE Computer 
                Society, IEEE802dot11-MIB." 
        ::= { cd11IfPhyDsssEntry 1 }

cd11IfPhyDsssChannelAutoEnable OBJECT-TYPE
        SYNTAX     TruthValue
        MAX-ACCESS read-write
        STATUS     current
        DESCRIPTION 
                "If the value is 'true' and the radio is function
                as an access point device (i.e., cd11IfStationRole 
                is 'roleRoot', the radio will scan for other BSS 
                activity on all channels available in the current
                cd11IfCurrentCarrierSet before establishing its 
                own BSS.  After the scan, this station will 
                establish its own BSS on the channel with the 
                least probability of radio signal congestion.   
                If the value is 'false', this station always
                establishes its BSS on IEEE802dot11-MIB
                dot11CurrentChannel.  The default value is 'true'."
        REFERENCE  
                "IEEE Std 802.11-Jan 14 1999, Wireless LAN Medium 
                Access Control and Physical Layer Specifications,
                LAN MAN Standards Committee of the IEEE Computer 
                Society, IEEE802dot11-MIB." 
        ::= { cd11IfPhyDsssEntry 2 }

cd11IfPhyDsssCurrentChannel OBJECT-TYPE
        SYNTAX     INTEGER (1..14 | 
                            34|36|38|40|42|44|46|48|52|56|60|64 | 
                            149|153|157|161)
        MAX-ACCESS read-only
        STATUS     current
        DESCRIPTION
                "The current operating frequency channel of 
                the DSSS PHY, as selected either by selective 
                scanning or via IEEE802dot11-MIB dot11CurrentChannel.  
                Valid channel numbers are defined in the
                IEEE 802.11 Standard. 

                For North America, 802.11b channels allowed are 1 to 
                11 and 802.11a channels allowed are 36,40,44,48,52,56,
                60, and 64."
        REFERENCE  
                "IEEE Std 802.11-Jan 14 1999, Wireless LAN Medium 
                Access Control and Physical Layer Specifications,
                LAN MAN Standards Committee of the IEEE Computer 
                Society, section 15.4.6.2." 
        ::= { cd11IfPhyDsssEntry 3 }


cd11IfSuppDataRatesPrivacyTable OBJECT-TYPE
        SYNTAX     SEQUENCE OF Cd11IfSuppDataRatesPrivacyEntry
        MAX-ACCESS not-accessible
        STATUS     current
        DESCRIPTION
                "This table defines the transmit and receive bit
                rate of the radio on each IEEE 802.11 interface
                and the WEP encryption support at those rates.  
                This table has an expansion dependent relationship 
                on the ifTable.  For each entry in this table, 
                there exists at least an entry in the ifTable of
                ifType ieee80211(71).  Entries in this table 
                cannot be created or deleted by the network 
                management system.  All entries are created or 
                deleted by the agent."
        ::= { cd11IfPhyConfig 11 }

cd11IfSuppDataRatesPrivacyEntry OBJECT-TYPE
        SYNTAX     Cd11IfSuppDataRatesPrivacyEntry
        MAX-ACCESS not-accessible
        STATUS     current
        DESCRIPTION
                "Each entry specifies the encryption support for 
                a particular data rate on a radio interface."
        INDEX      { 
                ifIndex, 
                cd11IfSuppDataRatesPrivacyIndex 
                   }
        ::= { cd11IfSuppDataRatesPrivacyTable 1 }

Cd11IfSuppDataRatesPrivacyEntry ::= 
        SEQUENCE   {
            cd11IfSuppDataRatesPrivacyIndex  Integer32,
            cd11IfSuppDataRatesPrivacyValue  Integer32,
            cd11IfSuppDataRatesPrivacyEnabl  TruthValue 
                   }

cd11IfSuppDataRatesPrivacyIndex OBJECT-TYPE
        SYNTAX     Integer32 (1..8)
        MAX-ACCESS not-accessible 
        STATUS     current
        DESCRIPTION
                "This object identifies a data rate supported 
                on a radio.  Each radio can support up to 8
                different rates."
        ::= { cd11IfSuppDataRatesPrivacyEntry 1 }

cd11IfSuppDataRatesPrivacyValue OBJECT-TYPE
        SYNTAX     Integer32 (2..127)
        UNITS      "500 Kb per second"
        MAX-ACCESS read-only
        STATUS     current
        DESCRIPTION
                "This object defines the receiving or transmission
                bit rates supported by the PLCP and PMD, represented
                by a count from 0x02-0x7f, corresponding to 
                data rates in increments of 500Kb/s from 1 Mb/s to 
                63.5 Mb/s."
        ::= { cd11IfSuppDataRatesPrivacyEntry 2 }

cd11IfSuppDataRatesPrivacyEnabl OBJECT-TYPE
        SYNTAX     TruthValue
        MAX-ACCESS read-only
        STATUS     current
        DESCRIPTION
                "This object indicates whether WEP encryption is 
                supported by the radio for both transmit and receive 
                operations at the corresponding bit rate specified 
                by the cd11IfSuppDataRatesPrivacyValue."
        ::= { cd11IfSuppDataRatesPrivacyEntry 3 }


cd11IfChanSelectTable OBJECT-TYPE
        SYNTAX     SEQUENCE OF Cd11IfChanSelectEntry
        MAX-ACCESS not-accessible
        STATUS     current
        DESCRIPTION
                "This table specifies for each 802.11 channel, 
                whether the scanning process controlled by the 
                cd11IfPhyDsssChannelAutoEnable can select a 
                particular channel for use.  This table has an 
                expansion dependent relationship on the ifTable.  
                For each entry in this table, there exists at least
                an entry in the ifTable of ifType ieee80211(71).
                Entries in this table cannot be created or deleted
                by the network management system.  All entries are
                created or deleted by the agent."
        REFERENCE  
                "IEEE Std 802.11-Jan 14 1999, Wireless LAN Medium 
                Access Control and Physical Layer Specifications,
                LAN MAN Standards Committee of the IEEE Computer 
                Society, section 15.4.6.2." 
        ::= { cd11IfPhyConfig 12 }

cd11IfChanSelectEntry OBJECT-TYPE
        SYNTAX     Cd11IfChanSelectEntry
        MAX-ACCESS not-accessible
        STATUS     current
        DESCRIPTION
                "Each entry specifies if a particular radio channel
                is enabled on a radio interface."
        INDEX      { 
                ifIndex, 
                cd11IfChanSelectChannel 
                   }
        ::= { cd11IfChanSelectTable 1 }

Cd11IfChanSelectEntry ::= 
        SEQUENCE   {
            cd11IfChanSelectChannel  INTEGER,
            cd11IfChanSelectEnable   TruthValue 
                   }

cd11IfChanSelectChannel OBJECT-TYPE
        SYNTAX     INTEGER (1..14 | 
                            34|36|38|40|42|44|46|48|52|56|60|64 | 
                            149|153|157|161)
        MAX-ACCESS not-accessible 
        STATUS     current
        DESCRIPTION
                "This object specifies an IEEE 802.11 channel 
                number which is a candidate for low-occupancy 
                scanning."
        REFERENCE  
                "IEEE Std 802.11-Jan 14 1999, Wireless LAN Medium 
                Access Control and Physical Layer Specifications,
                LAN MAN Standards Committee of the IEEE Computer 
                Society, section 15.4.6.2." 
        ::= { cd11IfChanSelectEntry 1 }

cd11IfChanSelectEnable OBJECT-TYPE
        SYNTAX     TruthValue
        MAX-ACCESS read-write
        STATUS     current
        DESCRIPTION
                "If the value is 'true', cd11IfChanSelectChannel 
                is available for the system to use as its 
                cd11IfPhyDsssCurrentChannel after scanning for 
                channel occupancy.  If the value is 'false', 
                cd11IfChanSelectChannel is not available.  The 
                default value is 'true'."
        ::= { cd11IfChanSelectEntry 2 }


cd11IfClientTxPowerTable OBJECT-TYPE
        SYNTAX     SEQUENCE OF Cd11IfClientTxPowerEntry
        MAX-ACCESS not-accessible
        STATUS     current
        DESCRIPTION 
                "This table shows the recommended client 
                transmit power level for the radio and selects 
                one of the levels as the desired transmit power
                level to be used by the client of the radio.  By 
                adjusting the transmit power, the radio can limit
                the interference caused by adjacent clients using 
                the same or adjacent channels." 
        ::= { cd11IfPhyConfig 13 }

cd11IfClientTxPowerEntry OBJECT-TYPE
        SYNTAX     Cd11IfClientTxPowerEntry
        MAX-ACCESS not-accessible
        STATUS     current
        DESCRIPTION
                "Each entry specifies the number of available
                transmit power levels, the values of all the 
                levels, and the selected level for a radio 
                interface."
        INDEX      { ifIndex }
        ::= { cd11IfClientTxPowerTable 1 }

Cd11IfClientTxPowerEntry ::=
        SEQUENCE   {      
            cd11IfClientNumberTxPowerLevels  Integer32,
            cd11IfClientTxPowerLevel1        Integer32,
            cd11IfClientTxPowerLevel2        Integer32,
            cd11IfClientTxPowerLevel3        Integer32,
            cd11IfClientTxPowerLevel4        Integer32,
            cd11IfClientTxPowerLevel5        Integer32,
            cd11IfClientTxPowerLevel6        Integer32,
            cd11IfClientTxPowerLevel7        Integer32,
            cd11IfClientTxPowerLevel8        Integer32,
            cd11IfClientCurrentTxPowerLevel  Integer32 
                   }

cd11IfClientNumberTxPowerLevels OBJECT-TYPE
        SYNTAX     Integer32 (1..8)
        MAX-ACCESS read-only
        STATUS     current
        DESCRIPTION
                "The number of power levels available for the
                clients.  This attribute can have a value of 
                1 to 8."
        ::= { cd11IfClientTxPowerEntry 1 }

cd11IfClientTxPowerLevel1 OBJECT-TYPE
        SYNTAX     Integer32 (-10000..10000)
        MAX-ACCESS read-only
        STATUS     current
        DESCRIPTION
                "The client transmit output power for LEVEL1 
                in mW or dBm."
        ::= { cd11IfClientTxPowerEntry 2 }

cd11IfClientTxPowerLevel2 OBJECT-TYPE
        SYNTAX     Integer32 (-10000..10000)
        MAX-ACCESS read-only
        STATUS     current
        DESCRIPTION
                "The client transmit output power for LEVEL2 
                in mW or dBm."
    ::= { cd11IfClientTxPowerEntry 3 }

cd11IfClientTxPowerLevel3 OBJECT-TYPE
        SYNTAX     Integer32 (-10000..10000)
        MAX-ACCESS read-only
        STATUS     current
        DESCRIPTION
                "The client transmit output power for LEVEL3 
                in mW or dBm."
        ::= { cd11IfClientTxPowerEntry 4 }

cd11IfClientTxPowerLevel4 OBJECT-TYPE
        SYNTAX     Integer32 (-10000..10000)
        MAX-ACCESS read-only
        STATUS     current
        DESCRIPTION
                "The client transmit output power for LEVEL4 
                in mW or dBm."
        ::= { cd11IfClientTxPowerEntry 5 }

cd11IfClientTxPowerLevel5 OBJECT-TYPE
        SYNTAX     Integer32 (-10000..10000)
        MAX-ACCESS read-only
        STATUS     current
        DESCRIPTION
                "The client transmit output power for LEVEL5 
                in mW or dBm."
        ::= { cd11IfClientTxPowerEntry 6 }

cd11IfClientTxPowerLevel6 OBJECT-TYPE
        SYNTAX     Integer32 (-10000..10000)
        MAX-ACCESS read-only
        STATUS     current
        DESCRIPTION
                "The client transmit output power for LEVEL6
                in mW or dBm."
        ::= { cd11IfClientTxPowerEntry 7 }

cd11IfClientTxPowerLevel7 OBJECT-TYPE
        SYNTAX     Integer32 (-10000..10000)
        MAX-ACCESS read-only
        STATUS     current
        DESCRIPTION
                "The client transmit output power for LEVEL7 
                in mW or dBm."
        ::= { cd11IfClientTxPowerEntry 8 }

cd11IfClientTxPowerLevel8 OBJECT-TYPE
        SYNTAX     Integer32 (-10000..10000)
        MAX-ACCESS read-only
        STATUS     current
        DESCRIPTION
                "The client transmit output power for LEVEL8
                in mW or dBm."
        ::= { cd11IfClientTxPowerEntry 9 }

cd11IfClientCurrentTxPowerLevel OBJECT-TYPE
        SYNTAX     Integer32 (1..8)
        MAX-ACCESS read-write
        STATUS     current
        DESCRIPTION
                "The TxPowerLevel N currently selected for client
                to transmit data.  It is up to the clients to honor
                this transmit power setting."
        ::= { cd11IfClientTxPowerEntry 10 }


cd11IfErpOfdmTxPowerTable OBJECT-TYPE
        SYNTAX     SEQUENCE OF Cd11IfErpOfdmTxPowerEntry
        MAX-ACCESS not-accessible
        STATUS     current
        DESCRIPTION 
                "This table shows the available ERP-OFDM 
                transmit power levels for radios implementing 
                IEEE 802.11g Protocol and configures one of the 
                levels as the transmit power level.  

                This table has a sparse dependent relationship 
                on the ifTable.  For each entry in this table, 
                there exists an entry in the ifTable of ifType 
                ieee80211(71) and the corresponding 
                cd11IfPhyMacSpecification is ieee802dot11g(3).

                For all IEEE802.11g radios with an entry in this
                table, the IEEE802dot11-MIB dot11PhyTxPowerTable 
                will be used to configure ERP-CCK transmit power
                levels."
        ::= { cd11IfPhyConfig 14 }

cd11IfErpOfdmTxPowerEntry OBJECT-TYPE
        SYNTAX     Cd11IfErpOfdmTxPowerEntry
        MAX-ACCESS not-accessible
        STATUS     current
        DESCRIPTION
                "Each entry specifies the number of available
                transmit power levels, the values of all the 
                levels, and the configured transmit power level 
                for an IEEE 802.11g radio interface."
        INDEX      { ifIndex }
        ::= { cd11IfErpOfdmTxPowerTable 1 }

Cd11IfErpOfdmTxPowerEntry ::=
        SEQUENCE   {      
            cd11IfErpOfdmNumberTxPowerLevels  Integer32,
            cd11IfErpOfdmTxPowerLevel1        Integer32,
            cd11IfErpOfdmTxPowerLevel2        Integer32,
            cd11IfErpOfdmTxPowerLevel3        Integer32,
            cd11IfErpOfdmTxPowerLevel4        Integer32,
            cd11IfErpOfdmTxPowerLevel5        Integer32,
            cd11IfErpOfdmTxPowerLevel6        Integer32,
            cd11IfErpOfdmTxPowerLevel7        Integer32,
            cd11IfErpOfdmTxPowerLevel8        Integer32,
            cd11IfErpOfdmCurrentTxPowerLevel  Integer32 
                   }

cd11IfErpOfdmNumberTxPowerLevels OBJECT-TYPE
        SYNTAX     Integer32 (1..8)
        MAX-ACCESS read-only
        STATUS     current
        DESCRIPTION
                "The number of power levels available for this
                radio.  This attribute can have a value of 
                1 to 8."
        ::= { cd11IfErpOfdmTxPowerEntry 1 }

cd11IfErpOfdmTxPowerLevel1 OBJECT-TYPE
        SYNTAX     Integer32 (0..10000)
        UNITS      "mW"
        MAX-ACCESS read-only
        STATUS     current
        DESCRIPTION
                "The ERP-OFDM transmit output power for LEVEL1."
        ::= { cd11IfErpOfdmTxPowerEntry 2 }

cd11IfErpOfdmTxPowerLevel2 OBJECT-TYPE
        SYNTAX     Integer32 (0..10000)
        UNITS      "mW"
        MAX-ACCESS read-only
        STATUS     current
        DESCRIPTION
                "The ERP-OFDM transmit output power for LEVEL2."
    ::= { cd11IfErpOfdmTxPowerEntry 3 }

cd11IfErpOfdmTxPowerLevel3 OBJECT-TYPE
        SYNTAX     Integer32 (0..10000)
        UNITS      "mW"
        MAX-ACCESS read-only
        STATUS     current
        DESCRIPTION
                "The ERP-OFDM transmit output power for LEVEL3."
        ::= { cd11IfErpOfdmTxPowerEntry 4 }

cd11IfErpOfdmTxPowerLevel4 OBJECT-TYPE
        SYNTAX     Integer32 (0..10000)
        UNITS      "mW"
        MAX-ACCESS read-only
        STATUS     current
        DESCRIPTION
                "The ERP-OFDM transmit output power for LEVEL4."
        ::= { cd11IfErpOfdmTxPowerEntry 5 }

cd11IfErpOfdmTxPowerLevel5 OBJECT-TYPE
        SYNTAX     Integer32 (0..10000)
        UNITS      "mW"
        MAX-ACCESS read-only
        STATUS     current
        DESCRIPTION
                "The ERP-OFDM transmit output power for LEVEL5."
        ::= { cd11IfErpOfdmTxPowerEntry 6 }

cd11IfErpOfdmTxPowerLevel6 OBJECT-TYPE
        SYNTAX     Integer32 (0..10000)
        UNITS      "mW"
        MAX-ACCESS read-only
        STATUS     current
        DESCRIPTION
                "The ERP-OFDM transmit output power for LEVEL6."
        ::= { cd11IfErpOfdmTxPowerEntry 7 }

cd11IfErpOfdmTxPowerLevel7 OBJECT-TYPE
        SYNTAX     Integer32 (0..10000)
        UNITS      "mW"
        MAX-ACCESS read-only
        STATUS     current
        DESCRIPTION
                "The ERP-OFDM transmit output power for LEVEL7."
        ::= { cd11IfErpOfdmTxPowerEntry 8 }

cd11IfErpOfdmTxPowerLevel8 OBJECT-TYPE
        SYNTAX     Integer32 (0..10000)
        UNITS      "mW"
        MAX-ACCESS read-only
        STATUS     current
        DESCRIPTION
                "The ERP-OFDM transmit output power for LEVEL8."
        ::= { cd11IfErpOfdmTxPowerEntry 9 }

cd11IfErpOfdmCurrentTxPowerLevel OBJECT-TYPE
        SYNTAX     Integer32 (1..8)
        MAX-ACCESS read-write
        STATUS     current
        DESCRIPTION
                "The TxPowerLevel N currently configured
                to transmit data."
        ::= { cd11IfErpOfdmTxPowerEntry 10 }

 
cd11IfFrequencyBandTable OBJECT-TYPE
        SYNTAX     SEQUENCE OF Cd11IfFrequencyBandEntry
        MAX-ACCESS not-accessible
        STATUS     current
        DESCRIPTION 
                "This table identifies the radio frequency 
                (sub)bands supported on the IEEE 802.11 radio
                interfaces while operating per the regulations
                imposed by the cd11IfCurrentCarrierSet. 

                This table has an expansion dependent relationship 
                on the ifTable.  For each entry in this table, 
                there exists at least an entry in the ifTable of 
                ifType ieee80211(71).  This table uses the 
                cd11IfRfFrequencyBand as the expansion index.  

                All entries in this table are created or deleted
                only by the agent."
        REFERENCE  
                "IEEE Std 802.11-Jan 14 1999, Wireless LAN Medium 
                Access Control and Physical Layer Specifications,
                LAN MAN Standards Committee of the IEEE Computer 
                Society, IEEE802dot11-MIB." 
        ::= { cd11IfPhyConfig 15 }

cd11IfFrequencyBandEntry OBJECT-TYPE
        SYNTAX     Cd11IfFrequencyBandEntry
        MAX-ACCESS not-accessible
        STATUS     current
        DESCRIPTION
                "Each entry defines a supported radio frequency 
                band for an IEEE 802.11 radio interface."
        INDEX      { 
                ifIndex, 
                cd11IfRfFrequencyBand
                   }
        ::= { cd11IfFrequencyBandTable 1 }

Cd11IfFrequencyBandEntry ::=
        SEQUENCE   {      
                cd11IfRfFrequencyBand          Unsigned32,
                cd11IfRfFrequencyUnits         INTEGER, 
                cd11IfRfStartChannelNumber     Unsigned32, 
                cd11IfRfEndChannelNumber       Unsigned32, 
                cd11IfRfChannelSpacingNumber   Unsigned32,
                cd11IfRfStartChannelFrequency  Unsigned32, 
                cd11IfRfFrequencySpacing       Unsigned32,
                cd11IfRfFrequencyBandType       
                        CDot11RadioFrequencyBandType,
                cd11IfMaxChannelSwitchTime     Unsigned32
                   }

cd11IfRfFrequencyBand OBJECT-TYPE
        SYNTAX     Unsigned32    
        MAX-ACCESS not-accessible 
        STATUS     current
        DESCRIPTION
                "This object identifies radio frequency bands 
                supported on the radio."  
        ::= { cd11IfFrequencyBandEntry 1 }

cd11IfRfFrequencyUnits OBJECT-TYPE
        SYNTAX     INTEGER {
                        mHz(1)
                           }
        MAX-ACCESS read-only
        STATUS     current
        DESCRIPTION
                "This base frequency units combines with the 
                cd11IfRfStartChannelFrequency to define the 
                actual frequency of the channel and combines
                with the cd11IfRfFrequencySpacing to define the
                minimum frequency spacing between two adjacent
                frequency channels. 

                For example, frequency spacing of 5 MHz is 
                'mHz' in cd11IfRfFrequencyUnits and 5 in 
                cd11IfRfFrequencySpacing." 
        DEFVAL     { mHz }
        ::= { cd11IfFrequencyBandEntry 2 }

cd11IfRfStartChannelNumber OBJECT-TYPE
        SYNTAX     Unsigned32
        MAX-ACCESS read-only
        STATUS     current
        DESCRIPTION
                "Numeric identifier of the first channel supported
                in this radio frequency band.  For example,  
                currently at the 2.4 GHz ISM band, the first channel 
                number is 1, while for the U-NII-1 band in the FCC 
                regulatory domain, the first supported channel is
                number 36 at frequency 5180 MHz."
        ::= { cd11IfFrequencyBandEntry 3 }

cd11IfRfEndChannelNumber OBJECT-TYPE     
        SYNTAX     Unsigned32 
        MAX-ACCESS read-only 
        STATUS     current  
        DESCRIPTION
                "Numeric identifier of the last channel supported
                in this radio frequency band.  For example, in the 
                FCC regulatory domain, the last channel of the 2.4
                GHz ISM band is number 11 and the last channel of
                the U-NII-1 band is number 48 at frequency 5240 MHz."
        ::= { cd11IfFrequencyBandEntry 4 }        

cd11IfRfChannelSpacingNumber OBJECT-TYPE
        SYNTAX     Unsigned32 
        MAX-ACCESS read-only
        STATUS     current
        DESCRIPTION
                "Numeric spacing between the identifiers of two 
                adjacent supported channels in this band.  For 
                example, currently at the 2.4 GHz ISM band, the 
                numeric channel spacing is 1, resulting in a channel
                identifier sequence of 1, 2, 3, etc.  In the
                U-NII-1 band, the numeric channel spacing is 4,
                resulting in a channel identifier sequence
                of 36, 40, 44, etc." 
        ::= { cd11IfFrequencyBandEntry 5 }

cd11IfRfStartChannelFrequency OBJECT-TYPE
        SYNTAX     Unsigned32 (0..10000)
        MAX-ACCESS read-only
        STATUS     current
        DESCRIPTION
                "This is the base channel frequency of the
                cd11IfRfStartChannelNumber channel from which 
                subsequent channels of this frequency band are
                defined.  The actual frequency value is defined 
                and calculated by multiplying this object with the 
                cd11IfRfFrequencyUnits.  The subsequent channels
                in the band are calculated by adding the 
                cd11IfRfChannelSpacingNumber multiplied by the
                cd11IfRfFrequencySpacing to this object value.

                For example, the first channel of U-NII-1 band is 
                channel 36, the cd11IfRfFrequencyUnits is 'mHz',
                the cd11IfRfStartChannelFrequency is '5180', and
                the cd11IfRfChannelSpacingNumber is 4.  If the 
                cd11IfRfFrequencySpacing is 5 MHz, the second 
                supported channel of the U-NII-1 band will be 
                channel 40 at frequency 5200 MHz."
        ::= { cd11IfFrequencyBandEntry 6 }

cd11IfRfFrequencySpacing OBJECT-TYPE
        SYNTAX     Unsigned32 
        MAX-ACCESS read-only
        STATUS     current
        DESCRIPTION
                "This is the frequency separation between two 
                adjacent radio frequency channels.  The actual
                frequency value is calculated by multiplying this
                object with the cd11IfRfFrequencyUnits.  For
                example, for a frequency spacing of 5 MHz, the 
                value of cd11IfRfFrequencyUnits is 'mHz' and
                the value of this object is 5." 
        ::= { cd11IfFrequencyBandEntry 7 }

cd11IfRfFrequencyBandType OBJECT-TYPE
        SYNTAX     CDot11RadioFrequencyBandType
        MAX-ACCESS read-only 
        STATUS     current
        DESCRIPTION
                "This is the enumerated radio frequency band name(s)
                which this (sub)band occupies.  

                If the frequency band defined in a table row is not 
                included in the current CDot11RadioFrequencyBandType
                definition, none of the bits are set for this object."
        ::= { cd11IfFrequencyBandEntry 8 }

cd11IfMaxChannelSwitchTime OBJECT-TYPE
        SYNTAX     Unsigned32
        UNITS      "milliseconds"
        MAX-ACCESS read-only
        STATUS     current
        DESCRIPTION
                "The maximum time required for the radio interface
                 to switch its transceiver from one channel to any
                 other supported channel in any supported band."
        ::= { cd11IfFrequencyBandEntry 9 }


cd11IfNativeTxPowerSupportTable OBJECT-TYPE
        SYNTAX     SEQUENCE OF Cd11IfNativeTxPowerSupportEntry
        MAX-ACCESS not-accessible
        STATUS     current
        DESCRIPTION 
                "This table shows the transmit powers supported for
                all the radio frequency bands on the IEEE 802.11 
                radios.

                This table has an expansion dependent relationship 
                on the ifTable.  For each entry in this table, 
                there exists at least an entry in the ifTable of 
                ifType ieee80211(71).  This table uses the 
                cd11IfRfFrequencyBand of cd11IfFrequencyBandTable,
                cd11IfRadioModulationClass, and 
                cd11IfNativeTxPowerLevel as the expansion indices.

                All entries in this table can only be created or
                deleted by the agent."
        ::= { cd11IfPhyConfig 16 }

cd11IfNativeTxPowerSupportEntry OBJECT-TYPE
        SYNTAX     Cd11IfNativeTxPowerSupportEntry
        MAX-ACCESS not-accessible
        STATUS     current
        DESCRIPTION
                "Each entry specifies a supported transmit power
                level for a frequency band, with a specified 
                modulation technique, on the IEEE 802.11 radio 
                interface."
        INDEX      { 
                ifIndex,
                cd11IfRfFrequencyBand, 
                cd11IfRadioModulationClass,
                cd11IfNativeTxPowerLevel
                   }
        ::= { cd11IfNativeTxPowerSupportTable 1 }

Cd11IfNativeTxPowerSupportEntry ::=
        SEQUENCE   {      
            cd11IfRadioModulationClass  CDot11RadioModulationClass,
            cd11IfNativeTxPowerLevel    Unsigned32,
            cd11IfNativeTxPower         Integer32
                   }

cd11IfRadioModulationClass OBJECT-TYPE
        SYNTAX     CDot11RadioModulationClass
        MAX-ACCESS not-accessible
        STATUS     current
        DESCRIPTION
                "This identifies a radio modulation technique
                used by the 802.11 radio interface."
        ::= { cd11IfNativeTxPowerSupportEntry 1 }


cd11IfNativeTxPowerLevel OBJECT-TYPE
        SYNTAX     Unsigned32 
        MAX-ACCESS not-accessible 
        STATUS     current
        DESCRIPTION
                "This is the unique index for a transmit power of a
                radio frequency band for the radio."
        ::= { cd11IfNativeTxPowerSupportEntry 2 }

cd11IfNativeTxPower OBJECT-TYPE
        SYNTAX     Integer32 
        MAX-ACCESS read-only
        STATUS     current
        DESCRIPTION
                "This is a transmit power available at a radio
                frequency band for the radio, when using the
                modulation technique specified by the
                cd11IfRadioModulationClass.  The value of the
                cd11IfNativeTxPowerUnits defines the units of this
                transmit power.  The value can be negative if the
                units is 'dBm'."
        ::= { cd11IfNativeTxPowerSupportEntry 3 }


cd11IfRfNativePowerTable OBJECT-TYPE
        SYNTAX     SEQUENCE OF Cd11IfRfNativePowerEntry
        MAX-ACCESS not-accessible
        STATUS     current
        DESCRIPTION 
                "This table configures the radio power settings
                for frequency bands supported on the IEEE 802.11 
                radios.  This table serves as an alternative for 
                the IEEE802dot11-MIB dot11PhyTxPowerTable.  This 
                table allows different transmit powers to be used 
                on different radio frequency bands.

                This table has an expansion dependent relationship 
                on the ifTable.  For each entry in this table, 
                there exists at least an entry in the ifTable of 
                ifType ieee80211(71).  This table uses the 
                cd11IfRfFrequencyBand and cd11IfRadioModulationClass
                as the expansion indices.  

                All entries in this table are created or deleted
                only by the agent."
        REFERENCE  
                "IEEE Std 802.11-Jan 14 1999, Wireless LAN Medium 
                Access Control and Physical Layer Specifications,
                LAN MAN Standards Committee of the IEEE Computer 
                Society, IEEE802dot11-MIB." 
        ::= { cd11IfPhyConfig 17 }

cd11IfRfNativePowerEntry OBJECT-TYPE
        SYNTAX     Cd11IfRfNativePowerEntry
        MAX-ACCESS not-accessible
        STATUS     current
        DESCRIPTION
                "Each entry specifies the transmit power
                settings of a particular radio frequency band,
                with a specified modulation technique, for
                an IEEE 802.11 radio interface."
        INDEX      { 
                ifIndex, 
                cd11IfRfFrequencyBand,
                cd11IfRadioModulationClass
                   }
        ::= { cd11IfRfNativePowerTable 1 }

Cd11IfRfNativePowerEntry ::=
        SEQUENCE   {      
            cd11IfNativeNumberPowerLevels  Unsigned32,
            cd11IfNativeCurrentPowerLevel  Unsigned32,
            cd11IfNativePowerUnits         INTEGER
                   }

cd11IfNativeNumberPowerLevels OBJECT-TYPE
        SYNTAX     Unsigned32 
        MAX-ACCESS read-only
        STATUS     current
        DESCRIPTION
                "The number of transmit power levels of a radio
                frequency band for the radio.  The value of this
                object should be the same as the maximum
                cd11IfNativeTxPowerLevel of the same ifIndex,
                cd11IfRadioFrequencyBand, and 
                cd11IfRadioModulationClass.

                If the value of this object is 0, the radio can
                only receive, not transmit, on this frequency 
                band and modulation technique."
        ::= { cd11IfRfNativePowerEntry 1 }

cd11IfNativeCurrentPowerLevel OBJECT-TYPE
        SYNTAX     Unsigned32 
        MAX-ACCESS read-write
        STATUS     current
        DESCRIPTION
                "If cd11IfPhyNativePowerUseStandard is 'false',
                this object configures the current transmit power
                level of a radio frequency band for the radio.
                The value shall be one of the supported 
                cd11IfNativeTxPowerLevel for the radio of the
                the same frequency band and modulation technique. 

                For any radio does not transmit power in the 
                specified radio frequency band and modulation
                technique, the value of this object is 0." 
        ::= { cd11IfRfNativePowerEntry 2 }

cd11IfNativePowerUnits OBJECT-TYPE
        SYNTAX     INTEGER { 
                        mW(1),
                        dBm(2)
                           } 
        MAX-ACCESS read-only
        STATUS     current
        DESCRIPTION
                "The native transmit power units implemented on the
                radio.  It is the units for the cd11IfNativeTxPower.
                For the IEEE802dot11-MIB dot11PhyTxPowerTable, 
                'mW' is the only supported units."
        REFERENCE  
                "IEEE Std 802.11-Jan 14 1999, Wireless LAN Medium 
                Access Control and Physical Layer Specifications,
                LAN MAN Standards Committee of the IEEE Computer 
                Society, IEEE802dot11-MIB." 
        DEFVAL     { mW }
        ::= { cd11IfRfNativePowerEntry 3 }


cd11IfDataRatesSensitivityTable OBJECT-TYPE
        SYNTAX     SEQUENCE OF Cd11IfDataRatesSensitivityEntry
        MAX-ACCESS not-accessible
        STATUS     current
        DESCRIPTION
                "This table specifies the receive sensitivity 
                specifications of IEEE 802.11 radio interfaces.

                This table has an expansion dependent relationship 
                on the ifTable.  For each entry in this table, 
                there exists at least an entry in the ifTable of 
                ifType ieee80211(71).  This table uses the 
                cd11IfRadioModulationClass and IEEE802dot11-MIB
                dot11SupportedDataRatesRxIndex as the expansion
                indices.  

                Entries in this table cannot be created or deleted
                by the network management system.  All entries are
                created or deleted by the agent."
        ::= { cd11IfPhyConfig 18 }

cd11IfDataRatesSensitivityEntry OBJECT-TYPE
        SYNTAX     Cd11IfDataRatesSensitivityEntry
        MAX-ACCESS not-accessible
        STATUS     current
        DESCRIPTION
                "Each entry specifies the receive sensitivity of an
                IEEE 802.11 radio interface, with a specified
                modulation technique, for each supported data
                rate identified by the dot11SupportedDataRatesRxIndex."
        INDEX      { 
                ifIndex, 
                cd11IfRadioModulationClass,
                dot11SupportedDataRatesRxIndex
                   }
        ::= { cd11IfDataRatesSensitivityTable  1 }

Cd11IfDataRatesSensitivityEntry ::= 
        SEQUENCE   {
            cd11IfRatesSensRequiredSnr Integer32,
            cd11IfRatesSensContention  Integer32 
                   }

cd11IfRatesSensRequiredSnr OBJECT-TYPE
        SYNTAX     Integer32
        UNITS      "dB"
        MAX-ACCESS read-only
        STATUS     current
        DESCRIPTION
                "The minimum SNR requirement for each data rate
                supported by a radio interface, when using the
                modulation technique specified by
                cd11IfRadioModulationClass.  This is the required
                carrier to noise difference."
        ::= { cd11IfDataRatesSensitivityEntry 1 }

cd11IfRatesSensContention OBJECT-TYPE
        SYNTAX     Integer32
        UNITS      "dBm"
        MAX-ACCESS read-only
        STATUS     current
        DESCRIPTION
                "The average contention sensitivity level for each
                data rate supported by a radio interface, when using
                the modulation technique specified by
                cd11IfRadioModulationClass.  This is the value where
                50% of the packets are received successfully."
        ::= { cd11IfDataRatesSensitivityEntry 2 }


-- Statistics Objects 

cd11IfMacLayerCountersTable OBJECT-TYPE
        SYNTAX     SEQUENCE OF Cd11IfMacLayerCountersEntry
        MAX-ACCESS not-accessible
        STATUS     current
        DESCRIPTION
                "This table includes MAC layer statistics collected 
                by the IEEE 802.11 radio interface.  This table has 
                a sparse dependent relationship on the ifTable. 
                For each entry in this table, there exists an entry
                in the ifTable of ifType ieee80211(71)."
        ::= { cd11IfMacStatistics 1 }

cd11IfMacLayerCountersEntry OBJECT-TYPE
        SYNTAX     Cd11IfMacLayerCountersEntry
        MAX-ACCESS not-accessible
        STATUS     current
        DESCRIPTION
                "Each entry contains counters of frame transmissions
                for a radio interface."
        INDEX      { ifIndex }
        ::= { cd11IfMacLayerCountersTable 1 }

Cd11IfMacLayerCountersEntry ::=
        SEQUENCE   {
            cd11IfTransDeferEnerDetects  Counter32,
            cd11IfRecFrameMacCrcErrors   Counter32,
            cd11IfSsidMismatches         Counter32 
                   }

cd11IfTransDeferEnerDetects OBJECT-TYPE
        SYNTAX     Counter32
        MAX-ACCESS read-only
        STATUS     current
        DESCRIPTION
                "This counter shall increment when a frame transmission 
                is deferred due to energy detection."
        ::= { cd11IfMacLayerCountersEntry 1 }

cd11IfRecFrameMacCrcErrors OBJECT-TYPE
        SYNTAX     Counter32
        MAX-ACCESS read-only
        STATUS     current
        DESCRIPTION
                "This counter shall increment when a frame received has 
                any MAC CRC error."
        ::= { cd11IfMacLayerCountersEntry 2 }

cd11IfSsidMismatches OBJECT-TYPE
        SYNTAX     Counter32
        MAX-ACCESS read-only
        STATUS     current
        DESCRIPTION
                "This counter shall increment when a beacon or probe 
                response frame received for which the SSIDs in the 
                frame do not match the IEEE802dot11-MIB 
                dot11DesiredSSID object."
        REFERENCE  
                "IEEE Std 802.11-Jan 14 1999, Wireless LAN Medium 
                Access Control and Physical Layer Specifications,
                LAN MAN Standards Committee of the IEEE Computer 
                Society, IEEE802dot11-MIB." 
        ::= { cd11IfMacLayerCountersEntry 3 }


cd11IfRogueApDetectedTable OBJECT-TYPE
        SYNTAX     SEQUENCE OF Cd11IfRogueApDetectedEntry
        MAX-ACCESS not-accessible
        STATUS     current
        DESCRIPTION
                "This table includes rogue AP detected
                information collected by the IEEE 802.11 radio
                interface and 802.11 system management.  This
                table has a sparse dependent relationship on
                the ifTable.  For each entry in this table,
                there exists an entry in the ifTable of ifType
                ieee80211(71)."
        ::= { cd11IfMacStatistics 2 }

cd11IfRogueApDetectedEntry OBJECT-TYPE
        SYNTAX     Cd11IfRogueApDetectedEntry
        MAX-ACCESS not-accessible
        STATUS     current
        DESCRIPTION
                "Each entry contains information of a rogue AP
                detected by a radio interface."
        INDEX      {
                ifIndex,
                cd11IfRogueApMacAddr
                    }
        ::= { cd11IfRogueApDetectedTable 1 }

Cd11IfRogueApDetectedEntry ::=
        SEQUENCE   {
                cd11IfRogueApMacAddr  MacAddress,
                cd11IfRogueApName     SnmpAdminString
                   }

cd11IfRogueApMacAddr OBJECT-TYPE
        SYNTAX     MacAddress
        MAX-ACCESS not-accessible
        STATUS     current
        DESCRIPTION
                "This is the MAC address of a rogue access point
                detected by this radio."
        ::= { cd11IfRogueApDetectedEntry 1 }

cd11IfRogueApName OBJECT-TYPE
        SYNTAX     SnmpAdminString
        MAX-ACCESS read-only
        STATUS     current
        DESCRIPTION
                "This is the name of the rogue access point."
        ::= { cd11IfRogueApDetectedEntry 2 }


-- ********************************************************************
-- *    Notifications  
-- ********************************************************************

cd11IfStationSwitchOverNotif NOTIFICATION-TYPE
        OBJECTS {
                cd11IfLocalRadioMonitorStatus
                }
        STATUS current
        DESCRIPTION
                "This notification will be sent when a radio
                interface changes the cd11IfLocalRadioMonitorStatus
                from 'monitor' to 'active'."
        ::= { ciscoDot11IfMIBNotifications 1 }

cd11IfRogueApDetectedNotif NOTIFICATION-TYPE 
        OBJECTS {
                cd11IfRogueApName    
                }
        STATUS current
        DESCRIPTION
                "This notification will be sent when a radio
                interface detects a new rogue AP and causes 
                a new row to be added to the 
                cd11IfRogueApDetectedTable." 
        ::= { ciscoDot11IfMIBNotifications 2 } 


-- ********************************************************************
-- *    Conformance information  
-- ********************************************************************


ciscoDot11IfMIBConformance
              OBJECT IDENTIFIER ::= { ciscoDot11IfMIB 3 }
ciscoDot11IfMIBCompliances
              OBJECT IDENTIFIER ::= { ciscoDot11IfMIBConformance 1 }
ciscoDot11IfMIBGroups
              OBJECT IDENTIFIER ::= { ciscoDot11IfMIBConformance 2 }


-- *****************************************************************
--   Compliance statements
-- *****************************************************************

ciscoDot11IfCompliance MODULE-COMPLIANCE
        STATUS     deprecated 
        DESCRIPTION
                "The compliance statement for the cd11IfManagement, 
                cd11IfPhyConfig, cd11IfMacStatisticsGroup, and
                cd11IfDomainCapabilityGroup groups."
        MODULE  
                MANDATORY-GROUPS {
                        cd11IfManagementGroup,
                        cd11IfPhyConfigGroup,
                        cd11IfMacStatisticsGroup,
                        cd11IfDomainCapabilityGroup
                                 }

                OBJECT  cd11IfVlanEncryptKeyStatus 
                DESCRIPTION
                        "Creation of rows must be done via 
                        'createAndGo' for all keys.  When the 
                        agent successfully creates the encryption
                        key, this object is set to 'active' by the
                        agent."

                GROUP   cd11IfVlanEncryptKeyConfigGroup 
                DESCRIPTION
                        "This group is required only if different
                        WEP keys are configured for the same VLAN
                        on different IEEE 802.11 radio interfaces.
                        The CISCO-WLAN-VLAN-MIB cwvlWlanNUcastKeyTable
                        should be used otherwise."
        ::= { ciscoDot11IfMIBCompliances 1 }

ciscoDot11IfComplianceRev1 MODULE-COMPLIANCE
        STATUS     deprecated 
        DESCRIPTION
                "The compliance statement of the ciscoDot11IfMIB
                module."
        MODULE
                MANDATORY-GROUPS {
                        cd11IfRadioManageGroup, 
                        cd11IfAssociationManageGroup,
                        cd11IfPhyConfigGroupRev1,
                        cd11IfMacStatisticsGroup
                                 }

                GROUP   cd11IfSsidAssociationGroup 
                DESCRIPTION
                        "This group is required only if the platform
                        implementing this MIB does not support
                        CISCO-DOT11-SSID-SECURITY-MIB."

                GROUP   cd11IfVlanManageGroup 
                DESCRIPTION
                        "This group is required only if different
                        WEP keys are configured for the same VLAN
                        on different IEEE 802.11 radio interfaces
                        or if the CISCO-WLAN-VLAN-MIB is not 
                        supported on the platform implementing
                        this MIB."

                GROUP   cd11IfRemoteMonitoringGroup 
                DESCRIPTION
                        "This group is required only if the platform
                        implementing this MIB does not support
                        CISCO-L2-DEV-MONITORING-MIB."

                GROUP   cd11IfPhyErpConfigGroup
                DESCRIPTION
                        "This group is required only if the platform
                        implementing IEEE 802.11g Protocol."

                OBJECT  cd11IfVlanEncryptKeyStatus
                DESCRIPTION
                        "Creation of rows must be done via
                        'createAndGo' for all keys.  When the
                        agent successfully creates the encryption
                        key, this object is set to 'active' by the
                        agent."

                OBJECT  cd11IfPhyFhssMaxCompatibleRate 
                DESCRIPTION
                        "This object is only mandatory for devices
                        supporting Frequency-Hopping Spread Spectrum."
        ::= { ciscoDot11IfMIBCompliances 2 }

ciscoDot11IfComplianceRev2 MODULE-COMPLIANCE
        STATUS     deprecated 
        DESCRIPTION
                "The compliance statement of the ciscoDot11IfMIB
                module."
        MODULE
                MANDATORY-GROUPS {
                        cd11IfStationManageGroup, 
                        cd11IfAssociationManageGroup,
                        cd11IfPhyConfigGroupRev1,
                        cd11IfMacStatisticsGroup,
                        cd11IfNativeRadioManageGroup, 
                        cd11IfDataRatesSensitivityGroup
                                 }

                GROUP   cd11IfSsidAssociationGroup 
                DESCRIPTION
                        "This group is required only if the platform
                        implementing this MIB does not support
                        CISCO-DOT11-SSID-SECURITY-MIB."

                GROUP   cd11IfVlanManageGroup 
                DESCRIPTION
                        "This group is required only if different
                        encryption cipher types are configured for
                        the same VLAN on different IEEE 802.11 radio 
                        interfaces or if the CISCO-WLAN-VLAN-MIB is
                        not supported on the platform implementing
                        this MIB."

                GROUP   cd11IfVlanWepManageGroup 
                DESCRIPTION
                        "This group is required only if different
                        WEP keys are configured for the same VLAN
                        on different IEEE 802.11 radio interfaces
                        or if the CISCO-WLAN-VLAN-MIB is not
                        supported on the platform implementing
                        this MIB."

                GROUP   cd11IfRemoteMonitoringGroup 
                DESCRIPTION
                        "This group is required only if the platform
                        implementing this MIB does not support
                        CISCO-L2-DEV-MONITORING-MIB."

                GROUP   cd11IfPhyErpConfigGroup
                DESCRIPTION
                        "This group is required only if the platform
                        implementing IEEE 802.11g Protocol."

                GROUP   cd11IfRogueApDetectedGroup 
                DESCRIPTION
                        "This group is required only if the platform
                        implementing this MIB does not support
                        ciscoDdpIappRogueApInfoGroup objects in
                        CISCO-DDP-IAPP-MIB."

                GROUP   cd11IfMonitorNotificationGroup
                DESCRIPTION
                        "This group is required only if the platform
                        implementing this MIB does not support
                        CISCO-DDP-IAPP-MIB ciscoDdpIappNotificationGroup
                        and CISCO-L2-DEV-MONITORING-MIB 
                        ciscoL2DevMonNotificationGroup." 

                OBJECT  cd11IfVlanEncryptKeyStatus
                DESCRIPTION
                        "Creation of rows must be done via
                        'createAndGo' for all keys.  When the
                        agent successfully creates the encryption
                        key, this object is set to 'active' by the
                        agent."

                OBJECT  cd11IfPhyFhssMaxCompatibleRate 
                DESCRIPTION
                        "This object is only mandatory for devices
                        supporting Frequency-Hopping Spread Spectrum."
        ::= { ciscoDot11IfMIBCompliances 3 }

ciscoDot11IfComplianceRev3 MODULE-COMPLIANCE
        STATUS     deprecated 
        DESCRIPTION
                "The compliance statement of the ciscoDot11IfMIB
                module."
        MODULE
                MANDATORY-GROUPS {
                        cd11IfStationManageGroup,
                        cd11IfAssociationManageGroup,
                        cd11IfPhyConfigGroupRev1,
                        cd11IfMacStatisticsGroup,
                        cd11IfNativeRadioManageGroup,
                        cd11IfDataRatesSensitivityGroup,
                        cd11Ifdot11UpgradeStatusGroup
                                 }

                GROUP   cd11IfSsidAssociationGroup
                DESCRIPTION
                        "This group is required only if the platform
                        implementing this MIB does not support
                        CISCO-DOT11-SSID-SECURITY-MIB."

                GROUP   cd11IfVlanManageGroup
                DESCRIPTION
                        "This group is required only if different
                        encryption cipher types are configured for
                        the same VLAN on different IEEE 802.11 radio
                        interfaces or if the CISCO-WLAN-VLAN-MIB is
                        not supported on the platform implementing
                        this MIB."

                GROUP   cd11IfVlanWepManageGroup
                DESCRIPTION
                        "This group is required only if different
                        WEP keys are configured for the same VLAN
                        on different IEEE 802.11 radio interfaces
                        or if the CISCO-WLAN-VLAN-MIB is not
                        supported on the platform implementing
                        this MIB."

                GROUP   cd11IfRemoteMonitoringGroup
                DESCRIPTION
                        "This group is required only if the platform
                        implementing this MIB does not support
                        CISCO-L2-DEV-MONITORING-MIB."

                GROUP   cd11IfPhyErpConfigGroup
                DESCRIPTION
                        "This group is required only if the platform
                        implementing IEEE 802.11g Protocol."

                GROUP   cd11IfRogueApDetectedGroup
                DESCRIPTION
                        "This group is required only if the platform
                        implementing this MIB does not support
                        ciscoDdpIappRogueApInfoGroup objects in
                        CISCO-DDP-IAPP-MIB."

                GROUP   cd11IfMonitorNotificationGroup
                DESCRIPTION
                        "This group is required only if the platform
                        implementing this MIB does not support
                        CISCO-DDP-IAPP-MIB ciscoDdpIappNotificationGroup
                        and CISCO-L2-DEV-MONITORING-MIB
                        ciscoL2DevMonNotificationGroup."

                OBJECT  cd11IfVlanEncryptKeyStatus
                DESCRIPTION
                        "Creation of rows must be done via
                        'createAndGo' for all keys.  When the
                        agent successfully creates the encryption
                        key, this object is set to 'active' by the
                        agent."

                OBJECT  cd11IfPhyFhssMaxCompatibleRate
                DESCRIPTION
                        "This object is only mandatory for devices
                        supporting Frequency-Hopping Spread Spectrum."
        ::= { ciscoDot11IfMIBCompliances 4 }

ciscoDot11IfComplianceRev4 MODULE-COMPLIANCE
        STATUS     current 
        DESCRIPTION
                "The compliance statement of the ciscoDot11IfMIB
                module."
        MODULE
                MANDATORY-GROUPS {
                        cd11IfStationManageGroup,
                        cd11IfAssociationManageGroup,
                        cd11IfPhyConfigGroupRev1,
                        cd11IfMacStatisticsGroup,
                        cd11IfNativeRadioManageGroup,
                        cd11IfDataRatesSensitivityGroup,
                        cd11Ifdot11UpgradeStatusGroup,
                        cd11Ifdot11MobileStationScanGroup
                                 }

                GROUP   cd11IfSsidAssociationGroup
                DESCRIPTION
                        "This group is required only if the platform
                        implementing this MIB does not support
                        CISCO-DOT11-SSID-SECURITY-MIB."

                GROUP   cd11IfVlanManageGroup
                DESCRIPTION
                        "This group is required only if different
                        encryption cipher types are configured for
                        the same VLAN on different IEEE 802.11 radio
                        interfaces or if the CISCO-WLAN-VLAN-MIB is
                        not supported on the platform implementing
                        this MIB."

                GROUP   cd11IfVlanWepManageGroup
                DESCRIPTION
                        "This group is required only if different
                        WEP keys are configured for the same VLAN
                        on different IEEE 802.11 radio interfaces
                        or if the CISCO-WLAN-VLAN-MIB is not
                        supported on the platform implementing
                        this MIB."

                GROUP   cd11IfRemoteMonitoringGroup
                DESCRIPTION
                        "This group is required only if the platform
                        implementing this MIB does not support
                        CISCO-L2-DEV-MONITORING-MIB."

                GROUP   cd11IfPhyErpConfigGroup
                DESCRIPTION
                        "This group is required only if the platform
                        implementing IEEE 802.11g Protocol."

                GROUP   cd11IfRogueApDetectedGroup
                DESCRIPTION
                        "This group is required only if the platform
                        implementing this MIB does not support
                        ciscoDdpIappRogueApInfoGroup objects in
                        CISCO-DDP-IAPP-MIB."

                GROUP   cd11IfMonitorNotificationGroup
                DESCRIPTION
                        "This group is required only if the platform
                        implementing this MIB does not support
                        CISCO-DDP-IAPP-MIB ciscoDdpIappNotificationGroup
                        and CISCO-L2-DEV-MONITORING-MIB
                        ciscoL2DevMonNotificationGroup."

                OBJECT  cd11IfVlanEncryptKeyStatus
                DESCRIPTION
                        "Creation of rows must be done via
                        'createAndGo' for all keys.  When the
                        agent successfully creates the encryption
                        key, this object is set to 'active' by the
                        agent."

                OBJECT  cd11IfPhyFhssMaxCompatibleRate
                DESCRIPTION
                        "This object is only mandatory for devices
                        supporting Frequency-Hopping Spread Spectrum."
        ::= { ciscoDot11IfMIBCompliances 5 }

-- *****************************************************************
--   Units of conformance
-- *****************************************************************

cd11IfManagementGroup OBJECT-GROUP
        OBJECTS { 
                cd11IfStationRole,
                cd11IfCiscoExtensionsEnable,
                cd11IfAllowBroadcastSsidAssoc,
                cd11IfPrivacyOptionMaxRate,
                cd11IfEthernetEncapsulDefault,
                cd11IfBridgeSpacing,
                cd11IfDesiredSsidMaxAssocSta,
                cd11IfAuxiliarySsidLength,
                cd11IfVoipExtensionsEnable,
                cd11IfDesiredSsidMicAlgorithm,
                cd11IfDesiredSsidWepPermuteAlg,
                cd11IfAuthAlgRequireEap,
                cd11IfAuthAlgRequireMacAddr,
                cd11IfAuthAlgDefaultVlan,
                cd11IfWepDefaultKeyLen,
                cd11IfWepDefaultKeyValue,
                cd11IfDesiredBssAddr,
                cd11IfAuxSsid,
                cd11IfAuxSsidBroadcastSsid,
                cd11IfAuxSsidMaxAssocSta,
                cd11IfAuxSsidMicAlgorithm,
                cd11IfAuxSsidWepPermuteAlg,
                cd11IfAuxSsidAuthAlgEnable,
                cd11IfAuxSsidAuthAlgRequireEap,
                cd11IfAuxSsidAuthAlgRequireMac,
                cd11IfAuxSsidAuthAlgDefaultVlan,
                cd11IfAssignedSta
                }
        STATUS     deprecated
        DESCRIPTION
                "Information to support management of
                IEEE 802.11 protocol interfaces."
        ::= { ciscoDot11IfMIBGroups 1 }


cd11IfPhyConfigGroup OBJECT-GROUP
        OBJECTS { 
                cd11IfCurrentCarrierSet,
                cd11IfModulationType,
                cd11IfPreambleType,
                cd11IfPhyFhssMaxCompatibleRate,
                cd11IfPhyDsssMaxCompatibleRate,
                cd11IfPhyDsssChannelAutoEnable,
                cd11IfPhyDsssCurrentChannel,
                cd11IfSuppDataRatesPrivacyValue,
                cd11IfSuppDataRatesPrivacyEnabl,
                cd11IfChanSelectEnable 
                }
        STATUS     deprecated
        DESCRIPTION
                "Information to support configuration of
                IEEE 802.11 protocol Physical layer."
        ::= { ciscoDot11IfMIBGroups 2 }


cd11IfMacStatisticsGroup OBJECT-GROUP
        OBJECTS { 
                cd11IfTransDeferEnerDetects,
                cd11IfRecFrameMacCrcErrors,
                cd11IfSsidMismatches 
                }
        STATUS     current
        DESCRIPTION
                "Statistics information on IEEE 802.11 
                 radio interface MAC layer."
        ::= { ciscoDot11IfMIBGroups 3 }


cd11IfVlanEncryptKeyConfigGroup OBJECT-GROUP
        OBJECTS {
                cd11IfVlanEncryptKeyLen, 
                cd11IfVlanEncryptKeyValue,
                cd11IfVlanEncryptKeyStatus
                }
        STATUS     deprecated
        DESCRIPTION
                "WEP key configuration for specific VLANs
                on IEEE 802.11 radio interface."
        ::= { ciscoDot11IfMIBGroups 4 }


cd11IfDomainCapabilityGroup OBJECT-GROUP
        OBJECTS {       
                cd11IfDomainCapabilitySet
                }
        STATUS     deprecated
        DESCRIPTION
                "This object class provides the objects necessary
                to manage the channels and transmit power usable by 
                a radio within its regulatory domain."
        ::= { ciscoDot11IfMIBGroups 5 }


cd11IfPhyMacCapabilityGroup OBJECT-GROUP
        OBJECTS {
                cd11IfPhyBasicRateSet,
                cd11IfPhyMacSpecification
                }
        STATUS     deprecated
        DESCRIPTION
                "This object class provides the objects necessary
                to manage the Basic Rate capability applied to the 
                defined operational data rate and and IEEE 802.11
                Standard applied to the radio." 
        ::= { ciscoDot11IfMIBGroups 6 }

cd11IfAuthAlgMethodListGroup OBJECT-GROUP
        OBJECTS {
                cd11IfAuthAlgEapMethod,  
                cd11IfAuthAlgMacAddrMethod,      
                cd11IfAuxSsidAuthAlgEapMethod,        
                cd11IfAuxSsidAuthAlgMacMethod
                }
        STATUS     deprecated
        DESCRIPTION
                "This object class provides the objects necessary
                to specify the authentication method applied to 
                MAC address or EAP authentications."
        ::= { ciscoDot11IfMIBGroups 7 }


cd11IfRadioManageGroup OBJECT-GROUP
        OBJECTS { 
                cd11IfStationRole,
                cd11IfCiscoExtensionsEnable,
                cd11IfPrivacyOptionMaxRate,
                cd11IfEthernetEncapsulDefault,
                cd11IfBridgeSpacing,
                cd11IfVoipExtensionsEnable,
                cd11IfAuxiliarySsidLength,
                cd11IfAllowBroadcastSsidAssoc,
                cd11IfDesiredBssAddr,
                cd11IfAssignedSta,
                cd11IfWorldMode,
                cd11IfWorldModeCountry,
                cd11IfMobileStationScanParent 
                }
        STATUS     deprecated
        DESCRIPTION
                "Information to manage IEEE 802.11 protocol 
                radio interface settings."
        ::= { ciscoDot11IfMIBGroups 8 }


cd11IfAssociationManageGroup OBJECT-GROUP
        OBJECTS { 
                cd11IfDesiredSsidMaxAssocSta,
                cd11IfDesiredSsidMicAlgorithm,
                cd11IfDesiredSsidWepPermuteAlg,
                cd11IfAuthAlgRequireEap,
                cd11IfAuthAlgRequireMacAddr,
                cd11IfAuthAlgDefaultVlan,
                cd11IfAuthAlgEapMethod,  
                cd11IfAuthAlgMacAddrMethod,      
                cd11IfWepDefaultKeyLen,
                cd11IfWepDefaultKeyValue
                }
        STATUS     current
        DESCRIPTION
                "Information to manage IEEE 802.11 protocol 
                interface desired SSID association and 
                default encryption key settings."
        ::= { ciscoDot11IfMIBGroups 9 }

cd11IfSsidAssociationGroup OBJECT-GROUP
        OBJECTS { 
                cd11IfAuxSsid,
                cd11IfAuxSsidBroadcastSsid,
                cd11IfAuxSsidMaxAssocSta,
                cd11IfAuxSsidMicAlgorithm,
                cd11IfAuxSsidWepPermuteAlg,
                cd11IfAuxSsidAuthAlgEnable,
                cd11IfAuxSsidAuthAlgRequireEap,
                cd11IfAuxSsidAuthAlgRequireMac,
                cd11IfAuxSsidAuthAlgDefaultVlan,
                cd11IfAuxSsidAuthAlgEapMethod,        
                cd11IfAuxSsidAuthAlgMacMethod
                }
        STATUS     current
        DESCRIPTION
                "Information to manage IEEE 802.11 protocol 
                interface SSID association and authentication 
                settings."
        ::= { ciscoDot11IfMIBGroups 10 }


cd11IfVlanManageGroup OBJECT-GROUP
        OBJECTS { 
                cd11IfVlanEncryptKeyLen, 
                cd11IfVlanEncryptKeyValue,
                cd11IfVlanEncryptKeyStatus,
                cd11IfVlanEncryptKeyTransmit,
                cd11IfVlanSecurityVlanEnabled,
                cd11IfVlanBcastKeyChangeInterval,
                cd11IfVlanBcastKeyCapabilChange, 
                cd11IfVlanBcastKeyClientLeave, 
                cd11IfVlanSecurityCiphers,  
                cd11IfVlanSecurityRowStatus  
                }
        STATUS     current
        DESCRIPTION
                "Information to manage IEEE 802.11 protocol
                interface VLAN and encryption settings."
        ::= { ciscoDot11IfMIBGroups 11 }


cd11IfRemoteMonitoringGroup OBJECT-GROUP
        OBJECTS {
                cd11IfRadioMonitorPollingFreq, 
                cd11IfRadioMonitorPollingTimeOut, 
                cd11IfLocalRadioMonitorStatus, 
                cd11IfRadioMonitorRowStatus
                }
        STATUS     current
        DESCRIPTION
                "Information to manage IEEE 802.11 protocol 
                interface remote radio monitoring settings."
        ::= { ciscoDot11IfMIBGroups 12 }


cd11IfPhyConfigGroupRev1 OBJECT-GROUP
        OBJECTS { 
                cd11IfCurrentCarrierSet,
                cd11IfModulationType,
                cd11IfPreambleType,
                cd11IfDomainCapabilitySet,
                cd11IfPhyBasicRateSet,
                cd11IfPhyMacSpecification,
                cd11IfPhyConcatenation,
                cd11IfPhyDsssMaxCompatibleRate,
                cd11IfPhyDsssChannelAutoEnable,
                cd11IfPhyDsssCurrentChannel,
                cd11IfPhyFhssMaxCompatibleRate, 
                cd11IfSuppDataRatesPrivacyValue,
                cd11IfSuppDataRatesPrivacyEnabl,
                cd11IfChanSelectEnable,
                cd11IfClientNumberTxPowerLevels,
                cd11IfClientTxPowerLevel1,
                cd11IfClientTxPowerLevel2,
                cd11IfClientTxPowerLevel3,
                cd11IfClientTxPowerLevel4,
                cd11IfClientTxPowerLevel5,
                cd11IfClientTxPowerLevel6,
                cd11IfClientTxPowerLevel7,
                cd11IfClientTxPowerLevel8,
                cd11IfClientCurrentTxPowerLevel
                }
        STATUS     current
        DESCRIPTION
                "Information to configure IEEE 802.11 protocol
                Physical layer settings."
        ::= { ciscoDot11IfMIBGroups 13 }

cd11IfPhyErpConfigGroup OBJECT-GROUP
        OBJECTS { 
                cd11IfErpOfdmNumberTxPowerLevels,
                cd11IfErpOfdmTxPowerLevel1,
                cd11IfErpOfdmTxPowerLevel2,
                cd11IfErpOfdmTxPowerLevel3,
                cd11IfErpOfdmTxPowerLevel4,
                cd11IfErpOfdmTxPowerLevel5,
                cd11IfErpOfdmTxPowerLevel6,
                cd11IfErpOfdmTxPowerLevel7,
                cd11IfErpOfdmTxPowerLevel8,
                cd11IfErpOfdmCurrentTxPowerLevel
                }
        STATUS     current
        DESCRIPTION
                "Information to configure IEEE 802.11g protocol
                Physical layer settings."
        ::= { ciscoDot11IfMIBGroups 14 }

cd11IfVlanWepManageGroup OBJECT-GROUP
        OBJECTS {
                cd11IfVlanEncryptionMode,
                cd11IfVlanWepEncryptOptions,
                cd11IfVlanWepEncryptMic,
                cd11IfVlanWepEncryptKeyHashing
                }
        STATUS     current
        DESCRIPTION
                "Information to manage IEEE 802.11 protocol
                interface VLAN WEP encryption settings."
        ::= { ciscoDot11IfMIBGroups 15 }

cd11IfRogueApDetectedGroup OBJECT-GROUP
        OBJECTS {
                cd11IfRogueApName
                }
        STATUS     current
        DESCRIPTION
                "Rogue AP detection information."
        ::= { ciscoDot11IfMIBGroups 16 }


cd11IfStationManageGroup OBJECT-GROUP
        OBJECTS {
                cd11IfStationRole,
                cd11IfCiscoExtensionsEnable,
                cd11IfPrivacyOptionMaxRate,
                cd11IfEthernetEncapsulDefault,
                cd11IfBridgeSpacing,
                cd11IfVoipExtensionsEnable,
                cd11IfAuxiliarySsidLength,
                cd11IfAllowBroadcastSsidAssoc,
                cd11IfDesiredBssAddr,
                cd11IfAssignedSta,
                cd11IfWorldMode,
                cd11IfWorldModeCountry,
                cd11IfMobileStationScanParent,
                cd11IfPsPacketForwardEnable,
                cd11IfMultipleBssidEnable, 
                cd11IfVlanPsPacketForwardEnable
                }
        STATUS     current
        DESCRIPTION
                "Information to manage IEEE 802.11 protocol
                radio interface settings."
        ::= { ciscoDot11IfMIBGroups 17 }

cd11IfNativeRadioManageGroup OBJECT-GROUP
        OBJECTS {
                cd11IfPhyNativePowerUseStandard,
                cd11IfRfFrequencyUnits,
                cd11IfRfStartChannelNumber,
                cd11IfRfEndChannelNumber,  
                cd11IfRfChannelSpacingNumber,
                cd11IfRfStartChannelFrequency,
                cd11IfRfFrequencySpacing,  
                cd11IfRfFrequencyBandType,       
                cd11IfMaxChannelSwitchTime, 
                cd11IfNativeNumberPowerLevels,
                cd11IfNativeCurrentPowerLevel,
                cd11IfNativePowerUnits, 
                cd11IfNativeTxPower      
                }
        STATUS     current
        DESCRIPTION
                "Native parameters to manage IEEE 802.11 
                radio power and frequency bands."
        ::= { ciscoDot11IfMIBGroups 18 }

cd11IfDataRatesSensitivityGroup OBJECT-GROUP
        OBJECTS {
                cd11IfRatesSensRequiredSnr,
                cd11IfRatesSensContention 
                }
        STATUS     current
        DESCRIPTION
                "Receive sensitivity specification for IEEE 
                802.11 radios."
        ::= { ciscoDot11IfMIBGroups 19 }

cd11IfMonitorNotificationGroup NOTIFICATION-GROUP
        NOTIFICATIONS {
                cd11IfStationSwitchOverNotif, 
                cd11IfRogueApDetectedNotif
        }
        STATUS current
        DESCRIPTION
                "The notification group for this module."
        ::= { ciscoDot11IfMIBGroups 20 }

cd11Ifdot11UpgradeStatusGroup OBJECT-GROUP
        OBJECTS {
                cd11IfDot11UpgradeStatus
        }
        STATUS current
        DESCRIPTION
                "This collection of objects provide information
                about the status of upgrade of the dot11 radios
                to operate in the new frequency set. "
        ::= { ciscoDot11IfMIBGroups 21 }

cd11Ifdot11MobileStationScanGroup OBJECT-GROUP
        OBJECTS {
                cd11IfMobileStationListIgnore,
                cd11IfMobileStationScanChannel
        }
        STATUS current
        DESCRIPTION
                "This collection of objects provide information
                about the limited channel to scan and Ignore
                List. "
        ::= { ciscoDot11IfMIBGroups 22 }
END
