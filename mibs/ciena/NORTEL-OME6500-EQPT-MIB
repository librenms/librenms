NORTEL-OME6500-EQPT-MIB DEFINITIONS ::= BEGIN

   IMPORTS
       ome6500             FROM NORTEL-OPTICAL-OME6500-MIB
       entPhysicalIndex    FROM ENTITY-MIB           
       DisplayString       FROM RFC1213-MIB
       RowStatus           FROM SNMPv2-TC

       MODULE-IDENTITY,
       OBJECT-TYPE,
       OBJECT-IDENTITY   FROM SNMPv2-SMI;

nnOme6500Equipments MODULE-IDENTITY
        LAST-UPDATED "202002190000Z"    
        ORGANIZATION "Nortel"
        CONTACT-INFO
           "   7035 Ridge Road
               Hanover, Maryland 21076
               United States
               Toll-free: +1-800-921-1144
               Phone: +1-410-694-5700
               Fax: +1-410-694-5750
               www.ciena.com "
        DESCRIPTION
              "Optical Multiservice Edge (ome)
              This Module will be used to identify the equipment attributes for
              the Nortel OME6500 40G cards."
   
        --Revision history
        REVISION "200708100000Z"
        DESCRIPTION "Initial Version - created for OME6500 REL 5.1"
	
	REVISION "200802070000Z"
        DESCRIPTION "Updating row formatting OME6500 REL 5.1"	 
	      
	REVISION "200802210000Z"
        DESCRIPTION "Updating EquipmentType enum list for OME6500 REL 5.1"
	
	REVISION "200803100000Z"
        DESCRIPTION "Updating EquipmentType enum list for OME6500 REL 5.1
	             L2SS20G -> 20GL2SS"

        REVISION "200803270000Z"
        DESCRIPTION "
	  change (1): Following EquipmentTypes were missing from the EquipmentType 
	              enum lis, so they have been added for OME6500 REL 5.1.  
	                DS3E3EC1, DS3E3EC1P, GE, L2RPR, MRO, and OTSC.
          change (2): Nil enum was required in SecondaryState,
		      and  EquipmentMode, so it is added to those enum types."

	REVISION "200807300000Z"
        DESCRIPTION " 
	   changed the min string size from 1 to 0."

	REVISION "200808200000Z"
        DESCRIPTION " 
	   Added new EquipmentType for OME6500 R5.2"

	REVISION "200904190000Z"
        DESCRIPTION " 
	   Added new 40GXCIF card for OME6500 R6.0"

	REVISION "200905050000Z"
        DESCRIPTION " 
	   Added new EquipmentType for OME6500 R7.0:
	    100GOCLD, 10x10GMUX, 4x10GMUX, 40GUOCLD"

	REVISION "200908050000Z"
        DESCRIPTION " 
	   Modified Equipment tag for OME6500 R7.0:
	     10x10GMUX --> 100GMUX, 4x10GMUX -- > 40GUMUX	
	   Added new EquipmentType for OME6500 R7.0: 100GOCI "

	REVISION "201006300000Z"
        DESCRIPTION " 
	   Added OSIC,PCFP and FLEXMOTR cards' Enums for R7.0"

	REVISION "201011010000Z"
        DESCRIPTION " 
	   Added multi state secondary states in SecondaryState Enum (15 to 22) for R8.0"

	REVISION "201012070000Z"
        DESCRIPTION " 
	   Added PSFP Enum for R8.0"
         
	REVISION "201101180000Z"
        DESCRIPTION " 
	   Added new card OTNFMOTR Enum for R8.0"
         
	REVISION "201103180000Z"
        DESCRIPTION " 
	   Added 2 new cards CCMD12, 2x8 SMD Enum for R8.9"

	REVISION "201103280000Z"
        DESCRIPTION " 
	   Added new card SPOTNFMOTR Enum for R8.0"

	REVISION "201108030000Z"
        DESCRIPTION " 
	   Added OTNFLEX & OTNXCIF cards and increased PEC Code range for R9.0"

	REVISION "201108190000Z"
        DESCRIPTION " 
	   Added new SLIC Card Enum for R9.0"

	REVISION "201108300000Z"
        DESCRIPTION " 
	   Added remote PPC6 chassis and passive photonic Cards for R9.0"
         
	REVISION "201202220000Z"
        DESCRIPTION " 
	   Added PXFP in EquipmentType enum and
	   mate-pending-xconnect EquipmentMode in for R9.0"
         
	REVISION "201203230000Z"
        DESCRIPTION " 
	   Added  new card OPS in EquipmentType enum for R9.2"
         
	REVISION "201205080000Z"
        DESCRIPTION " 
	   Added  AINS states in SecondaryState Enum for R9.2"
         
	REVISION "201207260000Z"
        DESCRIPTION " 
	   Added  new card EVOA in EquipmentType enum for R9.2"
         
	REVISION "201209110000Z"
        DESCRIPTION " 
	   Added  new cards EMOTR & PKTFLEX in EquipmentType enum for R9.2
	   Added  idleAndUeq states in SecondaryState Enum for R9.2"
         
	REVISION "201210050000Z"
        DESCRIPTION " 
	   Added  new cards SRA, SAM, ESAM & XLA in EquipmentType enum for Raman support in R9.3"

	REVISION "201212040000Z"
	DESCRIPTION " 
	   Added  fltAndWrksync state in SecondaryState Enum for R9.2"

	REVISION "201301230000Z"
	DESCRIPTION " 
	   Added  wrkctrl states in SecondaryState Enum for R9.3"
         
	REVISION "201304020000Z"
	DESCRIPTION " 
	   Added  ueqAndStbyh(60) and ainsAndUeqAndStbyh(61) states in SecondaryState Enum for R9.3"

	REVISION "201306090000Z"
	DESCRIPTION " 
	   Added  meaAndStbyh(62), fltAndStbyh(63), fltAndWrktrafAndWrksync(64), meaAndWrksync(65)  
                  and ueqAndWrksync(66) states in SecondaryState Enum for R10.0" 

	REVISION "201308010000Z"
        DESCRIPTION " 
	   Added  new card ISS in EquipmentType enum for R10.0"

	REVISION "201310300000Z"
	DESCRIPTION " 
	   Added actAndWrk(67), idleAndWrk(68),actAndStbyh(69), idleAndStbyh(70), stbys(71),
	   ainsAndStbys(72), ueqAndStbys(73), ainsAndUeqAndStbys(74), meaAndStbys(75),
	   fltAndStbys(76), actAndStbys(77), idleAndStbys(78) states in SecondaryState Enum for R10.0" 

	REVISION "201311190000Z"
	DESCRIPTION " 
	   Added fltAndWrk(79), fltAndUeq(80), fltAndWrktraf(81), fltAndWrktrafAndWrksyncAndWrkctrl(82),
           fltAndSgeo(83), idleAndSgeo(84), idleAndWrkAndUeq(85),
	   idleAndStbysAndUeq(86), idleAndStbysAndFlt(87), idleAndStbyhAndUeq(88), 
	   idleAndStbyhAndFlt(89)  states in SecondaryState Enum for R10.0"

	REVISION "201401140000Z"
	DESCRIPTION " 
	   Added  wrktrafAndWrkctrl(90) state in SecondaryState Enum for R10.0"

	REVISION "201405060000Z"
        DESCRIPTION " 
	   Added PQSFP Enum for R10.1"

	REVISION "201405150000Z"
        DESCRIPTION " 
	   Added new card OTR in EquipmentType enum for R10.1"

	REVISION "201405290000Z"
        DESCRIPTION " 
	   Added new card PKTOTN and PKTOTNXCIF in EquipmentType enum for R10.1"

	REVISION "201406030000Z"
        DESCRIPTION " 
	   Added FIM, PCXM, CCMD8X16 Enum for CDC support for R10.1"

	REVISION "201406230000Z"
	DESCRIPTION " 
	   Added  wrksyncAndWrkctrl(91), actAndUeq(92), wrkAndMea(93) states in SecondaryState Enum for R10.1"

	REVISION "201407220000Z"
        DESCRIPTION " 
	   Added new card BMD and GMD10 in EquipmentType enum for R10.1"

	REVISION "201408270000Z"
	DESCRIPTION " 
	   Added  idleAndMea(94) state in SecondaryState Enum for R10.1"

	REVISION "201410200000Z"
	DESCRIPTION " 
	   Added new card MOTR in EquipmentType enum for R10.2"

	REVISION "201411240000Z"
	DESCRIPTION " 
	   Added new cards OBB & OBMD8 in EquipmentType enum for R10.2"

	REVISION "201503310000Z"
	DESCRIPTION " 
	   Added new cards CTM, SM, CCMD16X12 & RLA in EquipmentType enum for R11.00"

	REVISION "201505150000Z"
	DESCRIPTION " 
	   Added new cards AMP4, PCFP2 in EquipmentType enum & secondary states viz. 
	   wrkoam(95), fltAndWrkoam(96), wrksyncAndWrkoam(97), wrkoamAndWrkctrlAndWrksync(98), fltAndWrksyncAndWrkoam(99) for R11.00"

	REVISION "201506110000Z"
	DESCRIPTION " 
	   Added new secondary state  wrkoamAndWrkctrl(100) for R11.00"

	REVISION "201507280000Z"
	DESCRIPTION " 
	   Added new secondary state  fltAndWrksyncAndWrkctrlAndWrkoam(101) for R11.10"

	REVISION "201508120000Z"
	DESCRIPTION " 
	   Added new card CMD96 and 200GOCI (OCI) for Release R11.10"

	REVISION "201602050000Z"
	DESCRIPTION " 
	   Added new secondary states viz.  wrkAndUeq, meaAndWrktraf, ueqAndWrktraf, fltAndUeqAndWrktraf and fltAndWrktrafAndWrkctrl in Release R11.50"

        REVISION "201608230000Z"
	DESCRIPTION " 
	   Added new card CMD64 for Release R11.6"

	REVISION "201605090000Z"
	DESCRIPTION " 
	   Added new cards MFC, CCMD8X4 and OTDR4 as well as  new secondary states viz.  xalgn and wrksyncAndWrkoamAndXalgn in Release R12.00"

	REVISION "201607110000Z"
	DESCRIPTION " 
	   Added new secondary states viz. wrksyncAndWrkctrlAndWrkoamAndXalgn, stbyhAndXalgn and ueqAndXalgn in Release R12.00"

        REVISION "201609120000Z"
	DESCRIPTION " 
	   Added new secondary states viz. fltAndWrksyncAndWrkctrlAndWrkoamAndXalgn in Release R12.10"

        REVISION "201611170000Z"
	DESCRIPTION " 
	   Added new card WL4 transponders (400G MOTR, 400G FOTR, 400G OTR) represented by equipment tag FOTR in Release R12.10"

	REVISION "201702150000Z"
	DESCRIPTION " 
	   Added new secondary states viz. stby (113), ainsAndStby (114), ueqAndStby (115), ainsAndUeqAndStby (116), meaAndStby (117), fltAndStby (118), actAndStby (119), idleAndStby (120), idleAndStbyAndUeq (121), idleAndStbyAndFlt (122), stbyAndXalgn (123)  in Release R12.10"

        REVISION "201709260000Z"
	DESCRIPTION " 
	   Added new secondary states viz. sgeoAndStby (124) in Release R12.30"

        REVISION "201710040000Z"
        DESCRIPTION " 
           Added new card CLMD, UCS and CCMD64 in Release R12.20"

        REVISION "201710240000Z"
        DESCRIPTION " 
           Changed equipment tag FOTR which used to represent card WL4 transponders (400G MOTR, 400G FOTR, 400G OTR)to TRM in Release R12.20"

        REVISION "201804230000Z"
        DESCRIPTION "
           Dummy Revision added in R12.3. Reason - R12.3 & R12.2 had the same revision number (i.e. LASTUPDATED value) but R12.3 MIB had extra enum value for SecondaryState sgeoAndStdby corresponding to revision 201709260000Z."
	
        REVISION "201808090000Z"
        DESCRIPTION "
           Added new secondary states viz. actAndWrktrafAndWrksync (125), actAndWrktrafAndWrksyncAndWrkctrl (126), idleAndWrktrafAndWrksyncAndWrkctrl (127), idleAndDim1wrkAndDim2wrk (128), idleAndDim2wrk (129) in Release R12.4."

        REVISION "202002190000Z"
        DESCRIPTION " 
           Added new card CMD42 in Release R12.70"

        ::= { ome6500 2 }


Boolean ::= INTEGER {
    false(0),
    true(1)
}

-- The Admin State and Primary States 
-- are doubly defined in the 40G Fac
-- module and the OME6500 Equipment
-- module. Ultimately, they need to 
-- be merged. In the meantime, they
-- need to be concurrently updated.
AdminState ::= INTEGER {
    unknown(0),
    is(1),
    oos(2)
}

PrimaryState ::= INTEGER {
    unknown(0),
    is(1),
    is-anr(2),
    oos-au(3),
    oos-ma(4),
    oos-auma(5),
    oos-maanr(6)
}

EquipmentType ::= INTEGER {
        eNil(0),
        eEMPTY(1),
        eUNKNOWN(2),
        eILAN(3),
        eODU2(4), -- AID object name for the ODU2 fac object 
        eDS1(5),
        eDS3(6),
        eOC3(7), -- OME OC3 fac AID name
        eXC(8), -- OM3K VTX or OME XC card equipment type
        eSP(9), -- OM3K and OME shelf processor equipment type
        eFC100(10),
        eOC12(11), -- OME OC12 fac AID name
        eSTS1DS3(12),
        eSTS1E3(13),
        eVT1DS1(14),
        eVT2E1(15),
        eSMUX(16), -- OME SuperMux equipment type
        eFC200(17),
        eEC1(18),
        eE1WAN(19),  -- L2 PDH E1 type "E1WAN"
        eFC400(20),
        eVCE-ETH10G(21),
        eVCEMAP-ETH10G(22),
        e40GMUX(23),  -- 4 x 10G Single Slot Client Mate Eqpt Type
        e20GL2SS(24), -- OME 20GL2SS card equipment type
        eDS1WAN(25),  -- L2 PDH DS1 type - "DS1WAN"
        eEIO(26),
        eE3WAN(27),  -- L2 PDH E3 type - "E3WAN"
        e40GOCI(28),  -- 40G Single Slot Client Mate Eqpt Type
        e40GOCLD(29),  -- 40G Single Slot Full C-band Tunable Line Eqpt Type
        eDS3V(30),
        eDS3WAN(31),  -- L2 PDH DS3 type - "DS3WAN"
        eE1(32),
        eP10GSOELFC(33),  -- Pluggable 10G+10.7G+11.05G+11.09G+11.27G XFP eqpt type
        eOTS(34),  -- Photonic OTS virtual equipment
        eWSSOPM(35), -- OME/CPL WSS card with OPM capability
        e155ME(36), -- OME STM1e card equipment type
        e155MEP(37), -- OME STM1e P card equipment type
        eOC48(38), -- OME OC48 fac AID name
        ePWR(39),
        eFILLED-IO(40),
        eBNC-IO(41),
        eFAN(42),
        eE1DS3(43), -- OME E1DS3 on Transmux
        eE1E3(44), -- OME E1E3 on Transmux
        eVT2DS3(45), -- OME VT2DS3 on Transmux
        eVT2E3(46), -- OME VT2E3 on Transmux
        ePGE(47), -- OME GE SFP equipment type
        ePGEFC200(48), -- OME GE/FC100/FC200 SFP equipment type
        eDS1TM(49),
        eDSMBP(50),
        eDSMOAMEX(51),
        eDSMFANX3(52),
        eDSMIO(53),
        eDSM(54),
        eCMD44(55), -- CPL CMD44 equipment type
        eDINPIO(56), -- OME DINP IO card equipment type
        eBackplane(57),
        e1GFOSFC(58), -- OME 1GFOS card equipment type
        eFILLED(59),
        eFC1200(60), -- FC1200
        eOC192(61), -- OME AID object name for oc192 fac obj
        eSLOT(62), -- OME used to identify a slot, non-card specific
        eMIC(63), -- OME MIC card equipment type
        eAP(64), -- OME Access Panel equipment type
        eFILLER(65), -- OME Filler card equipment type
        eFANHOUSING(66), -- OME Fan backplane/housing equipment type
        e155622M(67), -- OME OC3/OC12 combo card equipment type
        e2G5(68), -- OME 2.5G card equipment type
        e10G(69), -- OME 10G card equipment type
        e1GFOS(70), -- OME GE card equipment type
        eP155622M(71), -- OME OC3/OC12 SFP equipment type
        eP2G5(72), -- OME 2.5G SFP equipment type
        eP2G5W(73), -- OME 2.5G DWDM pluggable equipment type
        ePGEFC(74), -- OME GE/FC100 SFP equipment type
        eETH(75), -- OME AID object name for eth fac object
        eFC(76), -- OME AID object name for fc fac object
        eWAN(77), -- OME AID object name for wan object
        eSTS1(78), -- OME AID object name for sts1 fac object
        eSTS3c(79), -- OME AID object name for sts3c fac object
        eSTS12c(80), -- OME AID object name for sts12c fac object
        eSTS24c(81), -- OME AID object name for sts24c fac object
        eSTS48c(82), -- OME AID object name for sts48c fac object
        eSTS192c(83), -- OME AID object name for sts192c fac object
        eVT15(84), -- OME AID object name for vt15 fac object
        eVT2(85), -- OME AID object name for vt2 fac object
        eVT6(86), -- OME AID object name for vt6 fac object
        e2G5W(87), -- OME 2.5G DWDM card equipment type
        e10GW(88), -- OME 10G DWDM card equipment type
        eBITSIN(89), -- OME BITSIN equipment type
        eBITSOUT(90), -- OME BITSOUT equipment type
        eDS3EC1(91), -- OME DS3EC1 multi port combo card equipment type
        eE1PSM-IO(92), -- PSM(Protection sub module) IO for the E1 card
        eE1CNV-IO(93), -- E1 IO converter modules for E1 card
        eGMD(94),  -- CPL GMD equipment type
        eDOSC(95),  -- CPL DOSC equipment type
        eCMD4(96),  -- CPL CMD4 equipment type
        eLIM(97),  -- CPL LIM equipment type
        eSLA(98),  -- CPL SLA equipment type
        eMLA(99),  -- CPL MLA equipment type
        eVOA(100), -- CPL AID object name for voa fac object
        eEDFA(101), -- CPL AID object name for edfa fac object
        eOPTMON(102), -- CPL AID object name for optmon fac object
        eOSC(103), -- CPL AID object name for osc fac object
        eDOC(104), -- CPL AID object name for doc fac object
        eP155M(105), -- OME OC3 SFP equipment type
        eP622M(106), -- OME OC12 SFP equipment type
        eADJ(107), -- CPL AID object name for adj fac object
        eDS3EC1P(108), -- OME DS3EC1 protection card equipment type
        eE1P(109), -- OME E1 protection card equipment type
        eCOLAN(110), -- OME and CPL COLAN equipment type
        eWAYSIDE(111), -- CPL Wayside equipment type
        eADJTX(112), -- CPL TX Adjacency facility AID object name
        eADJRX(113), -- CPL RX Adjacency facility AID object name
        eADJLN(114), -- CPL Line Adjacency facility AID object name
        eNC(115), -- CPL Network Channel AID Object
        eVT15AU4(116), -- AU4-mapped VT15
        eVT2AU4(117), -- AU4-mapped VT2
        eVT6AU4(118), -- AU4-mapped VT6
        eSTS1AU4(119), -- AU4-mapped STS1
        eDSCM(120), -- CPL DSCM equipment type
        eSHELF(121), -- CPL SHELF
        eSWT(122), -- CPL Shelf Wavelength Topology
        eOST(123), -- CPL Optical System Topology
        eOPM(124), -- CPL Optical Power Monitor
        eWB(125), -- CPL Wavelength Blocker
        e10GOCWT(126), -- 10G SONET/SDH Single Slot Wavelength Translator (WT) eqpt type
        e10GELWT(127), -- 10G transparent Ethernet LAN PHY Single Slot WT eqpt type
        eOC768(128), -- OME AID object name for oc768 fac obj 
        e2G5MX(129), -- 4xOC-48/STM-16/OTU-1 MUX(ponder) eqpt type
        -- eOTN1(130),  obsolete - use OTM1 entry below
        eOTM1(130), -- AID object name for the otm1 fac object
        -- eOTN2(131),  obsolete - use OTM2 entry below
        eOTM2(131), -- AID object name for the otm2 fac object
        -- eOTN3(132),  obsolete - use OTM3 entry below
        eOTM3(132), -- AID object name for the otm3 fac object
        eETH10G(133), -- AID object name for the 10G eth fac object
        ePUNKNOWN(134), -- OME object name for SFP UNKNOWN type
        eP155Me(135), -- OME STM1e SFP equipment type
        eSTM1e(136), -- OME STM1e object name
        eL2SS(137), -- OME L2SS card equipment type
        eLAN(138), -- OME LAN equipment type, e.g. LAN-15
        eENV(139), -- OME ENV
        eCONT(140), -- OME CONT
        e1FN-BNC-IO(141), -- OME 1:N BNC I/O for DS3/EC1/E1 cards.
        eDEST(142), -- CPL SNMP Destination
        eUOSC(143), -- CPL UOSC equipment type
        eCMD8(144), -- CPL CMD8 equipment type
        eWSS(145), -- CPL WSS equipment type
        eCHC(146), -- CPL AID object name for channel control fac object
        eSCO(147), -- CPL SCMD Cascade Order object type
        eVCS(148), -- OME Layer 2 Virtual Circuit Segment
        eVCE(149), -- OME Layer 2 Virtual Circuit Endpoint
        eVCE-ETH(150), -- OME Layer 2 internal use
        eVCE-WAN(151), -- OME Layer 2 internal use
        eVCE-LAG(152), -- OME Layer 2 internal use
        eVCEMAP( 153), -- OME Layer 2 Virtual Circuit Endpoint Map
        eVCEMAP-ETH(154), -- OME Layer 2 internal use
        eVCEMAP-WAN(155), -- OME Layer 2 internal use
        eVCEMAP-LAG(156), -- OME Layer 2 internal use
        eBWPRF(157), -- OME Layer 2 internal use
        eDMPRF(158), -- OME Layer 2 internal use
        eCFPRF(159), -- OME Layer 2 internal use
        eFE(160), -- OME FE cards equipment type, e.g. 24xFE-SFP/IO, 24xFE-IO
        ePFE(161), -- OME FE pluggable equipment type
        eP10GS(162), -- Pluggable 10G XFP eqpt type
        eP10GEL(163), -- Pluggable 11.1G XFP eqpt type
        eP10GSEL(164), -- Pluggable 10G+11.1G XFP eqpt type
        eP10GSOEL(165), -- Pluggable 10G+10.7G+11.1G XFP eqpt type
        e10GOCLD(166), -- OME BB 10G OCLD card equipment type
        e2xOSC(167), -- OME 2 Port Optical Service Channel
        e10GOTR(168), -- OME BB 10G OTR card equipment type
        eTMUX(169), -- OME Transmux equipment type
        eDS1DS3(170), -- OME DS1 on Transmux
        eVT1DS3(171), -- OME VT15 on Transmux
        eSE(172), -- CPL Shared Eqpt
        eRPR(173), -- OME RPR card equipment type
        eMXC(174), -- OME MXC card equipment type
        eCOSST(175), -- OME COS Standard equipment type
        eCOSBR(176), -- OME COS Bronze equipment type
        eCOSSL(177), -- OME COS Silver equipment type
        eCOSGD(178), -- OME COS Gold equipment type
        eCOSPL(179), -- OME COS Platinum equipment type
        eCOSPR(180), -- OME COS Premium equipment type
        eCOSNT(181), -- OME COS Network equipment type
        eCOSCR(182), -- OME COS Critical equipment type
        eLAG(183), -- OME Link Aggregration Group equipment type
        eETH100(184), -- OME AID object name for eth100 fac object
        eCHMON(185), -- CPL CHMON equipment type
        eE1MIO75P(186), -- METRO 75 ohm protected I/O
        eE1MIO120P(187), -- METRO 120 ohm protected I/O
        eE1MIO75U(188), -- METRO 75 ohm unprotected I/O
        eE1MIO120U(189), -- METRO 120 ohm unprotected I/O
        eTNS(190), -- OME Layer 2 Tunnel
        eTNE(191), -- OME Layer 2 Tunnel Endpoint
        eTNE-ETH(192), -- OME Layer 2 Internal Use
        eTNE-WAN(193), -- OME Layer 2 Internal Use
        eTNE-RPR(194), -- OME Layer 2 Internal Use
        eTNE-LAG(195), -- OME Layer 2 Internal Use
        eTNEMAP(196), -- OME Layer 2 Tunnel Endpoint Map
        eTNEMAP-ETH(197), -- OME Layer 2 Internal Use
        eTNEMAP-WAN(198), -- OME Layer 2 Internal Use
        eTNEMAP-RPR(199), -- OME Layer 2 Internal Use
        eTNEMAP-LAG(200), -- OME Layer 2 Internal Use
        eVCE-RPR(201), -- OME Layer 2 Internal Use
        eVCEMAP-RPR(202), -- OME Layer 2 Internal Use
        eRPR-RING(203), -- OME RPR ring
        eRPR-RINGLET(204), -- OME RPR RINGLET
        eCOS(205), -- OME (all) COS equipment type
        eRPR-STATION(206), -- OME RPR station (topology)
        e10GOTNWT(207), -- 10G OTN Single Slot Wavelength Translator (WT) eqpt type
        eLNGRP(208), -- OME equipment group type
        eWTGRP(209), -- OME equipment group type
        eFE-IO(210), -- IO module for 24xFE card
        eOCH(211), -- CPL OCH eqpt type for OBM appl
        ePRTSCHED(212), -- OME Layer 2 scheduler
        eHOP(213), -- OME Layer 2 hop
        eE3(214), -- OME DS3E3x24 card E3 facility eqpt
        e10GOTSC(215), -- OME BB 10G OTSC card equipment type
        eFDB(216), -- OME Layer 2 Forwarding/Filtering Database
        eFDBSTATIC(217), -- OME Layer 2 FDB Static Entries
        eCOSA(218), -- OME Layer 2 Internal Use
        eCOSBC(219), -- OME Layer 2 Internal Use
        eCOSBE(220), -- OME Layer 2 Internal Use
        eCOSC(221), -- OME Layer 2 Internal Use
        eXGE(222), -- OME 10GE (XGE) card equipment type
        eDRA(223), -- CPL Distributed Raman Amplifier eqpt type
        eRAMAN(224), -- CPL AID object name for Raman fac object
        eVCEA(225), -- OME Layer 2 Internal Use
        eVCEBC(226), -- OME Layer 2 Internal Use
        eVCEBE(227), -- OME Layer 2 Internal Use
        eVCEC(228), -- OME Layer 2 Internal Use
        eTNEA(229), -- OME Layer 2 Internal Use
        eTNEBC(230), -- OME Layer 2 Internal Use
        eTNEBE(231), -- OME Layer 2 Internal Use
        eTNEC(232), -- OME Layer 2 Internal Use
        ePCWDMS(233), -- OME CWDM SONET|SDH OC3|OC12|OC48 SFP equipment type
        eSCHPRF(234), -- OME Layer 2 Internal Use
        eVCEST(235), -- OME Layer 2 Internal Use
        eVCESL(236), -- OME Layer 2 Internal Use
        eVCEGD(237), -- OME Layer 2 Internal Use
        eVCEPR(238), -- OME Layer 2 Internal Use
        eVCENT(239), -- OME Layer 2 Internal Use
        eTNEST(240), -- OME Layer 2 Internal Use
        eTNESL(241), -- OME Layer 2 Internal Use
        eTNEGD(242), -- OME Layer 2 Internal Use
        eTNEPR(243), -- OME Layer 2 Internal Use
        eTNENT(244), -- OME Layer 2 Internal Use
        ePFC400(245), -- OME FC100/FC200/FC400 SFP equipment type
        eDISP(246), -- OME AID object name for DISP facility object
        eHEXOCN(247), -- OME HEX OC-n card(MiF) equipment type
        eODU3(248), -- AID object name for the ODU3 fac object
        eCMDA(249), -- Photonic Channel Mux/Demux Amplifier
	e10GWT(250),
	e2G5MOTR(251),
        eGENERIC(252),   -- <== needs to be defined
	eDS3E3EC1(253),
	eDS3E3EC1P(254),
	eGE(255),
	eL2RPR(256),
	eMRO(257),
	eOTSC(258),
	eMRO2(259),  -- This is only for R5.2
	eL2MOTR(260),
	eTPT(261),
	eOMX(262),
	e40GXCIF(263),
	e100GOCLD(264),
	e100GOCI(265),
	e100GMUX(266),
	e40GUMUX(267),
	e40GUOCLD(268),
	eOSIC(269),
	eFLEXMOTR(270),
	ePCFP(271),
	ePSFP(272),
	eOTNFMOTR(273),
	eSPOTNFMOTR(274),
	eCCMD12(275),
	eSMD(276),
	eOTNFLEX(277),
	eOTNXCIF(278),
	eSLIC(279),
	ePPC6(280),
	eBS(281),
	eOMDF4(282),
	eOMDF8(283),
	eOSCF(284),
	eFGA(285),
	ePXFP(286),
	eOPS(287),
	eEVOA(288),
	eEMOTR(289),
	ePKTFLEX(290),
	eSRA(291),
	eSAM(292),
	eESAM(293),
	eXLA(294),
	eISS(295),
	ePQSFP(296),
        eOTR(297),
        ePKTOTN(298),
        ePKTOTNXCIF(299),
        eCCMD8X16(300),
        ePCXM(301),
        eFIM(302),
        eBMD(303),
        eGMD10(304),
        eMOTR(305),
        eOBB(306),
        eOBMD8(307),
        eCTM(308),
        eSM(309),
        eCCMD16X12(310),
        eRLA(311),
        eAMP4(312),
        ePCFP2(313),
        eCMD96(314),
        eOCI(315),
        eMFC(316),
        eCCMD8X4(317),
        eOTDR4(318),
        eCMD64(319),
        eTRM(320),
        eCLMD(321),
        eUCS(322),
        eCCMD64(323),
        eCMD42(324),
        eMAX(325)
}

SecondaryState ::= INTEGER {
        unknown(0),
	nil(1),
        act(2),
        idle(3),
        sgeo(4),
        psi(5),
        flt(6),
        mea(7),
        stbyh(8),
        ts(9),
        ueq(10),
        wrk(11),
        wrksync(12),
        wrktraf(13),
        faf(14),
        meaAndFlt(15),
        actAndFlt(16),
        actAndWrksync(17),
        actAndFltAndWrksync(18),
        idleAndFlt(19),
        idleAndWrksync(20),
        idleAndFltAndWrksync(21),
        wrktrafAndWrksync(22),
	ains(23),
        actAndAins(24),
        ainsAndIdle(25),
        ainsAndSgeo(26),
        ainsAndPsi(27),
        ainsAndFlt(28),
        ainsAndMea(29),
        ainsAndStbyh(30),
        ainsAndTs(31),
        ainsAndUeq(32),
        ainsAndWrk(33),
        ainsAndWrksync(34),
        ainsAndWrktraf(35),
        ainsAndFaf(36),
        ainsAndMeaAndFlt(37),
        actAndAinsAndFlt(38),
        actAndAinsAndWrksync(39),
        actAndAinsAndFltAndWrksync(40),
        ainsAndIdleAndFlt(41),
        ainsAndIdleAndWrksync(42),
        ainsAndIdleAndFltAndWrksync(43),
        ainsAndWrktrafAndWrksync(44),
        idleAndUeq(45),
	fltAndWrksync(46),
        wrkctrl(47),
        actAndWrkctrl(48),
        idleAndWrkctrl(49),
        ainsAndWrkctrl(50),
	fltAndWrkctrl(51),
        actAndFltAndWrkctrl(52),
        idleAndFltAndWrkctrl(53),
        actAndAinsAndWrkctrl(54),
        actAndAinsAndFltAndWrkctrl(55),
        ainsAndIdleAndWrkctrl(56),
        ainsAndIdleAndFltAndWrkctrl(57),
        wrktrafAndWrksyncAndWrkctrl(58),
        ainsAndWrktrafAndWrksyncAndWrkctrl(59),
	ueqAndStbyh(60),
	ainsAndUeqAndStbyh(61),
        meaAndStbyh(62),
        fltAndStbyh(63),
        fltAndWrktrafAndWrksync(64),
        meaAndWrksync(65),
        ueqAndWrksync(66),
        actAndWrk(67),
        idleAndWrk(68),
        actAndStbyh(69),
        idleAndStbyh(70),
        stbys(71),
        ainsAndStbys(72),
        ueqAndStbys(73),
        ainsAndUeqAndStbys(74),
        meaAndStbys(75),
        fltAndStbys(76),
        actAndStbys(77),
        idleAndStbys(78),
	fltAndWrk(79),
        fltAndUeq(80),
	fltAndWrktraf(81),
        fltAndWrktrafAndWrksyncAndWrkctrl(82),
        fltAndSgeo(83),
        idleAndSgeo(84),
        idleAndWrkAndUeq(85),
        idleAndStbysAndUeq(86),
        idleAndStbysAndFlt(87),
        idleAndStbyhAndUeq(88),
        idleAndStbyhAndFlt(89),
        wrktrafAndWrkctrl(90), 
        wrksyncAndWrkctrl(91), 
        actAndUeq(92),
        wrkAndMea(93),
        idleAndMea(94),
        wrkoam(95),
        fltAndWrkoam(96),
        wrksyncAndWrkoam(97),
        wrkoamAndWrkctrlAndWrksync(98),
        fltAndWrksyncAndWrkoam(99),
        wrkoamAndWrkctrl(100),
        fltAndWrksyncAndWrkctrlAndWrkoam(101),
        wrkAndUeq(102), 
        meaAndWrktraf(103), 
        ueqAndWrktraf(104), 
        fltAndUeqAndWrktraf(105),
        fltAndWrktrafAndWrkctrl (106),
        xalgn(107),
        wrksyncAndWrkoamAndXalgn (108),
        wrksyncAndWrkctrlAndWrkoamAndXalgn (109),
        stbyhAndXalgn (110),
        ueqAndXalgn (111),
        fltAndWrksyncAndWrkctrlAndWrkoamAndXalgn (112),
        stby (113),
        ainsAndStby (114),
        ueqAndStby (115),
        ainsAndUeqAndStby (116),
        meaAndStby (117),
        fltAndStby (118),
        actAndStby (119),
        idleAndStby (120),
        idleAndStbyAndUeq (121),
        idleAndStbyAndFlt (122),
        stbyAndXalgn (123), 
        sgeoAndStby (124),
        actAndWrktrafAndWrksync(125),
        actAndWrktrafAndWrksyncAndWrkctrl(126),
        idleAndWrktrafAndWrksyncAndWrkctrl(127),
        idleAndDim1wrkAndDim2wrk(128),
        idleAndDim2wrk(129)
 
}

EquipmentMode ::= INTEGER {
        unknown(0),
	nil(1),
	internal(2),
	mated(3),
	xconnect(4),
	internal-mated(5),
	internal-xconnect(6),
	mated-xconnect(7),
	internal-mated-xconnect(8),
	matedsym(9),
	internal-matedsym(10),
	matedsym-xc(11),
	internal-matedsym-xconnect(12),
	mate-pending(13),
	mate-pending-xconnect(14)
}

nnEqptProv       OBJECT IDENTIFIER ::= { nnOme6500Equipments 1 }
nnInventory    OBJECT IDENTIFIER ::= { nnOme6500Equipments 2 }

nnEqptProvTable    OBJECT-TYPE
	SYNTAX    SEQUENCE OF NnEqptProvEntry
	MAX-ACCESS    not-accessible
	STATUS    current
        DESCRIPTION  "This table contains entries of all the 
	              provisioned equipments."
	::= { nnEqptProv 1 }

nnEqptProvEntry   OBJECT-TYPE
	SYNTAX    NnEqptProvEntry
	MAX-ACCESS    not-accessible
	STATUS    current
        DESCRIPTION  ""
        INDEX     { entPhysicalIndex  }
	::= { nnEqptProvTable 1 }


NnEqptProvEntry ::= 
	SEQUENCE {
		provEqptType
			EquipmentType,
		provCardType
			DisplayString,
		provEqptAID
			DisplayString,
		provPec
			DisplayString,
		adminState
			AdminState,
		primaryState
			PrimaryState,
		secondaryState
			SecondaryState, 
		eqptMode
			EquipmentMode,
		mateEqpt1
			DisplayString,
		mateEqpt2
			DisplayString,
		mateEqpt3
			DisplayString,
        rowStatus
			RowStatus,
		mapMode
			INTEGER,
		timingGroupId
			DisplayString,
		dsmSiteAddress
			DisplayString
	}

provEqptType    OBJECT-TYPE
	SYNTAX   EquipmentType 
	MAX-ACCESS    read-create
	STATUS    current
    DESCRIPTION  "This is obtained from the TL1 Blueprint XML document 
                  from the AID template group for Equipment AIDs.
                  Search for aid_templategroup name=(EQPT) 
                  description=(General Equipment AID)
                  The parantheses are for strings in quotes. Make
                  sure the list is updated with the AID group in the
                  TL1 blueprint."
	::= { nnEqptProvEntry 1 }

provCardType    OBJECT-TYPE
	SYNTAX    DisplayString
	MAX-ACCESS    read-only
	STATUS    current
    DESCRIPTION  "Obtained from the CTYPE TL1 parameter"
	::= { nnEqptProvEntry 2 }

provEqptAID OBJECT-TYPE
    SYNTAX	  DisplayString
	MAX-ACCESS    read-only
	STATUS    current
        DESCRIPTION  "AID from the TL1 RTRV-EQPT AID"
	::= { nnEqptProvEntry 3 }

provPec OBJECT-TYPE
	SYNTAX    DisplayString(SIZE(0..22))
	MAX-ACCESS    read-create
	STATUS    current
    DESCRIPTION  ""
	::= { nnEqptProvEntry 4 }

adminState OBJECT-TYPE
	SYNTAX    AdminState 
	MAX-ACCESS    read-write
	STATUS    current
    DESCRIPTION  "Primary State of the Equipment."
	::= { nnEqptProvEntry 5 }

primaryState OBJECT-TYPE
	SYNTAX    PrimaryState
	MAX-ACCESS    read-only
	STATUS    current
    DESCRIPTION  "Primary State of the Equipment."
	::= { nnEqptProvEntry 6 }

secondaryState OBJECT-TYPE
	SYNTAX    SecondaryState
	MAX-ACCESS    read-only
	STATUS    current
    DESCRIPTION  "Secondary State of the Equipment"
	::= { nnEqptProvEntry 7 }

eqptMode OBJECT-TYPE
	SYNTAX  EquipmentMode
	MAX-ACCESS    read-only
	STATUS    current
    DESCRIPTION  ""
	::= { nnEqptProvEntry 8 }

mateEqpt1 OBJECT-TYPE
	SYNTAX DisplayString
	MAX-ACCESS    read-only
	STATUS    current
    DESCRIPTION  "AID of mate card"
	::= { nnEqptProvEntry 9 }

mateEqpt2 OBJECT-TYPE
	SYNTAX DisplayString
	MAX-ACCESS    read-only
	STATUS    current
    DESCRIPTION  "AID of mate card"
	::= { nnEqptProvEntry 10 }

mateEqpt3 OBJECT-TYPE
	SYNTAX DisplayString
	MAX-ACCESS    read-only
	STATUS    current
    DESCRIPTION  "AID of mate card"
	::= { nnEqptProvEntry 11 }

rowStatus OBJECT-TYPE
	SYNTAX    RowStatus
	MAX-ACCESS    read-write
	STATUS    current
    DESCRIPTION  "This is used to manage rows in the equipment table."
	::= { nnEqptProvEntry 12 }

mapMode OBJECT-TYPE
    SYNTAX	INTEGER {
		unknown(0),
		au3-vt15(1),
		au4-vt2(2)
	}
	MAX-ACCESS    read-only
	STATUS    current
    DESCRIPTION  "Payload Mapping Mode - FE only"
	::= { nnEqptProvEntry 13 }

timingGroupId OBJECT-TYPE
    SYNTAX	 DisplayString
	MAX-ACCESS    read-only
	STATUS    current
    DESCRIPTION  "Timing Group ID - SMUX only"
	::= { nnEqptProvEntry 14 }

dsmSiteAddress OBJECT-TYPE
    SYNTAX	  DisplayString(SIZE(0..40))
	MAX-ACCESS    read-only
	STATUS    current
    DESCRIPTION  "DSM Site address"
	::= { nnEqptProvEntry 15 }



nnInventoryTable    OBJECT-TYPE
	SYNTAX    SEQUENCE OF NnInventoryEntry
	MAX-ACCESS    not-accessible
	STATUS    current
    DESCRIPTION  ""
	::= { nnInventory 1 }

nnInventoryEntry   OBJECT-TYPE
	SYNTAX    NnInventoryEntry
	MAX-ACCESS    not-accessible
	STATUS    current
    DESCRIPTION  "This table contains unprovisionable attributes 
	              of equipments physically present on the shelf."
    INDEX     { entPhysicalIndex }
	::= { nnInventoryTable 1 }


NnInventoryEntry ::= 
	SEQUENCE {
		actualEqptType
			EquipmentType,
		actualCardType
			DisplayString,
		inventoryAID 
			DisplayString,
		productEqptCode 
			DisplayString,
		releaseLevel
			DisplayString,
		clei
			DisplayString,
		serialNumber
			DisplayString,
		manufactureDate
			DisplayString,
		inServiceAge
			DisplayString,
		onSince
			DisplayString,
		--flightRecorderInfo
			--DisplayString,
		physicallyPresent
			Boolean,
		restartCard
			INTEGER,
		dsmMate
			DisplayString,
		dsmConn
			INTEGER
	}


actualEqptType    OBJECT-TYPE
	SYNTAX        EquipmentType
	MAX-ACCESS    read-only
	STATUS    current
    DESCRIPTION  "This is obtained from the TL1 Blueprint XML document 
                  from the AID template group for Equipment AIDs.
                  Search for aid_templategroup name=(EQPT) 
                  description=(General Equipment AID)
                  The parantheses are for strings in quotes. Make
                  sure the list is updated with the AID group in the
                  TL1 blueprint."
	::= { nnInventoryEntry 1 }

actualCardType    OBJECT-TYPE
	SYNTAX    DisplayString
	MAX-ACCESS    read-only
	STATUS    current
        DESCRIPTION  "From the CTYPE of the TL1 command. Could be the same as
                      the same entry in the Admin table."
	::= { nnInventoryEntry 2 }

inventoryAID OBJECT-TYPE
    SYNTAX	  DisplayString
	MAX-ACCESS    read-only
	STATUS    current
    DESCRIPTION  "TL1 AID from RTRV-INVENTORY response"
	::= { nnInventoryEntry 3 }


productEqptCode OBJECT-TYPE
	SYNTAX    DisplayString(SIZE(0..8))
	MAX-ACCESS    read-only
	STATUS    current
    DESCRIPTION  ""
	::= { nnInventoryEntry 4 }

releaseLevel OBJECT-TYPE
	SYNTAX    DisplayString
	MAX-ACCESS    read-only
	STATUS    current
    DESCRIPTION  ""
	::= { nnInventoryEntry 5 }

clei OBJECT-TYPE
	SYNTAX    DisplayString(SIZE(0..10))
	MAX-ACCESS    read-only
	STATUS    current
    DESCRIPTION  "Common Language Equipment Identifier"
	::= { nnInventoryEntry 6 }

serialNumber OBJECT-TYPE
	SYNTAX    DisplayString(SIZE(0..25))
	MAX-ACCESS    read-only
	STATUS    current
        DESCRIPTION  ""
	::= { nnInventoryEntry 7 }

manufactureDate OBJECT-TYPE
	SYNTAX    DisplayString
	MAX-ACCESS    read-only
	STATUS    current
    DESCRIPTION  ""
	::= { nnInventoryEntry 8 }

inServiceAge OBJECT-TYPE
	SYNTAX    DisplayString
	MAX-ACCESS    read-only
	STATUS    current
    DESCRIPTION  ""
	::= { nnInventoryEntry 9 }

onSince OBJECT-TYPE
	SYNTAX    DisplayString
	MAX-ACCESS    read-only
	STATUS    current
    DESCRIPTION  ""
	::= { nnInventoryEntry 10 }

--flightRecorderInfo OBJECT-TYPE
	--SYNTAX    DisplayString
	--MAX-ACCESS    read-only
	--STATUS    current
        --DESCRIPTION  ""
	--:: { nnInventoryEntry 11 }

physicallyPresent OBJECT-TYPE
	SYNTAX    Boolean
	MAX-ACCESS    read-only
	STATUS    current
    DESCRIPTION  ""
	::= { nnInventoryEntry 11 }

restartCard OBJECT-TYPE
	SYNTAX    INTEGER {
	     unknown(0),
		cold(1),
		warm(2)
	}
	MAX-ACCESS    read-write
	STATUS    current
        DESCRIPTION  "1 for cold start, 2 for warm start"
	::= { nnInventoryEntry 12 }

dsmMate OBJECT-TYPE
	SYNTAX    DisplayString(SIZE(0..25))
	MAX-ACCESS    read-only
	STATUS    current
    DESCRIPTION  ""
	::= { nnInventoryEntry 13 }

dsmConn OBJECT-TYPE
	SYNTAX    INTEGER {
	       unknown(0),
		direct(1),
	      indirect(2)
	}
	MAX-ACCESS    read-only
	STATUS    current
    DESCRIPTION  ""
	::= { nnInventoryEntry 14 }

END
