SYNOPTICS-ROOT-MIB DEFINITIONS ::= BEGIN

IMPORTS
	MODULE-IDENTITY, enterprises
		FROM SNMPv2-SMI
	TEXTUAL-CONVENTION
		FROM SNMPv2-TC;

synoptics MODULE-IDENTITY
	LAST-UPDATED "200510110000Z"
	ORGANIZATION 
		"Nortel Networks"
	CONTACT-INFO 
		"Nortel Networks"
	DESCRIPTION 
		"SynOptics Root MIB
		
		            Copyright 1996 - 2004 Nortel Networks, Inc.
		            All rights reserved.
		            This Nortel Networks SNMP Management Information Base Specification
		            (Specification) embodies Nortel Networks' confidential and
		            proprietary intellectual property. Nortel Networks retains all
		            title and ownership in the Specification, including any
		            revisions.
		
		            This Specification is supplied 'AS IS,' and Nortel Networks makes
		            no warranty, either express or implied, as to the use,
		            operation, condition, or performance of the Specification."

	REVISION "200510110000Z"
	DESCRIPTION 
		"Version 218:  Added mMetro3500."

	REVISION "200506130000Z"
	DESCRIPTION 
		"Version 217:  Added mNnVPNGw3070."

	REVISION "200506020000Z"
	DESCRIPTION 
		"Version 216:  Added mSnsa4050."

	REVISION "200504210000Z"
	DESCRIPTION 
		"Version 215:  Added ntwsTrapezeNetworks."

	REVISION "200503150000Z"
	DESCRIPTION 
		"Version 213:  change enumeration labels to reflect rebranding
		                                  of baystack products."

	REVISION "200502140000Z"
	DESCRIPTION 
		"Version 212:  added Nortel WLAN sysObjectID values"

	REVISION "200411230000Z"
	DESCRIPTION 
		"Version 211:  added mMetroESU1850-12G-AC and
		                                  mMetroESU1850-12G-DC"

	REVISION "200410130000Z"
	DESCRIPTION 
		"Version 210:  added support for Outrigger and Dragline."

	REVISION "200407200001Z"
	DESCRIPTION 
		"Version 208:  Fix typo"

	REVISION "200407200000Z"
	DESCRIPTION 
		"Version 207:  Added version number"

	REVISION "200407190000Z"
	DESCRIPTION 
		"Added enum 127 to SnpxChassisType Textual Convention"

	REVISION "200305050000Z"
	DESCRIPTION 
		"v196:  Conversion to SMIv2"
::= { enterprises 45 }


-- 11 October 2005
-- 13 June 2005
-- 06 June 2005
-- 21 Apr 2005
-- 15 Mar 2005
-- 14 Feb 2005
-- 23 Nov 2004
-- 13 Oct 2004
-- 20 Jul 2004
-- 20 Jul 2004
-- 19 Jul 2004
-- 05 May 2003
-- Textual Conventions

SnpxBackplaneType ::= TEXTUAL-CONVENTION
	STATUS     current
	DESCRIPTION 
		""
	SYNTAX  INTEGER {
		other (1),
		eth (2),
		ethTok (3),
		ethFddi (4),
		ethTokFddi (5),
		ethTokRed (6),
		ethTokFddiRed (7),
		tok (8),
		enetTrFastEnet (9),
		enetFastEnet (10),
		enetTrFastEnetRed (11),
		enetFastGigEnet (12)
	}


-- This type is used to specify a concentrator backplane.

SnpxChassisType ::= TEXTUAL-CONVENTION
	STATUS     current
	DESCRIPTION 
		""
	SYNTAX  INTEGER {
		other (1),
		m3000 (2),
		m3030 (3),
		m2310 (4),
		m2810 (5),
		m2912 (6),
		m2914 (7),
		m271x (8),
		m2813 (9),
		m2814 (10),
		m2915 (11),
		m5000 (12),
		m2813SA (13),
		m2814SA (14),
		m810M (15),
		m1032x (16),
		m5005 (17),
		mAlcatelEthConc (18),
		m2715SA (20),
		m2486 (21),
		m28xxx (22),
		m2300x (23),
		m5DN00x (24),
		mBayStackEth (25),
		m2310x (26),
		mBayStack100Hub (27),
		m3000FastEth (28),
		mXediaSwitch (29),
		notUsed (30),
		m28200EthSwitch (31),
		mCent6Slot (32),
		mCent12Slot (33),
		mCent1Slot (34),
		mBayStack301 (35),
		mBayStackTr (36),
		mFVC10625 (37),
		mSwitchNode (38),
		mBayStack302 (39),
		mBayStack350 (40),
		mBayStack150 (41),
		mCent50N3Slot (42),
		mCent50T3Slot (43),
		mBayStack303-304 (44),
		mBayStack200 (45),
		mBayStack250 (46),
		mBayStack450 (48),
		mBayStack410 (49),
		mPassport1200 (50),
		mPassport1250 (51),
		mPassport1100 (52),
		mPassport1150 (53),
		mPassport1050 (54),
		mPassport1051 (55),
		mPassport8610 (56),
		mPassport8606 (57),
		mPassport8010 (58),
		mPassport8006 (59),
		mBayStack670 (60),
		mPassport740 (61),
		mPassport750 (62),
		mPassport790 (63),
		mBPS2000 (64),
		mPassport8110 (65),
		mPassport8106 (66),
		mBayStack3580 (67),
		mBayStack10 (68),
		mBayStack420 (69),
		mMetro1200ESM (70),
		mPassport8010co (71),
		mPassport8610co (72),
		mPassport8110co (73),
		mPassport8003 (74),
		mPassport8603 (75),
		mPassport8103 (76),
		mBayStack380 (77),
		mES470-48T (78),
		mMetro1450ESM (79),
		mMetro1400ESM (80),
		mAlteonSwitch (81),
		mES460-24T-PWR (82),
		mMetro8010 (83),
		mMetro8010co (84),
		mMetro8006 (85),
		mMetro8003 (86),
		mAlteon180e (87),
		mAlteonAD3 (88),
		mAlteon184 (89),
		mAlteonAD4 (90),
		mPassport1424 (91),
		mPassport1648 (92),
		mPassport1612 (93),
		mPassport1624 (94),
		mBayStack380-24F (95),
		mERS5510-24T (96),
		mERS5510-48T (97),
		mES470-24T (98),
		mWLANAccessPoint2220 (99),
		mPassport2402 (100),
		mAlteon2424 (101),
		mAlteon2224 (102),
		mAlteon2208 (103),
		mAlteon2216 (104),
		mAlteon3408 (105),
		mAlteon3416 (106),
		mWLANSecuritySwitch2250 (107),
		mES425-48T (108),
		mES425-24T (109),
		mWLANAccessPoint2221 (110),
		mMetroESU1800-24T (111),
		mMetroESU1800-24T-LX-DC (112),
		mPassport8310 (113),
		mPassport8306 (114),
		mERS5520-24T-PWR (115),
		mERS5520-48T-PWR (116),
		mNnVPNGw3050 (117),
		mAlteonSSL310 (118),
		mAlteonSSL310Fiber (119),
		mAlteonSSL310FIPS (120),
		mAlteonSSL410 (121),
		mAlteonSSL410Fiber (122),
		mAlteonAS2424SSL (123),
		mES325-24T (124),
		mES325-24G (125),
		mWLANAccessPoint2225 (126),
		mWLANSecuritySwitch2270 (127),
		mES470-24T-PWR (128),
		mES470-48T-PWR (129),
		mERS5530-24TFD (130),
		mES3510-24T (131),
		mMetroESU1850-12G-AC (132),
		mMetroESU1850-12G-DC (133),
		mSnas4050 (134),
		mNnVPNGw3070 (135),
		mMetro3500 (136)
	}


-- This type is used to specify a concentrator chassis.
-- Top Branches under "synoptics"

products             OBJECT IDENTIFIER ::= { synoptics 1 }

-- Branches under "products"

series1000           OBJECT IDENTIFIER ::= { products 1 }
s3SnmpAgent          OBJECT IDENTIFIER ::= { products 2 }
series3000           OBJECT IDENTIFIER ::= { products 3 }
superAgent           OBJECT IDENTIFIER ::= { products 4 }
specialTraps         OBJECT IDENTIFIER ::= { products 5 }
series5000           OBJECT IDENTIFIER ::= { products 6 }
lanSwitch            OBJECT IDENTIFIER ::= { products 7 }
snpxRmonExt          OBJECT IDENTIFIER ::= { products 8 }
wirelessLAN          OBJECT IDENTIFIER ::= { products 9 }
powerSupply          OBJECT IDENTIFIER ::= { products 10 }

--  powerSupply moved to 10 because of conflicts

wlan2200             OBJECT IDENTIFIER ::= { products 11 }
temporary            OBJECT IDENTIFIER ::= { synoptics 2 }
registration         OBJECT IDENTIFIER ::= { synoptics 3 }

-- Branches under "temporary"
-- ieee8023	OBJECT IDENTIFIER ::= { temporary 1 }
-- proj1(del)	OBJECT IDENTIFIER ::= { temporary 2 }
-- proj2(sa)	OBJECT IDENTIFIER ::= { temporary 3 }
-- proj3(lc)	OBJECT IDENTIFIER ::= { temporary 4 }
-- proj4(pen)	OBJECT IDENTIFIER ::= { temporary 5 }
-- proj5(phe)	OBJECT IDENTIFIER ::= { temporary 6 }
-- proj6(fddi)	OBJECT IDENTIFIER ::= { temporary 7 }
-- proj7(xo)	OBJECT IDENTIFIER ::= { temporary 8 }
-- Branches under "registration" (values for object sysObjectId)

s3reg-other          OBJECT IDENTIFIER ::= { registration 1 }
s3reg-3000           OBJECT IDENTIFIER ::= { registration 2 }
s3reg-3000-enetNMM   OBJECT IDENTIFIER ::= { s3reg-3000 1 }
s3reg-3000-trNMM     OBJECT IDENTIFIER ::= { s3reg-3000 2 }
s3reg-3000-FDDI-NMM  OBJECT IDENTIFIER ::= { s3reg-3000 3 }
s3reg-3000-FastEthNMM  OBJECT IDENTIFIER ::= { s3reg-3000 4 }
s3reg-3000-ethSwitchNMM  OBJECT IDENTIFIER ::= { s3reg-3000 5 }
s3reg-3030           OBJECT IDENTIFIER ::= { registration 3 }
s3reg-3030-enetNMM   OBJECT IDENTIFIER ::= { s3reg-3030 1 }
s3reg-3030-trNMM     OBJECT IDENTIFIER ::= { s3reg-3030 2 }
s3reg-3030-FDDI-NMM  OBJECT IDENTIFIER ::= { s3reg-3030 3 }
s3reg-3030-ethSwitchNMM  OBJECT IDENTIFIER ::= { s3reg-3030 4 }
s3reg-2310           OBJECT IDENTIFIER ::= { registration 4 }
s3reg-2310-enetNMM   OBJECT IDENTIFIER ::= { s3reg-2310 1 }
s3reg-2310-trNMM     OBJECT IDENTIFIER ::= { s3reg-2310 2 }
s3reg-2310-FDDI-NMM  OBJECT IDENTIFIER ::= { s3reg-2310 3 }
s3reg-332X           OBJECT IDENTIFIER ::= { registration 5 }
s3reg-332XS          OBJECT IDENTIFIER ::= { registration 6 }
s3reg-3356           OBJECT IDENTIFIER ::= { registration 7 }
s3reg-2810           OBJECT IDENTIFIER ::= { registration 8 }
s3reg-2810-enetNMM   OBJECT IDENTIFIER ::= { s3reg-2810 1 }
s3reg-2715           OBJECT IDENTIFIER ::= { registration 9 }
s3reg-2715-trNMM     OBJECT IDENTIFIER ::= { s3reg-2715 1 }
s3reg-291X           OBJECT IDENTIFIER ::= { registration 10 }
s3reg-291X-FDDI-NMM  OBJECT IDENTIFIER ::= { s3reg-291X 1 }
s3reg-3394           OBJECT IDENTIFIER ::= { registration 11 }
s3reg-281X           OBJECT IDENTIFIER ::= { registration 12 }
s3reg-281X-enetNMM   OBJECT IDENTIFIER ::= { s3reg-281X 1 }
s5reg-5000           OBJECT IDENTIFIER ::= { registration 13 }

-- Ethernet NMM in 5000 Chassis

s5reg-5000-ethNMM    OBJECT IDENTIFIER ::= { s5reg-5000 1 }

-- Token Ring NMM in 5000 Chassis

s5reg-5000-tokNMM    OBJECT IDENTIFIER ::= { s5reg-5000 2 }

-- FDDI NMM in 5000 Chassis

s5reg-5000-fddNMM    OBJECT IDENTIFIER ::= { s5reg-5000 3 }

-- ATM NMM in 5000 Chassis

s5reg-5000-atmNMM    OBJECT IDENTIFIER ::= { s5reg-5000 4 }

-- Ethernet Switch NMM in 5000 Chassis

s5reg-5000-ethSwitchNMM  OBJECT IDENTIFIER ::= { s5reg-5000 5 }

-- 10/100 Ethernet NMM in 5000 Chassis

s5reg-5000-ethFastEthNMM  OBJECT IDENTIFIER ::= { s5reg-5000 6 }

-- 10/100 Ethernet Switch NMM in 5000 Chassis

s5reg-5000-eth10-100SwitchNMM  OBJECT IDENTIFIER ::= { s5reg-5000 7 }
s3reg-281XSA         OBJECT IDENTIFIER ::= { registration 14 }
s3reg-281XSA-enetNMM  OBJECT IDENTIFIER ::= { s3reg-281XSA 1 }
lsreg-28xxx          OBJECT IDENTIFIER ::= { registration 15 }
lsreg-28xxx-NMM      OBJECT IDENTIFIER ::= { lsreg-28xxx 1 }
s3reg-8xx            OBJECT IDENTIFIER ::= { registration 16 }
s3reg-810M-enetNMM   OBJECT IDENTIFIER ::= { s3reg-8xx 1 }
s5reg-5005           OBJECT IDENTIFIER ::= { registration 17 }

-- Ethernet NMM in 5005 Chassis

s5reg-5005-ethNMM    OBJECT IDENTIFIER ::= { s5reg-5005 1 }

-- Token Ring NMM in 5005 Chassis

s5reg-5005-tokNMM    OBJECT IDENTIFIER ::= { s5reg-5005 2 }

-- Ethernet Switch NMM in 5005 Chassis

s5reg-5005-ethSwitchNMM  OBJECT IDENTIFIER ::= { s5reg-5005 3 }

-- FDDI NMM in 5005 Chassis

s5reg-5005-fddNMM    OBJECT IDENTIFIER ::= { s5reg-5005 4 }

-- 10/100 Ethernet NMM in 5005 Chassis

s5reg-5005-ethFastEthNMM  OBJECT IDENTIFIER ::= { s5reg-5005 5 }

-- 10/100 Ethernet Switch NMM in 5005 Chassis

s5reg-5005-eth10-100SwitchNMM  OBJECT IDENTIFIER ::= { s5reg-5005 7 }
s3reg-AlcatelConc    OBJECT IDENTIFIER ::= { registration 18 }
s3reg-AlcatelEthConc-enetNMM  OBJECT IDENTIFIER ::= { s3reg-AlcatelConc 1 }
s3reg-271XSA         OBJECT IDENTIFIER ::= { registration 19 }
s3reg-271XSA-trNMM   OBJECT IDENTIFIER ::= { s3reg-271XSA 1 }
ecreg-1032x          OBJECT IDENTIFIER ::= { registration 20 }
s3reg-1032x-NMM      OBJECT IDENTIFIER ::= { ecreg-1032x 1 }
sreg-5DN00x          OBJECT IDENTIFIER ::= { registration 21 }
sreg-5DN00x-EthNMM   OBJECT IDENTIFIER ::= { sreg-5DN00x 1 }
sreg-BayStackEth     OBJECT IDENTIFIER ::= { registration 22 }
sreg-BayStackEth-ethNMM  OBJECT IDENTIFIER ::= { sreg-BayStackEth 1 }
sreg-2300x           OBJECT IDENTIFIER ::= { registration 23 }
sreg-2300x-NMM       OBJECT IDENTIFIER ::= { sreg-2300x 1 }
sreg-2310x           OBJECT IDENTIFIER ::= { registration 24 }
sreg-2310x-NMM       OBJECT IDENTIFIER ::= { sreg-2310x 1 }
sreg-Orion           OBJECT IDENTIFIER ::= { registration 25 }
sreg-Orion-ethNMM    OBJECT IDENTIFIER ::= { sreg-Orion 1 }
sreg-BayStack100Hub  OBJECT IDENTIFIER ::= { registration 26 }
sreg-BayStack100Unit-12Port  OBJECT IDENTIFIER ::= { sreg-BayStack100Hub 1 }
sreg-BayStackTr      OBJECT IDENTIFIER ::= { registration 27 }

-- BayStackTr NMM in a virtual Chassis

sreg-BayStackTr-trNMM  OBJECT IDENTIFIER ::= { sreg-BayStackTr 1 }
lsreg-28200          OBJECT IDENTIFIER ::= { registration 28 }

-- 28200 Ethernet Switch

lsreg-28200-ethSwitchNMM  OBJECT IDENTIFIER ::= { lsreg-28200 1 }
sreg-BayStack302     OBJECT IDENTIFIER ::= { registration 29 }

-- BayStack302 8+1Tx/Fx 10 Mb/s Ethernet Switch 

sreg-BayStack302-9port  OBJECT IDENTIFIER ::= { sreg-BayStack302 1 }
sreg-BayStack350     OBJECT IDENTIFIER ::= { registration 30 }

-- BayStack350 Family 10/100 Adaptive Switches

sreg-BayStack350-ethSwitchNMM  OBJECT IDENTIFIER ::= { sreg-BayStack350 1 }

-- BayStack 350-24T and -12T 10/100/1000 Adaptive Switches

sreg-BayStack350-24T-ethSwitchNMM  OBJECT IDENTIFIER ::= { sreg-BayStack350 2 }
sreg-BayStack150Eth  OBJECT IDENTIFIER ::= { registration 31 }
sreg-BayStack150Eth-ethNMM  OBJECT IDENTIFIER ::= { sreg-BayStack150Eth 1 }
sreg-BayStack303-304  OBJECT IDENTIFIER ::= { registration 32 }

-- 12-24 10mb 1 100mb with MDA Switch

sreg-BayStack303-304-Sw  OBJECT IDENTIFIER ::= { sreg-BayStack303-304 1 }

-- 24 10mb 1 100mb with 2 MDA Switch

sreg-BayStack303-24T-Sw  OBJECT IDENTIFIER ::= { sreg-BayStack303-304 2 }
sreg-BayStack200Eth  OBJECT IDENTIFIER ::= { registration 33 }

-- BayStack200 Ethernet Hub

sreg-BayStack200Eth-ethNMM  OBJECT IDENTIFIER ::= { sreg-BayStack200Eth 1 }
sreg-BayStack250Eth  OBJECT IDENTIFIER ::= { registration 34 }

-- BayStack250 10/100 Ethernet Hub

sreg-BayStack250Eth-ethNMM  OBJECT IDENTIFIER ::= { sreg-BayStack250Eth 1 }
sreg-BayStack450     OBJECT IDENTIFIER ::= { registration 35 }

-- BayStack450 10/100/1000 Ethernet Switch

sreg-BayStack450-ethSwitchNMM  OBJECT IDENTIFIER ::= { sreg-BayStack450 1 }
sreg-BayStack410     OBJECT IDENTIFIER ::= { registration 36 }

-- BayStack 410-24T 10/100 Adaptive Switches

sreg-BayStack410-24T-ethSwitchNMM  OBJECT IDENTIFIER ::= { sreg-BayStack410 1 }
sreg-BayStackICS     OBJECT IDENTIFIER ::= { registration 37 }

-- BayStack Integrated Communication Server

sreg-BayStackICS-NMM  OBJECT IDENTIFIER ::= { sreg-BayStackICS 1 }
s5reg-Accelar8010    OBJECT IDENTIFIER ::= { registration 38 }

-- Ethernet Switch 32 port in 8010 Chassis

s5reg-Accelar8132TX  OBJECT IDENTIFIER ::= { s5reg-Accelar8010 1 }

-- Ethernet Switch 48 port in 8010 Chassis

s5reg-Accelar8148TX  OBJECT IDENTIFIER ::= { s5reg-Accelar8010 2 }
sreg-BayStack670     OBJECT IDENTIFIER ::= { registration 39 }

-- BayStack 670 11Mb/s wireless access point

sreg-BayStack670-wirelessLAN  OBJECT IDENTIFIER ::= { sreg-BayStack670 1 }
sreg-BPS2000         OBJECT IDENTIFIER ::= { registration 40 }

-- BPS 2000-24T 10/100 Switches

sreg-BPS2000-24T-ethSwitchNMM  OBJECT IDENTIFIER ::= { sreg-BPS2000 1 }
sreg-BayStack3580    OBJECT IDENTIFIER ::= { registration 41 }

-- BayStack 3580-16F Gigabit Switch

sreg-BayStack3580-16F-gigEthSwitch  OBJECT IDENTIFIER ::= { sreg-BayStack3580 1 }
sreg-BayStack10      OBJECT IDENTIFIER ::= { registration 42 }

-- BayStack 10 Power Supply Unit

sreg-BayStack10-powerSupplyUnit  OBJECT IDENTIFIER ::= { sreg-BayStack10 1 }
sreg-BayStack420     OBJECT IDENTIFIER ::= { registration 43 }

-- BayStack 420-24T 10/100 Switch

sreg-BayStack420-24T-ethSwitchNMM  OBJECT IDENTIFIER ::= { sreg-BayStack420 1 }
sreg-Metro1200ESM    OBJECT IDENTIFIER ::= { registration 44 }

-- OPTera Metro 1200 Ethernet Service Module

sreg-Metro1200ESM-12T-ethSwitchNMM  OBJECT IDENTIFIER ::= { sreg-Metro1200ESM 1 }
sreg-BayStack380     OBJECT IDENTIFIER ::= { registration 45 }

-- BayStack 380-24T Switch 10/100/1000 Switch

sreg-BayStack380-24T-ethSwitchNMM  OBJECT IDENTIFIER ::= { sreg-BayStack380 1 }
sreg-BayStack470     OBJECT IDENTIFIER ::= { registration 46 }

-- BayStack 470-48T Switch 10/100 Switch

sreg-BayStack470-48T-ethSwitchNMM  OBJECT IDENTIFIER ::= { sreg-BayStack470 1 }
sreg-Metro1450ESM    OBJECT IDENTIFIER ::= { registration 47 }

-- OPTera Metro 1450 Ethernet Service Module

sreg-Metro1450ESM-12T2GBIC-ethSwitchNMM  OBJECT IDENTIFIER ::= { sreg-Metro1450ESM 1 }
sreg-Metro1400ESM    OBJECT IDENTIFIER ::= { registration 48 }

-- OPTera Metro 1400 Ethernet Service Module

sreg-Metro1400ESM-12T2GBIC-ethSwitchNMM  OBJECT IDENTIFIER ::= { sreg-Metro1400ESM 1 }
sreg-BayStack460-24T-PWR  OBJECT IDENTIFIER ::= { registration 49 }

-- BayStack 460-24T-PWR

sreg-BayStack460-24T-PWR-ethSwitchNMM  OBJECT IDENTIFIER ::= { sreg-BayStack460-24T-PWR 1 }
sreg-Metro8000       OBJECT IDENTIFIER ::= { registration 50 }

-- OPTera Metro 8000 4 Ports Open Protocol Module

sreg-Metro8000-8664GB-OPM  OBJECT IDENTIFIER ::= { sreg-Metro8000 1 }
sreg-BayStack380-24F  OBJECT IDENTIFIER ::= { registration 51 }

-- BayStack 380-24F Switch 1000 Fiber Switch

sreg-BayStack380-24F-ethSwitchNMM  OBJECT IDENTIFIER ::= { sreg-BayStack380-24F 1 }
sreg-BayStack5510-24T  OBJECT IDENTIFIER ::= { registration 52 }

-- BayStack 5510-24T

sreg-BayStack5510-24T-ethSwitchNMM  OBJECT IDENTIFIER ::= { sreg-BayStack5510-24T 1 }
sreg-BayStack5510-48T  OBJECT IDENTIFIER ::= { registration 53 }

-- BayStack 5510-48T

sreg-BayStack5510-48T-ethSwitchNMM  OBJECT IDENTIFIER ::= { sreg-BayStack5510-48T 1 }
sreg-BayStack470-24T  OBJECT IDENTIFIER ::= { registration 54 }

-- BayStack 470-24T Switch 10/100 Switch

sreg-BayStack470-24T-ethSwitchNMM  OBJECT IDENTIFIER ::= { sreg-BayStack470-24T 1 }

-- Nortel Networks Wireless LAN Access Point 2220

sreg-WLANAccessPoint2220  OBJECT IDENTIFIER ::= { registration 55 }
sreg-WLANAccessPoint2220-wirelessAP  OBJECT IDENTIFIER ::= { sreg-WLANAccessPoint2220 1 }

-- Nortel Networks Wireless LAN Security Switch 2250

sreg-WLANSecuritySwitch2250  OBJECT IDENTIFIER ::= { registration 56 }

-- Nortel Networks BayStack 425, 48 and 24 port devices

sreg-BayStack425     OBJECT IDENTIFIER ::= { registration 57 }
sreg-BayStack425-48T  OBJECT IDENTIFIER ::= { sreg-BayStack425 1 }
sreg-BayStack425-24T  OBJECT IDENTIFIER ::= { sreg-BayStack425 2 }

-- Nortel Networks Wireless LAN Access Point 2221

sreg-WLANAccessPoint2221  OBJECT IDENTIFIER ::= { registration 58 }
sreg-WLANAccessPoint2221-wirelessAP  OBJECT IDENTIFIER ::= { sreg-WLANAccessPoint2221 1 }
sreg-BayStack5520    OBJECT IDENTIFIER ::= { registration 59 }
sreg-BayStack5520-24T-PWR  OBJECT IDENTIFIER ::= { sreg-BayStack5520 1 }
sreg-BayStack5520-48T-PWR  OBJECT IDENTIFIER ::= { sreg-BayStack5520 2 }

-- Nortel Networks WLAN Security Siwtch 2270

sreg-WLANSecuritySwitch  OBJECT IDENTIFIER ::= { registration 60 }
sreg-WLANSecuritySwitch2270  OBJECT IDENTIFIER ::= { sreg-WLANSecuritySwitch 1 }

-- Nortel Networks BayStack 325

sreg-BayStack325     OBJECT IDENTIFIER ::= { registration 61 }
sreg-BayStack325-24T  OBJECT IDENTIFIER ::= { sreg-BayStack325 1 }
sreg-BayStack325-24G  OBJECT IDENTIFIER ::= { sreg-BayStack325 2 }

-- Nortel Networks Wireless LAN Access Point 2225

sreg-WLANAccessPoint2225  OBJECT IDENTIFIER ::= { registration 62 }
sreg-WLANAccessPoint2225-wirelessAP  OBJECT IDENTIFIER ::= { sreg-WLANAccessPoint2225 1 }
sreg-BayStack470-24T-PWR  OBJECT IDENTIFIER ::= { registration 63 }

-- BayStack 470-24T-PWR Switch 10/100 Switch

sreg-BayStack470-24T-PWR-ethSwitchNMM  OBJECT IDENTIFIER ::= { sreg-BayStack470-24T-PWR 1 }
sreg-BayStack470-48T-PWR  OBJECT IDENTIFIER ::= { registration 64 }

-- BayStack 470-48T-PWR Switch 10/100 Switch

sreg-BayStack470-48T-PWR-ethSwitchNMM  OBJECT IDENTIFIER ::= { sreg-BayStack470-48T-PWR 1 }

-- Ethernet Routing Switch 5530-24TFD

sreg-EthernetRoutingSwitch5530-24TFD  OBJECT IDENTIFIER ::= { registration 65 }

-- Ethernet Switch 3510-24T

sreg-EthernetSwitch3510-24T  OBJECT IDENTIFIER ::= { registration 66 }

-- Nortel WLAN

sreg-NortelWLAN      OBJECT IDENTIFIER ::= { registration 67 }
sreg-NortelWLAN2350  OBJECT IDENTIFIER ::= { sreg-NortelWLAN 1 }
sreg-NortelWLAN2360  OBJECT IDENTIFIER ::= { sreg-NortelWLAN 2 }
sreg-NortelWLAN2361  OBJECT IDENTIFIER ::= { sreg-NortelWLAN 3 }
sreg-NortelWLAN2370  OBJECT IDENTIFIER ::= { sreg-NortelWLAN 4 }
sreg-NortelWLAN2380  OBJECT IDENTIFIER ::= { sreg-NortelWLAN 5 }
policy               OBJECT IDENTIFIER ::= { synoptics 4 }
bayStackMibs         OBJECT IDENTIFIER ::= { synoptics 5 }
ntwsTrapezeNetworks  OBJECT IDENTIFIER ::= { synoptics 6 }

END
