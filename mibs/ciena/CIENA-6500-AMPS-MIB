CIENA-6500-AMPS-MIB DEFINITIONS ::= BEGIN

IMPORTS
    Ampmode, Amppkmode, Flatmode, Forcedshutoff, Gainmode, Refbw
        FROM CIENA-6500-ENUMS-MIB
    Aid, Decimal, Int, String, Time
        FROM CIENA-6500-TYPES-MIB
    cienaGenericMIBs
        FROM CIENA-SMI
    MODULE-COMPLIANCE, OBJECT-GROUP
        FROM SNMPv2-CONF
    Integer32, MODULE-IDENTITY, OBJECT-TYPE
        FROM SNMPv2-SMI;

ciena6500AmpsMIB MODULE-IDENTITY
    LAST-UPDATED "201812310000Z"
    ORGANIZATION "Ciena Corporation"
    CONTACT-INFO "Web URL: http://www.ciena.com"
    DESCRIPTION "This modules describes Ciena's amps object for the 6500 platform"
    REVISION "201812310000Z"
    DESCRIPTION "Initial Draft"
    ::= { cienaGenericMIBs 200 }

c6500AmpsAmpsAmpTable OBJECT-TYPE
    SYNTAX SEQUENCE OF C6500AmpsAmpsAmpEntry
    MAX-ACCESS not-accessible
    STATUS current
    DESCRIPTION "None"
    ::= { ciena6500AmpsMIB 3 }

c6500AmpsAmpsAmpEntry OBJECT-TYPE
    SYNTAX C6500AmpsAmpsAmpEntry
    MAX-ACCESS not-accessible
    STATUS current
    DESCRIPTION "Entry for c6500AmpsAmpsAmpTable."
    INDEX { c6500AmpsAmpsAmpAmp }
    ::= { c6500AmpsAmpsAmpTable 1 }

C6500AmpsAmpsAmpEntry ::= SEQUENCE { 
    c6500AmpsAmpsAmpAmp OCTET STRING,
    c6500AmpsAmpsAmpAmpMode Ampmode,
    c6500AmpsAmpsAmpGainMode Gainmode,
    c6500AmpsAmpsAmpAmpPeakMode Amppkmode,
    c6500AmpsAmpsAmpTargGain OCTET STRING,
    c6500AmpsAmpsAmpTargPow OCTET STRING,
    c6500AmpsAmpsAmpTargPeakPow OCTET STRING,
    c6500AmpsAmpsAmpTargGainTilt Decimal,
    c6500AmpsAmpsAmpShutoffThresh OCTET STRING,
    c6500AmpsAmpsAmpInputLoss Decimal,
    c6500AmpsAmpsAmpOutputLoss OCTET STRING,
    c6500AmpsAmpsAmpInputLosThres String,
    c6500AmpsAmpsAmpOutputLosThres String,
    c6500AmpsAmpsAmpForcedShutoff Forcedshutoff,
    c6500AmpsAmpsAmpDropTargGain OCTET STRING,
    c6500AmpsAmpsAmpTopOffset String,
    c6500AmpsAmpsAmpAlsoDisabled INTEGER,
    c6500AmpsAmpsAmpGainOffset String,
    c6500AmpsAmpsAmpRefBw Refbw,
    c6500AmpsAmpsAmpPst INTEGER,
    c6500AmpsAmpsAmpFlatMode Flatmode,
    c6500AmpsAmpsAmpGain Decimal,
    c6500AmpsAmpsAmpMaxTargPow String,
    c6500AmpsAmpsAmpAinsTimeLeft Time,
    c6500AmpsAmpsAmpPathId Int,
    c6500AmpsAmpsAmpInputOvrldThres Decimal,
    c6500AmpsAmpsAmpAprThres Decimal 
}

c6500AmpsAmpsAmpAmp OBJECT-TYPE
    SYNTAX OCTET STRING(SIZE(1..80))
    MAX-ACCESS not-accessible
    STATUS current
    DESCRIPTION "AID in format AMP-shelf-slot-port, AMP-shelf-slot-portSsubport, AMP-shelf-slotSsubslot-portSsubport, AMP-shelf-ALL, AMP-shelf-slot-ALL, AMP-shelf-slotSsubslot-ALL, SHELF-shelf-ALL"
    ::= { c6500AmpsAmpsAmpEntry 1 }

c6500AmpsAmpsAmpAmpMode OBJECT-TYPE
    SYNTAX Ampmode
    MAX-ACCESS read-only
    STATUS current
    DESCRIPTION "Control Mode of the AMP."
    ::= { c6500AmpsAmpsAmpEntry 2 }

c6500AmpsAmpsAmpGainMode OBJECT-TYPE
    SYNTAX Gainmode
    MAX-ACCESS read-only
    STATUS current
    DESCRIPTION "Gain Mode of the AMP."
    ::= { c6500AmpsAmpsAmpEntry 3 }

c6500AmpsAmpsAmpAmpPeakMode OBJECT-TYPE
    SYNTAX Amppkmode
    MAX-ACCESS read-only
    STATUS current
    DESCRIPTION "Peak Power Control State of the AMP. This is only applicable to the line AMPs."
    ::= { c6500AmpsAmpsAmpEntry 4 }

c6500AmpsAmpsAmpTargGain OBJECT-TYPE
    SYNTAX OCTET STRING(SIZE(1..128))
    MAX-ACCESS read-only
    STATUS current
    DESCRIPTION "Target Gain in dB."
    ::= { c6500AmpsAmpsAmpEntry 5 }

c6500AmpsAmpsAmpTargPow OBJECT-TYPE
    SYNTAX OCTET STRING(SIZE(1..128))
    MAX-ACCESS read-only
    STATUS current
    DESCRIPTION "Target Total Power in dBm."
    ::= { c6500AmpsAmpsAmpEntry 6 }

c6500AmpsAmpsAmpTargPeakPow OBJECT-TYPE
    SYNTAX OCTET STRING(SIZE(1..128))
    MAX-ACCESS read-only
    STATUS current
    DESCRIPTION "Target peak Power in dBm. This is only applicable to the line AMPs."
    ::= { c6500AmpsAmpsAmpEntry 7 }

c6500AmpsAmpsAmpTargGainTilt OBJECT-TYPE
    SYNTAX Decimal
    MAX-ACCESS read-only
    STATUS current
    DESCRIPTION "Gain tilt in dB."
    ::= { c6500AmpsAmpsAmpEntry 8 }

c6500AmpsAmpsAmpShutoffThresh OBJECT-TYPE
    SYNTAX OCTET STRING(SIZE(1..128))
    MAX-ACCESS read-only
    STATUS current
    DESCRIPTION "Shutoff Threshold in dBm."
    ::= { c6500AmpsAmpsAmpEntry 9 }

c6500AmpsAmpsAmpInputLoss OBJECT-TYPE
    SYNTAX Decimal
    MAX-ACCESS read-only
    STATUS current
    DESCRIPTION "Input connector loss in dB. This is only applicable to the line AMPs."
    ::= { c6500AmpsAmpsAmpEntry 10 }

c6500AmpsAmpsAmpOutputLoss OBJECT-TYPE
    SYNTAX OCTET STRING(SIZE(1..128))
    MAX-ACCESS read-only
    STATUS current
    DESCRIPTION "Ouput connector loss in dB. This is only applicable to the line AMPs."
    ::= { c6500AmpsAmpsAmpEntry 11 }

c6500AmpsAmpsAmpInputLosThres OBJECT-TYPE
    SYNTAX String
    MAX-ACCESS read-only
    STATUS current
    DESCRIPTION "Input LOS Threshold"
    ::= { c6500AmpsAmpsAmpEntry 12 }

c6500AmpsAmpsAmpOutputLosThres OBJECT-TYPE
    SYNTAX String
    MAX-ACCESS read-only
    STATUS current
    DESCRIPTION "Output LOS Threshold"
    ::= { c6500AmpsAmpsAmpEntry 13 }

c6500AmpsAmpsAmpForcedShutoff OBJECT-TYPE
    SYNTAX Forcedshutoff
    MAX-ACCESS read-only
    STATUS current
    DESCRIPTION "Forced EDFA Shutoff State"
    ::= { c6500AmpsAmpsAmpEntry 14 }

c6500AmpsAmpsAmpDropTargGain OBJECT-TYPE
    SYNTAX OCTET STRING(SIZE(1..128))
    MAX-ACCESS read-only
    STATUS current
    DESCRIPTION "Drop Target Gain in dB."
    ::= { c6500AmpsAmpsAmpEntry 15 }

c6500AmpsAmpsAmpTopOffset OBJECT-TYPE
    SYNTAX String
    MAX-ACCESS read-only
    STATUS current
    DESCRIPTION " Offset of the Total Output Power for the EDFA"
    ::= { c6500AmpsAmpsAmpEntry 16 }

c6500AmpsAmpsAmpAlsoDisabled OBJECT-TYPE
    SYNTAX INTEGER { true(0), false(1) }
    MAX-ACCESS read-only
    STATUS current
    DESCRIPTION "Disable EDFA Shutoff State"
    ::= { c6500AmpsAmpsAmpEntry 17 }

c6500AmpsAmpsAmpGainOffset OBJECT-TYPE
    SYNTAX String
    MAX-ACCESS read-only
    STATUS current
    DESCRIPTION "Gain Offset of the AMP"
    ::= { c6500AmpsAmpsAmpEntry 18 }

c6500AmpsAmpsAmpRefBw OBJECT-TYPE
    SYNTAX Refbw
    MAX-ACCESS read-only
    STATUS current
    DESCRIPTION "Reference Bandwidth which refers to the frame of reference for TARGPKPOW value."
    ::= { c6500AmpsAmpsAmpEntry 19 }

c6500AmpsAmpsAmpPst OBJECT-TYPE
    SYNTAX INTEGER { is(0), oosMa(1), isAnr(2), oosAu(3), oosAuma(4), oosMaanr(5) }
    MAX-ACCESS read-only
    STATUS current
    DESCRIPTION "Identify the primary state"
    ::= { c6500AmpsAmpsAmpEntry 20 }

c6500AmpsAmpsAmpFlatMode OBJECT-TYPE
    SYNTAX Flatmode
    MAX-ACCESS read-only
    STATUS current
    DESCRIPTION "Flat Mode"
    ::= { c6500AmpsAmpsAmpEntry 21 }

c6500AmpsAmpsAmpGain OBJECT-TYPE
    SYNTAX Decimal
    MAX-ACCESS read-only
    STATUS current
    DESCRIPTION "The current gain of the amplifier."
    ::= { c6500AmpsAmpsAmpEntry 22 }

c6500AmpsAmpsAmpMaxTargPow OBJECT-TYPE
    SYNTAX String
    MAX-ACCESS read-only
    STATUS current
    DESCRIPTION "Maximum Target Power in dBm."
    ::= { c6500AmpsAmpsAmpEntry 23 }

c6500AmpsAmpsAmpAinsTimeLeft OBJECT-TYPE
    SYNTAX Time
    MAX-ACCESS read-only
    STATUS current
    DESCRIPTION "The format will be HH-MM for the time left in AINS timeout."
    ::= { c6500AmpsAmpsAmpEntry 24 }

c6500AmpsAmpsAmpPathId OBJECT-TYPE
    SYNTAX Int
    MAX-ACCESS read-only
    STATUS current
    DESCRIPTION "TX Path ID value"
    ::= { c6500AmpsAmpsAmpEntry 25 }

c6500AmpsAmpsAmpInputOvrldThres OBJECT-TYPE
    SYNTAX Decimal
    MAX-ACCESS read-only
    STATUS current
    DESCRIPTION "Input Overload Threshold in dBm."
    ::= { c6500AmpsAmpsAmpEntry 26 }

c6500AmpsAmpsAmpAprThres OBJECT-TYPE
    SYNTAX Decimal
    MAX-ACCESS read-only
    STATUS current
    DESCRIPTION "Automatic Power Reduction in dB"
    ::= { c6500AmpsAmpsAmpEntry 27 }

c6500AmpsAmpsAmpSstTable OBJECT-TYPE
    SYNTAX SEQUENCE OF C6500AmpsAmpsAmpSstEntry
    MAX-ACCESS not-accessible
    STATUS current
    DESCRIPTION "Identify the secondary state"
    ::= { ciena6500AmpsMIB 4 }

c6500AmpsAmpsAmpSstEntry OBJECT-TYPE
    SYNTAX C6500AmpsAmpsAmpSstEntry
    MAX-ACCESS not-accessible
    STATUS current
    DESCRIPTION "Entry for c6500AmpsAmpsAmpSstTable."
    INDEX { c6500AmpsAmpsAmpSstAmpAmp, c6500AmpsAmpsAmpSstTableSnmpKey }
    ::= { c6500AmpsAmpsAmpSstTable 1 }

C6500AmpsAmpsAmpSstEntry ::= SEQUENCE { 
    c6500AmpsAmpsAmpSstAmpAmp OCTET STRING,
    c6500AmpsAmpsAmpSstTableSnmpKey Integer32,
    c6500AmpsAmpsAmpSst INTEGER 
}

c6500AmpsAmpsAmpSstAmpAmp OBJECT-TYPE
    SYNTAX OCTET STRING(SIZE(1..80))
    MAX-ACCESS not-accessible
    STATUS current
    DESCRIPTION "AID in format AMP-shelf-slot-port, AMP-shelf-slot-portSsubport, AMP-shelf-slotSsubslot-portSsubport, AMP-shelf-ALL, AMP-shelf-slot-ALL, AMP-shelf-slotSsubslot-ALL, SHELF-shelf-ALL"
    ::= { c6500AmpsAmpsAmpSstEntry 1 }

c6500AmpsAmpsAmpSstTableSnmpKey OBJECT-TYPE
    SYNTAX Integer32(0..2147483647)
    MAX-ACCESS not-accessible
    STATUS current
    DESCRIPTION "Unique key for c6500AmpsAmpsAmpSst"
    ::= { c6500AmpsAmpsAmpSstEntry 2 }

c6500AmpsAmpsAmpSst OBJECT-TYPE
    SYNTAX INTEGER { ains(0), ainsDea(1), bridged(2), switched(3), roll(4), act(5), idle(6), stbys(7), wrk(8), erranl(9), psi(10), flt(11), mea(12), tstf(13), ueq(14), sgeo(15), discd(16), lpbk(17), ts(18), faf(19), stbyh(20), wrkrx(21), wrktx(22), prtcl(23), uas(24), nosite(25), noam(26), mon(27), msc(28), protected(29), mt(30), dsbld(31), inhip(32), l2dsbld(33), tsgen(34), tsmon(35), tsrecirc(36) }
    MAX-ACCESS read-only
    STATUS current
    DESCRIPTION "Identify the secondary state"
    ::= { c6500AmpsAmpsAmpSstEntry 3 }



-- Conformance statements
ciena6500AmpsObjects OBJECT IDENTIFIER
    ::= { ciena6500AmpsMIB 1 }

ciena6500AmpsConformance OBJECT IDENTIFIER
    ::= { ciena6500AmpsMIB 2 }

ciena6500AmpsGroups OBJECT IDENTIFIER
    ::= { ciena6500AmpsConformance 1 }

ciena6500AmpsGroup OBJECT-GROUP
    OBJECTS { 
        c6500AmpsAmpsAmpAmpMode,
        c6500AmpsAmpsAmpGainMode,
        c6500AmpsAmpsAmpAmpPeakMode,
        c6500AmpsAmpsAmpTargGain,
        c6500AmpsAmpsAmpTargPow,
        c6500AmpsAmpsAmpTargPeakPow,
        c6500AmpsAmpsAmpTargGainTilt,
        c6500AmpsAmpsAmpShutoffThresh,
        c6500AmpsAmpsAmpInputLoss,
        c6500AmpsAmpsAmpOutputLoss,
        c6500AmpsAmpsAmpInputLosThres,
        c6500AmpsAmpsAmpOutputLosThres,
        c6500AmpsAmpsAmpForcedShutoff,
        c6500AmpsAmpsAmpDropTargGain,
        c6500AmpsAmpsAmpTopOffset,
        c6500AmpsAmpsAmpAlsoDisabled,
        c6500AmpsAmpsAmpGainOffset,
        c6500AmpsAmpsAmpRefBw,
        c6500AmpsAmpsAmpPst,
        c6500AmpsAmpsAmpFlatMode,
        c6500AmpsAmpsAmpGain,
        c6500AmpsAmpsAmpMaxTargPow,
        c6500AmpsAmpsAmpAinsTimeLeft,
        c6500AmpsAmpsAmpPathId,
        c6500AmpsAmpsAmpInputOvrldThres,
        c6500AmpsAmpsAmpAprThres
    }
    STATUS current
    DESCRIPTION "Conformance Group"
    ::= { ciena6500AmpsGroups 1 }

ciena6500AmpsCompliances OBJECT IDENTIFIER
    ::= { ciena6500AmpsConformance 2 }

ciena6500AmpsCompliance MODULE-COMPLIANCE
    STATUS current
    DESCRIPTION "Compliance"
    MODULE MANDATORY-GROUPS { ciena6500AmpsGroup }
    ::= { ciena6500AmpsCompliances 1 }

END -- End module
