-- This file was automatically generated from ciena-6500-line-diag.yang. Do not edit.

CIENA-6500-LINE-DIAG-MIB DEFINITIONS ::= BEGIN

IMPORTS
    AdjFiber, Otdrtracestatus, PstfacRtrv, Sstfac, TraceType
        FROM CIENA-6500-ENUMS-MIB
    Aid, Int, String, Time
        FROM CIENA-6500-TYPES-MIB
    cienaGenericMIBs
        FROM CIENA-SMI
    MODULE-COMPLIANCE, OBJECT-GROUP
        FROM SNMPv2-CONF
    Integer32, MODULE-IDENTITY, OBJECT-TYPE
        FROM SNMPv2-SMI;

ciena6500LineDiagMIB MODULE-IDENTITY
    LAST-UPDATED "210001010000Z"
    ORGANIZATION "Ciena Corporation"
    CONTACT-INFO "Web URL: http://www.ciena.com"
    DESCRIPTION "This modules describes Ciena's line-diag object for the 6500 platform"
    REVISION "201812310000Z"
    DESCRIPTION "Initial Draft"
    REVISION "210001010000Z"
    DESCRIPTION "6500 Release 12.21 
  rpc line-diag-show-otdr-trace
    output
      list output
        leaf byte-stream
        - Changed type from ciena-6500-types:STRING to string
          type string
          - Added length: 0..128 
  container line-diag
    container otdr
      list trace
        leaf byte-stream
        - Changed type from ciena-6500-types:STRING to string
          type string
          - Added length: 0..128 "
    REVISION "210001010000Z"
    DESCRIPTION "6500 Release  
  container line-diag
    list telemetry
    - Removed leaf-list: fiber-type
    - Removed leaf-list: disc-fiber-type
    - Removed leaf: measure-time
    - Removed leaf: pulse-rate-short
    - Removed leaf: distance-short
    - Removed leaf: pulse-rate-long
    - Removed leaf: distance-long
    - Removed leaf: loss-single
    - Removed leaf: loss-all
    - Removed leaf: reflection-single
    - Removed leaf: reflection-all
    - Removed leaf: total-fiber-loss
    - Removed leaf: fiber-loss
    - Removed leaf: total-reflection
    - Removed leaf: total-loss
    list config
    - Added leaf: fiber-length
    - Added leaf: fiber-dispersion
    list events
    - Added leaf: reflection-value
    - Added leaf: loss-value
    - Added leaf: effective-loss-value
    - Added leaf: loss-threshold
    - Added leaf: reflection-threshold
    - Added leaf: result
  rpc line-diag-start-otdr-trace
    input
    - Added leaf: fbr-disp
    - Added leaf: handshake
  rpc line-diag-stop-otdr-trace
    input
      leaf trace-type
      - Changed type from enumeration to ciena-6500-enums:trace_type
  rpc line-diag-show-events
    output
      list output
      - Added key: otdrcfg 
      - Added leaf: reflection-value
      - Added leaf: loss-value
      - Added leaf: effective-loss-value
      - Added leaf: loss-threshold
      - Added leaf: reflection-threshold
      - Added leaf: result"
    ::= { cienaGenericMIBs 203 }

c6500LineDiagLineDiagOtdrTraceTable OBJECT-TYPE
    SYNTAX SEQUENCE OF C6500LineDiagLineDiagOtdrTraceEntry
    MAX-ACCESS not-accessible
    STATUS current
    DESCRIPTION "None"
    ::= { ciena6500LineDiagMIB 3 }

c6500LineDiagLineDiagOtdrTraceEntry OBJECT-TYPE
    SYNTAX C6500LineDiagLineDiagOtdrTraceEntry
    MAX-ACCESS not-accessible
    STATUS current
    DESCRIPTION "Entry for c6500LineDiagLineDiagOtdrTraceTable."
    INDEX { c6500LineDiagLineDiagOtdrTraceOtdrcfg }
    ::= { c6500LineDiagLineDiagOtdrTraceTable 1 }

C6500LineDiagLineDiagOtdrTraceEntry ::= SEQUENCE { 
    c6500LineDiagLineDiagOtdrTraceOtdrcfg OCTET STRING,
    c6500LineDiagLineDiagOtdrTraceByteStream OCTET STRING 
}

c6500LineDiagLineDiagOtdrTraceOtdrcfg OBJECT-TYPE
    SYNTAX OCTET STRING(SIZE(1..80))
    MAX-ACCESS not-accessible
    STATUS current
    DESCRIPTION "AID in format OTDRCFG-shelf-slot-port"
    ::= { c6500LineDiagLineDiagOtdrTraceEntry 1 }

c6500LineDiagLineDiagOtdrTraceByteStream OBJECT-TYPE
    SYNTAX OCTET STRING(SIZE(0..128))
    MAX-ACCESS read-only
    STATUS current
    DESCRIPTION "SOR file as a byte stream in TL1"
    ::= { c6500LineDiagLineDiagOtdrTraceEntry 2 }

c6500LineDiagLineDiagOtdrTracesTable OBJECT-TYPE
    SYNTAX SEQUENCE OF C6500LineDiagLineDiagOtdrTracesEntry
    MAX-ACCESS not-accessible
    STATUS current
    DESCRIPTION "None"
    ::= { ciena6500LineDiagMIB 4 }

c6500LineDiagLineDiagOtdrTracesEntry OBJECT-TYPE
    SYNTAX C6500LineDiagLineDiagOtdrTracesEntry
    MAX-ACCESS not-accessible
    STATUS current
    DESCRIPTION "Entry for c6500LineDiagLineDiagOtdrTracesTable."
    INDEX { c6500LineDiagLineDiagOtdrTracesOtdrcfg }
    ::= { c6500LineDiagLineDiagOtdrTracesTable 1 }

C6500LineDiagLineDiagOtdrTracesEntry ::= SEQUENCE { 
    c6500LineDiagLineDiagOtdrTracesOtdrcfg OCTET STRING,
    c6500LineDiagLineDiagOtdrTracesFileName String,
    c6500LineDiagLineDiagOtdrTracesTraceTag INTEGER,
    c6500LineDiagLineDiagOtdrTracesTraceType TraceType 
}

c6500LineDiagLineDiagOtdrTracesOtdrcfg OBJECT-TYPE
    SYNTAX OCTET STRING(SIZE(1..80))
    MAX-ACCESS not-accessible
    STATUS current
    DESCRIPTION "AID in format OTDRCFG-shelf-slot-port"
    ::= { c6500LineDiagLineDiagOtdrTracesEntry 1 }

c6500LineDiagLineDiagOtdrTracesFileName OBJECT-TYPE
    SYNTAX String
    MAX-ACCESS read-only
    STATUS current
    DESCRIPTION "The name of the SOR file"
    ::= { c6500LineDiagLineDiagOtdrTracesEntry 2 }

c6500LineDiagLineDiagOtdrTracesTraceTag OBJECT-TYPE
    SYNTAX INTEGER { bsln(0), current(1) }
    MAX-ACCESS read-only
    STATUS current
    DESCRIPTION "The tag of the SOR (Standard OTDR Record) file: CURRENT or BASELINE"
    ::= { c6500LineDiagLineDiagOtdrTracesEntry 3 }

c6500LineDiagLineDiagOtdrTracesTraceType OBJECT-TYPE
    SYNTAX TraceType
    MAX-ACCESS read-only
    STATUS current
    DESCRIPTION "The type of trace to be measured"
    ::= { c6500LineDiagLineDiagOtdrTracesEntry 4 }

c6500LineDiagLineDiagTelemetryTable OBJECT-TYPE
    SYNTAX SEQUENCE OF C6500LineDiagLineDiagTelemetryEntry
    MAX-ACCESS not-accessible
    STATUS current
    DESCRIPTION "None"
    ::= { ciena6500LineDiagMIB 5 }

c6500LineDiagLineDiagTelemetryEntry OBJECT-TYPE
    SYNTAX C6500LineDiagLineDiagTelemetryEntry
    MAX-ACCESS not-accessible
    STATUS current
    DESCRIPTION "Entry for c6500LineDiagLineDiagTelemetryTable."
    INDEX { c6500LineDiagLineDiagTelemetryTelemetry }
    ::= { c6500LineDiagLineDiagTelemetryTable 1 }

C6500LineDiagLineDiagTelemetryEntry ::= SEQUENCE { 
    c6500LineDiagLineDiagTelemetryTelemetry OCTET STRING,
    c6500LineDiagLineDiagTelemetryLosThresh String,
    c6500LineDiagLineDiagTelemetryTargTelemPower String,
    c6500LineDiagLineDiagTelemetryMode INTEGER,
    c6500LineDiagLineDiagTelemetrySignalPower String,
    c6500LineDiagLineDiagTelemetryRxPwr String,
    c6500LineDiagLineDiagTelemetrySpanLoss String,
    c6500LineDiagLineDiagTelemetryAinsTimeLeft Time,
    c6500LineDiagLineDiagTelemetryPst PstfacRtrv 
}

c6500LineDiagLineDiagTelemetryTelemetry OBJECT-TYPE
    SYNTAX OCTET STRING(SIZE(1..80))
    MAX-ACCESS not-accessible
    STATUS current
    DESCRIPTION "AID in format TELEMETRY-shelf-slot-port, TELEMETRY-shelf-slot-ALL, TELEMETRY-shelf-ALL, SHELF-shelf-ALL, ALL"
    ::= { c6500LineDiagLineDiagTelemetryEntry 1 }

c6500LineDiagLineDiagTelemetryLosThresh OBJECT-TYPE
    SYNTAX String
    MAX-ACCESS read-only
    STATUS current
    DESCRIPTION "Telemetry Gain Loss Threshold (dBm)"
    ::= { c6500LineDiagLineDiagTelemetryEntry 2 }

c6500LineDiagLineDiagTelemetryTargTelemPower OBJECT-TYPE
    SYNTAX String
    MAX-ACCESS read-only
    STATUS current
    DESCRIPTION "Provisioned Power of the Telemetry Gain Signal (dBm)"
    ::= { c6500LineDiagLineDiagTelemetryEntry 3 }

c6500LineDiagLineDiagTelemetryMode OBJECT-TYPE
    SYNTAX INTEGER { otdr(0), telemetrysignalon(1), telemetrysignaloff(2), busy(3), unknown(4) }
    MAX-ACCESS read-only
    STATUS current
    DESCRIPTION "Mode the Facility is operating in"
    ::= { c6500LineDiagLineDiagTelemetryEntry 4 }

c6500LineDiagLineDiagTelemetrySignalPower OBJECT-TYPE
    SYNTAX String
    MAX-ACCESS read-only
    STATUS current
    DESCRIPTION "Measured Telemetry Tx/OTDR Tx Signal Power (dBm)"
    ::= { c6500LineDiagLineDiagTelemetryEntry 5 }

c6500LineDiagLineDiagTelemetryRxPwr OBJECT-TYPE
    SYNTAX String
    MAX-ACCESS read-only
    STATUS current
    DESCRIPTION "Measured Telemetry Rx/OTDR Rx Signal Power (dBm)"
    ::= { c6500LineDiagLineDiagTelemetryEntry 6 }

c6500LineDiagLineDiagTelemetrySpanLoss OBJECT-TYPE
    SYNTAX String
    MAX-ACCESS read-only
    STATUS current
    DESCRIPTION "Span Loss"
    ::= { c6500LineDiagLineDiagTelemetryEntry 7 }

c6500LineDiagLineDiagTelemetryAinsTimeLeft OBJECT-TYPE
    SYNTAX Time
    MAX-ACCESS read-only
    STATUS current
    DESCRIPTION "AINS time left HH-MM"
    ::= { c6500LineDiagLineDiagTelemetryEntry 8 }

c6500LineDiagLineDiagTelemetryPst OBJECT-TYPE
    SYNTAX PstfacRtrv
    MAX-ACCESS read-only
    STATUS current
    DESCRIPTION "Identify the primary state"
    ::= { c6500LineDiagLineDiagTelemetryEntry 9 }

c6500LineDiagLineDiagTelemetrySstTable OBJECT-TYPE
    SYNTAX SEQUENCE OF C6500LineDiagLineDiagTelemetrySstEntry
    MAX-ACCESS not-accessible
    STATUS current
    DESCRIPTION "Identify the secondary state's auto-inservice state"
    ::= { ciena6500LineDiagMIB 6 }

c6500LineDiagLineDiagTelemetrySstEntry OBJECT-TYPE
    SYNTAX C6500LineDiagLineDiagTelemetrySstEntry
    MAX-ACCESS not-accessible
    STATUS current
    DESCRIPTION "Entry for c6500LineDiagLineDiagTelemetrySstTable."
    INDEX { c6500LineDiagLineDiagTelemetrySstTelemetryTelemetry, c6500LineDiagLineDiagTelemetrySstTableSnmpKey }
    ::= { c6500LineDiagLineDiagTelemetrySstTable 1 }

C6500LineDiagLineDiagTelemetrySstEntry ::= SEQUENCE { 
    c6500LineDiagLineDiagTelemetrySstTelemetryTelemetry OCTET STRING,
    c6500LineDiagLineDiagTelemetrySstTableSnmpKey Integer32,
    c6500LineDiagLineDiagTelemetrySst INTEGER 
}

c6500LineDiagLineDiagTelemetrySstTelemetryTelemetry OBJECT-TYPE
    SYNTAX OCTET STRING(SIZE(1..80))
    MAX-ACCESS not-accessible
    STATUS current
    DESCRIPTION "AID in format TELEMETRY-shelf-slot-port, TELEMETRY-shelf-slot-ALL, TELEMETRY-shelf-ALL, SHELF-shelf-ALL, ALL"
    ::= { c6500LineDiagLineDiagTelemetrySstEntry 1 }

c6500LineDiagLineDiagTelemetrySstTableSnmpKey OBJECT-TYPE
    SYNTAX Integer32(0..2147483647)
    MAX-ACCESS not-accessible
    STATUS current
    DESCRIPTION "Unique key for c6500LineDiagLineDiagTelemetrySst"
    ::= { c6500LineDiagLineDiagTelemetrySstEntry 2 }

c6500LineDiagLineDiagTelemetrySst OBJECT-TYPE
    SYNTAX INTEGER { ains(0), ainsDea(1), bridged(2), switched(3), roll(4), act(5), idle(6), stbys(7), wrk(8), erranl(9), psi(10), flt(11), mea(12), tstf(13), ueq(14), sgeo(15), discd(16), lpbk(17), ts(18), faf(19), stbyh(20), wrkrx(21), wrktx(22), prtcl(23), uas(24), nosite(25), noam(26), mon(27), msc(28), protected(29), mt(30), dsbld(31), inhip(32), l2dsbld(33), tsgen(34), tsmon(35), tsrecirc(36) }
    MAX-ACCESS read-only
    STATUS current
    DESCRIPTION "Identify the secondary state's auto-inservice state"
    ::= { c6500LineDiagLineDiagTelemetrySstEntry 3 }

c6500LineDiagLineDiagConfigTable OBJECT-TYPE
    SYNTAX SEQUENCE OF C6500LineDiagLineDiagConfigEntry
    MAX-ACCESS not-accessible
    STATUS current
    DESCRIPTION "None"
    ::= { ciena6500LineDiagMIB 7 }

c6500LineDiagLineDiagConfigEntry OBJECT-TYPE
    SYNTAX C6500LineDiagLineDiagConfigEntry
    MAX-ACCESS not-accessible
    STATUS current
    DESCRIPTION "Entry for c6500LineDiagLineDiagConfigTable."
    INDEX { c6500LineDiagLineDiagConfigOtdrcfg }
    ::= { c6500LineDiagLineDiagConfigTable 1 }

C6500LineDiagLineDiagConfigEntry ::= SEQUENCE { 
    c6500LineDiagLineDiagConfigOtdrcfg OCTET STRING,
    c6500LineDiagLineDiagConfigMeasureTime Int,
    c6500LineDiagLineDiagConfigPulseShort Int,
    c6500LineDiagLineDiagConfigDistanceShort Int,
    c6500LineDiagLineDiagConfigPulseLong Int,
    c6500LineDiagLineDiagConfigDistanceLong Int,
    c6500LineDiagLineDiagConfigDistanceOffice Int,
    c6500LineDiagLineDiagConfigPulseOffice Int,
    c6500LineDiagLineDiagConfigEventRange String,
    c6500LineDiagLineDiagConfigDiscoveredEventRange Int,
    c6500LineDiagLineDiagConfigLossSingle String,
    c6500LineDiagLineDiagConfigLossAll String,
    c6500LineDiagLineDiagConfigReflSingle String,
    c6500LineDiagLineDiagConfigReflAll String,
    c6500LineDiagLineDiagConfigTotalFiberLoss String,
    c6500LineDiagLineDiagConfigFiberLoss String,
    c6500LineDiagLineDiagConfigTotalReflection String,
    c6500LineDiagLineDiagConfigTotalLoss String,
    c6500LineDiagLineDiagConfigFiberLength String,
    c6500LineDiagLineDiagConfigFiberDispersion String,
    c6500LineDiagLineDiagConfigSignalPower String,
    c6500LineDiagLineDiagConfigWavelength String,
    c6500LineDiagLineDiagConfigPst PstfacRtrv 
}

c6500LineDiagLineDiagConfigOtdrcfg OBJECT-TYPE
    SYNTAX OCTET STRING(SIZE(1..80))
    MAX-ACCESS not-accessible
    STATUS current
    DESCRIPTION "AID in format OTDRCFG-shelf-slot-port, OTDRCFG-shelf-slot-ALL, OTDRCFG-shelf-ALL, SHELF-shelf-ALL, ALL"
    ::= { c6500LineDiagLineDiagConfigEntry 1 }

c6500LineDiagLineDiagConfigMeasureTime OBJECT-TYPE
    SYNTAX Int
    MAX-ACCESS read-only
    STATUS current
    DESCRIPTION "Acquisition Time for the OTDR Trace (s)"
    ::= { c6500LineDiagLineDiagConfigEntry 2 }

c6500LineDiagLineDiagConfigPulseShort OBJECT-TYPE
    SYNTAX Int
    MAX-ACCESS read-only
    STATUS current
    DESCRIPTION "Pulse Duration for Short Distance OTDR Trace (ns)"
    ::= { c6500LineDiagLineDiagConfigEntry 3 }

c6500LineDiagLineDiagConfigDistanceShort OBJECT-TYPE
    SYNTAX Int
    MAX-ACCESS read-only
    STATUS current
    DESCRIPTION "Span Length for Short Distance OTDR Trace (m)"
    ::= { c6500LineDiagLineDiagConfigEntry 4 }

c6500LineDiagLineDiagConfigPulseLong OBJECT-TYPE
    SYNTAX Int
    MAX-ACCESS read-only
    STATUS current
    DESCRIPTION "Pulse Duration for Long Distance OTDR Trace (us)"
    ::= { c6500LineDiagLineDiagConfigEntry 5 }

c6500LineDiagLineDiagConfigDistanceLong OBJECT-TYPE
    SYNTAX Int
    MAX-ACCESS read-only
    STATUS current
    DESCRIPTION "Span Length for Long Distance OTDR Trace (m)"
    ::= { c6500LineDiagLineDiagConfigEntry 6 }

c6500LineDiagLineDiagConfigDistanceOffice OBJECT-TYPE
    SYNTAX Int
    MAX-ACCESS read-only
    STATUS current
    DESCRIPTION "Span Length for Office Distance for OTDR Trace (m)"
    ::= { c6500LineDiagLineDiagConfigEntry 7 }

c6500LineDiagLineDiagConfigPulseOffice OBJECT-TYPE
    SYNTAX Int
    MAX-ACCESS read-only
    STATUS current
    DESCRIPTION "Pulse Rate for OFFICE Distance OTDR Trace (ns)"
    ::= { c6500LineDiagLineDiagConfigEntry 8 }

c6500LineDiagLineDiagConfigEventRange OBJECT-TYPE
    SYNTAX String
    MAX-ACCESS read-only
    STATUS current
    DESCRIPTION "OTDR Event Range (m)"
    ::= { c6500LineDiagLineDiagConfigEntry 9 }

c6500LineDiagLineDiagConfigDiscoveredEventRange OBJECT-TYPE
    SYNTAX Int
    MAX-ACCESS read-only
    STATUS current
    DESCRIPTION "Discovered OTDR Event Range (m)"
    ::= { c6500LineDiagLineDiagConfigEntry 10 }

c6500LineDiagLineDiagConfigLossSingle OBJECT-TYPE
    SYNTAX String
    MAX-ACCESS read-only
    STATUS current
    DESCRIPTION "Loss per event for OTDR Trace (dB)"
    ::= { c6500LineDiagLineDiagConfigEntry 11 }

c6500LineDiagLineDiagConfigLossAll OBJECT-TYPE
    SYNTAX String
    MAX-ACCESS read-only
    STATUS current
    DESCRIPTION "Loss for all events for OTDR Trace (dB)"
    ::= { c6500LineDiagLineDiagConfigEntry 12 }

c6500LineDiagLineDiagConfigReflSingle OBJECT-TYPE
    SYNTAX String
    MAX-ACCESS read-only
    STATUS current
    DESCRIPTION "Reflection for a single event for OTDR Trace (dB)"
    ::= { c6500LineDiagLineDiagConfigEntry 13 }

c6500LineDiagLineDiagConfigReflAll OBJECT-TYPE
    SYNTAX String
    MAX-ACCESS read-only
    STATUS current
    DESCRIPTION "Reflection for all events for OTDR Trace (dBm)"
    ::= { c6500LineDiagLineDiagConfigEntry 14 }

c6500LineDiagLineDiagConfigTotalFiberLoss OBJECT-TYPE
    SYNTAX String
    MAX-ACCESS read-only
    STATUS current
    DESCRIPTION "Total fiber loss for OTDR Trace (dBm)"
    ::= { c6500LineDiagLineDiagConfigEntry 15 }

c6500LineDiagLineDiagConfigFiberLoss OBJECT-TYPE
    SYNTAX String
    MAX-ACCESS read-only
    STATUS current
    DESCRIPTION "Slope of the OTDR trace in db/km"
    ::= { c6500LineDiagLineDiagConfigEntry 16 }

c6500LineDiagLineDiagConfigTotalReflection OBJECT-TYPE
    SYNTAX String
    MAX-ACCESS read-only
    STATUS current
    DESCRIPTION "Total Reflection in first 20 km of the fiber connected to the CP (dB)"
    ::= { c6500LineDiagLineDiagConfigEntry 17 }

c6500LineDiagLineDiagConfigTotalLoss OBJECT-TYPE
    SYNTAX String
    MAX-ACCESS read-only
    STATUS current
    DESCRIPTION "Total Loss in first 20 km of the fiber connected to the CP (dB)"
    ::= { c6500LineDiagLineDiagConfigEntry 18 }

c6500LineDiagLineDiagConfigFiberLength OBJECT-TYPE
    SYNTAX String
    MAX-ACCESS read-only
    STATUS current
    DESCRIPTION "Fiber length measured by the long trace(Param is applicable only on R-Series shelf.)"
    ::= { c6500LineDiagLineDiagConfigEntry 19 }

c6500LineDiagLineDiagConfigFiberDispersion OBJECT-TYPE
    SYNTAX String
    MAX-ACCESS read-only
    STATUS current
    DESCRIPTION "Fiber dispersion measurement(Param is applicable only on R-Series shelf.)"
    ::= { c6500LineDiagLineDiagConfigEntry 20 }

c6500LineDiagLineDiagConfigSignalPower OBJECT-TYPE
    SYNTAX String
    MAX-ACCESS read-only
    STATUS current
    DESCRIPTION "Measured OTDRCFG Signal Power (dBm)"
    ::= { c6500LineDiagLineDiagConfigEntry 21 }

c6500LineDiagLineDiagConfigWavelength OBJECT-TYPE
    SYNTAX String
    MAX-ACCESS read-only
    STATUS current
    DESCRIPTION "OTDR Wavelength"
    ::= { c6500LineDiagLineDiagConfigEntry 22 }

c6500LineDiagLineDiagConfigPst OBJECT-TYPE
    SYNTAX PstfacRtrv
    MAX-ACCESS read-only
    STATUS current
    DESCRIPTION "Identify the primary state"
    ::= { c6500LineDiagLineDiagConfigEntry 23 }

c6500LineDiagLineDiagConfigFiberTypeTable OBJECT-TYPE
    SYNTAX SEQUENCE OF C6500LineDiagLineDiagConfigFiberTypeEntry
    MAX-ACCESS not-accessible
    STATUS current
    DESCRIPTION "Fiber type."
    ::= { ciena6500LineDiagMIB 8 }

c6500LineDiagLineDiagConfigFiberTypeEntry OBJECT-TYPE
    SYNTAX C6500LineDiagLineDiagConfigFiberTypeEntry
    MAX-ACCESS not-accessible
    STATUS current
    DESCRIPTION "Entry for c6500LineDiagLineDiagConfigFiberTypeTable."
    INDEX { c6500LineDiagLineDiagConfigFiberTypeConfigOtdrcfg, c6500LineDiagLineDiagConfigFiberTypeTableSnmpKey }
    ::= { c6500LineDiagLineDiagConfigFiberTypeTable 1 }

C6500LineDiagLineDiagConfigFiberTypeEntry ::= SEQUENCE { 
    c6500LineDiagLineDiagConfigFiberTypeConfigOtdrcfg OCTET STRING,
    c6500LineDiagLineDiagConfigFiberTypeTableSnmpKey Integer32,
    c6500LineDiagLineDiagConfigFiberType AdjFiber 
}

c6500LineDiagLineDiagConfigFiberTypeConfigOtdrcfg OBJECT-TYPE
    SYNTAX OCTET STRING(SIZE(1..80))
    MAX-ACCESS not-accessible
    STATUS current
    DESCRIPTION "AID in format OTDRCFG-shelf-slot-port, OTDRCFG-shelf-slot-ALL, OTDRCFG-shelf-ALL, SHELF-shelf-ALL, ALL"
    ::= { c6500LineDiagLineDiagConfigFiberTypeEntry 1 }

c6500LineDiagLineDiagConfigFiberTypeTableSnmpKey OBJECT-TYPE
    SYNTAX Integer32(0..2147483647)
    MAX-ACCESS not-accessible
    STATUS current
    DESCRIPTION "Unique key for c6500LineDiagLineDiagConfigFiberType"
    ::= { c6500LineDiagLineDiagConfigFiberTypeEntry 2 }

c6500LineDiagLineDiagConfigFiberType OBJECT-TYPE
    SYNTAX AdjFiber
    MAX-ACCESS read-only
    STATUS current
    DESCRIPTION "Fiber type."
    ::= { c6500LineDiagLineDiagConfigFiberTypeEntry 3 }

c6500LineDiagLineDiagConfigDiscFiberTypeTable OBJECT-TYPE
    SYNTAX SEQUENCE OF C6500LineDiagLineDiagConfigDiscFiberTypeEntry
    MAX-ACCESS not-accessible
    STATUS current
    DESCRIPTION "Discovered Fiber type."
    ::= { ciena6500LineDiagMIB 9 }

c6500LineDiagLineDiagConfigDiscFiberTypeEntry OBJECT-TYPE
    SYNTAX C6500LineDiagLineDiagConfigDiscFiberTypeEntry
    MAX-ACCESS not-accessible
    STATUS current
    DESCRIPTION "Entry for c6500LineDiagLineDiagConfigDiscFiberTypeTable."
    INDEX { c6500LineDiagLineDiagConfigDiscFiberTypeConfigOtdrcfg, c6500LineDiagLineDiagConfigDiscFiberTypeTableSnmpKey }
    ::= { c6500LineDiagLineDiagConfigDiscFiberTypeTable 1 }

C6500LineDiagLineDiagConfigDiscFiberTypeEntry ::= SEQUENCE { 
    c6500LineDiagLineDiagConfigDiscFiberTypeConfigOtdrcfg OCTET STRING,
    c6500LineDiagLineDiagConfigDiscFiberTypeTableSnmpKey Integer32,
    c6500LineDiagLineDiagConfigDiscFiberType AdjFiber 
}

c6500LineDiagLineDiagConfigDiscFiberTypeConfigOtdrcfg OBJECT-TYPE
    SYNTAX OCTET STRING(SIZE(1..80))
    MAX-ACCESS not-accessible
    STATUS current
    DESCRIPTION "AID in format OTDRCFG-shelf-slot-port, OTDRCFG-shelf-slot-ALL, OTDRCFG-shelf-ALL, SHELF-shelf-ALL, ALL"
    ::= { c6500LineDiagLineDiagConfigDiscFiberTypeEntry 1 }

c6500LineDiagLineDiagConfigDiscFiberTypeTableSnmpKey OBJECT-TYPE
    SYNTAX Integer32(0..2147483647)
    MAX-ACCESS not-accessible
    STATUS current
    DESCRIPTION "Unique key for c6500LineDiagLineDiagConfigDiscFiberType"
    ::= { c6500LineDiagLineDiagConfigDiscFiberTypeEntry 2 }

c6500LineDiagLineDiagConfigDiscFiberType OBJECT-TYPE
    SYNTAX AdjFiber
    MAX-ACCESS read-only
    STATUS current
    DESCRIPTION "Discovered Fiber type."
    ::= { c6500LineDiagLineDiagConfigDiscFiberTypeEntry 3 }

c6500LineDiagLineDiagConfigTraceStatusTable OBJECT-TYPE
    SYNTAX SEQUENCE OF C6500LineDiagLineDiagConfigTraceStatusEntry
    MAX-ACCESS not-accessible
    STATUS current
    DESCRIPTION "OTDR Trace Status"
    ::= { ciena6500LineDiagMIB 10 }

c6500LineDiagLineDiagConfigTraceStatusEntry OBJECT-TYPE
    SYNTAX C6500LineDiagLineDiagConfigTraceStatusEntry
    MAX-ACCESS not-accessible
    STATUS current
    DESCRIPTION "Entry for c6500LineDiagLineDiagConfigTraceStatusTable."
    INDEX { c6500LineDiagLineDiagConfigTraceStatusConfigOtdrcfg, c6500LineDiagLineDiagConfigTraceStatusTableSnmpKey }
    ::= { c6500LineDiagLineDiagConfigTraceStatusTable 1 }

C6500LineDiagLineDiagConfigTraceStatusEntry ::= SEQUENCE { 
    c6500LineDiagLineDiagConfigTraceStatusConfigOtdrcfg OCTET STRING,
    c6500LineDiagLineDiagConfigTraceStatusTableSnmpKey Integer32,
    c6500LineDiagLineDiagConfigTraceStatus Otdrtracestatus 
}

c6500LineDiagLineDiagConfigTraceStatusConfigOtdrcfg OBJECT-TYPE
    SYNTAX OCTET STRING(SIZE(1..80))
    MAX-ACCESS not-accessible
    STATUS current
    DESCRIPTION "AID in format OTDRCFG-shelf-slot-port, OTDRCFG-shelf-slot-ALL, OTDRCFG-shelf-ALL, SHELF-shelf-ALL, ALL"
    ::= { c6500LineDiagLineDiagConfigTraceStatusEntry 1 }

c6500LineDiagLineDiagConfigTraceStatusTableSnmpKey OBJECT-TYPE
    SYNTAX Integer32(0..2147483647)
    MAX-ACCESS not-accessible
    STATUS current
    DESCRIPTION "Unique key for c6500LineDiagLineDiagConfigTraceStatus"
    ::= { c6500LineDiagLineDiagConfigTraceStatusEntry 2 }

c6500LineDiagLineDiagConfigTraceStatus OBJECT-TYPE
    SYNTAX Otdrtracestatus
    MAX-ACCESS read-only
    STATUS current
    DESCRIPTION "OTDR Trace Status"
    ::= { c6500LineDiagLineDiagConfigTraceStatusEntry 3 }

c6500LineDiagLineDiagConfigSstTable OBJECT-TYPE
    SYNTAX SEQUENCE OF C6500LineDiagLineDiagConfigSstEntry
    MAX-ACCESS not-accessible
    STATUS current
    DESCRIPTION "Identify the secondary state"
    ::= { ciena6500LineDiagMIB 11 }

c6500LineDiagLineDiagConfigSstEntry OBJECT-TYPE
    SYNTAX C6500LineDiagLineDiagConfigSstEntry
    MAX-ACCESS not-accessible
    STATUS current
    DESCRIPTION "Entry for c6500LineDiagLineDiagConfigSstTable."
    INDEX { c6500LineDiagLineDiagConfigSstConfigOtdrcfg, c6500LineDiagLineDiagConfigSstTableSnmpKey }
    ::= { c6500LineDiagLineDiagConfigSstTable 1 }

C6500LineDiagLineDiagConfigSstEntry ::= SEQUENCE { 
    c6500LineDiagLineDiagConfigSstConfigOtdrcfg OCTET STRING,
    c6500LineDiagLineDiagConfigSstTableSnmpKey Integer32,
    c6500LineDiagLineDiagConfigSst Sstfac 
}

c6500LineDiagLineDiagConfigSstConfigOtdrcfg OBJECT-TYPE
    SYNTAX OCTET STRING(SIZE(1..80))
    MAX-ACCESS not-accessible
    STATUS current
    DESCRIPTION "AID in format OTDRCFG-shelf-slot-port, OTDRCFG-shelf-slot-ALL, OTDRCFG-shelf-ALL, SHELF-shelf-ALL, ALL"
    ::= { c6500LineDiagLineDiagConfigSstEntry 1 }

c6500LineDiagLineDiagConfigSstTableSnmpKey OBJECT-TYPE
    SYNTAX Integer32(0..2147483647)
    MAX-ACCESS not-accessible
    STATUS current
    DESCRIPTION "Unique key for c6500LineDiagLineDiagConfigSst"
    ::= { c6500LineDiagLineDiagConfigSstEntry 2 }

c6500LineDiagLineDiagConfigSst OBJECT-TYPE
    SYNTAX Sstfac
    MAX-ACCESS read-only
    STATUS current
    DESCRIPTION "Identify the secondary state"
    ::= { c6500LineDiagLineDiagConfigSstEntry 3 }

c6500LineDiagLineDiagEventsTable OBJECT-TYPE
    SYNTAX SEQUENCE OF C6500LineDiagLineDiagEventsEntry
    MAX-ACCESS not-accessible
    STATUS current
    DESCRIPTION "None"
    ::= { ciena6500LineDiagMIB 12 }

c6500LineDiagLineDiagEventsEntry OBJECT-TYPE
    SYNTAX C6500LineDiagLineDiagEventsEntry
    MAX-ACCESS not-accessible
    STATUS current
    DESCRIPTION "Entry for c6500LineDiagLineDiagEventsTable."
    INDEX { c6500LineDiagLineDiagEventsOtdrcfg, c6500LineDiagLineDiagEventsAutoIdTableSnmpKey }
    ::= { c6500LineDiagLineDiagEventsTable 1 }

C6500LineDiagLineDiagEventsEntry ::= SEQUENCE { 
    c6500LineDiagLineDiagEventsOtdrcfg OCTET STRING,
    c6500LineDiagLineDiagEventsTraceDate String,
    c6500LineDiagLineDiagEventsTraceTime String,
    c6500LineDiagLineDiagEventsEventType String,
    c6500LineDiagLineDiagEventsDistance Int,
    c6500LineDiagLineDiagEventsEventValue String,
    c6500LineDiagLineDiagEventsReflectionValue String,
    c6500LineDiagLineDiagEventsLossValue String,
    c6500LineDiagLineDiagEventsEffectiveLossValue String,
    c6500LineDiagLineDiagEventsLossThreshold String,
    c6500LineDiagLineDiagEventsReflectionThreshold String,
    c6500LineDiagLineDiagEventsResult String,
    c6500LineDiagLineDiagEventsTraceType TraceType,
    c6500LineDiagLineDiagEventsTraceTag INTEGER,
    c6500LineDiagLineDiagEventsAutoIdTableSnmpKey Integer32 
}

c6500LineDiagLineDiagEventsOtdrcfg OBJECT-TYPE
    SYNTAX OCTET STRING(SIZE(1..80))
    MAX-ACCESS not-accessible
    STATUS current
    DESCRIPTION "AID in format OTDRCFG-shelf-slot-port, SHELF-shelf-ALL"
    ::= { c6500LineDiagLineDiagEventsEntry 1 }

c6500LineDiagLineDiagEventsTraceDate OBJECT-TYPE
    SYNTAX String
    MAX-ACCESS read-only
    STATUS current
    DESCRIPTION "The date of the OTDR trace"
    ::= { c6500LineDiagLineDiagEventsEntry 2 }

c6500LineDiagLineDiagEventsTraceTime OBJECT-TYPE
    SYNTAX String
    MAX-ACCESS read-only
    STATUS current
    DESCRIPTION "The time of the OTDR trace"
    ::= { c6500LineDiagLineDiagEventsEntry 3 }

c6500LineDiagLineDiagEventsEventType OBJECT-TYPE
    SYNTAX String
    MAX-ACCESS read-only
    STATUS current
    DESCRIPTION "The type of event. Range= 0-3 (0: INVALID, 1: LOSS, 2: REFLECTION; 3: SATURATE)"
    ::= { c6500LineDiagLineDiagEventsEntry 4 }

c6500LineDiagLineDiagEventsDistance OBJECT-TYPE
    SYNTAX Int
    MAX-ACCESS read-only
    STATUS current
    DESCRIPTION "The distance in meters."
    ::= { c6500LineDiagLineDiagEventsEntry 5 }

c6500LineDiagLineDiagEventsEventValue OBJECT-TYPE
    SYNTAX String
    MAX-ACCESS read-only
    STATUS current
    DESCRIPTION "The dB value of the event"
    ::= { c6500LineDiagLineDiagEventsEntry 6 }

c6500LineDiagLineDiagEventsReflectionValue OBJECT-TYPE
    SYNTAX String
    MAX-ACCESS read-only
    STATUS current
    DESCRIPTION "The dB value of the reflection. Range = -99.9dB to 0dB"
    ::= { c6500LineDiagLineDiagEventsEntry 7 }

c6500LineDiagLineDiagEventsLossValue OBJECT-TYPE
    SYNTAX String
    MAX-ACCESS read-only
    STATUS current
    DESCRIPTION "The dB value of the loss. Range = -30dB to 30dB"
    ::= { c6500LineDiagLineDiagEventsEntry 8 }

c6500LineDiagLineDiagEventsEffectiveLossValue OBJECT-TYPE
    SYNTAX String
    MAX-ACCESS read-only
    STATUS current
    DESCRIPTION "The dB value of the effective loss. Range = -30dB to 30dB"
    ::= { c6500LineDiagLineDiagEventsEntry 9 }

c6500LineDiagLineDiagEventsLossThreshold OBJECT-TYPE
    SYNTAX String
    MAX-ACCESS read-only
    STATUS current
    DESCRIPTION "The dB value of the loss threshold. Range = 0dB to 3dB"
    ::= { c6500LineDiagLineDiagEventsEntry 10 }

c6500LineDiagLineDiagEventsReflectionThreshold OBJECT-TYPE
    SYNTAX String
    MAX-ACCESS read-only
    STATUS current
    DESCRIPTION "The dB value of the reflection threshold. Range = -40dB to -24dB"
    ::= { c6500LineDiagLineDiagEventsEntry 11 }

c6500LineDiagLineDiagEventsResult OBJECT-TYPE
    SYNTAX String
    MAX-ACCESS read-only
    STATUS current
    DESCRIPTION "Results"
    ::= { c6500LineDiagLineDiagEventsEntry 12 }

c6500LineDiagLineDiagEventsTraceType OBJECT-TYPE
    SYNTAX TraceType
    MAX-ACCESS read-only
    STATUS current
    DESCRIPTION "The type of trace to be measured"
    ::= { c6500LineDiagLineDiagEventsEntry 13 }

c6500LineDiagLineDiagEventsTraceTag OBJECT-TYPE
    SYNTAX INTEGER { bsln(0), current(1) }
    MAX-ACCESS read-only
    STATUS current
    DESCRIPTION "Baseline or the current OTDR trace"
    ::= { c6500LineDiagLineDiagEventsEntry 14 }

c6500LineDiagLineDiagEventsAutoIdTableSnmpKey OBJECT-TYPE
    SYNTAX Integer32(0..2147483647)
    MAX-ACCESS not-accessible
    STATUS current
    DESCRIPTION "Incremental unique key for SNMP Table."
    ::= { c6500LineDiagLineDiagEventsEntry 15 }



-- Conformance statements
ciena6500LineDiagObjects OBJECT IDENTIFIER
    ::= { ciena6500LineDiagMIB 1 }

ciena6500LineDiagConformance OBJECT IDENTIFIER
    ::= { ciena6500LineDiagMIB 2 }

ciena6500LineDiagGroups OBJECT IDENTIFIER
    ::= { ciena6500LineDiagConformance 1 }

ciena6500LineDiagGroup OBJECT-GROUP
    OBJECTS { 
        c6500LineDiagLineDiagOtdrTraceByteStream,
        c6500LineDiagLineDiagOtdrTracesFileName,
        c6500LineDiagLineDiagOtdrTracesTraceTag,
        c6500LineDiagLineDiagOtdrTracesTraceType,
        c6500LineDiagLineDiagTelemetryLosThresh,
        c6500LineDiagLineDiagTelemetryTargTelemPower,
        c6500LineDiagLineDiagTelemetryMode,
        c6500LineDiagLineDiagTelemetrySignalPower,
        c6500LineDiagLineDiagTelemetryRxPwr,
        c6500LineDiagLineDiagTelemetrySpanLoss,
        c6500LineDiagLineDiagTelemetryAinsTimeLeft,
        c6500LineDiagLineDiagTelemetryPst,
        c6500LineDiagLineDiagConfigMeasureTime,
        c6500LineDiagLineDiagConfigPulseShort,
        c6500LineDiagLineDiagConfigDistanceShort,
        c6500LineDiagLineDiagConfigPulseLong,
        c6500LineDiagLineDiagConfigDistanceLong,
        c6500LineDiagLineDiagConfigDistanceOffice,
        c6500LineDiagLineDiagConfigPulseOffice,
        c6500LineDiagLineDiagConfigEventRange,
        c6500LineDiagLineDiagConfigDiscoveredEventRange,
        c6500LineDiagLineDiagConfigLossSingle,
        c6500LineDiagLineDiagConfigLossAll,
        c6500LineDiagLineDiagConfigReflSingle,
        c6500LineDiagLineDiagConfigReflAll,
        c6500LineDiagLineDiagConfigTotalFiberLoss,
        c6500LineDiagLineDiagConfigFiberLoss,
        c6500LineDiagLineDiagConfigTotalReflection,
        c6500LineDiagLineDiagConfigTotalLoss,
        c6500LineDiagLineDiagConfigFiberLength,
        c6500LineDiagLineDiagConfigFiberDispersion,
        c6500LineDiagLineDiagConfigSignalPower,
        c6500LineDiagLineDiagConfigWavelength,
        c6500LineDiagLineDiagConfigPst,
        c6500LineDiagLineDiagEventsTraceDate,
        c6500LineDiagLineDiagEventsTraceTime,
        c6500LineDiagLineDiagEventsEventType,
        c6500LineDiagLineDiagEventsDistance,
        c6500LineDiagLineDiagEventsEventValue,
        c6500LineDiagLineDiagEventsReflectionValue,
        c6500LineDiagLineDiagEventsLossValue,
        c6500LineDiagLineDiagEventsEffectiveLossValue,
        c6500LineDiagLineDiagEventsLossThreshold,
        c6500LineDiagLineDiagEventsReflectionThreshold,
        c6500LineDiagLineDiagEventsResult,
        c6500LineDiagLineDiagEventsTraceType,
        c6500LineDiagLineDiagEventsTraceTag
    }
    STATUS current
    DESCRIPTION "Conformance Group"
    ::= { ciena6500LineDiagGroups 1 }

ciena6500LineDiagCompliances OBJECT IDENTIFIER
    ::= { ciena6500LineDiagConformance 2 }

ciena6500LineDiagCompliance MODULE-COMPLIANCE
    STATUS current
    DESCRIPTION "Compliance"
    MODULE MANDATORY-GROUPS { ciena6500LineDiagGroup }
    ::= { ciena6500LineDiagCompliances 1 }

END -- End module
