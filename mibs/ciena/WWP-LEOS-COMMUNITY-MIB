-- This file was included in WWP MIB release 04-10-01-0027
 --
 -- WWP-LEOS-COMMUNITY-MIB.my
 -- MIB generated by MG-SOFT Visual MIB Builder Version 2.1 Build 199
 -- Sunday, March 25, 2001 at 19:17:08
 --

 WWP-LEOS-COMMUNITY-MIB DEFINITIONS ::= BEGIN

 IMPORTS 		
   IpAddress, OBJECT-TYPE, MODULE-IDENTITY			
	    FROM SNMPv2-SMI			
   RowStatus, DisplayString
	    FROM SNMPv2-TC						
   wwpModulesLeos		
	    FROM WWP-SMI;
	
	
 wwpLeosCommunityMIB MODULE-IDENTITY
	    LAST-UPDATED "200104031700Z"
	    ORGANIZATION "Ciena, Inc"
	    CONTACT-INFO
		    "   Mib Meister
		  			115 North Sullivan Road
					Spokane Valley, WA 99037
		        	USA		 		
		        	Phone:  +1 509 242 9000
					Email:  support@ciena.com"
	    DESCRIPTION
		    "The MIB module for the WWP Community specific information."
	    REVISION    "200104031700Z"
	    DESCRIPTION
		    "Initial creation."
	    ::= { wwpModulesLeos 22 }
						
 --
 -- Node definitions
 --
	
 wwpLeosCommunityMIBObjects OBJECT IDENTIFIER ::= { wwpLeosCommunityMIB 1 }
 wwpLeosCommunity OBJECT IDENTIFIER ::= { wwpLeosCommunityMIBObjects 1 }
 

 -- Notifications 
  
 wwpLeosCommunityMIBNotificationPrefix  OBJECT IDENTIFIER ::= { wwpLeosCommunityMIB 2 } 
 wwpLeosCommunityMIBNotifications    OBJECT IDENTIFIER ::=  
                       { wwpLeosCommunityMIBNotificationPrefix 0 }

 -- Conformance information 
 
 wwpLeosCommunityMIBConformance OBJECT IDENTIFIER ::= { wwpLeosCommunityMIB 3 } 
 wwpLeosCommunityMIBCompliances OBJECT IDENTIFIER ::= { wwpLeosCommunityMIBConformance 1 } 		
 wwpLeosCommunityMIBGroups      OBJECT IDENTIFIER ::= { wwpLeosCommunityMIBConformance 2 }
		
 wwpLeosCommunityTable OBJECT-TYPE
     SYNTAX       SEQUENCE OF WwpLeosCommunityEntry
     MAX-ACCESS   not-accessible
     STATUS       deprecated
     DESCRIPTION
	     "Table of read/write Community entries. Multiple Set Operation must be used
	      to create entries in the table.
	      Following objects must be set to valid values to create entry
	      wwpLeosCommunityRights, wwpLeosCommunityStatus.
	      If wwpLeosCommunityName is not set to anything then
	      device will set it to public.
	      If wwpLeosCommunityAddr is not set to anything then
	      device will set it to 0.0.0.0.
	      
	      While deleting entry if this is the last entry with read-only
	      or read-write permission then device will not allow to delete entry."
     ::= { wwpLeosCommunity 1 }
		
 wwpLeosCommunityEntry OBJECT-TYPE
     SYNTAX       WwpLeosCommunityEntry
     MAX-ACCESS   not-accessible
     STATUS       deprecated
     DESCRIPTION
	     "An entry for each read/write community.
	      Multiple Set Operation must be used
	      to create entries in the table."
     INDEX { wwpLeosCommunityIndex}
     ::= { wwpLeosCommunityTable 1 }
		 
 WwpLeosCommunityEntry ::= SEQUENCE { 
     wwpLeosCommunityIndex	     INTEGER,
     wwpLeosCommunityName            DisplayString,     
     wwpLeosCommunityAddr            DisplayString,
     wwpLeosCommunityResolvedIp	     IpAddress,
     wwpLeosCommunityRights          INTEGER,
     wwpLeosCommunityStatus          RowStatus
 }

 wwpLeosCommunityIndex OBJECT-TYPE
     SYNTAX       INTEGER (1..10)
     MAX-ACCESS   read-only
     STATUS       deprecated
     DESCRIPTION
	     "The index used in the table."
     ::= { wwpLeosCommunityEntry 1 }

 wwpLeosCommunityName OBJECT-TYPE
     SYNTAX       DisplayString
     MAX-ACCESS   read-create
     STATUS       deprecated
     DESCRIPTION
	     "The Name of Community String. This is mandatory 
	      object that needs to be set to create entry."
     ::= { wwpLeosCommunityEntry 2 }

 wwpLeosCommunityAddr OBJECT-TYPE
    SYNTAX      DisplayString
    MAX-ACCESS  read-create
    STATUS      deprecated
    DESCRIPTION
	    "The IP Address of the host(s) or the host name with access rights. 
	     A value of 0 means that access is allowed to any host.
	     This is mandatory object that needs to be set to create entry."
    ::= { wwpLeosCommunityEntry 3 }
 
 wwpLeosCommunityResolvedIp OBJECT-TYPE
    SYNTAX      IpAddress
    MAX-ACCESS  read-only
    STATUS      deprecated
    DESCRIPTION
	    "This object is set to the resolved IP address when 
	     wwpLeosCommunityAddr is set to host name.
	     If wwpLeosCommunityAddr is set to IP address
	     then this object will contain the same 
	     IP as wwpLeosCommunityAddr."
    ::= { wwpLeosCommunityEntry 4 }

 wwpLeosCommunityRights OBJECT-TYPE
     SYNTAX       INTEGER {
                     readOnly(1),
                     readWrite(2)
                  }
     MAX-ACCESS   read-create
     STATUS       deprecated
     DESCRIPTION
	     "Rights associated with the Community Strings. The community Name
             associated with 'readOnly' community Rights will not have any
             access (read\write) to the readWrite communities."
     ::= { wwpLeosCommunityEntry 5 }
		
 wwpLeosCommunityStatus OBJECT-TYPE
     SYNTAX      RowStatus
     MAX-ACCESS  read-create
     STATUS      deprecated
     DESCRIPTION
	     "To create a row in this table, a manager must
             set this object to 'createAndGo'. wwpLeosCommunityRights
             must be valid prior to creating entry.	     
             The Agent should not let all the communities to be deleted
             as this will cause isolation of the device. At least one
             readOnly community and one readWrite community should always
             be present."
     ::= { wwpLeosCommunityEntry 6 }

 wwpLeosNotifCommunityTable OBJECT-TYPE
     SYNTAX       SEQUENCE OF WwpLeosNotifCommunityEntry
     MAX-ACCESS   not-accessible
     STATUS       deprecated
     DESCRIPTION
	     "Table of Notification Community entries.
	      Multiple set operation must be used
	      to create entries in the table."
     ::= { wwpLeosCommunity 2 }
		
 wwpLeosNotifCommunityEntry OBJECT-TYPE
     SYNTAX       WwpLeosNotifCommunityEntry
     MAX-ACCESS   not-accessible
     STATUS       deprecated
     DESCRIPTION
	     "An entry for each notification community.
	      Multiple set operation must be used
	      to create entries in the table."
     INDEX { wwpLeosNotifIndex }
     ::= { wwpLeosNotifCommunityTable 1 }
		 
 WwpLeosNotifCommunityEntry ::= SEQUENCE { 
     wwpLeosNotifIndex		       INTEGER,
     wwpLeosNotifCommunityName         DisplayString,     
     wwpLeosNotifCommunityDestAddr     DisplayString,
     wwpLeosNotifCommunityResolvedIpAddr IpAddress,
     wwpLeosNotifCommunityStatus       RowStatus
 }

 wwpLeosNotifIndex OBJECT-TYPE
     SYNTAX       INTEGER (1..10)
     MAX-ACCESS   read-only
     STATUS       deprecated
     DESCRIPTION
	     "The index used in the table."
     ::= { wwpLeosNotifCommunityEntry 1 }

 wwpLeosNotifCommunityName OBJECT-TYPE
     SYNTAX       DisplayString
     MAX-ACCESS   read-create
     STATUS       deprecated
     DESCRIPTION
	     "The Community String to be used for the notifications.
	      This is mandatory object that needs to be set to create entry."
     ::= { wwpLeosNotifCommunityEntry 2 }

 wwpLeosNotifCommunityDestAddr OBJECT-TYPE
    SYNTAX      DisplayString
    MAX-ACCESS  read-create
    STATUS      deprecated
    DESCRIPTION
	    "The IP address or host names of the host to which notification 
	     is to be sent. This is mandatory object that needs to be set to 
	     create entry."
    ::= { wwpLeosNotifCommunityEntry 3 }

 wwpLeosNotifCommunityResolvedIpAddr OBJECT-TYPE
    SYNTAX      IpAddress
    MAX-ACCESS  read-only
    STATUS      deprecated
    DESCRIPTION
	    "This object is set to resolved IP address of host name
	     if wwpLeosNotifCommunityName is set to hostname.
	     If wwpLeosNotifCommunityName is set to ipv4 then 
	     this object will contain same IP as 
	     wwpLeosNotifCommunityDestAddr."
    ::= { wwpLeosNotifCommunityEntry 4 }
		
 wwpLeosNotifCommunityStatus OBJECT-TYPE
     SYNTAX      RowStatus
     MAX-ACCESS  read-create
     STATUS      deprecated
     DESCRIPTION
	     "To create a row in this table, a manager must
             set this object to 'createAndGo'.
	      This table uses"
     ::= { wwpLeosNotifCommunityEntry 5 } 
                 
 END

 --
 -- WWP-COMMUNITY-MIB
 --
