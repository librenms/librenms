-- This file was automatically generated from ciena-6500-types.yang. Do not edit.

CIENA-6500-TYPES-MIB DEFINITIONS ::= BEGIN

IMPORTS
    cienaGenericMIBs
        FROM CIENA-SMI
    MODULE-COMPLIANCE, OBJECT-GROUP
        FROM SNMPv2-CONF
    Counter64, MODULE-IDENTITY
        FROM SNMPv2-SMI
    TEXTUAL-CONVENTION, TruthValue
        FROM SNMPv2-TC;

ciena6500TypesMIB MODULE-IDENTITY
    LAST-UPDATED "201812310000Z"
    ORGANIZATION "Ciena Corporation"
    CONTACT-INFO "Web URL: http://www.ciena.com"
    DESCRIPTION "This modules describes Ciena's release object for the 6500 platform"
    REVISION "201812310000Z"
    DESCRIPTION "Initial Draft"
    ::= { cienaGenericMIBs 101 }

Aid ::= TEXTUAL-CONVENTION
    DISPLAY-HINT "80a"
    STATUS current
    DESCRIPTION "None"
    SYNTAX OCTET STRING(SIZE(1..80))

Boolean ::= TEXTUAL-CONVENTION
    STATUS current
    DESCRIPTION "None"
    SYNTAX TruthValue

Date ::= TEXTUAL-CONVENTION
    DISPLAY-HINT "9a"
    STATUS current
    DESCRIPTION "None"
    SYNTAX OCTET STRING(SIZE(1..9))

Decimal ::= TEXTUAL-CONVENTION
    STATUS current
    DESCRIPTION "None"
    SYNTAX OCTET STRING(SIZE(1..128))

Ident ::= TEXTUAL-CONVENTION
    DISPLAY-HINT "32a"
    STATUS current
    DESCRIPTION "None"
    SYNTAX OCTET STRING(SIZE(1..32))

Int ::= TEXTUAL-CONVENTION
    STATUS current
    DESCRIPTION "None"
    SYNTAX Counter64

Ipaddr ::= TEXTUAL-CONVENTION
    DISPLAY-HINT "47a"
    STATUS current
    DESCRIPTION "None"
    SYNTAX OCTET STRING(SIZE(1..47))

String ::= TEXTUAL-CONVENTION
    DISPLAY-HINT "79a"
    STATUS current
    DESCRIPTION "None"
    SYNTAX OCTET STRING(SIZE(0..79))

Time ::= TEXTUAL-CONVENTION
    DISPLAY-HINT "9a"
    STATUS current
    DESCRIPTION "None"
    SYNTAX OCTET STRING(SIZE(1..9))



END -- End module
