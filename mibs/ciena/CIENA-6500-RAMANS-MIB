-- This file was automatically generated from ciena-6500-ramans.yang. Do not edit.

CIENA-6500-RAMANS-MIB DEFINITIONS ::= BEGIN

IMPORTS
    Aid, Decimal, Int, String, Time
        FROM CIENA-6500-TYPES-MIB
    cienaGenericMIBs
        FROM CIENA-SMI
    MODULE-COMPLIANCE, OBJECT-GROUP
        FROM SNMPv2-CONF
    Integer32, MODULE-IDENTITY, OBJECT-TYPE
        FROM SNMPv2-SMI;

ciena6500RamansMIB MODULE-IDENTITY
    LAST-UPDATED "201812310000Z"
    ORGANIZATION "Ciena Corporation"
    CONTACT-INFO "Web URL: http://www.ciena.com"
    DESCRIPTION "This modules describes Ciena's ramans object for the 6500 platform"
    REVISION "201812310000Z"
    DESCRIPTION "Initial Draft"
    ::= { cienaGenericMIBs 201 }

c6500RamansRamansRamanTable OBJECT-TYPE
    SYNTAX SEQUENCE OF C6500RamansRamansRamanEntry
    MAX-ACCESS not-accessible
    STATUS current
    DESCRIPTION "None"
    ::= { ciena6500RamansMIB 3 }

c6500RamansRamansRamanEntry OBJECT-TYPE
    SYNTAX C6500RamansRamansRamanEntry
    MAX-ACCESS not-accessible
    STATUS current
    DESCRIPTION "Entry for c6500RamansRamansRamanTable."
    INDEX { c6500RamansRamansRamanRaman }
    ::= { c6500RamansRamansRamanTable 1 }

C6500RamansRamansRamanEntry ::= SEQUENCE { 
    c6500RamansRamansRamanRaman OCTET STRING,
    c6500RamansRamansRamanTargPow Decimal,
    c6500RamansRamansRamanTurnOnThres Decimal,
    c6500RamansRamansRamanAprThres Decimal,
    c6500RamansRamansRamanPumpRatio1 Decimal,
    c6500RamansRamansRamanPumpRatio2 Decimal,
    c6500RamansRamansRamanPumpRatio3 Decimal,
    c6500RamansRamansRamanPumpRatio4 Decimal,
    c6500RamansRamansRamanPst INTEGER,
    c6500RamansRamansRamanFiberPinchThresh Decimal,
    c6500RamansRamansRamanRamanMode INTEGER,
    c6500RamansRamansRamanPumpMode INTEGER,
    c6500RamansRamansRamanGainMode INTEGER,
    c6500RamansRamansRamanResPumpPwrThresh Decimal,
    c6500RamansRamansRamanTargGain Decimal,
    c6500RamansRamansRamanRecommendedGain Decimal,
    c6500RamansRamansRamanTargGainTilt Decimal,
    c6500RamansRamansRamanCalibrated INTEGER,
    c6500RamansRamansRamanForcedShutoff INTEGER,
    c6500RamansRamansRamanTgtUnachMin Decimal,
    c6500RamansRamansRamanTargPowPassword OCTET STRING,
    c6500RamansRamansRamanPump1Power Decimal,
    c6500RamansRamansRamanPump2Power Decimal,
    c6500RamansRamansRamanPump3Power Decimal,
    c6500RamansRamansRamanPump4Power Decimal,
    c6500RamansRamansRamanOperMode INTEGER,
    c6500RamansRamansRamanCalcGain Decimal,
    c6500RamansRamansRamanAinsTimeLeft Time,
    c6500RamansRamansRamanInputLosThres Decimal,
    c6500RamansRamansRamanShutoffThres Decimal,
    c6500RamansRamansRamanAprTargPow Decimal,
    c6500RamansRamansRamanInputLoss Decimal,
    c6500RamansRamansRamanAutoShutoffPassword OCTET STRING,
    c6500RamansRamansRamanAutoShutoffDisabledTime Int 
}

c6500RamansRamansRamanRaman OBJECT-TYPE
    SYNTAX OCTET STRING(SIZE(1..80))
    MAX-ACCESS not-accessible
    STATUS current
    DESCRIPTION "AID in format RAMAN-shelf-slot-port, RAMAN-shelf-ALL, RAMAN-shelf-slot-ALL, SHELF-shelf-ALL"
    ::= { c6500RamansRamansRamanEntry 1 }

c6500RamansRamansRamanTargPow OBJECT-TYPE
    SYNTAX Decimal
    MAX-ACCESS read-only
    STATUS current
    DESCRIPTION "Target Power."
    ::= { c6500RamansRamansRamanEntry 2 }

c6500RamansRamansRamanTurnOnThres OBJECT-TYPE
    SYNTAX Decimal
    MAX-ACCESS read-only
    STATUS current
    DESCRIPTION "OSC Turn On Threshold."
    ::= { c6500RamansRamansRamanEntry 3 }

c6500RamansRamansRamanAprThres OBJECT-TYPE
    SYNTAX Decimal
    MAX-ACCESS read-only
    STATUS current
    DESCRIPTION "APR Threshold."
    ::= { c6500RamansRamansRamanEntry 4 }

c6500RamansRamansRamanPumpRatio1 OBJECT-TYPE
    SYNTAX Decimal
    MAX-ACCESS read-only
    STATUS current
    DESCRIPTION "Pump 1 Power Ratio"
    ::= { c6500RamansRamansRamanEntry 5 }

c6500RamansRamansRamanPumpRatio2 OBJECT-TYPE
    SYNTAX Decimal
    MAX-ACCESS read-only
    STATUS current
    DESCRIPTION "Pump 2 Power Ratio"
    ::= { c6500RamansRamansRamanEntry 6 }

c6500RamansRamansRamanPumpRatio3 OBJECT-TYPE
    SYNTAX Decimal
    MAX-ACCESS read-only
    STATUS current
    DESCRIPTION "Pump 3 Power Ratio"
    ::= { c6500RamansRamansRamanEntry 7 }

c6500RamansRamansRamanPumpRatio4 OBJECT-TYPE
    SYNTAX Decimal
    MAX-ACCESS read-only
    STATUS current
    DESCRIPTION "Pump 4 Power Ratio"
    ::= { c6500RamansRamansRamanEntry 8 }

c6500RamansRamansRamanPst OBJECT-TYPE
    SYNTAX INTEGER { is(0), oosMa(1), isAnr(2), oosAu(3), oosAuma(4), oosMaanr(5) }
    MAX-ACCESS read-only
    STATUS current
    DESCRIPTION "Identify the primary state"
    ::= { c6500RamansRamansRamanEntry 9 }

c6500RamansRamansRamanFiberPinchThresh OBJECT-TYPE
    SYNTAX Decimal
    MAX-ACCESS read-only
    STATUS current
    DESCRIPTION "Fiber Pinch Threshold."
    ::= { c6500RamansRamansRamanEntry 10 }

c6500RamansRamansRamanRamanMode OBJECT-TYPE
    SYNTAX INTEGER { auto(0), manual(1), maxgain(2) }
    MAX-ACCESS read-only
    STATUS current
    DESCRIPTION "Provisioned mode for RAMAN Pumps."
    ::= { c6500RamansRamansRamanEntry 11 }

c6500RamansRamansRamanPumpMode OBJECT-TYPE
    SYNTAX INTEGER { cw(0), pwm(1) }
    MAX-ACCESS read-only
    STATUS current
    DESCRIPTION "Mode of operation for RAMAN Pumps."
    ::= { c6500RamansRamansRamanEntry 12 }

c6500RamansRamansRamanGainMode OBJECT-TYPE
    SYNTAX INTEGER { provisioned(0), recommended(1) }
    MAX-ACCESS read-only
    STATUS current
    DESCRIPTION "Provisioned gain mode for RAMAN Pumps."
    ::= { c6500RamansRamansRamanEntry 13 }

c6500RamansRamansRamanResPumpPwrThresh OBJECT-TYPE
    SYNTAX Decimal
    MAX-ACCESS read-only
    STATUS current
    DESCRIPTION "Residual Pump Power Threshold."
    ::= { c6500RamansRamansRamanEntry 14 }

c6500RamansRamansRamanTargGain OBJECT-TYPE
    SYNTAX Decimal
    MAX-ACCESS read-only
    STATUS current
    DESCRIPTION "Provisioned Gain for Raman pumps."
    ::= { c6500RamansRamansRamanEntry 15 }

c6500RamansRamansRamanRecommendedGain OBJECT-TYPE
    SYNTAX Decimal
    MAX-ACCESS read-only
    STATUS current
    DESCRIPTION "Recommended Gain for Raman pumps."
    ::= { c6500RamansRamansRamanEntry 16 }

c6500RamansRamansRamanTargGainTilt OBJECT-TYPE
    SYNTAX Decimal
    MAX-ACCESS read-only
    STATUS current
    DESCRIPTION "Gain Tilt of Raman pumps."
    ::= { c6500RamansRamansRamanEntry 17 }

c6500RamansRamansRamanCalibrated OBJECT-TYPE
    SYNTAX INTEGER { notcalibrated(0), calibrated(1), recalibrationrequired(2), calibrationnotrequired(3) }
    MAX-ACCESS read-only
    STATUS current
    DESCRIPTION "State of Raman pump DOC calibration."
    ::= { c6500RamansRamansRamanEntry 18 }

c6500RamansRamansRamanForcedShutoff OBJECT-TYPE
    SYNTAX INTEGER { true(0), false(1) }
    MAX-ACCESS read-only
    STATUS current
    DESCRIPTION "Force Shutoff of Raman pumps."
    ::= { c6500RamansRamansRamanEntry 19 }

c6500RamansRamansRamanTgtUnachMin OBJECT-TYPE
    SYNTAX Decimal
    MAX-ACCESS read-only
    STATUS current
    DESCRIPTION "Target Unachievable Minor Threshold."
    ::= { c6500RamansRamansRamanEntry 20 }

c6500RamansRamansRamanTargPowPassword OBJECT-TYPE
    SYNTAX OCTET STRING(SIZE(8..10))
    MAX-ACCESS read-only
    STATUS current
    DESCRIPTION "Target Power Password"
    ::= { c6500RamansRamansRamanEntry 21 }

c6500RamansRamansRamanPump1Power OBJECT-TYPE
    SYNTAX Decimal
    MAX-ACCESS read-only
    STATUS current
    DESCRIPTION "Actual Pump1 Power"
    ::= { c6500RamansRamansRamanEntry 22 }

c6500RamansRamansRamanPump2Power OBJECT-TYPE
    SYNTAX Decimal
    MAX-ACCESS read-only
    STATUS current
    DESCRIPTION "Actual Pump2 Power"
    ::= { c6500RamansRamansRamanEntry 23 }

c6500RamansRamansRamanPump3Power OBJECT-TYPE
    SYNTAX Decimal
    MAX-ACCESS read-only
    STATUS current
    DESCRIPTION "Actual Pump3 Power"
    ::= { c6500RamansRamansRamanEntry 24 }

c6500RamansRamansRamanPump4Power OBJECT-TYPE
    SYNTAX Decimal
    MAX-ACCESS read-only
    STATUS current
    DESCRIPTION "Actual Pump4 Power"
    ::= { c6500RamansRamansRamanEntry 25 }

c6500RamansRamansRamanOperMode OBJECT-TYPE
    SYNTAX INTEGER { normal(0), apr(1), shutoff(2) }
    MAX-ACCESS read-only
    STATUS current
    DESCRIPTION "Provides the operating state of the RAMAN Pumps."
    ::= { c6500RamansRamansRamanEntry 26 }

c6500RamansRamansRamanCalcGain OBJECT-TYPE
    SYNTAX Decimal
    MAX-ACCESS read-only
    STATUS current
    DESCRIPTION "Calculated Gain of Raman pumps."
    ::= { c6500RamansRamansRamanEntry 27 }

c6500RamansRamansRamanAinsTimeLeft OBJECT-TYPE
    SYNTAX Time
    MAX-ACCESS read-only
    STATUS current
    DESCRIPTION "AINS time left HH-MM"
    ::= { c6500RamansRamansRamanEntry 28 }

c6500RamansRamansRamanInputLosThres OBJECT-TYPE
    SYNTAX Decimal
    MAX-ACCESS read-only
    STATUS current
    DESCRIPTION "OSC Input LOS Threshold."
    ::= { c6500RamansRamansRamanEntry 29 }

c6500RamansRamansRamanShutoffThres OBJECT-TYPE
    SYNTAX Decimal
    MAX-ACCESS read-only
    STATUS current
    DESCRIPTION "OSC Shut Off Threshold."
    ::= { c6500RamansRamansRamanEntry 30 }

c6500RamansRamansRamanAprTargPow OBJECT-TYPE
    SYNTAX Decimal
    MAX-ACCESS read-only
    STATUS current
    DESCRIPTION "APR Target Power"
    ::= { c6500RamansRamansRamanEntry 31 }

c6500RamansRamansRamanInputLoss OBJECT-TYPE
    SYNTAX Decimal
    MAX-ACCESS read-only
    STATUS current
    DESCRIPTION "Input Connector Loss"
    ::= { c6500RamansRamansRamanEntry 32 }

c6500RamansRamansRamanAutoShutoffPassword OBJECT-TYPE
    SYNTAX OCTET STRING(SIZE(8..10))
    MAX-ACCESS read-only
    STATUS current
    DESCRIPTION "Auto Shutoff Disabled Password"
    ::= { c6500RamansRamansRamanEntry 33 }

c6500RamansRamansRamanAutoShutoffDisabledTime OBJECT-TYPE
    SYNTAX Int
    MAX-ACCESS read-only
    STATUS current
    DESCRIPTION "Auto Shutoff Disabled Time"
    ::= { c6500RamansRamansRamanEntry 34 }

c6500RamansRamansRamanSstTable OBJECT-TYPE
    SYNTAX SEQUENCE OF C6500RamansRamansRamanSstEntry
    MAX-ACCESS not-accessible
    STATUS current
    DESCRIPTION "Identify the secondary state"
    ::= { ciena6500RamansMIB 4 }

c6500RamansRamansRamanSstEntry OBJECT-TYPE
    SYNTAX C6500RamansRamansRamanSstEntry
    MAX-ACCESS not-accessible
    STATUS current
    DESCRIPTION "Entry for c6500RamansRamansRamanSstTable."
    INDEX { c6500RamansRamansRamanSstRamanRaman, c6500RamansRamansRamanSstTableSnmpKey }
    ::= { c6500RamansRamansRamanSstTable 1 }

C6500RamansRamansRamanSstEntry ::= SEQUENCE { 
    c6500RamansRamansRamanSstRamanRaman OCTET STRING,
    c6500RamansRamansRamanSstTableSnmpKey Integer32,
    c6500RamansRamansRamanSst INTEGER 
}

c6500RamansRamansRamanSstRamanRaman OBJECT-TYPE
    SYNTAX OCTET STRING(SIZE(1..80))
    MAX-ACCESS not-accessible
    STATUS current
    DESCRIPTION "AID in format RAMAN-shelf-slot-port, RAMAN-shelf-ALL, RAMAN-shelf-slot-ALL, SHELF-shelf-ALL"
    ::= { c6500RamansRamansRamanSstEntry 1 }

c6500RamansRamansRamanSstTableSnmpKey OBJECT-TYPE
    SYNTAX Integer32(0..2147483647)
    MAX-ACCESS not-accessible
    STATUS current
    DESCRIPTION "Unique key for c6500RamansRamansRamanSst"
    ::= { c6500RamansRamansRamanSstEntry 2 }

c6500RamansRamansRamanSst OBJECT-TYPE
    SYNTAX INTEGER { ains(0), ainsDea(1), bridged(2), switched(3), roll(4), act(5), idle(6), stbys(7), wrk(8), erranl(9), psi(10), flt(11), mea(12), tstf(13), ueq(14), sgeo(15), discd(16), lpbk(17), ts(18), faf(19), stbyh(20), wrkrx(21), wrktx(22), prtcl(23), uas(24), nosite(25), noam(26), mon(27), msc(28), protected(29), mt(30), dsbld(31), inhip(32), l2dsbld(33), tsgen(34), tsmon(35), tsrecirc(36) }
    MAX-ACCESS read-only
    STATUS current
    DESCRIPTION "Identify the secondary state"
    ::= { c6500RamansRamansRamanSstEntry 3 }

c6500RamansRamansPasswordStateTable OBJECT-TYPE
    SYNTAX SEQUENCE OF C6500RamansRamansPasswordStateEntry
    MAX-ACCESS not-accessible
    STATUS current
    DESCRIPTION "None"
    ::= { ciena6500RamansMIB 5 }

c6500RamansRamansPasswordStateEntry OBJECT-TYPE
    SYNTAX C6500RamansRamansPasswordStateEntry
    MAX-ACCESS not-accessible
    STATUS current
    DESCRIPTION "Entry for c6500RamansRamansPasswordStateTable."
    INDEX { c6500RamansRamansPasswordStateShelf }
    ::= { c6500RamansRamansPasswordStateTable 1 }

C6500RamansRamansPasswordStateEntry ::= SEQUENCE { 
    c6500RamansRamansPasswordStateShelf OCTET STRING,
    c6500RamansRamansPasswordStateTargPowPassword String 
}

c6500RamansRamansPasswordStateShelf OBJECT-TYPE
    SYNTAX OCTET STRING(SIZE(1..80))
    MAX-ACCESS not-accessible
    STATUS current
    DESCRIPTION "AID in format SHELF-shelf"
    ::= { c6500RamansRamansPasswordStateEntry 1 }

c6500RamansRamansPasswordStateTargPowPassword OBJECT-TYPE
    SYNTAX String
    MAX-ACCESS read-only
    STATUS current
    DESCRIPTION "SET if Raman password set, NOT_SET otherwise"
    ::= { c6500RamansRamansPasswordStateEntry 2 }

c6500RamansRamansOverrideTable OBJECT-TYPE
    SYNTAX SEQUENCE OF C6500RamansRamansOverrideEntry
    MAX-ACCESS not-accessible
    STATUS current
    DESCRIPTION "None"
    ::= { ciena6500RamansMIB 6 }

c6500RamansRamansOverrideEntry OBJECT-TYPE
    SYNTAX C6500RamansRamansOverrideEntry
    MAX-ACCESS not-accessible
    STATUS current
    DESCRIPTION "Entry for c6500RamansRamansOverrideTable."
    INDEX { c6500RamansRamansOverrideRaman }
    ::= { c6500RamansRamansOverrideTable 1 }

C6500RamansRamansOverrideEntry ::= SEQUENCE { 
    c6500RamansRamansOverrideRaman OCTET STRING,
    c6500RamansRamansOverrideOverridePassword OCTET STRING 
}

c6500RamansRamansOverrideRaman OBJECT-TYPE
    SYNTAX OCTET STRING(SIZE(1..80))
    MAX-ACCESS not-accessible
    STATUS current
    DESCRIPTION "AID in format RAMAN-shelf-slot-port"
    ::= { c6500RamansRamansOverrideEntry 1 }

c6500RamansRamansOverrideOverridePassword OBJECT-TYPE
    SYNTAX OCTET STRING(SIZE(8..10))
    MAX-ACCESS read-only
    STATUS current
    DESCRIPTION "Override Password(Mandatory for edit operations)"
    ::= { c6500RamansRamansOverrideEntry 2 }

c6500RamansRamansOverrideOtdrTable OBJECT-TYPE
    SYNTAX SEQUENCE OF C6500RamansRamansOverrideOtdrEntry
    MAX-ACCESS not-accessible
    STATUS current
    DESCRIPTION "State of the Raman pumps to turn on when OTDR failed(Mandatory for edit operations)"
    ::= { ciena6500RamansMIB 7 }

c6500RamansRamansOverrideOtdrEntry OBJECT-TYPE
    SYNTAX C6500RamansRamansOverrideOtdrEntry
    MAX-ACCESS not-accessible
    STATUS current
    DESCRIPTION "Entry for c6500RamansRamansOverrideOtdrTable."
    INDEX { c6500RamansRamansOverrideOtdrOverrideRaman, c6500RamansRamansOverrideOtdrTableSnmpKey }
    ::= { c6500RamansRamansOverrideOtdrTable 1 }

C6500RamansRamansOverrideOtdrEntry ::= SEQUENCE { 
    c6500RamansRamansOverrideOtdrOverrideRaman OCTET STRING,
    c6500RamansRamansOverrideOtdrTableSnmpKey Integer32,
    c6500RamansRamansOverrideOtdr INTEGER 
}

c6500RamansRamansOverrideOtdrOverrideRaman OBJECT-TYPE
    SYNTAX OCTET STRING(SIZE(1..80))
    MAX-ACCESS not-accessible
    STATUS current
    DESCRIPTION "AID in format RAMAN-shelf-slot-port"
    ::= { c6500RamansRamansOverrideOtdrEntry 1 }

c6500RamansRamansOverrideOtdrTableSnmpKey OBJECT-TYPE
    SYNTAX Integer32(0..2147483647)
    MAX-ACCESS not-accessible
    STATUS current
    DESCRIPTION "Unique key for c6500RamansRamansOverrideOtdr"
    ::= { c6500RamansRamansOverrideOtdrEntry 2 }

c6500RamansRamansOverrideOtdr OBJECT-TYPE
    SYNTAX INTEGER { enable(0), disable(1) }
    MAX-ACCESS read-only
    STATUS current
    DESCRIPTION "State of the Raman pumps to turn on when OTDR failed(Mandatory for edit operations)"
    ::= { c6500RamansRamansOverrideOtdrEntry 3 }



-- Conformance statements
ciena6500RamansObjects OBJECT IDENTIFIER
    ::= { ciena6500RamansMIB 1 }

ciena6500RamansConformance OBJECT IDENTIFIER
    ::= { ciena6500RamansMIB 2 }

ciena6500RamansGroups OBJECT IDENTIFIER
    ::= { ciena6500RamansConformance 1 }

ciena6500RamansGroup OBJECT-GROUP
    OBJECTS { 
        c6500RamansRamansRamanTargPow,
        c6500RamansRamansRamanTurnOnThres,
        c6500RamansRamansRamanAprThres,
        c6500RamansRamansRamanPumpRatio1,
        c6500RamansRamansRamanPumpRatio2,
        c6500RamansRamansRamanPumpRatio3,
        c6500RamansRamansRamanPumpRatio4,
        c6500RamansRamansRamanPst,
        c6500RamansRamansRamanFiberPinchThresh,
        c6500RamansRamansRamanRamanMode,
        c6500RamansRamansRamanPumpMode,
        c6500RamansRamansRamanGainMode,
        c6500RamansRamansRamanResPumpPwrThresh,
        c6500RamansRamansRamanTargGain,
        c6500RamansRamansRamanRecommendedGain,
        c6500RamansRamansRamanTargGainTilt,
        c6500RamansRamansRamanCalibrated,
        c6500RamansRamansRamanForcedShutoff,
        c6500RamansRamansRamanTgtUnachMin,
        c6500RamansRamansRamanTargPowPassword,
        c6500RamansRamansRamanPump1Power,
        c6500RamansRamansRamanPump2Power,
        c6500RamansRamansRamanPump3Power,
        c6500RamansRamansRamanPump4Power,
        c6500RamansRamansRamanOperMode,
        c6500RamansRamansRamanCalcGain,
        c6500RamansRamansRamanAinsTimeLeft,
        c6500RamansRamansRamanInputLosThres,
        c6500RamansRamansRamanShutoffThres,
        c6500RamansRamansRamanAprTargPow,
        c6500RamansRamansRamanInputLoss,
        c6500RamansRamansRamanAutoShutoffPassword,
        c6500RamansRamansRamanAutoShutoffDisabledTime,
        c6500RamansRamansPasswordStateTargPowPassword,
        c6500RamansRamansOverrideOverridePassword
    }
    STATUS current
    DESCRIPTION "Conformance Group"
    ::= { ciena6500RamansGroups 1 }

ciena6500RamansCompliances OBJECT IDENTIFIER
    ::= { ciena6500RamansConformance 2 }

ciena6500RamansCompliance MODULE-COMPLIANCE
    STATUS current
    DESCRIPTION "Compliance"
    MODULE MANDATORY-GROUPS { ciena6500RamansGroup }
    ::= { ciena6500RamansCompliances 1 }

END -- End module
