-- This file was included in WWP MIB release 04-10-01-0027
--
-- WWP-LEOS-8021X-MIB.my
-- MIB generated by MG-SOFT Visual MIB Builder Version 6.0  Build 88
-- Sunday, August 28, 2005 at 19:49:14
--


	WWP-LEOS-8021X-MIB DEFINITIONS ::= BEGIN
 
		IMPORTS
			Integer32, OBJECT-TYPE, MODULE-IDENTITY			
				FROM SNMPv2-SMI				
			DisplayString, TruthValue			
			    FROM SNMPv2-TC						   		
			wwpModulesLeos			
				FROM WWP-SMI;	
	
		-- 1.3.6.1.4.1.6141.2.60.401
		wwpLeos8021xMibModule MODULE-IDENTITY 
			LAST-UPDATED "200508281935Z"		-- August 28, 2005 at 19:35 GMT
			ORGANIZATION 
				"Ciena, Inc"
			CONTACT-INFO
				"   Mib Meister
		  			115 North Sullivan Road
					Spokane Valley, WA 99037
		        	USA		 		
		        	Phone:  +1 509 242 9000
					Email:  support@ciena.com"
			DESCRIPTION 
				"Description."

			REVISION
				"200508281935Z"
			DESCRIPTION
			    	"Initial version."

			::= { wwpModulesLeos 401 }

		
	
--
-- Node definitions
--
	
		-- 1.3.6.1.4.1.6141.2.60.401.1
		wwpLeos8021xMIB OBJECT IDENTIFIER ::= { wwpLeos8021xMibModule 1 }

		
		-- 1.3.6.1.4.1.6141.2.60.401.1.1
		wwpLeos8021xConf OBJECT IDENTIFIER ::= { wwpLeos8021xMIB 1 }

		
		-- 1.3.6.1.4.1.6141.2.60.401.1.1.1
		wwpLeos8021xGroups OBJECT IDENTIFIER ::= { wwpLeos8021xConf 1 }

		
	       
		
		-- 1.3.6.1.4.1.6141.2.60.401.1.1.2
		wwpLeos8021xCompls OBJECT IDENTIFIER ::= { wwpLeos8021xConf 2 }

		
		-- 1.3.6.1.4.1.6141.2.60.401.1.2
		wwpLeos8021xObjs OBJECT IDENTIFIER ::= { wwpLeos8021xMIB 2 }

		-- 1.3.6.1.4.1.6141.2.60.401.1.2.1
		wwpLeos8021xPortTable OBJECT-TYPE
			SYNTAX SEQUENCE OF WwpLeos8021xPortEntry
			MAX-ACCESS not-accessible
			STATUS current
			DESCRIPTION
				"Table with an entry for every port on the switch"
			::= { wwpLeos8021xObjs 1 }

		
		-- 1.3.6.1.4.1.6141.2.60.401.1.2.1.1
		wwpLeos8021xPortEntry OBJECT-TYPE
			SYNTAX WwpLeos8021xPortEntry
			MAX-ACCESS not-accessible
			STATUS current
			DESCRIPTION
				"Description."
			INDEX { wwpLeos8021xPort }
			::= { wwpLeos8021xPortTable 1 }

		
		WwpLeos8021xPortEntry ::=
			SEQUENCE { 
				wwpLeos8021xPort					INTEGER,
				wwpLeos8021xRole					INTEGER,
				wwpLeos8021xAuthPortStatsClear		INTEGER			
			 }

		-- 1.3.6.1.4.1.6141.2.60.401.1.2.1.1.1
		wwpLeos8021xPort OBJECT-TYPE
			SYNTAX INTEGER (1..1000)
			MAX-ACCESS read-only
			STATUS current
			DESCRIPTION
				"Switch Ethernet Port"
			::= { wwpLeos8021xPortEntry 1 }

		
		-- 1.3.6.1.4.1.6141.2.60.401.1.2.1.1.2
		wwpLeos8021xRole OBJECT-TYPE
			SYNTAX INTEGER
				{
				none(1),
				supplicant(2),
				authenticator(3),
				both(4)
				}
			MAX-ACCESS read-write
			STATUS current
			DESCRIPTION
				"802.1x role of the Port."
			::= { wwpLeos8021xPortEntry 2 }         	    				
		
		wwpLeos8021xAuthPortStatsClear OBJECT-TYPE
			SYNTAX 		TruthValue			
			MAX-ACCESS 	read-write
			STATUS 		current
			DESCRIPTION
				"Setting this MIB object to 'true' will clear the authenticator port statistics."
			::= { wwpLeos8021xPortEntry 3 }
					
					-- 1.3.6.1.4.1.6141.2.60.401.1.3
		wwpLeos8021xEvents OBJECT IDENTIFIER ::= { wwpLeos8021xMIB 3 }

		
		-- 1.3.6.1.4.1.6141.2.60.401.1.3.0
		wwpLeos8021xEventsV2 OBJECT IDENTIFIER ::= { wwpLeos8021xEvents 0 }

	--
	-- Extension to dot1xSuppConfigTable Supplicant MIB
	--		        
		-- 1.3.6.1.4.1.6141.2.60.401.1.2.2
		wwpLeos8021xSuppTable OBJECT-TYPE
			SYNTAX SEQUENCE OF WwpLeos8021xSuppEntry
			MAX-ACCESS not-accessible
			STATUS current
			DESCRIPTION
				"A table that contains the configuration objects for the
 				 Supplicant PAE associated with each port.
 				 An entry appears in this table for each port that may
 				 authenticate itself when challenged by a remote system."
			::= { wwpLeos8021xObjs 2 }
		
		-- 1.3.6.1.4.1.6141.2.60.401.1.2.2.1
		wwpLeos8021xSuppEntry OBJECT-TYPE
			SYNTAX WwpLeos8021xSuppEntry
			MAX-ACCESS not-accessible
			STATUS current
			DESCRIPTION
				"The configuration information for a Supplicant PAE."
			INDEX { wwpLeos8021xSuppPort }
			::= { wwpLeos8021xSuppTable 1 }
		
		WwpLeos8021xSuppEntry ::=
			SEQUENCE { 
				wwpLeos8021xSuppPort				Integer32,
				wwpLeos8021xSuppUserName			DisplayString,
				wwpLeos8021xSuppPassword			DisplayString,
				wwpLeos8021xSuppPortStatsClear		INTEGER,
				wwpLeos8021xSuppEAPMethod			INTEGER				
			 }
                                                            
		-- 1.3.6.1.4.1.6141.2.60.401.1.2.2.1.1
		wwpLeos8021xSuppPort OBJECT-TYPE
			SYNTAX 		Integer32 (1..1000)
			MAX-ACCESS 	read-only
			STATUS 		current
			DESCRIPTION
				"The MIB object is used as an index in the table and specifies the port."
			::= { wwpLeos8021xSuppEntry 1 }
        
		-- 1.3.6.1.4.1.6141.2.60.401.1.2.2.1.2
		wwpLeos8021xSuppUserName OBJECT-TYPE
			SYNTAX 		DisplayString (SIZE(0..15))
			MAX-ACCESS 	read-write
			STATUS 		current
			DESCRIPTION
				"The username that shall be used along with the password specified by wwpLeos8021xSuppPassword
				 to gain access to the PAE resources.
				 Setting this object to 0 will reset the username."
			::= { wwpLeos8021xSuppEntry 2 }
         
        wwpLeos8021xSuppPassword OBJECT-TYPE
			SYNTAX 		DisplayString (SIZE(0..15))
			MAX-ACCESS 	read-write
			STATUS 		current
			DESCRIPTION
				"The password that shall be used along with the username specified by wwpLeos8021xSuppUserName to gain access on port.
				 Setting this object to 0 will reset the password.	Doing a get on this object will always return NULL for security reasons."
			::= { wwpLeos8021xSuppEntry 3 } 
			
	    wwpLeos8021xSuppPortStatsClear OBJECT-TYPE
			SYNTAX 		TruthValue			
			MAX-ACCESS 	read-write
			STATUS 		current
			DESCRIPTION
				"Setting this MIB object to 'true' will clear the supplicant port statistics."
			::= { wwpLeos8021xSuppEntry 5 }
        
        wwpLeos8021xSuppEAPMethod OBJECT-TYPE
			SYNTAX 		INTEGER	{
								eapMd5(1)
			}		
			MAX-ACCESS 	read-write
			STATUS 		current
			DESCRIPTION
				"Extensible Authentication Protocol associated with this supplicant."
			::= { wwpLeos8021xSuppEntry 10 }
        
     wwpLeos8021xGlobalAttrs OBJECT IDENTIFIER ::= { wwpLeos8021xObjs 3 }
                
	 wwpLeos8021xAuthStatsClear OBJECT-TYPE
			SYNTAX 		TruthValue			
			MAX-ACCESS 	read-write
			STATUS 		current
			DESCRIPTION
				"Setting this MIB object to 'true' will clear the authenticator global statistics."
			::= { wwpLeos8021xGlobalAttrs 1 }                
     
     wwpLeos8021xSuppStatsClear OBJECT-TYPE
			SYNTAX 		TruthValue			
			MAX-ACCESS 	read-write
			STATUS 		current
			DESCRIPTION
				"Setting this MIB object to 'true' will clear the supplicant global statistics."
			::= { wwpLeos8021xGlobalAttrs 2 }                
	
	END

--
-- WWP-LEOS-8021X-MIB.my
--
