NORTEL-GENERIC-MIB DEFINITIONS ::= BEGIN

IMPORTS
 
       MODULE-IDENTITY, OBJECT-IDENTITY, enterprises
           FROM SNMPv2-SMI;

nortelGenericMIBs  MODULE-IDENTITY
	    LAST-UPDATED "200802070000Z"    
	    ORGANIZATION "Nortel Networks"
	    CONTACT-INFO
           "   7035 Ridge Road
               Hanover, Maryland 21076
               United States
               Toll-free: +1-800-921-1144
               Phone: +1-410-694-5700
               Fax: +1-410-694-5750
               www.ciena.com "
       DESCRIPTION  
               "This module represents the top-level MIB branch for some of the generic MIBs that are common to NortelNetworks products."

       -- Revision history
       REVISION "200802070000Z"
       DESCRIPTION
                " Removed Draft."

       REVISION "200305010000Z"
       DESCRIPTION
                " Updated with Generic Contact Information"
            
       REVISION "9906240000Z"
       DESCRIPTION
                " The fourth version of this MIB module. Module name changed."
                
       REVISION "199904120000Z"
       DESCRIPTION
                " The second version of this MIB module."
            
       REVISION "199903220000Z"
       DESCRIPTION
                " The first version of this MIB module."
            
               ::= { nortel 29 }

nortel OBJECT IDENTIFIER ::= {enterprises 562}    

END
