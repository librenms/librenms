-- *****************************************************************
-- Moxa Industrial Wireless AP AWK-4131A MIB
-- version 1.17 build 21091612
--
-- Copyright (c) 2021 by Moxa Inc.
-- All rights reserved.
-- *****************************************************************

MOXA-AWK4131A-MIB DEFINITIONS ::= BEGIN

    IMPORTS
        enterprises, IpAddress, OBJECT-TYPE
            FROM SNMPv2-SMI
        DateAndTime, TEXTUAL-CONVENTION, MacAddress, DisplayString
            FROM SNMPv2-TC;

    moxa OBJECT IDENTIFIER ::= { enterprises 8691 } -- 1.3.6.1.4.1.8691

    industrialWirelessLan OBJECT IDENTIFIER ::= { moxa 15 } -- 1.3.6.1.4.1.8691.15

    awk4131A MODULE-IDENTITY
        LAST-UPDATED "202109161204Z"
        ORGANIZATION "Moxa Inc."
        CONTACT-INFO
            "Postal: Moxa Inc.
             Fl.4, No.135, Lane 235, Pao-Chiao Rd.
             Xindian Dist., New Taipei City, Taiwan
             E-mail: support@moxa.com
             Tel: +866-2-89191230 "
        DESCRIPTION
            "The MIB module for Moxa AWK-4131A series specific information."
        ::= { industrialWirelessLan 34 } -- 1.3.6.1.4.1.8691.15.34

-- -------------------------------------------------------------
-- groups in the MOXA IndustrialWireless  AWK-4131A MIB
-- -------------------------------------------------------------

    swMgmt OBJECT IDENTIFIER ::= { awk4131A 1 } -- 1.3.6.1.4.1.8691.15.34.1

-- -------------------------------------------------------------
-- Textual Conventions
-- -------------------------------------------------------------

    PortList ::= TEXTUAL-CONVENTION
        STATUS current
        DESCRIPTION
            "Each octet within this value specifies a set of eight
             ports, with the first octet specifying ports 1 through
             8, the second octet specifying ports 9 through 16, etc.
             Within each octet, the most significant bit represents
             the lowest numbered port, and the least significant bit
             represents the highest numbered port.  Thus, each port
             of the bridge is represented by a single bit within the
             value of this object.  If that bit has a value of '1'
             then that port is included in the set of ports; the port
             is not included if its bit has a value of '0'."
        SYNTAX OCTET STRING

-- -------------------------------------------------------------
-- swMgmt group
-- -------------------------------------------------------------

    overview OBJECT IDENTIFIER ::= { swMgmt 1 }

        overviewModelName OBJECT-TYPE
            SYNTAX DisplayString
            MAX-ACCESS read-only
            STATUS current
            DESCRIPTION
                "Model name

                "
            ::= { overview 1 }

        overviewDeviceName OBJECT-TYPE
            SYNTAX DisplayString
            MAX-ACCESS read-write
            STATUS current
            DESCRIPTION
                "Device name

                "
            ::= { overview 2 }

        overviewSerialNumber OBJECT-TYPE
            SYNTAX DisplayString
            MAX-ACCESS read-only
            STATUS current
            DESCRIPTION
                "Serial number

                "
            ::= { overview 3 }

        overviewUpTime OBJECT-TYPE
            SYNTAX DisplayString
            MAX-ACCESS read-only
            STATUS current
            DESCRIPTION
                "System uptime

                "
            ::= { overview 4 }

        overviewFirmwareVersion OBJECT-TYPE
            SYNTAX DisplayString
            MAX-ACCESS read-only
            STATUS current
            DESCRIPTION
                "Firmware version

                "
            ::= { overview 5 }

        overviewMacAddress OBJECT-TYPE
            SYNTAX DisplayString
            MAX-ACCESS read-only
            STATUS current
            DESCRIPTION
                "Device MAC address

                "
            ::= { overview 6 }

        overviewDeviceLocation OBJECT-TYPE
            SYNTAX DisplayString
            MAX-ACCESS read-write
            STATUS current
            DESCRIPTION
                "Device location

                "
            ::= { overview 9 }

        overviewDeviceDescription OBJECT-TYPE
            SYNTAX DisplayString
            MAX-ACCESS read-write
            STATUS current
            DESCRIPTION
                "Device description

                "
            ::= { overview 10 }

        overviewDeviceContactInfo OBJECT-TYPE
            SYNTAX DisplayString
            MAX-ACCESS read-write
            STATUS current
            DESCRIPTION
                "Device contact information

                "
            ::= { overview 11 }

        overviewWebLoginMessage OBJECT-TYPE
            SYNTAX DisplayString
            MAX-ACCESS read-write
            STATUS current
            DESCRIPTION
                "Login Message

                "
            ::= { overview 30 }

        overviewWebLoginFailMessage OBJECT-TYPE
            SYNTAX DisplayString
            MAX-ACCESS read-write
            STATUS current
            DESCRIPTION
                "Login authentication failure message

                "
            ::= { overview 31 }

    basic OBJECT IDENTIFIER ::= { swMgmt 3 }

    netDev OBJECT IDENTIFIER ::= { basic 1 }

        netDevDhcpEnable OBJECT-TYPE
            SYNTAX INTEGER { enable(1), disable(2) }
            MAX-ACCESS read-write
            STATUS current
            DESCRIPTION
                "IP address assignment

                Value : 1 -> enable, 2 -> disable"
            ::= { netDev 1 }

        netDevIpV4Addr OBJECT-TYPE
            SYNTAX IpAddress
            MAX-ACCESS read-write
            STATUS current
            DESCRIPTION
                "IP address

                "
            ::= { netDev 2 }

        netDevIpV4Mask OBJECT-TYPE
            SYNTAX IpAddress
            MAX-ACCESS read-write
            STATUS current
            DESCRIPTION
                "Subnet mask

                "
            ::= { netDev 3 }

        netDevIpV4Gateway OBJECT-TYPE
            SYNTAX IpAddress
            MAX-ACCESS read-write
            STATUS current
            DESCRIPTION
                "Gateway

                "
            ::= { netDev 4 }

        netDevIpV4DnsTable OBJECT-TYPE
            SYNTAX SEQUENCE OF NetDevIpV4DnsEntry
            MAX-ACCESS not-accessible
            STATUS current
            DESCRIPTION
                "Table of netDevIpV4Dns"
            ::= { netDev 5 }

        netDevIpV4DnsEntry OBJECT-TYPE
            SYNTAX NetDevIpV4DnsEntry
            MAX-ACCESS not-accessible
            STATUS current
            DESCRIPTION
                "Entry of netDevIpV4Dns"
            INDEX { netDevIpV4DnsIndex }
            ::= { netDevIpV4DnsTable 1 }

        NetDevIpV4DnsEntry ::=
            SEQUENCE {
                netDevIpV4DnsIndex
                    INTEGER,
                netDevIpV4DnsData
                    IpAddress
            }

        netDevIpV4DnsIndex OBJECT-TYPE
            SYNTAX INTEGER (1..2)
            MAX-ACCESS read-only
            STATUS current
            DESCRIPTION
                "Index of IpV4Dns"
            ::= { netDevIpV4DnsEntry 1 }

        netDevIpV4DnsData OBJECT-TYPE
            SYNTAX IpAddress
            MAX-ACCESS read-write
            STATUS current
            DESCRIPTION
                "Primary DNS server

                "
            ::= { netDevIpV4DnsEntry 2 }

    time OBJECT IDENTIFIER ::= { basic 2 }

        timeNow OBJECT-TYPE
            SYNTAX INTEGER
            MAX-ACCESS read-write
            STATUS current
            DESCRIPTION
                "Current time in seconds since 1970/01/01
                "
            ::= { time 1 }

        timeTimeZone OBJECT-TYPE
            SYNTAX INTEGER (0..62)
            MAX-ACCESS read-write
            STATUS current
            DESCRIPTION
                "Time zone

                "
            ::= { time 2 }

        timeTimeServerTable OBJECT-TYPE
            SYNTAX SEQUENCE OF TimeTimeServerEntry
            MAX-ACCESS not-accessible
            STATUS current
            DESCRIPTION
                "Table of timeTimeServer"
            ::= { time 3 }

        timeTimeServerEntry OBJECT-TYPE
            SYNTAX TimeTimeServerEntry
            MAX-ACCESS not-accessible
            STATUS current
            DESCRIPTION
                "Entry of timeTimeServer"
            INDEX { timeTimeServerIndex }
            ::= { timeTimeServerTable 1 }

        TimeTimeServerEntry ::=
            SEQUENCE {
                timeTimeServerIndex
                    INTEGER,
                timeTimeServerData
                    DisplayString
            }

        timeTimeServerIndex OBJECT-TYPE
            SYNTAX INTEGER (1..2)
            MAX-ACCESS read-only
            STATUS current
            DESCRIPTION
                "Index of TimeServer"
            ::= { timeTimeServerEntry 1 }

        timeTimeServerData OBJECT-TYPE
            SYNTAX DisplayString
            MAX-ACCESS read-write
            STATUS current
            DESCRIPTION
                "Time server

                "
            ::= { timeTimeServerEntry 2 }

        timeQueryPeriod OBJECT-TYPE
            SYNTAX INTEGER (600..9999)
            MAX-ACCESS read-write
            STATUS current
            DESCRIPTION
                "Time sync interval

                "
            ::= { time 4 }

        timeDaylightSavingEnable OBJECT-TYPE
            SYNTAX INTEGER { enable(1), disable(2) }
            MAX-ACCESS read-write
            STATUS current
            DESCRIPTION
                "Enable

                Value : 1 -> enable, 2 -> disable"
            ::= { time 5 }

        timeDaylightSavingStartMonth OBJECT-TYPE
            SYNTAX INTEGER { january(1), february(2), march(3), april(4), may(5), june(6), july(7), augest(8), september(9), october(10), november(11), december(12) }
            MAX-ACCESS read-write
            STATUS current
            DESCRIPTION
                "DaylightSavingStartMonth
                Value : 1 -> january, 2 -> february, 3 -> march, 4 -> april, 5 -> may, 6 -> june, 7 -> july, 8 -> augest, 9 -> september, 10 -> october, 11 -> november, 12 -> december"
            ::= { time 6 }

        timeDaylightSavingStartWeekIndex OBJECT-TYPE
            SYNTAX INTEGER { first(1), second(2), third(3), fourth(4), last(5) }
            MAX-ACCESS read-write
            STATUS current
            DESCRIPTION
                "DaylightSavingStartWeekIndex
                Value : 1 -> first, 2 -> second, 3 -> third, 4 -> fourth, 5 -> last"
            ::= { time 7 }

        timeDaylightSavingStartWeekday OBJECT-TYPE
            SYNTAX INTEGER { sunday(1), monday(2), tuesday(3), wednesday(4), thursday(5), friday(6), saturday(7) }
            MAX-ACCESS read-write
            STATUS current
            DESCRIPTION
                "DaylightSavingStartWeekday
                Value : 1 -> sunday, 2 -> monday, 3 -> tuesday, 4 -> wednesday, 5 -> thursday, 6 -> friday, 7 -> saturday"
            ::= { time 8 }

        timeDaylightSavingStartHour OBJECT-TYPE
            SYNTAX INTEGER (0..23)
            MAX-ACCESS read-write
            STATUS current
            DESCRIPTION
                "Daylight saving start time : hour

                "
            ::= { time 9 }

        timeDaylightSavingStartMin OBJECT-TYPE
            SYNTAX INTEGER (0..59)
            MAX-ACCESS read-write
            STATUS current
            DESCRIPTION
                "Daylight saving start time : minute

                "
            ::= { time 10 }

        timeDaylightSavingStopMonth OBJECT-TYPE
            SYNTAX INTEGER { january(1), february(2), march(3), april(4), may(5), june(6), july(7), augest(8), september(9), october(10), november(11), december(12) }
            MAX-ACCESS read-write
            STATUS current
            DESCRIPTION
                "DaylightSavingStopMonth
                Value : 1 -> january, 2 -> february, 3 -> march, 4 -> april, 5 -> may, 6 -> june, 7 -> july, 8 -> augest, 9 -> september, 10 -> october, 11 -> november, 12 -> december"
            ::= { time 11 }

        timeDaylightSavingStopWeekIndex OBJECT-TYPE
            SYNTAX INTEGER { first(1), second(2), third(3), fourth(4), last(5) }
            MAX-ACCESS read-write
            STATUS current
            DESCRIPTION
                "DaylightSavingStopWeekIndex
                Value : 1 -> first, 2 -> second, 3 -> third, 4 -> fourth, 5 -> last"
            ::= { time 12 }

        timeDaylightSavingStopWeekday OBJECT-TYPE
            SYNTAX INTEGER { sunday(1), monday(2), tuesday(3), wednesday(4), thursday(5), friday(6), saturday(7) }
            MAX-ACCESS read-write
            STATUS current
            DESCRIPTION
                "DaylightSavingStopWeekday
                Value : 1 -> sunday, 2 -> monday, 3 -> tuesday, 4 -> wednesday, 5 -> thursday, 6 -> friday, 7 -> saturday"
            ::= { time 13 }

        timeDaylightSavingStophour OBJECT-TYPE
            SYNTAX INTEGER (0..23)
            MAX-ACCESS read-write
            STATUS current
            DESCRIPTION
                "Daylight saving stop time : hour

                "
            ::= { time 14 }

        timeDaylightSavingStopMin OBJECT-TYPE
            SYNTAX INTEGER (0..59)
            MAX-ACCESS read-write
            STATUS current
            DESCRIPTION
                "Daylight saving stop time : minute

                "
            ::= { time 15 }

        timeDaylightSavingTimeOffset OBJECT-TYPE
            SYNTAX INTEGER { plus30min(1), plus60min(2), plus90min(3), plus120min(4) }
            MAX-ACCESS read-write
            STATUS current
            DESCRIPTION
                "DaylightSavingTimeOffset
                Value : 1 -> plus30min, 2 -> plus60min, 3 -> plus90min, 4 -> plus120min"
            ::= { time 16 }

        timeNtpOption OBJECT-TYPE
            SYNTAX INTEGER { sntp(1) }
            MAX-ACCESS read-write
            STATUS current
            DESCRIPTION
                "NtpOption
                Value : 1 -> sntp"
            ::= { time 17 }

    netDevWlan OBJECT IDENTIFIER ::= { basic 3 }

        netDevWlanDhcpEnable OBJECT-TYPE
            SYNTAX INTEGER { enable(1), disable(2) }
            MAX-ACCESS read-write
            STATUS current
            DESCRIPTION
                "IP address assignment

                Value : 1 -> enable, 2 -> disable"
            ::= { netDevWlan 1 }

        netDevWlanIpV4Addr OBJECT-TYPE
            SYNTAX IpAddress
            MAX-ACCESS read-write
            STATUS current
            DESCRIPTION
                "IP address

                "
            ::= { netDevWlan 2 }

        netDevWlanIpV4Mask OBJECT-TYPE
            SYNTAX IpAddress
            MAX-ACCESS read-write
            STATUS current
            DESCRIPTION
                "Subnet mask

                "
            ::= { netDevWlan 3 }

        netDevWlanIpV4Gateway OBJECT-TYPE
            SYNTAX IpAddress
            MAX-ACCESS read-write
            STATUS current
            DESCRIPTION
                "Gateway

                "
            ::= { netDevWlan 4 }

        netDevWlanIpV4DnsTable OBJECT-TYPE
            SYNTAX SEQUENCE OF NetDevWlanIpV4DnsEntry
            MAX-ACCESS not-accessible
            STATUS current
            DESCRIPTION
                "Table of netDevWlanIpV4Dns"
            ::= { netDevWlan 5 }

        netDevWlanIpV4DnsEntry OBJECT-TYPE
            SYNTAX NetDevWlanIpV4DnsEntry
            MAX-ACCESS not-accessible
            STATUS current
            DESCRIPTION
                "Entry of netDevWlanIpV4Dns"
            INDEX { netDevWlanIpV4DnsIndex }
            ::= { netDevWlanIpV4DnsTable 1 }

        NetDevWlanIpV4DnsEntry ::=
            SEQUENCE {
                netDevWlanIpV4DnsIndex
                    INTEGER,
                netDevWlanIpV4DnsData
                    IpAddress
            }

        netDevWlanIpV4DnsIndex OBJECT-TYPE
            SYNTAX INTEGER (1..2)
            MAX-ACCESS read-only
            STATUS current
            DESCRIPTION
                "Index of IpV4Dns"
            ::= { netDevWlanIpV4DnsEntry 1 }

        netDevWlanIpV4DnsData OBJECT-TYPE
            SYNTAX IpAddress
            MAX-ACCESS read-write
            STATUS current
            DESCRIPTION
                "Primary DNS server

                "
            ::= { netDevWlanIpV4DnsEntry 2 }

    netDevLan OBJECT IDENTIFIER ::= { basic 4 }

        netDevLanDhcpEnable OBJECT-TYPE
            SYNTAX INTEGER { enable(1), disable(2) }
            MAX-ACCESS read-write
            STATUS current
            DESCRIPTION
                "IP address assignment

                Value : 1 -> enable, 2 -> disable"
            ::= { netDevLan 1 }

        netDevLanIpV4Addr OBJECT-TYPE
            SYNTAX IpAddress
            MAX-ACCESS read-write
            STATUS current
            DESCRIPTION
                "IP address

                "
            ::= { netDevLan 2 }

        netDevLanIpV4Mask OBJECT-TYPE
            SYNTAX IpAddress
            MAX-ACCESS read-write
            STATUS current
            DESCRIPTION
                "Subnet mask

                "
            ::= { netDevLan 3 }

    wireless OBJECT IDENTIFIER ::= { swMgmt 5 }

        devTable OBJECT-TYPE
            SYNTAX SEQUENCE OF DevEntry
            MAX-ACCESS not-accessible
            STATUS current
            DESCRIPTION
                "Table of dev"
            ::= { wireless 1 }

        devEntry OBJECT-TYPE
            SYNTAX DevEntry
            MAX-ACCESS not-accessible
            STATUS current
            DESCRIPTION
                "Entry of dev"
            INDEX { devIndex }
            ::= { devTable 1 }

        DevEntry ::=
            SEQUENCE {
                devIndex
                    INTEGER,
                devChannelA
                    INTEGER,
                devChannelB
                    INTEGER,
                devChannelG
                    INTEGER,
                devChannelListA
                    DisplayString,
                devChannelListB
                    DisplayString,
                devChannelListG
                    DisplayString,
                devRfType
                    INTEGER,
                devCountryCode
                    DisplayString,
                devTXrateA
                    INTEGER,
                devTXrateB
                    INTEGER,
                devTXrateG
                    INTEGER,
                devTXrateBG
                    INTEGER,
                devBeaconInterval
                    INTEGER,
                devDTIMinterval
                    INTEGER,
                devFragThresh
                    INTEGER,
                devRtsthreshold
                    INTEGER,
                devTxRange
                    INTEGER,
                devTxAntenna
                    INTEGER,
                devWMMenable
                    INTEGER,
                devOperationmode
                    INTEGER,
                devChannelWidth
                    INTEGER,
                devChannelN24GHz
                    INTEGER,
                devChannelN5GHz
                    INTEGER,
                devTxRateN
                    INTEGER,
                devMulticastRateA
                    INTEGER,
                devMulticastRateB
                    INTEGER,
                devMulticastRateG
                    INTEGER,
                devMulticastRateBG
                    INTEGER,
                devMulticastRateBGN
                    INTEGER,
                devMulticastRateAN
                    INTEGER,
                devMulticastRateN
                    INTEGER,
                devTxPowerdBm
                    INTEGER,
                devMacClone
                    INTEGER,
                devTXrateMin
                    INTEGER,
                devInactiveTimeout
                    INTEGER,
                devProxyArp
                    INTEGER,
                devMacCloneMethod
                    INTEGER,
                devMacCloneStaticMac
                    DisplayString,
                devRemoteConnCheckEnable
                    INTEGER,
                devRemoteConnCheckReconnWLAN
                    INTEGER,
                devRemoteConnCheckRebootDevice
                    INTEGER,
                devRemoteConnCheckRemoteHost
                    IpAddress,
                devRemoteConnCheckCheckInterval
                    INTEGER,
                devRemoteConnCheckCheckTimeout
                    INTEGER,
                devRemoteConnCheckRetryCount
                    INTEGER,
                devRemoteConnCheckRetryInterval
                    INTEGER,
                devRemoteConnCheckRebootCount
                    INTEGER
            }

        devIndex OBJECT-TYPE
            SYNTAX INTEGER (1..1)
            MAX-ACCESS read-only
            STATUS current
            DESCRIPTION
                "Index of dev"
            ::= { devEntry 1 }

        devChannelA OBJECT-TYPE
            SYNTAX INTEGER
            MAX-ACCESS read-write
            STATUS current
            DESCRIPTION
                "Channel

                "
            ::= { devEntry 2 }

        devChannelB OBJECT-TYPE
            SYNTAX INTEGER
            MAX-ACCESS read-write
            STATUS current
            DESCRIPTION
                "Channel

                "
            ::= { devEntry 3 }

        devChannelG OBJECT-TYPE
            SYNTAX INTEGER
            MAX-ACCESS read-write
            STATUS current
            DESCRIPTION
                "Channel

                "
            ::= { devEntry 4 }

        devChannelListA OBJECT-TYPE
            SYNTAX DisplayString
            MAX-ACCESS read-only
            STATUS current
            DESCRIPTION
                "Channel

                "
            ::= { devEntry 5 }

        devChannelListB OBJECT-TYPE
            SYNTAX DisplayString
            MAX-ACCESS read-only
            STATUS current
            DESCRIPTION
                "Channel

                "
            ::= { devEntry 6 }

        devChannelListG OBJECT-TYPE
            SYNTAX DisplayString
            MAX-ACCESS read-only
            STATUS current
            DESCRIPTION
                "Channel

                "
            ::= { devEntry 7 }

        devRfType OBJECT-TYPE
            SYNTAX INTEGER { bg(1), a(2), b(3), g(4), gn(5), bgn(6), an(7), n24GHz(8), n5GHz(9) }
            MAX-ACCESS read-write
            STATUS current
            DESCRIPTION
                "RF type

                Value : 1 -> bg, 2 -> a, 3 -> b, 4 -> g, 5 -> gn, 6 -> bgn, 7 -> an, 8 -> n24GHz, 9 -> n5GHz"
            ::= { devEntry 8 }

        devCountryCode OBJECT-TYPE
            SYNTAX DisplayString
            MAX-ACCESS read-only
            STATUS current
            DESCRIPTION
                "Country code

                "
            ::= { devEntry 9 }

        devTXrateA OBJECT-TYPE
            SYNTAX INTEGER { rateAuto(1), rate6M(2), rate9M(3), rate12M(4), rate18M(5), rate24M(6), rate36M(7), rate48M(8), rate54M(9) }
            MAX-ACCESS read-write
            STATUS current
            DESCRIPTION
                "Transmission rate

                Value : 1 -> rateAuto, 2 -> rate6M, 3 -> rate9M, 4 -> rate12M, 5 -> rate18M, 6 -> rate24M, 7 -> rate36M, 8 -> rate48M, 9 -> rate54M"
            ::= { devEntry 10 }

        devTXrateB OBJECT-TYPE
            SYNTAX INTEGER { rateAuto(1), rate1M(2), rate2M(3), rate5-5M(4), rate11M(5) }
            MAX-ACCESS read-write
            STATUS current
            DESCRIPTION
                "Transmission rate

                Value : 1 -> rateAuto, 2 -> rate1M, 3 -> rate2M, 4 -> rate5-5M, 5 -> rate11M"
            ::= { devEntry 11 }

        devTXrateG OBJECT-TYPE
            SYNTAX INTEGER { rateAuto(1), rate6M(2), rate9M(3), rate12M(4), rate18M(5), rate24M(6), rate36M(7), rate48M(8), rate54M(9) }
            MAX-ACCESS read-write
            STATUS current
            DESCRIPTION
                "Transmission rate

                Value : 1 -> rateAuto, 2 -> rate6M, 3 -> rate9M, 4 -> rate12M, 5 -> rate18M, 6 -> rate24M, 7 -> rate36M, 8 -> rate48M, 9 -> rate54M"
            ::= { devEntry 12 }

        devTXrateBG OBJECT-TYPE
            SYNTAX INTEGER { rateAuto(1), rate1M(2), rate2M(3), rate5-5M(4), rate6M(5), rate9M(6), rate11M(7), rate12M(8), rate18M(9), rate24M(10), rate36M(11), rate48M(12), rate54M(13) }
            MAX-ACCESS read-write
            STATUS current
            DESCRIPTION
                "Transmission rate

                Value : 1 -> rateAuto, 2 -> rate1M, 3 -> rate2M, 4 -> rate5-5M, 5 -> rate6M, 6 -> rate9M, 7 -> rate11M, 8 -> rate12M, 9 -> rate18M, 10 -> rate24M, 11 -> rate36M, 12 -> rate48M, 13 -> rate54M"
            ::= { devEntry 13 }

        devBeaconInterval OBJECT-TYPE
            SYNTAX INTEGER (40..1000)
            MAX-ACCESS read-write
            STATUS current
            DESCRIPTION
                "Beacon interval

                "
            ::= { devEntry 15 }

        devDTIMinterval OBJECT-TYPE
            SYNTAX INTEGER (1..15)
            MAX-ACCESS read-write
            STATUS current
            DESCRIPTION
                "DTIM interval

                "
            ::= { devEntry 16 }

        devFragThresh OBJECT-TYPE
            SYNTAX INTEGER (256..2346)
            MAX-ACCESS read-write
            STATUS current
            DESCRIPTION
                "Fragmentation threshold

                "
            ::= { devEntry 17 }

        devRtsthreshold OBJECT-TYPE
            SYNTAX INTEGER (32..2346)
            MAX-ACCESS read-write
            STATUS current
            DESCRIPTION
                "RTS threshold

                "
            ::= { devEntry 18 }

        devTxRange OBJECT-TYPE
            SYNTAX INTEGER (500..11000)
            MAX-ACCESS read-write
            STATUS current
            DESCRIPTION
                "Transmission distance

                "
            ::= { devEntry 19 }

        devTxAntenna OBJECT-TYPE
            SYNTAX INTEGER { mainAntenna(1), auxAntenna(2), diversityAntenna(3) }
            MAX-ACCESS read-write
            STATUS current
            DESCRIPTION
                "Antenna

                Value : 1 -> mainAntenna, 2 -> auxAntenna, 3 -> diversityAntenna"
            ::= { devEntry 21 }

        devWMMenable OBJECT-TYPE
            SYNTAX INTEGER { enable(1), disable(2) }
            MAX-ACCESS read-write
            STATUS current
            DESCRIPTION
                "WMM

                Value : 1 -> enable, 2 -> disable"
            ::= { devEntry 23 }

        devOperationmode OBJECT-TYPE
            SYNTAX INTEGER { client(1), ap(2), sniffer(3), master(4), slave(5), clientRouter(6) }
            MAX-ACCESS read-write
            STATUS current
            DESCRIPTION
                "Operation mode

                Value : 1 -> client, 2 -> ap, 3 -> sniffer, 4 -> master, 5 -> slave, 6 -> clientRouter"
            ::= { devEntry 24 }

        devChannelWidth OBJECT-TYPE
            SYNTAX INTEGER { width20MHz(1), width40MHz(2) }
            MAX-ACCESS read-write
            STATUS current
            DESCRIPTION
                "Channel width

                Value : 1 -> width20MHz, 2 -> width40MHz"
            ::= { devEntry 25 }

        devChannelN24GHz OBJECT-TYPE
            SYNTAX INTEGER
            MAX-ACCESS read-write
            STATUS current
            DESCRIPTION
                "Channel

                "
            ::= { devEntry 26 }

        devChannelN5GHz OBJECT-TYPE
            SYNTAX INTEGER
            MAX-ACCESS read-write
            STATUS current
            DESCRIPTION
                "Channel

                "
            ::= { devEntry 27 }

        devTxRateN OBJECT-TYPE
            SYNTAX INTEGER { rateAuto(1), rateMCS0(2), rateMCS1(3), rateMCS2(4), rateMCS3(5), rateMCS4(6), rateMCS5(7), rateMCS6(8), rateMCS7(9), rateMCS8(10), rateMCS9(11), rateMCS10(12), rateMCS11(13), rateMCS12(14), rateMCS13(15), rateMCS14(16), rateMCS15(17) }
            MAX-ACCESS read-write
            STATUS current
            DESCRIPTION
                "Transmission rate

                Value : 1 -> rateAuto, 2 -> rateMCS0, 3 -> rateMCS1, 4 -> rateMCS2, 5 -> rateMCS3, 6 -> rateMCS4, 7 -> rateMCS5, 8 -> rateMCS6, 9 -> rateMCS7, 10 -> rateMCS8, 11 -> rateMCS9, 12 -> rateMCS10, 13 -> rateMCS11, 14 -> rateMCS12, 15 -> rateMCS13, 16 -> rateMCS14, 17 -> rateMCS15"
            ::= { devEntry 28 }

        devMulticastRateA OBJECT-TYPE
            SYNTAX INTEGER { rateAuto(1), rate6M(2), rate9M(3), rate12M(4), rate18M(5), rate24M(6), rate36M(7), rate48M(8), rate54M(9) }
            MAX-ACCESS read-write
            STATUS current
            DESCRIPTION
                "Multicast rate

                Value : 1 -> rateAuto, 2 -> rate6M, 3 -> rate9M, 4 -> rate12M, 5 -> rate18M, 6 -> rate24M, 7 -> rate36M, 8 -> rate48M, 9 -> rate54M"
            ::= { devEntry 30 }

        devMulticastRateB OBJECT-TYPE
            SYNTAX INTEGER { rateAuto(1), rate1M(2), rate2M(3), rate5-5M(4), rate11M(5) }
            MAX-ACCESS read-write
            STATUS current
            DESCRIPTION
                "Multicast rate

                Value : 1 -> rateAuto, 2 -> rate1M, 3 -> rate2M, 4 -> rate5-5M, 5 -> rate11M"
            ::= { devEntry 31 }

        devMulticastRateG OBJECT-TYPE
            SYNTAX INTEGER { rateAuto(1), rate6M(2), rate9M(3), rate12M(4), rate18M(5), rate24M(6), rate36M(7), rate48M(8), rate54M(9) }
            MAX-ACCESS read-write
            STATUS current
            DESCRIPTION
                "Multicast rate

                Value : 1 -> rateAuto, 2 -> rate6M, 3 -> rate9M, 4 -> rate12M, 5 -> rate18M, 6 -> rate24M, 7 -> rate36M, 8 -> rate48M, 9 -> rate54M"
            ::= { devEntry 32 }

        devMulticastRateBG OBJECT-TYPE
            SYNTAX INTEGER { rateAuto(1), rate1M(2), rate2M(3), rate5-5M(4), rate11M(5) }
            MAX-ACCESS read-write
            STATUS current
            DESCRIPTION
                "Multicast rate

                Value : 1 -> rateAuto, 2 -> rate1M, 3 -> rate2M, 4 -> rate5-5M, 5 -> rate11M"
            ::= { devEntry 33 }

        devMulticastRateBGN OBJECT-TYPE
            SYNTAX INTEGER { rateAuto(1), rate1M(2), rate2M(3), rate5-5M(4), rate11M(5) }
            MAX-ACCESS read-write
            STATUS current
            DESCRIPTION
                "Multicast rate

                Value : 1 -> rateAuto, 2 -> rate1M, 3 -> rate2M, 4 -> rate5-5M, 5 -> rate11M"
            ::= { devEntry 34 }

        devMulticastRateAN OBJECT-TYPE
            SYNTAX INTEGER { rateAuto(1), rate6M(2), rate9M(3), rate12M(4), rate18M(5), rate24M(6), rate36M(7), rate48M(8), rate54M(9) }
            MAX-ACCESS read-write
            STATUS current
            DESCRIPTION
                "Multicast rate

                Value : 1 -> rateAuto, 2 -> rate6M, 3 -> rate9M, 4 -> rate12M, 5 -> rate18M, 6 -> rate24M, 7 -> rate36M, 8 -> rate48M, 9 -> rate54M"
            ::= { devEntry 35 }

        devMulticastRateN OBJECT-TYPE
            SYNTAX INTEGER { rateAuto(1), rateMCS0(2), rateMCS1(3), rateMCS2(4), rateMCS3(5), rateMCS4(6), rateMCS5(7), rateMCS6(8), rateMCS7(9), rateMCS8(10), rateMCS9(11), rateMCS10(12), rateMCS11(13), rateMCS12(14), rateMCS13(15), rateMCS14(16), rateMCS15(17) }
            MAX-ACCESS read-write
            STATUS current
            DESCRIPTION
                "Multicast rate

                Value : 1 -> rateAuto, 2 -> rateMCS0, 3 -> rateMCS1, 4 -> rateMCS2, 5 -> rateMCS3, 6 -> rateMCS4, 7 -> rateMCS5, 8 -> rateMCS6, 9 -> rateMCS7, 10 -> rateMCS8, 11 -> rateMCS9, 12 -> rateMCS10, 13 -> rateMCS11, 14 -> rateMCS12, 15 -> rateMCS13, 16 -> rateMCS14, 17 -> rateMCS15"
            ::= { devEntry 36 }

        devTxPowerdBm OBJECT-TYPE
            SYNTAX INTEGER (5..100)
            MAX-ACCESS read-write
            STATUS current
            DESCRIPTION
                "Maximum transmission power

                "
            ::= { devEntry 41 }

        devMacClone OBJECT-TYPE
            SYNTAX INTEGER { enable(1), disable(2) }
            MAX-ACCESS read-write
            STATUS current
            DESCRIPTION
                "MAC clone

                Value : 1 -> enable, 2 -> disable"
            ::= { devEntry 42 }

        devTXrateMin OBJECT-TYPE
            SYNTAX INTEGER (0..0)
            MAX-ACCESS read-write
            STATUS current
            DESCRIPTION
                "Minimum transmission rate

                "
            ::= { devEntry 58 }

        devInactiveTimeout OBJECT-TYPE
            SYNTAX INTEGER (8..240)
            MAX-ACCESS read-write
            STATUS current
            DESCRIPTION
                "Inactive timeout

                "
            ::= { devEntry 59 }

        devProxyArp OBJECT-TYPE
            SYNTAX INTEGER { enable(1), disable(2) }
            MAX-ACCESS read-write
            STATUS current
            DESCRIPTION
                "Proxy arp

                Value : 1 -> enable, 2 -> disable"
            ::= { devEntry 60 }

        devMacCloneMethod OBJECT-TYPE
            SYNTAX INTEGER { auto(1), static(2) }
            MAX-ACCESS read-write
            STATUS current
            DESCRIPTION
                "MAC clone method

                Value : 1 -> auto, 2 -> static"
            ::= { devEntry 63 }

        devMacCloneStaticMac OBJECT-TYPE
            SYNTAX DisplayString
            MAX-ACCESS read-write
            STATUS current
            DESCRIPTION
                "Static MAC clone address

                "
            ::= { devEntry 64 }

        devRemoteConnCheckEnable OBJECT-TYPE
            SYNTAX INTEGER { enable(1), disable(2) }
            MAX-ACCESS read-write
            STATUS current
            DESCRIPTION
                "Remote connection check

                Value : 1 -> enable, 2 -> disable"
            ::= { devEntry 106 }

        devRemoteConnCheckReconnWLAN OBJECT-TYPE
            SYNTAX INTEGER { enable(1), disable(2) }
            MAX-ACCESS read-write
            STATUS current
            DESCRIPTION
                "Re-establish WLAN connection

                Value : 1 -> enable, 2 -> disable"
            ::= { devEntry 107 }

        devRemoteConnCheckRebootDevice OBJECT-TYPE
            SYNTAX INTEGER { enable(1), disable(2) }
            MAX-ACCESS read-write
            STATUS current
            DESCRIPTION
                "Device reboot

                Value : 1 -> enable, 2 -> disable"
            ::= { devEntry 108 }

        devRemoteConnCheckRemoteHost OBJECT-TYPE
            SYNTAX IpAddress
            MAX-ACCESS read-write
            STATUS current
            DESCRIPTION
                "Remote host

                "
            ::= { devEntry 109 }

        devRemoteConnCheckCheckInterval OBJECT-TYPE
            SYNTAX INTEGER (1..30)
            MAX-ACCESS read-write
            STATUS current
            DESCRIPTION
                "Check interval

                "
            ::= { devEntry 110 }

        devRemoteConnCheckCheckTimeout OBJECT-TYPE
            SYNTAX INTEGER (100..10000)
            MAX-ACCESS read-write
            STATUS current
            DESCRIPTION
                "Timeout

                "
            ::= { devEntry 111 }

        devRemoteConnCheckRetryCount OBJECT-TYPE
            SYNTAX INTEGER (1..5)
            MAX-ACCESS read-write
            STATUS current
            DESCRIPTION
                "Retry count

                "
            ::= { devEntry 112 }

        devRemoteConnCheckRetryInterval OBJECT-TYPE
            SYNTAX INTEGER (1..30)
            MAX-ACCESS read-write
            STATUS current
            DESCRIPTION
                "Retry interval

                "
            ::= { devEntry 113 }

        devRemoteConnCheckRebootCount OBJECT-TYPE
            SYNTAX INTEGER (0..5)
            MAX-ACCESS read-write
            STATUS current
            DESCRIPTION
                "Reboot count

                "
            ::= { devEntry 114 }

        vapTable OBJECT-TYPE
            SYNTAX SEQUENCE OF VapEntry
            MAX-ACCESS not-accessible
            STATUS current
            DESCRIPTION
                "Table of vap"
            ::= { wireless 3 }

        vapEntry OBJECT-TYPE
            SYNTAX VapEntry
            MAX-ACCESS not-accessible
            STATUS current
            DESCRIPTION
                "Entry of vap"
            INDEX { vapIndex }
            ::= { vapTable 1 }

        VapEntry ::=
            SEQUENCE {
                vapIndex
                    INTEGER,
                vapSSID
                    DisplayString,
                vapSignalLV
                    DisplayString,
                vapSsidBroadcast
                    INTEGER,
                vapWdsEnable
                    INTEGER,
                vapAPfunctionality
                    INTEGER,
                vapAuthType
                    INTEGER,
                vapWEPauth
                    INTEGER,
                vapWEPtype
                    INTEGER,
                vapWEPlen
                    INTEGER,
                vapWEPkeyIndex
                    INTEGER,
                vapWPAtype
                    INTEGER,
                vapEapolVer
                    INTEGER,
                vapWpaEncrypt
                    INTEGER,
                vap1stAuthServerIPv4Addr
                    IpAddress,
                vap1stAuthServerPort
                    INTEGER,
                vap2ndAuthServerIPv4Addr
                    IpAddress,
                vap2ndAuthServerPort
                    INTEGER,
                vapCertInfo
                    DisplayString,
                vapEapProto
                    INTEGER,
                vapEAPanonymous
                    DisplayString,
                vapTtlsInner
                    INTEGER,
                vapPeapInner
                    INTEGER,
                vapEapUser
                    DisplayString,
                vapRekey
                    INTEGER,
                vapBssidClient
                    DisplayString,
                vapClientIsolation
                    INTEGER,
                vapClientIsolationGateway
                    IpAddress,
                vapClientIsolationNetMask
                    IpAddress,
                vapMgmtEncryption
                    INTEGER,
                vapAerolink-ap
                    INTEGER,
                vapClientIsolationSubnetType
                    INTEGER,
                vapClntIsoEnableRule1
                    INTEGER,
                vapClntIsoHostRule1
                    DisplayString,
                vapClntIsoNetmaskRule1
                    IpAddress,
                vapClntIsoProtoRule1
                    INTEGER,
                vapClntIsoPortStartRule1
                    INTEGER,
                vapClntIsoPortEndRule1
                    INTEGER,
                vapClntIsoEnableRule2
                    INTEGER,
                vapClntIsoHostRule2
                    DisplayString,
                vapClntIsoNetmaskRule2
                    IpAddress,
                vapClntIsoProtoRule2
                    INTEGER,
                vapClntIsoPortStartRule2
                    INTEGER,
                vapClntIsoPortEndRule2
                    INTEGER,
                vapClntIsoEnableRule3
                    INTEGER,
                vapClntIsoHostRule3
                    DisplayString,
                vapClntIsoNetmaskRule3
                    IpAddress,
                vapClntIsoProtoRule3
                    INTEGER,
                vapClntIsoPortStartRule3
                    INTEGER,
                vapClntIsoPortEndRule3
                    INTEGER,
                vapClntIsoEnableRule4
                    INTEGER,
                vapClntIsoHostRule4
                    DisplayString,
                vapClntIsoNetmaskRule4
                    IpAddress,
                vapClntIsoProtoRule4
                    INTEGER,
                vapClntIsoPortStartRule4
                    INTEGER,
                vapClntIsoPortEndRule4
                    INTEGER,
                vapClntIsoEnableRule5
                    INTEGER,
                vapClntIsoHostRule5
                    DisplayString,
                vapClntIsoNetmaskRule5
                    IpAddress,
                vapClntIsoProtoRule5
                    INTEGER,
                vapClntIsoPortStartRule5
                    INTEGER,
                vapClntIsoPortEndRule5
                    INTEGER,
                vapClntIsoEnableRule6
                    INTEGER,
                vapClntIsoHostRule6
                    DisplayString,
                vapClntIsoNetmaskRule6
                    IpAddress,
                vapClntIsoProtoRule6
                    INTEGER,
                vapClntIsoPortStartRule6
                    INTEGER,
                vapClntIsoPortEndRule6
                    INTEGER,
                vapClntIsoEnableRule7
                    INTEGER,
                vapClntIsoHostRule7
                    DisplayString,
                vapClntIsoNetmaskRule7
                    IpAddress,
                vapClntIsoProtoRule7
                    INTEGER,
                vapClntIsoPortStartRule7
                    INTEGER,
                vapClntIsoPortEndRule7
                    INTEGER,
                vapClntIsoEnableRule8
                    INTEGER,
                vapClntIsoHostRule8
                    DisplayString,
                vapClntIsoNetmaskRule8
                    IpAddress,
                vapClntIsoProtoRule8
                    INTEGER,
                vapClntIsoPortStartRule8
                    INTEGER,
                vapClntIsoPortEndRule8
                    INTEGER
            }

        vapIndex OBJECT-TYPE
            SYNTAX INTEGER (1..9)
            MAX-ACCESS read-only
            STATUS current
            DESCRIPTION
                "Index of vap"
            ::= { vapEntry 1 }

        vapSSID OBJECT-TYPE
            SYNTAX DisplayString
            MAX-ACCESS read-write
            STATUS current
            DESCRIPTION
                "SSID

                "
            ::= { vapEntry 2 }

        vapSignalLV OBJECT-TYPE
            SYNTAX DisplayString
            MAX-ACCESS read-only
            STATUS current
            DESCRIPTION
                "Signal

                "
            ::= { vapEntry 3 }

        vapSsidBroadcast OBJECT-TYPE
            SYNTAX INTEGER { enable(1), disable(2) }
            MAX-ACCESS read-write
            STATUS current
            DESCRIPTION
                "SSID broadcast

                Value : 1 -> enable, 2 -> disable"
            ::= { vapEntry 4 }

        vapWdsEnable OBJECT-TYPE
            SYNTAX INTEGER { enable(1), disable(2) }
            MAX-ACCESS read-write
            STATUS current
            DESCRIPTION
                "WDS

                Value : 1 -> enable, 2 -> disable"
            ::= { vapEntry 5 }

        vapAPfunctionality OBJECT-TYPE
            SYNTAX INTEGER { enable(1), disable(2) }
            MAX-ACCESS read-write
            STATUS current
            DESCRIPTION
                "AP functionality

                Value : 1 -> enable, 2 -> disable"
            ::= { vapEntry 6 }

        vapAuthType OBJECT-TYPE
            SYNTAX INTEGER { open(1), wep(2), wpa(3), wpa2(4), wpa-wpa2-mix(5) }
            MAX-ACCESS read-write
            STATUS current
            DESCRIPTION
                "Security mode

                Value : 1 -> open, 2 -> wep, 3 -> wpa, 4 -> wpa2, 5 -> wpa-wpa2-mix"
            ::= { vapEntry 7 }

        vapWEPauth OBJECT-TYPE
            SYNTAX INTEGER { open(1), share(2) }
            MAX-ACCESS read-write
            STATUS current
            DESCRIPTION
                "Authentication type

                Value : 1 -> open, 2 -> share"
            ::= { vapEntry 8 }

        vapWEPtype OBJECT-TYPE
            SYNTAX INTEGER { ascii(1), hex(2) }
            MAX-ACCESS read-write
            STATUS current
            DESCRIPTION
                "Key type

                Value : 1 -> ascii, 2 -> hex"
            ::= { vapEntry 9 }

        vapWEPlen OBJECT-TYPE
            SYNTAX INTEGER { wep64(1), wep128(2) }
            MAX-ACCESS read-write
            STATUS current
            DESCRIPTION
                "Key length

                Value : 1 -> wep64, 2 -> wep128"
            ::= { vapEntry 10 }

        vapWEPkeyIndex OBJECT-TYPE
            SYNTAX INTEGER { key1(1), key2(2), key3(3), key4(4) }
            MAX-ACCESS read-write
            STATUS current
            DESCRIPTION
                "Key index

                Value : 1 -> key1, 2 -> key2, 3 -> key3, 4 -> key4"
            ::= { vapEntry 11 }

        vapWPAtype OBJECT-TYPE
            SYNTAX INTEGER { personal(1), enterprise(2) }
            MAX-ACCESS read-write
            STATUS current
            DESCRIPTION
                "WPA type

                Value : 1 -> personal, 2 -> enterprise"
            ::= { vapEntry 16 }

        vapEapolVer OBJECT-TYPE
            SYNTAX INTEGER (1..2)
            MAX-ACCESS read-write
            STATUS current
            DESCRIPTION
                "EAPOL version

                "
            ::= { vapEntry 17 }

        vapWpaEncrypt OBJECT-TYPE
            SYNTAX INTEGER { tkip(1), aes(2), mixed(3) }
            MAX-ACCESS read-write
            STATUS current
            DESCRIPTION
                "Encryption method

                Value : 1 -> tkip, 2 -> aes, 3 -> mixed"
            ::= { vapEntry 18 }

        vap1stAuthServerIPv4Addr OBJECT-TYPE
            SYNTAX IpAddress
            MAX-ACCESS read-write
            STATUS current
            DESCRIPTION
                "Primary RADIUS server IP

                "
            ::= { vapEntry 20 }

        vap1stAuthServerPort OBJECT-TYPE
            SYNTAX INTEGER (1..65535)
            MAX-ACCESS read-write
            STATUS current
            DESCRIPTION
                "Primary RADIUS server port

                "
            ::= { vapEntry 21 }

        vap2ndAuthServerIPv4Addr OBJECT-TYPE
            SYNTAX IpAddress
            MAX-ACCESS read-write
            STATUS current
            DESCRIPTION
                "Secondary RADIUS server IP

                "
            ::= { vapEntry 23 }

        vap2ndAuthServerPort OBJECT-TYPE
            SYNTAX INTEGER (1..65535)
            MAX-ACCESS read-write
            STATUS current
            DESCRIPTION
                "Secondary RADIUS server port

                "
            ::= { vapEntry 24 }

        vapCertInfo OBJECT-TYPE
            SYNTAX DisplayString
            MAX-ACCESS read-only
            STATUS current
            DESCRIPTION
                "Certificate information

                "
            ::= { vapEntry 26 }

        vapEapProto OBJECT-TYPE
            SYNTAX INTEGER { tls(1), ttls(2), peap(3) }
            MAX-ACCESS read-write
            STATUS current
            DESCRIPTION
                "EAP protocol

                Value : 1 -> tls, 2 -> ttls, 3 -> peap"
            ::= { vapEntry 27 }

        vapEAPanonymous OBJECT-TYPE
            SYNTAX DisplayString
            MAX-ACCESS read-write
            STATUS current
            DESCRIPTION
                "Anonymous name

                "
            ::= { vapEntry 28 }

        vapTtlsInner OBJECT-TYPE
            SYNTAX INTEGER { pap(1), chap(2), ms-chap(3), ms-chapV2(4) }
            MAX-ACCESS read-write
            STATUS current
            DESCRIPTION
                "TTLS inner authentication

                Value : 1 -> pap, 2 -> chap, 3 -> ms-chap, 4 -> ms-chapV2"
            ::= { vapEntry 29 }

        vapPeapInner OBJECT-TYPE
            SYNTAX INTEGER { ms-chapV2(1) }
            MAX-ACCESS read-write
            STATUS current
            DESCRIPTION
                "Inner EAP protocol

                Value : 1 -> ms-chapV2"
            ::= { vapEntry 30 }

        vapEapUser OBJECT-TYPE
            SYNTAX DisplayString
            MAX-ACCESS read-write
            STATUS current
            DESCRIPTION
                "User name

                "
            ::= { vapEntry 31 }

        vapRekey OBJECT-TYPE
            SYNTAX INTEGER (60..86400)
            MAX-ACCESS read-write
            STATUS current
            DESCRIPTION
                "Key renewal

                "
            ::= { vapEntry 33 }

        vapBssidClient OBJECT-TYPE
            SYNTAX DisplayString
            MAX-ACCESS read-only
            STATUS current
            DESCRIPTION
                "Current BSSID

                "
            ::= { vapEntry 34 }

        vapClientIsolation OBJECT-TYPE
            SYNTAX INTEGER { noIsolation(1), isolatedWithinTheSameAP(2), isolatedWithinTheSameSubnet(3) }
            MAX-ACCESS read-write
            STATUS current
            DESCRIPTION
                "Client isolation

                Value : 1 -> noIsolation, 2 -> isolatedWithinTheSameAP, 3 -> isolatedWithinTheSameSubnet"
            ::= { vapEntry 38 }

        vapClientIsolationGateway OBJECT-TYPE
            SYNTAX IpAddress
            MAX-ACCESS read-write
            STATUS current
            DESCRIPTION
                "Gateway

                "
            ::= { vapEntry 39 }

        vapClientIsolationNetMask OBJECT-TYPE
            SYNTAX IpAddress
            MAX-ACCESS read-write
            STATUS current
            DESCRIPTION
                "Netmask

                "
            ::= { vapEntry 40 }

        vapMgmtEncryption OBJECT-TYPE
            SYNTAX INTEGER { enable(1), disable(2) }
            MAX-ACCESS read-write
            STATUS current
            DESCRIPTION
                "Management frame encryption

                Value : 1 -> enable, 2 -> disable"
            ::= { vapEntry 41 }

        vapAerolink-ap OBJECT-TYPE
            SYNTAX INTEGER { enable(1), disable(2) }
            MAX-ACCESS read-write
            STATUS current
            DESCRIPTION
                "AeroLink AP

                Value : 1 -> enable, 2 -> disable"
            ::= { vapEntry 43 }

        vapClientIsolationSubnetType OBJECT-TYPE
            SYNTAX INTEGER { static(1), dhcp(2) }
            MAX-ACCESS read-write
            STATUS current
            DESCRIPTION
                "Subnet type

                Value : 1 -> static, 2 -> dhcp"
            ::= { vapEntry 201 }

        vapClntIsoEnableRule1 OBJECT-TYPE
            SYNTAX INTEGER { enable(1), disable(2) }
            MAX-ACCESS read-write
            STATUS current
            DESCRIPTION
                "Active

                Value : 1 -> enable, 2 -> disable"
            ::= { vapEntry 211 }

        vapClntIsoHostRule1 OBJECT-TYPE
            SYNTAX DisplayString
            MAX-ACCESS read-write
            STATUS current
            DESCRIPTION
                "IP

                "
            ::= { vapEntry 212 }

        vapClntIsoNetmaskRule1 OBJECT-TYPE
            SYNTAX IpAddress
            MAX-ACCESS read-write
            STATUS current
            DESCRIPTION
                "Netmask

                "
            ::= { vapEntry 213 }

        vapClntIsoProtoRule1 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 214 }

        vapClntIsoPortStartRule1 OBJECT-TYPE
            SYNTAX INTEGER (1..65535)
            MAX-ACCESS read-write
            STATUS current
            DESCRIPTION
                "Port

                "
            ::= { vapEntry 215 }

        vapClntIsoPortEndRule1 OBJECT-TYPE
            SYNTAX INTEGER (1..65535)
            MAX-ACCESS read-write
            STATUS current
            DESCRIPTION
                "Port

                "
            ::= { vapEntry 216 }

        vapClntIsoEnableRule2 OBJECT-TYPE
            SYNTAX INTEGER { enable(1), disable(2) }
            MAX-ACCESS read-write
            STATUS current
            DESCRIPTION
                "Active

                Value : 1 -> enable, 2 -> disable"
            ::= { vapEntry 221 }

        vapClntIsoHostRule2 OBJECT-TYPE
            SYNTAX DisplayString
            MAX-ACCESS read-write
            STATUS current
            DESCRIPTION
                "IP

                "
            ::= { vapEntry 222 }

        vapClntIsoNetmaskRule2 OBJECT-TYPE
            SYNTAX IpAddress
            MAX-ACCESS read-write
            STATUS current
            DESCRIPTION
                "Netmask

                "
            ::= { vapEntry 223 }

        vapClntIsoProtoRule2 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 224 }

        vapClntIsoPortStartRule2 OBJECT-TYPE
            SYNTAX INTEGER (1..65535)
            MAX-ACCESS read-write
            STATUS current
            DESCRIPTION
                "Port

                "
            ::= { vapEntry 225 }

        vapClntIsoPortEndRule2 OBJECT-TYPE
            SYNTAX INTEGER (1..65535)
            MAX-ACCESS read-write
            STATUS current
            DESCRIPTION
                "Port

                "
            ::= { vapEntry 226 }

        vapClntIsoEnableRule3 OBJECT-TYPE
            SYNTAX INTEGER { enable(1), disable(2) }
            MAX-ACCESS read-write
            STATUS current
            DESCRIPTION
                "Active

                Value : 1 -> enable, 2 -> disable"
            ::= { vapEntry 231 }

        vapClntIsoHostRule3 OBJECT-TYPE
            SYNTAX DisplayString
            MAX-ACCESS read-write
            STATUS current
            DESCRIPTION
                "IP

                "
            ::= { vapEntry 232 }

        vapClntIsoNetmaskRule3 OBJECT-TYPE
            SYNTAX IpAddress
            MAX-ACCESS read-write
            STATUS current
            DESCRIPTION
                "Netmask

                "
            ::= { vapEntry 233 }

        vapClntIsoProtoRule3 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 234 }

        vapClntIsoPortStartRule3 OBJECT-TYPE
            SYNTAX INTEGER (1..65535)
            MAX-ACCESS read-write
            STATUS current
            DESCRIPTION
                "Port

                "
            ::= { vapEntry 235 }

        vapClntIsoPortEndRule3 OBJECT-TYPE
            SYNTAX INTEGER (1..65535)
            MAX-ACCESS read-write
            STATUS current
            DESCRIPTION
                "Port

                "
            ::= { vapEntry 236 }

        vapClntIsoEnableRule4 OBJECT-TYPE
            SYNTAX INTEGER { enable(1), disable(2) }
            MAX-ACCESS read-write
            STATUS current
            DESCRIPTION
                "Active

                Value : 1 -> enable, 2 -> disable"
            ::= { vapEntry 241 }

        vapClntIsoHostRule4 OBJECT-TYPE
            SYNTAX DisplayString
            MAX-ACCESS read-write
            STATUS current
            DESCRIPTION
                "IP

                "
            ::= { vapEntry 242 }

        vapClntIsoNetmaskRule4 OBJECT-TYPE
            SYNTAX IpAddress
            MAX-ACCESS read-write
            STATUS current
            DESCRIPTION
                "Netmask

                "
            ::= { vapEntry 243 }

        vapClntIsoProtoRule4 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 244 }

        vapClntIsoPortStartRule4 OBJECT-TYPE
            SYNTAX INTEGER (1..65535)
            MAX-ACCESS read-write
            STATUS current
            DESCRIPTION
                "Port

                "
            ::= { vapEntry 245 }

        vapClntIsoPortEndRule4 OBJECT-TYPE
            SYNTAX INTEGER (1..65535)
            MAX-ACCESS read-write
            STATUS current
            DESCRIPTION
                "Port

                "
            ::= { vapEntry 246 }

        vapClntIsoEnableRule5 OBJECT-TYPE
            SYNTAX INTEGER { enable(1), disable(2) }
            MAX-ACCESS read-write
            STATUS current
            DESCRIPTION
                "Active

                Value : 1 -> enable, 2 -> disable"
            ::= { vapEntry 251 }

        vapClntIsoHostRule5 OBJECT-TYPE
            SYNTAX DisplayString
            MAX-ACCESS read-write
            STATUS current
            DESCRIPTION
                "IP

                "
            ::= { vapEntry 252 }

        vapClntIsoNetmaskRule5 OBJECT-TYPE
            SYNTAX IpAddress
            MAX-ACCESS read-write
            STATUS current
            DESCRIPTION
                "Netmask

                "
            ::= { vapEntry 253 }

        vapClntIsoProtoRule5 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 254 }

        vapClntIsoPortStartRule5 OBJECT-TYPE
            SYNTAX INTEGER (1..65535)
            MAX-ACCESS read-write
            STATUS current
            DESCRIPTION
                "Port

                "
            ::= { vapEntry 255 }

        vapClntIsoPortEndRule5 OBJECT-TYPE
            SYNTAX INTEGER (1..65535)
            MAX-ACCESS read-write
            STATUS current
            DESCRIPTION
                "Port

                "
            ::= { vapEntry 256 }

        vapClntIsoEnableRule6 OBJECT-TYPE
            SYNTAX INTEGER { enable(1), disable(2) }
            MAX-ACCESS read-write
            STATUS current
            DESCRIPTION
                "Active

                Value : 1 -> enable, 2 -> disable"
            ::= { vapEntry 261 }

        vapClntIsoHostRule6 OBJECT-TYPE
            SYNTAX DisplayString
            MAX-ACCESS read-write
            STATUS current
            DESCRIPTION
                "IP

                "
            ::= { vapEntry 262 }

        vapClntIsoNetmaskRule6 OBJECT-TYPE
            SYNTAX IpAddress
            MAX-ACCESS read-write
            STATUS current
            DESCRIPTION
                "Netmask

                "
            ::= { vapEntry 263 }

        vapClntIsoProtoRule6 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 264 }

        vapClntIsoPortStartRule6 OBJECT-TYPE
            SYNTAX INTEGER (1..65535)
            MAX-ACCESS read-write
            STATUS current
            DESCRIPTION
                "Port

                "
            ::= { vapEntry 265 }

        vapClntIsoPortEndRule6 OBJECT-TYPE
            SYNTAX INTEGER (1..65535)
            MAX-ACCESS read-write
            STATUS current
            DESCRIPTION
                "Port

                "
            ::= { vapEntry 266 }

        vapClntIsoEnableRule7 OBJECT-TYPE
            SYNTAX INTEGER { enable(1), disable(2) }
            MAX-ACCESS read-write
            STATUS current
            DESCRIPTION
                "Active

                Value : 1 -> enable, 2 -> disable"
            ::= { vapEntry 271 }

        vapClntIsoHostRule7 OBJECT-TYPE
            SYNTAX DisplayString
            MAX-ACCESS read-write
            STATUS current
            DESCRIPTION
                "IP

                "
            ::= { vapEntry 272 }

        vapClntIsoNetmaskRule7 OBJECT-TYPE
            SYNTAX IpAddress
            MAX-ACCESS read-write
            STATUS current
            DESCRIPTION
                "Netmask

                "
            ::= { vapEntry 273 }

        vapClntIsoProtoRule7 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 274 }

        vapClntIsoPortStartRule7 OBJECT-TYPE
            SYNTAX INTEGER (1..65535)
            MAX-ACCESS read-write
            STATUS current
            DESCRIPTION
                "Port

                "
            ::= { vapEntry 275 }

        vapClntIsoPortEndRule7 OBJECT-TYPE
            SYNTAX INTEGER (1..65535)
            MAX-ACCESS read-write
            STATUS current
            DESCRIPTION
                "Port

                "
            ::= { vapEntry 276 }

        vapClntIsoEnableRule8 OBJECT-TYPE
            SYNTAX INTEGER { enable(1), disable(2) }
            MAX-ACCESS read-write
            STATUS current
            DESCRIPTION
                "Active

                Value : 1 -> enable, 2 -> disable"
            ::= { vapEntry 281 }

        vapClntIsoHostRule8 OBJECT-TYPE
            SYNTAX DisplayString
            MAX-ACCESS read-write
            STATUS current
            DESCRIPTION
                "IP

                "
            ::= { vapEntry 282 }

        vapClntIsoNetmaskRule8 OBJECT-TYPE
            SYNTAX IpAddress
            MAX-ACCESS read-write
            STATUS current
            DESCRIPTION
                "Netmask

                "
            ::= { vapEntry 283 }

        vapClntIsoProtoRule8 OBJECT-TYPE
            SYNTAX INTEGER { all(1), icmp(2), tcp(3), udp(4) }
            MAX-ACCESS read-write
            STATUS current
            DESCRIPTION
                "Protocol

                Value : 1 -> all, 2 -> icmp, 3 -> tcp, 4 -> udp"
            ::= { vapEntry 284 }

        vapClntIsoPortStartRule8 OBJECT-TYPE
            SYNTAX INTEGER (1..65535)
            MAX-ACCESS read-write
            STATUS current
            DESCRIPTION
                "Port

                "
            ::= { vapEntry 285 }

        vapClntIsoPortEndRule8 OBJECT-TYPE
            SYNTAX INTEGER (1..65535)
            MAX-ACCESS read-write
            STATUS current
            DESCRIPTION
                "Port

                "
            ::= { vapEntry 286 }

        wdsTable OBJECT-TYPE
            SYNTAX SEQUENCE OF WdsEntry
            MAX-ACCESS not-accessible
            STATUS current
            DESCRIPTION
                "Table of wds"
            ::= { wireless 5 }

        wdsEntry OBJECT-TYPE
            SYNTAX WdsEntry
            MAX-ACCESS not-accessible
            STATUS current
            DESCRIPTION
                "Entry of wds"
            INDEX { wdsIndex }
            ::= { wdsTable 1 }

        WdsEntry ::=
            SEQUENCE {
                wdsIndex
                    INTEGER,
                wdsWdsEnable
                    INTEGER,
                wdsWdsPeerMac
                    DisplayString
            }

        wdsIndex OBJECT-TYPE
            SYNTAX INTEGER (1..8)
            MAX-ACCESS read-only
            STATUS current
            DESCRIPTION
                "Index of wds"
            ::= { wdsEntry 1 }

        wdsWdsEnable OBJECT-TYPE
            SYNTAX INTEGER { enable(1), disable(2) }
            MAX-ACCESS read-write
            STATUS current
            DESCRIPTION
                "ENABLE

                Value : 1 -> enable, 2 -> disable"
            ::= { wdsEntry 2 }

        wdsWdsPeerMac OBJECT-TYPE
            SYNTAX DisplayString
            MAX-ACCESS read-write
            STATUS current
            DESCRIPTION
                "Device Peer Mac

                "
            ::= { wdsEntry 3 }

        certWlanTable OBJECT-TYPE
            SYNTAX SEQUENCE OF CertWlanEntry
            MAX-ACCESS not-accessible
            STATUS current
            DESCRIPTION
                "Table of certWlan"
            ::= { wireless 6 }

        certWlanEntry OBJECT-TYPE
            SYNTAX CertWlanEntry
            MAX-ACCESS not-accessible
            STATUS current
            DESCRIPTION
                "Entry of certWlan"
            INDEX { certWlanIndex }
            ::= { certWlanTable 1 }

        CertWlanEntry ::=
            SEQUENCE {
                certWlanIndex
                    INTEGER,
                certWlanIssueTo
                    DisplayString,
                certWlanIssueBy
                    DisplayString,
                certWlanExpireDate
                    DisplayString
            }

        certWlanIndex OBJECT-TYPE
            SYNTAX INTEGER (1..1)
            MAX-ACCESS read-only
            STATUS current
            DESCRIPTION
                "Index of certWlan"
            ::= { certWlanEntry 1 }

        certWlanIssueTo OBJECT-TYPE
            SYNTAX DisplayString
            MAX-ACCESS read-only
            STATUS current
            DESCRIPTION
                "Certificate issued to

                "
            ::= { certWlanEntry 2 }

        certWlanIssueBy OBJECT-TYPE
            SYNTAX DisplayString
            MAX-ACCESS read-only
            STATUS current
            DESCRIPTION
                "Certificate issued by

                "
            ::= { certWlanEntry 3 }

        certWlanExpireDate OBJECT-TYPE
            SYNTAX DisplayString
            MAX-ACCESS read-only
            STATUS current
            DESCRIPTION
                "Certificate expiration date

                "
            ::= { certWlanEntry 4 }

        turboRoamingTable OBJECT-TYPE
            SYNTAX SEQUENCE OF TurboRoamingEntry
            MAX-ACCESS not-accessible
            STATUS current
            DESCRIPTION
                "Table of turboRoaming"
            ::= { wireless 7 }

        turboRoamingEntry OBJECT-TYPE
            SYNTAX TurboRoamingEntry
            MAX-ACCESS not-accessible
            STATUS current
            DESCRIPTION
                "Entry of turboRoaming"
            INDEX { turboRoamingIndex }
            ::= { turboRoamingTable 1 }

        TurboRoamingEntry ::=
            SEQUENCE {
                turboRoamingIndex
                    INTEGER,
                turboRoamingEnable
                    INTEGER,
                turboRoamingChannelA1
                    INTEGER,
                turboRoamingChannelA2
                    INTEGER,
                turboRoamingChannelA3
                    INTEGER,
                turboRoamingChannelB1
                    INTEGER,
                turboRoamingChannelB2
                    INTEGER,
                turboRoamingChannelB3
                    INTEGER,
                turboRoamingChannelG1
                    INTEGER,
                turboRoamingChannelG2
                    INTEGER,
                turboRoamingChannelG3
                    INTEGER,
                turboRoamingChannelBG1
                    INTEGER,
                turboRoamingChannelBG2
                    INTEGER,
                turboRoamingChannelBG3
                    INTEGER,
                turboRoamingApAliveCheckEnable
                    INTEGER,
                turboRoamingChannelN24GHz1
                    INTEGER,
                turboRoamingChannelN24GHz2
                    INTEGER,
                turboRoamingChannelN24GHz3
                    INTEGER,
                turboRoamingChannelN5GHz1
                    INTEGER,
                turboRoamingChannelN5GHz2
                    INTEGER,
                turboRoamingChannelN5GHz3
                    INTEGER,
                turboRoamingSelectTRtypeEnable
                    INTEGER,
                turboRoamingRoamingThreshunit
                    INTEGER,
                turboRoamingRoamingAliveunit
                    INTEGER,
                turboRoamingRoamingThresh2GSNR
                    INTEGER,
                turboRoamingRoamingThresh2GSignal
                    INTEGER,
                turboRoamingRoamingDifference2G
                    INTEGER,
                turboRoamingApCandidateThreshold2GSNR
                    INTEGER,
                turboRoamingApCandidateThreshold2GSignal
                    INTEGER,
                turboRoamingRoamingThresh5GSNR
                    INTEGER,
                turboRoamingRoamingThresh5GSignal
                    INTEGER,
                turboRoamingRoamingDifference5G
                    INTEGER,
                turboRoamingApCandidateThreshold5GSNR
                    INTEGER,
                turboRoamingApCandidateThreshold5GSignal
                    INTEGER,
                turboRoamingRoamingThreshLegacySNR
                    INTEGER,
                turboRoamingRoamingThreshLegacySignal
                    INTEGER,
                turboRoamingRoamingThreshNmodeSNR
                    INTEGER,
                turboRoamingRoamingThreshNmode24GSignal
                    INTEGER,
                turboRoamingRoamingThreshNmode5GSignal
                    INTEGER,
                turboRoamingChannelA4
                    INTEGER,
                turboRoamingChannelA5
                    INTEGER,
                turboRoamingChannelB4
                    INTEGER,
                turboRoamingChannelB5
                    INTEGER,
                turboRoamingChannelG4
                    INTEGER,
                turboRoamingChannelG5
                    INTEGER,
                turboRoamingChannelBG4
                    INTEGER,
                turboRoamingChannelBG5
                    INTEGER,
                turboRoamingChannelN24GHz4
                    INTEGER,
                turboRoamingChannelN24GHz5
                    INTEGER,
                turboRoamingChannelN5GHz4
                    INTEGER,
                turboRoamingChannelN5GHz5
                    INTEGER,
                turboRoamingRoamingAliveLegacySNR
                    INTEGER,
                turboRoamingRoamingAliveSignal
                    INTEGER,
                turboRoamingRoamingAliveNmode24GSNR
                    INTEGER,
                turboRoamingRoamingAliveNmode24GSignal
                    INTEGER,
                turboRoamingRoamingAliveNmode5GSNR
                    INTEGER,
                turboRoamingRoamingAliveNmode5GSignal
                    INTEGER,
                turboRoamingChannelA6
                    INTEGER,
                turboRoamingChannelA7
                    INTEGER,
                turboRoamingChannelA8
                    INTEGER,
                turboRoamingChannelA9
                    INTEGER,
                turboRoamingChannelA10
                    INTEGER,
                turboRoamingChannelA11
                    INTEGER,
                turboRoamingChannelB6
                    INTEGER,
                turboRoamingChannelB7
                    INTEGER,
                turboRoamingChannelB8
                    INTEGER,
                turboRoamingChannelB9
                    INTEGER,
                turboRoamingChannelB10
                    INTEGER,
                turboRoamingChannelB11
                    INTEGER,
                turboRoamingChannelG6
                    INTEGER,
                turboRoamingChannelG7
                    INTEGER,
                turboRoamingChannelG8
                    INTEGER,
                turboRoamingChannelG9
                    INTEGER,
                turboRoamingChannelG10
                    INTEGER,
                turboRoamingChannelG11
                    INTEGER,
                turboRoamingChannelBG6
                    INTEGER,
                turboRoamingChannelBG7
                    INTEGER,
                turboRoamingChannelBG8
                    INTEGER,
                turboRoamingChannelBG9
                    INTEGER,
                turboRoamingChannelBG10
                    INTEGER,
                turboRoamingChannelBG11
                    INTEGER,
                turboRoamingChannelN24GHz6
                    INTEGER,
                turboRoamingChannelN24GHz7
                    INTEGER,
                turboRoamingChannelN24GHz8
                    INTEGER,
                turboRoamingChannelN24GHz9
                    INTEGER,
                turboRoamingChannelN24GHz10
                    INTEGER,
                turboRoamingChannelN24GHz11
                    INTEGER,
                turboRoamingChannelN5GHz6
                    INTEGER,
                turboRoamingChannelN5GHz7
                    INTEGER,
                turboRoamingChannelN5GHz8
                    INTEGER,
                turboRoamingChannelN5GHz9
                    INTEGER,
                turboRoamingChannelN5GHz10
                    INTEGER,
                turboRoamingChannelN5GHz11
                    INTEGER
            }

        turboRoamingIndex OBJECT-TYPE
            SYNTAX INTEGER (1..1)
            MAX-ACCESS read-only
            STATUS current
            DESCRIPTION
                "Index of turboRoaming"
            ::= { turboRoamingEntry 1 }

        turboRoamingEnable OBJECT-TYPE
            SYNTAX INTEGER { enable(1), disable(2) }
            MAX-ACCESS read-write
            STATUS current
            DESCRIPTION
                "Enable

                Value : 1 -> enable, 2 -> disable"
            ::= { turboRoamingEntry 2 }

        turboRoamingChannelA1 OBJECT-TYPE
            SYNTAX INTEGER
            MAX-ACCESS read-write
            STATUS current
            DESCRIPTION
                "Scan channels

                "
            ::= { turboRoamingEntry 3 }

        turboRoamingChannelA2 OBJECT-TYPE
            SYNTAX INTEGER
            MAX-ACCESS read-write
            STATUS current
            DESCRIPTION
                "Scan channels

                "
            ::= { turboRoamingEntry 4 }

        turboRoamingChannelA3 OBJECT-TYPE
            SYNTAX INTEGER
            MAX-ACCESS read-write
            STATUS current
            DESCRIPTION
                "Scan channels

                "
            ::= { turboRoamingEntry 5 }

        turboRoamingChannelB1 OBJECT-TYPE
            SYNTAX INTEGER
            MAX-ACCESS read-write
            STATUS current
            DESCRIPTION
                "Scan channels

                "
            ::= { turboRoamingEntry 6 }

        turboRoamingChannelB2 OBJECT-TYPE
            SYNTAX INTEGER
            MAX-ACCESS read-write
            STATUS current
            DESCRIPTION
                "Scan channels

                "
            ::= { turboRoamingEntry 7 }

        turboRoamingChannelB3 OBJECT-TYPE
            SYNTAX INTEGER
            MAX-ACCESS read-write
            STATUS current
            DESCRIPTION
                "Scan channels

                "
            ::= { turboRoamingEntry 8 }

        turboRoamingChannelG1 OBJECT-TYPE
            SYNTAX INTEGER
            MAX-ACCESS read-write
            STATUS current
            DESCRIPTION
                "Scan channels

                "
            ::= { turboRoamingEntry 9 }

        turboRoamingChannelG2 OBJECT-TYPE
            SYNTAX INTEGER
            MAX-ACCESS read-write
            STATUS current
            DESCRIPTION
                "Scan channels

                "
            ::= { turboRoamingEntry 10 }

        turboRoamingChannelG3 OBJECT-TYPE
            SYNTAX INTEGER
            MAX-ACCESS read-write
            STATUS current
            DESCRIPTION
                "Scan channels

                "
            ::= { turboRoamingEntry 11 }

        turboRoamingChannelBG1 OBJECT-TYPE
            SYNTAX INTEGER
            MAX-ACCESS read-write
            STATUS current
            DESCRIPTION
                "Scan channels

                "
            ::= { turboRoamingEntry 12 }

        turboRoamingChannelBG2 OBJECT-TYPE
            SYNTAX INTEGER
            MAX-ACCESS read-write
            STATUS current
            DESCRIPTION
                "Scan channels

                "
            ::= { turboRoamingEntry 13 }

        turboRoamingChannelBG3 OBJECT-TYPE
            SYNTAX INTEGER
            MAX-ACCESS read-write
            STATUS current
            DESCRIPTION
                "Scan channels

                "
            ::= { turboRoamingEntry 14 }

        turboRoamingApAliveCheckEnable OBJECT-TYPE
            SYNTAX INTEGER { enable(1), disable(2) }
            MAX-ACCESS read-write
            STATUS current
            DESCRIPTION
                "AP alive check

                Value : 1 -> enable, 2 -> disable"
            ::= { turboRoamingEntry 15 }

        turboRoamingChannelN24GHz1 OBJECT-TYPE
            SYNTAX INTEGER
            MAX-ACCESS read-write
            STATUS current
            DESCRIPTION
                "Scan channels

                "
            ::= { turboRoamingEntry 16 }

        turboRoamingChannelN24GHz2 OBJECT-TYPE
            SYNTAX INTEGER
            MAX-ACCESS read-write
            STATUS current
            DESCRIPTION
                "Scan channels

                "
            ::= { turboRoamingEntry 17 }

        turboRoamingChannelN24GHz3 OBJECT-TYPE
            SYNTAX INTEGER
            MAX-ACCESS read-write
            STATUS current
            DESCRIPTION
                "Scan channels

                "
            ::= { turboRoamingEntry 18 }

        turboRoamingChannelN5GHz1 OBJECT-TYPE
            SYNTAX INTEGER
            MAX-ACCESS read-write
            STATUS current
            DESCRIPTION
                "Scan channels

                "
            ::= { turboRoamingEntry 19 }

        turboRoamingChannelN5GHz2 OBJECT-TYPE
            SYNTAX INTEGER
            MAX-ACCESS read-write
            STATUS current
            DESCRIPTION
                "Scan channels

                "
            ::= { turboRoamingEntry 20 }

        turboRoamingChannelN5GHz3 OBJECT-TYPE
            SYNTAX INTEGER
            MAX-ACCESS read-write
            STATUS current
            DESCRIPTION
                "Scan channels

                "
            ::= { turboRoamingEntry 21 }

        turboRoamingSelectTRtypeEnable OBJECT-TYPE
            SYNTAX INTEGER { troam100(1), troam50(2) }
            MAX-ACCESS read-write
            STATUS current
            DESCRIPTION
                "Turbo Roaming type

                Value : 1 -> troam100, 2 -> troam50"
            ::= { turboRoamingEntry 22 }

        turboRoamingRoamingThreshunit OBJECT-TYPE
            SYNTAX INTEGER { snr(1), signal-strength(2) }
            MAX-ACCESS read-write
            STATUS current
            DESCRIPTION
                "Roaming threshold unit

                Value : 1 -> snr, 2 -> signal-strength"
            ::= { turboRoamingEntry 23 }

        turboRoamingRoamingAliveunit OBJECT-TYPE
            SYNTAX INTEGER { snr(1), signal-strength(2) }
            MAX-ACCESS read-write
            STATUS current
            DESCRIPTION
                "Roaming threshold unit

                Value : 1 -> snr, 2 -> signal-strength"
            ::= { turboRoamingEntry 24 }

        turboRoamingRoamingThresh2GSNR OBJECT-TYPE
            SYNTAX INTEGER (5..60)
            MAX-ACCESS read-write
            STATUS current
            DESCRIPTION
                "Roaming threshold

                "
            ::= { turboRoamingEntry 25 }

        turboRoamingRoamingThresh2GSignal OBJECT-TYPE
            SYNTAX INTEGER (-100..-35)
            MAX-ACCESS read-write
            STATUS current
            DESCRIPTION
                "Roaming threshold

                "
            ::= { turboRoamingEntry 26 }

        turboRoamingRoamingDifference2G OBJECT-TYPE
            SYNTAX INTEGER (5..20)
            MAX-ACCESS read-write
            STATUS current
            DESCRIPTION
                "Roaming difference

                "
            ::= { turboRoamingEntry 27 }

        turboRoamingApCandidateThreshold2GSNR OBJECT-TYPE
            SYNTAX INTEGER (5..40)
            MAX-ACCESS read-write
            STATUS current
            DESCRIPTION
                "AP candidate threshold

                "
            ::= { turboRoamingEntry 28 }

        turboRoamingApCandidateThreshold2GSignal OBJECT-TYPE
            SYNTAX INTEGER (-100..-35)
            MAX-ACCESS read-write
            STATUS current
            DESCRIPTION
                "AP candidate threshold

                "
            ::= { turboRoamingEntry 29 }

        turboRoamingRoamingThresh5GSNR OBJECT-TYPE
            SYNTAX INTEGER (5..60)
            MAX-ACCESS read-write
            STATUS current
            DESCRIPTION
                "Roaming threshold

                "
            ::= { turboRoamingEntry 30 }

        turboRoamingRoamingThresh5GSignal OBJECT-TYPE
            SYNTAX INTEGER (-100..-35)
            MAX-ACCESS read-write
            STATUS current
            DESCRIPTION
                "Roaming threshold

                "
            ::= { turboRoamingEntry 31 }

        turboRoamingRoamingDifference5G OBJECT-TYPE
            SYNTAX INTEGER (5..20)
            MAX-ACCESS read-write
            STATUS current
            DESCRIPTION
                "Roaming difference

                "
            ::= { turboRoamingEntry 32 }

        turboRoamingApCandidateThreshold5GSNR OBJECT-TYPE
            SYNTAX INTEGER (5..40)
            MAX-ACCESS read-write
            STATUS current
            DESCRIPTION
                "AP candidate threshold

                "
            ::= { turboRoamingEntry 33 }

        turboRoamingApCandidateThreshold5GSignal OBJECT-TYPE
            SYNTAX INTEGER (-100..-35)
            MAX-ACCESS read-write
            STATUS current
            DESCRIPTION
                "AP candidate threshold

                "
            ::= { turboRoamingEntry 34 }

        turboRoamingRoamingThreshLegacySNR OBJECT-TYPE
            SYNTAX INTEGER (5..60)
            MAX-ACCESS read-write
            STATUS current
            DESCRIPTION
                "Roaming threshold

                "
            ::= { turboRoamingEntry 36 }

        turboRoamingRoamingThreshLegacySignal OBJECT-TYPE
            SYNTAX INTEGER (-100..-35)
            MAX-ACCESS read-write
            STATUS current
            DESCRIPTION
                "Roaming threshold

                "
            ::= { turboRoamingEntry 37 }

        turboRoamingRoamingThreshNmodeSNR OBJECT-TYPE
            SYNTAX INTEGER (5..60)
            MAX-ACCESS read-write
            STATUS current
            DESCRIPTION
                "Roaming threshold

                "
            ::= { turboRoamingEntry 38 }

        turboRoamingRoamingThreshNmode24GSignal OBJECT-TYPE
            SYNTAX INTEGER (-100..-35)
            MAX-ACCESS read-write
            STATUS current
            DESCRIPTION
                "Roaming threshold

                "
            ::= { turboRoamingEntry 39 }

        turboRoamingRoamingThreshNmode5GSignal OBJECT-TYPE
            SYNTAX INTEGER (-100..-35)
            MAX-ACCESS read-write
            STATUS current
            DESCRIPTION
                "Roaming threshold

                "
            ::= { turboRoamingEntry 40 }

        turboRoamingChannelA4 OBJECT-TYPE
            SYNTAX INTEGER
            MAX-ACCESS read-write
            STATUS current
            DESCRIPTION
                "Scan channels

                "
            ::= { turboRoamingEntry 54 }

        turboRoamingChannelA5 OBJECT-TYPE
            SYNTAX INTEGER
            MAX-ACCESS read-write
            STATUS current
            DESCRIPTION
                "Scan channels

                "
            ::= { turboRoamingEntry 55 }

        turboRoamingChannelB4 OBJECT-TYPE
            SYNTAX INTEGER
            MAX-ACCESS read-write
            STATUS current
            DESCRIPTION
                "Scan channels

                "
            ::= { turboRoamingEntry 56 }

        turboRoamingChannelB5 OBJECT-TYPE
            SYNTAX INTEGER
            MAX-ACCESS read-write
            STATUS current
            DESCRIPTION
                "Scan channels

                "
            ::= { turboRoamingEntry 57 }

        turboRoamingChannelG4 OBJECT-TYPE
            SYNTAX INTEGER
            MAX-ACCESS read-write
            STATUS current
            DESCRIPTION
                "Scan channels

                "
            ::= { turboRoamingEntry 58 }

        turboRoamingChannelG5 OBJECT-TYPE
            SYNTAX INTEGER
            MAX-ACCESS read-write
            STATUS current
            DESCRIPTION
                "Scan channels

                "
            ::= { turboRoamingEntry 59 }

        turboRoamingChannelBG4 OBJECT-TYPE
            SYNTAX INTEGER
            MAX-ACCESS read-write
            STATUS current
            DESCRIPTION
                "Scan channels

                "
            ::= { turboRoamingEntry 60 }

        turboRoamingChannelBG5 OBJECT-TYPE
            SYNTAX INTEGER
            MAX-ACCESS read-write
            STATUS current
            DESCRIPTION
                "Scan channels

                "
            ::= { turboRoamingEntry 61 }

        turboRoamingChannelN24GHz4 OBJECT-TYPE
            SYNTAX INTEGER
            MAX-ACCESS read-write
            STATUS current
            DESCRIPTION
                "Scan channels

                "
            ::= { turboRoamingEntry 62 }

        turboRoamingChannelN24GHz5 OBJECT-TYPE
            SYNTAX INTEGER
            MAX-ACCESS read-write
            STATUS current
            DESCRIPTION
                "Scan channels

                "
            ::= { turboRoamingEntry 63 }

        turboRoamingChannelN5GHz4 OBJECT-TYPE
            SYNTAX INTEGER
            MAX-ACCESS read-write
            STATUS current
            DESCRIPTION
                "Scan channels

                "
            ::= { turboRoamingEntry 64 }

        turboRoamingChannelN5GHz5 OBJECT-TYPE
            SYNTAX INTEGER
            MAX-ACCESS read-write
            STATUS current
            DESCRIPTION
                "Scan channels

                "
            ::= { turboRoamingEntry 65 }

        turboRoamingRoamingAliveLegacySNR OBJECT-TYPE
            SYNTAX INTEGER (5..60)
            MAX-ACCESS read-write
            STATUS current
            DESCRIPTION
                "AP candidate threshold

                "
            ::= { turboRoamingEntry 68 }

        turboRoamingRoamingAliveSignal OBJECT-TYPE
            SYNTAX INTEGER (-100..-35)
            MAX-ACCESS read-write
            STATUS current
            DESCRIPTION
                "AP candidate threshold

                "
            ::= { turboRoamingEntry 69 }

        turboRoamingRoamingAliveNmode24GSNR OBJECT-TYPE
            SYNTAX INTEGER (5..60)
            MAX-ACCESS read-write
            STATUS current
            DESCRIPTION
                "AP candidate threshold

                "
            ::= { turboRoamingEntry 70 }

        turboRoamingRoamingAliveNmode24GSignal OBJECT-TYPE
            SYNTAX INTEGER (-100..-35)
            MAX-ACCESS read-write
            STATUS current
            DESCRIPTION
                "AP candidate threshold

                "
            ::= { turboRoamingEntry 71 }

        turboRoamingRoamingAliveNmode5GSNR OBJECT-TYPE
            SYNTAX INTEGER (5..60)
            MAX-ACCESS read-write
            STATUS current
            DESCRIPTION
                "AP candidate threshold

                "
            ::= { turboRoamingEntry 72 }

        turboRoamingRoamingAliveNmode5GSignal OBJECT-TYPE
            SYNTAX INTEGER (-100..-35)
            MAX-ACCESS read-write
            STATUS current
            DESCRIPTION
                "AP candidate threshold

                "
            ::= { turboRoamingEntry 73 }

        turboRoamingChannelA6 OBJECT-TYPE
            SYNTAX INTEGER
            MAX-ACCESS read-write
            STATUS current
            DESCRIPTION
                "Scan channels

                "
            ::= { turboRoamingEntry 203 }

        turboRoamingChannelA7 OBJECT-TYPE
            SYNTAX INTEGER
            MAX-ACCESS read-write
            STATUS current
            DESCRIPTION
                "Scan channels

                "
            ::= { turboRoamingEntry 204 }

        turboRoamingChannelA8 OBJECT-TYPE
            SYNTAX INTEGER
            MAX-ACCESS read-write
            STATUS current
            DESCRIPTION
                "Scan channels

                "
            ::= { turboRoamingEntry 205 }

        turboRoamingChannelA9 OBJECT-TYPE
            SYNTAX INTEGER
            MAX-ACCESS read-write
            STATUS current
            DESCRIPTION
                "Scan channels

                "
            ::= { turboRoamingEntry 206 }

        turboRoamingChannelA10 OBJECT-TYPE
            SYNTAX INTEGER
            MAX-ACCESS read-write
            STATUS current
            DESCRIPTION
                "Scan channels

                "
            ::= { turboRoamingEntry 207 }

        turboRoamingChannelA11 OBJECT-TYPE
            SYNTAX INTEGER
            MAX-ACCESS read-write
            STATUS current
            DESCRIPTION
                "Scan channels

                "
            ::= { turboRoamingEntry 208 }

        turboRoamingChannelB6 OBJECT-TYPE
            SYNTAX INTEGER
            MAX-ACCESS read-write
            STATUS current
            DESCRIPTION
                "Scan channels

                "
            ::= { turboRoamingEntry 223 }

        turboRoamingChannelB7 OBJECT-TYPE
            SYNTAX INTEGER
            MAX-ACCESS read-write
            STATUS current
            DESCRIPTION
                "Scan channels

                "
            ::= { turboRoamingEntry 224 }

        turboRoamingChannelB8 OBJECT-TYPE
            SYNTAX INTEGER
            MAX-ACCESS read-write
            STATUS current
            DESCRIPTION
                "Scan channels

                "
            ::= { turboRoamingEntry 225 }

        turboRoamingChannelB9 OBJECT-TYPE
            SYNTAX INTEGER
            MAX-ACCESS read-write
            STATUS current
            DESCRIPTION
                "Scan channels

                "
            ::= { turboRoamingEntry 226 }

        turboRoamingChannelB10 OBJECT-TYPE
            SYNTAX INTEGER
            MAX-ACCESS read-write
            STATUS current
            DESCRIPTION
                "Scan channels

                "
            ::= { turboRoamingEntry 227 }

        turboRoamingChannelB11 OBJECT-TYPE
            SYNTAX INTEGER
            MAX-ACCESS read-write
            STATUS current
            DESCRIPTION
                "Scan channels

                "
            ::= { turboRoamingEntry 228 }

        turboRoamingChannelG6 OBJECT-TYPE
            SYNTAX INTEGER
            MAX-ACCESS read-write
            STATUS current
            DESCRIPTION
                "Scan channels

                "
            ::= { turboRoamingEntry 243 }

        turboRoamingChannelG7 OBJECT-TYPE
            SYNTAX INTEGER
            MAX-ACCESS read-write
            STATUS current
            DESCRIPTION
                "Scan channels

                "
            ::= { turboRoamingEntry 244 }

        turboRoamingChannelG8 OBJECT-TYPE
            SYNTAX INTEGER
            MAX-ACCESS read-write
            STATUS current
            DESCRIPTION
                "Scan channels

                "
            ::= { turboRoamingEntry 245 }

        turboRoamingChannelG9 OBJECT-TYPE
            SYNTAX INTEGER
            MAX-ACCESS read-write
            STATUS current
            DESCRIPTION
                "Scan channels

                "
            ::= { turboRoamingEntry 246 }

        turboRoamingChannelG10 OBJECT-TYPE
            SYNTAX INTEGER
            MAX-ACCESS read-write
            STATUS current
            DESCRIPTION
                "Scan channels

                "
            ::= { turboRoamingEntry 247 }

        turboRoamingChannelG11 OBJECT-TYPE
            SYNTAX INTEGER
            MAX-ACCESS read-write
            STATUS current
            DESCRIPTION
                "Scan channels

                "
            ::= { turboRoamingEntry 248 }

        turboRoamingChannelBG6 OBJECT-TYPE
            SYNTAX INTEGER
            MAX-ACCESS read-write
            STATUS current
            DESCRIPTION
                "Scan channels

                "
            ::= { turboRoamingEntry 263 }

        turboRoamingChannelBG7 OBJECT-TYPE
            SYNTAX INTEGER
            MAX-ACCESS read-write
            STATUS current
            DESCRIPTION
                "Scan channels

                "
            ::= { turboRoamingEntry 264 }

        turboRoamingChannelBG8 OBJECT-TYPE
            SYNTAX INTEGER
            MAX-ACCESS read-write
            STATUS current
            DESCRIPTION
                "Scan channels

                "
            ::= { turboRoamingEntry 265 }

        turboRoamingChannelBG9 OBJECT-TYPE
            SYNTAX INTEGER
            MAX-ACCESS read-write
            STATUS current
            DESCRIPTION
                "Scan channels

                "
            ::= { turboRoamingEntry 266 }

        turboRoamingChannelBG10 OBJECT-TYPE
            SYNTAX INTEGER
            MAX-ACCESS read-write
            STATUS current
            DESCRIPTION
                "Scan channels

                "
            ::= { turboRoamingEntry 267 }

        turboRoamingChannelBG11 OBJECT-TYPE
            SYNTAX INTEGER
            MAX-ACCESS read-write
            STATUS current
            DESCRIPTION
                "Scan channels

                "
            ::= { turboRoamingEntry 268 }

        turboRoamingChannelN24GHz6 OBJECT-TYPE
            SYNTAX INTEGER
            MAX-ACCESS read-write
            STATUS current
            DESCRIPTION
                "Scan channels

                "
            ::= { turboRoamingEntry 283 }

        turboRoamingChannelN24GHz7 OBJECT-TYPE
            SYNTAX INTEGER
            MAX-ACCESS read-write
            STATUS current
            DESCRIPTION
                "Scan channels

                "
            ::= { turboRoamingEntry 284 }

        turboRoamingChannelN24GHz8 OBJECT-TYPE
            SYNTAX INTEGER
            MAX-ACCESS read-write
            STATUS current
            DESCRIPTION
                "Scan channels

                "
            ::= { turboRoamingEntry 285 }

        turboRoamingChannelN24GHz9 OBJECT-TYPE
            SYNTAX INTEGER
            MAX-ACCESS read-write
            STATUS current
            DESCRIPTION
                "Scan channels

                "
            ::= { turboRoamingEntry 286 }

        turboRoamingChannelN24GHz10 OBJECT-TYPE
            SYNTAX INTEGER
            MAX-ACCESS read-write
            STATUS current
            DESCRIPTION
                "Scan channels

                "
            ::= { turboRoamingEntry 287 }

        turboRoamingChannelN24GHz11 OBJECT-TYPE
            SYNTAX INTEGER
            MAX-ACCESS read-write
            STATUS current
            DESCRIPTION
                "Scan channels

                "
            ::= { turboRoamingEntry 288 }

        turboRoamingChannelN5GHz6 OBJECT-TYPE
            SYNTAX INTEGER
            MAX-ACCESS read-write
            STATUS current
            DESCRIPTION
                "Scan channels

                "
            ::= { turboRoamingEntry 303 }

        turboRoamingChannelN5GHz7 OBJECT-TYPE
            SYNTAX INTEGER
            MAX-ACCESS read-write
            STATUS current
            DESCRIPTION
                "Scan channels

                "
            ::= { turboRoamingEntry 304 }

        turboRoamingChannelN5GHz8 OBJECT-TYPE
            SYNTAX INTEGER
            MAX-ACCESS read-write
            STATUS current
            DESCRIPTION
                "Scan channels

                "
            ::= { turboRoamingEntry 305 }

        turboRoamingChannelN5GHz9 OBJECT-TYPE
            SYNTAX INTEGER
            MAX-ACCESS read-write
            STATUS current
            DESCRIPTION
                "Scan channels

                "
            ::= { turboRoamingEntry 306 }

        turboRoamingChannelN5GHz10 OBJECT-TYPE
            SYNTAX INTEGER
            MAX-ACCESS read-write
            STATUS current
            DESCRIPTION
                "Scan channels

                "
            ::= { turboRoamingEntry 307 }

        turboRoamingChannelN5GHz11 OBJECT-TYPE
            SYNTAX INTEGER
            MAX-ACCESS read-write
            STATUS current
            DESCRIPTION
                "Scan channels

                "
            ::= { turboRoamingEntry 308 }

    aeroLinkProtection OBJECT IDENTIFIER ::= { wireless 23 }

        aeroLinkProtectionAPAliveCheck OBJECT-TYPE
            SYNTAX INTEGER { enable(1), disable(2) }
            MAX-ACCESS read-write
            STATUS current
            DESCRIPTION
                "AP alive check

                Value : 1 -> enable, 2 -> disable"
            ::= { aeroLinkProtection 1 }

        aeroLinkProtectionType OBJECT-TYPE
            SYNTAX INTEGER { enable(4), disable(5) }
            MAX-ACCESS read-write
            STATUS current
            DESCRIPTION
                "AeroLink Protection

                Value : 4 -> enable, 5 -> disable"
            ::= { aeroLinkProtection 2 }

        aeroLinkProtectionNumPort OBJECT-TYPE
            SYNTAX INTEGER { port1(1) }
            MAX-ACCESS read-write
            STATUS current
            DESCRIPTION
                "LAN Interface

                Value : 1 -> port1"
            ::= { aeroLinkProtection 3 }

        aeroLinkProtectionRfIndex OBJECT-TYPE
            SYNTAX INTEGER { rf1(1) }
            MAX-ACCESS read-write
            STATUS current
            DESCRIPTION
                "WLAN Interface

                Value : 1 -> rf1"
            ::= { aeroLinkProtection 4 }

        aeroLinkProtectionRssi-detect-en OBJECT-TYPE
            SYNTAX INTEGER { enable(1), disable(2) }
            MAX-ACCESS read-write
            STATUS current
            DESCRIPTION
                "AeroLink SNR/Signal Strength detection

                Value : 1 -> enable, 2 -> disable"
            ::= { aeroLinkProtection 7 }

        aeroLinkProtectionRssi-detect-unit OBJECT-TYPE
            SYNTAX INTEGER { snr(1), signal-strength(2) }
            MAX-ACCESS read-write
            STATUS current
            DESCRIPTION
                "AeroLink threshold unit

                Value : 1 -> snr, 2 -> signal-strength"
            ::= { aeroLinkProtection 8 }

        aeroLinkProtectionThreshold2G-SNR OBJECT-TYPE
            SYNTAX INTEGER (5..40)
            MAX-ACCESS read-write
            STATUS current
            DESCRIPTION
                "AeroLink threshold

                "
            ::= { aeroLinkProtection 9 }

        aeroLinkProtectionThreshold2G-Signal OBJECT-TYPE
            SYNTAX INTEGER
            MAX-ACCESS read-write
            STATUS current
            DESCRIPTION
                "AeroLink threshold

                "
            ::= { aeroLinkProtection 10 }

        aeroLinkProtectionDifference2G OBJECT-TYPE
            SYNTAX INTEGER (5..20)
            MAX-ACCESS read-write
            STATUS current
            DESCRIPTION
                "AeroLink difference

                "
            ::= { aeroLinkProtection 11 }

        aeroLinkProtectionThreshold5G-SNR OBJECT-TYPE
            SYNTAX INTEGER (5..40)
            MAX-ACCESS read-write
            STATUS current
            DESCRIPTION
                "AeroLink threshold

                "
            ::= { aeroLinkProtection 12 }

        aeroLinkProtectionThreshold5G-Signal OBJECT-TYPE
            SYNTAX INTEGER
            MAX-ACCESS read-write
            STATUS current
            DESCRIPTION
                "AeroLink threshold

                "
            ::= { aeroLinkProtection 13 }

        aeroLinkProtectionDifference5G OBJECT-TYPE
            SYNTAX INTEGER (5..20)
            MAX-ACCESS read-write
            STATUS current
            DESCRIPTION
                "AeroLink difference

                "
            ::= { aeroLinkProtection 14 }

        aeroLinkProtectionThresholdLegacy-SNR OBJECT-TYPE
            SYNTAX INTEGER (5..40)
            MAX-ACCESS read-write
            STATUS current
            DESCRIPTION
                "AeroLink threshold

                "
            ::= { aeroLinkProtection 15 }

        aeroLinkProtectionThresholdLegacy-Signal OBJECT-TYPE
            SYNTAX INTEGER
            MAX-ACCESS read-write
            STATUS current
            DESCRIPTION
                "AeroLink threshold

                "
            ::= { aeroLinkProtection 16 }

        aeroLinkProtectionThresholdNmode-SNR OBJECT-TYPE
            SYNTAX INTEGER (5..40)
            MAX-ACCESS read-write
            STATUS current
            DESCRIPTION
                "AeroLink threshold

                "
            ::= { aeroLinkProtection 17 }

        aeroLinkProtectionThresholdNmode24G-Signal OBJECT-TYPE
            SYNTAX INTEGER
            MAX-ACCESS read-write
            STATUS current
            DESCRIPTION
                "AeroLink threshold

                "
            ::= { aeroLinkProtection 18 }

        aeroLinkProtectionThresholdNmode5G-Signal OBJECT-TYPE
            SYNTAX INTEGER
            MAX-ACCESS read-write
            STATUS current
            DESCRIPTION
                "AeroLink threshold

                "
            ::= { aeroLinkProtection 19 }

    advanced OBJECT IDENTIFIER ::= { swMgmt 7 }

    dhcpServer OBJECT IDENTIFIER ::= { advanced 1 }

        dhcpServerEnable OBJECT-TYPE
            SYNTAX INTEGER { enable(1), disable(2) }
            MAX-ACCESS read-write
            STATUS current
            DESCRIPTION
                "DHCP server

                Value : 1 -> enable, 2 -> disable"
            ::= { dhcpServer 1 }

        dhcpServerIPv4Gateway OBJECT-TYPE
            SYNTAX IpAddress
            MAX-ACCESS read-write
            STATUS current
            DESCRIPTION
                "Default gateway

                "
            ::= { dhcpServer 2 }

        dhcpServerIPv4Netmask OBJECT-TYPE
            SYNTAX IpAddress
            MAX-ACCESS read-write
            STATUS current
            DESCRIPTION
                "Subnet mask

                "
            ::= { dhcpServer 3 }

        dhcpServerDnsTable OBJECT-TYPE
            SYNTAX SEQUENCE OF DhcpServerDnsEntry
            MAX-ACCESS not-accessible
            STATUS current
            DESCRIPTION
                "Table of dhcpServerDns"
            ::= { dhcpServer 4 }

        dhcpServerDnsEntry OBJECT-TYPE
            SYNTAX DhcpServerDnsEntry
            MAX-ACCESS not-accessible
            STATUS current
            DESCRIPTION
                "Entry of dhcpServerDns"
            INDEX { dhcpServerDnsIndex }
            ::= { dhcpServerDnsTable 1 }

        DhcpServerDnsEntry ::=
            SEQUENCE {
                dhcpServerDnsIndex
                    INTEGER,
                dhcpServerDnsData
                    IpAddress
            }

        dhcpServerDnsIndex OBJECT-TYPE
            SYNTAX INTEGER (1..2)
            MAX-ACCESS read-only
            STATUS current
            DESCRIPTION
                "Index of Dns"
            ::= { dhcpServerDnsEntry 1 }

        dhcpServerDnsData OBJECT-TYPE
            SYNTAX IpAddress
            MAX-ACCESS read-write
            STATUS current
            DESCRIPTION
                "Primary DNS server

                "
            ::= { dhcpServerDnsEntry 2 }

        dhcpServerIPv4StartAddr OBJECT-TYPE
            SYNTAX IpAddress
            MAX-ACCESS read-write
            STATUS current
            DESCRIPTION
                "Starting IP address

                "
            ::= { dhcpServer 5 }

        dhcpServerMaxClient OBJECT-TYPE
            SYNTAX INTEGER (1..128)
            MAX-ACCESS read-write
            STATUS current
            DESCRIPTION
                "Maximum number of users

                "
            ::= { dhcpServer 6 }

        dhcpServerLeaseTimeMinute OBJECT-TYPE
            SYNTAX INTEGER (2..14400)
            MAX-ACCESS read-write
            STATUS current
            DESCRIPTION
                "Client lease time

                "
            ::= { dhcpServer 8 }

        dhcpServerMapTable OBJECT-TYPE
            SYNTAX SEQUENCE OF DhcpServerMapEntry
            MAX-ACCESS not-accessible
            STATUS current
            DESCRIPTION
                "Table of dhcpServerMap"
            ::= { advanced 2 }

        dhcpServerMapEntry OBJECT-TYPE
            SYNTAX DhcpServerMapEntry
            MAX-ACCESS not-accessible
            STATUS current
            DESCRIPTION
                "Entry of dhcpServerMap"
            INDEX { dhcpServerMapIndex }
            ::= { dhcpServerMapTable 1 }

        DhcpServerMapEntry ::=
            SEQUENCE {
                dhcpServerMapIndex
                    INTEGER,
                dhcpServerMapEnable
                    INTEGER,
                dhcpServerMapMac
                    DisplayString,
                dhcpServerMapIPv4Addr
                    IpAddress
            }

        dhcpServerMapIndex OBJECT-TYPE
            SYNTAX INTEGER (1..16)
            MAX-ACCESS read-only
            STATUS current
            DESCRIPTION
                "Index of dhcpServerMap"
            ::= { dhcpServerMapEntry 1 }

        dhcpServerMapEnable OBJECT-TYPE
            SYNTAX INTEGER { enable(1), disable(2) }
            MAX-ACCESS read-write
            STATUS current
            DESCRIPTION
                "Enable

                Value : 1 -> enable, 2 -> disable"
            ::= { dhcpServerMapEntry 2 }

        dhcpServerMapMac OBJECT-TYPE
            SYNTAX DisplayString
            MAX-ACCESS read-write
            STATUS current
            DESCRIPTION
                "MAC address

                "
            ::= { dhcpServerMapEntry 3 }

        dhcpServerMapIPv4Addr OBJECT-TYPE
            SYNTAX IpAddress
            MAX-ACCESS read-write
            STATUS current
            DESCRIPTION
                "IP address

                "
            ::= { dhcpServerMapEntry 4 }

    macFilter OBJECT IDENTIFIER ::= { advanced 3 }

        macFilterEnable OBJECT-TYPE
            SYNTAX INTEGER { enable(1), disable(2) }
            MAX-ACCESS read-write
            STATUS current
            DESCRIPTION
                "MAC filters function

                Value : 1 -> enable, 2 -> disable"
            ::= { macFilter 1 }

        macFilterPolicy OBJECT-TYPE
            SYNTAX INTEGER { accept(1), drop(2) }
            MAX-ACCESS read-write
            STATUS current
            DESCRIPTION
                "Policy

                Value : 1 -> accept, 2 -> drop"
            ::= { macFilter 2 }

        macFilterRulesTable OBJECT-TYPE
            SYNTAX SEQUENCE OF MacFilterRulesEntry
            MAX-ACCESS not-accessible
            STATUS current
            DESCRIPTION
                "Table of macFilterRules"
            ::= { macFilter 3 }

        macFilterRulesEntry OBJECT-TYPE
            SYNTAX MacFilterRulesEntry
            MAX-ACCESS not-accessible
            STATUS current
            DESCRIPTION
                "Entry of macFilterRules"
            INDEX { macFilterRuleIndex }
            ::= { macFilterRulesTable 1 }

        MacFilterRulesEntry ::=
            SEQUENCE {
                macFilterRuleIndex
                    INTEGER,
                macFilterRuleEnable
                    INTEGER,
                macFilterRuleName
                    DisplayString,
                macFilterRuleAddr
                    DisplayString
            }

        macFilterRuleIndex OBJECT-TYPE
            SYNTAX INTEGER
            MAX-ACCESS read-only
            STATUS current
            DESCRIPTION
                "Index of MAC filter rule
                "
            ::= { macFilterRulesEntry 1 }

        macFilterRuleEnable OBJECT-TYPE
            SYNTAX INTEGER { enable(1), disable(2) }
            MAX-ACCESS read-write
            STATUS current
            DESCRIPTION
                "Enable MAC filter rule
                Value : 1 -> enable, 2 -> disable"
            ::= { macFilterRulesEntry 2 }

        macFilterRuleName OBJECT-TYPE
            SYNTAX DisplayString
            MAX-ACCESS read-write
            STATUS current
            DESCRIPTION
                "Name for MAC filter rule
                "
            ::= { macFilterRulesEntry 3 }

        macFilterRuleAddr OBJECT-TYPE
            SYNTAX DisplayString
            MAX-ACCESS read-write
            STATUS current
            DESCRIPTION
                "MAC address to filter rule
                "
            ::= { macFilterRulesEntry 4 }

    protocolFilter OBJECT IDENTIFIER ::= { advanced 4 }

        protocolFilterEnable OBJECT-TYPE
            SYNTAX INTEGER { enable(1), disable(2) }
            MAX-ACCESS read-write
            STATUS current
            DESCRIPTION
                "IP protocol filters function

                Value : 1 -> enable, 2 -> disable"
            ::= { protocolFilter 1 }

        protocolFilterPolicy OBJECT-TYPE
            SYNTAX INTEGER { accept(1), drop(2) }
            MAX-ACCESS read-write
            STATUS current
            DESCRIPTION
                "Policy

                Value : 1 -> accept, 2 -> drop"
            ::= { protocolFilter 2 }

        protocolFilterRulesTable OBJECT-TYPE
            SYNTAX SEQUENCE OF ProtocolFilterRulesEntry
            MAX-ACCESS not-accessible
            STATUS current
            DESCRIPTION
                "Table of protocolFilterRules"
            ::= { protocolFilter 3 }

        protocolFilterRulesEntry OBJECT-TYPE
            SYNTAX ProtocolFilterRulesEntry
            MAX-ACCESS not-accessible
            STATUS current
            DESCRIPTION
                "Entry of protocolFilterRules"
            INDEX { protocolFilterRuleIndex }
            ::= { protocolFilterRulesTable 1 }

        ProtocolFilterRulesEntry ::=
            SEQUENCE {
                protocolFilterRuleIndex
                    INTEGER,
                protocolFilterRuleEnable
                    INTEGER,
                protocolFilterRuleProtocol
                    INTEGER,
                protocolFilterRuleSrcIp
                    IpAddress,
                protocolFilterRuleSrcMask
                    IpAddress,
                protocolFilterRuleDstIp
                    IpAddress,
                protocolFilterRuleDstMask
                    IpAddress
            }

        protocolFilterRuleIndex OBJECT-TYPE
            SYNTAX INTEGER
            MAX-ACCESS read-only
            STATUS current
            DESCRIPTION
                "Index of protocol filter rule
                "
            ::= { protocolFilterRulesEntry 1 }

        protocolFilterRuleEnable OBJECT-TYPE
            SYNTAX INTEGER { enable(1), disable(2) }
            MAX-ACCESS read-write
            STATUS current
            DESCRIPTION
                "Enable protocol filter
                Value : 1 -> enable, 2 -> disable"
            ::= { protocolFilterRulesEntry 2 }

        protocolFilterRuleProtocol OBJECT-TYPE
            SYNTAX INTEGER { all(1), icmp(2), tcp(3), udp(4) }
            MAX-ACCESS read-write
            STATUS current
            DESCRIPTION
                "Protocol to filter
                Value : 1 -> all, 2 -> icmp, 3 -> tcp, 4 -> udp"
            ::= { protocolFilterRulesEntry 3 }

        protocolFilterRuleSrcIp OBJECT-TYPE
            SYNTAX IpAddress
            MAX-ACCESS read-write
            STATUS current
            DESCRIPTION
                "Source IP to filter
                "
            ::= { protocolFilterRulesEntry 4 }

        protocolFilterRuleSrcMask OBJECT-TYPE
            SYNTAX IpAddress
            MAX-ACCESS read-write
            STATUS current
            DESCRIPTION
                "Source IP mask to filter
                "
            ::= { protocolFilterRulesEntry 5 }

        protocolFilterRuleDstIp OBJECT-TYPE
            SYNTAX IpAddress
            MAX-ACCESS read-write
            STATUS current
            DESCRIPTION
                "Destination IP to filter
                "
            ::= { protocolFilterRulesEntry 6 }

        protocolFilterRuleDstMask OBJECT-TYPE
            SYNTAX IpAddress
            MAX-ACCESS read-write
            STATUS current
            DESCRIPTION
                "Destination IP mask to filter
                "
            ::= { protocolFilterRulesEntry 7 }

    portFilter OBJECT IDENTIFIER ::= { advanced 5 }

        portFilterEnable OBJECT-TYPE
            SYNTAX INTEGER { enable(1), disable(2) }
            MAX-ACCESS read-write
            STATUS current
            DESCRIPTION
                "TCP/UDP port filters function

                Value : 1 -> enable, 2 -> disable"
            ::= { portFilter 1 }

        portFilterPolicy OBJECT-TYPE
            SYNTAX INTEGER { accept(1), drop(2) }
            MAX-ACCESS read-write
            STATUS current
            DESCRIPTION
                "Policy

                Value : 1 -> accept, 2 -> drop"
            ::= { portFilter 2 }

        portFilterRulesTable OBJECT-TYPE
            SYNTAX SEQUENCE OF PortFilterRulesEntry
            MAX-ACCESS not-accessible
            STATUS current
            DESCRIPTION
                "Table of portFilterRules"
            ::= { portFilter 3 }

        portFilterRulesEntry OBJECT-TYPE
            SYNTAX PortFilterRulesEntry
            MAX-ACCESS not-accessible
            STATUS current
            DESCRIPTION
                "Entry of portFilterRules"
            INDEX { portFilterRuleIndex }
            ::= { portFilterRulesTable 1 }

        PortFilterRulesEntry ::=
            SEQUENCE {
                portFilterRuleIndex
                    INTEGER,
                portFilterRuleEnable
                    INTEGER,
                portFilterRuleName
                    DisplayString,
                portFilterRuleProtocol
                    INTEGER,
                portFilterRuleSrcPortStart
                    INTEGER,
                portFilterRuleSrcPortEnd
                    INTEGER,
                portFilterRuleDstPortStart
                    INTEGER,
                portFilterRuleDstPortEnd
                    INTEGER
            }

        portFilterRuleIndex OBJECT-TYPE
            SYNTAX INTEGER
            MAX-ACCESS read-only
            STATUS current
            DESCRIPTION
                "Index of port filter rule
                "
            ::= { portFilterRulesEntry 1 }

        portFilterRuleEnable OBJECT-TYPE
            SYNTAX INTEGER { enable(1), disable(2) }
            MAX-ACCESS read-write
            STATUS current
            DESCRIPTION
                "Enable port filter rule
                Value : 1 -> enable, 2 -> disable"
            ::= { portFilterRulesEntry 2 }

        portFilterRuleName OBJECT-TYPE
            SYNTAX DisplayString
            MAX-ACCESS read-write
            STATUS current
            DESCRIPTION
                "Name for port filter rule
                "
            ::= { portFilterRulesEntry 3 }

        portFilterRuleProtocol OBJECT-TYPE
            SYNTAX INTEGER { tcp(1), udp(2) }
            MAX-ACCESS read-write
            STATUS current
            DESCRIPTION
                "Protocol to filter
                Value : 1 -> tcp, 2 -> udp"
            ::= { portFilterRulesEntry 4 }

        portFilterRuleSrcPortStart OBJECT-TYPE
            SYNTAX INTEGER (1..65535)
            MAX-ACCESS read-write
            STATUS current
            DESCRIPTION
                "Start of source port to filter
                "
            ::= { portFilterRulesEntry 5 }

        portFilterRuleSrcPortEnd OBJECT-TYPE
            SYNTAX INTEGER (1..65535)
            MAX-ACCESS read-write
            STATUS current
            DESCRIPTION
                "End of source port to filter
                "
            ::= { portFilterRulesEntry 6 }

        portFilterRuleDstPortStart OBJECT-TYPE
            SYNTAX INTEGER (1..65535)
            MAX-ACCESS read-write
            STATUS current
            DESCRIPTION
                "Start of destination port to filter
                "
            ::= { portFilterRulesEntry 7 }

        portFilterRuleDstPortEnd OBJECT-TYPE
            SYNTAX INTEGER (1..65535)
            MAX-ACCESS read-write
            STATUS current
            DESCRIPTION
                "End of destination port to filter
                "
            ::= { portFilterRulesEntry 8 }

    stpBridge OBJECT IDENTIFIER ::= { advanced 6 }

        stpBridgeHelloTime OBJECT-TYPE
            SYNTAX INTEGER (1..10)
            MAX-ACCESS read-write
            STATUS current
            DESCRIPTION
                "Hello time

                "
            ::= { stpBridge 1 }

        stpBridgeMaxAgeTime OBJECT-TYPE
            SYNTAX INTEGER (6..40)
            MAX-ACCESS read-write
            STATUS current
            DESCRIPTION
                "Max. age

                "
            ::= { stpBridge 2 }

        stpBridgeForwardDelay OBJECT-TYPE
            SYNTAX INTEGER (4..30)
            MAX-ACCESS read-write
            STATUS current
            DESCRIPTION
                "Forwarding delay

                "
            ::= { stpBridge 3 }

        stpBridgePriority OBJECT-TYPE
            SYNTAX INTEGER { priority0(1), priority4096(2), priority8192(3), priority12288(4), priority16384(5), priority20480(6), priority24576(7), priority28672(8), priority32768(9), priority36864(10), priority40960(11), priority45056(12), priority49152(13), priority53248(14), priority57344(15), priority61440(16) }
            MAX-ACCESS read-write
            STATUS current
            DESCRIPTION
                "Bridge priority

                Value : 1 -> priority0, 2 -> priority4096, 3 -> priority8192, 4 -> priority12288, 5 -> priority16384, 6 -> priority20480, 7 -> priority24576, 8 -> priority28672, 9 -> priority32768, 10 -> priority36864, 11 -> priority40960, 12 -> priority45056, 13 -> priority49152, 14 -> priority53248, 15 -> priority57344, 16 -> priority61440"
            ::= { stpBridge 4 }

        stpPortLanTable OBJECT-TYPE
            SYNTAX SEQUENCE OF StpPortLanEntry
            MAX-ACCESS not-accessible
            STATUS current
            DESCRIPTION
                "Table of stpPortLan"
            ::= { advanced 7 }

        stpPortLanEntry OBJECT-TYPE
            SYNTAX StpPortLanEntry
            MAX-ACCESS not-accessible
            STATUS current
            DESCRIPTION
                "Entry of stpPortLan"
            INDEX { stpPortLanIndex }
            ::= { stpPortLanTable 1 }

        StpPortLanEntry ::=
            SEQUENCE {
                stpPortLanIndex
                    INTEGER,
                stpPortLanEnable
                    INTEGER,
                stpPortLanPriority
                    INTEGER,
                stpPortLanPathCost
                    INTEGER,
                stpPortLanEdgePort
                    INTEGER
            }

        stpPortLanIndex OBJECT-TYPE
            SYNTAX INTEGER (1..1)
            MAX-ACCESS read-only
            STATUS current
            DESCRIPTION
                "Index of stpPortLan"
            ::= { stpPortLanEntry 1 }

        stpPortLanEnable OBJECT-TYPE
            SYNTAX INTEGER { enable(1), disable(2) }
            MAX-ACCESS read-write
            STATUS current
            DESCRIPTION
                "Enable

                Value : 1 -> enable, 2 -> disable"
            ::= { stpPortLanEntry 2 }

        stpPortLanPriority OBJECT-TYPE
            SYNTAX INTEGER { priority0(1), priority16(2), priority32(3), priority48(4), priority64(5), priority80(6), priority96(7), priority112(8), priority128(9), priority144(10), priority160(11), priority176(12), priority192(13), priority208(14), priority224(15), priority240(16) }
            MAX-ACCESS read-write
            STATUS current
            DESCRIPTION
                "Port Priority

                Value : 1 -> priority0, 2 -> priority16, 3 -> priority32, 4 -> priority48, 5 -> priority64, 6 -> priority80, 7 -> priority96, 8 -> priority112, 9 -> priority128, 10 -> priority144, 11 -> priority160, 12 -> priority176, 13 -> priority192, 14 -> priority208, 15 -> priority224, 16 -> priority240"
            ::= { stpPortLanEntry 3 }

        stpPortLanPathCost OBJECT-TYPE
            SYNTAX INTEGER (1..200000000)
            MAX-ACCESS read-write
            STATUS current
            DESCRIPTION
                "Port Cost

                "
            ::= { stpPortLanEntry 4 }

        stpPortLanEdgePort OBJECT-TYPE
            SYNTAX INTEGER { enable(1), disable(2) }
            MAX-ACCESS read-write
            STATUS current
            DESCRIPTION
                "Edge Por

                Value : 1 -> enable, 2 -> disable"
            ::= { stpPortLanEntry 5 }

        stpPortWlanTable OBJECT-TYPE
            SYNTAX SEQUENCE OF StpPortWlanEntry
            MAX-ACCESS not-accessible
            STATUS current
            DESCRIPTION
                "Table of stpPortWlan"
            ::= { advanced 8 }

        stpPortWlanEntry OBJECT-TYPE
            SYNTAX StpPortWlanEntry
            MAX-ACCESS not-accessible
            STATUS current
            DESCRIPTION
                "Entry of stpPortWlan"
            INDEX { stpPortWlanIndex }
            ::= { stpPortWlanTable 1 }

        StpPortWlanEntry ::=
            SEQUENCE {
                stpPortWlanIndex
                    INTEGER,
                stpPortWlanEnable
                    INTEGER,
                stpPortWlanPriority
                    INTEGER,
                stpPortWlanPathCost
                    INTEGER,
                stpPortWlanEdgePort
                    INTEGER
            }

        stpPortWlanIndex OBJECT-TYPE
            SYNTAX INTEGER (1..1)
            MAX-ACCESS read-only
            STATUS current
            DESCRIPTION
                "Index of stpPortWlan"
            ::= { stpPortWlanEntry 1 }

        stpPortWlanEnable OBJECT-TYPE
            SYNTAX INTEGER { enable(1), disable(2) }
            MAX-ACCESS read-write
            STATUS current
            DESCRIPTION
                "Enable

                Value : 1 -> enable, 2 -> disable"
            ::= { stpPortWlanEntry 2 }

        stpPortWlanPriority OBJECT-TYPE
            SYNTAX INTEGER { priority0(1), priority16(2), priority32(3), priority48(4), priority64(5), priority80(6), priority96(7), priority112(8), priority128(9), priority144(10), priority160(11), priority176(12), priority192(13), priority208(14), priority224(15), priority240(16) }
            MAX-ACCESS read-write
            STATUS current
            DESCRIPTION
                "Port Priority

                Value : 1 -> priority0, 2 -> priority16, 3 -> priority32, 4 -> priority48, 5 -> priority64, 6 -> priority80, 7 -> priority96, 8 -> priority112, 9 -> priority128, 10 -> priority144, 11 -> priority160, 12 -> priority176, 13 -> priority192, 14 -> priority208, 15 -> priority224, 16 -> priority240"
            ::= { stpPortWlanEntry 3 }

        stpPortWlanPathCost OBJECT-TYPE
            SYNTAX INTEGER (1..200000000)
            MAX-ACCESS read-write
            STATUS current
            DESCRIPTION
                "Port Cost

                "
            ::= { stpPortWlanEntry 4 }

        stpPortWlanEdgePort OBJECT-TYPE
            SYNTAX INTEGER { enable(1), disable(2) }
            MAX-ACCESS read-write
            STATUS current
            DESCRIPTION
                "Edge Por

                Value : 1 -> enable, 2 -> disable"
            ::= { stpPortWlanEntry 5 }

    managementVID OBJECT IDENTIFIER ::= { advanced 11 }

        managementVIDVid OBJECT-TYPE
            SYNTAX INTEGER (1..4094)
            MAX-ACCESS read-write
            STATUS current
            DESCRIPTION
                "Management VLAN ID

                "
            ::= { managementVID 1 }

        lanVLANTable OBJECT-TYPE
            SYNTAX SEQUENCE OF LanVLANEntry
            MAX-ACCESS not-accessible
            STATUS current
            DESCRIPTION
                "Table of lanVLAN"
            ::= { advanced 12 }

        lanVLANEntry OBJECT-TYPE
            SYNTAX LanVLANEntry
            MAX-ACCESS not-accessible
            STATUS current
            DESCRIPTION
                "Entry of lanVLAN"
            INDEX { lanVLANIndex }
            ::= { lanVLANTable 1 }

        LanVLANEntry ::=
            SEQUENCE {
                lanVLANIndex
                    INTEGER,
                lanVLANPvid
                    INTEGER,
                lanVLANVlanTag0
                    INTEGER,
                lanVLANVlanTag1
                    INTEGER,
                lanVLANVlanTag2
                    INTEGER,
                lanVLANVlanTag3
                    INTEGER,
                lanVLANVlanTag4
                    INTEGER,
                lanVLANVlanTag5
                    INTEGER,
                lanVLANVlanTag6
                    INTEGER,
                lanVLANVlanTag7
                    INTEGER,
                lanVLANVlanTag8
                    INTEGER,
                lanVLANVlanTag9
                    INTEGER,
                lanVLANVlanTag10
                    INTEGER,
                lanVLANVlanTag11
                    INTEGER,
                lanVLANVlanTag12
                    INTEGER,
                lanVLANVlanTag13
                    INTEGER,
                lanVLANVlanTag14
                    INTEGER,
                lanVLANVlanTag15
                    INTEGER,
                lanVLANVlanTag16
                    INTEGER,
                lanVLANVlanTag17
                    INTEGER,
                lanVLANVlanTag18
                    INTEGER,
                lanVLANVlanTag19
                    INTEGER,
                lanVLANVlanTag20
                    INTEGER,
                lanVLANVlanTag21
                    INTEGER,
                lanVLANVlanTag22
                    INTEGER,
                lanVLANVlanTag23
                    INTEGER,
                lanVLANVlanTag24
                    INTEGER,
                lanVLANVlanTag25
                    INTEGER,
                lanVLANVlanTag26
                    INTEGER,
                lanVLANVlanTag27
                    INTEGER,
                lanVLANVlanTag28
                    INTEGER,
                lanVLANVlanTag29
                    INTEGER,
                lanVLANVlanTag30
                    INTEGER,
                lanVLANVlanTag31
                    INTEGER
            }

        lanVLANIndex OBJECT-TYPE
            SYNTAX INTEGER (1..1)
            MAX-ACCESS read-only
            STATUS current
            DESCRIPTION
                "Index of lanVLAN"
            ::= { lanVLANEntry 1 }

        lanVLANPvid OBJECT-TYPE
            SYNTAX INTEGER (1..4094)
            MAX-ACCESS read-write
            STATUS current
            DESCRIPTION
                "PVID

                "
            ::= { lanVLANEntry 2 }

        lanVLANVlanTag0 OBJECT-TYPE
            SYNTAX INTEGER (0..4094)
            MAX-ACCESS read-write
            STATUS current
            DESCRIPTION
                "VLAN Tagged

                "
            ::= { lanVLANEntry 3 }

        lanVLANVlanTag1 OBJECT-TYPE
            SYNTAX INTEGER (0..4094)
            MAX-ACCESS read-write
            STATUS current
            DESCRIPTION
                "VLAN Tagged

                "
            ::= { lanVLANEntry 4 }

        lanVLANVlanTag2 OBJECT-TYPE
            SYNTAX INTEGER (0..4094)
            MAX-ACCESS read-write
            STATUS current
            DESCRIPTION
                "VLAN Tagged

                "
            ::= { lanVLANEntry 5 }

        lanVLANVlanTag3 OBJECT-TYPE
            SYNTAX INTEGER (0..4094)
            MAX-ACCESS read-write
            STATUS current
            DESCRIPTION
                "VLAN Tagged

                "
            ::= { lanVLANEntry 6 }

        lanVLANVlanTag4 OBJECT-TYPE
            SYNTAX INTEGER (0..4094)
            MAX-ACCESS read-write
            STATUS current
            DESCRIPTION
                "VLAN Tagged

                "
            ::= { lanVLANEntry 7 }

        lanVLANVlanTag5 OBJECT-TYPE
            SYNTAX INTEGER (0..4094)
            MAX-ACCESS read-write
            STATUS current
            DESCRIPTION
                "VLAN Tagged

                "
            ::= { lanVLANEntry 8 }

        lanVLANVlanTag6 OBJECT-TYPE
            SYNTAX INTEGER (0..4094)
            MAX-ACCESS read-write
            STATUS current
            DESCRIPTION
                "VLAN Tagged

                "
            ::= { lanVLANEntry 9 }

        lanVLANVlanTag7 OBJECT-TYPE
            SYNTAX INTEGER (0..4094)
            MAX-ACCESS read-write
            STATUS current
            DESCRIPTION
                "VLAN Tagged

                "
            ::= { lanVLANEntry 10 }

        lanVLANVlanTag8 OBJECT-TYPE
            SYNTAX INTEGER (0..4094)
            MAX-ACCESS read-write
            STATUS current
            DESCRIPTION
                "VLAN Tagged

                "
            ::= { lanVLANEntry 11 }

        lanVLANVlanTag9 OBJECT-TYPE
            SYNTAX INTEGER (0..4094)
            MAX-ACCESS read-write
            STATUS current
            DESCRIPTION
                "VLAN Tagged

                "
            ::= { lanVLANEntry 12 }

        lanVLANVlanTag10 OBJECT-TYPE
            SYNTAX INTEGER (0..4094)
            MAX-ACCESS read-write
            STATUS current
            DESCRIPTION
                "VLAN Tagged

                "
            ::= { lanVLANEntry 13 }

        lanVLANVlanTag11 OBJECT-TYPE
            SYNTAX INTEGER (0..4094)
            MAX-ACCESS read-write
            STATUS current
            DESCRIPTION
                "VLAN Tagged

                "
            ::= { lanVLANEntry 14 }

        lanVLANVlanTag12 OBJECT-TYPE
            SYNTAX INTEGER (0..4094)
            MAX-ACCESS read-write
            STATUS current
            DESCRIPTION
                "VLAN Tagged

                "
            ::= { lanVLANEntry 15 }

        lanVLANVlanTag13 OBJECT-TYPE
            SYNTAX INTEGER (0..4094)
            MAX-ACCESS read-write
            STATUS current
            DESCRIPTION
                "VLAN Tagged

                "
            ::= { lanVLANEntry 16 }

        lanVLANVlanTag14 OBJECT-TYPE
            SYNTAX INTEGER (0..4094)
            MAX-ACCESS read-write
            STATUS current
            DESCRIPTION
                "VLAN Tagged

                "
            ::= { lanVLANEntry 17 }

        lanVLANVlanTag15 OBJECT-TYPE
            SYNTAX INTEGER (0..4094)
            MAX-ACCESS read-write
            STATUS current
            DESCRIPTION
                "VLAN Tagged

                "
            ::= { lanVLANEntry 18 }

        lanVLANVlanTag16 OBJECT-TYPE
            SYNTAX INTEGER (0..4094)
            MAX-ACCESS read-write
            STATUS current
            DESCRIPTION
                "VLAN Tagged

                "
            ::= { lanVLANEntry 19 }

        lanVLANVlanTag17 OBJECT-TYPE
            SYNTAX INTEGER (0..4094)
            MAX-ACCESS read-write
            STATUS current
            DESCRIPTION
                "VLAN Tagged

                "
            ::= { lanVLANEntry 20 }

        lanVLANVlanTag18 OBJECT-TYPE
            SYNTAX INTEGER (0..4094)
            MAX-ACCESS read-write
            STATUS current
            DESCRIPTION
                "VLAN Tagged

                "
            ::= { lanVLANEntry 21 }

        lanVLANVlanTag19 OBJECT-TYPE
            SYNTAX INTEGER (0..4094)
            MAX-ACCESS read-write
            STATUS current
            DESCRIPTION
                "VLAN Tagged

                "
            ::= { lanVLANEntry 22 }

        lanVLANVlanTag20 OBJECT-TYPE
            SYNTAX INTEGER (0..4094)
            MAX-ACCESS read-write
            STATUS current
            DESCRIPTION
                "VLAN Tagged

                "
            ::= { lanVLANEntry 23 }

        lanVLANVlanTag21 OBJECT-TYPE
            SYNTAX INTEGER (0..4094)
            MAX-ACCESS read-write
            STATUS current
            DESCRIPTION
                "VLAN Tagged

                "
            ::= { lanVLANEntry 24 }

        lanVLANVlanTag22 OBJECT-TYPE
            SYNTAX INTEGER (0..4094)
            MAX-ACCESS read-write
            STATUS current
            DESCRIPTION
                "VLAN Tagged

                "
            ::= { lanVLANEntry 25 }

        lanVLANVlanTag23 OBJECT-TYPE
            SYNTAX INTEGER (0..4094)
            MAX-ACCESS read-write
            STATUS current
            DESCRIPTION
                "VLAN Tagged

                "
            ::= { lanVLANEntry 26 }

        lanVLANVlanTag24 OBJECT-TYPE
            SYNTAX INTEGER (0..4094)
            MAX-ACCESS read-write
            STATUS current
            DESCRIPTION
                "VLAN Tagged

                "
            ::= { lanVLANEntry 27 }

        lanVLANVlanTag25 OBJECT-TYPE
            SYNTAX INTEGER (0..4094)
            MAX-ACCESS read-write
            STATUS current
            DESCRIPTION
                "VLAN Tagged

                "
            ::= { lanVLANEntry 28 }

        lanVLANVlanTag26 OBJECT-TYPE
            SYNTAX INTEGER (0..4094)
            MAX-ACCESS read-write
            STATUS current
            DESCRIPTION
                "VLAN Tagged

                "
            ::= { lanVLANEntry 29 }

        lanVLANVlanTag27 OBJECT-TYPE
            SYNTAX INTEGER (0..4094)
            MAX-ACCESS read-write
            STATUS current
            DESCRIPTION
                "VLAN Tagged

                "
            ::= { lanVLANEntry 30 }

        lanVLANVlanTag28 OBJECT-TYPE
            SYNTAX INTEGER (0..4094)
            MAX-ACCESS read-write
            STATUS current
            DESCRIPTION
                "VLAN Tagged

                "
            ::= { lanVLANEntry 31 }

        lanVLANVlanTag29 OBJECT-TYPE
            SYNTAX INTEGER (0..4094)
            MAX-ACCESS read-write
            STATUS current
            DESCRIPTION
                "VLAN Tagged

                "
            ::= { lanVLANEntry 32 }

        lanVLANVlanTag30 OBJECT-TYPE
            SYNTAX INTEGER (0..4094)
            MAX-ACCESS read-write
            STATUS current
            DESCRIPTION
                "VLAN Tagged

                "
            ::= { lanVLANEntry 33 }

        lanVLANVlanTag31 OBJECT-TYPE
            SYNTAX INTEGER (0..4094)
            MAX-ACCESS read-write
            STATUS current
            DESCRIPTION
                "VLAN Tagged

                "
            ::= { lanVLANEntry 34 }

        wlanVLANTable OBJECT-TYPE
            SYNTAX SEQUENCE OF WlanVLANEntry
            MAX-ACCESS not-accessible
            STATUS current
            DESCRIPTION
                "Table of wlanVLAN"
            ::= { advanced 13 }

        wlanVLANEntry OBJECT-TYPE
            SYNTAX WlanVLANEntry
            MAX-ACCESS not-accessible
            STATUS current
            DESCRIPTION
                "Entry of wlanVLAN"
            INDEX { wlanVLANIndex }
            ::= { wlanVLANTable 1 }

        WlanVLANEntry ::=
            SEQUENCE {
                wlanVLANIndex
                    INTEGER,
                wlanVLANPvid
                    INTEGER,
                wlanVLANVlanTag0
                    INTEGER,
                wlanVLANVlanTag1
                    INTEGER,
                wlanVLANVlanTag2
                    INTEGER,
                wlanVLANVlanTag3
                    INTEGER,
                wlanVLANVlanTag4
                    INTEGER,
                wlanVLANVlanTag5
                    INTEGER,
                wlanVLANVlanTag6
                    INTEGER,
                wlanVLANVlanTag7
                    INTEGER,
                wlanVLANVlanTag8
                    INTEGER,
                wlanVLANVlanTag9
                    INTEGER,
                wlanVLANVlanTag10
                    INTEGER,
                wlanVLANVlanTag11
                    INTEGER,
                wlanVLANVlanTag12
                    INTEGER,
                wlanVLANVlanTag13
                    INTEGER,
                wlanVLANVlanTag14
                    INTEGER,
                wlanVLANVlanTag15
                    INTEGER,
                wlanVLANVlanTag16
                    INTEGER,
                wlanVLANVlanTag17
                    INTEGER,
                wlanVLANVlanTag18
                    INTEGER,
                wlanVLANVlanTag19
                    INTEGER,
                wlanVLANVlanTag20
                    INTEGER,
                wlanVLANVlanTag21
                    INTEGER,
                wlanVLANVlanTag22
                    INTEGER,
                wlanVLANVlanTag23
                    INTEGER,
                wlanVLANVlanTag24
                    INTEGER,
                wlanVLANVlanTag25
                    INTEGER,
                wlanVLANVlanTag26
                    INTEGER,
                wlanVLANVlanTag27
                    INTEGER,
                wlanVLANVlanTag28
                    INTEGER,
                wlanVLANVlanTag29
                    INTEGER,
                wlanVLANVlanTag30
                    INTEGER,
                wlanVLANVlanTag31
                    INTEGER
            }

        wlanVLANIndex OBJECT-TYPE
            SYNTAX INTEGER (1..9)
            MAX-ACCESS read-only
            STATUS current
            DESCRIPTION
                "Index of wlanVLAN"
            ::= { wlanVLANEntry 1 }

        wlanVLANPvid OBJECT-TYPE
            SYNTAX INTEGER (1..4094)
            MAX-ACCESS read-write
            STATUS current
            DESCRIPTION
                "PVID

                "
            ::= { wlanVLANEntry 2 }

        wlanVLANVlanTag0 OBJECT-TYPE
            SYNTAX INTEGER (0..4094)
            MAX-ACCESS read-write
            STATUS current
            DESCRIPTION
                "VLAN Tagged

                "
            ::= { wlanVLANEntry 3 }

        wlanVLANVlanTag1 OBJECT-TYPE
            SYNTAX INTEGER (0..4094)
            MAX-ACCESS read-write
            STATUS current
            DESCRIPTION
                "VLAN Tagged

                "
            ::= { wlanVLANEntry 4 }

        wlanVLANVlanTag2 OBJECT-TYPE
            SYNTAX INTEGER (0..4094)
            MAX-ACCESS read-write
            STATUS current
            DESCRIPTION
                "VLAN Tagged

                "
            ::= { wlanVLANEntry 5 }

        wlanVLANVlanTag3 OBJECT-TYPE
            SYNTAX INTEGER (0..4094)
            MAX-ACCESS read-write
            STATUS current
            DESCRIPTION
                "VLAN Tagged

                "
            ::= { wlanVLANEntry 6 }

        wlanVLANVlanTag4 OBJECT-TYPE
            SYNTAX INTEGER (0..4094)
            MAX-ACCESS read-write
            STATUS current
            DESCRIPTION
                "VLAN Tagged

                "
            ::= { wlanVLANEntry 7 }

        wlanVLANVlanTag5 OBJECT-TYPE
            SYNTAX INTEGER (0..4094)
            MAX-ACCESS read-write
            STATUS current
            DESCRIPTION
                "VLAN Tagged

                "
            ::= { wlanVLANEntry 8 }

        wlanVLANVlanTag6 OBJECT-TYPE
            SYNTAX INTEGER (0..4094)
            MAX-ACCESS read-write
            STATUS current
            DESCRIPTION
                "VLAN Tagged

                "
            ::= { wlanVLANEntry 9 }

        wlanVLANVlanTag7 OBJECT-TYPE
            SYNTAX INTEGER (0..4094)
            MAX-ACCESS read-write
            STATUS current
            DESCRIPTION
                "VLAN Tagged

                "
            ::= { wlanVLANEntry 10 }

        wlanVLANVlanTag8 OBJECT-TYPE
            SYNTAX INTEGER (0..4094)
            MAX-ACCESS read-write
            STATUS current
            DESCRIPTION
                "VLAN Tagged

                "
            ::= { wlanVLANEntry 11 }

        wlanVLANVlanTag9 OBJECT-TYPE
            SYNTAX INTEGER (0..4094)
            MAX-ACCESS read-write
            STATUS current
            DESCRIPTION
                "VLAN Tagged

                "
            ::= { wlanVLANEntry 12 }

        wlanVLANVlanTag10 OBJECT-TYPE
            SYNTAX INTEGER (0..4094)
            MAX-ACCESS read-write
            STATUS current
            DESCRIPTION
                "VLAN Tagged

                "
            ::= { wlanVLANEntry 13 }

        wlanVLANVlanTag11 OBJECT-TYPE
            SYNTAX INTEGER (0..4094)
            MAX-ACCESS read-write
            STATUS current
            DESCRIPTION
                "VLAN Tagged

                "
            ::= { wlanVLANEntry 14 }

        wlanVLANVlanTag12 OBJECT-TYPE
            SYNTAX INTEGER (0..4094)
            MAX-ACCESS read-write
            STATUS current
            DESCRIPTION
                "VLAN Tagged

                "
            ::= { wlanVLANEntry 15 }

        wlanVLANVlanTag13 OBJECT-TYPE
            SYNTAX INTEGER (0..4094)
            MAX-ACCESS read-write
            STATUS current
            DESCRIPTION
                "VLAN Tagged

                "
            ::= { wlanVLANEntry 16 }

        wlanVLANVlanTag14 OBJECT-TYPE
            SYNTAX INTEGER (0..4094)
            MAX-ACCESS read-write
            STATUS current
            DESCRIPTION
                "VLAN Tagged

                "
            ::= { wlanVLANEntry 17 }

        wlanVLANVlanTag15 OBJECT-TYPE
            SYNTAX INTEGER (0..4094)
            MAX-ACCESS read-write
            STATUS current
            DESCRIPTION
                "VLAN Tagged

                "
            ::= { wlanVLANEntry 18 }

        wlanVLANVlanTag16 OBJECT-TYPE
            SYNTAX INTEGER (0..4094)
            MAX-ACCESS read-write
            STATUS current
            DESCRIPTION
                "VLAN Tagged

                "
            ::= { wlanVLANEntry 19 }

        wlanVLANVlanTag17 OBJECT-TYPE
            SYNTAX INTEGER (0..4094)
            MAX-ACCESS read-write
            STATUS current
            DESCRIPTION
                "VLAN Tagged

                "
            ::= { wlanVLANEntry 20 }

        wlanVLANVlanTag18 OBJECT-TYPE
            SYNTAX INTEGER (0..4094)
            MAX-ACCESS read-write
            STATUS current
            DESCRIPTION
                "VLAN Tagged

                "
            ::= { wlanVLANEntry 21 }

        wlanVLANVlanTag19 OBJECT-TYPE
            SYNTAX INTEGER (0..4094)
            MAX-ACCESS read-write
            STATUS current
            DESCRIPTION
                "VLAN Tagged

                "
            ::= { wlanVLANEntry 22 }

        wlanVLANVlanTag20 OBJECT-TYPE
            SYNTAX INTEGER (0..4094)
            MAX-ACCESS read-write
            STATUS current
            DESCRIPTION
                "VLAN Tagged

                "
            ::= { wlanVLANEntry 23 }

        wlanVLANVlanTag21 OBJECT-TYPE
            SYNTAX INTEGER (0..4094)
            MAX-ACCESS read-write
            STATUS current
            DESCRIPTION
                "VLAN Tagged

                "
            ::= { wlanVLANEntry 24 }

        wlanVLANVlanTag22 OBJECT-TYPE
            SYNTAX INTEGER (0..4094)
            MAX-ACCESS read-write
            STATUS current
            DESCRIPTION
                "VLAN Tagged

                "
            ::= { wlanVLANEntry 25 }

        wlanVLANVlanTag23 OBJECT-TYPE
            SYNTAX INTEGER (0..4094)
            MAX-ACCESS read-write
            STATUS current
            DESCRIPTION
                "VLAN Tagged

                "
            ::= { wlanVLANEntry 26 }

        wlanVLANVlanTag24 OBJECT-TYPE
            SYNTAX INTEGER (0..4094)
            MAX-ACCESS read-write
            STATUS current
            DESCRIPTION
                "VLAN Tagged

                "
            ::= { wlanVLANEntry 27 }

        wlanVLANVlanTag25 OBJECT-TYPE
            SYNTAX INTEGER (0..4094)
            MAX-ACCESS read-write
            STATUS current
            DESCRIPTION
                "VLAN Tagged

                "
            ::= { wlanVLANEntry 28 }

        wlanVLANVlanTag26 OBJECT-TYPE
            SYNTAX INTEGER (0..4094)
            MAX-ACCESS read-write
            STATUS current
            DESCRIPTION
                "VLAN Tagged

                "
            ::= { wlanVLANEntry 29 }

        wlanVLANVlanTag27 OBJECT-TYPE
            SYNTAX INTEGER (0..4094)
            MAX-ACCESS read-write
            STATUS current
            DESCRIPTION
                "VLAN Tagged

                "
            ::= { wlanVLANEntry 30 }

        wlanVLANVlanTag28 OBJECT-TYPE
            SYNTAX INTEGER (0..4094)
            MAX-ACCESS read-write
            STATUS current
            DESCRIPTION
                "VLAN Tagged

                "
            ::= { wlanVLANEntry 31 }

        wlanVLANVlanTag29 OBJECT-TYPE
            SYNTAX INTEGER (0..4094)
            MAX-ACCESS read-write
            STATUS current
            DESCRIPTION
                "VLAN Tagged

                "
            ::= { wlanVLANEntry 32 }

        wlanVLANVlanTag30 OBJECT-TYPE
            SYNTAX INTEGER (0..4094)
            MAX-ACCESS read-write
            STATUS current
            DESCRIPTION
                "VLAN Tagged

                "
            ::= { wlanVLANEntry 33 }

        wlanVLANVlanTag31 OBJECT-TYPE
            SYNTAX INTEGER (0..4094)
            MAX-ACCESS read-write
            STATUS current
            DESCRIPTION
                "VLAN Tagged

                "
            ::= { wlanVLANEntry 34 }

        wdsVLANTable OBJECT-TYPE
            SYNTAX SEQUENCE OF WdsVLANEntry
            MAX-ACCESS not-accessible
            STATUS current
            DESCRIPTION
                "Table of wdsVLAN"
            ::= { advanced 14 }

        wdsVLANEntry OBJECT-TYPE
            SYNTAX WdsVLANEntry
            MAX-ACCESS not-accessible
            STATUS current
            DESCRIPTION
                "Entry of wdsVLAN"
            INDEX { wdsVLANIndex }
            ::= { wdsVLANTable 1 }

        WdsVLANEntry ::=
            SEQUENCE {
                wdsVLANIndex
                    INTEGER,
                wdsVLANPvid
                    INTEGER,
                wdsVLANVlanTag0
                    INTEGER,
                wdsVLANVlanTag1
                    INTEGER,
                wdsVLANVlanTag2
                    INTEGER,
                wdsVLANVlanTag3
                    INTEGER,
                wdsVLANVlanTag4
                    INTEGER,
                wdsVLANVlanTag5
                    INTEGER,
                wdsVLANVlanTag6
                    INTEGER,
                wdsVLANVlanTag7
                    INTEGER,
                wdsVLANVlanTag8
                    INTEGER,
                wdsVLANVlanTag9
                    INTEGER,
                wdsVLANVlanTag10
                    INTEGER,
                wdsVLANVlanTag11
                    INTEGER,
                wdsVLANVlanTag12
                    INTEGER,
                wdsVLANVlanTag13
                    INTEGER,
                wdsVLANVlanTag14
                    INTEGER,
                wdsVLANVlanTag15
                    INTEGER,
                wdsVLANVlanTag16
                    INTEGER,
                wdsVLANVlanTag17
                    INTEGER,
                wdsVLANVlanTag18
                    INTEGER,
                wdsVLANVlanTag19
                    INTEGER,
                wdsVLANVlanTag20
                    INTEGER,
                wdsVLANVlanTag21
                    INTEGER,
                wdsVLANVlanTag22
                    INTEGER,
                wdsVLANVlanTag23
                    INTEGER,
                wdsVLANVlanTag24
                    INTEGER,
                wdsVLANVlanTag25
                    INTEGER,
                wdsVLANVlanTag26
                    INTEGER,
                wdsVLANVlanTag27
                    INTEGER,
                wdsVLANVlanTag28
                    INTEGER,
                wdsVLANVlanTag29
                    INTEGER,
                wdsVLANVlanTag30
                    INTEGER,
                wdsVLANVlanTag31
                    INTEGER
            }

        wdsVLANIndex OBJECT-TYPE
            SYNTAX INTEGER (1..8)
            MAX-ACCESS read-only
            STATUS current
            DESCRIPTION
                "Index of wdsVLAN"
            ::= { wdsVLANEntry 1 }

        wdsVLANPvid OBJECT-TYPE
            SYNTAX INTEGER (1..4094)
            MAX-ACCESS read-write
            STATUS current
            DESCRIPTION
                "PVID

                "
            ::= { wdsVLANEntry 2 }

        wdsVLANVlanTag0 OBJECT-TYPE
            SYNTAX INTEGER (0..4094)
            MAX-ACCESS read-write
            STATUS current
            DESCRIPTION
                "VLAN Tagged

                "
            ::= { wdsVLANEntry 3 }

        wdsVLANVlanTag1 OBJECT-TYPE
            SYNTAX INTEGER (0..4094)
            MAX-ACCESS read-write
            STATUS current
            DESCRIPTION
                "VLAN Tagged

                "
            ::= { wdsVLANEntry 4 }

        wdsVLANVlanTag2 OBJECT-TYPE
            SYNTAX INTEGER (0..4094)
            MAX-ACCESS read-write
            STATUS current
            DESCRIPTION
                "VLAN Tagged

                "
            ::= { wdsVLANEntry 5 }

        wdsVLANVlanTag3 OBJECT-TYPE
            SYNTAX INTEGER (0..4094)
            MAX-ACCESS read-write
            STATUS current
            DESCRIPTION
                "VLAN Tagged

                "
            ::= { wdsVLANEntry 6 }

        wdsVLANVlanTag4 OBJECT-TYPE
            SYNTAX INTEGER (0..4094)
            MAX-ACCESS read-write
            STATUS current
            DESCRIPTION
                "VLAN Tagged

                "
            ::= { wdsVLANEntry 7 }

        wdsVLANVlanTag5 OBJECT-TYPE
            SYNTAX INTEGER (0..4094)
            MAX-ACCESS read-write
            STATUS current
            DESCRIPTION
                "VLAN Tagged

                "
            ::= { wdsVLANEntry 8 }

        wdsVLANVlanTag6 OBJECT-TYPE
            SYNTAX INTEGER (0..4094)
            MAX-ACCESS read-write
            STATUS current
            DESCRIPTION
                "VLAN Tagged

                "
            ::= { wdsVLANEntry 9 }

        wdsVLANVlanTag7 OBJECT-TYPE
            SYNTAX INTEGER (0..4094)
            MAX-ACCESS read-write
            STATUS current
            DESCRIPTION
                "VLAN Tagged

                "
            ::= { wdsVLANEntry 10 }

        wdsVLANVlanTag8 OBJECT-TYPE
            SYNTAX INTEGER (0..4094)
            MAX-ACCESS read-write
            STATUS current
            DESCRIPTION
                "VLAN Tagged

                "
            ::= { wdsVLANEntry 11 }

        wdsVLANVlanTag9 OBJECT-TYPE
            SYNTAX INTEGER (0..4094)
            MAX-ACCESS read-write
            STATUS current
            DESCRIPTION
                "VLAN Tagged

                "
            ::= { wdsVLANEntry 12 }

        wdsVLANVlanTag10 OBJECT-TYPE
            SYNTAX INTEGER (0..4094)
            MAX-ACCESS read-write
            STATUS current
            DESCRIPTION
                "VLAN Tagged

                "
            ::= { wdsVLANEntry 13 }

        wdsVLANVlanTag11 OBJECT-TYPE
            SYNTAX INTEGER (0..4094)
            MAX-ACCESS read-write
            STATUS current
            DESCRIPTION
                "VLAN Tagged

                "
            ::= { wdsVLANEntry 14 }

        wdsVLANVlanTag12 OBJECT-TYPE
            SYNTAX INTEGER (0..4094)
            MAX-ACCESS read-write
            STATUS current
            DESCRIPTION
                "VLAN Tagged

                "
            ::= { wdsVLANEntry 15 }

        wdsVLANVlanTag13 OBJECT-TYPE
            SYNTAX INTEGER (0..4094)
            MAX-ACCESS read-write
            STATUS current
            DESCRIPTION
                "VLAN Tagged

                "
            ::= { wdsVLANEntry 16 }

        wdsVLANVlanTag14 OBJECT-TYPE
            SYNTAX INTEGER (0..4094)
            MAX-ACCESS read-write
            STATUS current
            DESCRIPTION
                "VLAN Tagged

                "
            ::= { wdsVLANEntry 17 }

        wdsVLANVlanTag15 OBJECT-TYPE
            SYNTAX INTEGER (0..4094)
            MAX-ACCESS read-write
            STATUS current
            DESCRIPTION
                "VLAN Tagged

                "
            ::= { wdsVLANEntry 18 }

        wdsVLANVlanTag16 OBJECT-TYPE
            SYNTAX INTEGER (0..4094)
            MAX-ACCESS read-write
            STATUS current
            DESCRIPTION
                "VLAN Tagged

                "
            ::= { wdsVLANEntry 19 }

        wdsVLANVlanTag17 OBJECT-TYPE
            SYNTAX INTEGER (0..4094)
            MAX-ACCESS read-write
            STATUS current
            DESCRIPTION
                "VLAN Tagged

                "
            ::= { wdsVLANEntry 20 }

        wdsVLANVlanTag18 OBJECT-TYPE
            SYNTAX INTEGER (0..4094)
            MAX-ACCESS read-write
            STATUS current
            DESCRIPTION
                "VLAN Tagged

                "
            ::= { wdsVLANEntry 21 }

        wdsVLANVlanTag19 OBJECT-TYPE
            SYNTAX INTEGER (0..4094)
            MAX-ACCESS read-write
            STATUS current
            DESCRIPTION
                "VLAN Tagged

                "
            ::= { wdsVLANEntry 22 }

        wdsVLANVlanTag20 OBJECT-TYPE
            SYNTAX INTEGER (0..4094)
            MAX-ACCESS read-write
            STATUS current
            DESCRIPTION
                "VLAN Tagged

                "
            ::= { wdsVLANEntry 23 }

        wdsVLANVlanTag21 OBJECT-TYPE
            SYNTAX INTEGER (0..4094)
            MAX-ACCESS read-write
            STATUS current
            DESCRIPTION
                "VLAN Tagged

                "
            ::= { wdsVLANEntry 24 }

        wdsVLANVlanTag22 OBJECT-TYPE
            SYNTAX INTEGER (0..4094)
            MAX-ACCESS read-write
            STATUS current
            DESCRIPTION
                "VLAN Tagged

                "
            ::= { wdsVLANEntry 25 }

        wdsVLANVlanTag23 OBJECT-TYPE
            SYNTAX INTEGER (0..4094)
            MAX-ACCESS read-write
            STATUS current
            DESCRIPTION
                "VLAN Tagged

                "
            ::= { wdsVLANEntry 26 }

        wdsVLANVlanTag24 OBJECT-TYPE
            SYNTAX INTEGER (0..4094)
            MAX-ACCESS read-write
            STATUS current
            DESCRIPTION
                "VLAN Tagged

                "
            ::= { wdsVLANEntry 27 }

        wdsVLANVlanTag25 OBJECT-TYPE
            SYNTAX INTEGER (0..4094)
            MAX-ACCESS read-write
            STATUS current
            DESCRIPTION
                "VLAN Tagged

                "
            ::= { wdsVLANEntry 28 }

        wdsVLANVlanTag26 OBJECT-TYPE
            SYNTAX INTEGER (0..4094)
            MAX-ACCESS read-write
            STATUS current
            DESCRIPTION
                "VLAN Tagged

                "
            ::= { wdsVLANEntry 29 }

        wdsVLANVlanTag27 OBJECT-TYPE
            SYNTAX INTEGER (0..4094)
            MAX-ACCESS read-write
            STATUS current
            DESCRIPTION
                "VLAN Tagged

                "
            ::= { wdsVLANEntry 30 }

        wdsVLANVlanTag28 OBJECT-TYPE
            SYNTAX INTEGER (0..4094)
            MAX-ACCESS read-write
            STATUS current
            DESCRIPTION
                "VLAN Tagged

                "
            ::= { wdsVLANEntry 31 }

        wdsVLANVlanTag29 OBJECT-TYPE
            SYNTAX INTEGER (0..4094)
            MAX-ACCESS read-write
            STATUS current
            DESCRIPTION
                "VLAN Tagged

                "
            ::= { wdsVLANEntry 32 }

        wdsVLANVlanTag30 OBJECT-TYPE
            SYNTAX INTEGER (0..4094)
            MAX-ACCESS read-write
            STATUS current
            DESCRIPTION
                "VLAN Tagged

                "
            ::= { wdsVLANEntry 33 }

        wdsVLANVlanTag31 OBJECT-TYPE
            SYNTAX INTEGER (0..4094)
            MAX-ACCESS read-write
            STATUS current
            DESCRIPTION
                "VLAN Tagged

                "
            ::= { wdsVLANEntry 34 }

    linkFaultPassThrough OBJECT IDENTIFIER ::= { advanced 15 }

        linkFaultPassThroughEnable OBJECT-TYPE
            SYNTAX INTEGER { enable(1), disable(2) }
            MAX-ACCESS read-write
            STATUS current
            DESCRIPTION
                "Link Fault Pass-Through

                Value : 1 -> enable, 2 -> disable"
            ::= { linkFaultPassThrough 1 }

    aeroMag OBJECT IDENTIFIER ::= { advanced 16 }

        aeroMagEnable OBJECT-TYPE
            SYNTAX INTEGER { disable(1), ap(2), client(3), clientRouter(4) }
            MAX-ACCESS read-write
            STATUS current
            DESCRIPTION
                "Enable

                Value : 1 -> disable, 2 -> ap, 3 -> client, 4 -> clientRouter"
            ::= { aeroMag 2 }

        aeroMagReset OBJECT-TYPE
            SYNTAX INTEGER { enable(1), disable(2) }
            MAX-ACCESS read-write
            STATUS current
            DESCRIPTION
                "Reset

                Value : 1 -> enable, 2 -> disable"
            ::= { aeroMag 3 }

        staticRouteTable OBJECT-TYPE
            SYNTAX SEQUENCE OF StaticRouteEntry
            MAX-ACCESS not-accessible
            STATUS current
            DESCRIPTION
                "Table of staticRoute"
            ::= { advanced 17 }

        staticRouteEntry OBJECT-TYPE
            SYNTAX StaticRouteEntry
            MAX-ACCESS not-accessible
            STATUS current
            DESCRIPTION
                "Entry of staticRoute"
            INDEX { staticRouteIndex }
            ::= { staticRouteTable 1 }

        StaticRouteEntry ::=
            SEQUENCE {
                staticRouteIndex
                    INTEGER,
                staticRouteStaticRouteEnable
                    INTEGER,
                staticRouteStaticRouteInterface
                    INTEGER,
                staticRouteStaticRouteDst
                    IpAddress,
                staticRouteStaticRouteNetmask
                    IpAddress,
                staticRouteStaticRouteGateway
                    IpAddress,
                staticRouteStaticRouteMetric
                    INTEGER
            }

        staticRouteIndex OBJECT-TYPE
            SYNTAX INTEGER (1..16)
            MAX-ACCESS read-only
            STATUS current
            DESCRIPTION
                "Index of staticRoute"
            ::= { staticRouteEntry 1 }

        staticRouteStaticRouteEnable OBJECT-TYPE
            SYNTAX INTEGER { enable(1), disable(2) }
            MAX-ACCESS read-write
            STATUS current
            DESCRIPTION
                "Active

                Value : 1 -> enable, 2 -> disable"
            ::= { staticRouteEntry 2 }

        staticRouteStaticRouteInterface OBJECT-TYPE
            SYNTAX INTEGER { wlan(1), lan(2) }
            MAX-ACCESS read-write
            STATUS current
            DESCRIPTION
                "Interface

                Value : 1 -> wlan, 2 -> lan"
            ::= { staticRouteEntry 3 }

        staticRouteStaticRouteDst OBJECT-TYPE
            SYNTAX IpAddress
            MAX-ACCESS read-write
            STATUS current
            DESCRIPTION
                "Destination

                "
            ::= { staticRouteEntry 4 }

        staticRouteStaticRouteNetmask OBJECT-TYPE
            SYNTAX IpAddress
            MAX-ACCESS read-write
            STATUS current
            DESCRIPTION
                "Netmask

                "
            ::= { staticRouteEntry 5 }

        staticRouteStaticRouteGateway OBJECT-TYPE
            SYNTAX IpAddress
            MAX-ACCESS read-write
            STATUS current
            DESCRIPTION
                "Gateway

                "
            ::= { staticRouteEntry 6 }

        staticRouteStaticRouteMetric OBJECT-TYPE
            SYNTAX INTEGER (1..9999)
            MAX-ACCESS read-write
            STATUS current
            DESCRIPTION
                "Metric

                "
            ::= { staticRouteEntry 7 }

    nat OBJECT IDENTIFIER ::= { advanced 18 }

        natNatMode OBJECT-TYPE
            SYNTAX INTEGER { nto1(1), disable(2), oneToOne(3) }
            MAX-ACCESS read-write
            STATUS current
            DESCRIPTION
                "NAT mode

                Value : 1 -> nto1, 2 -> disable, 3 -> oneToOne"
            ::= { nat 1 }

        portForwardingTable OBJECT-TYPE
            SYNTAX SEQUENCE OF PortForwardingEntry
            MAX-ACCESS not-accessible
            STATUS current
            DESCRIPTION
                "Table of portForwarding"
            ::= { advanced 19 }

        portForwardingEntry OBJECT-TYPE
            SYNTAX PortForwardingEntry
            MAX-ACCESS not-accessible
            STATUS current
            DESCRIPTION
                "Entry of portForwarding"
            INDEX { portForwardingIndex }
            ::= { portForwardingTable 1 }

        PortForwardingEntry ::=
            SEQUENCE {
                portForwardingIndex
                    INTEGER,
                portForwardingPortForwardingEnable
                    INTEGER,
                portForwardingPortForwardingProtocol
                    INTEGER,
                portForwardingPortForwardingWANPort
                    INTEGER,
                portForwardingPortForwardingLANIP
                    IpAddress,
                portForwardingPortForwardingLANPort
                    INTEGER
            }

        portForwardingIndex OBJECT-TYPE
            SYNTAX INTEGER (1..32)
            MAX-ACCESS read-only
            STATUS current
            DESCRIPTION
                "Index of portForwarding"
            ::= { portForwardingEntry 1 }

        portForwardingPortForwardingEnable OBJECT-TYPE
            SYNTAX INTEGER { enable(1), disable(2) }
            MAX-ACCESS read-write
            STATUS current
            DESCRIPTION
                "Port Forwarding Enable

                Value : 1 -> enable, 2 -> disable"
            ::= { portForwardingEntry 2 }

        portForwardingPortForwardingProtocol OBJECT-TYPE
            SYNTAX INTEGER { tcp(1), udp(2) }
            MAX-ACCESS read-write
            STATUS current
            DESCRIPTION
                "Protocol

                Value : 1 -> tcp, 2 -> udp"
            ::= { portForwardingEntry 3 }

        portForwardingPortForwardingWANPort OBJECT-TYPE
            SYNTAX INTEGER (1..65535)
            MAX-ACCESS read-write
            STATUS current
            DESCRIPTION
                "WAN port

                "
            ::= { portForwardingEntry 4 }

        portForwardingPortForwardingLANIP OBJECT-TYPE
            SYNTAX IpAddress
            MAX-ACCESS read-write
            STATUS current
            DESCRIPTION
                "LAN IP

                "
            ::= { portForwardingEntry 5 }

        portForwardingPortForwardingLANPort OBJECT-TYPE
            SYNTAX INTEGER (1..65535)
            MAX-ACCESS read-write
            STATUS current
            DESCRIPTION
                "LAN port

                "
            ::= { portForwardingEntry 6 }

    portForwardingservice OBJECT IDENTIFIER ::= { advanced 20 }

        portForwardingservicePortForwardingserviceEnable OBJECT-TYPE
            SYNTAX INTEGER { enable(1), disable(2) }
            MAX-ACCESS read-write
            STATUS current
            DESCRIPTION
                "Port Forwarding function

                Value : 1 -> enable, 2 -> disable"
            ::= { portForwardingservice 2 }

    aeroMagAction OBJECT IDENTIFIER ::= { advanced 23 }

        refreshChannel OBJECT-TYPE
            SYNTAX INTEGER
            MAX-ACCESS read-write
            STATUS current
            DESCRIPTION
                "Set 1 to refresh channel.
The AWK will change channels when the active channel is congested.
                "
            ::= { aeroMagAction 1 }

        oneToOneNatEntryTable OBJECT-TYPE
            SYNTAX SEQUENCE OF OneToOneNatEntryEntry
            MAX-ACCESS not-accessible
            STATUS current
            DESCRIPTION
                "Table of oneToOneNatEntry"
            ::= { advanced 61 }

        oneToOneNatEntryEntry OBJECT-TYPE
            SYNTAX OneToOneNatEntryEntry
            MAX-ACCESS not-accessible
            STATUS current
            DESCRIPTION
                "Entry of oneToOneNatEntry"
            INDEX { oneToOneNatEntryIndex }
            ::= { oneToOneNatEntryTable 1 }

        OneToOneNatEntryEntry ::=
            SEQUENCE {
                oneToOneNatEntryIndex
                    INTEGER,
                oneToOneNatEntryEnable
                    INTEGER,
                oneToOneNatEntryLanIP
                    IpAddress,
                oneToOneNatEntryWanIP
                    IpAddress
            }

        oneToOneNatEntryIndex OBJECT-TYPE
            SYNTAX INTEGER (1..16)
            MAX-ACCESS read-only
            STATUS current
            DESCRIPTION
                "Index of oneToOneNatEntry"
            ::= { oneToOneNatEntryEntry 1 }

        oneToOneNatEntryEnable OBJECT-TYPE
            SYNTAX INTEGER { enable(1), disable(2) }
            MAX-ACCESS read-write
            STATUS current
            DESCRIPTION
                "Active

                Value : 1 -> enable, 2 -> disable"
            ::= { oneToOneNatEntryEntry 2 }

        oneToOneNatEntryLanIP OBJECT-TYPE
            SYNTAX IpAddress
            MAX-ACCESS read-write
            STATUS current
            DESCRIPTION
                "LAN IP

                "
            ::= { oneToOneNatEntryEntry 3 }

        oneToOneNatEntryWanIP OBJECT-TYPE
            SYNTAX IpAddress
            MAX-ACCESS read-write
            STATUS current
            DESCRIPTION
                "WAN IP

                "
            ::= { oneToOneNatEntryEntry 4 }

    hTTPSetting OBJECT IDENTIFIER ::= { advanced 62 }

        hTTPSettingHTTPPort OBJECT-TYPE
            SYNTAX INTEGER (1..65535)
            MAX-ACCESS read-write
            STATUS current
            DESCRIPTION
                "HTTP port

                "
            ::= { hTTPSetting 1 }

        hTTPSettingHTTPSPort OBJECT-TYPE
            SYNTAX INTEGER (1..65535)
            MAX-ACCESS read-write
            STATUS current
            DESCRIPTION
                "HTTPS port

                "
            ::= { hTTPSetting 2 }

    autoWarning OBJECT IDENTIFIER ::= { swMgmt 9 }

    emailAction OBJECT IDENTIFIER ::= { autoWarning 1 }

        emailActionColdStart OBJECT-TYPE
            SYNTAX INTEGER { enable(1), disable(2) }
            MAX-ACCESS read-write
            STATUS current
            DESCRIPTION
                "Cold start

                Value : 1 -> enable, 2 -> disable"
            ::= { emailAction 1 }

        emailActionWarmStart OBJECT-TYPE
            SYNTAX INTEGER { enable(1), disable(2) }
            MAX-ACCESS read-write
            STATUS current
            DESCRIPTION
                "Warm start

                Value : 1 -> enable, 2 -> disable"
            ::= { emailAction 2 }

        emailActionPower1Off OBJECT-TYPE
            SYNTAX INTEGER { enable(1), disable(2) }
            MAX-ACCESS read-write
            STATUS current
            DESCRIPTION
                "Power 1 transition (On-->Off)

                Value : 1 -> enable, 2 -> disable"
            ::= { emailAction 3 }

        emailActionPower1On OBJECT-TYPE
            SYNTAX INTEGER { enable(1), disable(2) }
            MAX-ACCESS read-write
            STATUS current
            DESCRIPTION
                "Power 1 transition (Off-->On)

                Value : 1 -> enable, 2 -> disable"
            ::= { emailAction 4 }

        emailActionPower2Off OBJECT-TYPE
            SYNTAX INTEGER { enable(1), disable(2) }
            MAX-ACCESS read-write
            STATUS current
            DESCRIPTION
                "Power 2 transition (On-->Off)

                Value : 1 -> enable, 2 -> disable"
            ::= { emailAction 5 }

        emailActionPower2On OBJECT-TYPE
            SYNTAX INTEGER { enable(1), disable(2) }
            MAX-ACCESS read-write
            STATUS current
            DESCRIPTION
                "Power 2 transition (Off-->On)

                Value : 1 -> enable, 2 -> disable"
            ::= { emailAction 6 }

        emailActionPoeOff OBJECT-TYPE
            SYNTAX INTEGER { enable(1), disable(2) }
            MAX-ACCESS read-write
            STATUS current
            DESCRIPTION
                "PoE transition (On-->Off)

                Value : 1 -> enable, 2 -> disable"
            ::= { emailAction 7 }

        emailActionPoeOn OBJECT-TYPE
            SYNTAX INTEGER { enable(1), disable(2) }
            MAX-ACCESS read-write
            STATUS current
            DESCRIPTION
                "PoE transition (Off-->On)

                Value : 1 -> enable, 2 -> disable"
            ::= { emailAction 8 }

        emailActionDi1On2Off OBJECT-TYPE
            SYNTAX INTEGER { enable(1), disable(2) }
            MAX-ACCESS read-write
            STATUS current
            DESCRIPTION
                "DI 1 transition (On-->Off)

                Value : 1 -> enable, 2 -> disable"
            ::= { emailAction 9 }

        emailActionDi1Off2On OBJECT-TYPE
            SYNTAX INTEGER { enable(1), disable(2) }
            MAX-ACCESS read-write
            STATUS current
            DESCRIPTION
                "DI 1 transition (Off-->On)

                Value : 1 -> enable, 2 -> disable"
            ::= { emailAction 10 }

        emailActionDi2On2Off OBJECT-TYPE
            SYNTAX INTEGER { enable(1), disable(2) }
            MAX-ACCESS read-write
            STATUS current
            DESCRIPTION
                "DI 2 transition (On-->Off)

                Value : 1 -> enable, 2 -> disable"
            ::= { emailAction 11 }

        emailActionDi2Off2On OBJECT-TYPE
            SYNTAX INTEGER { enable(1), disable(2) }
            MAX-ACCESS read-write
            STATUS current
            DESCRIPTION
                "DI 2 transition (Off-->On)

                Value : 1 -> enable, 2 -> disable"
            ::= { emailAction 12 }

        emailActionConfigChange OBJECT-TYPE
            SYNTAX INTEGER { enable(1), disable(2) }
            MAX-ACCESS read-write
            STATUS current
            DESCRIPTION
                "Configuration changed

                Value : 1 -> enable, 2 -> disable"
            ::= { emailAction 13 }

        emailActionConsoleAuthFail OBJECT-TYPE
            SYNTAX INTEGER { enable(1), disable(2) }
            MAX-ACCESS read-write
            STATUS current
            DESCRIPTION
                "Console authentication failure

                Value : 1 -> enable, 2 -> disable"
            ::= { emailAction 14 }

        emailActionLanLinkOn OBJECT-TYPE
            SYNTAX INTEGER { enable(1), disable(2) }
            MAX-ACCESS read-write
            STATUS current
            DESCRIPTION
                "LAN link on

                Value : 1 -> enable, 2 -> disable"
            ::= { emailAction 18 }

        emailActionLanLinkOff OBJECT-TYPE
            SYNTAX INTEGER { enable(1), disable(2) }
            MAX-ACCESS read-write
            STATUS current
            DESCRIPTION
                "LAN link off

                Value : 1 -> enable, 2 -> disable"
            ::= { emailAction 19 }

        emailActionWlan1Connect OBJECT-TYPE
            SYNTAX INTEGER { enable(1), disable(2) }
            MAX-ACCESS read-write
            STATUS current
            DESCRIPTION
                "Port Connect

                Value : 1 -> enable, 2 -> disable"
            ::= { emailAction 40 }

        emailActionWlan1Disconnect OBJECT-TYPE
            SYNTAX INTEGER { enable(1), disable(2) }
            MAX-ACCESS read-write
            STATUS current
            DESCRIPTION
                "Port DisConnect

                Value : 1 -> enable, 2 -> disable"
            ::= { emailAction 41 }

        emailActionWlan1-1Connect OBJECT-TYPE
            SYNTAX INTEGER { enable(1), disable(2) }
            MAX-ACCESS read-write
            STATUS current
            DESCRIPTION
                "Port Connect

                Value : 1 -> enable, 2 -> disable"
            ::= { emailAction 46 }

        emailActionWlan1-1Disconnect OBJECT-TYPE
            SYNTAX INTEGER { enable(1), disable(2) }
            MAX-ACCESS read-write
            STATUS current
            DESCRIPTION
                "Port DisConnect

                Value : 1 -> enable, 2 -> disable"
            ::= { emailAction 47 }

        emailActionWlan1-2Connect OBJECT-TYPE
            SYNTAX INTEGER { enable(1), disable(2) }
            MAX-ACCESS read-write
            STATUS current
            DESCRIPTION
                "Port Connect

                Value : 1 -> enable, 2 -> disable"
            ::= { emailAction 49 }

        emailActionWlan1-2Disconnect OBJECT-TYPE
            SYNTAX INTEGER { enable(1), disable(2) }
            MAX-ACCESS read-write
            STATUS current
            DESCRIPTION
                "Port DisConnect

                Value : 1 -> enable, 2 -> disable"
            ::= { emailAction 50 }

        emailActionWlan1-3Connect OBJECT-TYPE
            SYNTAX INTEGER { enable(1), disable(2) }
            MAX-ACCESS read-write
            STATUS current
            DESCRIPTION
                "Port Connect

                Value : 1 -> enable, 2 -> disable"
            ::= { emailAction 52 }

        emailActionWlan1-3Disconnect OBJECT-TYPE
            SYNTAX INTEGER { enable(1), disable(2) }
            MAX-ACCESS read-write
            STATUS current
            DESCRIPTION
                "Port DisConnect

                Value : 1 -> enable, 2 -> disable"
            ::= { emailAction 53 }

        emailActionWlan1-4Connect OBJECT-TYPE
            SYNTAX INTEGER { enable(1), disable(2) }
            MAX-ACCESS read-write
            STATUS current
            DESCRIPTION
                "Port Connect

                Value : 1 -> enable, 2 -> disable"
            ::= { emailAction 55 }

        emailActionWlan1-4Disconnect OBJECT-TYPE
            SYNTAX INTEGER { enable(1), disable(2) }
            MAX-ACCESS read-write
            STATUS current
            DESCRIPTION
                "Port DisConnect

                Value : 1 -> enable, 2 -> disable"
            ::= { emailAction 56 }

        emailActionWlan1-5Connect OBJECT-TYPE
            SYNTAX INTEGER { enable(1), disable(2) }
            MAX-ACCESS read-write
            STATUS current
            DESCRIPTION
                "Port Connect

                Value : 1 -> enable, 2 -> disable"
            ::= { emailAction 58 }

        emailActionWlan1-5Disconnect OBJECT-TYPE
            SYNTAX INTEGER { enable(1), disable(2) }
            MAX-ACCESS read-write
            STATUS current
            DESCRIPTION
                "Port DisConnect

                Value : 1 -> enable, 2 -> disable"
            ::= { emailAction 59 }

        emailActionWlan1-6Connect OBJECT-TYPE
            SYNTAX INTEGER { enable(1), disable(2) }
            MAX-ACCESS read-write
            STATUS current
            DESCRIPTION
                "Port Connect

                Value : 1 -> enable, 2 -> disable"
            ::= { emailAction 61 }

        emailActionWlan1-6Disconnect OBJECT-TYPE
            SYNTAX INTEGER { enable(1), disable(2) }
            MAX-ACCESS read-write
            STATUS current
            DESCRIPTION
                "Port DisConnect

                Value : 1 -> enable, 2 -> disable"
            ::= { emailAction 62 }

        emailActionWlan1-7Connect OBJECT-TYPE
            SYNTAX INTEGER { enable(1), disable(2) }
            MAX-ACCESS read-write
            STATUS current
            DESCRIPTION
                "Port Connect

                Value : 1 -> enable, 2 -> disable"
            ::= { emailAction 64 }

        emailActionWlan1-7Disconnect OBJECT-TYPE
            SYNTAX INTEGER { enable(1), disable(2) }
            MAX-ACCESS read-write
            STATUS current
            DESCRIPTION
                "Port DisConnect

                Value : 1 -> enable, 2 -> disable"
            ::= { emailAction 65 }

        emailActionWlan1-8Connect OBJECT-TYPE
            SYNTAX INTEGER { enable(1), disable(2) }
            MAX-ACCESS read-write
            STATUS current
            DESCRIPTION
                "Port Connect

                Value : 1 -> enable, 2 -> disable"
            ::= { emailAction 67 }

        emailActionWlan1-8Disconnect OBJECT-TYPE
            SYNTAX INTEGER { enable(1), disable(2) }
            MAX-ACCESS read-write
            STATUS current
            DESCRIPTION
                "Port DisConnect

                Value : 1 -> enable, 2 -> disable"
            ::= { emailAction 68 }

    relayAction OBJECT IDENTIFIER ::= { autoWarning 2 }

        relayActionColdStart OBJECT-TYPE
            SYNTAX INTEGER { enable(1), disable(2) }
            MAX-ACCESS read-write
            STATUS current
            DESCRIPTION
                "Cold start

                Value : 1 -> enable, 2 -> disable"
            ::= { relayAction 1 }

        relayActionWarmStart OBJECT-TYPE
            SYNTAX INTEGER { enable(1), disable(2) }
            MAX-ACCESS read-write
            STATUS current
            DESCRIPTION
                "Warm start

                Value : 1 -> enable, 2 -> disable"
            ::= { relayAction 2 }

        relayActionPower1Off OBJECT-TYPE
            SYNTAX INTEGER { enable(1), disable(2) }
            MAX-ACCESS read-write
            STATUS current
            DESCRIPTION
                "Power 1 transition (On-->Off)

                Value : 1 -> enable, 2 -> disable"
            ::= { relayAction 3 }

        relayActionPower1On OBJECT-TYPE
            SYNTAX INTEGER { enable(1), disable(2) }
            MAX-ACCESS read-write
            STATUS current
            DESCRIPTION
                "Power 1 transition (Off-->On)

                Value : 1 -> enable, 2 -> disable"
            ::= { relayAction 4 }

        relayActionPower2Off OBJECT-TYPE
            SYNTAX INTEGER { enable(1), disable(2) }
            MAX-ACCESS read-write
            STATUS current
            DESCRIPTION
                "Power 2 transition (On-->Off)

                Value : 1 -> enable, 2 -> disable"
            ::= { relayAction 5 }

        relayActionPower2On OBJECT-TYPE
            SYNTAX INTEGER { enable(1), disable(2) }
            MAX-ACCESS read-write
            STATUS current
            DESCRIPTION
                "Power 2 transition (Off-->On)

                Value : 1 -> enable, 2 -> disable"
            ::= { relayAction 6 }

        relayActionPoeOff OBJECT-TYPE
            SYNTAX INTEGER { enable(1), disable(2) }
            MAX-ACCESS read-write
            STATUS current
            DESCRIPTION
                "PoE transition (On-->Off)

                Value : 1 -> enable, 2 -> disable"
            ::= { relayAction 7 }

        relayActionPoeOn OBJECT-TYPE
            SYNTAX INTEGER { enable(1), disable(2) }
            MAX-ACCESS read-write
            STATUS current
            DESCRIPTION
                "PoE transition (Off-->On)

                Value : 1 -> enable, 2 -> disable"
            ::= { relayAction 8 }

        relayActionDi1On2Off OBJECT-TYPE
            SYNTAX INTEGER { enable(1), disable(2) }
            MAX-ACCESS read-write
            STATUS current
            DESCRIPTION
                "DI 1 transition (On-->Off)

                Value : 1 -> enable, 2 -> disable"
            ::= { relayAction 9 }

        relayActionDi1Off2On OBJECT-TYPE
            SYNTAX INTEGER { enable(1), disable(2) }
            MAX-ACCESS read-write
            STATUS current
            DESCRIPTION
                "DI 1 transition (Off-->On)

                Value : 1 -> enable, 2 -> disable"
            ::= { relayAction 10 }

        relayActionDi2On2Off OBJECT-TYPE
            SYNTAX INTEGER { enable(1), disable(2) }
            MAX-ACCESS read-write
            STATUS current
            DESCRIPTION
                "DI 2 transition (On-->Off)

                Value : 1 -> enable, 2 -> disable"
            ::= { relayAction 11 }

        relayActionDi2Off2On OBJECT-TYPE
            SYNTAX INTEGER { enable(1), disable(2) }
            MAX-ACCESS read-write
            STATUS current
            DESCRIPTION
                "DI 2 transition (Off-->On)

                Value : 1 -> enable, 2 -> disable"
            ::= { relayAction 12 }

        relayActionConfigChange OBJECT-TYPE
            SYNTAX INTEGER { enable(1), disable(2) }
            MAX-ACCESS read-write
            STATUS current
            DESCRIPTION
                "Configuration changed

                Value : 1 -> enable, 2 -> disable"
            ::= { relayAction 13 }

        relayActionConsoleAuthFail OBJECT-TYPE
            SYNTAX INTEGER { enable(1), disable(2) }
            MAX-ACCESS read-write
            STATUS current
            DESCRIPTION
                "Console authentication failure

                Value : 1 -> enable, 2 -> disable"
            ::= { relayAction 14 }

        relayActionLanLinkOn OBJECT-TYPE
            SYNTAX INTEGER { enable(1), disable(2) }
            MAX-ACCESS read-write
            STATUS current
            DESCRIPTION
                "LAN link on

                Value : 1 -> enable, 2 -> disable"
            ::= { relayAction 18 }

        relayActionLanLinkOff OBJECT-TYPE
            SYNTAX INTEGER { enable(1), disable(2) }
            MAX-ACCESS read-write
            STATUS current
            DESCRIPTION
                "LAN link off

                Value : 1 -> enable, 2 -> disable"
            ::= { relayAction 19 }

        relayActionWlan1Connect OBJECT-TYPE
            SYNTAX INTEGER { enable(1), disable(2) }
            MAX-ACCESS read-write
            STATUS current
            DESCRIPTION
                "Port Connect

                Value : 1 -> enable, 2 -> disable"
            ::= { relayAction 40 }

        relayActionWlan1Disconnect OBJECT-TYPE
            SYNTAX INTEGER { enable(1), disable(2) }
            MAX-ACCESS read-write
            STATUS current
            DESCRIPTION
                "Port DisConnect

                Value : 1 -> enable, 2 -> disable"
            ::= { relayAction 41 }

        relayActionWlan1-1Connect OBJECT-TYPE
            SYNTAX INTEGER { enable(1), disable(2) }
            MAX-ACCESS read-write
            STATUS current
            DESCRIPTION
                "Port Connect

                Value : 1 -> enable, 2 -> disable"
            ::= { relayAction 46 }

        relayActionWlan1-1Disconnect OBJECT-TYPE
            SYNTAX INTEGER { enable(1), disable(2) }
            MAX-ACCESS read-write
            STATUS current
            DESCRIPTION
                "Port DisConnect

                Value : 1 -> enable, 2 -> disable"
            ::= { relayAction 47 }

        relayActionWlan1-2Connect OBJECT-TYPE
            SYNTAX INTEGER { enable(1), disable(2) }
            MAX-ACCESS read-write
            STATUS current
            DESCRIPTION
                "Port Connect

                Value : 1 -> enable, 2 -> disable"
            ::= { relayAction 49 }

        relayActionWlan1-2Disconnect OBJECT-TYPE
            SYNTAX INTEGER { enable(1), disable(2) }
            MAX-ACCESS read-write
            STATUS current
            DESCRIPTION
                "Port DisConnect

                Value : 1 -> enable, 2 -> disable"
            ::= { relayAction 50 }

        relayActionWlan1-3Connect OBJECT-TYPE
            SYNTAX INTEGER { enable(1), disable(2) }
            MAX-ACCESS read-write
            STATUS current
            DESCRIPTION
                "Port Connect

                Value : 1 -> enable, 2 -> disable"
            ::= { relayAction 52 }

        relayActionWlan1-3Disconnect OBJECT-TYPE
            SYNTAX INTEGER { enable(1), disable(2) }
            MAX-ACCESS read-write
            STATUS current
            DESCRIPTION
                "Port DisConnect

                Value : 1 -> enable, 2 -> disable"
            ::= { relayAction 53 }

        relayActionWlan1-4Connect OBJECT-TYPE
            SYNTAX INTEGER { enable(1), disable(2) }
            MAX-ACCESS read-write
            STATUS current
            DESCRIPTION
                "Port Connect

                Value : 1 -> enable, 2 -> disable"
            ::= { relayAction 55 }

        relayActionWlan1-4Disconnect OBJECT-TYPE
            SYNTAX INTEGER { enable(1), disable(2) }
            MAX-ACCESS read-write
            STATUS current
            DESCRIPTION
                "Port DisConnect

                Value : 1 -> enable, 2 -> disable"
            ::= { relayAction 56 }

        relayActionWlan1-5Connect OBJECT-TYPE
            SYNTAX INTEGER { enable(1), disable(2) }
            MAX-ACCESS read-write
            STATUS current
            DESCRIPTION
                "Port Connect

                Value : 1 -> enable, 2 -> disable"
            ::= { relayAction 58 }

        relayActionWlan1-5Disconnect OBJECT-TYPE
            SYNTAX INTEGER { enable(1), disable(2) }
            MAX-ACCESS read-write
            STATUS current
            DESCRIPTION
                "Port DisConnect

                Value : 1 -> enable, 2 -> disable"
            ::= { relayAction 59 }

        relayActionWlan1-6Connect OBJECT-TYPE
            SYNTAX INTEGER { enable(1), disable(2) }
            MAX-ACCESS read-write
            STATUS current
            DESCRIPTION
                "Port Connect

                Value : 1 -> enable, 2 -> disable"
            ::= { relayAction 61 }

        relayActionWlan1-6Disconnect OBJECT-TYPE
            SYNTAX INTEGER { enable(1), disable(2) }
            MAX-ACCESS read-write
            STATUS current
            DESCRIPTION
                "Port DisConnect

                Value : 1 -> enable, 2 -> disable"
            ::= { relayAction 62 }

        relayActionWlan1-7Connect OBJECT-TYPE
            SYNTAX INTEGER { enable(1), disable(2) }
            MAX-ACCESS read-write
            STATUS current
            DESCRIPTION
                "Port Connect

                Value : 1 -> enable, 2 -> disable"
            ::= { relayAction 64 }

        relayActionWlan1-7Disconnect OBJECT-TYPE
            SYNTAX INTEGER { enable(1), disable(2) }
            MAX-ACCESS read-write
            STATUS current
            DESCRIPTION
                "Port DisConnect

                Value : 1 -> enable, 2 -> disable"
            ::= { relayAction 65 }

        relayActionWlan1-8Connect OBJECT-TYPE
            SYNTAX INTEGER { enable(1), disable(2) }
            MAX-ACCESS read-write
            STATUS current
            DESCRIPTION
                "Port Connect

                Value : 1 -> enable, 2 -> disable"
            ::= { relayAction 67 }

        relayActionWlan1-8Disconnect OBJECT-TYPE
            SYNTAX INTEGER { enable(1), disable(2) }
            MAX-ACCESS read-write
            STATUS current
            DESCRIPTION
                "Port DisConnect

                Value : 1 -> enable, 2 -> disable"
            ::= { relayAction 68 }

    trapAction OBJECT IDENTIFIER ::= { autoWarning 3 }

        trapActionColdStart OBJECT-TYPE
            SYNTAX INTEGER { enable(1), disable(2) }
            MAX-ACCESS read-write
            STATUS current
            DESCRIPTION
                "Cold start

                Value : 1 -> enable, 2 -> disable"
            ::= { trapAction 1 }

        trapActionWarmStart OBJECT-TYPE
            SYNTAX INTEGER { enable(1), disable(2) }
            MAX-ACCESS read-write
            STATUS current
            DESCRIPTION
                "Warm start

                Value : 1 -> enable, 2 -> disable"
            ::= { trapAction 2 }

        trapActionPower1Off OBJECT-TYPE
            SYNTAX INTEGER { enable(1), disable(2) }
            MAX-ACCESS read-write
            STATUS current
            DESCRIPTION
                "Power 1 transition (On-->Off)

                Value : 1 -> enable, 2 -> disable"
            ::= { trapAction 3 }

        trapActionPower1On OBJECT-TYPE
            SYNTAX INTEGER { enable(1), disable(2) }
            MAX-ACCESS read-write
            STATUS current
            DESCRIPTION
                "Power 1 transition (Off-->On)

                Value : 1 -> enable, 2 -> disable"
            ::= { trapAction 4 }

        trapActionPower2Off OBJECT-TYPE
            SYNTAX INTEGER { enable(1), disable(2) }
            MAX-ACCESS read-write
            STATUS current
            DESCRIPTION
                "Power 2 transition (On-->Off)

                Value : 1 -> enable, 2 -> disable"
            ::= { trapAction 5 }

        trapActionPower2On OBJECT-TYPE
            SYNTAX INTEGER { enable(1), disable(2) }
            MAX-ACCESS read-write
            STATUS current
            DESCRIPTION
                "Power 2 transition (Off-->On)

                Value : 1 -> enable, 2 -> disable"
            ::= { trapAction 6 }

        trapActionPoeOff OBJECT-TYPE
            SYNTAX INTEGER { enable(1), disable(2) }
            MAX-ACCESS read-write
            STATUS current
            DESCRIPTION
                "PoE transition (On-->Off)

                Value : 1 -> enable, 2 -> disable"
            ::= { trapAction 7 }

        trapActionPoeOn OBJECT-TYPE
            SYNTAX INTEGER { enable(1), disable(2) }
            MAX-ACCESS read-write
            STATUS current
            DESCRIPTION
                "PoE transition (Off-->On)

                Value : 1 -> enable, 2 -> disable"
            ::= { trapAction 8 }

        trapActionDi1On2Off OBJECT-TYPE
            SYNTAX INTEGER { enable(1), disable(2) }
            MAX-ACCESS read-write
            STATUS current
            DESCRIPTION
                "DI 1 transition (On-->Off)

                Value : 1 -> enable, 2 -> disable"
            ::= { trapAction 9 }

        trapActionDi1Off2On OBJECT-TYPE
            SYNTAX INTEGER { enable(1), disable(2) }
            MAX-ACCESS read-write
            STATUS current
            DESCRIPTION
                "DI 1 transition (Off-->On)

                Value : 1 -> enable, 2 -> disable"
            ::= { trapAction 10 }

        trapActionDi2On2Off OBJECT-TYPE
            SYNTAX INTEGER { enable(1), disable(2) }
            MAX-ACCESS read-write
            STATUS current
            DESCRIPTION
                "DI 2 transition (On-->Off)

                Value : 1 -> enable, 2 -> disable"
            ::= { trapAction 11 }

        trapActionDi2Off2On OBJECT-TYPE
            SYNTAX INTEGER { enable(1), disable(2) }
            MAX-ACCESS read-write
            STATUS current
            DESCRIPTION
                "DI 2 transition (Off-->On)

                Value : 1 -> enable, 2 -> disable"
            ::= { trapAction 12 }

        trapActionConfigChange OBJECT-TYPE
            SYNTAX INTEGER { enable(1), disable(2) }
            MAX-ACCESS read-write
            STATUS current
            DESCRIPTION
                "Configuration changed

                Value : 1 -> enable, 2 -> disable"
            ::= { trapAction 13 }

        trapActionConsoleAuthFail OBJECT-TYPE
            SYNTAX INTEGER { enable(1), disable(2) }
            MAX-ACCESS read-write
            STATUS current
            DESCRIPTION
                "Console authentication failure

                Value : 1 -> enable, 2 -> disable"
            ::= { trapAction 14 }

        trapActionLanLinkOn OBJECT-TYPE
            SYNTAX INTEGER { enable(1), disable(2) }
            MAX-ACCESS read-write
            STATUS current
            DESCRIPTION
                "LAN link on

                Value : 1 -> enable, 2 -> disable"
            ::= { trapAction 18 }

        trapActionLanLinkOff OBJECT-TYPE
            SYNTAX INTEGER { enable(1), disable(2) }
            MAX-ACCESS read-write
            STATUS current
            DESCRIPTION
                "LAN link off

                Value : 1 -> enable, 2 -> disable"
            ::= { trapAction 19 }

        trapActionWlan1Connect OBJECT-TYPE
            SYNTAX INTEGER { enable(1), disable(2) }
            MAX-ACCESS read-write
            STATUS current
            DESCRIPTION
                "Port Connect

                Value : 1 -> enable, 2 -> disable"
            ::= { trapAction 40 }

        trapActionWlan1Disconnect OBJECT-TYPE
            SYNTAX INTEGER { enable(1), disable(2) }
            MAX-ACCESS read-write
            STATUS current
            DESCRIPTION
                "Port DisConnect

                Value : 1 -> enable, 2 -> disable"
            ::= { trapAction 41 }

        trapActionWlan1-1Connect OBJECT-TYPE
            SYNTAX INTEGER { enable(1), disable(2) }
            MAX-ACCESS read-write
            STATUS current
            DESCRIPTION
                "Port Connect

                Value : 1 -> enable, 2 -> disable"
            ::= { trapAction 46 }

        trapActionWlan1-1Disconnect OBJECT-TYPE
            SYNTAX INTEGER { enable(1), disable(2) }
            MAX-ACCESS read-write
            STATUS current
            DESCRIPTION
                "Port DisConnect

                Value : 1 -> enable, 2 -> disable"
            ::= { trapAction 47 }

        trapActionWlan1-2Connect OBJECT-TYPE
            SYNTAX INTEGER { enable(1), disable(2) }
            MAX-ACCESS read-write
            STATUS current
            DESCRIPTION
                "Port Connect

                Value : 1 -> enable, 2 -> disable"
            ::= { trapAction 49 }

        trapActionWlan1-2Disconnect OBJECT-TYPE
            SYNTAX INTEGER { enable(1), disable(2) }
            MAX-ACCESS read-write
            STATUS current
            DESCRIPTION
                "Port DisConnect

                Value : 1 -> enable, 2 -> disable"
            ::= { trapAction 50 }

        trapActionWlan1-3Connect OBJECT-TYPE
            SYNTAX INTEGER { enable(1), disable(2) }
            MAX-ACCESS read-write
            STATUS current
            DESCRIPTION
                "Port Connect

                Value : 1 -> enable, 2 -> disable"
            ::= { trapAction 52 }

        trapActionWlan1-3Disconnect OBJECT-TYPE
            SYNTAX INTEGER { enable(1), disable(2) }
            MAX-ACCESS read-write
            STATUS current
            DESCRIPTION
                "Port DisConnect

                Value : 1 -> enable, 2 -> disable"
            ::= { trapAction 53 }

        trapActionWlan1-4Connect OBJECT-TYPE
            SYNTAX INTEGER { enable(1), disable(2) }
            MAX-ACCESS read-write
            STATUS current
            DESCRIPTION
                "Port Connect

                Value : 1 -> enable, 2 -> disable"
            ::= { trapAction 55 }

        trapActionWlan1-4Disconnect OBJECT-TYPE
            SYNTAX INTEGER { enable(1), disable(2) }
            MAX-ACCESS read-write
            STATUS current
            DESCRIPTION
                "Port DisConnect

                Value : 1 -> enable, 2 -> disable"
            ::= { trapAction 56 }

        trapActionWlan1-5Connect OBJECT-TYPE
            SYNTAX INTEGER { enable(1), disable(2) }
            MAX-ACCESS read-write
            STATUS current
            DESCRIPTION
                "Port Connect

                Value : 1 -> enable, 2 -> disable"
            ::= { trapAction 58 }

        trapActionWlan1-5Disconnect OBJECT-TYPE
            SYNTAX INTEGER { enable(1), disable(2) }
            MAX-ACCESS read-write
            STATUS current
            DESCRIPTION
                "Port DisConnect

                Value : 1 -> enable, 2 -> disable"
            ::= { trapAction 59 }

        trapActionWlan1-6Connect OBJECT-TYPE
            SYNTAX INTEGER { enable(1), disable(2) }
            MAX-ACCESS read-write
            STATUS current
            DESCRIPTION
                "Port Connect

                Value : 1 -> enable, 2 -> disable"
            ::= { trapAction 61 }

        trapActionWlan1-6Disconnect OBJECT-TYPE
            SYNTAX INTEGER { enable(1), disable(2) }
            MAX-ACCESS read-write
            STATUS current
            DESCRIPTION
                "Port DisConnect

                Value : 1 -> enable, 2 -> disable"
            ::= { trapAction 62 }

        trapActionWlan1-7Connect OBJECT-TYPE
            SYNTAX INTEGER { enable(1), disable(2) }
            MAX-ACCESS read-write
            STATUS current
            DESCRIPTION
                "Port Connect

                Value : 1 -> enable, 2 -> disable"
            ::= { trapAction 64 }

        trapActionWlan1-7Disconnect OBJECT-TYPE
            SYNTAX INTEGER { enable(1), disable(2) }
            MAX-ACCESS read-write
            STATUS current
            DESCRIPTION
                "Port DisConnect

                Value : 1 -> enable, 2 -> disable"
            ::= { trapAction 65 }

        trapActionWlan1-8Connect OBJECT-TYPE
            SYNTAX INTEGER { enable(1), disable(2) }
            MAX-ACCESS read-write
            STATUS current
            DESCRIPTION
                "Port Connect

                Value : 1 -> enable, 2 -> disable"
            ::= { trapAction 67 }

        trapActionWlan1-8Disconnect OBJECT-TYPE
            SYNTAX INTEGER { enable(1), disable(2) }
            MAX-ACCESS read-write
            STATUS current
            DESCRIPTION
                "Port DisConnect

                Value : 1 -> enable, 2 -> disable"
            ::= { trapAction 68 }

    systemLog OBJECT IDENTIFIER ::= { autoWarning 4 }

        systemLogSystemEnable OBJECT-TYPE
            SYNTAX INTEGER { enable(1), disable(2) }
            MAX-ACCESS read-write
            STATUS current
            DESCRIPTION
                "System-related events

                Value : 1 -> enable, 2 -> disable"
            ::= { systemLog 1 }

        systemLogNetworkEnable OBJECT-TYPE
            SYNTAX INTEGER { enable(1), disable(2) }
            MAX-ACCESS read-write
            STATUS current
            DESCRIPTION
                "Network-related events

                Value : 1 -> enable, 2 -> disable"
            ::= { systemLog 2 }

        systemLogConfigEnable OBJECT-TYPE
            SYNTAX INTEGER { enable(1), disable(2) }
            MAX-ACCESS read-write
            STATUS current
            DESCRIPTION
                "Configuration-related events

                Value : 1 -> enable, 2 -> disable"
            ::= { systemLog 3 }

        systemLogPowerEnable OBJECT-TYPE
            SYNTAX INTEGER { enable(1), disable(2) }
            MAX-ACCESS read-write
            STATUS current
            DESCRIPTION
                "Power events

                Value : 1 -> enable, 2 -> disable"
            ::= { systemLog 4 }

        systemLogDinEnable OBJECT-TYPE
            SYNTAX INTEGER { enable(1), disable(2) }
            MAX-ACCESS read-write
            STATUS current
            DESCRIPTION
                "DI events

                Value : 1 -> enable, 2 -> disable"
            ::= { systemLog 5 }

        systemLogRssiReport OBJECT-TYPE
            SYNTAX INTEGER { enable(1), disable(2) }
            MAX-ACCESS read-write
            STATUS current
            DESCRIPTION
                "RSSI report events

                Value : 1 -> enable, 2 -> disable"
            ::= { systemLog 7 }

    sysLog OBJECT IDENTIFIER ::= { autoWarning 5 }

        sysLogSystemEnable OBJECT-TYPE
            SYNTAX INTEGER { enable(1), disable(2) }
            MAX-ACCESS read-write
            STATUS current
            DESCRIPTION
                "System-related events

                Value : 1 -> enable, 2 -> disable"
            ::= { sysLog 1 }

        sysLogNetworkEnable OBJECT-TYPE
            SYNTAX INTEGER { enable(1), disable(2) }
            MAX-ACCESS read-write
            STATUS current
            DESCRIPTION
                "Network-related events

                Value : 1 -> enable, 2 -> disable"
            ::= { sysLog 2 }

        sysLogConfigEnable OBJECT-TYPE
            SYNTAX INTEGER { enable(1), disable(2) }
            MAX-ACCESS read-write
            STATUS current
            DESCRIPTION
                "Configuration-related events

                Value : 1 -> enable, 2 -> disable"
            ::= { sysLog 3 }

        sysLogPowerEnable OBJECT-TYPE
            SYNTAX INTEGER { enable(1), disable(2) }
            MAX-ACCESS read-write
            STATUS current
            DESCRIPTION
                "Power events

                Value : 1 -> enable, 2 -> disable"
            ::= { sysLog 4 }

        sysLogDinEnable OBJECT-TYPE
            SYNTAX INTEGER { enable(1), disable(2) }
            MAX-ACCESS read-write
            STATUS current
            DESCRIPTION
                "DI events

                Value : 1 -> enable, 2 -> disable"
            ::= { sysLog 5 }

        sysLogRssiReport OBJECT-TYPE
            SYNTAX INTEGER { enable(1), disable(2) }
            MAX-ACCESS read-write
            STATUS current
            DESCRIPTION
                "RSSI report events

                Value : 1 -> enable, 2 -> disable"
            ::= { sysLog 7 }

    snmp OBJECT IDENTIFIER ::= { autoWarning 6 }

        snmpEnable OBJECT-TYPE
            SYNTAX INTEGER { enable(1), disable(2) }
            MAX-ACCESS read-write
            STATUS current
            DESCRIPTION
                "SNMP agent

                Value : 1 -> enable, 2 -> disable"
            ::= { snmp 1 }

        snmpVersion OBJECT-TYPE
            SYNTAX INTEGER { v1-v2c-v3(1), v1-v2c(2), v3(3) }
            MAX-ACCESS read-write
            STATUS current
            DESCRIPTION
                "SNMP agent version

                Value : 1 -> v1-v2c-v3, 2 -> v1-v2c, 3 -> v3"
            ::= { snmp 2 }

        snmpRoCommunity OBJECT-TYPE
            SYNTAX DisplayString
            MAX-ACCESS read-write
            STATUS current
            DESCRIPTION
                "Read community

                "
            ::= { snmp 3 }

        snmpRwCommunity OBJECT-TYPE
            SYNTAX DisplayString
            MAX-ACCESS read-write
            STATUS current
            DESCRIPTION
                "Write commnuity

                "
            ::= { snmp 4 }

        snmpFirstTrapServer OBJECT-TYPE
            SYNTAX DisplayString
            MAX-ACCESS read-write
            STATUS current
            DESCRIPTION
                "1st trap server IP/name

                "
            ::= { snmp 5 }

        snmpFirstTrapVersion OBJECT-TYPE
            SYNTAX INTEGER { v1(1), v2(2) }
            MAX-ACCESS read-write
            STATUS current
            DESCRIPTION
                "1st trap version

                Value : 1 -> v1, 2 -> v2"
            ::= { snmp 6 }

        snmpFirstTrapCommunity OBJECT-TYPE
            SYNTAX DisplayString
            MAX-ACCESS read-write
            STATUS current
            DESCRIPTION
                "1st trap community

                "
            ::= { snmp 7 }

        snmpSecondTrapServer OBJECT-TYPE
            SYNTAX DisplayString
            MAX-ACCESS read-write
            STATUS current
            DESCRIPTION
                "2nd trap server IP/name

                "
            ::= { snmp 8 }

        snmpSecondTrapVersion OBJECT-TYPE
            SYNTAX INTEGER { v1(1), v2(2) }
            MAX-ACCESS read-write
            STATUS current
            DESCRIPTION
                "2nd trap version

                Value : 1 -> v1, 2 -> v2"
            ::= { snmp 9 }

        snmpSecondTrapCommunity OBJECT-TYPE
            SYNTAX DisplayString
            MAX-ACCESS read-write
            STATUS current
            DESCRIPTION
                "2nd trap community

                "
            ::= { snmp 10 }

        snmpAdminAuthType OBJECT-TYPE
            SYNTAX INTEGER { noAuth(1), md5(2), sha(3) }
            MAX-ACCESS read-write
            STATUS current
            DESCRIPTION
                "Admin authentication type

                Value : 1 -> noAuth, 2 -> md5, 3 -> sha"
            ::= { snmp 11 }

        snmpAdminAuthKey OBJECT-TYPE
            SYNTAX INTEGER { disable(1), des(2), aes(3) }
            MAX-ACCESS read-write
            STATUS current
            DESCRIPTION
                "Admin encryption method

                Value : 1 -> disable, 2 -> des, 3 -> aes"
            ::= { snmp 12 }

        snmpPrivMib OBJECT-TYPE
            SYNTAX DisplayString
            MAX-ACCESS read-only
            STATUS current
            DESCRIPTION
                "Device object ID

                "
            ::= { snmp 17 }

        snmpRmtMngtEnable OBJECT-TYPE
            SYNTAX INTEGER { enable(1), disable(2) }
            MAX-ACCESS read-write
            STATUS current
            DESCRIPTION
                "Remote management

                Value : 1 -> enable, 2 -> disable"
            ::= { snmp 18 }

        snmpUserAuthAccount OBJECT-TYPE
            SYNTAX INTEGER (0..7)
            MAX-ACCESS read-write
            STATUS current
            DESCRIPTION
                "Authentication username

                "
            ::= { snmp 19 }

        snmpThirdTrapServer OBJECT-TYPE
            SYNTAX DisplayString
            MAX-ACCESS read-write
            STATUS current
            DESCRIPTION
                "3rd trap server IP/name

                "
            ::= { snmp 20 }

        snmpThirdTrapVersion OBJECT-TYPE
            SYNTAX INTEGER { v1(1), v2(2) }
            MAX-ACCESS read-write
            STATUS current
            DESCRIPTION
                "3rd trap version

                Value : 1 -> v1, 2 -> v2"
            ::= { snmp 21 }

        snmpThirdTrapCommunity OBJECT-TYPE
            SYNTAX DisplayString
            MAX-ACCESS read-write
            STATUS current
            DESCRIPTION
                "3rd trap community

                "
            ::= { snmp 22 }

    emailSmtp OBJECT IDENTIFIER ::= { autoWarning 7 }

        emailSmtpServerTable OBJECT-TYPE
            SYNTAX SEQUENCE OF EmailSmtpServerEntry
            MAX-ACCESS not-accessible
            STATUS current
            DESCRIPTION
                "Table of emailSmtpServer"
            ::= { emailSmtp 1 }

        emailSmtpServerEntry OBJECT-TYPE
            SYNTAX EmailSmtpServerEntry
            MAX-ACCESS not-accessible
            STATUS current
            DESCRIPTION
                "Entry of emailSmtpServer"
            INDEX { emailSmtpServerIndex }
            ::= { emailSmtpServerTable 1 }

        EmailSmtpServerEntry ::=
            SEQUENCE {
                emailSmtpServerIndex
                    INTEGER,
                emailSmtpServerData
                    DisplayString
            }

        emailSmtpServerIndex OBJECT-TYPE
            SYNTAX INTEGER (1..3)
            MAX-ACCESS read-only
            STATUS current
            DESCRIPTION
                "Index of Server"
            ::= { emailSmtpServerEntry 1 }

        emailSmtpServerData OBJECT-TYPE
            SYNTAX DisplayString
            MAX-ACCESS read-write
            STATUS current
            DESCRIPTION
                "SMTP

                "
            ::= { emailSmtpServerEntry 2 }

        emailSmtpMailAddressTable OBJECT-TYPE
            SYNTAX SEQUENCE OF EmailSmtpMailAddressEntry
            MAX-ACCESS not-accessible
            STATUS current
            DESCRIPTION
                "Table of emailSmtpMailAddress"
            ::= { emailSmtp 2 }

        emailSmtpMailAddressEntry OBJECT-TYPE
            SYNTAX EmailSmtpMailAddressEntry
            MAX-ACCESS not-accessible
            STATUS current
            DESCRIPTION
                "Entry of emailSmtpMailAddress"
            INDEX { emailSmtpMailAddressIndex }
            ::= { emailSmtpMailAddressTable 1 }

        EmailSmtpMailAddressEntry ::=
            SEQUENCE {
                emailSmtpMailAddressIndex
                    INTEGER,
                emailSmtpMailAddressData
                    DisplayString
            }

        emailSmtpMailAddressIndex OBJECT-TYPE
            SYNTAX INTEGER (1..4)
            MAX-ACCESS read-only
            STATUS current
            DESCRIPTION
                "Index of MailAddress"
            ::= { emailSmtpMailAddressEntry 1 }

        emailSmtpMailAddressData OBJECT-TYPE
            SYNTAX DisplayString
            MAX-ACCESS read-write
            STATUS current
            DESCRIPTION
                "To e-mail address 1

                "
            ::= { emailSmtpMailAddressEntry 2 }

        emailSmtpUserName OBJECT-TYPE
            SYNTAX DisplayString
            MAX-ACCESS read-write
            STATUS current
            DESCRIPTION
                "User name

                "
            ::= { emailSmtp 3 }

        emailSmtpFrom OBJECT-TYPE
            SYNTAX DisplayString
            MAX-ACCESS read-write
            STATUS current
            DESCRIPTION
                "From e-mail address

                "
            ::= { emailSmtp 5 }

        sysLogServerTable OBJECT-TYPE
            SYNTAX SEQUENCE OF SysLogServerEntry
            MAX-ACCESS not-accessible
            STATUS current
            DESCRIPTION
                "Table of sysLogServer"
            ::= { autoWarning 8 }

        sysLogServerEntry OBJECT-TYPE
            SYNTAX SysLogServerEntry
            MAX-ACCESS not-accessible
            STATUS current
            DESCRIPTION
                "Entry of sysLogServer"
            INDEX { sysLogServerIndex }
            ::= { sysLogServerTable 1 }

        SysLogServerEntry ::=
            SEQUENCE {
                sysLogServerIndex
                    INTEGER,
                sysLogServerServer
                    DisplayString,
                sysLogServerPort
                    INTEGER
            }

        sysLogServerIndex OBJECT-TYPE
            SYNTAX INTEGER (1..3)
            MAX-ACCESS read-only
            STATUS current
            DESCRIPTION
                "Index of sysLogServer"
            ::= { sysLogServerEntry 1 }

        sysLogServerServer OBJECT-TYPE
            SYNTAX DisplayString
            MAX-ACCESS read-write
            STATUS current
            DESCRIPTION
                "Syslog server

                "
            ::= { sysLogServerEntry 2 }

        sysLogServerPort OBJECT-TYPE
            SYNTAX INTEGER (1..65535)
            MAX-ACCESS read-write
            STATUS current
            DESCRIPTION
                "Syslog port

                "
            ::= { sysLogServerEntry 3 }

    sysStatus OBJECT IDENTIFIER ::= { swMgmt 11 }

        powerInputTable OBJECT-TYPE
            SYNTAX SEQUENCE OF PowerInputEntry
            MAX-ACCESS not-accessible
            STATUS current
            DESCRIPTION
                "Table of powerInput"
            ::= { sysStatus 9 }

        powerInputEntry OBJECT-TYPE
            SYNTAX PowerInputEntry
            MAX-ACCESS not-accessible
            STATUS current
            DESCRIPTION
                "Entry of powerInput"
            INDEX { powerInputIndex }
            ::= { powerInputTable 1 }

        PowerInputEntry ::=
            SEQUENCE {
                powerInputIndex
                    INTEGER,
                powerInputStatus
                    INTEGER
            }

        powerInputIndex OBJECT-TYPE
            SYNTAX INTEGER
            MAX-ACCESS read-only
            STATUS current
            DESCRIPTION
                "The power input index of monitor function
                "
            ::= { powerInputEntry 1 }

        powerInputStatus OBJECT-TYPE
            SYNTAX INTEGER { off(0), on(1) }
            MAX-ACCESS read-only
            STATUS current
            DESCRIPTION
                "The power input status
                Value : 0 -> off, 1 -> on"
            ::= { powerInputEntry 2 }

        diTable OBJECT-TYPE
            SYNTAX SEQUENCE OF DiEntry
            MAX-ACCESS not-accessible
            STATUS current
            DESCRIPTION
                "Table of di"
            ::= { sysStatus 11 }

        diEntry OBJECT-TYPE
            SYNTAX DiEntry
            MAX-ACCESS not-accessible
            STATUS current
            DESCRIPTION
                "Entry of di"
            INDEX { diIndex }
            ::= { diTable 1 }

        DiEntry ::=
            SEQUENCE {
                diIndex
                    INTEGER,
                diInputStatus
                    INTEGER
            }

        diIndex OBJECT-TYPE
            SYNTAX INTEGER
            MAX-ACCESS read-only
            STATUS current
            DESCRIPTION
                "The DI index of monitor function
                "
            ::= { diEntry 1 }

        diInputStatus OBJECT-TYPE
            SYNTAX INTEGER { off(0), on(1) }
            MAX-ACCESS read-only
            STATUS current
            DESCRIPTION
                "The DI input status
                Value : 0 -> off, 1 -> on"
            ::= { diEntry 2 }

        wlanClientListTable OBJECT-TYPE
            SYNTAX SEQUENCE OF WlanClientListEntry
            MAX-ACCESS not-accessible
            STATUS current
            DESCRIPTION
                "Table of wlanClientList"
            ::= { sysStatus 13 }

        wlanClientListEntry OBJECT-TYPE
            SYNTAX WlanClientListEntry
            MAX-ACCESS not-accessible
            STATUS current
            DESCRIPTION
                "Entry of wlanClientList"
            INDEX { wlanDevIndex, wlanSsidIndex, wlanClientIndex }
            ::= { wlanClientListTable 1 }

        WlanClientListEntry ::=
            SEQUENCE {
                wlanDevIndex
                    INTEGER,
                wlanSsidIndex
                    INTEGER,
                wlanClientIndex
                    INTEGER,
                wlanClientMAC
                    DisplayString,
                wlanClientIP
                    DisplayString,
                wlanClientSignalStrength
                    INTEGER,
                wlanClientSNR
                    INTEGER,
                wlanClientConnectionTime
                    INTEGER
            }

        wlanDevIndex OBJECT-TYPE
            SYNTAX INTEGER
            MAX-ACCESS read-only
            STATUS current
            DESCRIPTION
                "Wlan device client connects to
                "
            ::= { wlanClientListEntry 1 }

        wlanSsidIndex OBJECT-TYPE
            SYNTAX INTEGER
            MAX-ACCESS read-only
            STATUS current
            DESCRIPTION
                "SSID index client connects to
                "
            ::= { wlanClientListEntry 2 }

        wlanClientIndex OBJECT-TYPE
            SYNTAX INTEGER
            MAX-ACCESS read-only
            STATUS current
            DESCRIPTION
                "Index of client
                "
            ::= { wlanClientListEntry 3 }

        wlanClientMAC OBJECT-TYPE
            SYNTAX DisplayString
            MAX-ACCESS read-only
            STATUS current
            DESCRIPTION
                "MAC of client
                "
            ::= { wlanClientListEntry 4 }

        wlanClientIP OBJECT-TYPE
            SYNTAX DisplayString
            MAX-ACCESS read-only
            STATUS current
            DESCRIPTION
                "IP of client
                "
            ::= { wlanClientListEntry 5 }

        wlanClientSignalStrength OBJECT-TYPE
            SYNTAX INTEGER
            MAX-ACCESS read-only
            STATUS current
            DESCRIPTION
                "Current Signal Strength(dBm)
                "
            ::= { wlanClientListEntry 6 }

        wlanClientSNR OBJECT-TYPE
            SYNTAX INTEGER
            MAX-ACCESS read-only
            STATUS current
            DESCRIPTION
                "Current RSSI of Client
                "
            ::= { wlanClientListEntry 7 }

        wlanClientConnectionTime OBJECT-TYPE
            SYNTAX INTEGER
            MAX-ACCESS read-only
            STATUS current
            DESCRIPTION
                "Connection Time (Sec) of Client
                "
            ::= { wlanClientListEntry 8 }

        dhcpClientListTable OBJECT-TYPE
            SYNTAX SEQUENCE OF DhcpClientListEntry
            MAX-ACCESS not-accessible
            STATUS current
            DESCRIPTION
                "Table of dhcpClientList"
            ::= { sysStatus 15 }

        dhcpClientListEntry OBJECT-TYPE
            SYNTAX DhcpClientListEntry
            MAX-ACCESS not-accessible
            STATUS current
            DESCRIPTION
                "Entry of dhcpClientList"
            INDEX { dhcpClientIndex }
            ::= { dhcpClientListTable 1 }

        DhcpClientListEntry ::=
            SEQUENCE {
                dhcpClientIndex
                    INTEGER,
                dhcpClientIP
                    DisplayString,
                dhcpClientMAC
                    DisplayString
            }

        dhcpClientIndex OBJECT-TYPE
            SYNTAX INTEGER
            MAX-ACCESS read-only
            STATUS current
            DESCRIPTION
                "Index of DHCP client
                "
            ::= { dhcpClientListEntry 1 }

        dhcpClientIP OBJECT-TYPE
            SYNTAX DisplayString
            MAX-ACCESS read-only
            STATUS current
            DESCRIPTION
                "IP of client
                "
            ::= { dhcpClientListEntry 2 }

        dhcpClientMAC OBJECT-TYPE
            SYNTAX DisplayString
            MAX-ACCESS read-only
            STATUS current
            DESCRIPTION
                "MAC of client
                "
            ::= { dhcpClientListEntry 3 }

        wirelessStatusTable OBJECT-TYPE
            SYNTAX SEQUENCE OF WirelessStatusEntry
            MAX-ACCESS not-accessible
            STATUS current
            DESCRIPTION
                "Table of wirelessStatus"
            ::= { sysStatus 17 }

        wirelessStatusEntry OBJECT-TYPE
            SYNTAX WirelessStatusEntry
            MAX-ACCESS not-accessible
            STATUS current
            DESCRIPTION
                "Entry of wirelessStatus"
            INDEX { wlanIndex, wlanVapIndex }
            ::= { wirelessStatusTable 1 }

        WirelessStatusEntry ::=
            SEQUENCE {
                wlanIndex
                    INTEGER,
                wlanChannel
                    INTEGER,
                wlanBSSID
                    DisplayString,
                wlanSingal
                    DisplayString,
                wlanTxRate
                    INTEGER,
                wlanSSID
                    DisplayString,
                wlanVapIndex
                    INTEGER,
                wlanAPip
                    DisplayString,
                wlanSNR
                    DisplayString,
                wlanNoiseLevel
                    DisplayString,
                wlanSNR-A
                    DisplayString,
                wlanSNR-B
                    DisplayString,
                wlanChannelWidth
                    DisplayString,
                wlanConnectionTime
                    INTEGER,
                wlanOperationMode
                    INTEGER
            }

        wlanIndex OBJECT-TYPE
            SYNTAX INTEGER
            MAX-ACCESS read-only
            STATUS current
            DESCRIPTION
                "Index of WLAN
                "
            ::= { wirelessStatusEntry 1 }

        wlanChannel OBJECT-TYPE
            SYNTAX INTEGER
            MAX-ACCESS read-only
            STATUS current
            DESCRIPTION
                "Current Channel of Virtual Device
                "
            ::= { wirelessStatusEntry 2 }

        wlanBSSID OBJECT-TYPE
            SYNTAX DisplayString
            MAX-ACCESS read-only
            STATUS current
            DESCRIPTION
                "Current BSSID of Virtual Device
                "
            ::= { wirelessStatusEntry 3 }

        wlanSingal OBJECT-TYPE
            SYNTAX DisplayString
            MAX-ACCESS read-only
            STATUS current
            DESCRIPTION
                "Current Signal of Virtual Device ( Client/Slave Only )
                "
            ::= { wirelessStatusEntry 4 }

        wlanTxRate OBJECT-TYPE
            SYNTAX INTEGER
            MAX-ACCESS read-only
            STATUS current
            DESCRIPTION
                "Current TX rate of Virtual Device in Mbps
                "
            ::= { wirelessStatusEntry 5 }

        wlanSSID OBJECT-TYPE
            SYNTAX DisplayString
            MAX-ACCESS read-only
            STATUS current
            DESCRIPTION
                "SSID of Virtual Device
                "
            ::= { wirelessStatusEntry 6 }

        wlanVapIndex OBJECT-TYPE
            SYNTAX INTEGER
            MAX-ACCESS read-only
            STATUS current
            DESCRIPTION
                "Index of corresponding Virtual Device
                "
            ::= { wirelessStatusEntry 7 }

        wlanAPip OBJECT-TYPE
            SYNTAX DisplayString
            MAX-ACCESS read-only
            STATUS current
            DESCRIPTION
                "Associate AP IP ( Client/Slave Only )
                "
            ::= { wirelessStatusEntry 10 }

        wlanSNR OBJECT-TYPE
            SYNTAX DisplayString
            MAX-ACCESS read-only
            STATUS current
            DESCRIPTION
                "Associate AP SNR ( Client/Slave Only )
                "
            ::= { wirelessStatusEntry 11 }

        wlanNoiseLevel OBJECT-TYPE
            SYNTAX DisplayString
            MAX-ACCESS read-only
            STATUS current
            DESCRIPTION
                "Noise level in dBm ( Client/Slave Only )
                "
            ::= { wirelessStatusEntry 12 }

        wlanSNR-A OBJECT-TYPE
            SYNTAX DisplayString
            MAX-ACCESS read-only
            STATUS current
            DESCRIPTION
                "SNR on RF-A ( Client/Slave Only )
                "
            ::= { wirelessStatusEntry 13 }

        wlanSNR-B OBJECT-TYPE
            SYNTAX DisplayString
            MAX-ACCESS read-only
            STATUS current
            DESCRIPTION
                "SNR on RF-B ( Client/Slave Only )
                "
            ::= { wirelessStatusEntry 14 }

        wlanChannelWidth OBJECT-TYPE
            SYNTAX DisplayString
            MAX-ACCESS read-only
            STATUS current
            DESCRIPTION
                "Channel Width ( Client/Slave Only )
                "
            ::= { wirelessStatusEntry 15 }

        wlanConnectionTime OBJECT-TYPE
            SYNTAX INTEGER
            MAX-ACCESS read-only
            STATUS current
            DESCRIPTION
                "Connection Time (Client/Slave Only)
                "
            ::= { wirelessStatusEntry 16 }

        wlanOperationMode OBJECT-TYPE
            SYNTAX INTEGER { client(1), ap(2), sniffer(3), master(4), slave(5), clientRouter(6) }
            MAX-ACCESS read-only
            STATUS current
            DESCRIPTION
                "WLAN Operation Mode
                Value : 1 -> client, 2 -> ap, 3 -> sniffer, 4 -> master, 5 -> slave, 6 -> clientRouter"
            ::= { wirelessStatusEntry 17 }

        relayStatusAckTable OBJECT-TYPE
            SYNTAX SEQUENCE OF RelayStatusAckEntry
            MAX-ACCESS not-accessible
            STATUS current
            DESCRIPTION
                "Table of relayStatusAck"
            ::= { sysStatus 19 }

        relayStatusAckEntry OBJECT-TYPE
            SYNTAX RelayStatusAckEntry
            MAX-ACCESS not-accessible
            STATUS current
            DESCRIPTION
                "Entry of relayStatusAck"
            INDEX { relayIndex }
            ::= { relayStatusAckTable 1 }

        RelayStatusAckEntry ::=
            SEQUENCE {
                relayIndex
                    INTEGER,
                relayType
                    DisplayString,
                relayStatus
                    INTEGER,
                relayAck
                    INTEGER
            }

        relayIndex OBJECT-TYPE
            SYNTAX INTEGER
            MAX-ACCESS read-only
            STATUS current
            DESCRIPTION
                "Index of relay type
                "
            ::= { relayStatusAckEntry 1 }

        relayType OBJECT-TYPE
            SYNTAX DisplayString
            MAX-ACCESS read-only
            STATUS current
            DESCRIPTION
                "Type of relay status
                "
            ::= { relayStatusAckEntry 2 }

        relayStatus OBJECT-TYPE
            SYNTAX INTEGER { none(1), alarm(2), alarmAck(3) }
            MAX-ACCESS read-only
            STATUS current
            DESCRIPTION
                "Current status relay
                Value : 1 -> none, 2 -> alarm, 3 -> alarmAck"
            ::= { relayStatusAckEntry 3 }

        relayAck OBJECT-TYPE
            SYNTAX INTEGER { ack(1), none(2) }
            MAX-ACCESS read-write
            STATUS current
            DESCRIPTION
                "Relay ack status, Set 1 to ack
                Value : 1 -> ack, 2 -> none"
            ::= { relayStatusAckEntry 4 }

        bridgeStatusTable OBJECT-TYPE
            SYNTAX SEQUENCE OF BridgeStatusEntry
            MAX-ACCESS not-accessible
            STATUS current
            DESCRIPTION
                "Table of bridgeStatus"
            ::= { sysStatus 20 }

        bridgeStatusEntry OBJECT-TYPE
            SYNTAX BridgeStatusEntry
            MAX-ACCESS not-accessible
            STATUS current
            DESCRIPTION
                "Entry of bridgeStatus"
            INDEX { entryIndex }
            ::= { bridgeStatusTable 1 }

        BridgeStatusEntry ::=
            SEQUENCE {
                entryIndex
                    INTEGER,
                interface
                    DisplayString,
                macAddr
                    DisplayString
            }

        entryIndex OBJECT-TYPE
            SYNTAX INTEGER
            MAX-ACCESS read-only
            STATUS current
            DESCRIPTION
                "Index of bridge status table
                "
            ::= { bridgeStatusEntry 1 }

        interface OBJECT-TYPE
            SYNTAX DisplayString
            MAX-ACCESS read-only
            STATUS current
            DESCRIPTION
                "Interface of bridge entry
                "
            ::= { bridgeStatusEntry 2 }

        macAddr OBJECT-TYPE
            SYNTAX DisplayString
            MAX-ACCESS read-only
            STATUS current
            DESCRIPTION
                "MAC address of bridge entry
                "
            ::= { bridgeStatusEntry 3 }

    systemStatus OBJECT IDENTIFIER ::= { sysStatus 25 }

        cpuUsage OBJECT-TYPE
            SYNTAX INTEGER
            MAX-ACCESS read-only
            STATUS current
            DESCRIPTION
                "Get system cpu usage status
                "
            ::= { systemStatus 1 }

        memTotalKB OBJECT-TYPE
            SYNTAX INTEGER
            MAX-ACCESS read-only
            STATUS current
            DESCRIPTION
                "Get system total memory status
                "
            ::= { systemStatus 2 }

        memUsedKB OBJECT-TYPE
            SYNTAX INTEGER
            MAX-ACCESS read-only
            STATUS current
            DESCRIPTION
                "Get system used memory status
                "
            ::= { systemStatus 3 }

        memFreeKB OBJECT-TYPE
            SYNTAX INTEGER
            MAX-ACCESS read-only
            STATUS current
            DESCRIPTION
                "Get system free memory status
                "
            ::= { systemStatus 4 }

    maintenance OBJECT IDENTIFIER ::= { swMgmt 13 }

    misc OBJECT IDENTIFIER ::= { maintenance 1 }

        miscTelnetEnable OBJECT-TYPE
            SYNTAX INTEGER { enable(1), disable(2) }
            MAX-ACCESS read-write
            STATUS current
            DESCRIPTION
                "Telnet console

                Value : 1 -> enable, 2 -> disable"
            ::= { misc 1 }

        miscWebEnable OBJECT-TYPE
            SYNTAX INTEGER { enable(1), disable(2) }
            MAX-ACCESS read-write
            STATUS current
            DESCRIPTION
                "HTTP console

                Value : 1 -> enable, 2 -> disable"
            ::= { misc 2 }

        miscSshEnable OBJECT-TYPE
            SYNTAX INTEGER { enable(1), disable(2) }
            MAX-ACCESS read-write
            STATUS current
            DESCRIPTION
                "SSH console

                Value : 1 -> enable, 2 -> disable"
            ::= { misc 3 }

        miscHttpsEnable OBJECT-TYPE
            SYNTAX INTEGER { enable(1), disable(2) }
            MAX-ACCESS read-write
            STATUS current
            DESCRIPTION
                "HTTPS console

                Value : 1 -> enable, 2 -> disable"
            ::= { misc 4 }

        miscWlanEnable OBJECT-TYPE
            SYNTAX INTEGER { enable(1), disable(2) }
            MAX-ACCESS read-write
            STATUS current
            DESCRIPTION
                "Wireless

                Value : 1 -> enable, 2 -> disable"
            ::= { misc 7 }

        miscResetButtonEnable OBJECT-TYPE
            SYNTAX INTEGER { enable(1), disable(2) }
            MAX-ACCESS read-write
            STATUS current
            DESCRIPTION
                "Disable will make the reset button become invalid 60 seconds after boot up finishes

                Value : 1 -> enable, 2 -> disable"
            ::= { misc 8 }

        miscAutoLogoutTimeout OBJECT-TYPE
            SYNTAX INTEGER (1..60)
            MAX-ACCESS read-write
            STATUS current
            DESCRIPTION
                "Auto logout period

                "
            ::= { misc 11 }

        miscMoxaServiceEnable OBJECT-TYPE
            SYNTAX INTEGER { enable(1), disable(2) }
            MAX-ACCESS read-write
            STATUS current
            DESCRIPTION
                "Moxa service

                Value : 1 -> enable, 2 -> disable"
            ::= { misc 12 }

        miscLanEnable OBJECT-TYPE
            SYNTAX INTEGER { enable(1), disable(2) }
            MAX-ACCESS read-write
            STATUS current
            DESCRIPTION
                "LAN

                Value : 1 -> enable, 2 -> disable"
            ::= { misc 15 }

        miscAllowSpecialCharacters OBJECT-TYPE
            SYNTAX INTEGER { enable(1), disable(2) }
            MAX-ACCESS read-write
            STATUS current
            DESCRIPTION
                "Allow special characters

                Value : 1 -> enable, 2 -> disable"
            ::= { misc 22 }

    saveAndReboot OBJECT IDENTIFIER ::= { maintenance 3 }

        configChangeStatus OBJECT-TYPE
            SYNTAX INTEGER { unchanged(0), changeSavedRequireReboot(1), changedNotSaved(2) }
            MAX-ACCESS read-only
            STATUS current
            DESCRIPTION
                "Configuration has changed or not
                Value : 0 -> unchanged, 1 -> changeSavedRequireReboot, 2 -> changedNotSaved"
            ::= { saveAndReboot 1 }

        saveConfig OBJECT-TYPE
            SYNTAX INTEGER { savedConfig(1) }
            MAX-ACCESS read-write
            STATUS current
            DESCRIPTION
                "Set 1 to save configuration
Get operation will always get 0
When getting fail response on saveConfig, try save config on web page and you will get detail information.
                Value : 1 -> savedConfig"
            ::= { saveAndReboot 2 }

        reboot OBJECT-TYPE
            SYNTAX INTEGER { reboot(1) }
            MAX-ACCESS read-write
            STATUS current
            DESCRIPTION
                "Set 1 to reboot
Get operation will always get 0
                Value : 1 -> reboot"
            ::= { saveAndReboot 3 }

    accountMgmt OBJECT IDENTIFIER ::= { maintenance 6 }

        accountMgmtPasswdStrengthCheck OBJECT-TYPE
            SYNTAX INTEGER { enable(1), disable(2) }
            MAX-ACCESS read-write
            STATUS current
            DESCRIPTION
                "Password strength check

                Value : 1 -> enable, 2 -> disable"
            ::= { accountMgmt 1 }

        accountMgmtPasswdLength OBJECT-TYPE
            SYNTAX INTEGER (4..16)
            MAX-ACCESS read-write
            STATUS current
            DESCRIPTION
                "Minimum password length

                "
            ::= { accountMgmt 2 }

        accountMgmtPasswdExpiredTime OBJECT-TYPE
            SYNTAX INTEGER (0..365)
            MAX-ACCESS read-write
            STATUS current
            DESCRIPTION
                "Password validity

                "
            ::= { accountMgmt 3 }

        accountMgmtRetry OBJECT-TYPE
            SYNTAX INTEGER (0..10)
            MAX-ACCESS read-write
            STATUS current
            DESCRIPTION
                "Password retry count

                "
            ::= { accountMgmt 4 }

        accountMgmtLockTime OBJECT-TYPE
            SYNTAX INTEGER (1..3600)
            MAX-ACCESS read-write
            STATUS current
            DESCRIPTION
                "Lockout time

                "
            ::= { accountMgmt 5 }

        accountTable OBJECT-TYPE
            SYNTAX SEQUENCE OF AccountEntry
            MAX-ACCESS not-accessible
            STATUS current
            DESCRIPTION
                "Table of account"
            ::= { maintenance 7 }

        accountEntry OBJECT-TYPE
            SYNTAX AccountEntry
            MAX-ACCESS not-accessible
            STATUS current
            DESCRIPTION
                "Entry of account"
            INDEX { accountIndex }
            ::= { accountTable 1 }

        AccountEntry ::=
            SEQUENCE {
                accountIndex
                    INTEGER,
                accountActive
                    INTEGER,
                accountUsername
                    DisplayString,
                accountGroup
                    INTEGER,
                accountAccessHttp
                    INTEGER,
                accountAccessConsole
                    INTEGER,
                accountAccessMoxaService
                    INTEGER,
                accountAccessDiag
                    INTEGER
            }

        accountIndex OBJECT-TYPE
            SYNTAX INTEGER (1..8)
            MAX-ACCESS read-only
            STATUS current
            DESCRIPTION
                "Index of account"
            ::= { accountEntry 1 }

        accountActive OBJECT-TYPE
            SYNTAX INTEGER { enable(1), disable(2) }
            MAX-ACCESS read-write
            STATUS current
            DESCRIPTION
                "Active

                Value : 1 -> enable, 2 -> disable"
            ::= { accountEntry 2 }

        accountUsername OBJECT-TYPE
            SYNTAX DisplayString
            MAX-ACCESS read-write
            STATUS current
            DESCRIPTION
                "Account name

                "
            ::= { accountEntry 3 }

        accountGroup OBJECT-TYPE
            SYNTAX INTEGER { admin(1), user(2) }
            MAX-ACCESS read-write
            STATUS current
            DESCRIPTION
                "User level

                Value : 1 -> admin, 2 -> user"
            ::= { accountEntry 5 }

        accountAccessHttp OBJECT-TYPE
            SYNTAX INTEGER { enable(1), disable(2) }
            MAX-ACCESS read-write
            STATUS current
            DESCRIPTION
                "HTTP/HTTPS

                Value : 1 -> enable, 2 -> disable"
            ::= { accountEntry 7 }

        accountAccessConsole OBJECT-TYPE
            SYNTAX INTEGER { enable(1), disable(2) }
            MAX-ACCESS read-write
            STATUS current
            DESCRIPTION
                "Telnet/SSH/Console

                Value : 1 -> enable, 2 -> disable"
            ::= { accountEntry 8 }

        accountAccessMoxaService OBJECT-TYPE
            SYNTAX INTEGER { enable(1), disable(2) }
            MAX-ACCESS read-write
            STATUS current
            DESCRIPTION
                "Moxa Service

                Value : 1 -> enable, 2 -> disable"
            ::= { accountEntry 9 }

        accountAccessDiag OBJECT-TYPE
            SYNTAX INTEGER { enable(1), disable(2) }
            MAX-ACCESS read-write
            STATUS current
            DESCRIPTION
                "Diagnostic

                Value : 1 -> enable, 2 -> disable"
            ::= { accountEntry 10 }

    configEncrypt OBJECT IDENTIFIER ::= { maintenance 8 }

        configEncryptEnable OBJECT-TYPE
            SYNTAX INTEGER { enable(1), disable(2) }
            MAX-ACCESS read-write
            STATUS current
            DESCRIPTION
                "Encryption of import/export configuration

                Value : 1 -> enable, 2 -> disable"
            ::= { configEncrypt 1 }

        configEncryptPassword OBJECT-TYPE
            SYNTAX DisplayString
            MAX-ACCESS read-write
            STATUS current
            DESCRIPTION
                "Password

                "
            ::= { configEncrypt 2 }

    consoles OBJECT IDENTIFIER ::= { maintenance 9 }

        consolesEthTelnetEnable OBJECT-TYPE
            SYNTAX INTEGER { enable(1), disable(2) }
            MAX-ACCESS read-write
            STATUS current
            DESCRIPTION
                "Telnet console

                Value : 1 -> enable, 2 -> disable"
            ::= { consoles 11 }

        consolesEthWebEnable OBJECT-TYPE
            SYNTAX INTEGER { enable(1), disable(2) }
            MAX-ACCESS read-write
            STATUS current
            DESCRIPTION
                "HTTP console

                Value : 1 -> enable, 2 -> disable"
            ::= { consoles 12 }

        consolesEthSshEnable OBJECT-TYPE
            SYNTAX INTEGER { enable(1), disable(2) }
            MAX-ACCESS read-write
            STATUS current
            DESCRIPTION
                "SSH console

                Value : 1 -> enable, 2 -> disable"
            ::= { consoles 13 }

        consolesEthHttpsEnable OBJECT-TYPE
            SYNTAX INTEGER { enable(1), disable(2) }
            MAX-ACCESS read-write
            STATUS current
            DESCRIPTION
                "HTTPS console

                Value : 1 -> enable, 2 -> disable"
            ::= { consoles 14 }

        consolesEthSnmpEnable OBJECT-TYPE
            SYNTAX INTEGER { enable(1), disable(2) }
            MAX-ACCESS read-write
            STATUS current
            DESCRIPTION
                "SNMP console

                Value : 1 -> enable, 2 -> disable"
            ::= { consoles 15 }

        consolesEthMoxaServiceEnable OBJECT-TYPE
            SYNTAX INTEGER { enable(1), disable(2) }
            MAX-ACCESS read-write
            STATUS current
            DESCRIPTION
                "Moxa service

                Value : 1 -> enable, 2 -> disable"
            ::= { consoles 16 }

        consolesWlanTelnetEnableTable OBJECT-TYPE
            SYNTAX SEQUENCE OF ConsolesWlanTelnetEnableEntry
            MAX-ACCESS not-accessible
            STATUS current
            DESCRIPTION
                "Table of consolesWlanTelnetEnable"
            ::= { consoles 31 }

        consolesWlanTelnetEnableEntry OBJECT-TYPE
            SYNTAX ConsolesWlanTelnetEnableEntry
            MAX-ACCESS not-accessible
            STATUS current
            DESCRIPTION
                "Entry of consolesWlanTelnetEnable"
            INDEX { consolesWlanTelnetEnableIndex }
            ::= { consolesWlanTelnetEnableTable 1 }

        ConsolesWlanTelnetEnableEntry ::=
            SEQUENCE {
                consolesWlanTelnetEnableIndex
                    INTEGER,
                consolesWlanTelnetEnableData
                    INTEGER { enable(1), disable(2) }
            }

        consolesWlanTelnetEnableIndex OBJECT-TYPE
            SYNTAX INTEGER (1..9)
            MAX-ACCESS read-only
            STATUS current
            DESCRIPTION
                "Index of WlanTelnetEnable"
            ::= { consolesWlanTelnetEnableEntry 1 }

        consolesWlanTelnetEnableData OBJECT-TYPE
            SYNTAX INTEGER { enable(1), disable(2) }
            MAX-ACCESS read-write
            STATUS current
            DESCRIPTION
                "Telnet console

                Value : 1 -> enable, 2 -> disable"
            ::= { consolesWlanTelnetEnableEntry 2 }

        consolesWlanWebEnableTable OBJECT-TYPE
            SYNTAX SEQUENCE OF ConsolesWlanWebEnableEntry
            MAX-ACCESS not-accessible
            STATUS current
            DESCRIPTION
                "Table of consolesWlanWebEnable"
            ::= { consoles 32 }

        consolesWlanWebEnableEntry OBJECT-TYPE
            SYNTAX ConsolesWlanWebEnableEntry
            MAX-ACCESS not-accessible
            STATUS current
            DESCRIPTION
                "Entry of consolesWlanWebEnable"
            INDEX { consolesWlanWebEnableIndex }
            ::= { consolesWlanWebEnableTable 1 }

        ConsolesWlanWebEnableEntry ::=
            SEQUENCE {
                consolesWlanWebEnableIndex
                    INTEGER,
                consolesWlanWebEnableData
                    INTEGER { enable(1), disable(2) }
            }

        consolesWlanWebEnableIndex OBJECT-TYPE
            SYNTAX INTEGER (1..9)
            MAX-ACCESS read-only
            STATUS current
            DESCRIPTION
                "Index of WlanWebEnable"
            ::= { consolesWlanWebEnableEntry 1 }

        consolesWlanWebEnableData OBJECT-TYPE
            SYNTAX INTEGER { enable(1), disable(2) }
            MAX-ACCESS read-write
            STATUS current
            DESCRIPTION
                "HTTP console

                Value : 1 -> enable, 2 -> disable"
            ::= { consolesWlanWebEnableEntry 2 }

        consolesWlanSshEnableTable OBJECT-TYPE
            SYNTAX SEQUENCE OF ConsolesWlanSshEnableEntry
            MAX-ACCESS not-accessible
            STATUS current
            DESCRIPTION
                "Table of consolesWlanSshEnable"
            ::= { consoles 33 }

        consolesWlanSshEnableEntry OBJECT-TYPE
            SYNTAX ConsolesWlanSshEnableEntry
            MAX-ACCESS not-accessible
            STATUS current
            DESCRIPTION
                "Entry of consolesWlanSshEnable"
            INDEX { consolesWlanSshEnableIndex }
            ::= { consolesWlanSshEnableTable 1 }

        ConsolesWlanSshEnableEntry ::=
            SEQUENCE {
                consolesWlanSshEnableIndex
                    INTEGER,
                consolesWlanSshEnableData
                    INTEGER { enable(1), disable(2) }
            }

        consolesWlanSshEnableIndex OBJECT-TYPE
            SYNTAX INTEGER (1..9)
            MAX-ACCESS read-only
            STATUS current
            DESCRIPTION
                "Index of WlanSshEnable"
            ::= { consolesWlanSshEnableEntry 1 }

        consolesWlanSshEnableData OBJECT-TYPE
            SYNTAX INTEGER { enable(1), disable(2) }
            MAX-ACCESS read-write
            STATUS current
            DESCRIPTION
                "SSH console

                Value : 1 -> enable, 2 -> disable"
            ::= { consolesWlanSshEnableEntry 2 }

        consolesWlanHttpsEnableTable OBJECT-TYPE
            SYNTAX SEQUENCE OF ConsolesWlanHttpsEnableEntry
            MAX-ACCESS not-accessible
            STATUS current
            DESCRIPTION
                "Table of consolesWlanHttpsEnable"
            ::= { consoles 34 }

        consolesWlanHttpsEnableEntry OBJECT-TYPE
            SYNTAX ConsolesWlanHttpsEnableEntry
            MAX-ACCESS not-accessible
            STATUS current
            DESCRIPTION
                "Entry of consolesWlanHttpsEnable"
            INDEX { consolesWlanHttpsEnableIndex }
            ::= { consolesWlanHttpsEnableTable 1 }

        ConsolesWlanHttpsEnableEntry ::=
            SEQUENCE {
                consolesWlanHttpsEnableIndex
                    INTEGER,
                consolesWlanHttpsEnableData
                    INTEGER { enable(1), disable(2) }
            }

        consolesWlanHttpsEnableIndex OBJECT-TYPE
            SYNTAX INTEGER (1..9)
            MAX-ACCESS read-only
            STATUS current
            DESCRIPTION
                "Index of WlanHttpsEnable"
            ::= { consolesWlanHttpsEnableEntry 1 }

        consolesWlanHttpsEnableData OBJECT-TYPE
            SYNTAX INTEGER { enable(1), disable(2) }
            MAX-ACCESS read-write
            STATUS current
            DESCRIPTION
                "HTTPS console

                Value : 1 -> enable, 2 -> disable"
            ::= { consolesWlanHttpsEnableEntry 2 }

        consolesWlanSnmpEnableTable OBJECT-TYPE
            SYNTAX SEQUENCE OF ConsolesWlanSnmpEnableEntry
            MAX-ACCESS not-accessible
            STATUS current
            DESCRIPTION
                "Table of consolesWlanSnmpEnable"
            ::= { consoles 35 }

        consolesWlanSnmpEnableEntry OBJECT-TYPE
            SYNTAX ConsolesWlanSnmpEnableEntry
            MAX-ACCESS not-accessible
            STATUS current
            DESCRIPTION
                "Entry of consolesWlanSnmpEnable"
            INDEX { consolesWlanSnmpEnableIndex }
            ::= { consolesWlanSnmpEnableTable 1 }

        ConsolesWlanSnmpEnableEntry ::=
            SEQUENCE {
                consolesWlanSnmpEnableIndex
                    INTEGER,
                consolesWlanSnmpEnableData
                    INTEGER { enable(1), disable(2) }
            }

        consolesWlanSnmpEnableIndex OBJECT-TYPE
            SYNTAX INTEGER (1..9)
            MAX-ACCESS read-only
            STATUS current
            DESCRIPTION
                "Index of WlanSnmpEnable"
            ::= { consolesWlanSnmpEnableEntry 1 }

        consolesWlanSnmpEnableData OBJECT-TYPE
            SYNTAX INTEGER { enable(1), disable(2) }
            MAX-ACCESS read-write
            STATUS current
            DESCRIPTION
                "SNMP console

                Value : 1 -> enable, 2 -> disable"
            ::= { consolesWlanSnmpEnableEntry 2 }

        consolesWlanMoxaServiceEnableTable OBJECT-TYPE
            SYNTAX SEQUENCE OF ConsolesWlanMoxaServiceEnableEntry
            MAX-ACCESS not-accessible
            STATUS current
            DESCRIPTION
                "Table of consolesWlanMoxaServiceEnable"
            ::= { consoles 36 }

        consolesWlanMoxaServiceEnableEntry OBJECT-TYPE
            SYNTAX ConsolesWlanMoxaServiceEnableEntry
            MAX-ACCESS not-accessible
            STATUS current
            DESCRIPTION
                "Entry of consolesWlanMoxaServiceEnable"
            INDEX { consolesWlanMoxaServiceEnableIndex }
            ::= { consolesWlanMoxaServiceEnableTable 1 }

        ConsolesWlanMoxaServiceEnableEntry ::=
            SEQUENCE {
                consolesWlanMoxaServiceEnableIndex
                    INTEGER,
                consolesWlanMoxaServiceEnableData
                    INTEGER { enable(1), disable(2) }
            }

        consolesWlanMoxaServiceEnableIndex OBJECT-TYPE
            SYNTAX INTEGER (1..9)
            MAX-ACCESS read-only
            STATUS current
            DESCRIPTION
                "Index of WlanMoxaServiceEnable"
            ::= { consolesWlanMoxaServiceEnableEntry 1 }

        consolesWlanMoxaServiceEnableData OBJECT-TYPE
            SYNTAX INTEGER { enable(1), disable(2) }
            MAX-ACCESS read-write
            STATUS current
            DESCRIPTION
                "Moxa service

                Value : 1 -> enable, 2 -> disable"
            ::= { consolesWlanMoxaServiceEnableEntry 2 }

    consolesAccessibleNet OBJECT IDENTIFIER ::= { maintenance 10 }

        consolesAccessibleNetAccessibleNet OBJECT-TYPE
            SYNTAX INTEGER { enable(1), disable(2) }
            MAX-ACCESS read-write
            STATUS current
            DESCRIPTION
                "Accessible Net List

                Value : 1 -> enable, 2 -> disable"
            ::= { consolesAccessibleNet 1 }

        consolesAccessibleNetAccessibleNetPolicy OBJECT-TYPE
            SYNTAX INTEGER { accept(1), drop(2) }
            MAX-ACCESS read-write
            STATUS current
            DESCRIPTION
                "Policy

                Value : 1 -> accept, 2 -> drop"
            ::= { consolesAccessibleNet 2 }

        consolesAccessibleNetTable OBJECT-TYPE
            SYNTAX SEQUENCE OF ConsolesAccessibleNetEntry
            MAX-ACCESS not-accessible
            STATUS current
            DESCRIPTION
                "Table of consolesAccessibleNet"
            ::= { maintenance 11 }

        consolesAccessibleNetEntry OBJECT-TYPE
            SYNTAX ConsolesAccessibleNetEntry
            MAX-ACCESS not-accessible
            STATUS current
            DESCRIPTION
                "Entry of consolesAccessibleNet"
            INDEX { consolesAccessibleNetIndex }
            ::= { consolesAccessibleNetTable 1 }

        ConsolesAccessibleNetEntry ::=
            SEQUENCE {
                consolesAccessibleNetIndex
                    INTEGER,
                consolesAccessibleNetActive
                    INTEGER,
                consolesAccessibleNetSrcIP
                    IpAddress,
                consolesAccessibleNetSrcMask
                    IpAddress
            }

        consolesAccessibleNetIndex OBJECT-TYPE
            SYNTAX INTEGER (1..8)
            MAX-ACCESS read-only
            STATUS current
            DESCRIPTION
                "Index of consolesAccessibleNet"
            ::= { consolesAccessibleNetEntry 1 }

        consolesAccessibleNetActive OBJECT-TYPE
            SYNTAX INTEGER { enable(1), disable(2) }
            MAX-ACCESS read-write
            STATUS current
            DESCRIPTION
                "Accessible Net List

                Value : 1 -> enable, 2 -> disable"
            ::= { consolesAccessibleNetEntry 2 }

        consolesAccessibleNetSrcIP OBJECT-TYPE
            SYNTAX IpAddress
            MAX-ACCESS read-write
            STATUS current
            DESCRIPTION
                "Source IP

                "
            ::= { consolesAccessibleNetEntry 3 }

        consolesAccessibleNetSrcMask OBJECT-TYPE
            SYNTAX IpAddress
            MAX-ACCESS read-write
            STATUS current
            DESCRIPTION
                "Source Netmask

                "
            ::= { consolesAccessibleNetEntry 4 }

    userWebCertificate OBJECT IDENTIFIER ::= { maintenance 13 }

        userWebCertificateEnable OBJECT-TYPE
            SYNTAX INTEGER { enable(1), disable(2) }
            MAX-ACCESS read-write
            STATUS current
            DESCRIPTION
                "SSL certificate enable

                Value : 1 -> enable, 2 -> disable"
            ::= { userWebCertificate 1 }

        awkTraps OBJECT IDENTIFIER ::= { awk4131A 0 }

        configChange NOTIFICATION-TYPE
            STATUS current
            DESCRIPTION
                "The configuration has been changed."
            ::= {awkTraps 1}

        powerOn NOTIFICATION-TYPE
            OBJECTS { powerInputIndex }
            STATUS current
            DESCRIPTION
                "The power transition(off -> on) trap."
            ::= {awkTraps 2}

        powerOff NOTIFICATION-TYPE
            OBJECTS { powerInputIndex }
            STATUS current
            DESCRIPTION
                "The power transition(on -> off) trap."
            ::= {awkTraps 3}

        diOn NOTIFICATION-TYPE
            OBJECTS { diIndex }
            STATUS current
            DESCRIPTION
                "The DI transition(off -> on) trap."
            ::= {awkTraps 4}

        diOff NOTIFICATION-TYPE
            OBJECTS { diIndex }
            STATUS current
            DESCRIPTION
                "The DI transition(on -> off) trap."
            ::= {awkTraps 5}

        clientJoined NOTIFICATION-TYPE
            OBJECTS { wlanClientMAC }
            STATUS current
            DESCRIPTION
                "New client has joined AP"
            ::= {awkTraps 6}

        clientLeft NOTIFICATION-TYPE
            OBJECTS { wlanClientMAC }
            STATUS current
            DESCRIPTION
                "A client has left AP"
            ::= {awkTraps 7}

END
