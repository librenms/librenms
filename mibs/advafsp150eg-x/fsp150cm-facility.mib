CM-FACILITY-MIB DEFINITIONS ::= BEGIN

IMPORTS
    MODULE-COMPLIANCE, OBJECT-GROUP 
             FROM SNMPv2-CONF
    MODULE-IDENTITY, OBJECT-TYPE, Integer32, Unsigned32, IpAddress
             FROM SNMPv2-SMI
    DateAndTime, DisplayString, TruthValue, RowStatus, StorageType, 
    MacAddress, VariablePointer, TEXTUAL-CONVENTION
             FROM SNMPv2-TC
    Ipv6Address
             FROM IPV6-TC
    InterfaceIndex
             FROM IF-MIB
    PhysicalIndex
             FROM ENTITY-MIB
    neIndex, shelfIndex, slotIndex, f3UsbHostIndex, networkElementEntry
             FROM CM-ENTITY-MIB
    fsp150cm
             FROM  ADVA-MIB 
    AdminState, OperationalState, SecondaryState, EthernetMediaType, 
    EthernetPortSpeed, TrafficDirection, SfpConnectorValue, SfpMediaType,
    VlanId, VlanPriority, VlanTagType, PriorityMapMode, SignalDirectionType,
    AfpTagControl, VlanEthertype,
    CmTrafficAclFilterActionType,IpVersion,CmTrafficACLPriorityType,
    CmTrafficAclFilterType, CmTrafficAclProtocolType, TDMFrequencySourceType,
    F3DisplayString
             FROM  CM-COMMON-MIB
    f3LagIndex
             FROM F3-LAG-MIB
    SSMQualityLevel, SquelchControl, TimeSource
             FROM F3-SYNC-MIB;


cmFacilityMIB MODULE-IDENTITY
    LAST-UPDATED        "201106110000Z"
    ORGANIZATION    "ADVA Optical Networking"
    CONTACT-INFO
            "        Raghav Trivedi
                     ADVA Optical Networking, Inc.
                Tel: +1 972 759-1239
             E-mail: rtrivedi@advaoptical.com
             Postal: 2301 N. Greenville Ave. #300
                     Richardson, TX USA 75082"
    DESCRIPTION
            "This module defines the Facility MIB definitions used by 
             the F3 (FSP150CM/CC) product lines.  
             Copyright (C) ADVA Optical Networking."
    REVISION        "201106110000Z"
    DESCRIPTION
        "Notes from release 201310210000Z,
           (1) Deleted cmEthernetAccPortTable object:
               - cmEthernetAccPortMonitorPortEnabled,
               - cmEthernetAccPortBufferSize,
               - cmEthernetAccPortJDSUControlFramesSnoopingEnabled,
               - cmEthernetAccPortJDSULoopbackVlan.
           (2) Deleted cmEthernetNetPortTable object:
               - cmEthernetNetPortJDSUControlFramesSnoopingEnabled,
               - cmEthernetNetPortJDSULoopbackVlan.
           (3) Added tables:
               - cmEthernetAccPortJdsuExtTable, 
               - cmEthernetNetPortJdsuExtTable.
         Notes from release 201310140000Z,
           (1) New cmEthernetAccPortTable objects:
               - cmEthernetAccPortMonitorPortEnabled,
               - cmEthernetAccPortBufferSize.
         Notes from release 201310070000Z,
           (1) Deleted cmEthernetAccPortTable object:
               - cmEthernetAccPortJDSUUnitTextId.
           (2) Deleted cmEthernetNetPortTable object:
               - cmEthernetNetPortJDSUUnitTextId.
         Notes from release 201310030000Z,
           (1) New gps10MHzPortTable object:
               gps10MHzPortAssumedQL
         Notes from release 201309160000Z,
           (1) Added new literals for CmLoopbackType:
               - jdsu-terminal-port-tailend,
               - jdsu-terminal-vlan-tailend,
               - jdsu-facility-port-tailend,
               - jdsu-facility-vlan-tailend.
           (2) New cmEthernetAccPortTable objects:
               - cmEthernetAccPortJDSUControlFramesSnoopingEnabled,
               - cmEthernetAccPortJDSULoopbackVlan,
               - cmEthernetAccPortJDSUUnitTextId.
           (3) New cmEthernetNetPortTable objects:
               - cmEthernetNetPortJDSUControlFramesSnoopingEnabled,
               - cmEthernetNetPortJDSULoopbackVlan,
               - cmEthernetNetPortJDSUUnitTextId.
         Notes from release 201306100000Z,
           (1) Added table: networkElementTMParamsTable
           (2) Added TEXTUAL-CONVENTION: BandwidthProfileMode
           (3) Added group: networkElementTMParamsGroup
         Notes frome release 201305230000Z,
           (1) New cmEthernetAccPortTable objects:
               - cmEthernetAccPortLoopbackSourceMacControlEnabled,
               - cmEthernetAccPortLoopbackDestMacControlEnabled,
               - cmEthernetAccPortLoopbackSourceMacAddress,
               - cmEthernetAccPortLoopbackDestMacAddress,
               - cmEthernetAccPortLoopbackBlockingEnabled
           (2) New cmEthernetNetPortTable objects:
               - cmEthernetNetPortLoopbackSourceMacControlEnabled,
               - cmEthernetNetPortLoopbackDestMacControlEnabled,
               - cmEthernetNetPortLoopbackSourceMacAddress,
               - cmEthernetNetPortLoopbackDestMacAddress,
               - cmEthernetNetPortLoopbackBlockingEnabled

         Notes from release 201303140000Z,
           (1) New cmFlowTable object:
               cmFlowN2NForwardingEnabled

         Notes from release 201210150000Z,
           (1) New cmFlowTable objects:
               cmFlowPort1, cmFlowPort2, cmFlowPolicingControl, cmFlowAutoCIRPercentage,
               cmFlowLoopAvoidanceObject

         Notes from release 201207190000Z,
           (1) New textual conventions: OCNSTMPortType, E1T1LineType, E1T1LineCode,
               E1T1FrameFormat, E1T1RcvSensitivity  
           (2) New ocnStmTable object: ocnStmPortType
           (3) New e1T1Table objects: e1t1LineType, e1t1LineCode, e1t1FrameFormat,
                 e1t1LineBuildOut, e1T1TimingDomain, e1T1RcvSensitivity,
                 e1T1IdlePatternProfile, e1T1LoopbackProfile

         Notes from release 201106110000Z,
           -Added f3PulsePerSecondPortTable, f3TimeOfDayPortTable 

         Notes from release 201205020000Z,
           -CPD support for LLDP and ELMI for Access/Network Port, Flow CPD 

         Notes from release 201105270000Z,
           -Formalized the OBJECT-GROUP definitions

         Notes from release 201102100000Z
            (i)Added variable bitsPortLineBuildOut 

         Notes from release 201101250000Z
            (i)Added enc-custom to PcpDEEncType

         Notes from release 201010130000Z
            PCP based Drop Eligibility function is added,
            (i)New textual conventions PcpDEEncType, PcpDEPairsAction
            (ii)New Access Port objects cmEthernetAccPortDeiEnable, 
                            cmEthernetAccPortPcpDEEncType, 
                            cmEthernetAccPortPcpDEPairsAction
            (iii)New Network Port objects cmEthernetNetPortDeiEnable, 
                            cmEthernetNetPortPcpDEEncType, 
                            cmEthernetNetPortPcpDEPairsAction
            (iv)New Access Port tables cmAccPortPcpDEEncTable, cmAccPortPcpDEDecTable,
                          cmAccPortPcpDEPairTable
            (v)New Network tables cmNetPortPcpDEEncTable, cmNetPortPcpDEDecTable,
                          cmNetPortPcpDEPairTable

         Notes from release 201010130000Z
           (i)Added cmFlowN2AOuterTagPrioEnabled, cmEthernetNetPortPrioMapMode and 
              cmNetPortPrioMapTable to support the Network Port Priority Mapping function
           (ii)Added FlowTagControl of pop 

         Notes from release 201006100000Z
         Updated range of cmEthernetAccPortOuterVlanLoopbackMask,
            cmEthernetAccPortInnerVlanLoopbackMask, cmEthernetNetPortOuterVlanLoopbackMask,
            cmEthernetNetPortInnerVlanLoopbackMask,
            to INTEGER(0..16) to indicate mask not SET

         Notes from release 201003310000Z
        (1)cmFlowTable has two new objects 
               cmFlowPreserveSTagProperties, cmFlowInnerTagPrioEnabled,
               cmPrioMapInnerTagPriority

         Notes from release 201002120000Z
        (1)cmFlowTable has new object cmFlowPolicingEnabled
        (2)New table ieee1588EthernetPortTable represents the IEEE 1588 Ethernet Port
        (3)New table gps10MHzPortTable represents the 10MHz Port


         Notes from release 200903160000Z
         This release is applicable to the FSP150CC Release 4.1 
         devices GE206.
         Following new objects are added to cmEthernetAccPortEntry,
          cmEthernetAccPortMDIXStatus, cmEthernetAccPortSfpReach,
          cmEthernetAccPortSfpLaserWaveLength,
          cmEthernetAccPortSfpMediaType, cmEthernetAccPortOamEnabled,
          cmEthernetAccPortShapingEnabled,
          cmEthernetAccPortShapedSpeedLo, cmEthernetAccPortShapedSpeedHi,
          cmEthernetAccPortQinQEtherType, cmEthernetAccPortRxPauseEnabled,
          cmEthernetAccPortAutoDiagEnabled,
          cmEthernetAccPortLinkLossFwdTxActionType,
          cmEthernetAccPortN2AVlanTrunkingEnabled, 
          cmEthernetAccPortA2NPushPVIDEnabled,
          cmEthernetAccPortN2APopPVIDEnabled, cmEthernetAccPortPortVlanId,
          cmEthernetAccPortPortVlanPriority, 
          cmEthernetAccPortPrioMapMode, cmEthernetAccPortSyncEEnabled,
          cmEthernetAccPortQLModeEnabled, cmEthernetAccPortExpectedQL,
          cmEthernetAccPortAssumedQL, cmEthernetAccPortReceivedQL, 
          cmEthernetAccPortTransmitQL,
          cmEthernetAccPortDeiEnable,
          cmEthernetAccPortPcpDEEncType, cmEthernetAccPortPcpDEPairsAction,

         Following new objects are added to cmFlowEntry,
          cmFlowTrafficType, cmFlowCOS, cmFlowVlanMemberList,
          cmFlowAction, cmFlowActionVlan, cmFlowUntaggedMemberEnabled,
          cmFlowA2NCIRHi, cmFlowA2NEIRHi,
          cmFlowN2ACIRHi, cmFlowN2AEIRHi, cmFlowHCOSMgmtEnabled,
          cmFlowGuaranteedA2NBandwidthLo,
          cmFlowGuaranteedA2NBandwidthHi, cmFlowMaximumA2NBandwidthLo,
          cmFlowMaximumA2NBandwidthHi, cmFlowCTagControl,
          cmFlowCTagVlanId, cmFlowCTagVlanPriority, cmFlowCTagMatchRxPrio,
          cmFlowSTagControl, cmFlowSTagVlanId, cmFlowSTagVlanPriority,
          cmFlowOuterTagPrioEnabled, cmFlowESFramesLossThreshold,
          cmFlowSESFramesLossThresholdRatio, 

         Following new objects are added to cmQosShaperEntry,
          cmQosShaperCOS, cmQosShaperCIRHi, cmQosShaperEIRHi

         Following new objects are added to cmEthernetNetPortEntry,
          cmEthernetNetPortMDIXStatus, cmEthernetNetPortSfpReach,
          cmEthernetNetPortSfpLaserWaveLength,
          cmEthernetNetPortSfpMediaType, cmEthernetNetPortOamEnabled,
          cmEthernetNetPortShapingEnabled,
          cmEthernetNetPortShapedSpeedLo, cmEthernetNetPortShapedSpeedHi,
          cmEthernetNetPortQinQEtherType, cmEthernetNetPortAutoDiagEnabled,
          cmEthernetNetPortLinkLossFwdTxActionType,
          cmEthernetNetPortSyncEEnabled, cmEthernetNetPortQLModeEnabled,
          cmEthernetNetPortExpectedQL, cmEthernetNetPortAssumedQL,
          cmEthernetNetPortReceivedQL, cmEthernetNetPortTransmitQL,
          cmEthernetNetPortPrioMapMode, cmEthernetNetPortDeiEnable,
          cmEthernetNetPortPcpDEEncType, cmEthernetNetPortPcpDEPairsAction,


         Following new objects are added to cmEthernetMgmtPortEntry,
          cmEthernetMgmtPortMDIXStatus
    
         Following SNMP tables are new,
          cmPrioMapTable, cmQosFlowPolicerTable, cmAccPortQosShaperTable,
          cmEthernetAccPortCpdV2Table, cmFlowCpdV2Table, 
          cmEthernetNetPortCpdV2Table, bitsPortTable

         Enumeration literals use-group-setting, not-active added to TC CmControlProtocolDispType

         Notes from release 200803030000Z,
         (1)MIB version ready for release FSP150CM 3.1." 
    ::= {fsp150cm 4}    

-- 
-- OID definitions
-- 
cmFacilityObjects      OBJECT IDENTIFIER ::= {cmFacilityMIB 1}
cmFacilityConformance  OBJECT IDENTIFIER ::= {cmFacilityMIB 2}

--
-- Textual Conventions
--
CmEthernetSvcPortMode ::= TEXTUAL-CONVENTION
    STATUS       current
    DESCRIPTION
        "Describes the Ethernet Service Port Mode Type."
    SYNTAX       INTEGER {
                   connection-oriented (1),
                   connection-less (2)
                 }

CmEthernetSvcType ::= TEXTUAL-CONVENTION
    STATUS       current
    DESCRIPTION
        "Describes the Ethernet Service Type.
            epl  - Ethernet Private Linei, Port-based, all-to-one bundling
            evpl - Ethernet Virtual Private Line, VLAN based, 
                   service multiplexed."
    SYNTAX       INTEGER {
                   epl (1),
                   evpl (2)
                 }

CmEthernetTrafficSvcType ::= TEXTUAL-CONVENTION
    STATUS       current
    DESCRIPTION
        "Describes the Ethernet Service Type, including port-based and vlan-based."
    SYNTAX       INTEGER {
                   all-to-one(1),
                   service-multiplexing(2)
                 }
                 
CmAclConfiguration ::= TEXTUAL-CONVENTION
    STATUS       current
    DESCRIPTION
        "This object is defined to set traffic acl resource allocation.
         Supported actions are:
           all-bk-l2 (1)      - all bank allocated to l2.
 	         all-bk-l2-ipv4(2)  - all bank allocated to l2/ipv4. 
 	         two-bk-l2-ipv4(3)  - two thirds allocated to l2/ipv4, the left belongs to ipv6.
           one-bk-l2-ipv4(4)  - one thirds allocated to l2/ipv4, the left belongs to ipv6.
 	         none-bk-l2-ipv4(5) - all bank allocated to ipv6. "
    SYNTAX       INTEGER {
                   all-bk-l2 (1),
                   all-bk-l2-ipv4 (2),
                   two-bk-l2-ipv4 (3),
                   one-bk-l2-ipv4 (4),
                   none-bk-l2-ipv4(5)
                 }
                 
CmAfpType ::= TEXTUAL-CONVENTION
    STATUS       current
    DESCRIPTION
        "Describes the Ethernet Acceptable Framing Policy Type."
    SYNTAX       INTEGER {
                   tagged (1),
                   untagged (2),
                   all (3)
                 }

CmEthernetDiagAction ::= TEXTUAL-CONVENTION
    STATUS       current
    DESCRIPTION
        "Describes the Ethernet Diagnosis Action.
          autoNeg - Auto negotiation capability,
          cable   - Cable diagnostics, cable fault 
          loopback- Terminal loopback with traffic injection and monitoring  
          efm-oam-lpbk- EFM OAM loopback 
          all         - autoNeg, cable tests and loopback, not include efm-oam-lpbk."
    SYNTAX       INTEGER {
                   not-applicable(0),
                   autoneg (1),
                   cable (2),
                   loopback (3),
                   efm-oam-lpbk (4),
                   all (5)
                 }

CmDiagCableCondType ::= TEXTUAL-CONVENTION
    STATUS       current
    DESCRIPTION
        "Describes the Ethernet Diagnosis Cable Condition Result."
    SYNTAX       INTEGER {
                   cableshort (1),
                   cableopen (2),
                   cableimpedance (3),
                   cablenotfound (4),
                   cableok (5),
                   cablefailed (6),
                   cablenotrun(7)
                 }

CmDiagAutoNegCondType ::= TEXTUAL-CONVENTION
    STATUS       current
    DESCRIPTION
        "Describes the Ethernet Diagnosis Auto Negotiation Condition Result."
    SYNTAX       INTEGER {
                   autonegok (1),
                   autonegfailed (2),
                   autonegnotrun (3)
                 }

CmDiagLpbkCondType ::= TEXTUAL-CONVENTION
    STATUS       current
    DESCRIPTION
        "Describes the Ethernet Diagnosis Loopback Condition Result."
    SYNTAX       INTEGER {
                   lpbkok(1),
                   lpbkfailed (2),
                   lpbknotrun (3)
                 }

CmDiagEfmOamLpbkCondType ::= TEXTUAL-CONVENTION
    STATUS       current
    DESCRIPTION
        "Describes the Ethernet Diagnosis EFM OAM Loopback Condition Result."
    SYNTAX       INTEGER {
                   efmlpbkok (1),
                   efmlpbkfailed (2),
                   efmlpbkfailednendNA (3),
                   efmlpbkfailedfendNA (4),
                   efmlpbknotrun (5)
                 }

CmDiagTestStatus ::= TEXTUAL-CONVENTION
    STATUS       current
    DESCRIPTION
        "ECPA Test Status."
    SYNTAX       INTEGER {
                   initial (1),
                   in-progress (2),
                   stopped (3),
                   completed (4),
                   aborted (5)
                 }

CmControlProtocolFilterType ::= TEXTUAL-CONVENTION
    STATUS       current
    DESCRIPTION
        "Describes the Control Protocol Filter Types."
    SYNTAX       INTEGER {
                   efmoam(1),
                   pause(2)
                 }

CmLoopbackType ::= TEXTUAL-CONVENTION
    STATUS       current
    DESCRIPTION
        "Describes the Loopback Types."
    SYNTAX       INTEGER {
                   lpbk-none (1),
                   efm-oam-remote(2),
                   efm-oam-remote-timed(3),
                   facility-port(4),
                   facility-port-timed(5),
                   facility-vlan(6),
                   terminal-port(7),
                   terminal-port-timed(8),
                   terminal-vlan(9),
                   efm-oam-tailend(10),
                   facility-payload(11),
                   facility-payload-timed(12),
                   remote-facility(13),
                   remote-facility-payload(14),
                   tailend-facility(15),
                   tailend-facility-payload(16),
                   terminal-itag(17),
                   facility-itag(18),
                   jdsu-terminal-port-tailend(19),
                   jdsu-terminal-vlan-tailend(20),
                   jdsu-facility-port-tailend(21),
                   jdsu-facility-vlan-tailend(22)
                 }

CmSwapSADAType ::= TEXTUAL-CONVENTION
    STATUS    current
    DESCRIPTION
        "Describes the SWAP SADA Types supported.
            no-swapSADA - No swapping of Source MAC and Destination MAC addrs
            swapSADA    - Do swapping of Source MAC and Destination MAC, Source IP and Destination IP
            swapDAOverrideSA - Swap Destination MAC and IP as Source MAC and IP, override
                               source MAC adn IP with local MAC and IP
            swapSADAMacOnly    - Do swapping of Source MAC and Destination MAC
            swapDAOverridesSAMacOnly - Swap Destination MAC as Source MAC, override
                               source MAC with local MAC."
    SYNTAX       INTEGER {
                   not-applicable(0),
                   noswapSADA(1),
                   swapSADA  (2),
                   swapDAOverrideSA (3),
                   swapSADAMacOnly (4),
                   swapDAOverridesSAMacOnly (5)
                 }


CmControlProtocolDispType ::= TEXTUAL-CONVENTION
    STATUS    current
    DESCRIPTION
        "Describes the Protocol Disposition Type on an interface."
    SYNTAX       INTEGER {
                   not-applicable(0),
                   discard (1),
                   peer  (2),
                   pass-thru (3),
                   --
                   use-group-setting(4),
                   not-active(5),
                   use-port-setting(6),
                   --
                   pass-thru-l2pt(7)  -- Layer 2 Protocol Tunneling
                 }

CmLinkLossFwdSignalType ::= TEXTUAL-CONVENTION
    STATUS       current
    DESCRIPTION
        "Describes the Link Loss Forwarding Signal Types."
    SYNTAX       INTEGER {
                   not-applicable(0),
                   llf-efm-signal (1),
                   llf-link-down(2)
                 }

CmLinkLossFwdTriggerTypes ::= TEXTUAL-CONVENTION
    STATUS       current
    DESCRIPTION
        "Describes the Link Loss Forwarding Trigger Types."
    SYNTAX     BITS {
                 trig-efm-signal(1),
                 trig-link-down(2)
               }

CmLinkLossFwdTxActionType ::= TEXTUAL-CONVENTION
    STATUS       current
    DESCRIPTION
        "Describes the Link Loss Forwarding Tx Action Types."
    SYNTAX       INTEGER {
                   llf-tx-no-action(1),  -- perform no link loss forwarding action
                   llf-tx-efm-signal (2),-- EFM signal
                   llf-tx-link-down(3)   -- Link Down
                 }

CmRemoteLinkIds ::= TEXTUAL-CONVENTION
    STATUS       current
    DESCRIPTION
        "Remote Link Ids used to match for Link Loss Forwarding."
    SYNTAX     BITS {
                 remoteLinkId1(1),
                 remoteLinkId2(2),
                 remoteLinkId3(3),
                 remoteLinkId4(4),
                 remoteLinkId5(5),
                 remoteLinkId6(6),
                 remoteLinkId7(7),
                 remoteLinkId8(8),
                 remoteLinkId9(9),
                 remoteLinkId10(10),
                 remoteLinkId11(11),
                 remoteLinkId12(12),
                 remoteLinkId13(13),
                 remoteLinkId14(14),
                 remoteLinkId15(15),
                 remoteLinkId16(16)
               }

CmOamMode ::= TEXTUAL-CONVENTION
    STATUS       current
    DESCRIPTION
        "Describes the OAM Mode."
    SYNTAX       INTEGER {
                   unknown (0),
                   active (1),
                   passive (2)
                 }

CmOamAdminState ::= TEXTUAL-CONVENTION
    STATUS       current
    DESCRIPTION
        "Describes the OAM Admin State."
    SYNTAX       INTEGER {
                   not-applicable(0),
                   enabled (1),
                   disabled (2)
                 }


CmOamDiscoveryState ::= TEXTUAL-CONVENTION
    STATUS       current
    DESCRIPTION
        "Describes the OAM Discovery State."
    SYNTAX       INTEGER {
                   unknown (0),
                   fault (1),
                   activesendlocal (2),
                   passivewait (3),
                   sendlocalremote (4),
                   sendlocalremoteok (5),
                   sendany (6)
                 }

CmFlowType ::= TEXTUAL-CONVENTION
    STATUS       current
    DESCRIPTION
        "Describes the Ethernet Flow Type.
          portbased - Port based Flow with full bandwidth of port;
                      this Flow does not do VLAN/MAC based processing 
          regular   - Connection-oriented, VLAN based service 
          default   - Connection-oriented, service that matches all VLANs."
    SYNTAX       INTEGER {
                   portbased (1),
                   regular   (2),
                   default   (3)
                 }

CmEthernetMDIXType ::= TEXTUAL-CONVENTION
    STATUS     current
    DESCRIPTION
        "Describes the Ethernet MDIX Type.
          auto-mdix - Auto MDIX 
          crossed   - Crossed 
          uncrossed - Uncrossed."
    SYNTAX       INTEGER {
                   not-applicable (1),
                   auto-mdix (2),
                   crossed   (3),
                   uncrossed (4)
                 }


FlowTrafficType ::= TEXTUAL-CONVENTION
    STATUS     current
    DESCRIPTION
        "Describes the Flow Traffic Type.
          shaped-only, 
          policed-shaped."
    SYNTAX       INTEGER {
                   shaped-only (1),
                   policed-shaped (2)
                 }

FlowVlanActionType ::= TEXTUAL-CONVENTION
    STATUS       current
    DESCRIPTION
        "Describes the Ethernet Flow Action.  Used for
         adding/removing VLAN members"
    SYNTAX       INTEGER {
                   no-action (1),
                   add-vlan (2),
                   remove-vlan (3)
                 }

FlowTagControl ::= TEXTUAL-CONVENTION
    STATUS       current
    DESCRIPTION
        "Describes the Ethernet Flow Tag Control Type."
    SYNTAX       INTEGER {
                   none    (1),
                   push    (2),
                   swapvid (3),
                   pushvid (4),
                   pop(5),
                   pushisid(6)
                 }

PrioMapControlType ::= TEXTUAL-CONVENTION
    STATUS       current
    DESCRIPTION
        "Describes the Priority Mapping Control Type."
    SYNTAX       INTEGER {
                   none (1),
                   swap (2)
                 }

PolicerAlgorithmType ::= TEXTUAL-CONVENTION
    STATUS       current
    DESCRIPTION
        "Describes the Policer Algorithm Type."
    SYNTAX       INTEGER {
                   srTCM (1),
                   trTCM (2)
                 }

PolicerColorMode ::= TEXTUAL-CONVENTION
    STATUS       current
    DESCRIPTION
        "Describes the Policer Color Mode."
    SYNTAX       INTEGER {
                   color-aware (1),
                   color-blind (2)
                 }

BitsPortType ::= TEXTUAL-CONVENTION
    STATUS       current
    DESCRIPTION
        "Enumerations for BITS Port Type.
             bits-in, 
             bits-out." 
    SYNTAX       INTEGER {
                   bits-in(1),
                   bits-out(2)
                 }

BitsPortLineType ::= TEXTUAL-CONVENTION
    STATUS       current
    DESCRIPTION
        "Enumerations for BITS Line Type.
             t1, 
             e1,
             2048kHz." 
    SYNTAX       INTEGER {
                   t1(1),
                   e1(2),
                   type-2048kHz(3)
                 }

BitsPortLineCode ::= TEXTUAL-CONVENTION
    STATUS       current
    DESCRIPTION
        "Enumerations for BITS Line Code.
             none,  
             t1-b8zs,  
             t1-ami,
             e1-hdb3,
             e1-ami."
    SYNTAX       INTEGER {
                   none(1),
                   t1-b8zs (2),
                   t1-ami (3),
                   e1-hdb3 (4),
                   e1-ami (5)
                 }

BitsFrameFormat ::= TEXTUAL-CONVENTION
    STATUS       current
    DESCRIPTION
        "Enumerations for Bits Frame Format.
             none,
             t1-sf,
             t1-esf,
             e1-unframed,
             e1-crc4,
             e1-dualframe."
    SYNTAX       INTEGER {
                   none(1),
                   t1-sf(2),
                   t1-esf(3),
                   e1-unframed(4),
                   e1-crc4(5),
                   e1-dualframe(6)
                 }

SaBitDesignation ::= TEXTUAL-CONVENTION
    STATUS       current
    DESCRIPTION
        "Enumerations for SA Bit Desgination.
             none,
             bit4,
             bit5,
             bit6,
             bit7,
             bit8."
    SYNTAX   INTEGER {
               none(1),
               bit4(2),
               bit5(3),
               bit6(4),
               bit7(5),
               bit8(6)
             }

CmActiveControlProtocolsType ::= TEXTUAL-CONVENTION
    STATUS       current
    DESCRIPTION
        "Remote Link Ids used to match for Link Loss Forwarding."
    SYNTAX     BITS {
                 ciscoGroup(1),
                 isl(2),
                 pagp(3),
                 udld(4),
                 cdp(5),
                 vtp(6),
                 dtp(7),
                 pvstpplus(8),
                 uplinkfast(9),
                 vlanbridge(10),
                 l2pt(11),
                 bridgegroup(12),
                 bpdu(13),
                 pause(14),
                 lacp(15),
                 lacpmarker(16),
                 efmoam(17),
                 ssm(18),
                 portauthen(19),
                 bridgereserved(20),
                 lanbridges(21),
                 garpgroup(22),
                 gmrp(23),
                 gvrp(24),
                 garp(25),
                 --
                 lldp(26),
                 elmi(27)
               }

PcpDEEncType ::= TEXTUAL-CONVENTION
    STATUS       current
    DESCRIPTION
        "Enumerations for PCP Drop Eligibility Encode Type.
             enc-none,
             enc-7p1d,
             enc-6p2d,
             enc-5p3d,
             enc-custom."
    SYNTAX   INTEGER {
               enc-none(1),
               enc-7p1d(2),
               enc-6p2d(3),
               enc-5p3d(4),
               enc-custom(5)
             }

PcpDEPairsAction ::= TEXTUAL-CONVENTION
    STATUS       current
    DESCRIPTION
        "    none,
             apply-pairs."
    SYNTAX   INTEGER {
               none(0),
               apply-pairs(1)
             }

LineBuildOut ::= TEXTUAL-CONVENTION
    STATUS       current
    DESCRIPTION
        "    none,
             0-133ft,
             133-266ft,
             266-399ft,
             399-533ft,
             533-655ft,
             7dot5db,
             15db,
             22dot5db."
    SYNTAX   INTEGER {
               none(0),
               lbo-0-133ft(1),
               lbo-133-266ft(2),
               lbo-266-399ft(3),
               lbo-399-533ft(4),
               lbo-533-655ft(5),
               lbo-7dot5db(6),
               lbo-15db(7),
               lbo-22dot5db(8)
             }

BitsPortImpedanceMode ::= TEXTUAL-CONVENTION
    STATUS       current
    DESCRIPTION
        "Describes the impedance mode of the BITS-IN and BITS-OUT interfaces:
             120OHM."
    SYNTAX   INTEGER {
               bits-120Ohm(1),
               bits-100Ohm(2)
             }

ShapingType ::= TEXTUAL-CONVENTION
    STATUS       current
    DESCRIPTION
            "
                port-based - traffic shaping at Port level
                flow-based - traffic shaping at Flow level"
    SYNTAX   INTEGER {
               port-based(1),
               flow-based(2)
             }

XgePhyType ::= TEXTUAL-CONVENTION
    STATUS       current
    DESCRIPTION
            " Specifies the Ethernet 10G port PHY type.
                not-applicable - for non-10G ports
                lan - 10G LAN-PHY mode (10GBASE-R) operating at 10Gb/sec
                wan - 10G WAN-PHY mode (10GBASE-W) operating at 9.29Gb/sec
                "
    SYNTAX   INTEGER {
               not-applicable(0),
               lan(1),
               wan(2)
             }

F3Usb3GDCNPINCodeActionType ::= TEXTUAL-CONVENTION
    STATUS       current
    DESCRIPTION
        "Describes the 3G Dcn Pin Code Action Types."
    SYNTAX       INTEGER {
                     not-applicable(0),
                     enable-pin(1),
                     disable-pin(2),
                     change-pin(3),
                     authentication-pin(4),
                     unlock-pin(5)
                 }

F3Usb3GSimCardState ::= TEXTUAL-CONVENTION
    STATUS       current
    DESCRIPTION
        "Describes the 3G Usb Sim Card States."
    SYNTAX       INTEGER {
                     not-applicable(0),
                     ok(1),
                     notinserted(2),
                     networkrejected(3),
                     unknown(4)
                 }

F3Usb3GNetworkConnectionState ::= TEXTUAL-CONVENTION
    STATUS       current
    DESCRIPTION
        "Describes the Connection State of the 3G Usb Modem."
    SYNTAX       INTEGER {
                     not-applicable(0),
                     connecting(1),
                     connected(2),
                     disconnected(3)
                 }

F3Usb3GRecvSignalStrengthInd ::= TEXTUAL-CONVENTION
    STATUS       current
    DESCRIPTION
        "Describes the Recived Signal Strength of the 3G Usb Modem."
    SYNTAX       INTEGER {
                     not-applicable(0),
                     high(1),
                     medium(2),
                     low(3),
                     none(4)
                 }

TrailTraceFormat ::= TEXTUAL-CONVENTION
    STATUS       current
    DESCRIPTION
        "Describes the Trail Trace Format."
    SYNTAX       INTEGER {
                   not-applicable (0),
                   onebytemode (1),
                   sixteenbytemode (2),
                   sixtyfourbytemode (3)
                 }

MultiplexingStructure ::= TEXTUAL-CONVENTION
    STATUS       current
    DESCRIPTION
        "Describes the Multiplexing Structure."
    SYNTAX       INTEGER {
                   not-applicable (0),
                   vt-sts1 (1),
                   sts1spe-sts1 (2),
                   sts3cspe-sts3c (3),
                   vc12-vc4-aug (4),
                   vc12-vc3-aug (5),
                   vc3-aug (6),
                   vc3-vc4-aug (7),
                   vc4-aug (8),
                   custom (9)
                 }

EoTDMMode ::= TEXTUAL-CONVENTION
    STATUS       current
    DESCRIPTION
        "Describes the EoTDM Mode."
    SYNTAX       INTEGER {
                   not-applicable (0),
                   eosdh (1),
                   eopdh (2)
                 }

BitErrRate ::= TEXTUAL-CONVENTION
    STATUS       current
    DESCRIPTION
        "."
    SYNTAX       INTEGER {
                   none (0),
                   ber-1e-1 (1),
                   ber-1e-2 (2),
                   ber-1e-3 (3),
                   ber-1e-4 (4),
                   ber-1e-5 (5),
                   ber-1e-6 (6),
                   ber-1e-7 (7),
                   ber-1e-8 (8),
                   ber-1e-9 (9),
                   ber-1e-10 (10)
                 }


GFPEncapsulationType ::= TEXTUAL-CONVENTION
    STATUS       current
    DESCRIPTION
        "Describes the GFP Encapsulation of the traffic port."
    SYNTAX   INTEGER {
               none(0),
               gfp (1),
               gfp-fcs (2),
               gfp-novcat (3),
               gfp-zerovcat (4),
               gfp-fcs-novcat (5),
               gfp-fcs-zerovcat (6),
               x86 (7)
             }

PPSInputRate ::= TEXTUAL-CONVENTION
    STATUS       current
    DESCRIPTION
        "Describes the PPS Input Rate."
    SYNTAX   INTEGER {
               pulse-per-sec(1),
               pulse-per-2sec(2)
             }

OCNSTMPortType ::= TEXTUAL-CONVENTION
    STATUS  current
    DESCRIPTION
        "OCN/STM Port Type."
    SYNTAX  INTEGER {
                oc12(1),
                oc3(2),
                stm4(3),
                stm1(4)
            }

E1T1LineType ::= TEXTUAL-CONVENTION
    STATUS       current
    DESCRIPTION
        "Enumerations for E1/T1 Line Type.
             t1, 
             e1"
    SYNTAX       INTEGER {
                   t1(1),
                   e1(2)
                 }

E1T1LineCode ::= TEXTUAL-CONVENTION
    STATUS       current
    DESCRIPTION
        "Enumerations for E1/T1 Line Code.
             none,  
             t1-b8zs,  
             t1-ami,
             e1-hdb3,
             e1-ami."
    SYNTAX       INTEGER {
                   none(1),
                   t1-b8zs (2),
                   t1-ami (3),
                   e1-hdb3 (4),
                   e1-ami (5)
                 }

E1T1FrameFormat ::= TEXTUAL-CONVENTION
    STATUS       current
    DESCRIPTION
        "Enumerations for E1/T1 Frame Format.
             none,
             t1-sf,
             t1-esf,
             e1-unframed,
             e1-crc4,
             e1-dualframe,
             e1-basicframe."
    SYNTAX       INTEGER {
                   none(1),
                   t1-sf(2),
                   t1-esf(3),
                   e1-unframed(4),
                   e1-crc4(5),
                   e1-dualframe(6),
                   t1-unframed(7),
                   e1-basicframe(8)
                 }

E1T1RcvSensitivity ::= TEXTUAL-CONVENTION
    STATUS       current
    DESCRIPTION
        "Enumerations for E1/T1 Receive Sensitivity
             high-range,
             low-range"
    SYNTAX       INTEGER {
                   high-range(1),
                   low-range(2)
                 }

E3T3FrameFormat ::= TEXTUAL-CONVENTION
    STATUS       current
    DESCRIPTION
        "Describes the Frame Format of E3/T3."
    SYNTAX   INTEGER {
               none(0),
               dsx3CbitParity (1),
               g832 (2),
               e3Unframed (3),
               dsx3M23 (4),
               g751 (5),
               dsx3Unframed (6)
             }

TDMPathType ::= TEXTUAL-CONVENTION
    STATUS       current
    DESCRIPTION
        "Describes the path type."
    SYNTAX       INTEGER {
                   none (0),
                   t1 (1),
                   e1 (2),
                   t3 (3),
                   e3 (4),
                   vc12 (5),
                   vc3 (6),
                   vc4 (7),
                   vt15 (8),
                   sts1 (9),
                   sts3c (10)
                 }

PPSGenCondition ::= TEXTUAL-CONVENTION
    STATUS       current
    DESCRIPTION
        "Enumerations for PPS Generation Condition 
             tracked-1sat,
             tracked-3sat"
    SYNTAX       INTEGER {
                   tracked-1sat(1),
                   tracked-3sat(2)
                 }


GPSAntennaStatus ::= TEXTUAL-CONVENTION
    STATUS       current
    DESCRIPTION
        "Enumerations for GPS Antenna Status"
    SYNTAX       INTEGER {
                   open(1),
                   short(2),
                   normal(3),
                   unavailable(4)
                 }

PolicingControl ::= TEXTUAL-CONVENTION
    STATUS       current
    DESCRIPTION
        "Defines Policing Control options."
    SYNTAX       INTEGER {
                   a2n(1),
                   n2a(2),
                   a2nN2a(3),
                   n2n(4)
                 }

FlowConfigType ::= TEXTUAL-CONVENTION
    STATUS       current
    DESCRIPTION
        "Defines types of Flow."
    SYNTAX       INTEGER {
                   access(1),       -- Flow on an Access Port
                   passThru(2)      -- Pass-thru Flow between the 2 Network Ports
                 }

G3AuthStatus ::= TEXTUAL-CONVENTION
    STATUS       current
    DESCRIPTION
        "Disabled (PIN protection is disabled)
         OK (PIN protection is enabled and PIN code is correct)   
         Input PIN (input PIN to unlock)
         Input PUK (PIN code is locked, input PUK to unlock)
         Locked (must contact with SIM provider)."
    SYNTAX       INTEGER {
                   disabled (1),
                   ok (2),
                   input-pin (3),
                   input-puk (4),
                   locked (5),
                   none (6)
                 }

PsePowerLevel ::= TEXTUAL-CONVENTION
    STATUS       current
    DESCRIPTION
        "Defines the power level for pse port.
        class1 (4.00 Watts) :0
        class2 (7.00 Watts) :1
        class0andclass 3 (15.4 Watts):2
        class4 (30 Watts):3."
    SYNTAX       INTEGER {
                   class1 (1),
                   class2 (2),
                   class0andclass3 (3),
                   class4 (4)
                 }

PSENonStandardPD ::= TEXTUAL-CONVENTION
    STATUS       current
    DESCRIPTION
        "Enumerations for NonStandardPD 
             disabled:don't support non-standard PD,
             enabled:support non-standard PD"
    SYNTAX       INTEGER {
                   enabled (1),
                   disabled (2)
                 }

LearningAction ::= TEXTUAL-CONVENTION
    STATUS       current
    DESCRIPTION
        "Describes Action on ingress frames when the number of MAC 
        Table entires has reached the maximum defined by tableSize"
    SYNTAX       INTEGER {
                   block (1),
                   forward (2)
                 }

SfpChannelIdentifier ::= TEXTUAL-CONVENTION
    STATUS       current
    DESCRIPTION
        "Describes Channel number of WDM tunable XFP setting."
    SYNTAX   INTEGER {
                not-applicable (0),   -- null
                none(1),              -- not tunnable
                frequency-19610 (2),  -- 196.10THz  1528.7734nm 
                frequency-19595 (3),  -- 195.95THz  1529.9436nm 
                frequency-19585 (4),  -- 195.85THz  1530.7248nm 
                frequency-19575 (5),  -- 195.75THz  1531.5068nm 
                frequency-19565 (6),  -- 195.65THz  1532.2896nm 
                frequency-19555 (7),  -- 195.55THz  1533.0732nm 
                frequency-19545 (8),  -- 195.45THz  1533.8575nm 
                frequency-19535 (9),  -- 195.35THz  1534.6427nm 
                frequency-19525 (10), -- 195.25THz  1535.4287nm 
                frequency-19515 (11), -- 195.15THz  1536.2155nm 
                frequency-19505 (12), -- 195.05THz  1537.0031nm 
                frequency-19495 (13), -- 194.95THz  1537.7915nm 
                frequency-19485 (14), -- 194.85THz  1538.5807nm 
                frequency-19475 (15), -- 194.75THz  1539.3708nm 
                frequency-19465 (16), -- 194.65THz  1540.1616nm 
                frequency-19455 (17), -- 194.55THz  1540.9533nm 
                frequency-19445 (18), -- 194.45THz  1541.7457nm 
                frequency-19435 (19), -- 194.35THz  1542.5390nm 
                frequency-19425 (20), -- 194.25THz  1543.3331nm 
                frequency-19415 (21), -- 194.15THz  1544.1280nm 
                frequency-19405 (22), -- 194.05THz  1544.9238nm 
                frequency-19395 (23), -- 193.95THz  1545.7203nm 
                frequency-19385 (24), -- 193.85THz  1546.5177nm 
                frequency-19375 (25), -- 193.75THz  1547.3159nm 
                frequency-19365 (26), -- 193.65THz  1548.1149nm 
                frequency-19355 (27), -- 193.55THz  1548.9148nm 
                frequency-19345 (28), -- 193.45THz  1549.7155nm 
                frequency-19335 (29), -- 193.35THz  1550.5170nm 
                frequency-19325 (30), -- 193.25THz  1551.3193nm 
                frequency-19315 (31), -- 193.15THz  1552.1225nm 
                frequency-19305 (32), -- 193.05THz  1552.9265nm 
                frequency-19295 (33), -- 192.95THz  1553.7313nm 
                frequency-19285 (34), -- 192.85THz  1554.5370nm 
                frequency-19275 (35), -- 192.75THz  1555.3435nm 
                frequency-19265 (36), -- 192.65THz  1556.1508nm 
                frequency-19255 (37), -- 192.55THz  1556.9590nm 
                frequency-19245 (38), -- 192.45THz  1557.7680nm 
                frequency-19235 (39), -- 192.35THz  1558.5779nm 
                frequency-19225 (40), -- 192.25THz  1559.3886nm 
                frequency-19215 (41), -- 192.15THz  1560.2001nm 
                frequency-19205 (42), -- 192.05THz  1561.0125nm 
                frequency-19600 (43), -- 196.00THz  1529.55nm D01
                frequency-19590 (44), -- 195.90THz  1530.33nm D02
                frequency-19580 (45), -- 195.80THz  1531.12nm D03
                frequency-19570 (46), -- 195.70THz  1531.90nm D04
                frequency-19560 (47), -- 195.60THz  1532.68nm DC1
                frequency-19550 (48), -- 195.50THz  1533.47nm D05
                frequency-19540 (49), -- 195.40THz  1534.25nm D06
                frequency-19530 (50), -- 195.30THz  1535.04nm D07
                frequency-19520 (51), -- 195.20THz  1535.82nm D08
                frequency-19510 (52), -- 195.10THz  1536.60nm DC2
                frequency-19500 (53), -- 195.00THz  1537.40nm D09
                frequency-19490 (54), -- 194.90THz  1538.19nm D10
                frequency-19480 (55), -- 194.80THz  1538.98nm D11
                frequency-19470 (56), -- 194.70THz  1539.77nm D12
                frequency-19460 (57), -- 194.60THz  1540.55nm DC3
                frequency-19450 (58), -- 194.50THz  1541.35nm D13
                frequency-19440 (59), -- 194.40THz  1542.14nm D14
                frequency-19430 (60), -- 194.30THz  1542.94nm D15
                frequency-19420 (61), -- 194.20THz  1543.73nm D16
                frequency-19410 (62), -- 194.10THz  1544.52nm DC4
                frequency-19400 (63), -- 194.00THz  1545.32nm DC9
                frequency-19390 (64), -- 193.90THz  1546.11nm DC5
                frequency-19380 (65), -- 193.80THz  1546.92nm D17
                frequency-19370 (66), -- 193.70THz  1547.72nm D18
                frequency-19360 (67), -- 193.60THz  1548.51nm D19
                frequency-19350 (68), -- 193.50THz  1549.32nm D20
                frequency-19340 (69), -- 193.40THz  1550.11nm DC6
                frequency-19330 (70), -- 193.30THz  1550.92nm D21
                frequency-19320 (71), -- 193.20THz  1551.72nm D22
                frequency-19310 (72), -- 193.10THz  1552.52nm D23
                frequency-19300 (73), -- 193.00THz  1553.33nm D24
                frequency-19290 (74), -- 192.90THz  1554.13nm DC7
                frequency-19280 (75), -- 192.80THz  1554.94nm D25
                frequency-19270 (76), -- 192.70THz  1555.75nm D26
                frequency-19260 (77), -- 192.60THz  1556.55nm D27
                frequency-19250 (78), -- 192.50THz  1557.36nm D28
                frequency-19240 (79), -- 192.40THz  1558.17nm DC8
                frequency-19230 (80), -- 192.30THz  1558.98nm D29
                frequency-19220 (81), -- 192.20THz  1559.79nm D30
                frequency-19210 (82), -- 192.10THz  1560.61nm D31
                frequency-19200 (83)  -- 192.00THz  1561.42nm D32
               }

BandwidthProfileMode ::= TEXTUAL-CONVENTION
    STATUS       current
    DESCRIPTION
        " A Network Element level Frame Rate Bandwidth Profile Mode shall be supported 
         which will indicate if the CIR/EIR is interpreted as Information Rate (IR) or Line Rate 
         (LR). In IR mode BWP is enforced based on number of bytes beginning with DA and 
         ending with FCS as it was received at a port which is called the Service Frame in 
         MEF terminology. In LR mode the BWP is enforced based on the whole frame 
         including IFG, Preamble and SFD."
    SYNTAX       INTEGER {
                   lineRate (1),
                   informationRate (2)
                 }

LearningConfigAction ::= TEXTUAL-CONVENTION
    STATUS       current
    DESCRIPTION
        "Learning Action:
            noAction        - No Action
            flushFwdTable   - Removes all dynamic entries from the Forwarding table
                              of a Flow.
            clearBlock      - removes the secondary state of BLCKD and transitions 
                              the flow to a state where frames are not blocked
            resetAgingTimer - reset the aging timer
            "
    SYNTAX       INTEGER {
                   noAction (1),
                   flushFwdTable (2),
                   clearBlock (3),
                   resetAgingTimer(4)
                 }

TrafficPortDeleteEntitiesAction ::= TEXTUAL-CONVENTION
    STATUS       current
    DESCRIPTION
        "Learning Action:
            no-action        - No Action
            delete-esa-entities   - Removes all esa entities relate to this port.
            delete-cfm-entities   - Removes all cfm entities relate to this port."
    SYNTAX       INTEGER {
                   no-action (1),
                   delete-esa-entities (2),
                   delete-cfm-entities (3)
                 }

UsbDCNMobileNetworkType ::= TEXTUAL-CONVENTION
    STATUS       current
    DESCRIPTION
        "Mobile network type:
            none
            secondGeneration - 2G.
            thirdGeneration  - 3G,
            fourthGeneration - 4G,
            notApplicable."
    SYNTAX       INTEGER {
                   none (1),
                   secondGeneration (2),
                   thirdGeneration (3),
                   fourthGeneration (4),
                   notApplicable(5)
                 }

TxDeiAction ::= TEXTUAL-CONVENTION
    STATUS       current
    DESCRIPTION
        "Transmit DEI Action."
    SYNTAX       INTEGER {
                   setToZero (1),
                   markColor (2),
                   noChange (3)
                 }

RxDeiAction ::= TEXTUAL-CONVENTION
    STATUS       current
    DESCRIPTION
        "Receive DEI Action."
    SYNTAX       INTEGER {
                   ignore (1),
                   use (2)
                 }

DeiOuterTagType ::= TEXTUAL-CONVENTION
    STATUS       current
    DESCRIPTION
        "DEI Outer Tag Type."
    SYNTAX       INTEGER {
                   stag (1),
                   ctagOrStag (2)
                 }

--
--  Ethernet Access Port 
--
cmEthernetAccPortTable  OBJECT-TYPE
    SYNTAX      SEQUENCE OF CmEthernetAccPortEntry
    MAX-ACCESS  not-accessible
    STATUS      current
    DESCRIPTION
            "A list of entries corresponding to Ethernet Access Port 
             Facilities for configuration purposes."
    ::= { cmFacilityObjects 1 }

cmEthernetAccPortEntry OBJECT-TYPE
    SYNTAX      CmEthernetAccPortEntry 
    MAX-ACCESS  not-accessible
    STATUS      current
    DESCRIPTION
            "A conceptual row in the cmEthernetAccPortTable."
    INDEX { neIndex, shelfIndex, slotIndex, cmEthernetAccPortIndex }
    ::= { cmEthernetAccPortTable 1 }

CmEthernetAccPortEntry ::= SEQUENCE {
    -- Port Indices 
    cmEthernetAccPortIndex                           Integer32,
    cmEthernetAccPortIfIndex                         InterfaceIndex,
    cmEthernetAccPortEntityIndex                     PhysicalIndex,

    -- State Management params
    cmEthernetAccPortAdminState                      AdminState,
    cmEthernetAccPortOperationalState                OperationalState,
    cmEthernetAccPortSecondaryState                  SecondaryState,

    -- Generic Port params
    cmEthernetAccPortMTU                             Integer32,

    -- Generic Ethernet Port params
    cmEthernetAccPortMediaType                       EthernetMediaType,
    cmEthernetAccPortConfigSpeed                     EthernetPortSpeed,
    cmEthernetAccPortNegotiatedSpeed                 EthernetPortSpeed,
    cmEthernetAccPortMDIXType                        CmEthernetMDIXType,  
    cmEthernetAccPortJumboFramesEnabled              TruthValue,
    cmEthernetAccPortSfpVendorName                   DisplayString,
    cmEthernetAccPortSfpPartNumber                   DisplayString,
    cmEthernetAccPortSfpSerialNumber                 DisplayString,
    cmEthernetAccPortSfpDateOfManufacture            DateAndTime,
    cmEthernetAccPortSfpConnectorValue               SfpConnectorValue,

    -- EtherJack Diagnosis params
    cmEthernetAccPortInitiateDiag                    CmEthernetDiagAction,
    cmEthernetAccPortDiagnosePair1Cond               CmDiagCableCondType,
    cmEthernetAccPortDiagnosePair2Cond               CmDiagCableCondType,
    cmEthernetAccPortDiagnosePair3Cond               CmDiagCableCondType,
    cmEthernetAccPortDiagnosePair4Cond               CmDiagCableCondType,
    cmEthernetAccPortDiagnoseAutoNegCond             CmDiagAutoNegCondType,
    cmEthernetAccPortDiagnoseLpbkCond                CmDiagLpbkCondType,
    cmEthernetAccPortDiagnoseEfmLpbkCond             CmDiagEfmOamLpbkCondType,
    cmEthernetAccPortDiagnoseResult                  DisplayString,
    cmEthernetAccPortDiagnoseTestStatus              CmDiagTestStatus,
    cmEthernetAccPortDiagnoseTestTime                DateAndTime,

    -- Ethernet Loopback params
    cmEthernetAccPortLoopbackConfig                  CmLoopbackType,
    cmEthernetAccPortLoopbackStatus                  CmLoopbackType,
    cmEthernetAccPortLoopbackTime                    Integer32,
    cmEthernetAccPortLoopbackSwapSADA                CmSwapSADAType,
    cmEthernetAccPortOuterVlanLoopbackMask           INTEGER,
    cmEthernetAccPortOuterVlanLoopback1              DisplayString,
    cmEthernetAccPortOuterVlanLoopback2              DisplayString,
    cmEthernetAccPortOuterVlanLoopback3              DisplayString,
    cmEthernetAccPortInnerVlanLoopbackMask           INTEGER,
    cmEthernetAccPortInnerVlanLoopback1              DisplayString,
    cmEthernetAccPortInnerVlanLoopback2              DisplayString,
    cmEthernetAccPortInnerVlanLoopback3              DisplayString,

    -- Link Loss Forwarding params 
    cmEthernetAccPortLinkLossFwdEnabled              TruthValue,
    cmEthernetAccPortLinkLossFwdSignalType           CmLinkLossFwdSignalType,
    cmEthernetAccPortLinkLossFwdTriggerTypes         CmLinkLossFwdTriggerTypes,
    cmEthernetAccPortLinkLossFwdDelay                Integer32,
    cmEthernetAccPortLinkLossFwdActive               TruthValue,
    cmEthernetAccPortLinkLossFwdPartnerEnabled       TruthValue,
    cmEthernetAccPortLinkLossFwdLocalLinkId          Integer32,
    cmEthernetAccPortLinkLossFwdRemoteLinkIds        CmRemoteLinkIds,

    -- OAM params
    cmEthernetAccPortOamId                           Integer32,
    cmEthernetAccPortOamAdminDisposition             CmControlProtocolDispType,
    cmEthernetAccPortOamDiscoveryState               CmOamDiscoveryState,
    cmEthernetAccPortOamLocalVarRtrvsEnabled         TruthValue,
    cmEthernetAccPortOamLocalLinkEventsEnabled       TruthValue,
    cmEthernetAccPortOamLocalOamLoopbacksSupported   TruthValue,
    cmEthernetAccPortOamLocalUnidirSupportEnabled    TruthValue,
    cmEthernetAccPortOamLocalMaxPDUSize              Integer32,
    cmEthernetAccPortOamLocalMode                    CmOamMode,
    cmEthernetAccPortOamRemoteMacAddress             MacAddress,
    cmEthernetAccPortOamRemoteVarRtrvsEnabled        TruthValue,
    cmEthernetAccPortOamRemoteLinkEventsEnabled      TruthValue,
    cmEthernetAccPortOamRemoteOamLoopbacksSupported  TruthValue,
    cmEthernetAccPortOamRemoteUnidirSupportEnabled   TruthValue,
    cmEthernetAccPortOamRemoteMaxPDUSize             Integer32,
    cmEthernetAccPortOamRemoteMode                   CmOamMode,

    -- Ethernet Port Service params
    cmEthernetAccPortMode                            CmEthernetSvcPortMode,
    cmEthernetAccPortSvcType                         CmEthernetSvcType,

    -- Ethernet Port Traffic params
    cmEthernetAccPortRxPauseDisposition              CmControlProtocolDispType,
    cmEthernetAccPortTxPauseEnabled                  TruthValue,
    cmEthernetAccPortAfpType                         CmAfpType,

    --New objects available with FSP150CC GE206 (Release 4.1CC)
    -- Generic Ethernet Port params
    cmEthernetAccPortMDIXStatus                      CmEthernetMDIXType,
    cmEthernetAccPortSfpReach                        Integer32,
    cmEthernetAccPortSfpLaserWaveLength              Integer32,
    cmEthernetAccPortSfpMediaType                    SfpMediaType,

    -- EFM OAM 
    cmEthernetAccPortOamEnabled                      TruthValue,
    cmEthernetAccPortOamAdminState                   CmOamAdminState,

    -- Ethernet Port Traffic params
    cmEthernetAccPortShapingEnabled                  TruthValue,
    cmEthernetAccPortShapedSpeedLo                   Unsigned32,
    cmEthernetAccPortShapedSpeedHi                   Unsigned32,
    cmEthernetAccPortQinQEtherType                   Unsigned32,
    cmEthernetAccPortRxPauseEnabled                  TruthValue,

    -- EtherJack Diagnosis params
    cmEthernetAccPortAutoDiagEnabled                 TruthValue,

    -- LLF param
    cmEthernetAccPortLinkLossFwdTxActionType         CmLinkLossFwdTxActionType,
    cmEthernetAccPortLinkLossFwdRxRLDLinkIds         CmRemoteLinkIds,

    --Ethernet Port Services params
    cmEthernetAccPortN2AVlanTrunkingEnabled          TruthValue,
    cmEthernetAccPortA2NPushPVIDEnabled              TruthValue,
    cmEthernetAccPortN2APopPVIDEnabled               TruthValue,
    cmEthernetAccPortPortVlanId                      VlanId,
    cmEthernetAccPortPortVlanPriority                VlanPriority,     
    cmEthernetAccPortPrioMapMode                     PriorityMapMode,     

    --Synchronous Port params
    cmEthernetAccPortSyncEEnabled                    TruthValue,
    cmEthernetAccPortQLModeEnabled                   TruthValue,
    cmEthernetAccPortExpectedQL                      SSMQualityLevel,
    cmEthernetAccPortAssumedQL                       SSMQualityLevel,
    cmEthernetAccPortReceivedQL                      SSMQualityLevel,
    cmEthernetAccPortTransmitQL                      SSMQualityLevel,
  
    --PCP DEI params
    cmEthernetAccPortDeiEnable                       TruthValue, 
    cmEthernetAccPortPcpDEEncType                    PcpDEEncType,
    cmEthernetAccPortPcpDEPairsAction                PcpDEPairsAction,

    cmEthernetAccPortSSMRemoteMacAddress             MacAddress,

    --XG params
    cmEthernetAccPortXgePhyType                      XgePhyType,
    
    --Mac Loopback Params
    cmEthernetAccPortLoopbackSourceMacControlEnabled TruthValue,
    cmEthernetAccPortLoopbackDestMacControlEnabled   TruthValue,
    cmEthernetAccPortLoopbackSourceMacAddress        MacAddress,
    cmEthernetAccPortLoopbackDestMacAddress          MacAddress,
    cmEthernetAccPortLoopbackBlockingEnabled         TruthValue
}

-- Port Indices 
cmEthernetAccPortIndex OBJECT-TYPE
    SYNTAX      Integer32 (0|1..65535)
    MAX-ACCESS  read-only
    STATUS      current
    DESCRIPTION
            "An integer index value used to uniquely identify
             this Ethernet Access Port within a card.
             Note that each Ethernet Access Port is uniquely identified
             by the indices neIndex, shelfIndex, 
             slotIndex, cmEthernetAccPortIndex.
             From release 5.6CC zero value becomes valid.
             The zero value is used in Network Element level objects which contain
             cmEthernetAccPortIndex in the index which is not-applicable for 
             these objects e.g. Pass-thru Flows, Shapers or Policers." 
    ::= { cmEthernetAccPortEntry 1 }

cmEthernetAccPortIfIndex OBJECT-TYPE
    SYNTAX      InterfaceIndex 
    MAX-ACCESS  read-only
    STATUS      current
    DESCRIPTION
            "This object has the same value as ifIndex for 
             Ethernet Access Port.  An integer index value used to 
             uniquely identify this Ethernet Access Port."
    ::= { cmEthernetAccPortEntry 2 }

cmEthernetAccPortEntityIndex OBJECT-TYPE
    SYNTAX      PhysicalIndex 
    MAX-ACCESS  read-only
    STATUS      current
    DESCRIPTION
           "Entity Index from ENTITY-MIB for this port."
    ::= { cmEthernetAccPortEntry 3 }

-- State Management params
cmEthernetAccPortAdminState OBJECT-TYPE
    SYNTAX      AdminState 
    MAX-ACCESS  read-write
    STATUS      current
    DESCRIPTION
            "This object represents the Administrative State of the Ethernet 
             Access Port."
    ::= { cmEthernetAccPortEntry 4 }

cmEthernetAccPortOperationalState OBJECT-TYPE
    SYNTAX      OperationalState 
    MAX-ACCESS  read-only
    STATUS      current
    DESCRIPTION
            "This object represents the Operational State of the Ethernet 
             Access Port."
    ::= { cmEthernetAccPortEntry 5 }

cmEthernetAccPortSecondaryState OBJECT-TYPE
    SYNTAX      SecondaryState 
    MAX-ACCESS  read-only
    STATUS      current
    DESCRIPTION
            "This object represents the Secondary State of the Ethernet 
             Access Port."
    ::= { cmEthernetAccPortEntry 6 }

-- Generic Port params
cmEthernetAccPortMTU OBJECT-TYPE
    SYNTAX      Integer32 
    MAX-ACCESS  read-write
    STATUS      current
    DESCRIPTION
            "This object provides the MTU on the Ethernet Access Port.
             The object is made read-write for FSP150CC devices."
    ::= { cmEthernetAccPortEntry 7 }

cmEthernetAccPortMediaType OBJECT-TYPE
    SYNTAX     EthernetMediaType
    MAX-ACCESS read-write
    STATUS     current
    DESCRIPTION
            "This object represents the type of Ethernet Media on the 
             Ethernet Access Port."
    ::= { cmEthernetAccPortEntry 8 }

cmEthernetAccPortConfigSpeed OBJECT-TYPE
    SYNTAX     EthernetPortSpeed
    MAX-ACCESS read-write
    STATUS     current
    DESCRIPTION
            "This object allows to configure the speed of the 
             Ethernet Access Port."
    ::= { cmEthernetAccPortEntry 9 }

cmEthernetAccPortNegotiatedSpeed OBJECT-TYPE
    SYNTAX     EthernetPortSpeed
    MAX-ACCESS read-only
    STATUS     current
    DESCRIPTION
            "This object provides the negotiated speed of the 
             Ethernet Access Port."
    ::= { cmEthernetAccPortEntry 10 }

cmEthernetAccPortMDIXType OBJECT-TYPE
    SYNTAX     CmEthernetMDIXType
    MAX-ACCESS read-write
    STATUS     current
    DESCRIPTION
            "This object allows management of MDIX property on  
             Ethernet Access Port."
    ::= { cmEthernetAccPortEntry 11 }

cmEthernetAccPortJumboFramesEnabled OBJECT-TYPE
    SYNTAX     TruthValue
    MAX-ACCESS read-write
    STATUS     current
    DESCRIPTION
            "This object allows enabling/disabling jumbo frames support on 
             the Ethernet Access Port.  This object is only applicable for
             Ethernet Access Port on R3.1CM NTU Card."
    ::= { cmEthernetAccPortEntry 12 }

cmEthernetAccPortSfpVendorName OBJECT-TYPE
    SYNTAX  DisplayString (SIZE (0..16)) 
    MAX-ACCESS read-only
    STATUS     current
    DESCRIPTION
            "This object provides the vendor name of the SFP. 
             This is applicable when cmEthernetAccPortMediaType is fiber or coppersfp."
     ::= { cmEthernetAccPortEntry 13 }

cmEthernetAccPortSfpPartNumber OBJECT-TYPE
    SYNTAX  DisplayString (SIZE (0..16)) 
    MAX-ACCESS read-only
    STATUS     current
    DESCRIPTION
            "This object provides the part number of the SFP. 
             This is applicable when cmEthernetAccPortMediaType is fiber or coppersfp."
     ::= { cmEthernetAccPortEntry 14 }

cmEthernetAccPortSfpSerialNumber OBJECT-TYPE
    SYNTAX  DisplayString (SIZE (0..32)) 
    MAX-ACCESS read-only
    STATUS     current
    DESCRIPTION
            "This object provides the serial number of the SFP.  
             This is applicable when cmEthernetAccPortMediaType is fiber or coppersfp."
     ::= { cmEthernetAccPortEntry 15 }

cmEthernetAccPortSfpDateOfManufacture OBJECT-TYPE
    SYNTAX     DateAndTime 
    MAX-ACCESS read-only
    STATUS     current
    DESCRIPTION
            "This object provides the date of manufacture of the SFP.
             This is applicable when cmEthernetAccPortMediaType is fiber or coppersfp."
     ::= { cmEthernetAccPortEntry 16 }

cmEthernetAccPortSfpConnectorValue OBJECT-TYPE
    SYNTAX     SfpConnectorValue 
    MAX-ACCESS read-only
    STATUS     current
    DESCRIPTION
            "This object provides the SFP connector value.
             This is applicable when cmEthernetAccPortMediaType is fiber or coppersfp."
     ::= { cmEthernetAccPortEntry 17 }

-- EtherJack Diagnosis params
cmEthernetAccPortInitiateDiag  OBJECT-TYPE
    SYNTAX     CmEthernetDiagAction
    MAX-ACCESS read-write
    STATUS     current
    DESCRIPTION
            "This object allows to initiate Etherjack diagnosis on the
             Ethernet Access Port."
     ::= { cmEthernetAccPortEntry 18 }

cmEthernetAccPortDiagnosePair1Cond OBJECT-TYPE
    SYNTAX     CmDiagCableCondType
    MAX-ACCESS read-only
    STATUS     current
    DESCRIPTION
            "This object provides diagnosis results for the cable Pair 1
             on Ethernet Access Port."
     ::= { cmEthernetAccPortEntry 19 }

cmEthernetAccPortDiagnosePair2Cond OBJECT-TYPE
    SYNTAX     CmDiagCableCondType
    MAX-ACCESS read-only
    STATUS     current
    DESCRIPTION
            "This object provides diagnosis results for the cable Pair 2
             on Ethernet Access Port."
     ::= { cmEthernetAccPortEntry 20 }

cmEthernetAccPortDiagnosePair3Cond OBJECT-TYPE
    SYNTAX     CmDiagCableCondType
    MAX-ACCESS read-only
    STATUS     current
    DESCRIPTION
            "This object provides diagnosis results for the cable Pair 3
             on Ethernet Access Port."
     ::= { cmEthernetAccPortEntry 21 }

cmEthernetAccPortDiagnosePair4Cond OBJECT-TYPE
    SYNTAX     CmDiagCableCondType
    MAX-ACCESS read-only
    STATUS     current
    DESCRIPTION
            "This object provides diagnosis results for the cable Pair 4
             on Ethernet Access Port."
     ::= { cmEthernetAccPortEntry 22 }

cmEthernetAccPortDiagnoseAutoNegCond OBJECT-TYPE
    SYNTAX     CmDiagAutoNegCondType
    MAX-ACCESS read-only
    STATUS     current
    DESCRIPTION
            "This object provides auto negotiation results of the diagnosis
             test on Ethernet Access Port."
     ::= { cmEthernetAccPortEntry 23 }

cmEthernetAccPortDiagnoseLpbkCond OBJECT-TYPE
    SYNTAX     CmDiagLpbkCondType
    MAX-ACCESS read-only
    STATUS     current
    DESCRIPTION
            "This object provides port loopback results of the diagnosis
             test on Ethernet Access Port."
     ::= { cmEthernetAccPortEntry 24 }

cmEthernetAccPortDiagnoseEfmLpbkCond OBJECT-TYPE
    SYNTAX     CmDiagEfmOamLpbkCondType
    MAX-ACCESS read-only
    STATUS     current
    DESCRIPTION
            "This object provides remote EFM loopback results of the diagnosis
             test on Ethernet Access Port."
     ::= { cmEthernetAccPortEntry 25 }

cmEthernetAccPortDiagnoseResult OBJECT-TYPE
    SYNTAX  DisplayString (SIZE (0..256)) 
    MAX-ACCESS read-only
    STATUS     current
    DESCRIPTION
            "This object provides results of the diagnosis
             test in string form on Ethernet Access Port."
     ::= { cmEthernetAccPortEntry 26 }

cmEthernetAccPortDiagnoseTestStatus OBJECT-TYPE
    SYNTAX  CmDiagTestStatus 
    MAX-ACCESS read-only
    STATUS     current
    DESCRIPTION
            "This object provides the current status of the diagnosis
             test on Ethernet Access Port."
     ::= { cmEthernetAccPortEntry 27 }

cmEthernetAccPortDiagnoseTestTime OBJECT-TYPE
    SYNTAX  DateAndTime 
    MAX-ACCESS read-only
    STATUS     current
    DESCRIPTION
       "This object provides the time when diagnosis test was last executed."
     ::= { cmEthernetAccPortEntry 28 }

-- Ethernet Loopback params
cmEthernetAccPortLoopbackConfig OBJECT-TYPE
    SYNTAX     CmLoopbackType
    MAX-ACCESS read-write
    STATUS     current
    DESCRIPTION
            "This object allows to initiate loopbacks on 
             on the Ethernet Access Port."
     ::= { cmEthernetAccPortEntry 29 }

cmEthernetAccPortLoopbackStatus OBJECT-TYPE
    SYNTAX     CmLoopbackType
    MAX-ACCESS read-only
    STATUS     current
    DESCRIPTION
            "This object provides status of the current loopback 
             on the Ethernet Access Port."
     ::= { cmEthernetAccPortEntry 30 }

cmEthernetAccPortLoopbackTime OBJECT-TYPE                   
    SYNTAX     Integer32 (2..300)
    MAX-ACCESS read-write
    STATUS     current
    DESCRIPTION
            "This object allows to specify time for timed-loopbacks on 
             on the Ethernet Access Port."
     ::= { cmEthernetAccPortEntry 31 }

cmEthernetAccPortLoopbackSwapSADA OBJECT-TYPE
    SYNTAX     CmSwapSADAType
    MAX-ACCESS read-write
    STATUS     current
    DESCRIPTION
            "This object allows to specify whether or not the loopbacked
             frame will have the Source Address and Destination Address
             swapped."
     ::= { cmEthernetAccPortEntry 32 }

cmEthernetAccPortOuterVlanLoopbackMask OBJECT-TYPE
    SYNTAX     INTEGER (0..16)
    MAX-ACCESS read-write
    STATUS     current
    DESCRIPTION
             "This object allows specification of the outer VLANs to be 
              looped back when port is in vlan(terminal/facility) 
              loopback configuration. Only 3 VLANs can be specified 
              for vlan loopback. The various bit positions are:
                   1         Outer VLAN 1 Loopback Enabled
                   2         Outer VLAN 2 Loopback Enabled
                   4         Outer VLAN 3 Loopback Enabled
              Value of 0 means that no VLANs are enabled."
     ::= { cmEthernetAccPortEntry 33 }

cmEthernetAccPortOuterVlanLoopback1 OBJECT-TYPE              
    SYNTAX  DisplayString (SIZE (0..6)) 
    MAX-ACCESS read-write
    STATUS     current
    DESCRIPTION
             "This object allows specification of the outer VLAN 1 to be 
              looped back when port is in vlan(terminal/facility) 
              loopback configuration. This is valid only if the
              corresponding bit in cmEthernetAccPortOuterVlanLoopbackMask
              is set.  The value to be specified should be in the form 
              X-Y where X is the VLAN Id and Y is the VLAN Priority.  
              If Y is specified as a *, all Priorities (0 to 7) 
              are looped back."
     ::= { cmEthernetAccPortEntry 34 }

cmEthernetAccPortOuterVlanLoopback2 OBJECT-TYPE
    SYNTAX  DisplayString (SIZE (0..6)) 
    MAX-ACCESS read-write
    STATUS     current
    DESCRIPTION
             "This object allows specification of the outer VLAN 2 to be 
              looped back when port is in vlan(terminal/facility) 
              loopback configuration. This is valid only if the
              corresponding bit in cmEthernetAccPortOuterVlanLoopbackMask
              is set.  The value to be specified should be in the form 
              X-Y where X is the VLAN Id and Y is the VLAN Priority.  
              If Y is specified as a *, all Priorities (0 to 7) 
              are looped back."
     ::= { cmEthernetAccPortEntry 35 }

cmEthernetAccPortOuterVlanLoopback3 OBJECT-TYPE
    SYNTAX  DisplayString (SIZE (0..6)) 
    MAX-ACCESS read-write
    STATUS     current
    DESCRIPTION
             "This object allows specification of the outer VLAN 3 to be 
              looped back when port is in vlan(terminal/facility) 
              loopback configuration. This is valid only if the
              corresponding bit in cmEthernetAccPortOuterVlanLoopbackMask
              is set.  The value to be specified should be in the form 
              X-Y where X is the VLAN Id and Y is the VLAN Priority.  
              If Y is specified as a *, all Priorities (0 to 7) 
              are looped back."
     ::= { cmEthernetAccPortEntry 36 }

cmEthernetAccPortInnerVlanLoopbackMask OBJECT-TYPE
    SYNTAX     INTEGER (0..16)
    MAX-ACCESS read-write
    STATUS     current
    DESCRIPTION
             "This object allows specification of the inner VLANs to be 
              looped back when port is in vlan(terminal/facility) 
              loopback configuration. Only 3 VLANs can be specified 
              for vlan loopback. The various bit positions are:
                   1         Inner VLAN 1 Loopback Enabled
                   2         Inner VLAN 2 Loopback Enabled
                   4         Inner VLAN 3 Loopback Enabled
              Value of 0 means that no VLANs are enabled."
     ::= { cmEthernetAccPortEntry 37 }

cmEthernetAccPortInnerVlanLoopback1 OBJECT-TYPE 
    SYNTAX  DisplayString (SIZE (0..6)) 
    MAX-ACCESS read-write
    STATUS     current
    DESCRIPTION
             "This object allows specification of the inner VLAN 1 to be 
              looped back when port is in vlan(terminal/facility) 
              loopback configuration. This is valid only if the
              corresponding bit in cmEthernetAccPortInnerVlanLoopbackMask
              is set.  The value to be specified should be in the form 
              X-Y where X is the VLAN Id and Y is the VLAN Priority.  
              If Y is specified as a *, all Priorities (0 to 7) 
              are looped back."
     ::= { cmEthernetAccPortEntry 38 }

cmEthernetAccPortInnerVlanLoopback2 OBJECT-TYPE
    SYNTAX  DisplayString (SIZE (0..6)) 
    MAX-ACCESS read-write
    STATUS     current
    DESCRIPTION
             "This object allows specification of the inner VLAN 2 to be 
              looped back when port is in vlan(terminal/facility) 
              loopback configuration. This is valid only if the
              corresponding bit in cmEthernetAccPortInnerVlanLoopbackMask
              is set.  The value to be specified should be in the form 
              X-Y where X is the VLAN Id and Y is the VLAN Priority.  
              If Y is specified as a *, all Priorities (0 to 7) 
              are looped back."
     ::= { cmEthernetAccPortEntry 39 }

cmEthernetAccPortInnerVlanLoopback3 OBJECT-TYPE
    SYNTAX  DisplayString (SIZE (0..6)) 
    MAX-ACCESS read-write
    STATUS     current
    DESCRIPTION
             "This object allows specification of the inner VLAN 3 to be 
              looped back when port is in vlan(terminal/facility) 
              loopback configuration. This is valid only if the
              corresponding bit in cmEthernetAccPortInnerVlanLoopbackMask
              is set.  The value to be specified should be in the form 
              X-Y where X is the VLAN Id and Y is the VLAN Priority.  
              If Y is specified as a *, all Priorities (0 to 7) 
              are looped back."
     ::= { cmEthernetAccPortEntry 40 }


-- Link Loss Forwarding params 
cmEthernetAccPortLinkLossFwdEnabled OBJECT-TYPE
    SYNTAX     TruthValue
    MAX-ACCESS read-write
    STATUS     current
    DESCRIPTION
             "This object allows enabling/disabling link loss forwarding 
              on the Ethernet Access Port." 
     ::= { cmEthernetAccPortEntry 41 }

cmEthernetAccPortLinkLossFwdSignalType  OBJECT-TYPE
    SYNTAX     CmLinkLossFwdSignalType
    MAX-ACCESS read-write
    STATUS     deprecated
    DESCRIPTION
             "This object allows definition of the link loss forwarding
              signalling type.  This is applicable only if 
              cmEthernetAccPortLinkLossFwdEnabled is enabled.
              This object is applicable only for FSP150CM Release 3.1.
              This object is deprecated henceforth. 
              Link Loss signalling will be supported using the object
              cmEthernetAccPortLinkLossFwdTxActionType."
     ::= { cmEthernetAccPortEntry 42 }

cmEthernetAccPortLinkLossFwdTriggerTypes  OBJECT-TYPE
    SYNTAX     CmLinkLossFwdTriggerTypes
    MAX-ACCESS read-write
    STATUS     current
    DESCRIPTION
             "This object allows definition of the link loss forwarding
              trigger types.  This is applicable only if 
              cmEthernetAccPortLinkLossFwdEnabled is enabled."
     ::= { cmEthernetAccPortEntry 43 }

cmEthernetAccPortLinkLossFwdDelay OBJECT-TYPE                
    SYNTAX     Integer32
    MAX-ACCESS read-write
    STATUS     current
    DESCRIPTION
             "This object allows specification of the delay between
              detection of link loss and signalling of link loss forwarding. 
              Time specified is in seconds."
     ::= { cmEthernetAccPortEntry 44 }

cmEthernetAccPortLinkLossFwdActive OBJECT-TYPE 
    SYNTAX     TruthValue
    MAX-ACCESS read-only
    STATUS     current
    DESCRIPTION
             "This object provides the link loss forwarding status indicating
              if link loss forwarding is currently being signaled via 
              the port." 
     ::= { cmEthernetAccPortEntry 45 }

cmEthernetAccPortLinkLossFwdPartnerEnabled OBJECT-TYPE 
    SYNTAX     TruthValue
    MAX-ACCESS read-only
    STATUS     current
    DESCRIPTION
             "This object provides the indication of a link partners ability
              to support link loss forwarding via EFM, i.e. from
              received organization specific OAMPDUs." 
     ::= { cmEthernetAccPortEntry 46 }

cmEthernetAccPortLinkLossFwdLocalLinkId OBJECT-TYPE 
    SYNTAX     Integer32
    MAX-ACCESS read-write
    STATUS     current
    DESCRIPTION
             "This object allows configuration of the Local Link Id on 
              Ethernet access port." 
     ::= { cmEthernetAccPortEntry 47 }

cmEthernetAccPortLinkLossFwdRemoteLinkIds OBJECT-TYPE 
    SYNTAX     CmRemoteLinkIds 
    MAX-ACCESS read-write
    STATUS     current
    DESCRIPTION
             "This object allows enabling/disabling Remote Link Ids 
              on Ethernet access port. By setting the appropriate bit
              positions, the Ethernet access port is able to distinguish
              the remote side client ports from the Remote Link Down
              PDUs coming from remote end."
     ::= { cmEthernetAccPortEntry 48 }

-- OAM params
cmEthernetAccPortOamId  OBJECT-TYPE
    SYNTAX     Integer32 
    MAX-ACCESS read-only
    STATUS     current
    DESCRIPTION
             "OAM Id.  This is unique EFM OAM sublayer port id." 
     ::= { cmEthernetAccPortEntry 49 }

cmEthernetAccPortOamAdminDisposition  OBJECT-TYPE
    SYNTAX     CmControlProtocolDispType
    MAX-ACCESS read-write 
    STATUS     deprecated
    DESCRIPTION
             "Ethernet Access Port's EFM OAM Disposition.
              This object is applicable only for FSP150CM Release 3.1.
              This object is deprecated henceforth.  
              With FSP150CC Release 4.1, this property is managed using 
              the Control Protocol Disposition tables."
     ::= { cmEthernetAccPortEntry 50 }

cmEthernetAccPortOamDiscoveryState  OBJECT-TYPE
    SYNTAX     CmOamDiscoveryState
    MAX-ACCESS read-only
    STATUS     current
    DESCRIPTION
             "Ethernet Access Port's OAM discovery state." 
     ::= { cmEthernetAccPortEntry 51 }

cmEthernetAccPortOamLocalVarRtrvsEnabled  OBJECT-TYPE
    SYNTAX     TruthValue
    MAX-ACCESS read-only
    STATUS     current
    DESCRIPTION
             "This object allows specification of whether the Ethernet
              Access Port supports sending variable response OAMPDUs." 
     ::= { cmEthernetAccPortEntry 52 }

cmEthernetAccPortOamLocalLinkEventsEnabled  OBJECT-TYPE
    SYNTAX     TruthValue 
    MAX-ACCESS read-only
    STATUS     current
    DESCRIPTION
             "This object allows specification of whether the Ethernet
              Access Port supports interpreting Link Events."
     ::= { cmEthernetAccPortEntry 53 }

cmEthernetAccPortOamLocalOamLoopbacksSupported  OBJECT-TYPE
    SYNTAX     TruthValue 
    MAX-ACCESS read-write
    STATUS     current
    DESCRIPTION
             "This object allows specification of whether the Ethernet
              Access Port is capable of OAM remote loopback mode."
     ::= { cmEthernetAccPortEntry 54 }

cmEthernetAccPortOamLocalUnidirSupportEnabled  OBJECT-TYPE
    SYNTAX     TruthValue 
    MAX-ACCESS read-only
    STATUS     current
    DESCRIPTION
             "This object allows specification of whether the Ethernet
              Access Port is capable of sending OAMPDUs when the receive path 
              is non-operational."
     ::= { cmEthernetAccPortEntry 55 }

cmEthernetAccPortOamLocalMaxPDUSize  OBJECT-TYPE
    SYNTAX     Integer32
    MAX-ACCESS read-only
    STATUS     current
    DESCRIPTION
             "This object represents the largest OAMPDU, in octets, 
              supported by the Ethernet Access Port.  This value is
              compared to the remote Maximum PDU Size and the smaller of 
              the two is used." 
     ::= { cmEthernetAccPortEntry 56 }

cmEthernetAccPortOamLocalMode OBJECT-TYPE
    SYNTAX     CmOamMode 
    MAX-ACCESS read-write
    STATUS     current
    DESCRIPTION
             "This object allows to configure the OAM sublayer entity in
              either Active or Passive mode." 
     ::= { cmEthernetAccPortEntry 57 }

cmEthernetAccPortOamRemoteMacAddress OBJECT-TYPE
    SYNTAX     MacAddress
    MAX-ACCESS read-only
    STATUS     current
    DESCRIPTION
             "This object allows retrieval of the Remote Mac Address." 
     ::= { cmEthernetAccPortEntry 58 }

cmEthernetAccPortOamRemoteVarRtrvsEnabled OBJECT-TYPE
    SYNTAX     TruthValue
    MAX-ACCESS read-only
    STATUS     current
    DESCRIPTION
             "This object allows retrieval of whether the remote OAM 
              entity supports sending variable response OAMPDUs." 
     ::= { cmEthernetAccPortEntry 59 }

cmEthernetAccPortOamRemoteLinkEventsEnabled OBJECT-TYPE
    SYNTAX     TruthValue 
    MAX-ACCESS read-only
    STATUS     current
    DESCRIPTION
             "This object allows retrieval of whether the remote OAM 
              entity supports interpreting Link Events."
     ::= { cmEthernetAccPortEntry 60 }

cmEthernetAccPortOamRemoteOamLoopbacksSupported OBJECT-TYPE
    SYNTAX     TruthValue 
    MAX-ACCESS read-only
    STATUS     current
    DESCRIPTION
             "This object allows retrieval of whether the remote OAM 
              entity supports OAM remote loopback mode."
     ::= { cmEthernetAccPortEntry 61 }

cmEthernetAccPortOamRemoteUnidirSupportEnabled OBJECT-TYPE
    SYNTAX     TruthValue 
    MAX-ACCESS read-only
    STATUS     current
    DESCRIPTION
             "This object allows retrieval of whether the remote 
              OAM entity is capable of sending OAMPDUs when the receive path 
              is non-operational."
     ::= { cmEthernetAccPortEntry 62 }

cmEthernetAccPortOamRemoteMaxPDUSize OBJECT-TYPE
    SYNTAX     Integer32
    MAX-ACCESS read-only
    STATUS     current
    DESCRIPTION
             "This object allows retrieval of the remote OAM 
              entity maximum OAMPDU size."
     ::= { cmEthernetAccPortEntry 63 }

cmEthernetAccPortOamRemoteMode OBJECT-TYPE
    SYNTAX     CmOamMode 
    MAX-ACCESS read-only
    STATUS     current
    DESCRIPTION
             "This object allows to retrieve whether the remote OAM 
              sublayer entity is either in Active or Passive mode." 
     ::= { cmEthernetAccPortEntry 64 }


-- Ethernet Port Service params
cmEthernetAccPortMode OBJECT-TYPE 
    SYNTAX     CmEthernetSvcPortMode 
    MAX-ACCESS read-write
    STATUS     current
    DESCRIPTION
             "This object allows specification of whether the 
              Ethernet Access Port is in a connection-oriented 
              (offering VLAN based services) mode or connection-less 
              (offering MAC based services) mode." 
     ::= { cmEthernetAccPortEntry 65 }

cmEthernetAccPortSvcType  OBJECT-TYPE 
    SYNTAX     CmEthernetSvcType 
    MAX-ACCESS read-write
    STATUS     current
    DESCRIPTION
             "This object allows specification of whether the 
              Ethernet Access Port provides transparent port based services,
              or multi-flow VLAN based services." 
     ::= { cmEthernetAccPortEntry 66 }

-- Ethernet Port Traffic params
cmEthernetAccPortRxPauseDisposition OBJECT-TYPE
    SYNTAX     CmControlProtocolDispType
    MAX-ACCESS read-write 
    STATUS     deprecated
    DESCRIPTION
         "This object allows management of RX pause frames on 
          Ethernet Access port. This object is applicable only 
          for FSP150CM Release 3.1.
          This object is deprecated henceforth.  With FSP150CC Release 4.1,
          this property is managed using the Control Protocol
          Disposition tables."
     ::= { cmEthernetAccPortEntry 67 }

cmEthernetAccPortTxPauseEnabled OBJECT-TYPE
    SYNTAX     TruthValue
    MAX-ACCESS read-write
    STATUS     current
    DESCRIPTION
         "This object allows enabling/disabling transmit pause frames on
          Ethernet Access port."
     ::= { cmEthernetAccPortEntry 68 }

cmEthernetAccPortAfpType OBJECT-TYPE
    SYNTAX     CmAfpType
    MAX-ACCESS read-write
    STATUS     current
    DESCRIPTION
         "This object allows specification of the Acceptable Frame Policy on
          Ethernet Access port. Users can specify whether the port supports
          only tagged frames, only untagged frames or both tagged and 
          untagged frames."
     ::= { cmEthernetAccPortEntry 69 }

-- Generic Ethernet Port params
cmEthernetAccPortMDIXStatus OBJECT-TYPE
    SYNTAX     CmEthernetMDIXType
    MAX-ACCESS read-only
    STATUS     current
    DESCRIPTION
         "This object provides the current MDIX status of the 
          Ethernet Access port."
     ::= { cmEthernetAccPortEntry 70 }

cmEthernetAccPortSfpReach OBJECT-TYPE
    SYNTAX     Integer32
    MAX-ACCESS read-only
    STATUS     current
    DESCRIPTION
         "This object provides the SFP Reach in meters.
          This is applicable when cmEthernetAccPortMediaType is fiber or coppersfp."
     ::= { cmEthernetAccPortEntry 71 }

cmEthernetAccPortSfpLaserWaveLength OBJECT-TYPE
    SYNTAX     Integer32
    MAX-ACCESS read-only
    STATUS     current
    DESCRIPTION
         "This object provides the SFP Laser Wave Length in nano meters.
          This is applicable only when cmEthernetAccPortMediaType is fiber."
     ::= { cmEthernetAccPortEntry 72 }

cmEthernetAccPortSfpMediaType OBJECT-TYPE
    SYNTAX     SfpMediaType
    MAX-ACCESS read-only
    STATUS     current
    DESCRIPTION
         "This object provides the SFP Media Type.
          This is applicable when cmEthernetAccPortMediaType is fiber or coppersfp."
     ::= { cmEthernetAccPortEntry 73 }

cmEthernetAccPortOamEnabled  OBJECT-TYPE
    SYNTAX     TruthValue
    MAX-ACCESS read-write 
    STATUS     current
    DESCRIPTION
             "This object allows to manage the EFM OAM on Ethernet Access Port."
     ::= { cmEthernetAccPortEntry 74 }

cmEthernetAccPortOamAdminState OBJECT-TYPE
    SYNTAX     CmOamAdminState
    MAX-ACCESS read-only 
    STATUS     current
    DESCRIPTION
             "This object provides the EFM OAM Admin State."
     ::= { cmEthernetAccPortEntry 75 }

-- Ethernet Port Traffic params
cmEthernetAccPortShapingEnabled OBJECT-TYPE
    SYNTAX     TruthValue
    MAX-ACCESS read-write
    STATUS     current
    DESCRIPTION
         "This object allows to manage the Access Port Shaping.
          When enabled, values in cmEthernetAccPortShapedSpeedLo and
          cmEthernetAccPortShapedSpeedHi are applicable."
     ::= { cmEthernetAccPortEntry 76 }

cmEthernetAccPortShapedSpeedLo OBJECT-TYPE
    SYNTAX     Unsigned32
    MAX-ACCESS read-write
    STATUS     current
    DESCRIPTION
         "This object allows to specify the lower 32 bits of 
          the Access Port Shaped speed. This value is applicable
          when cmEthernetAccPortShapingEnabled is enabled."
     ::= { cmEthernetAccPortEntry 77 }

cmEthernetAccPortShapedSpeedHi OBJECT-TYPE
    SYNTAX     Unsigned32
    MAX-ACCESS read-write
    STATUS     current
    DESCRIPTION
         "This object allows to specify the higher 32 bits of 
          the Access Port Shaped speed. This value is applicable
          when cmEthernetAccPortShapingEnabled is enabled."
     ::= { cmEthernetAccPortEntry 78 }

cmEthernetAccPortQinQEtherType OBJECT-TYPE
    SYNTAX     Unsigned32
    MAX-ACCESS read-write
    STATUS     current
    DESCRIPTION
         "This object allows to specify the Q-in-Q Ether Type 
          on the Access Port.  Setting this value to 0 will disable
          the Q-in-Q override on the Access Port."
     ::= { cmEthernetAccPortEntry 79 }

cmEthernetAccPortRxPauseEnabled OBJECT-TYPE
    SYNTAX     TruthValue
    MAX-ACCESS read-write
    STATUS     current
    DESCRIPTION
         "This object allows to enable/disable the RX PAUSE 
          on the Access Port. This object is not applicable for FSP150CM NTU Card.
          On NTU Card cmEthernetAccPortRxPauseDisposition object should be used to
          provision RxPause disposition."
     ::= { cmEthernetAccPortEntry 80 }

-- EtherJack Diagnosis params
cmEthernetAccPortAutoDiagEnabled OBJECT-TYPE
    SYNTAX     TruthValue
    MAX-ACCESS read-write
    STATUS     current
    DESCRIPTION
         "This object allows to enable or disable the automatic 
          Cable Diagnostic tests when the cable is removed from the port."
     ::= { cmEthernetAccPortEntry 81 }

-- Link Loss Forwarding params
cmEthernetAccPortLinkLossFwdTxActionType OBJECT-TYPE
    SYNTAX     CmLinkLossFwdTxActionType
    MAX-ACCESS read-write
    STATUS     current
    DESCRIPTION
         "This object allows to specify the Access Port's behavior when
          link loss forwarding trigger events occur on the Network Port.
          This provides ability to configure per access port LLF behavior." 
     ::= { cmEthernetAccPortEntry 82 }

cmEthernetAccPortLinkLossFwdRxRLDLinkIds OBJECT-TYPE
    SYNTAX     CmRemoteLinkIds
    MAX-ACCESS read-only
    STATUS     current
    DESCRIPTION
         "This object provides the received Remote Link IDs in 
          EFM RLD messages on the Access Port." 
     ::= { cmEthernetAccPortEntry 83 }

--Ethernet Port Services params
cmEthernetAccPortN2AVlanTrunkingEnabled OBJECT-TYPE
    SYNTAX     TruthValue
    MAX-ACCESS read-write
    STATUS     current
    DESCRIPTION
         "This object allows to enable or disable the VLAN trunking on
          Ethernet Access port. Disabling VLAN trunking removes all
          VLAN tags before transmitting traffic out of the access port. 
          This object is only applicable for connection-oriented, 
          evpl service type."
     ::= { cmEthernetAccPortEntry 84 }

cmEthernetAccPortA2NPushPVIDEnabled OBJECT-TYPE
    SYNTAX     TruthValue
    MAX-ACCESS read-write
    STATUS     current
    DESCRIPTION
         "This object allows to specify whether cmEthernetAccPortPortVlanId
          value will be PUSHed on untagged frames or not in the 
          Access to Network direction.  This object is only applicable 
          for connection-oriented, evpl service type."
     ::= { cmEthernetAccPortEntry 85 }

cmEthernetAccPortN2APopPVIDEnabled OBJECT-TYPE
    SYNTAX     TruthValue
    MAX-ACCESS read-write
    STATUS     current
    DESCRIPTION
         "This object allows to specify whether cmEthernetAccPortPortVlanId
          value will be POPed in the 
          Network to Access direction.  This object is only applicable 
          for connection-oriented, evpl service type."
     ::= { cmEthernetAccPortEntry 86 }

cmEthernetAccPortPortVlanId OBJECT-TYPE
    SYNTAX     VlanId
    MAX-ACCESS read-write
    STATUS     current
    DESCRIPTION
         "This object allows to specify the Ethernet Access Port VLAN Id 
          to PUSH on untagged frames in the Access to Network
          direction.  This object is only applicable for connection-oriented,
          evpl service type, when cmEthernetAccPortA2NPushPVIDEnabled 
          is set to true."
     ::= { cmEthernetAccPortEntry 87 }

cmEthernetAccPortPortVlanPriority OBJECT-TYPE
    SYNTAX     VlanPriority
    MAX-ACCESS read-write
    STATUS     current
    DESCRIPTION
         "This object allows to specify the Ethernet Access Port VLAN Priority 
          for the PUSHed VLAN tag (specified by cmEthernetAccPortPortVlanId) 
          on untagged frames in the Access to Network direction.  
          This object is only applicable for connection-oriented,
          evpl service type, when cmEthernetAccPortA2NPushPVIDEnabled 
          is set to true."
     ::= { cmEthernetAccPortEntry 88 }

cmEthernetAccPortPrioMapMode OBJECT-TYPE
    SYNTAX     PriorityMapMode
    MAX-ACCESS read-write
    STATUS     current
    DESCRIPTION
         "This object allows to specify the Ethernet Access Port 
          Priority Mapping Mode used for classification of frames.
          This object is only applicable for connection-oriented,
          evpl service type."
     ::= { cmEthernetAccPortEntry 89 }

--Synchronous Port params
cmEthernetAccPortSyncEEnabled OBJECT-TYPE 
    SYNTAX     TruthValue
    MAX-ACCESS read-write
    STATUS     current
    DESCRIPTION
         "This object allows to specify whether the Ethernet Access Port 
          can be enabled/disabled for Synchronous Ethernet. This object
          is only applicable for Synchronous Ethernet capable ports.
          When enabled, on receive side 
            -port can extract the frequency of its input signal
             and pass the recovered clock to the system clock
            -port processes the ESMC(Ethernet Synchronization Messaging
             Channel) and extracts the QL (when also QL enabled)   
            -port is eligible to be selected as a system clock reference
          When enabled, on transmit side 
            -port's transmit clock is locked to the system clock
            -port generates an ESMC to generate a QL (when also QL enabled)

          When disabled, on receive side,
            -port does not pass the recovered clock to the system clock 
            -port does not process the ESMC (if present) 
            -port is not eligible to be selected as a 
                     system clock reference
          When disabled, on transmit side 
            -port's output frequency may be synchronized to the system clock
            -port does not generate an ESMC."
     ::= { cmEthernetAccPortEntry 90 }

cmEthernetAccPortQLModeEnabled OBJECT-TYPE 
    SYNTAX     TruthValue
    MAX-ACCESS read-write
    STATUS     current
    DESCRIPTION
         "This object allows to specify whether the Ethernet Access Port 
          can be enabled/disabled for QL Mode. This object
          is only applicable for Synchronous Ethernet capable ports,
          when cmEthernetAccPortQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { cmEthernetAccPortEntry 91 }

cmEthernetAccPortExpectedQL OBJECT-TYPE 
    SYNTAX     SSMQualityLevel
    MAX-ACCESS read-write
    STATUS     current
    DESCRIPTION
         "This object allows to specify the expected QL when the 
          Ethernet Access Port is enabled for QL Mode. This object
          is only applicable for Synchronous Ethernet capable ports,
          when cmEthernetAccPortQLModeEnabled is set to true.
          This object allows the user to set a minimum
          expected received Quality Level on the port. The valid values
          depend upon the SYNC entity's Network Clock Type. A value of
          None represents that a minimum Quality Level is not expected. 
          The default value shall be None."
     ::= { cmEthernetAccPortEntry 92 }

cmEthernetAccPortAssumedQL OBJECT-TYPE 
    SYNTAX     SSMQualityLevel
    MAX-ACCESS read-write
    STATUS     current
    DESCRIPTION
         "This object allows to specify the assumed QL on the 
          Ethernet Access Port. This object is only applicable for 
          Synchronous Ethernet capable ports. 
          The Assumed QL is only meaningful if the Network Clock Type
          (see fsp150cm-sync.mib) is option1 and the 
          port's QL Mode is disabled and the port is being used as 
          an input reference source. Under these conditions, 
          the specified QL value is assumed to be the Quality Level of the
          non-failed reference."
     ::= { cmEthernetAccPortEntry 93 }

cmEthernetAccPortReceivedQL OBJECT-TYPE 
    SYNTAX     SSMQualityLevel
    MAX-ACCESS read-only
    STATUS     current
    DESCRIPTION
         "This object provides the Received QL value for the Ethernet port. 
          If the Ethernet port's QL Mode is disabled, then the received 
          QL value is not applicable.This object is only applicable for 
          Synchronous Ethernet capable ports."
     ::= { cmEthernetAccPortEntry 94 }

cmEthernetAccPortTransmitQL OBJECT-TYPE 
    SYNTAX     SSMQualityLevel
    MAX-ACCESS read-only
    STATUS     current
    DESCRIPTION
         "This object provides the Transmitted QL value for the Ethernet port. 
          If the Ethernet port's QL Mode is disabled, then the received 
          QL value is not applicable. This object is only applicable for 
          Synchronous Ethernet capable ports."
     ::= { cmEthernetAccPortEntry 95 }

cmEthernetAccPortDeiEnable OBJECT-TYPE
    SYNTAX      TruthValue
    MAX-ACCESS  read-write
    STATUS      current
    DESCRIPTION
        "This is a port level control to reset the DEI 
         (Drop Eligibility Indicator) bit in the S-Tag,
         if the downstream equipment supports S-Tag TPID (EtherType) but 
         cannot handle DEI bit set. In the receive direction,
         it uses the S-TAG DEI when enabled, else ignores it."
    ::= { cmEthernetAccPortEntry 96 }

cmEthernetAccPortPcpDEEncType OBJECT-TYPE
    SYNTAX      PcpDEEncType
    MAX-ACCESS  read-write
    STATUS      current
    DESCRIPTION
        "This is a port level control that specifies the mode of drop
         eligibility encoding in PCP bits of the VLAN tag."
    ::= { cmEthernetAccPortEntry 97 }

cmEthernetAccPortPcpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetAccPortPcpDEEncType is of type 7p1d, 6p2d, 5p3d,
         the cmAccPortPcpDEPairTable can be used to specify 
         alternate pairs of priorities to specify drop eligibility/
         ineligibility."
    ::= { cmEthernetAccPortEntry 98 }

cmEthernetAccPortSSMRemoteMacAddress OBJECT-TYPE
    SYNTAX     MacAddress
    MAX-ACCESS read-only
    STATUS     current
    DESCRIPTION
             "This object allows retrieval of the Remote Mac Address, when
              the port is peering using SSM." 
     ::= { cmEthernetAccPortEntry 99 }

cmEthernetAccPortXgePhyType OBJECT-TYPE
    SYNTAX      XgePhyType  
    MAX-ACCESS  read-write
    STATUS      current
    DESCRIPTION
        "This object allows to specify the PHY type of 10G Ethernet Port.
         10G ports can operate in LAN-PHY or WAN-PHY mode. The default mode is LAN-PHY
         and port rate in this mode is 10Gbps. In WAN-PHY mode the port rate is 9.29Gbps.
         This attribute is only applicable for ports configured to work at speed-10G-full.
         For other speeds the value of this object must be 'not-applicable' and cannot
         be changed.
        "
    ::= { cmEthernetAccPortEntry 100 }

cmEthernetAccPortLoopbackSourceMacControlEnabled OBJECT-TYPE
    SYNTAX      TruthValue  
    MAX-ACCESS  read-write
    STATUS      current
    DESCRIPTION
         "This object allows to Enable/Disable the Acc Port Source MAC 
         Address frame matching criteria for all streams. 
         Not applicable for: efm-oam-remote, efm-oam-remote-timed."
    ::= { cmEthernetAccPortEntry 101 }

cmEthernetAccPortLoopbackDestMacControlEnabled OBJECT-TYPE
    SYNTAX      TruthValue  
    MAX-ACCESS  read-write
    STATUS      current
    DESCRIPTION
         "This object allows to Enable/Disable the Acc Port Destination MAC 
         Address frame matching criteria for all streams. 
         Not applicable for: efm-oam-remote, efm-oam-remote-timed."
    ::= { cmEthernetAccPortEntry 102 }

cmEthernetAccPortLoopbackSourceMacAddress OBJECT-TYPE
    SYNTAX      MacAddress  
    MAX-ACCESS  read-write
    STATUS      current
    DESCRIPTION
         "This object allows to set Acc Port Source MAC Address for frame 
          matching when Acc Port Source MAC Control is enabled."
    ::= { cmEthernetAccPortEntry 103 }

cmEthernetAccPortLoopbackDestMacAddress OBJECT-TYPE
    SYNTAX      MacAddress  
    MAX-ACCESS  read-write
    STATUS      current
    DESCRIPTION
         "This object allows to set Acc Port Destination MAC Address for frame 
          matching when Acc Port Destination MAC Control is enabled."
    ::= { cmEthernetAccPortEntry 104 }

cmEthernetAccPortLoopbackBlockingEnabled OBJECT-TYPE
    SYNTAX      TruthValue  
    MAX-ACCESS  read-write
    STATUS      current
    DESCRIPTION
        "This object allows frame blocking when loopback is active.
         - True: Blocks frames in the non-loopback direction 
           that match the PORT or VLAN received in the 
           non-loopback direction. Discards  frames 
           in the loopback direction that match 
           the PORT or VLAN, but do not match 
           the MAC address criteria,
         - False: No blocking of  frames."
    ::= { cmEthernetAccPortEntry 105 }

--
--  Ethernet Access Port Control Protocol Disposition 
--
cmEthernetAccPortCpdTable  OBJECT-TYPE
    SYNTAX      SEQUENCE OF CmEthernetAccPortCpdEntry
    MAX-ACCESS  not-accessible
    STATUS      current
    DESCRIPTION
            "A list of entries corresponding to Ethernet Access Port 
             Control Protocol Disposition.  

             This table is only
             applicable for FSP150CM Hub Shelf Release 3.x."
    ::= { cmFacilityObjects 2 }

cmEthernetAccPortCpdEntry OBJECT-TYPE
    SYNTAX      CmEthernetAccPortCpdEntry 
    MAX-ACCESS  not-accessible
    STATUS      current
    DESCRIPTION
            "A conceptual row in the cmEthernetAccPortCpdTable. 
             These entries represent a Control Protocol Disposition 
             filtering criteria on the Ethernet Access Port."
    INDEX { neIndex, shelfIndex, slotIndex, cmEthernetAccPortIndex, 
            cmEthernetAccPortCpdIndex }
    ::= { cmEthernetAccPortCpdTable 1 }


CmEthernetAccPortCpdEntry ::= SEQUENCE {
    -- Index
    cmEthernetAccPortCpdIndex             Integer32,

    -- Filtering Criteria
    cmEthernetAccPortCpdFilterType        CmControlProtocolFilterType,
    cmEthernetAccPortCpdFilterDescr       DisplayString,
    cmEthernetAccPortCpdDispType          CmControlProtocolDispType,
    cmEthernetAccPortCpdMacAddressMatch   MacAddress,
    cmEthernetAccPortCpdMacAddressMask    MacAddress,
    cmEthernetAccPortCpdEthertype         Integer32,
    cmEthernetAccPortCpdEthertypeMask     Integer32,
    cmEthernetAccPortCpdSubtype           Integer32,
    cmEthernetAccPortCpdSubtypeMask       Integer32
}


cmEthernetAccPortCpdIndex OBJECT-TYPE
    SYNTAX      Integer32 (1..65535)
    MAX-ACCESS  read-only
    STATUS      current
    DESCRIPTION
            "An arbitrary integer index value used to uniquely identify
             this CPD Service Entry."
    ::= { cmEthernetAccPortCpdEntry 1 }

cmEthernetAccPortCpdFilterType OBJECT-TYPE
    SYNTAX     CmControlProtocolFilterType
    MAX-ACCESS read-only
    STATUS     current
    DESCRIPTION
            "This enables specification of type of CPD Filter."
    ::= { cmEthernetAccPortCpdEntry 2 }

cmEthernetAccPortCpdFilterDescr OBJECT-TYPE
    SYNTAX  DisplayString (SIZE (0..32)) 
    MAX-ACCESS read-only
    STATUS     current
    DESCRIPTION
            "This provides description of CPD Filter."
    ::= { cmEthernetAccPortCpdEntry 3 }

cmEthernetAccPortCpdDispType OBJECT-TYPE
    SYNTAX     CmControlProtocolDispType
    MAX-ACCESS read-write
    STATUS     current
    DESCRIPTION
            "This enables specification of disposion type of CPD Filter."
    ::= { cmEthernetAccPortCpdEntry 4 }

cmEthernetAccPortCpdMacAddressMatch OBJECT-TYPE
    SYNTAX     MacAddress
    MAX-ACCESS read-write
    STATUS     current
    DESCRIPTION
         "This enables provides the Filter MAC Address to match."
    ::= { cmEthernetAccPortCpdEntry 5 }

cmEthernetAccPortCpdMacAddressMask OBJECT-TYPE
    SYNTAX     MacAddress
    MAX-ACCESS read-write
    STATUS     current
    DESCRIPTION
         "This enables provides the Filter MAC Address Mask to match."
    ::= { cmEthernetAccPortCpdEntry 6 }

cmEthernetAccPortCpdEthertype OBJECT-TYPE
    SYNTAX     Integer32 (0..65535)
    MAX-ACCESS read-write
    STATUS     current
    DESCRIPTION
         "This enables provides the Filter Ethertype to match."
    ::= { cmEthernetAccPortCpdEntry 7 }

cmEthernetAccPortCpdEthertypeMask OBJECT-TYPE
    SYNTAX     Integer32
    MAX-ACCESS read-write
    STATUS     current
    DESCRIPTION
         "This enables provides the Filter Ethertype Mask to match."
    ::= { cmEthernetAccPortCpdEntry 8 }

cmEthernetAccPortCpdSubtype OBJECT-TYPE
    SYNTAX     Integer32
    MAX-ACCESS read-write
    STATUS     current
    DESCRIPTION
         "This enables provides the Filter Subtype to match."
    ::= { cmEthernetAccPortCpdEntry 9 }

cmEthernetAccPortCpdSubtypeMask OBJECT-TYPE
    SYNTAX     Integer32
    MAX-ACCESS read-write
    STATUS     current
    DESCRIPTION
         "This enables provides the Filter Subtype Mask to match."
    ::= { cmEthernetAccPortCpdEntry 10 }


--
--  Ethernet Access Port Cable Length Benchmark 
--
cmEthernetAccPortClbTable  OBJECT-TYPE
    SYNTAX      SEQUENCE OF CmEthernetAccPortClbEntry
    MAX-ACCESS  not-accessible
    STATUS      current
    DESCRIPTION
            "A list of entries corresponding to Ethernet Access Port 
             Cable Length Benchmark."
    ::= { cmFacilityObjects 3 }

cmEthernetAccPortClbEntry OBJECT-TYPE
    SYNTAX      CmEthernetAccPortClbEntry 
    MAX-ACCESS  not-accessible
    STATUS      current
    DESCRIPTION
            "A conceptual row in the cmEthernetAccPortClbTable. 
             These entries represent Cable Length Benchmarks 
             on the Ethernet Access Port."
    INDEX { neIndex, shelfIndex, slotIndex, cmEthernetAccPortIndex, 
            cmEthernetAccPortClbIndex }
    ::= { cmEthernetAccPortClbTable 1 }


CmEthernetAccPortClbEntry ::= SEQUENCE {
    cmEthernetAccPortClbIndex          Integer32,
    cmEthernetAccPortClbEnabled        TruthValue,
    cmEthernetAccPortClbLength         DisplayString,
    cmEthernetAccPortClbDescr          DisplayString
}

cmEthernetAccPortClbIndex OBJECT-TYPE
    SYNTAX      Integer32 (1..5)
    MAX-ACCESS  read-only
    STATUS      current
    DESCRIPTION
            "An integer index value used to uniquely identify
             this Cable Length Benchmark Entry specification."
    ::= { cmEthernetAccPortClbEntry 1 }

cmEthernetAccPortClbEnabled OBJECT-TYPE
    SYNTAX     TruthValue
    MAX-ACCESS read-write
    STATUS     current
    DESCRIPTION
            "This enables specification of Cable Length Benchmark entry."
    ::= { cmEthernetAccPortClbEntry 2 }

cmEthernetAccPortClbLength OBJECT-TYPE
    SYNTAX  DisplayString 
    MAX-ACCESS read-write
    STATUS     current
    DESCRIPTION
            "Cable length of Cable Points Entry. The cable length is of
             the form XXX[.YY] where XX can be any integer value and YY
             allows precision of 2 decimals after the floating point. Note
             that .YY is optional."
    ::= { cmEthernetAccPortClbEntry 3 }

cmEthernetAccPortClbDescr OBJECT-TYPE
    SYNTAX     DisplayString (SIZE (0..256))
    MAX-ACCESS read-write
    STATUS     current
    DESCRIPTION
         "A textual string containing description of cable span."
    ::= { cmEthernetAccPortClbEntry 4 }

--
--  Ethernet Flow 
--
cmFlowTable  OBJECT-TYPE
    SYNTAX      SEQUENCE OF CmFlowEntry
    MAX-ACCESS  not-accessible
    STATUS      current
    DESCRIPTION
            "A list of entries corresponding to Ethernet Flows 
             for configuration purposes.  If the corresponding
             Ethernet Access Port's  cmEthernetAccPortMode is 
             connection-oriented and cmEthernetAccPortSvcType is epl,
             there exists a single Flow in this table.  

             No Flow creation or deletion is allowed on this table
             for FSP150CM NTU based services.
                
             Since Fsp150 R5.6CC release this table is used to manage 2 types of Flows:
               - Access Port Flow as in the previous releases
               - Tranparent Flow (new in 5.6CC)
              A Transparent Flow is Flow between Network-1 and Network-2 ports used
              to convey pass-thru traffic in the ring topology e.g. ERP.
              Few of the existing attributes will have new semantix for Transperent Flow.
              Transparent Flow is a NE level object and hence has different indexing 
              than the Access Port Flow. The valid indices are neIndex and cmFlowIndex.
              The remaining indices will have constant values as follows:
                  shelfIndex = 1
                  slotIndex = 255
                  cmEthernetAccPortIndex = 0
              "
    ::= { cmFacilityObjects 4 }

cmFlowEntry OBJECT-TYPE
    SYNTAX      CmFlowEntry 
    MAX-ACCESS  not-accessible
    STATUS      current
    DESCRIPTION
            "A conceptual row in the cmFlowTable. These entries represent
             an Ethernet Flow."
    INDEX { neIndex, shelfIndex, slotIndex, cmEthernetAccPortIndex, cmFlowIndex }
    ::= { cmFlowTable 1 }

CmFlowEntry ::= SEQUENCE {
    -- Flow Index/Id
    cmFlowIndex                           Integer32,
    cmFlowCircuitName                     DisplayString,

    -- State Management params
    cmFlowAdminState                      AdminState,
    cmFlowOperationalState                OperationalState,
    cmFlowSecondaryState                  SecondaryState,

    -- Flow Properties
    cmFlowType                            CmFlowType,
    cmFlowMultiCOS                        TruthValue,
    cmFlowA2NCIR                          Unsigned32,
    cmFlowA2NEIR                          Unsigned32,
    cmFlowN2ARateLimitingEnabled          TruthValue,
    cmFlowN2ACIR                          Unsigned32,
    cmFlowN2AEIR                          Unsigned32,
  
    --SNMP row creation 
    cmFlowStorageType                     StorageType,
    cmFlowRowStatus                       RowStatus,

    --New objects available with FSP150CC GE206 devices (Release 4.1CC)
    cmFlowTrafficType                     FlowTrafficType,
    cmFlowCOS                             Integer32,

    --flow membership
    cmFlowVlanMemberList                  DisplayString, 
    cmFlowAction                          FlowVlanActionType, 
    cmFlowActionVlan                      DisplayString, 
    cmFlowUntaggedMemberEnabled           TruthValue,

    --flow bandwidth
    cmFlowA2NCIRHi                        Unsigned32,
    cmFlowA2NEIRHi                        Unsigned32,
    cmFlowN2ACIRHi                        Unsigned32,
    cmFlowN2AEIRHi                        Unsigned32,
    cmFlowHCOSMgmtEnabled                 TruthValue,
    cmFlowGuaranteedA2NBandwidthLo        Unsigned32,
    cmFlowGuaranteedA2NBandwidthHi        Unsigned32,
    cmFlowMaximumA2NBandwidthLo           Unsigned32,
    cmFlowMaximumA2NBandwidthHi           Unsigned32,

    --flow tag management
    cmFlowCTagControl                     FlowTagControl,
    cmFlowCTagVlanId                      VlanId,
    cmFlowCTagVlanPriority                VlanPriority,
    cmFlowCTagMatchRxPrio                 TruthValue,
    cmFlowSTagControl                     FlowTagControl,
    cmFlowSTagVlanId                      VlanId,
    cmFlowSTagVlanPriority                VlanPriority,
    cmFlowOuterTagPrioEnabled             TruthValue,

    --N2A COS Priority
    cmFlowN2ACOSPriorityTagType           VlanTagType,

    --flow frame loss thresholds
    cmFlowESFramesLossThreshold           Integer32,
    cmFlowSESFramesLossThresholdRatio     Integer32,

    --New objects available with FSP150CC GE201 (Release 4.3CC)
    cmFlowPolicingEnabled                 TruthValue,
    cmFlowPreserveSTagProperties          TruthValue,
    cmFlowInnerTagPrioEnabled             TruthValue,

    --New objects available with FSP150CC GE206 (Release 4.4.2CC)
    cmFlowN2AOuterTagPrioEnabled          TruthValue,

    --New objects available with FSP150CC GE206V (Release 5.3CC)
    cmFlowA2NShapingType                  ShapingType, 
    cmFlowN2AShapingType                  ShapingType,

    cmFlowSTagMatchRxPrio                 TruthValue,

    --New objects available with FSP150CC GE206V (Release 5.4CC)
    cmFlowAutoBandwidthConfigEnabled      TruthValue,

    --New objects available with FSP150CC GE206V/GE201/GE206/XG210 (Release 5.6CC)
    cmFlowPort1                           VariablePointer,
    cmFlowPort2                           VariablePointer,
    cmFlowPolicingControl                 PolicingControl,
    cmFlowAutoCIRPercentage               Integer32,
    cmFlowLoopAvoidanceObject             VariablePointer,
    cmFlowConfigType                      FlowConfigType,
    cmFlowN2NForwardingEnabled            TruthValue
}

cmFlowIndex OBJECT-TYPE
    SYNTAX      Integer32 (1..400)
    MAX-ACCESS  read-create
    STATUS      current
    DESCRIPTION
            "The integer index value corresponding to an Ethernet Flow." 
    ::= { cmFlowEntry 1 }

cmFlowCircuitName    OBJECT-TYPE
    SYNTAX      DisplayString (SIZE(0..256))
    MAX-ACCESS  read-create
    STATUS      current
    DESCRIPTION
         "This object allows SNMP management entities to provide a
          circuit identifier with the Flow."
     ::= { cmFlowEntry 2 }

-- State Management params
cmFlowAdminState OBJECT-TYPE
    SYNTAX      AdminState 
    MAX-ACCESS  read-write
    STATUS      current
    DESCRIPTION
            "This object represents the Administrative State of the Flow." 
    ::= { cmFlowEntry 3 }

cmFlowOperationalState OBJECT-TYPE
    SYNTAX      OperationalState 
    MAX-ACCESS  read-only
    STATUS      current
    DESCRIPTION
            "This object represents the Operational State of the Flow." 
    ::= { cmFlowEntry 4 }

cmFlowSecondaryState OBJECT-TYPE
    SYNTAX      SecondaryState 
    MAX-ACCESS  read-only
    STATUS      current
    DESCRIPTION
            "This object represents the Secondary State of the Flow." 
    ::= { cmFlowEntry 5 }

cmFlowType OBJECT-TYPE
    SYNTAX      CmFlowType
    MAX-ACCESS  read-create
    STATUS      current
    DESCRIPTION
            "This object represents the type of the Flow." 
    ::= { cmFlowEntry 6 }

cmFlowMultiCOS OBJECT-TYPE
    SYNTAX     TruthValue
    MAX-ACCESS read-create
    STATUS     current
    DESCRIPTION
         "This object allows specification of multiple COS (Class of Service)
          Flow." 
     ::= { cmFlowEntry 7 }

cmFlowA2NCIR OBJECT-TYPE
    SYNTAX     Unsigned32
    MAX-ACCESS read-create
    STATUS     current
    DESCRIPTION
         "This object represents the Commited Information
          Rate(CIR) of an Flow in the Access to Network (A2N) direction. 
          For a portbased Flow(FSP150CM NTU, CPMR), 
          this object is not settable. This value represents the lower 
          32-bits of the CIR. For a Multi COS flow, this value
          is settable only at creation time.
          
          In case of Tranparent Flow this object represents N1 to N2 CIR."
     ::= { cmFlowEntry 8 }

cmFlowA2NEIR OBJECT-TYPE
    SYNTAX     Unsigned32
    MAX-ACCESS read-create
    STATUS     current
    DESCRIPTION
         "This object represents the Excess Information
          Rate(EIR) on an Flow in the Access to Network (A2N) direction.  
          For a portbased Flow(FSP150CM NTU, CPMR), 
          this object is not settable.  This value represents the lower
          32-bits of the CIR. For a Multi COS flow, this value
          is settable only at creation time.

          In case of Tranparent Flow this object represents N1 to N2 EIR."
     ::= { cmFlowEntry 9 }

cmFlowN2ARateLimitingEnabled    OBJECT-TYPE
    SYNTAX      TruthValue
    MAX-ACCESS  read-create
    STATUS      current
    DESCRIPTION
         "This object allows management of the N2A rate limiting,
          independent of A2N rate limiting. When not enabled,
          N2A specification is the same as A2N.
          
          This object is not applicable for Tranparent Flow; the value should be FALSE."
    ::= { cmFlowEntry 10 }

cmFlowN2ACIR OBJECT-TYPE
    SYNTAX     Unsigned32
    MAX-ACCESS read-create
    STATUS     current
    DESCRIPTION
         "This object represents the Commited Information
          Rate(CIR) of an Flow in the Network to Access (N2A) direction. 
          For a portbased Flow, this object is not settable. This is
          only settable if cmFlowN2ARateLimitingEnabled is enabled.

          In case of Tranparent Flow this object represents N2 to N1 CIR."
     ::= { cmFlowEntry 11 }

cmFlowN2AEIR OBJECT-TYPE
    SYNTAX     Unsigned32
    MAX-ACCESS read-create
    STATUS     current
    DESCRIPTION
         "This object represents the Excess Information
          Rate(CIR) of an Flow in the Network to Access (N2A) direction. 
          For a portbased Flow, this object is not settable. This is
          only settable if cmFlowN2ARateLimitingEnabled is enabled.

          In case of Tranparent Flow this object represents N2 to N1 EIR."
     ::= { cmFlowEntry 12 }

cmFlowStorageType OBJECT-TYPE
    SYNTAX     StorageType
    MAX-ACCESS read-create
    STATUS     current
    DESCRIPTION
            "The type of storage configured for this entry."
    ::= { cmFlowEntry 13 }

cmFlowRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmFlowRowStatus supported are
            createAndGo(4) and destroy(6).  All mandatory attributes
            must be specified in a single SNMP SET request with
            cmFlowRowStatus value as createAndGo(4).
            Upon successful row creation, this object has a
            value of active(1).

            The cmFlowRowStatus object may be modified if
            the associated instance of this object is equal to active(1).
            
            Note that flow creation and deletion is only supported
            with access port in connection-oriented evpl mode."
    ::= { cmFlowEntry 14 }

--New objects available with FSP150CC GE206 devices (Release 4.1CC)
cmFlowTrafficType OBJECT-TYPE 
    SYNTAX     FlowTrafficType
    MAX-ACCESS read-only
    STATUS     current
    DESCRIPTION
            "This object provides information on the type of traffic flow 
             supported by the system, i.e.'shaped-only' flows (support
             only shaping) or 'policed-shaped' (support policing and shaping) flows.  
             'shaped-only' flow exists for FSP150CM NTU and CPMR access ports. 
             'policed-shaped' flows are supported in FSP150CC devices.
             Please note that this object refers to how traffic profiles
             are managed on devices and is independent of the policing enabling/disabling
             feature."
    ::= { cmFlowEntry 15 }

cmFlowCOS  OBJECT-TYPE
    SYNTAX     Integer32 (0..7)
    MAX-ACCESS read-create
    STATUS     current
    DESCRIPTION
            "This object allows specification of the COS (Class of Service)
             value for the Traffic Flow. This value is used at flow creation
             time to identify the COS level of the A2N and N2A shaper.
             In case of a multi-COS flow, this value is not applicable
             when multiple policers/shapers exist on the flow.
             This object is also applicable to specify the COS of a
             connection-oriented epl service."
    ::= { cmFlowEntry 16 }

--flow membership
cmFlowVlanMemberList OBJECT-TYPE
    SYNTAX     DisplayString (SIZE (0..512))
    MAX-ACCESS read-create
    STATUS     current
    DESCRIPTION
         "This object is applicable only when Port is in connection-oriented
          evpl mode. This attribute is mandatory if creation of
          connection-oriented evpl regular flow is desired.
          It allows specification of VLAN members of the Flow.
          VLAN members are comma separated, of the form X-Y where X is the
          VLAN Id and Y is the VLAN Priority.  VLAN members can be of
          the form X-* or X (vlan X with all priorities), 
          *-Y (all vlans with priority Y), and X1:X2 
          (range of vlans from X1 to X2, all priorities). Members 
          with specific VLAN Id and specific VLAN Priority are not supported.
          Once the flow is created, this attribute can only be updated
          using cmFlowAction and cmFlowActionVlan objects."
     ::= { cmFlowEntry 17 }

cmFlowAction OBJECT-TYPE
    SYNTAX     FlowVlanActionType 
    MAX-ACCESS read-write
    STATUS     current
    DESCRIPTION
         "This object is applicable only when Port is in connection-oriented
          evpl mode and the cmFlowType is regular.  This object allows to
          add or remove the VLAN members specified by
          cmFlowActionVlan object.  SNMP manager must first
          configure the VLAN member to be added/removed in the object
          cmFlowActionVlan and then should specify
          cmFlowAction on whether to add/remove the specified
          VLAN member."
     ::= { cmFlowEntry 18 }

cmFlowActionVlan OBJECT-TYPE
    SYNTAX     DisplayString (SIZE (0..16))
    MAX-ACCESS read-create
    STATUS     current
    DESCRIPTION
         "This object is applicable only when Port is in connection-oriented
          evpl mode. This object allows adding/removing VLAN members
          to a connection-oriented evpl regular flow.
          VLAN member is of the form X-Y where X is the
          VLAN Id and Y is the VLAN Priority.  VLAN members can be of
          the form X-* (vlan X with all priorities), 
          *-Y (all vlans with priority Y), and X1:X2 
          (range of vlans from X1 to X2, all priorities).  
          Members with specific VLAN Id and 
          specific VLAN Priority are not supported.
          In order to add/remove VLAN member to a flow, user must
          specify this object with appropriate VLAN and then invoke
          cmFlowAction."
     ::= { cmFlowEntry 19 }

cmFlowUntaggedMemberEnabled OBJECT-TYPE
    SYNTAX     TruthValue 
    MAX-ACCESS read-create
    STATUS     current
    DESCRIPTION
         "This object is applicable only when Port is in connection-oriented
          evpl mode for a regular flow as well as default flow. 
          This object allows to specify whether or not the flow 
          supports untagged traffic."
     ::= { cmFlowEntry 20 }

--flow bandwidth
cmFlowA2NCIRHi OBJECT-TYPE
    SYNTAX     Unsigned32
    MAX-ACCESS read-create
    STATUS     current
    DESCRIPTION
         "This object represents the Commited Information
          Rate(CIR) of an Flow in the Access to Network (A2N) direction. 
          This value represents the upper 32 bits of CIR (lower is 
          provided in cmFlowA2NCIR). For a Multi COS flow, this value
          is settable only at creation time.

          In case of Tranparent Flow this object represents N1 to N2 CIR."
     ::= { cmFlowEntry 21 }

cmFlowA2NEIRHi OBJECT-TYPE
    SYNTAX     Unsigned32
    MAX-ACCESS read-create
    STATUS     current
    DESCRIPTION
         "This object represents the Excess Information
          Rate(EIR) on an Flow in the Access to Network (A2N) direction.  
          For a portbased Flow(FSP150CM NTU, CPMR), 
          this object is not settable.  This value represents the higher
          32-bits of the CIR.  For a Multi COS flow, this value
          is settable only at creation time.

          In case of Tranparent Flow this object represents N1 to N2 EIR."
     ::= { cmFlowEntry 22 }

cmFlowN2ACIRHi OBJECT-TYPE
    SYNTAX     Unsigned32
    MAX-ACCESS read-create
    STATUS     current
    DESCRIPTION
         "This object represents the Commited Information
          Rate(CIR) of an Flow in the Network to Access (N2A) direction. 
          This value represents the upper 32 bits of CIR (lower is 
          provided in cmFlowN2ACIR). For a Multi COS flow, this value
          is settable only at creation time. This is
          only settable if cmFlowN2ARateLimitingEnabled is enabled.

          In case of Tranparent Flow this object represents N2 to N1 CIR."
     ::= { cmFlowEntry 23 }

cmFlowN2AEIRHi OBJECT-TYPE
    SYNTAX     Unsigned32
    MAX-ACCESS read-create
    STATUS     current
    DESCRIPTION
         "This object represents the Excess Information
          Rate(EIR) on an Flow in the Network to Access (N2A) direction.  
          For a portbased Flow(FSP150CM NTU, CPMR), 
          this object is not settable.  This value represents the higher
          32-bits of the CIR.  For a Multi COS flow, this value
          is settable only at creation time. This is
          only settable if cmFlowN2ARateLimitingEnabled is enabled.

          In case of Tranparent Flow this object represents N2 to N1 EIR."
     ::= { cmFlowEntry 24 }

cmFlowHCOSMgmtEnabled OBJECT-TYPE
    SYNTAX     TruthValue
    MAX-ACCESS read-create
    STATUS     current
    DESCRIPTION
         "This object allows management of Hierarchical COS on the Flow." 
     ::= { cmFlowEntry 25 }

cmFlowGuaranteedA2NBandwidthLo OBJECT-TYPE
    SYNTAX     Unsigned32
    MAX-ACCESS read-write
    STATUS     current
    DESCRIPTION
         "This object supports the Hierarchical Class of Service (HCOS)
          feature.  It is only applicable for a flow with multiple
          class of services. This allows the provisioning of 
          guaranteed bandwidth (lower 32 bits) of a flow.
          This value must be greater than or equal to the sum of all
          individual COS CIRs.

          In case of Tranparent Flow this object represents N1 to N2 and N2 to N1
          guaranteed bandwidth."
     ::= { cmFlowEntry 26 }

cmFlowGuaranteedA2NBandwidthHi OBJECT-TYPE
    SYNTAX     Unsigned32
    MAX-ACCESS read-write
    STATUS     current
    DESCRIPTION
         "This object supports the Hierarchical Class of Service (HCOS)
          feature.  It is only applicable for a flow with multiple
          class of services. This allows the provisioning of 
          guaranteed bandwidth (upper 32 bits) of a flow.
          This value must be greater than or equal to the sum of all
          individual COS CIRs.

          In case of Tranparent Flow this object represents N1 to N2 and N2 to N1
          guaranteed bandwidth."
     ::= { cmFlowEntry 27 }

cmFlowMaximumA2NBandwidthLo OBJECT-TYPE
    SYNTAX     Unsigned32
    MAX-ACCESS read-write
    STATUS     current
    DESCRIPTION
         "This object supports the Hierarchical Class of Service (HCOS)
          feature.  It is only applicable for a flow with multiple
          class of services. This allows the provisioning of 
          maximum bandwidth (lower 32 bits) of a flow.  This is the peak
          limit of a flow.  This value must be greater than or equal 
          to the sum of all individual COS CIRs.

          In case of Tranparent Flow this object represents N1 to N2 and N2 to N1
          maximum bandwidth."
     ::= { cmFlowEntry 28 }

cmFlowMaximumA2NBandwidthHi OBJECT-TYPE
    SYNTAX     Unsigned32
    MAX-ACCESS read-write
    STATUS     current
    DESCRIPTION
         "This object supports the Hierarchical Class of Service (HCOS)
          feature.  It is only applicable for a flow with multiple
          class of services. This allows the provisioning of 
          maximum bandwidth (upper 32 bits) of a flow.  This is the peak
          limit of a flow.  This value must be greater than or equal 
          to the sum of all individual COS CIRs.

          In case of Tranparent Flow this object represents N1 to N2 and N2 to N1
          maximum bandwidth."
     ::= { cmFlowEntry 29 }

--flow tag management
cmFlowCTagControl  OBJECT-TYPE
    SYNTAX     FlowTagControl
    MAX-ACCESS read-create
    STATUS     current
    DESCRIPTION
         "This object allows specification of the tag management 
          operation on the C-TAG.  Supported types are 'push', 'pushvid',
          'swapvid' and 'none'. If the type is 'push', 
          the VLAN Id (cmFlowCTagVlanId) and priority
          (cmFlowCTagVlanPriority) are pushed onto the frame;
          if the type is 'pushvid', only the VLAN Id (12 bits) is pushed,
          the Priority is copied from incoming tag's priority;
          if the type is 'swapvid', only the VLAN Id (12 bits) are 
          swapped with the specified cmFlowCTagVlanId; 
          if the type is 'none', no C-TAG management is performed.

          This object is not applicable for Tranparent Flow; the value should be 'none'."
     ::= { cmFlowEntry 30 }

cmFlowCTagVlanId  OBJECT-TYPE
    SYNTAX     VlanId
    MAX-ACCESS read-create
    STATUS     current
    DESCRIPTION
         "This object allows specification of the VLAN Id to
          be pushed or swapped, based on the value of cmFlowCTagControl.
          It is applicable for 'push', 'swapvid' and 'pushvid'
          control types.

          This object is not applicable for Tranparent Flow; the value should be 0."
     ::= { cmFlowEntry 31 }

cmFlowCTagVlanPriority  OBJECT-TYPE
    SYNTAX     VlanPriority
    MAX-ACCESS read-create
    STATUS     current
    DESCRIPTION
         "This object allows specification of the VLAN Priority to
          be pushed or swapped, based on the value of cmFlowCTagControl.
          It is applicable for 'push' control type.

          This object is not applicable for Tranparent Flow; the value should be 0."
     ::= { cmFlowEntry 32 }

cmFlowCTagMatchRxPrio  OBJECT-TYPE
    SYNTAX     TruthValue
    MAX-ACCESS read-create
    STATUS     current
    DESCRIPTION
         "This object is used to specify whether the C-TAG  priority
          be used or ignored for traffic in the N2A direction.
          This is only applicable if  cmFlowCTagControl
          is 'push'.

          This object is not applicable for Tranparent Flow; the value should be FALSE."
     ::= { cmFlowEntry 33 }

cmFlowSTagControl  OBJECT-TYPE
    SYNTAX     FlowTagControl
    MAX-ACCESS read-create
    STATUS     current
    DESCRIPTION
         "This object allows specification of the tag management 
          operation on the S-TAG.  Supported types are 'push', 'swapvid', and 'none'.
          If the type is 'push', the VLAN Id (cmFlowSTagVlanId) and priority
          (cmFlowSTagVlanPriority) are pushed onto the frame; if the type is
          'swapvid', the VLAN Id(12 bits) is swapped with the specified
          cmFlowSTagVlanId; type is 'none', no S-TAG manament is performed.

          This object is not applicable for Tranparent Flow; the value should be 'none'."
     ::= { cmFlowEntry 34 }

cmFlowSTagVlanId  OBJECT-TYPE
    SYNTAX     VlanId
    MAX-ACCESS read-create
    STATUS     current
    DESCRIPTION
         "This object allows specification of the VLAN Id to
          be pushed, based on the value of cmFlowSTagControl.
          It is applicable for 'push' control type.

          This object is not applicable for Tranparent Flow; the value should be 0."
     ::= { cmFlowEntry 35 }

cmFlowSTagVlanPriority  OBJECT-TYPE
    SYNTAX     VlanPriority
    MAX-ACCESS read-create
    STATUS     current
    DESCRIPTION
         "This object allows specification of the VLAN Priority to
          be pushed, based on the value of cmFlowSTagControl.
          It is applicable for 'push' control type.

          This object is not applicable for Tranparent Flow; the value should be 0."
     ::= { cmFlowEntry 36 }

cmFlowOuterTagPrioEnabled  OBJECT-TYPE
    SYNTAX     TruthValue
    MAX-ACCESS read-create
    STATUS     current
    DESCRIPTION
         "This object is used to specify whether the flow
          participates in outer-tag priority swap.  The Priority 
          Mapping Table cmPrioMapTable allows the A2N outer-tag
          priority to be specified based on incoming priority at
          Access Port (based on priority mapping mode - 802.1P, TOS, DSCP).

          This object is not applicable for Tranparent Flow; the value should be FALSE."
     ::= { cmFlowEntry 37 }

cmFlowN2ACOSPriorityTagType  OBJECT-TYPE
    SYNTAX     VlanTagType
    MAX-ACCESS read-create
    STATUS     current
    DESCRIPTION
         "This object is used to specify whether the flow
          uses the inner-tag or the outer-tag in determining the COS (Class of Service) in the
          N2A direction.  This object is applicable in the case of a Multi COS Flow.

          This object is not supported for Tranparent Flow;"
     ::= { cmFlowEntry 38 }

--flow frame loss thresholds
cmFlowESFramesLossThreshold  OBJECT-TYPE
    SYNTAX     Integer32 (1..2147483647)
    MAX-ACCESS read-write
    STATUS     current
    DESCRIPTION
         "This object is used to specify the number of frames lost
          per flow that starts counting Errored Seconds (ES) on the flow.
          This functionality is applicable if the flow is monitored
          using the Y.1731 ESA functionality." 
     ::= { cmFlowEntry 39 }
           
cmFlowSESFramesLossThresholdRatio OBJECT-TYPE 
    SYNTAX     Integer32 (1..100)
    MAX-ACCESS read-write
    STATUS     current
    DESCRIPTION
         "This object is used to specify the frame-loss ratio 
          per flow that starts counting Severely Errored Seconds (SES) 
          on the flow.
          This functionality is applicable if the flow is monitored
          using the Y.1731 ESA functionality." 
     ::= { cmFlowEntry 40 }

cmFlowPolicingEnabled OBJECT-TYPE
    SYNTAX     TruthValue 
    MAX-ACCESS read-create
    STATUS     current
    DESCRIPTION
         "This object is applicable only when Port is in connection-oriented mode.
          This object is applicable to both epl and evpl mode flows. 
          This object allows to enable/disable the policing function on the flow." 
     ::= { cmFlowEntry 41 }

cmFlowPreserveSTagProperties OBJECT-TYPE
    SYNTAX     TruthValue 
    MAX-ACCESS read-create
    STATUS     current
    DESCRIPTION
         "This object is applicable only when Port is in connection-oriented mode.
          This object is applicable to evpl mode Regular flows, when S-TAG control
          is specified as SWAPVID.
          When enabled, this attribute preserves the EtherType (0x88a8) and 
          DEI (Drop Eligibility Indicator) bit
          in the incoming S-TAG (both from Access and Network Port perspective)
          into the outgoing S-TAG.
          When not enabled, the incoming tag is considered as a Q-TAG (0x8100)
          and both EtherType and CFI (Canonical Form Indicator) bits are over-written 
          by the S-TAG Ethertype (0x88a8) and DEI bit. 

          This object is not applicable for Tranparent Flow; the value should be FALSE." 
     ::= { cmFlowEntry 42 }

cmFlowInnerTagPrioEnabled  OBJECT-TYPE
    SYNTAX     TruthValue
    MAX-ACCESS read-create
    STATUS     current
    DESCRIPTION
         "This object is used to specify whether the flow
          participates in inner-tag (second) priority swap.  The Priority 
          Mapping Table cmPrioMapTable allows the A2N inner-tag
          priority to be specified based on incoming priority at
          Access Port (based on priority mapping mode - 802.1P, TOS, DSCP).

          This object is not applicable for Tranparent Flow; the value should FALSE." 
     ::= { cmFlowEntry 43 }

cmFlowN2AOuterTagPrioEnabled  OBJECT-TYPE
    SYNTAX     TruthValue
    MAX-ACCESS read-create
    STATUS     current
    DESCRIPTION
         "This object is used to specify whether the flow
          participates in outer-tag priority swap in the A2N direction.
          The Priority Mapping Table cmNetPortPrioMapTable allows the N2A outer-tag
          priority to be specified based on incoming priority at
          Network Port (based on priority mapping mode - 802.1P, TOS, DSCP).

          This object is not applicable for Tranparent Flow; the value should be FALSE." 
     ::= { cmFlowEntry 44 }

cmFlowA2NShapingType  OBJECT-TYPE
    SYNTAX     ShapingType  
    MAX-ACCESS read-create
    STATUS     current
    DESCRIPTION
         "This object is used to specify whether the traffic in A2N direction
          passing through this flow is shaped by port-level or flow-level Shapers.
          In case of portbased flows the value of this attribute is flow-based and 
          cannot be changed. In case of regular and default flows Fsp150 products
          may support both port-based and flow-based shaping."
     ::= { cmFlowEntry 45 }

cmFlowN2AShapingType  OBJECT-TYPE
    SYNTAX     ShapingType  
    MAX-ACCESS read-create
    STATUS     current
    DESCRIPTION
         "This object is used to specify whether the traffic in N2A direction
          passing through this flow is shaped by port-level or flow-level Shapers.
          In case of portbased flows the value of this attribute is flow-based and 
          cannot be changed. In case of regular and default flows Fsp150 products
          may support both port-based and flow-based shaping."
     ::= { cmFlowEntry 46 }

cmFlowSTagMatchRxPrio  OBJECT-TYPE
    SYNTAX     TruthValue
    MAX-ACCESS read-create
    STATUS     current
    DESCRIPTION
         "This object indicates whether the S-TAG  priority
          is used or ignored for traffic in the N2A direction.
          This is only applicable if  cmFlowSTagControl
          is 'push'.

          This object is not applicable for Tranparent Flow; the value should be FALSE." 
     ::= { cmFlowEntry 47 }

cmFlowAutoBandwidthConfigEnabled OBJECT-TYPE
    SYNTAX     TruthValue
    MAX-ACCESS read-create
    STATUS     current
    DESCRIPTION
         "This object is applicable for Flows on the PWE3 Ethernet Backplane Port.
          When set to TRUE bandwidth of this Flow will be automatically adjusted when
          PWE3 SATOPs are provisioned. The bandwidth will be adjusted based on the
          TDM entities of associated SATOPs.
          Flow on ports other than PWE3 Ethernet Backplane Port will always have
          this value set to FALSE and it is not configurable."
     ::= { cmFlowEntry 48 }

cmFlowPort1 OBJECT-TYPE
    SYNTAX     VariablePointer
    MAX-ACCESS read-create
    STATUS     current
    DESCRIPTION
         "This object specifies a physical or logical port on the Access side of the 
          Flow. This can be Access Port, Access LAG or Access Split Horizion Group.
          
          In case of Tranparent Flow this object specifies port1 of the Flow which is
          Network-1."
     ::= { cmFlowEntry 49 }

cmFlowPort2 OBJECT-TYPE
    SYNTAX     VariablePointer
    MAX-ACCESS read-create
    STATUS     current
    DESCRIPTION
         "This object specifies a physical or logical port on the Network side of the 
          Flow. This can be Network Port, Network LAG, Network Split Horizion Group
          ERP or Protection Group.

          In case of Tranparent Flow this object specifies port2 of the Flow which is
          Network-2."
     ::= { cmFlowEntry 50 }

cmFlowPolicingControl OBJECT-TYPE
    SYNTAX     PolicingControl
    MAX-ACCESS read-create
    STATUS     current
    DESCRIPTION
         "This object specifies the direction(s) in which Poling is enabled on traffic 
          within this Flow when cmFlowPolicingEnabled is TRUE."

     ::= { cmFlowEntry 51 }

cmFlowAutoCIRPercentage OBJECT-TYPE
    SYNTAX     Integer32 (0..100)
    MAX-ACCESS read-create
    STATUS     current
    DESCRIPTION
         "This object specifies the percentage of available CIR on the Network 
          ports assigned to this Flow when cmFlowAutoBandwidthConfigEnabled is TRUE.  
          The flow guaranteedBW is set to available BW multiplied by this value.
          This object is only applicable to Tranparent Flow.
          The value of this object should be 0 for Access Flow."
     ::= { cmFlowEntry 52 }

cmFlowLoopAvoidanceObject OBJECT-TYPE
    SYNTAX     VariablePointer
    MAX-ACCESS read-create
    STATUS     current
    DESCRIPTION
          "This object specifies the Loop Avoidance instance to which this Flow belongs.
           This object is appicable only for Transparent Flow and should point to the
           ERP instance for which this Flows carries pass-thru traffic.
           
           In case of Access Flow the value of this object should be zeroDotZero."
     ::= { cmFlowEntry 53 }

cmFlowConfigType OBJECT-TYPE
    SYNTAX     FlowConfigType
    MAX-ACCESS read-only
    STATUS     current
    DESCRIPTION
          "This object specifies if this Flow is an Access Flow or Pass-thru Flow."
     ::= { cmFlowEntry 54 }

cmFlowN2NForwardingEnabled OBJECT-TYPE
    SYNTAX     TruthValue
    MAX-ACCESS read-create
    STATUS     current
    DESCRIPTION
          "This object is used to specify whether n2n forwarding 
           is enabled on particular Flow."
     ::= { cmFlowEntry 55 }

--
--  Ethernet Flow Control Protocol Disposition 
--
cmFlowCpdTable  OBJECT-TYPE
    SYNTAX      SEQUENCE OF CmFlowCpdEntry
    MAX-ACCESS  not-accessible
    STATUS      current
    DESCRIPTION
            "A list of entries corresponding to Flow 
             Control Protocol Disposition.
             This table is only
             applicable for FSP150CM Hub Shelf Release 3.x."
    ::= { cmFacilityObjects 5 }

cmFlowCpdEntry OBJECT-TYPE
    SYNTAX      CmFlowCpdEntry 
    MAX-ACCESS  not-accessible
    STATUS      current
    DESCRIPTION
            "A conceptual row in the cmFlowCpdTable. 
             These entries represent a Control Protocol Disposition 
             filtering criteria on the Ethernet Network Port."
    INDEX { neIndex, shelfIndex, slotIndex, cmEthernetAccPortIndex, 
            cmFlowIndex, cmFlowCpdIndex }
    ::= { cmFlowCpdTable 1 }


CmFlowCpdEntry ::= SEQUENCE {
    -- Index
    cmFlowCpdIndex             Integer32,

    -- Filter parameters
    cmFlowCpdFilterType        CmControlProtocolFilterType,
    cmFlowCpdFilterDescr       DisplayString,
    cmFlowCpdDispType          CmControlProtocolDispType,
    cmFlowCpdMacAddressMatch   MacAddress,
    cmFlowCpdMacAddressMask    MacAddress,
    cmFlowCpdEthertype         Integer32,
    cmFlowCpdEthertypeMask     Integer32,
    cmFlowCpdSubtype           Integer32,
    cmFlowCpdSubtypeMask       Integer32
}

cmFlowCpdIndex OBJECT-TYPE
    SYNTAX      Integer32 (1..65535)
    MAX-ACCESS  read-only
    STATUS      current
    DESCRIPTION
            "An arbitrary integer index value used to uniquely identify
             this CPD Service Entry."
    ::= { cmFlowCpdEntry 1 }

cmFlowCpdFilterType OBJECT-TYPE
    SYNTAX     CmControlProtocolFilterType
    MAX-ACCESS read-only
    STATUS     current
    DESCRIPTION
            "This enables specification of type of CPD Filter."
    ::= { cmFlowCpdEntry 2 }

cmFlowCpdFilterDescr OBJECT-TYPE
    SYNTAX  DisplayString (SIZE (0..32)) 
    MAX-ACCESS read-only
    STATUS     current
    DESCRIPTION
            "This provides description of CPD Filter."
    ::= { cmFlowCpdEntry 3 }

cmFlowCpdDispType OBJECT-TYPE
    SYNTAX     CmControlProtocolDispType
    MAX-ACCESS read-write
    STATUS     current
    DESCRIPTION
            "This enables specification of disposion type of CPD Filter."
    ::= { cmFlowCpdEntry 4 }

cmFlowCpdMacAddressMatch OBJECT-TYPE
    SYNTAX     MacAddress
    MAX-ACCESS read-write
    STATUS     current
    DESCRIPTION
         "This enables provides the Filter MAC Address to match."
    ::= { cmFlowCpdEntry 5 }

cmFlowCpdMacAddressMask OBJECT-TYPE
    SYNTAX     MacAddress
    MAX-ACCESS read-write
    STATUS     current
    DESCRIPTION
         "This enables provides the Filter MAC Address Mask to match."
    ::= { cmFlowCpdEntry 6 }

cmFlowCpdEthertype OBJECT-TYPE
    SYNTAX     Integer32 (0..65535)
    MAX-ACCESS read-write
    STATUS     current
    DESCRIPTION
         "This enables provides the Filter Ethertype to match."
    ::= { cmFlowCpdEntry 7 }

cmFlowCpdEthertypeMask OBJECT-TYPE
    SYNTAX     Integer32
    MAX-ACCESS read-write
    STATUS     current
    DESCRIPTION
         "This enables provides the Filter Ethertype Mask to match."
    ::= { cmFlowCpdEntry 8 }

cmFlowCpdSubtype OBJECT-TYPE
    SYNTAX     Integer32
    MAX-ACCESS read-write
    STATUS     current
    DESCRIPTION
         "This enables provides the Filter Subtype to match."
    ::= { cmFlowCpdEntry 9 }

cmFlowCpdSubtypeMask OBJECT-TYPE
    SYNTAX     Integer32
    MAX-ACCESS read-write
    STATUS     current
    DESCRIPTION
         "This enables provides the Filter Subtype Mask to match."
    ::= { cmFlowCpdEntry 10 }


--
--  Ethernet Flow Quality of Service Shaper 
--
cmQosShaperTable  OBJECT-TYPE
    SYNTAX      SEQUENCE OF CmQosShaperEntry
    MAX-ACCESS  not-accessible
    STATUS      current
    DESCRIPTION
            "A list of entries corresponding to Ethernet Quality of Service 
             Shaper for configuration purposes."
    ::= { cmFacilityObjects 6 }

cmQosShaperEntry OBJECT-TYPE
    SYNTAX      CmQosShaperEntry 
    MAX-ACCESS  not-accessible
    STATUS      current
    DESCRIPTION
            "A conceptual row in the cmQosShaperTable. 
             These entries represent a Quality of Service Shaper."
    INDEX { neIndex, shelfIndex, slotIndex, cmEthernetAccPortIndex, 
            cmFlowIndex, cmQosShaperTypeIndex, cmQosShaperIndex }
    ::= { cmQosShaperTable 1 }

CmQosShaperEntry ::= SEQUENCE {
    -- QOS Shaper Index/Id
    cmQosShaperTypeIndex           Integer32,
    cmQosShaperIndex               Integer32,
    cmQosShaperDirection           TrafficDirection,

    -- State Management params
    cmQosShaperAdminState          AdminState,
    cmQosShaperOperationalState    OperationalState,
    cmQosShaperSecondaryState      SecondaryState,

    -- QOS Shaper Properties
    cmQosShaperCIR                 Unsigned32,
    cmQosShaperCBS                 Unsigned32,
    cmQosShaperEIR                 Unsigned32,
    cmQosShaperEBS                 Unsigned32,
    cmQosShaperBufferSize          Unsigned32,

    --SNMP row creation 
    cmQosShaperStorageType         StorageType,
    cmQosShaperRowStatus           RowStatus,

    --New objects available with FSP150CC GE206 device  (Release 4.1CC)
    cmQosShaperCOS                 Integer32,
    cmQosShaperCIRHi               Unsigned32,
    cmQosShaperEIRHi               Unsigned32,
    cmQosShaperSoamCIRLo           Unsigned32,
    cmQosShaperSoamCIRHi           Unsigned32,
    cmQosShaperSoamEIRLo           Unsigned32,
    cmQosShaperSoamEIRHi           Unsigned32
}

cmQosShaperTypeIndex OBJECT-TYPE
    SYNTAX      Integer32 (1..4)
    MAX-ACCESS  read-create
    STATUS      current
    DESCRIPTION
          "The unique index value corresponding to a Quality of Service 
           Shaper's direction.
           Values 1 and 2 are applicable to the Access Flow Shaper:
           - value of 1 stands for A2N direction,
           - value of 2 stands for N2A direction.
           Values 3 and 4 are applicable to Pass-thru Flow Shaper (new in 5.6CC release):
           - value of 3 stands for N1toN2 direction
           - value of 4 stands for N2toN1 direction
           "
    ::= { cmQosShaperEntry 1 }

cmQosShaperIndex OBJECT-TYPE
    SYNTAX      Integer32 (1..16)
    MAX-ACCESS  read-create
    STATUS      current
    DESCRIPTION
            "The unique integer index value corresponding to a 
             Quality of Service Shaper.
             
             In release 5.6CC the range is extended to 1..16 to support duplicate
             A2N shapers on a Flow. The duplicate shapers are created under a Flow 
             if network interface of the Flow is ERP Group or Split Horizon Group. 
             In case of multi-cos Flow indices 1..8 represent shapers of COS 0..7 
             going to Network 1 port; indices 9..16 represent shapers for COS 0..7 
             going to Network 2 port.
             In case of single-cos Flow index 1 represents shaper going to Network 1
             port; index 9 represents shaper going to Network 2 port.
             "
    ::= { cmQosShaperEntry 2 }

cmQosShaperDirection OBJECT-TYPE
    SYNTAX      TrafficDirection 
    MAX-ACCESS  read-only
    STATUS      current
    DESCRIPTION
            "The direction of the Quality of Service Shaper."
    ::= { cmQosShaperEntry 3 }

-- State Management params
cmQosShaperAdminState OBJECT-TYPE
    SYNTAX      AdminState 
    MAX-ACCESS  read-write
    STATUS      current
    DESCRIPTION
            "This object represents the Administrative State of 
             the QOS Shaper." 
    ::= { cmQosShaperEntry 4 }

cmQosShaperOperationalState OBJECT-TYPE
    SYNTAX      OperationalState 
    MAX-ACCESS  read-only
    STATUS      current
    DESCRIPTION
            "This object represents the Operational State of the QOS Shaper." 
    ::= { cmQosShaperEntry 5 }

cmQosShaperSecondaryState OBJECT-TYPE
    SYNTAX      SecondaryState 
    MAX-ACCESS  read-only
    STATUS      current
    DESCRIPTION
            "This object represents the Secondary State of the QOS Shaper." 
    ::= { cmQosShaperEntry 6 }

cmQosShaperCIR OBJECT-TYPE
    SYNTAX     Unsigned32
    MAX-ACCESS read-create
    STATUS     current
    DESCRIPTION
         "This object represents the Commited Information
          Rate(CIR) (Lower 32 bits)of a Shaper."
     ::= { cmQosShaperEntry 7 }

cmQosShaperCBS OBJECT-TYPE
    SYNTAX     Unsigned32
    MAX-ACCESS read-create
    STATUS     current
    DESCRIPTION
         "This object represents the Commited Burst Size (CBS) of the Shaper."
     ::= { cmQosShaperEntry 8 }

cmQosShaperEIR OBJECT-TYPE
    SYNTAX     Unsigned32
    MAX-ACCESS read-create
    STATUS     current
    DESCRIPTION
         "This object represents the Excess Information
          Rate(EIR) (Lower 32 bits) of a Shaper."
     ::= { cmQosShaperEntry 9 }

cmQosShaperEBS OBJECT-TYPE
    SYNTAX     Unsigned32
    MAX-ACCESS read-create
    STATUS     current
    DESCRIPTION
         "This object represents the Excess Burst Size (EBS) of the Shaper."
     ::= { cmQosShaperEntry 10 }

cmQosShaperBufferSize OBJECT-TYPE
    SYNTAX     Unsigned32
    MAX-ACCESS read-create
    STATUS     current
    DESCRIPTION
         "This object represents the Buffer Size of the Shaper."
     ::= { cmQosShaperEntry 11 }

cmQosShaperStorageType OBJECT-TYPE
    SYNTAX     StorageType
    MAX-ACCESS read-create
    STATUS     current
    DESCRIPTION
            "The type of storage configured for this entry."
    ::= { cmQosShaperEntry 12 }

cmQosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosShaperRowStatus supported are
            createAndGo(4) and destroy(6).  All mandatory attributes
            must be specified in a single SNMP SET request with
            cmQosShaperRowStatus value as createAndGo(4).
            Upon successful row creation, this object has a
            value of active(1).

            The cmQosShaperRowStatus object may be modified if
            the associated instance of this object is equal to active(1)."
    ::= { cmQosShaperEntry 13 }

cmQosShaperCOS OBJECT-TYPE
    SYNTAX     Integer32 (0..7)
    MAX-ACCESS read-only
    STATUS     current
    DESCRIPTION
            "This object provides the COS (Class of Service)
             value for the QOS Shaper."
    ::= { cmQosShaperEntry 14 }

cmQosShaperCIRHi OBJECT-TYPE
    SYNTAX     Unsigned32
    MAX-ACCESS read-create
    STATUS     current
    DESCRIPTION
         "This object represents the Commited Information
          Rate(CIR) (Higher 32 bits) of a Shaper."
     ::= { cmQosShaperEntry 15 }

cmQosShaperEIRHi OBJECT-TYPE
    SYNTAX     Unsigned32
    MAX-ACCESS read-create
    STATUS     current
    DESCRIPTION
         "This object represents the Excess Information
          Rate(EIR) (Higher 32 bits) on the Shaper."
     ::= { cmQosShaperEntry 16 }

cmQosShaperSoamCIRLo OBJECT-TYPE
    SYNTAX     Unsigned32
    MAX-ACCESS read-create
    STATUS     current
    DESCRIPTION
         "This object represents the Soam Commited Information
          Rate(SOAM-CIR) (Lower 32 bits) of a Shaper."
     ::= { cmQosShaperEntry 17 }

cmQosShaperSoamCIRHi OBJECT-TYPE
    SYNTAX     Unsigned32
    MAX-ACCESS read-create
    STATUS     current
    DESCRIPTION
         "This object represents the Soam Commited Information
          Rate(SOAM-CIR) (Higher 32 bits) on the Shaper."
     ::= { cmQosShaperEntry 18 }

cmQosShaperSoamEIRLo OBJECT-TYPE
    SYNTAX     Unsigned32
    MAX-ACCESS read-create
    STATUS     current
    DESCRIPTION
         "This object represents the Soam Excess Information
          Rate(SOAM-EIR) (Lower 32 bits) of a Shaper."
     ::= { cmQosShaperEntry 19 }

cmQosShaperSoamEIRHi OBJECT-TYPE
    SYNTAX     Unsigned32
    MAX-ACCESS read-create
    STATUS     current
    DESCRIPTION
         "This object represents the Soam Excess Information
          Rate(SOAM-EIR) (Higher 32 bits) on the Shaper."
     ::= { cmQosShaperEntry 20 }

--
--  Ethernet Network Port 
--
cmEthernetNetPortTable  OBJECT-TYPE
    SYNTAX      SEQUENCE OF CmEthernetNetPortEntry
    MAX-ACCESS  not-accessible
    STATUS      current
    DESCRIPTION
            "A list of entries corresponding to Ethernet Network Port 
             Facilities for configuration purposes."
    ::= { cmFacilityObjects 7 }

cmEthernetNetPortEntry OBJECT-TYPE
    SYNTAX      CmEthernetNetPortEntry 
    MAX-ACCESS  not-accessible
    STATUS      current
    DESCRIPTION
            "A conceptual row in the cmEthernetNetPortTable."
    INDEX { neIndex, shelfIndex, slotIndex, cmEthernetNetPortIndex }
    ::= { cmEthernetNetPortTable 1 }

CmEthernetNetPortEntry ::= SEQUENCE {
    -- Port Indices 
    cmEthernetNetPortIndex                           Integer32,
    cmEthernetNetPortIfIndex                         InterfaceIndex,
    cmEthernetNetPortEntityIndex                     PhysicalIndex,

    -- State Management params
    cmEthernetNetPortAdminState                      AdminState,
    cmEthernetNetPortOperationalState                OperationalState,
    cmEthernetNetPortSecondaryState                  SecondaryState,

    -- Generic Port params
    cmEthernetNetPortMTU                             Integer32,

    -- Generic Ethernet Port params
    cmEthernetNetPortMediaType                       EthernetMediaType,
    cmEthernetNetPortConfigSpeed                     EthernetPortSpeed,
    cmEthernetNetPortNegotiatedSpeed                 EthernetPortSpeed,
    cmEthernetNetPortMDIXType                        CmEthernetMDIXType,
    cmEthernetNetPortJumboFramesEnabled              TruthValue,
    cmEthernetNetPortSfpVendorName                   DisplayString,
    cmEthernetNetPortSfpPartNumber                   DisplayString,
    cmEthernetNetPortSfpSerialNumber                 DisplayString,
    cmEthernetNetPortSfpDateOfManufacture            DateAndTime,
    cmEthernetNetPortSfpConnectorValue               SfpConnectorValue,

    -- EtherJack Diagnosis params
    cmEthernetNetPortInitiateDiag                    CmEthernetDiagAction,
    cmEthernetNetPortDiagnosePair1Cond               CmDiagCableCondType,
    cmEthernetNetPortDiagnosePair2Cond               CmDiagCableCondType,
    cmEthernetNetPortDiagnosePair3Cond               CmDiagCableCondType,
    cmEthernetNetPortDiagnosePair4Cond               CmDiagCableCondType,
    cmEthernetNetPortDiagnoseAutoNegCond             CmDiagAutoNegCondType,
    cmEthernetNetPortDiagnoseLpbkCond                CmDiagLpbkCondType,
    cmEthernetNetPortDiagnoseEfmLpbkCond             CmDiagEfmOamLpbkCondType,
    cmEthernetNetPortDiagnoseResult                  DisplayString,
    cmEthernetNetPortDiagnoseTestStatus              CmDiagTestStatus,
    cmEthernetNetPortDiagnoseTestTime                DateAndTime,

    -- Ethernet Loopback params
    cmEthernetNetPortLoopbackConfig                  CmLoopbackType,
    cmEthernetNetPortLoopbackStatus                  CmLoopbackType,
    cmEthernetNetPortLoopbackTime                    Integer32,
    cmEthernetNetPortLoopbackSwapSADA                CmSwapSADAType,
    cmEthernetNetPortOuterVlanLoopbackMask           INTEGER,
    cmEthernetNetPortOuterVlanLoopback1              DisplayString,
    cmEthernetNetPortOuterVlanLoopback2              DisplayString,
    cmEthernetNetPortOuterVlanLoopback3              DisplayString,
    cmEthernetNetPortInnerVlanLoopbackMask           INTEGER,
    cmEthernetNetPortInnerVlanLoopback1              DisplayString,
    cmEthernetNetPortInnerVlanLoopback2              DisplayString,
    cmEthernetNetPortInnerVlanLoopback3              DisplayString,

    -- Link Loss Forwarding params 
    cmEthernetNetPortLinkLossFwdEnabled              TruthValue,
    cmEthernetNetPortLinkLossFwdSignalType           CmLinkLossFwdSignalType,
    cmEthernetNetPortLinkLossFwdTriggerTypes         CmLinkLossFwdTriggerTypes,
    cmEthernetNetPortLinkLossFwdDelay                Integer32,
    cmEthernetNetPortLinkLossFwdActive               TruthValue,
    cmEthernetNetPortLinkLossFwdPartnerEnabled       TruthValue,
    cmEthernetNetPortLinkLossFwdLocalLinkId          Integer32,
    cmEthernetNetPortLinkLossFwdRemoteLinkIds        CmRemoteLinkIds,

    -- OAM params
    cmEthernetNetPortOamId                           Integer32,
    cmEthernetNetPortOamAdminDisposition             CmControlProtocolDispType,
    cmEthernetNetPortOamDiscoveryState               CmOamDiscoveryState,
    cmEthernetNetPortOamLocalVarRtrvsEnabled         TruthValue,
    cmEthernetNetPortOamLocalLinkEventsEnabled       TruthValue,
    cmEthernetNetPortOamLocalOamLoopbacksSupported   TruthValue,
    cmEthernetNetPortOamLocalUnidirSupportEnabled    TruthValue,
    cmEthernetNetPortOamLocalMaxPDUSize              Integer32,
    cmEthernetNetPortOamLocalMode                    CmOamMode,
    cmEthernetNetPortOamRemoteMacAddress             MacAddress,
    cmEthernetNetPortOamRemoteVarRtrvsEnabled        TruthValue,
    cmEthernetNetPortOamRemoteLinkEventsEnabled      TruthValue,
    cmEthernetNetPortOamRemoteOamLoopbacksSupported  TruthValue,
    cmEthernetNetPortOamRemoteUnidirSupportEnabled   TruthValue,
    cmEthernetNetPortOamRemoteMaxPDUSize             Integer32,
    cmEthernetNetPortOamRemoteMode                   CmOamMode,

    -- Ethernet Port Traffic params
    cmEthernetNetPortRxPauseDisposition              CmControlProtocolDispType,
    cmEthernetNetPortTxPauseEnabled                  TruthValue,
    cmEthernetNetPortAfpType                         CmAfpType,

    --New objects available with FSP150CC GE206 device (Release 4.1CC)
    -- Generic Ethernet Port params
    cmEthernetNetPortMDIXStatus                      CmEthernetMDIXType,
    cmEthernetNetPortSfpReach                        Integer32,
    cmEthernetNetPortSfpLaserWaveLength              Integer32,
    cmEthernetNetPortSfpMediaType                    SfpMediaType,

    -- EFM OAM params
    cmEthernetNetPortOamEnabled                      TruthValue,
    cmEthernetNetPortOamAdminState                   CmOamAdminState,

    -- Ethernet Port Traffic params
    cmEthernetNetPortShapingEnabled                  TruthValue,
    cmEthernetNetPortShapedSpeedLo                   Unsigned32,
    cmEthernetNetPortShapedSpeedHi                   Unsigned32,
    cmEthernetNetPortQinQEtherType                   Unsigned32,

    -- LLF params
    cmEthernetNetPortLinkLossFwdTxActionType         CmLinkLossFwdTxActionType,
    cmEthernetNetPortLinkLossFwdRxRLDLinkIds         CmRemoteLinkIds,

    -- EtherJack Diagnosis params
    cmEthernetNetPortAutoDiagEnabled                 TruthValue,

    --Synchronous Port params
    cmEthernetNetPortSyncEEnabled                    TruthValue,
    cmEthernetNetPortQLModeEnabled                   TruthValue,
    cmEthernetNetPortExpectedQL                      SSMQualityLevel,
    cmEthernetNetPortAssumedQL                       SSMQualityLevel,
    cmEthernetNetPortReceivedQL                      SSMQualityLevel,
    cmEthernetNetPortTransmitQL                      SSMQualityLevel,

    --Network Port Priority Mapping Mode
    cmEthernetNetPortPrioMapMode                     PriorityMapMode,

    --PCP DE Pairs
    cmEthernetNetPortDeiEnable                       TruthValue, 
    cmEthernetNetPortPcpDEEncType                    PcpDEEncType,
    cmEthernetNetPortPcpDEPairsAction                PcpDEPairsAction,

    cmEthernetNetPortSSMRemoteMacAddress             MacAddress,

    --XG params
    cmEthernetNetPortXgePhyType                      XgePhyType,

    --Mac Loopback Params
    cmEthernetNetPortLoopbackSourceMacControlEnabled TruthValue,
    cmEthernetNetPortLoopbackDestMacControlEnabled   TruthValue,
    cmEthernetNetPortLoopbackSourceMacAddress        MacAddress,
    cmEthernetNetPortLoopbackDestMacAddress          MacAddress,
    cmEthernetNetPortLoopbackBlockingEnabled         TruthValue
}
    
-- Port Indices 
cmEthernetNetPortIndex OBJECT-TYPE
    SYNTAX      Integer32 (1..65535)
    MAX-ACCESS  read-only
    STATUS      current
    DESCRIPTION
            "An integer index value used to uniquely identify
             this Ethernet Network Port within a card.
             Note that each Ethernet Network Port is uniquely identified
             by the indices neIndex, shelfIndex, 
             slotIndex, cmEthernetNetPortIndex." 
    ::= { cmEthernetNetPortEntry 1 }

cmEthernetNetPortIfIndex OBJECT-TYPE
    SYNTAX      InterfaceIndex
    MAX-ACCESS  read-only
    STATUS      current
    DESCRIPTION
            "This object has the same value as ifIndex for 
             Ethernet Network Port.  An integer index value used to 
             uniquely identify this Ethernet Network Port."
    ::= { cmEthernetNetPortEntry 2 }

cmEthernetNetPortEntityIndex OBJECT-TYPE
    SYNTAX      PhysicalIndex 
    MAX-ACCESS  read-only
    STATUS      current
    DESCRIPTION
           "Entity Index from ENTITY-MIB for this port."
    ::= { cmEthernetNetPortEntry 3 }

-- State Management params
cmEthernetNetPortAdminState OBJECT-TYPE
    SYNTAX      AdminState 
    MAX-ACCESS  read-write
    STATUS      current
    DESCRIPTION
            "This object represents the Administrative State of the Ethernet 
             Network Port."
    ::= { cmEthernetNetPortEntry 4 }

cmEthernetNetPortOperationalState OBJECT-TYPE
    SYNTAX      OperationalState 
    MAX-ACCESS  read-only
    STATUS      current
    DESCRIPTION
            "This object represents the Operational State of the Ethernet 
             Network Port."
    ::= { cmEthernetNetPortEntry 5 }

cmEthernetNetPortSecondaryState OBJECT-TYPE
    SYNTAX      SecondaryState 
    MAX-ACCESS  read-only
    STATUS      current
    DESCRIPTION
            "This object represents the Secondary State of the Ethernet 
             Network Port."
    ::= { cmEthernetNetPortEntry 6 }

-- Generic Port params
cmEthernetNetPortMTU OBJECT-TYPE
    SYNTAX      Integer32 
    MAX-ACCESS  read-write
    STATUS      current
    DESCRIPTION
            "This object provides the MTU on the Ethernet Network Port."
    ::= { cmEthernetNetPortEntry 7 }

cmEthernetNetPortMediaType OBJECT-TYPE
    SYNTAX     EthernetMediaType
    MAX-ACCESS read-write
    STATUS     current
    DESCRIPTION
            "This object represents the type of Ethernet Media on the 
             Ethernet Network Port."
    ::= { cmEthernetNetPortEntry 8 }

cmEthernetNetPortConfigSpeed OBJECT-TYPE
    SYNTAX     EthernetPortSpeed
    MAX-ACCESS read-write
    STATUS     current
    DESCRIPTION
            "This object allows to configure the speed of the 
             Ethernet Network Port."
    ::= { cmEthernetNetPortEntry 9 }

cmEthernetNetPortNegotiatedSpeed OBJECT-TYPE
    SYNTAX     EthernetPortSpeed
    MAX-ACCESS read-only
    STATUS     current
    DESCRIPTION
            "This object provides the negotiated speed of the 
             Ethernet Network Port."
    ::= { cmEthernetNetPortEntry 10 }

cmEthernetNetPortMDIXType OBJECT-TYPE
    SYNTAX     CmEthernetMDIXType
    MAX-ACCESS read-write
    STATUS     current
    DESCRIPTION
            "This object allows management of MDIX property on  
             Ethernet Network Port."
    ::= { cmEthernetNetPortEntry 11 }

cmEthernetNetPortJumboFramesEnabled OBJECT-TYPE
    SYNTAX     TruthValue
    MAX-ACCESS read-write
    STATUS     current
    DESCRIPTION
            "This object allows enabling/disabling jumbo frames support on 
             the Ethernet Network Port.  This object is only applicable for
             Ethernet Network Port on R3.1CM NTU Card."
    ::= { cmEthernetNetPortEntry 12 }

cmEthernetNetPortSfpVendorName OBJECT-TYPE
    SYNTAX  DisplayString (SIZE (0..16)) 
    MAX-ACCESS read-only
    STATUS     current
    DESCRIPTION
            "This object provides the vendor name of the SFP. 
             This is applicable when cmEthernetNetPortMediaType is fiber or coppersfp."
     ::= { cmEthernetNetPortEntry 13 }

cmEthernetNetPortSfpPartNumber OBJECT-TYPE
    SYNTAX  DisplayString (SIZE (0..16)) 
    MAX-ACCESS read-only
    STATUS     current
    DESCRIPTION
            "This object provides the part number of the SFP. 
             This is applicable when cmEthernetNetPortMediaType is fiber or coppersfp."
     ::= { cmEthernetNetPortEntry 14 }

cmEthernetNetPortSfpSerialNumber OBJECT-TYPE
    SYNTAX  DisplayString (SIZE (0..32)) 
    MAX-ACCESS read-only
    STATUS     current
    DESCRIPTION
            "This object provides the serial number of the SFP.  
             This is applicable when cmEthernetNetPortMediaType is fiber or coppersfp."
     ::= { cmEthernetNetPortEntry 15 }

cmEthernetNetPortSfpDateOfManufacture OBJECT-TYPE
    SYNTAX     DateAndTime
    MAX-ACCESS read-only
    STATUS     current
    DESCRIPTION
            "This object provides the date of manufacture of the SFP.
             This is applicable when cmEthernetNetPortMediaType is fiber or coppersfp."
     ::= { cmEthernetNetPortEntry 16 }

cmEthernetNetPortSfpConnectorValue OBJECT-TYPE
    SYNTAX     SfpConnectorValue 
    MAX-ACCESS read-only
    STATUS     current
    DESCRIPTION
            "This object provides the SFP connector value.
             This is applicable when cmEthernetNetPortMediaType is fiber or coppersfp."
     ::= { cmEthernetNetPortEntry 17 }

-- EtherJack Diagnosis params
cmEthernetNetPortInitiateDiag  OBJECT-TYPE
    SYNTAX     CmEthernetDiagAction
    MAX-ACCESS read-write
    STATUS     current
    DESCRIPTION
            "This object allows to initiate Etherjack diagnosis on the
             Ethernet Network Port."
     ::= { cmEthernetNetPortEntry 18 }

cmEthernetNetPortDiagnosePair1Cond OBJECT-TYPE
    SYNTAX     CmDiagCableCondType
    MAX-ACCESS read-only
    STATUS     current
    DESCRIPTION
            "This object provides diagnosis results for the cable Pair 1
             on Ethernet Network Port."
     ::= { cmEthernetNetPortEntry 19 }

cmEthernetNetPortDiagnosePair2Cond OBJECT-TYPE
    SYNTAX     CmDiagCableCondType
    MAX-ACCESS read-only
    STATUS     current
    DESCRIPTION
            "This object provides diagnosis results for the cable Pair 2
             on Ethernet Network Port."
     ::= { cmEthernetNetPortEntry 20 }

cmEthernetNetPortDiagnosePair3Cond OBJECT-TYPE
    SYNTAX     CmDiagCableCondType
    MAX-ACCESS read-only
    STATUS     current
    DESCRIPTION
            "This object provides diagnosis results for the cable Pair 3
             on Ethernet Network Port."
     ::= { cmEthernetNetPortEntry 21 }

cmEthernetNetPortDiagnosePair4Cond OBJECT-TYPE
    SYNTAX     CmDiagCableCondType
    MAX-ACCESS read-only
    STATUS     current
    DESCRIPTION
            "This object provides diagnosis results for the cable Pair 4
             on Ethernet Network Port."
     ::= { cmEthernetNetPortEntry 22 }

cmEthernetNetPortDiagnoseAutoNegCond OBJECT-TYPE
    SYNTAX     CmDiagAutoNegCondType
    MAX-ACCESS read-only
    STATUS     current
    DESCRIPTION
            "This object provides auto negotiation results of the diagnosis
             test on Ethernet Network Port."
     ::= { cmEthernetNetPortEntry 23 }

cmEthernetNetPortDiagnoseLpbkCond OBJECT-TYPE
    SYNTAX     CmDiagLpbkCondType
    MAX-ACCESS read-only
    STATUS     current
    DESCRIPTION
            "This object provides port loopback results of the diagnosis
             test on Ethernet Network Port."
     ::= { cmEthernetNetPortEntry 24 }

cmEthernetNetPortDiagnoseEfmLpbkCond OBJECT-TYPE
    SYNTAX     CmDiagEfmOamLpbkCondType
    MAX-ACCESS read-only
    STATUS     current
    DESCRIPTION
            "This object provides remote EFM loopback results of the diagnosis
             test on Ethernet Network Port."
     ::= { cmEthernetNetPortEntry 25 }

cmEthernetNetPortDiagnoseResult OBJECT-TYPE
    SYNTAX  DisplayString (SIZE (0..256)) 
    MAX-ACCESS read-only
    STATUS     current
    DESCRIPTION
            "This object provides results of the diagnosis
             test in string form on Ethernet Network Port."
     ::= { cmEthernetNetPortEntry 26 }

cmEthernetNetPortDiagnoseTestStatus OBJECT-TYPE
    SYNTAX  CmDiagTestStatus 
    MAX-ACCESS read-only
    STATUS     current
    DESCRIPTION
            "This object provides the current status of the diagnosis
             test on Ethernet Access Port."
     ::= { cmEthernetNetPortEntry 27 }

cmEthernetNetPortDiagnoseTestTime OBJECT-TYPE
    SYNTAX  DateAndTime 
    MAX-ACCESS read-only
    STATUS     current
    DESCRIPTION
            "This object provides the time when diagnosis test was last executed."
     ::= { cmEthernetNetPortEntry 28 }

-- Ethernet Loopback params
cmEthernetNetPortLoopbackConfig OBJECT-TYPE 
    SYNTAX     CmLoopbackType
    MAX-ACCESS read-write
    STATUS     current
    DESCRIPTION
            "This object allows to initiate loopbacks on 
             on the Ethernet Network Port."
     ::= { cmEthernetNetPortEntry 29 }

cmEthernetNetPortLoopbackStatus OBJECT-TYPE
    SYNTAX     CmLoopbackType
    MAX-ACCESS read-only
    STATUS     current
    DESCRIPTION
            "This object provides status of the current loopback 
             on the Ethernet Network Port."
     ::= { cmEthernetNetPortEntry 30 }

cmEthernetNetPortLoopbackTime OBJECT-TYPE 
    SYNTAX     Integer32 (2..300)
    MAX-ACCESS read-write
    STATUS     current
    DESCRIPTION
            "This object allows to specify time for timed-loopbacks on 
             on the Ethernet Network Port."
     ::= { cmEthernetNetPortEntry 31 }

cmEthernetNetPortLoopbackSwapSADA OBJECT-TYPE
    SYNTAX     CmSwapSADAType
    MAX-ACCESS read-write
    STATUS     current
    DESCRIPTION
            "This object allows to specify whether or not the loopbacked
             frame will have the Source Address and Destination Address
             swapped."
     ::= { cmEthernetNetPortEntry 32 }

cmEthernetNetPortOuterVlanLoopbackMask OBJECT-TYPE
    SYNTAX     INTEGER (0..16)
    MAX-ACCESS read-write
    STATUS     current
    DESCRIPTION
             "This object allows specification of the outer VLANs to be 
              looped back when port is in vlan(terminal/facility) 
              loopback configuration. Only 3 VLANs can be specified 
              for vlan loopback. The various bit positions are:
                   1         Outer VLAN 1 Loopback Enabled
                   2         Outer VLAN 2 Loopback Enabled
                   4         Outer VLAN 3 Loopback Enabled
              Value of 0 means that no VLANs are enabled."
     ::= { cmEthernetNetPortEntry 33 }

cmEthernetNetPortOuterVlanLoopback1 OBJECT-TYPE 
    SYNTAX  DisplayString (SIZE (0..6)) 
    MAX-ACCESS read-write
    STATUS     current
    DESCRIPTION
             "This object allows specification of the outer VLAN 1 to be 
              looped back when port is in vlan(terminal/facility) 
              loopback configuration. This is valid only if the
              corresponding bit in cmEthernetNetPortOuterVlanLoopbackMask
              is set.  The value to be specified should be in the form 
              X-Y where X is the VLAN Id and Y is the VLAN Priority.  
              If Y is specified as a *, all Priorities (0 to 7) 
              are looped back."
     ::= { cmEthernetNetPortEntry 34 }

cmEthernetNetPortOuterVlanLoopback2 OBJECT-TYPE
    SYNTAX  DisplayString (SIZE (0..6)) 
    MAX-ACCESS read-write
    STATUS     current
    DESCRIPTION
             "This object allows specification of the outer VLAN 2 to be 
              looped back when port is in vlan(terminal/facility) 
              loopback configuration. This is valid only if the
              corresponding bit in cmEthernetNetPortOuterVlanLoopbackMask
              is set.  The value to be specified should be in the form 
              X-Y where X is the VLAN Id and Y is the VLAN Priority.  
              If Y is specified as a *, all Priorities (0 to 7) 
              are looped back."
     ::= { cmEthernetNetPortEntry 35 }

cmEthernetNetPortOuterVlanLoopback3 OBJECT-TYPE
    SYNTAX  DisplayString (SIZE (0..6)) 
    MAX-ACCESS read-write
    STATUS     current
    DESCRIPTION
             "This object allows specification of the outer VLAN 3 to be 
              looped back when port is in vlan(terminal/facility) 
              loopback configuration. This is valid only if the
              corresponding bit in cmEthernetNetPortOuterVlanLoopbackMask
              is set.  The value to be specified should be in the form 
              X-Y where X is the VLAN Id and Y is the VLAN Priority.  
              If Y is specified as a *, all Priorities (0 to 7) 
              are looped back."
     ::= { cmEthernetNetPortEntry 36 }

cmEthernetNetPortInnerVlanLoopbackMask OBJECT-TYPE
    SYNTAX     INTEGER (0..16)
    MAX-ACCESS read-write
    STATUS     current
    DESCRIPTION
             "This object allows specification of the inner VLANs to be 
              looped back when port is in vlan(terminal/facility) 
              loopback configuration. Only 3 VLANs can be specified 
              for vlan loopback. The various bit positions are:
                   1         Inner VLAN 1 Loopback Enabled
                   2         Inner VLAN 2 Loopback Enabled
                   4         Inner VLAN 3 Loopback Enabled
              Value of 0 means that no VLANs are enabled."
     ::= { cmEthernetNetPortEntry 37 }

cmEthernetNetPortInnerVlanLoopback1 OBJECT-TYPE 
    SYNTAX  DisplayString (SIZE (0..6)) 
    MAX-ACCESS read-write
    STATUS     current
    DESCRIPTION
             "This object allows specification of the inner VLAN 1 to be 
              looped back when port is in vlan(terminal/facility) 
              loopback configuration. This is valid only if the
              corresponding bit in cmEthernetNetPortInnerVlanLoopbackMask
              is set.  The value to be specified should be in the form 
              X-Y where X is the VLAN Id and Y is the VLAN Priority.  
              If Y is specified as a *, all Priorities (0 to 7) 
              are looped back."
     ::= { cmEthernetNetPortEntry 38 }

cmEthernetNetPortInnerVlanLoopback2 OBJECT-TYPE
    SYNTAX  DisplayString (SIZE (0..6)) 
    MAX-ACCESS read-write
    STATUS     current
    DESCRIPTION
             "This object allows specification of the inner VLAN 2 to be 
              looped back when port is in vlan(terminal/facility) 
              loopback configuration. This is valid only if the
              corresponding bit in cmEthernetNetPortInnerVlanLoopbackMask
              is set.  The value to be specified should be in the form 
              X-Y where X is the VLAN Id and Y is the VLAN Priority.  
              If Y is specified as a *, all Priorities (0 to 7) 
              are looped back."
     ::= { cmEthernetNetPortEntry 39 }

cmEthernetNetPortInnerVlanLoopback3 OBJECT-TYPE
    SYNTAX  DisplayString (SIZE (0..6)) 
    MAX-ACCESS read-write
    STATUS     current
    DESCRIPTION
             "This object allows specification of the inner VLAN 3 to be 
              looped back when port is in vlan(terminal/facility) 
              loopback configuration. This is valid only if the
              corresponding bit in cmEthernetNetPortInnerVlanLoopbackMask
              is set.  The value to be specified should be in the form 
              X-Y where X is the VLAN Id and Y is the VLAN Priority.  
              If Y is specified as a *, all Priorities (0 to 7) 
              are looped back."
     ::= { cmEthernetNetPortEntry 40 }


-- Link Loss Forwarding params 
cmEthernetNetPortLinkLossFwdEnabled OBJECT-TYPE
    SYNTAX     TruthValue
    MAX-ACCESS read-write
    STATUS     current
    DESCRIPTION
             "This object allows enabling/disabling link loss forwarding 
              on the Ethernet Network Port." 
     ::= { cmEthernetNetPortEntry 41 }

cmEthernetNetPortLinkLossFwdSignalType OBJECT-TYPE 
    SYNTAX     CmLinkLossFwdSignalType
    MAX-ACCESS read-write
    STATUS     deprecated
    DESCRIPTION
             "This object allows definition of the link loss forwarding
              signalling type.  This is applicable only if 
              cmEthernetNetPortLinkLossFwdEnabled is enabled.
              This object is only valid for FSP150CM Release 3.1. 
              This object is deprecated henceforth. 
              Link Loss signalling will be supported using the object
              cmEthernetAccPortLinkLossFwdTxActionType."
     ::= { cmEthernetNetPortEntry 42 }

cmEthernetNetPortLinkLossFwdTriggerTypes  OBJECT-TYPE
    SYNTAX     CmLinkLossFwdTriggerTypes
    MAX-ACCESS read-write
    STATUS     current
    DESCRIPTION
             "This object allows definition of the link loss forwarding
              trigger types.  This is applicable only if 
              cmEthernetAccPortLinkLossFwdEnabled is enabled."
     ::= { cmEthernetNetPortEntry 43 }

cmEthernetNetPortLinkLossFwdDelay OBJECT-TYPE 
    SYNTAX     Integer32
    MAX-ACCESS read-write
    STATUS     current
    DESCRIPTION
             "This object allows specification of the delay between
              detection of link loss and signalling of link loss forwarding. 
              Time specified is in seconds."
     ::= { cmEthernetNetPortEntry 44 }

cmEthernetNetPortLinkLossFwdActive OBJECT-TYPE 
    SYNTAX     TruthValue
    MAX-ACCESS read-only
    STATUS     current
    DESCRIPTION
             "This object provides the link loss forwarding status indicating
              if link loss forwarding is currently being signaled via 
              the port." 
     ::= { cmEthernetNetPortEntry 45 }

cmEthernetNetPortLinkLossFwdPartnerEnabled OBJECT-TYPE 
    SYNTAX     TruthValue
    MAX-ACCESS read-only
    STATUS     current
    DESCRIPTION
             "This object provides the indication of a link partners ability
              to support link loss forwarding via EFM, i.e. from
              received organization specific OAMPDUs." 
     ::= { cmEthernetNetPortEntry 46 }

cmEthernetNetPortLinkLossFwdLocalLinkId  OBJECT-TYPE 
    SYNTAX     Integer32
    MAX-ACCESS read-write
    STATUS     current
    DESCRIPTION
             "This object allows configuration of the Local Link Id on 
              Ethernet Network port." 
     ::= { cmEthernetNetPortEntry 47 }

cmEthernetNetPortLinkLossFwdRemoteLinkIds OBJECT-TYPE 
    SYNTAX     CmRemoteLinkIds 
    MAX-ACCESS read-write
    STATUS     current
    DESCRIPTION
             "This object allows enabling/disabling Remote Link Ids 
              on Ethernet Network port. By setting the appropriate bit
              positions, the Ethernet Network port is able to distinguish
              the remote side client ports from the Remote Link Down
              PDUs coming from remote end."
     ::= { cmEthernetNetPortEntry 48 }

-- OAM params
cmEthernetNetPortOamId  OBJECT-TYPE
    SYNTAX     Integer32 
    MAX-ACCESS read-only
    STATUS     current
    DESCRIPTION
             "OAM Id.  This is unique EFM OAM sublayer port id." 
     ::= { cmEthernetNetPortEntry 49 }

cmEthernetNetPortOamAdminDisposition OBJECT-TYPE
    SYNTAX     CmControlProtocolDispType
    MAX-ACCESS read-write
    STATUS     deprecated
    DESCRIPTION
             "Ethernet Network Port's EFM OAM Administrative Disposition. 
              This object is applicable only for FSP150CM Release 3.1.
              This object is deprecated henceforth.  
              With FSP150CC Release 4.1, this property is managed using 
              the Control Protocol Disposition tables."
     ::= { cmEthernetNetPortEntry 50 }

cmEthernetNetPortOamDiscoveryState OBJECT-TYPE
    SYNTAX     CmOamDiscoveryState
    MAX-ACCESS read-only
    STATUS     current
    DESCRIPTION
             "Ethernet Network Port's OAM discovery state." 
     ::= { cmEthernetNetPortEntry 51 }

cmEthernetNetPortOamLocalVarRtrvsEnabled OBJECT-TYPE
    SYNTAX     TruthValue
    MAX-ACCESS read-only
    STATUS     current
    DESCRIPTION
             "This object allows specification of whether the Ethernet
              Network Port supports sending variable response OAMPDUs." 
     ::= { cmEthernetNetPortEntry 52 }

cmEthernetNetPortOamLocalLinkEventsEnabled OBJECT-TYPE
    SYNTAX     TruthValue 
    MAX-ACCESS read-only
    STATUS     current
    DESCRIPTION
             "This object allows specification of whether the Ethernet
              Network Port supports interpreting Link Events."
     ::= { cmEthernetNetPortEntry 53 }

cmEthernetNetPortOamLocalOamLoopbacksSupported OBJECT-TYPE
    SYNTAX     TruthValue 
    MAX-ACCESS read-write
    STATUS     current
    DESCRIPTION
             "This object allows specification of whether the Ethernet
              Network Port is capable of OAM remote loopback mode."
     ::= { cmEthernetNetPortEntry 54 }

cmEthernetNetPortOamLocalUnidirSupportEnabled OBJECT-TYPE
    SYNTAX     TruthValue 
    MAX-ACCESS read-only
    STATUS     current
    DESCRIPTION
             "This object allows specification of whether the Ethernet
              Network Port is capable of sending OAMPDUs when the receive path 
              is non-operational."
     ::= { cmEthernetNetPortEntry 55 }

cmEthernetNetPortOamLocalMaxPDUSize OBJECT-TYPE
    SYNTAX     Integer32
    MAX-ACCESS read-only
    STATUS     current
    DESCRIPTION
             "This object represents the largest OAMPDU, in octets, 
              supported by the Ethernet Network Port.  This value is
              compared to the remote Maximum PDU Size and the smaller of 
              the two is used." 
     ::= { cmEthernetNetPortEntry 56 }

cmEthernetNetPortOamLocalMode OBJECT-TYPE
    SYNTAX     CmOamMode 
    MAX-ACCESS read-write
    STATUS     current
    DESCRIPTION
             "This object allows to configure the OAM sublayer entity in
              either Active or Passive mode." 
     ::= { cmEthernetNetPortEntry 57 }

cmEthernetNetPortOamRemoteMacAddress OBJECT-TYPE
    SYNTAX     MacAddress
    MAX-ACCESS read-only
    STATUS     current
    DESCRIPTION
             "This object allows retrieval of the Remote Mac Address." 
     ::= { cmEthernetNetPortEntry 58 }

cmEthernetNetPortOamRemoteVarRtrvsEnabled OBJECT-TYPE
    SYNTAX     TruthValue
    MAX-ACCESS read-only
    STATUS     current
    DESCRIPTION
             "This object allows retrieval of whether the remote OAM 
              entity supports sending variable response OAMPDUs." 
     ::= { cmEthernetNetPortEntry 59 }

cmEthernetNetPortOamRemoteLinkEventsEnabled OBJECT-TYPE
    SYNTAX     TruthValue 
    MAX-ACCESS read-only
    STATUS     current
    DESCRIPTION
             "This object allows retrieval of whether the remote OAM 
              entity supports interpreting Link Events."
     ::= { cmEthernetNetPortEntry 60 }

cmEthernetNetPortOamRemoteOamLoopbacksSupported OBJECT-TYPE
    SYNTAX     TruthValue 
    MAX-ACCESS read-only
    STATUS     current
    DESCRIPTION
             "This object allows retrieval of whether the remote OAM 
              entity supports OAM remote loopback mode."
     ::= { cmEthernetNetPortEntry 61 }

cmEthernetNetPortOamRemoteUnidirSupportEnabled OBJECT-TYPE
    SYNTAX     TruthValue 
    MAX-ACCESS read-only
    STATUS     current
    DESCRIPTION
             "This object allows retrieval of whether the remote 
              OAM entity is capable of sending OAMPDUs when the receive path 
              is non-operational."
     ::= { cmEthernetNetPortEntry 62 }

cmEthernetNetPortOamRemoteMaxPDUSize OBJECT-TYPE
    SYNTAX     Integer32
    MAX-ACCESS read-only
    STATUS     current
    DESCRIPTION
             "This object allows retrieval of the remote OAM 
              entity maximum OAMPDU size."
     ::= { cmEthernetNetPortEntry 63 }

cmEthernetNetPortOamRemoteMode OBJECT-TYPE
    SYNTAX     CmOamMode 
    MAX-ACCESS read-only
    STATUS     current
    DESCRIPTION
             "This object allows to retrieve whether the remote OAM 
              sublayer entity is either in Active or Passive mode." 
     ::= { cmEthernetNetPortEntry 64 }


-- Ethernet Port Traffic params
cmEthernetNetPortRxPauseDisposition OBJECT-TYPE
    SYNTAX     CmControlProtocolDispType
    MAX-ACCESS read-write
    STATUS     current
    DESCRIPTION
         "This object allows enabling/disabling receive pause frames on
          Ethernet Network port.  This object is not applicable 
          for FSP150CC Release 4.1 products."
     ::= { cmEthernetNetPortEntry 65 }

cmEthernetNetPortTxPauseEnabled OBJECT-TYPE
    SYNTAX     TruthValue
    MAX-ACCESS read-write
    STATUS     current
    DESCRIPTION
         "This object allows enabling/disabling transmit pause frames on
          Ethernet Network port.
          This object is not applicable for FSP150CC Release 4.1 products."
     ::= { cmEthernetNetPortEntry 66 }

cmEthernetNetPortAfpType OBJECT-TYPE
    SYNTAX     CmAfpType
    MAX-ACCESS read-write
    STATUS     current
    DESCRIPTION
         "This object allows specification of the Acceptable Frame Policy on
          Ethernet Network port. Users can specify whether the port supports
          only tagged frames, only untagged frames or both tagged and 
          untagged frames.
          This object is not applicable for FSP150CC Release 4.1 products."
     ::= { cmEthernetNetPortEntry 67 }

-- Generic Ethernet Port params
cmEthernetNetPortMDIXStatus OBJECT-TYPE
    SYNTAX     CmEthernetMDIXType
    MAX-ACCESS read-only
    STATUS     current
    DESCRIPTION
         "This object provides the current MDIX status of the 
          Ethernet Network port."
     ::= { cmEthernetNetPortEntry 68 }

cmEthernetNetPortSfpReach OBJECT-TYPE
    SYNTAX     Integer32
    MAX-ACCESS read-only
    STATUS     current
    DESCRIPTION
         "This object provides the SFP Reach in meters.
          This is applicable when cmEthernetNetPortMediaType is fiber or coppersfp."
     ::= { cmEthernetNetPortEntry 69 }

cmEthernetNetPortSfpLaserWaveLength OBJECT-TYPE
    SYNTAX     Integer32
    MAX-ACCESS read-only
    STATUS     current
    DESCRIPTION
         "This object provides the SFP Laser Wave Length in nano meters.
          This is applicable only when cmEthernetNetPortMediaType is fiber."
     ::= { cmEthernetNetPortEntry 70 }

cmEthernetNetPortSfpMediaType OBJECT-TYPE
    SYNTAX     SfpMediaType
    MAX-ACCESS read-only
    STATUS     current
    DESCRIPTION
         "This object provides the SFP Media Type.
          This is applicable when cmEthernetNetPortMediaType is fiber or coppersfp."
     ::= { cmEthernetNetPortEntry 71 }

cmEthernetNetPortOamEnabled  OBJECT-TYPE
    SYNTAX     TruthValue
    MAX-ACCESS read-write 
    STATUS     current
    DESCRIPTION
             "This object allows to manage the EFM OAM on Ethernet Network Port."
     ::= { cmEthernetNetPortEntry 72 }

cmEthernetNetPortOamAdminState OBJECT-TYPE
    SYNTAX     CmOamAdminState
    MAX-ACCESS read-only 
    STATUS     current
    DESCRIPTION
             "This object provides the EFM OAM Admin State."
     ::= { cmEthernetNetPortEntry 73 }

-- Ethernet Port Traffic params
cmEthernetNetPortShapingEnabled OBJECT-TYPE
    SYNTAX     TruthValue
    MAX-ACCESS read-write
    STATUS     current
    DESCRIPTION
         "This object allows to manage the Network Port Shaping.
          When enabled, values in cmEthernetNetPortShapedSpeedLo and
          cmEthernetNetPortShapedSpeedHi are applicable."
     ::= { cmEthernetNetPortEntry 74 }

cmEthernetNetPortShapedSpeedLo OBJECT-TYPE
    SYNTAX     Unsigned32
    MAX-ACCESS read-write
    STATUS     current
    DESCRIPTION
         "This object allows to specify the lower 32 bits of 
          the Network Port Shaped speed. This value is applicable
          when cmEthernetNetPortShapingEnabled is enabled."
     ::= { cmEthernetNetPortEntry 75 }

cmEthernetNetPortShapedSpeedHi OBJECT-TYPE
    SYNTAX     Unsigned32
    MAX-ACCESS read-write
    STATUS     current
    DESCRIPTION
         "This object allows to specify the higher 32 bits of 
          the Network Port Shaped speed. This value is applicable
          when cmEthernetNetPortShapingEnabled is enabled."
     ::= { cmEthernetNetPortEntry 76 }

cmEthernetNetPortQinQEtherType OBJECT-TYPE
    SYNTAX     Unsigned32
    MAX-ACCESS read-write
    STATUS     current
    DESCRIPTION
         "This object allows to specify the Q-in-Q Ether Type 
          on the Network Port.  Setting this value to 0 will disable
          the Q-in-Q override on the Network Port."
     ::= { cmEthernetNetPortEntry 77 }

-- Link Loss Forwarding params
cmEthernetNetPortLinkLossFwdTxActionType OBJECT-TYPE
    SYNTAX     CmLinkLossFwdTxActionType
    MAX-ACCESS read-write
    STATUS     current
    DESCRIPTION
         "This object allows to specify the Network Port's behavior when
          link loss forwarding trigger events occur on the Access Port." 
     ::= { cmEthernetNetPortEntry 78 }

cmEthernetNetPortLinkLossFwdRxRLDLinkIds OBJECT-TYPE
    SYNTAX     CmRemoteLinkIds
    MAX-ACCESS read-only
    STATUS     current
    DESCRIPTION
         "This object provides the received Remote Link IDs in 
          EFM RLD messages on the Network Port." 
     ::= { cmEthernetNetPortEntry 79 }

-- EtherJack Diagnosis params
cmEthernetNetPortAutoDiagEnabled OBJECT-TYPE
    SYNTAX     TruthValue
    MAX-ACCESS read-write
    STATUS     current
    DESCRIPTION
         "This object allows to enable or disable the automatic 
          Cable Diagnostic tests when the cable is removed from the port."
     ::= { cmEthernetNetPortEntry 80 }

--Synchronous Port params
cmEthernetNetPortSyncEEnabled OBJECT-TYPE 
    SYNTAX     TruthValue
    MAX-ACCESS read-write
    STATUS     current
    DESCRIPTION
         "This object allows to specify whether the Ethernet Network Port 
          can be enabled/disabled for Synchronous Ethernet. This object
          is only applicable for Synchronous Ethernet capable ports.
          When enabled, on receive side 
            -port can extract the frequency of its input signal
             and pass the recovered clock to the system clock
            -port processes the ESMC(Ethernet Synchronization Messaging
             Channel) and extracts the QL (when also QL enabled)   
            -port is eligible to be selected as a system clock reference
          When enabled, on transmit side 
            -port's transmit clock is locked to the system clock
            -port generates an ESMC to generate a QL (when also QL enabled)

          When disabled, on receive side,
            -port does not pass the recovered clock to the system clock 
            -port does not process the ESMC (if present) 
            -port is not eligible to be selected as a 
                     system clock reference
          When disabled, on transmit side 
            -port's output frequency may be synchronized to the system clock
            -port does not generate an ESMC."
     ::= { cmEthernetNetPortEntry 81 }

cmEthernetNetPortQLModeEnabled OBJECT-TYPE 
    SYNTAX     TruthValue
    MAX-ACCESS read-write
    STATUS     current
    DESCRIPTION
         "This object allows to specify whether the Ethernet Network Port 
          can be enabled/disabled for QL Mode. This object
          is only applicable for Synchronous Ethernet capable ports,
          when cmEthernetNetPortQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { cmEthernetNetPortEntry 82 }

cmEthernetNetPortExpectedQL OBJECT-TYPE 
    SYNTAX     SSMQualityLevel
    MAX-ACCESS read-write
    STATUS     current
    DESCRIPTION
         "This object allows to specify the expected QL when the 
          Ethernet Network Port is enabled for QL Mode. This object
          is only applicable for Synchronous Ethernet capable ports,
          when cmEthernetNetPortQLModeEnabled is set to true.
          This object allows the user to set a minimum
          expected received Quality Level on the port. The valid values
          depend upon the SYNC entity's Network Clock Type. A value of
          None represents that a minimum Quality Level is not expected. 
          The default value shall be None."
     ::= { cmEthernetNetPortEntry 83 }

cmEthernetNetPortAssumedQL OBJECT-TYPE 
    SYNTAX     SSMQualityLevel
    MAX-ACCESS read-write
    STATUS     current
    DESCRIPTION
         "This object allows to specify the assumed QL on the 
          Ethernet Network Port. This object is only applicable for 
          Synchronous Ethernet capable ports. 
          The Assumed QL is only meaningful if the Network Clock Type
          (see fsp150cm-sync.mib) is option1 and the 
          port's QL Mode is disabled and the port is being used as 
          an input reference source. Under these conditions, 
          the specified QL value is assumed to be the Quality Level of the
          non-failed reference."
     ::= { cmEthernetNetPortEntry 84 }

cmEthernetNetPortReceivedQL OBJECT-TYPE 
    SYNTAX     SSMQualityLevel
    MAX-ACCESS read-only
    STATUS     current
    DESCRIPTION
         "This object provides the Received QL value for the Ethernet port. 
          If the Ethernet port's QL Mode is disabled, then the received 
          QL value is not applicable.This object is only applicable for 
          Synchronous Ethernet capable ports."
     ::= { cmEthernetNetPortEntry 85 }

cmEthernetNetPortTransmitQL OBJECT-TYPE 
    SYNTAX     SSMQualityLevel
    MAX-ACCESS read-only
    STATUS     current
    DESCRIPTION
         "This object provides the Transmitted QL value for the Ethernet port. 
          If the Ethernet port's QL Mode is disabled, then the received 
          QL value is not applicable. This object is only applicable for 
          Synchronous Ethernet capable ports."
     ::= { cmEthernetNetPortEntry 86 }

cmEthernetNetPortPrioMapMode OBJECT-TYPE
    SYNTAX     PriorityMapMode
    MAX-ACCESS read-only
    STATUS     current
    DESCRIPTION
         "This object provides the  Priority Mapping Mode used for
          classification of frames."
     ::= { cmEthernetNetPortEntry 87 }

cmEthernetNetPortDeiEnable OBJECT-TYPE
    SYNTAX      TruthValue
    MAX-ACCESS  read-write
    STATUS      current
    DESCRIPTION
        "This is a port level control to reset the DEI 
         (Drop Eligibility Indicator) bit in the S-Tag,
         if the downstream equipment supports S-Tag TPID (EtherType) but 
         cannot handle DEI bit set. In the receive direction,
         it uses the S-TAG DEI when enabled, else ignores it."
    ::= { cmEthernetNetPortEntry 88 }

cmEthernetNetPortPcpDEEncType OBJECT-TYPE
    SYNTAX      PcpDEEncType
    MAX-ACCESS  read-write
    STATUS      current
    DESCRIPTION
        "This is a port level control that specifies the mode of drop
         eligibility encoding in PCP bits of the VLAN tag."
    ::= { cmEthernetNetPortEntry 89 }

cmEthernetNetPortPcpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetNetPortPcpDEEncType is of type 7p1d, 6p2d, 5p3d,
         the cmNetPortPcpDEPairTable can be used to specify 
         alternate pairs of priorities to specify drop eligibility/
         ineligibility."
    ::= { cmEthernetNetPortEntry 90 }

cmEthernetNetPortSSMRemoteMacAddress OBJECT-TYPE
    SYNTAX     MacAddress
    MAX-ACCESS read-only
    STATUS     current
    DESCRIPTION
             "This object allows retrieval of the Remote Mac Address, when
              the port is peering using SSM." 
     ::= { cmEthernetNetPortEntry 91 }

cmEthernetNetPortXgePhyType OBJECT-TYPE
    SYNTAX      XgePhyType  
    MAX-ACCESS  read-write
    STATUS      current
    DESCRIPTION
        "This object allows to specify the PHY type of 10G Ethernet Port.
         10G ports can operate in LAN-PHY or WAN-PHY mode. The default mode is LAN-PHY
         and port rate in this mode is 10Gbps. In WAN-PHY mode the port rate is 9.29Gbps.
         This attribute is only applicable for ports configured to work at speed-10G-full.
         For other speeds the value of this object must be 'not-applicable' and cannot
         be changed.
        "
    ::= { cmEthernetNetPortEntry 92 }

cmEthernetNetPortLoopbackSourceMacControlEnabled OBJECT-TYPE
    SYNTAX      TruthValue  
    MAX-ACCESS  read-write
    STATUS      current
    DESCRIPTION
         "This object allows to Enable/Disable the Net Port Source MAC 
         Address frame matching criteria for all streams. 
         Not applicable for: efm-oam-remote, efm-oam-remote-timed."
    ::= { cmEthernetNetPortEntry 93 }

cmEthernetNetPortLoopbackDestMacControlEnabled OBJECT-TYPE
    SYNTAX      TruthValue  
    MAX-ACCESS  read-write
    STATUS      current
    DESCRIPTION
         "This object allows to Enable/Disable the Net Port Destination MAC 
         Address frame matching criteria for all streams. 
         Not applicable for: efm-oam-remote, efm-oam-remote-timed."
    ::= { cmEthernetNetPortEntry 94 }

cmEthernetNetPortLoopbackSourceMacAddress OBJECT-TYPE
    SYNTAX      MacAddress  
    MAX-ACCESS  read-write
    STATUS      current
    DESCRIPTION
         "This object allows to set Net Port Source MAC Address for frame 
          matching when Net Port Source MAC Control is enabled."
    ::= { cmEthernetNetPortEntry 95 }

cmEthernetNetPortLoopbackDestMacAddress OBJECT-TYPE
    SYNTAX      MacAddress  
    MAX-ACCESS  read-write
    STATUS      current
    DESCRIPTION
         "This object allows to set Net Port Destination MAC Address for frame 
          matching when Net Port Destination MAC Control is enabled."
    ::= { cmEthernetNetPortEntry 96 }

cmEthernetNetPortLoopbackBlockingEnabled OBJECT-TYPE
    SYNTAX      TruthValue  
    MAX-ACCESS  read-write
    STATUS      current
    DESCRIPTION
        "This object allows frame blocking when loopback is active.
         - True: Blocks frames in the non-loopback direction 
           that match the PORT or VLAN received in the 
           non-loopback direction. Discards  frames 
           in the loopback direction that match 
           the PORT or VLAN, but do not match 
           the MAC address criteria,
         - False: No blocking of  frames."
    ::= { cmEthernetNetPortEntry 97 }

--
--  Ethernet Network Port Control Protocol Disposition 
--
cmEthernetNetPortCpdTable  OBJECT-TYPE
    SYNTAX      SEQUENCE OF CmEthernetNetPortCpdEntry
    MAX-ACCESS  not-accessible
    STATUS      current
    DESCRIPTION
            "A list of entries corresponding to Ethernet Network Port 
             Control Protocol Disposition.
             This table is only
             applicable for FSP150CM Hub Shelf Release 3.x."
    ::= { cmFacilityObjects 8 }

cmEthernetNetPortCpdEntry OBJECT-TYPE
    SYNTAX      CmEthernetNetPortCpdEntry 
    MAX-ACCESS  not-accessible
    STATUS      current
    DESCRIPTION
            "A conceptual row in the cmEthernetNetPortCpdTable. 
             These entries represent a Control Protocol Disposition 
             filtering criteria on the Ethernet Network Port."
    INDEX { neIndex, shelfIndex, slotIndex, cmEthernetNetPortIndex, 
            cmEthernetNetPortCpdIndex }
    ::= { cmEthernetNetPortCpdTable 1 }


CmEthernetNetPortCpdEntry ::= SEQUENCE {
    -- Index
    cmEthernetNetPortCpdIndex             Integer32,

    -- CPD Filter Params
    cmEthernetNetPortCpdFilterType        CmControlProtocolFilterType,
    cmEthernetNetPortCpdFilterDescr       DisplayString,
    cmEthernetNetPortCpdDispType          CmControlProtocolDispType,
    cmEthernetNetPortCpdMacAddressMatch   MacAddress,
    cmEthernetNetPortCpdMacAddressMask    MacAddress,
    cmEthernetNetPortCpdEthertype         Integer32,
    cmEthernetNetPortCpdEthertypeMask     Integer32,
    cmEthernetNetPortCpdSubtype           Integer32,
    cmEthernetNetPortCpdSubtypeMask       Integer32
}

cmEthernetNetPortCpdIndex OBJECT-TYPE
    SYNTAX      Integer32 (1..65535)
    MAX-ACCESS  read-only
    STATUS      current
    DESCRIPTION
            "An arbitrary integer index value used to uniquely identify
             this CPD Service Entry."
    ::= { cmEthernetNetPortCpdEntry 1 }

cmEthernetNetPortCpdFilterType OBJECT-TYPE
    SYNTAX     CmControlProtocolFilterType
    MAX-ACCESS read-only
    STATUS     current
    DESCRIPTION
            "This enables specification of type of CPD Filter."
    ::= { cmEthernetNetPortCpdEntry 2 }

cmEthernetNetPortCpdFilterDescr OBJECT-TYPE
    SYNTAX  DisplayString (SIZE (0..32)) 
    MAX-ACCESS read-only
    STATUS     current
    DESCRIPTION
            "This provides description of CPD Filter."
    ::= { cmEthernetNetPortCpdEntry 3 }

cmEthernetNetPortCpdDispType OBJECT-TYPE
    SYNTAX     CmControlProtocolDispType
    MAX-ACCESS read-write
    STATUS     current
    DESCRIPTION
            "This enables specification of disposion type of CPD Filter."
    ::= { cmEthernetNetPortCpdEntry 4 }

cmEthernetNetPortCpdMacAddressMatch OBJECT-TYPE
    SYNTAX     MacAddress
    MAX-ACCESS read-write
    STATUS     current
    DESCRIPTION
         "This enables provides the Filter MAC Address to match."
    ::= { cmEthernetNetPortCpdEntry 5 }

cmEthernetNetPortCpdMacAddressMask OBJECT-TYPE
    SYNTAX     MacAddress
    MAX-ACCESS read-write
    STATUS     current
    DESCRIPTION
         "This enables provides the Filter MAC Address Mask to match."
    ::= { cmEthernetNetPortCpdEntry 6 }

cmEthernetNetPortCpdEthertype OBJECT-TYPE
    SYNTAX     Integer32 (0..65535)
    MAX-ACCESS read-write
    STATUS     current
    DESCRIPTION
         "This enables provides the Filter Ethertype to match."
    ::= { cmEthernetNetPortCpdEntry 7 }

cmEthernetNetPortCpdEthertypeMask OBJECT-TYPE
    SYNTAX     Integer32
    MAX-ACCESS read-write
    STATUS     current
    DESCRIPTION
         "This enables provides the Filter Ethertype Mask to match."
    ::= { cmEthernetNetPortCpdEntry 8 }

cmEthernetNetPortCpdSubtype OBJECT-TYPE
    SYNTAX     Integer32
    MAX-ACCESS read-write
    STATUS     current
    DESCRIPTION
         "This enables provides the Filter Subtype to match."
    ::= { cmEthernetNetPortCpdEntry 9 }

cmEthernetNetPortCpdSubtypeMask OBJECT-TYPE
    SYNTAX     Integer32
    MAX-ACCESS read-write
    STATUS     current
    DESCRIPTION
         "This enables provides the Filter Subtype Mask to match."
    ::= { cmEthernetNetPortCpdEntry 10 }


--
--  Ethernet Management Port 
--
cmEthernetMgmtPortTable  OBJECT-TYPE
    SYNTAX      SEQUENCE OF CmEthernetMgmtPortEntry
    MAX-ACCESS  not-accessible
    STATUS      current
    DESCRIPTION
            "A list of entries corresponding to Ethernet Management Port 
             Facilities for configuration purposes."
    ::= { cmFacilityObjects 9 }

cmEthernetMgmtPortEntry OBJECT-TYPE
    SYNTAX      CmEthernetMgmtPortEntry 
    MAX-ACCESS  not-accessible
    STATUS      current
    DESCRIPTION
            "A conceptual row in the cmEthernetMgmtPortTable."
    INDEX { neIndex, shelfIndex, slotIndex, cmEthernetMgmtPortIndex }
    ::= { cmEthernetMgmtPortTable 1 }

CmEthernetMgmtPortEntry ::= SEQUENCE {
    -- Port Indices 
    cmEthernetMgmtPortIndex                  Integer32,
    cmEthernetMgmtPortEntityIndex            PhysicalIndex,

    -- State Management params
    cmEthernetMgmtPortAdminState             AdminState,
    cmEthernetMgmtPortOperationalState       OperationalState,
    cmEthernetMgmtPortSecondaryState         SecondaryState,

    -- Generic Port params
    cmEthernetMgmtPortMTU                    Integer32,

    -- Generic Ethernet Port params
    cmEthernetMgmtPortConfigSpeed            EthernetPortSpeed,
    cmEthernetMgmtPortNegotiatedSpeed        EthernetPortSpeed,
    cmEthernetMgmtPortMDIXType               CmEthernetMDIXType,

    --New objects available with FSP150CC GE206 device (Release 4.1CC)
    cmEthernetMgmtPortMDIXStatus             CmEthernetMDIXType,  

    cmEthernetMgmtPortMediaType              EthernetMediaType
}
    
-- Port Indices 
cmEthernetMgmtPortIndex OBJECT-TYPE
    SYNTAX      Integer32 (1..65535)
    MAX-ACCESS  read-only
    STATUS      current
    DESCRIPTION
            "An integer index value used to uniquely identify
             this Ethernet Management Port within a card.
             Note that each Ethernet Management Port is uniquely identified
             by the indices neIndex, shelfIndex, 
             slotIndex, cmEthernetMgmtPortIndex." 
    ::= { cmEthernetMgmtPortEntry 1 }

cmEthernetMgmtPortEntityIndex OBJECT-TYPE
    SYNTAX      PhysicalIndex 
    MAX-ACCESS  read-only
    STATUS      current
    DESCRIPTION
           "Entity Index from ENTITY-MIB for this port."
    ::= { cmEthernetMgmtPortEntry 2 }

-- State Management params
cmEthernetMgmtPortAdminState OBJECT-TYPE
    SYNTAX      AdminState 
    MAX-ACCESS  read-write
    STATUS      current
    DESCRIPTION
            "This object represents the Administrative State of the Ethernet 
             Management Port."
    ::= { cmEthernetMgmtPortEntry 3 }

cmEthernetMgmtPortOperationalState OBJECT-TYPE
    SYNTAX      OperationalState 
    MAX-ACCESS  read-only
    STATUS      current
    DESCRIPTION
            "This object represents the Operational State of the Ethernet 
             Management Port."
    ::= { cmEthernetMgmtPortEntry 4 }

cmEthernetMgmtPortSecondaryState OBJECT-TYPE
    SYNTAX      SecondaryState 
    MAX-ACCESS  read-only
    STATUS      current
    DESCRIPTION
            "This object represents the Secondary State of the Ethernet 
             Management Port."
    ::= { cmEthernetMgmtPortEntry 5 }

-- Generic Port params
cmEthernetMgmtPortMTU OBJECT-TYPE
    SYNTAX      Integer32 
    MAX-ACCESS  read-only
    STATUS      current
    DESCRIPTION
            "This object provides the MTU on the Ethernet Management Port."
    ::= { cmEthernetMgmtPortEntry 6 }

cmEthernetMgmtPortConfigSpeed OBJECT-TYPE
    SYNTAX     EthernetPortSpeed
    MAX-ACCESS read-write
    STATUS     current
    DESCRIPTION
            "This object allows to configure the speed of the 
             Ethernet Management Port."
    ::= { cmEthernetMgmtPortEntry 7 }

cmEthernetMgmtPortNegotiatedSpeed OBJECT-TYPE
    SYNTAX     EthernetPortSpeed
    MAX-ACCESS read-only
    STATUS     current
    DESCRIPTION
            "This object provides the negotiated speed of the 
             Ethernet Management Port."
    ::= { cmEthernetMgmtPortEntry 8 }

cmEthernetMgmtPortMDIXType OBJECT-TYPE
    SYNTAX     CmEthernetMDIXType
    MAX-ACCESS read-write
    STATUS     current
    DESCRIPTION
            "This object allows management of MDIX property on  
             Ethernet Management Port."
    ::= { cmEthernetMgmtPortEntry 9 }

cmEthernetMgmtPortMDIXStatus OBJECT-TYPE
    SYNTAX     CmEthernetMDIXType
    MAX-ACCESS read-only
    STATUS     current
    DESCRIPTION
         "This object provides the current MDIX status of the 
          Ethernet Management port."
     ::= { cmEthernetMgmtPortEntry 10 }

cmEthernetMgmtPortMediaType OBJECT-TYPE
    SYNTAX     EthernetMediaType
    MAX-ACCESS read-only
    STATUS     current
    DESCRIPTION
            "This object represents the type of Ethernet Media on the 
             Ethernet Management Port."
    ::= { cmEthernetMgmtPortEntry 11 }


--Priority Mapping
cmPrioMapTable  OBJECT-TYPE
    SYNTAX      SEQUENCE OF CmPrioMapEntry
    MAX-ACCESS  not-accessible
    STATUS      current
    DESCRIPTION
            "A list of entries corresponding to Ethernet Priority Mappings
             in multi Class of Service (COS) mode. This table is applicable
             only when the Access Port is in connection-oriented evpl mode."
    ::= { cmFacilityObjects 10 }

cmPrioMapEntry OBJECT-TYPE
    SYNTAX      CmPrioMapEntry
    MAX-ACCESS  not-accessible
    STATUS      current
    DESCRIPTION
            "A conceptual row in the cmPrioMapTable."
    INDEX { neIndex, shelfIndex, slotIndex, 
            cmEthernetAccPortIndex, cmPrioMapIndex }
    ::= { cmPrioMapTable 1 }

CmPrioMapEntry ::= SEQUENCE {
    cmPrioMapIndex            Integer32,
    cmPrioMapInPriority       Integer32,
    cmPrioMapXTagControl      PrioMapControlType,
    cmPrioMapXTagPriority     VlanPriority,
    cmPrioMapCOS              Integer32,
    cmPrioMapOuterTagPriority VlanPriority,
    cmPrioMapInnerTagPriority VlanPriority
}

cmPrioMapIndex OBJECT-TYPE
    SYNTAX      Integer32 (1..64)
    MAX-ACCESS  read-only
    STATUS      current
    DESCRIPTION
            "The integer index value corresponding to a priority value
             based on the cmEthernetAccPortPrioMapMode.
             In case of TOS and 8021P, valid indices are 1 to 8,
             in case of DSCP, valid indices are 1 to 64."
    ::= { cmPrioMapEntry 1 }

cmPrioMapInPriority OBJECT-TYPE
    SYNTAX      Integer32 (0..63)
    MAX-ACCESS  read-write
    STATUS      current
    DESCRIPTION
            "The integer index value corresponding to a priority value
             based on the cmEthernetAccPortPrioMapMode.
             In case of TOS and 8021P, valid indices are 0 to 7,
             in case of DSCP, valid indices are 0 to 63."
    ::= { cmPrioMapEntry 2 }

cmPrioMapXTagControl OBJECT-TYPE
    SYNTAX      PrioMapControlType
    MAX-ACCESS  read-write
    STATUS      current
    DESCRIPTION
            "This allows specification of whether the priority of
             incoming X-TAG should be swapped with cmPrioMapXTagPriority."
    ::= { cmPrioMapEntry 3 }

cmPrioMapXTagPriority OBJECT-TYPE
    SYNTAX      VlanPriority
    MAX-ACCESS  read-write
    STATUS      current
    DESCRIPTION
            "This allows specification of the VLAN priority that
             will replace the incoming X-TAG's priority.  This is
             applicable with cmPrioMapXTagControl as 'swap'."
    ::= { cmPrioMapEntry 4 }

cmPrioMapCOS OBJECT-TYPE
    SYNTAX      Integer32 (0..7)
    MAX-ACCESS  read-write
    STATUS      current
    DESCRIPTION
            "This allows specification of the COS Priority, i.e.
             this helps in determining the appropriate COS Policer for
             the Flow."
    ::= { cmPrioMapEntry 5 }

cmPrioMapOuterTagPriority OBJECT-TYPE
    SYNTAX      VlanPriority
    MAX-ACCESS  read-write
    STATUS      current
    DESCRIPTION
            "This allows specification of the VLAN priority that
             will replace the outgoing (A2N direction) outer-tag's priority.  
             Note that, each flow participates or not in outer-tag 
             priority mapping, using the object 'cmFlowOuterTagPrioEnabled'."
    ::= { cmPrioMapEntry 6 }

cmPrioMapInnerTagPriority OBJECT-TYPE
    SYNTAX      VlanPriority
    MAX-ACCESS  read-write
    STATUS      current
    DESCRIPTION
            "This allows specification of the VLAN priority that
             will replace the outgoing (A2N direction) inner-tag's (i.e. second tag) 
             priority.  Note that, each flow participates or not in inner-tag 
             priority mapping, using the object 'cmFlowInnerTagPrioEnabled'."
    ::= { cmPrioMapEntry 7 }

--Flow Policer
cmQosFlowPolicerTable  OBJECT-TYPE
    SYNTAX      SEQUENCE OF CmQosFlowPolicerEntry
    MAX-ACCESS  not-accessible
    STATUS      current
    DESCRIPTION
        "A list of entries corresponding to Ethernet Quality of Service 
         Policer for configuration purposes."
    ::= { cmFacilityObjects 11 }

cmQosFlowPolicerEntry OBJECT-TYPE
    SYNTAX      CmQosFlowPolicerEntry 
    MAX-ACCESS  not-accessible
    STATUS      current
    DESCRIPTION
         "A conceptual row in the cmQosFlowPolicerTable. 
          These entries represent a Quality of Service Policer."
    INDEX { neIndex, shelfIndex, slotIndex, cmEthernetAccPortIndex, 
            cmFlowIndex, cmQosFlowPolicerTypeIndex, cmQosFlowPolicerIndex }
    ::= { cmQosFlowPolicerTable 1 }

CmQosFlowPolicerEntry ::= SEQUENCE {
    cmQosFlowPolicerTypeIndex             Integer32,
    cmQosFlowPolicerIndex                 Integer32,
    cmQosFlowPolicerDirection             TrafficDirection,

    -- State Management params
    cmQosFlowPolicerAdminState            AdminState,
    cmQosFlowPolicerOperationalState      OperationalState,
    cmQosFlowPolicerSecondaryState        SecondaryState,

    cmQosFlowPolicerCIRLo                 Unsigned32,
    cmQosFlowPolicerCIRHi                 Unsigned32,
    cmQosFlowPolicerEIRLo                 Unsigned32,
    cmQosFlowPolicerEIRHi                 Unsigned32,
    cmQosFlowPolicerCBS                   Integer32,
    cmQosFlowPolicerEBS                   Integer32,
    cmQosFlowPolicerAlgorithm             PolicerAlgorithmType,
    cmQosFlowPolicerColorMode             PolicerColorMode,
    cmQosFlowPolicerColorMarkingFlag      TruthValue,
    cmQosFlowPolicerCouplingFlag          TruthValue,
    cmQosFlowPolicerAssociatedShaper      VariablePointer,
    cmQosFlowPolicerStorageType           StorageType,
    cmQosFlowPolicerRowStatus             RowStatus 
}

cmQosFlowPolicerTypeIndex OBJECT-TYPE
    SYNTAX      Integer32 (1..4)
    MAX-ACCESS  read-create
    STATUS      current
    DESCRIPTION
            "The unique index value corresponding to a Quality of Service 
             Policer's direction.
             Values 1 and 2 are applicable to the Access Flow Policer
              - value of 1 stands for A2N direction,
              - value of 2 stands for N2A direction.
             Values 3 and 4 are applicable to Pass-thru Flow Policer 
               (new in 5.6CC release):
               - value of 3 stands for N1toN2 direction
               - value of 4 stands for N2toN1 direction
           "
    ::= { cmQosFlowPolicerEntry 1 }

cmQosFlowPolicerIndex OBJECT-TYPE
    SYNTAX      Integer32 (1..16)
    MAX-ACCESS  read-create
    STATUS      current
    DESCRIPTION
            "The Policer Index that represents the COS level.  This
             is applicable in case of a Multi COS flow. Index 1
             represents COS 0; Index 2 represents COS 1 and so on. 

             In release 5.6CC the range is extended to 1..16 to support duplicate
             N2A policers on a Flow. The duplicate policers are created under a Flow 
             if network interface of the Flow is ERP Group or Split Horizon Group. 
             In case of multi-cos Flow indices 1..8 represent policers of COS 0..7 
             going from Network 1 port; indices 9..16 represent policers for COS 0..7 
             going from Network 2 port.
             In case of single-cos Flow index 1 represents policer going from Network 1
             port; index 9 represents policer going from Network 2 port.
             "
    ::= { cmQosFlowPolicerEntry 2 }

cmQosFlowPolicerDirection OBJECT-TYPE
    SYNTAX      TrafficDirection 
    MAX-ACCESS  read-create
    STATUS      current
    DESCRIPTION
            "This object is allows specification of Policer direction as
             'a2n' or 'n2a'."
    ::= { cmQosFlowPolicerEntry 3 }

-- State Management params
cmQosFlowPolicerAdminState OBJECT-TYPE
    SYNTAX      AdminState 
    MAX-ACCESS  read-write
    STATUS      current
    DESCRIPTION
            "This object represents the Administrative State of 
             the QOS Flow Policer." 
    ::= { cmQosFlowPolicerEntry 4 }

cmQosFlowPolicerOperationalState OBJECT-TYPE
    SYNTAX      OperationalState 
    MAX-ACCESS  read-only
    STATUS      current
    DESCRIPTION
            "This object represents the Operational State of the QOS Flow Policer." 
    ::= { cmQosFlowPolicerEntry 5 }

cmQosFlowPolicerSecondaryState OBJECT-TYPE
    SYNTAX      SecondaryState 
    MAX-ACCESS  read-only
    STATUS      current
    DESCRIPTION
            "This object represents the Secondary State of the QOS Flow Policer." 
    ::= { cmQosFlowPolicerEntry 6 }

cmQosFlowPolicerCIRLo OBJECT-TYPE
    SYNTAX     Unsigned32
    MAX-ACCESS read-create
    STATUS     current
    DESCRIPTION
         "This object allows specification of the Commited Information
          Rate(CIR) on Policer.  This represents the lower 32 bits of the
          CIR."
     ::= { cmQosFlowPolicerEntry 7 }

cmQosFlowPolicerCIRHi OBJECT-TYPE
    SYNTAX     Unsigned32
    MAX-ACCESS read-create
    STATUS     current
    DESCRIPTION
         "This object allows specification of the Commited Information
          Rate(CIR) on Policer.  This represents the upper 32 bits of the
          CIR."
     ::= { cmQosFlowPolicerEntry 8 }

cmQosFlowPolicerEIRLo OBJECT-TYPE
    SYNTAX     Unsigned32
    MAX-ACCESS read-create
    STATUS     current
    DESCRIPTION
         "This object allows specification of the Excess Information
          Rate(EIR) on the Policer.  This represents the lower 32 bits
          of the EIR."
     ::= { cmQosFlowPolicerEntry 9 }

cmQosFlowPolicerEIRHi OBJECT-TYPE
    SYNTAX     Unsigned32
    MAX-ACCESS read-create
    STATUS     current
    DESCRIPTION
         "This object allows specification of the Excess Information
          Rate(EIR) on the Policer.  This represents the upper 32 bits
          of the EIR."
     ::= { cmQosFlowPolicerEntry 10 }

cmQosFlowPolicerCBS OBJECT-TYPE
    SYNTAX     Integer32
    MAX-ACCESS read-create
    STATUS     current
    DESCRIPTION
         "This object allows specification of the Commited Burst Size
          (CBS) on Policer."
     ::= { cmQosFlowPolicerEntry 11 }

cmQosFlowPolicerEBS OBJECT-TYPE
    SYNTAX     Integer32
    MAX-ACCESS read-create
    STATUS     current
    DESCRIPTION
         "This object allows specification of the Excess Burst Size
          (EBS) on the Policer."
     ::= { cmQosFlowPolicerEntry 12 }

cmQosFlowPolicerAlgorithm OBJECT-TYPE
    SYNTAX      PolicerAlgorithmType 
    MAX-ACCESS  read-only
    STATUS      current
    DESCRIPTION
          "This object allows specification of Policer algorithm as
           'srTCM' (Single Rate Triple Color Marking) or 'trTCM' (Two Rate
           Triple Color Marking)."
    ::= { cmQosFlowPolicerEntry 13 }

cmQosFlowPolicerColorMode OBJECT-TYPE
    SYNTAX      PolicerColorMode 
    MAX-ACCESS  read-create
    STATUS      current
    DESCRIPTION
          "This object allows specification of Policer Color Mode as
           'color-aware' or 'color-blind'."
    ::= { cmQosFlowPolicerEntry 14 }

cmQosFlowPolicerColorMarkingFlag OBJECT-TYPE
    SYNTAX      TruthValue 
    MAX-ACCESS  read-create
    STATUS      deprecated
    DESCRIPTION
          "This object allows specification of Policer Color Marking Flag.
           The policer will set/clear the DEI (Drop Eligibility Indication) 
           bit of the frame on an S-TAG if this flag is enabled.
           This object is not supported - setting any value will not have effect
           on the System."
    ::= { cmQosFlowPolicerEntry 15 }

cmQosFlowPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { cmQosFlowPolicerEntry 16 }

cmQosFlowPolicerAssociatedShaper OBJECT-TYPE
    SYNTAX     VariablePointer 
    MAX-ACCESS read-create
    STATUS     current
    DESCRIPTION
         "This object allows specification of the QOS Shaper
          associated with this Policer. Multiple Policers can map
          to single Shaper. The corresponding row with the 
          specified QOS value must exist in 
          cmQosShaperTable when this value is specified."
     ::= { cmQosFlowPolicerEntry 17 }

cmQosFlowPolicerStorageType OBJECT-TYPE
    SYNTAX     StorageType
    MAX-ACCESS read-create
    STATUS     current
    DESCRIPTION
            "The type of storage configured for this entry."
    ::= { cmQosFlowPolicerEntry 18 }

cmQosFlowPolicerRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosFlowPolicerRowStatus supported are
            createAndGo(4) and destroy(6).  All mandatory attributes
            must be specified in a single SNMP SET request with
            cmQosFlowPolicerRowStatus value as createAndGo(4).
            Upon successful row creation, this object has a
            value of active(1).

            The cmQosFlowPolicerRowStatus object may be modified if
            the associated instance of this object is equal to active(1)."
    ::= { cmQosFlowPolicerEntry 19 }


--
--  Ethernet Access Port Quality of Service Shaper 
--
cmAccPortQosShaperTable  OBJECT-TYPE
    SYNTAX      SEQUENCE OF CmAccPortQosShaperEntry
    MAX-ACCESS  not-accessible
    STATUS      current
    DESCRIPTION
            "A list of entries corresponding to Ethernet Access Port 
             Quality of Service Shaper for configuration purposes.
             These shapers can be managed when the Access Port is
             in evpl mode and are relevant for traffic in the
             network to access direction."
    ::= { cmFacilityObjects 12 }

cmAccPortQosShaperEntry OBJECT-TYPE
    SYNTAX      CmAccPortQosShaperEntry 
    MAX-ACCESS  not-accessible
    STATUS      current
    DESCRIPTION
            "A conceptual row in the cmAccPortQosShaperTable. 
             These entries represent a Quality of Service Shaper."
    INDEX { neIndex, shelfIndex, slotIndex, cmEthernetAccPortIndex, 
            cmAccPortQosShaperIndex }
    ::= { cmAccPortQosShaperTable 1 }

CmAccPortQosShaperEntry ::= SEQUENCE {
    -- QOS Shaper Index/Id
    cmAccPortQosShaperIndex               Integer32,
    cmAccPortQosShaperDirection           TrafficDirection,

    -- State Management params
    cmAccPortQosShaperAdminState          AdminState,
    cmAccPortQosShaperOperationalState    OperationalState,
    cmAccPortQosShaperSecondaryState      SecondaryState,

    -- QOS Shaper Properties
    cmAccPortQosShaperCIRLo               Unsigned32,
    cmAccPortQosShaperCIRHi               Unsigned32,
    cmAccPortQosShaperEIRLo               Unsigned32,
    cmAccPortQosShaperEIRHi               Unsigned32,
    cmAccPortQosShaperCBS                 Unsigned32,
    cmAccPortQosShaperEBS                 Unsigned32,
    cmAccPortQosShaperBufferSize          Unsigned32,
    cmAccPortQosShaperCOS                 Integer32,
    cmAccPortQosShaperSoamCIRLo           Unsigned32,
    cmAccPortQosShaperSoamCIRHi           Unsigned32,
    cmAccPortQosShaperSoamEIRLo           Unsigned32,
    cmAccPortQosShaperSoamEIRHi           Unsigned32
}

cmAccPortQosShaperIndex OBJECT-TYPE
    SYNTAX      Integer32 (1..8)
    MAX-ACCESS  read-create
    STATUS      current
    DESCRIPTION
            "The unique integer index value corresponding to a 
             Quality of Service Shaper."
    ::= { cmAccPortQosShaperEntry 1 }

cmAccPortQosShaperDirection OBJECT-TYPE
    SYNTAX      TrafficDirection 
    MAX-ACCESS  read-only
    STATUS      current
    DESCRIPTION
            "The direction of the Quality of Service Shaper."
    ::= { cmAccPortQosShaperEntry 2 }

-- State Management params
cmAccPortQosShaperAdminState OBJECT-TYPE
    SYNTAX      AdminState 
    MAX-ACCESS  read-write
    STATUS      current
    DESCRIPTION
            "This object represents the Administrative State of 
             the QOS Shaper." 
    ::= { cmAccPortQosShaperEntry 3 }

cmAccPortQosShaperOperationalState OBJECT-TYPE
    SYNTAX      OperationalState 
    MAX-ACCESS  read-only
    STATUS      current
    DESCRIPTION
            "This object represents the Operational State of the QOS Shaper." 
    ::= { cmAccPortQosShaperEntry 4 }

cmAccPortQosShaperSecondaryState OBJECT-TYPE
    SYNTAX      SecondaryState 
    MAX-ACCESS  read-only
    STATUS      current
    DESCRIPTION
            "This object represents the Secondary State of the QOS Shaper." 
    ::= { cmAccPortQosShaperEntry 5 }

cmAccPortQosShaperCIRLo OBJECT-TYPE
    SYNTAX     Unsigned32
    MAX-ACCESS read-create
    STATUS     current
    DESCRIPTION
         "This object represents the Commited Information
          Rate(CIR) (Lower 32 bits)of a Shaper."
     ::= { cmAccPortQosShaperEntry 6 }

cmAccPortQosShaperCIRHi OBJECT-TYPE
    SYNTAX     Unsigned32
    MAX-ACCESS read-create
    STATUS     current
    DESCRIPTION
         "This object represents the Commited Information
          Rate(CIR) (Higher 32 bits) of a Shaper."
     ::= { cmAccPortQosShaperEntry 7 }

cmAccPortQosShaperEIRLo OBJECT-TYPE
    SYNTAX     Unsigned32
    MAX-ACCESS read-create
    STATUS     current
    DESCRIPTION
         "This object represents the Excess Information
          Rate(EIR) (Higher 32 bits) on the Shaper."
     ::= { cmAccPortQosShaperEntry 8 }

cmAccPortQosShaperEIRHi OBJECT-TYPE
    SYNTAX     Unsigned32
    MAX-ACCESS read-create
    STATUS     current
    DESCRIPTION
         "This object represents the Excess Information
          Rate(EIR) (Higher 32 bits) on the Shaper."
     ::= { cmAccPortQosShaperEntry 9 }

cmAccPortQosShaperCBS OBJECT-TYPE
    SYNTAX     Unsigned32
    MAX-ACCESS read-create
    STATUS     current
    DESCRIPTION
         "This object represents the Commited Burst Size (CBS) of the Shaper."
     ::= { cmAccPortQosShaperEntry 10 }

cmAccPortQosShaperEBS OBJECT-TYPE
    SYNTAX     Unsigned32
    MAX-ACCESS read-create
    STATUS     current
    DESCRIPTION
         "This object represents the Excess Burst Size (EBS) of the Shaper."
     ::= { cmAccPortQosShaperEntry 11 }

cmAccPortQosShaperBufferSize OBJECT-TYPE
    SYNTAX     Unsigned32
    MAX-ACCESS read-create
    STATUS     current
    DESCRIPTION
         "This object represents the Buffer Size of the Shaper."
     ::= { cmAccPortQosShaperEntry 12 }

cmAccPortQosShaperCOS OBJECT-TYPE
    SYNTAX     Integer32 (0..7)
    MAX-ACCESS read-only
    STATUS     current
    DESCRIPTION
            "This object provides the COS (Class of Service)
             value for the QOS Shaper."
    ::= { cmAccPortQosShaperEntry 13 }

cmAccPortQosShaperSoamCIRLo OBJECT-TYPE
    SYNTAX     Unsigned32
    MAX-ACCESS read-create
    STATUS     current
    DESCRIPTION
         "This object represents the Soam Commited Information
          Rate(SOAM-CIR) (Lower 32 bits)of a Shaper."
     ::= { cmAccPortQosShaperEntry 14 }

cmAccPortQosShaperSoamCIRHi OBJECT-TYPE
    SYNTAX     Unsigned32
    MAX-ACCESS read-create
    STATUS     current
    DESCRIPTION
         "This object represents the Soam Commited Information
          Rate(SOAM-CIR) (Higher 32 bits) of a Shaper."
     ::= { cmAccPortQosShaperEntry 15 }

cmAccPortQosShaperSoamEIRLo OBJECT-TYPE
    SYNTAX     Unsigned32
    MAX-ACCESS read-create
    STATUS     current
    DESCRIPTION
         "This object represents the Soam Excess Information
          Rate(SOAM-EIR) (Higher 32 bits) on the Shaper."
     ::= { cmAccPortQosShaperEntry 16 }

cmAccPortQosShaperSoamEIRHi OBJECT-TYPE
    SYNTAX     Unsigned32
    MAX-ACCESS read-create
    STATUS     current
    DESCRIPTION
         "This object represents the Soam Excess Information
          Rate(SOAM-EIR) (Higher 32 bits) on the Shaper."
     ::= { cmAccPortQosShaperEntry 17 }
--
--
--  Ethernet Access Port Control Protocol Disposition V2
--
cmEthernetAccPortCpdV2Table  OBJECT-TYPE
    SYNTAX      SEQUENCE OF CmEthernetAccPortCpdV2Entry
    MAX-ACCESS  not-accessible
    STATUS      current
    DESCRIPTION
            "A list of entries corresponding to Ethernet Access Port 
             Control Protocol Disposition (CPD) V2.  This support of
             CPD is provided on the GE206/GE201 device."
    ::= { cmFacilityObjects 13 }

cmEthernetAccPortCpdV2Entry OBJECT-TYPE
    SYNTAX      CmEthernetAccPortCpdV2Entry 
    MAX-ACCESS  not-accessible
    STATUS      current
    DESCRIPTION
            "A conceptual row in the cmEthernetAccPortCpdV2Table. 
             These entries represent a Control Protocol Disposition 
             filtering criteria on the Ethernet Access Port."
    INDEX { neIndex, shelfIndex, slotIndex, cmEthernetAccPortIndex, 
            cmEthernetAccPortCpdV2Index }
    ::= { cmEthernetAccPortCpdV2Table 1 }

CmEthernetAccPortCpdV2Entry ::= SEQUENCE {
    -- Index
    cmEthernetAccPortCpdV2Index            Integer32,

    -- Filtering Criteria
    cmEthernetAccPortCpdV2CiscoGroupDispType        CmControlProtocolDispType,
    cmEthernetAccPortCpdV2IslDispType               CmControlProtocolDispType,
    cmEthernetAccPortCpdV2PagpDispType              CmControlProtocolDispType,
    cmEthernetAccPortCpdV2UdldDispType              CmControlProtocolDispType,
    cmEthernetAccPortCpdV2CdpDispType               CmControlProtocolDispType,
    cmEthernetAccPortCpdV2VtpDispType               CmControlProtocolDispType,
    cmEthernetAccPortCpdV2DtpDispType               CmControlProtocolDispType,
    cmEthernetAccPortCpdV2PvstpPlusDispType         CmControlProtocolDispType,
    cmEthernetAccPortCpdV2UplinkFastDispType        CmControlProtocolDispType,
    cmEthernetAccPortCpdV2VlanBridgeDispType        CmControlProtocolDispType,
    cmEthernetAccPortCpdV2L2PTDispType              CmControlProtocolDispType,
    cmEthernetAccPortCpdV2BridgeGroupDispType       CmControlProtocolDispType,
    cmEthernetAccPortCpdV2BPDUDispType              CmControlProtocolDispType,
    cmEthernetAccPortCpdV2PauseDispType             CmControlProtocolDispType,
    cmEthernetAccPortCpdV2LACPDispType              CmControlProtocolDispType,
    cmEthernetAccPortCpdV2LACPMarkerDispType        CmControlProtocolDispType,
    cmEthernetAccPortCpdV2EfmOamDispType            CmControlProtocolDispType,
    cmEthernetAccPortCpdV2SSMDispType               CmControlProtocolDispType,
    cmEthernetAccPortCpdV2PortAuthenDispType        CmControlProtocolDispType,
    cmEthernetAccPortCpdV2BridgeReservedDispType    CmControlProtocolDispType,
    cmEthernetAccPortCpdV2LANBridgesDispType        CmControlProtocolDispType,
    cmEthernetAccPortCpdV2GARPGroupDispType         CmControlProtocolDispType,
    cmEthernetAccPortCpdV2GMRPDispType              CmControlProtocolDispType,
    cmEthernetAccPortCpdV2GVRPDispType              CmControlProtocolDispType,
    cmEthernetAccPortCpdV2GARPDispType              CmControlProtocolDispType,
    --
    cmEthernetAccPortCpdV2LLDPDispType              CmControlProtocolDispType,
    cmEthernetAccPortCpdV2ELMIDispType              CmControlProtocolDispType,
    cmEthernetAccPortCpdV2L2PTTunnelMac             MacAddress 
}

cmEthernetAccPortCpdV2Index OBJECT-TYPE
    SYNTAX      Integer32 
    MAX-ACCESS  read-only
    STATUS      current
    DESCRIPTION
        "Unique Index value to access the CPD row."
    ::= { cmEthernetAccPortCpdV2Entry 1 }

cmEthernetAccPortCpdV2CiscoGroupDispType OBJECT-TYPE
    SYNTAX      CmControlProtocolDispType 
    MAX-ACCESS  read-write
    STATUS      current
    DESCRIPTION
        "Control Protocol Disposition for Cisco Group.  This includes
         ISL, PAGP, UDLD, CDP, VTP, DTP, PSVTP+, UplinkFast, VLAN Bridge,
         L2PT.  Note that a specific protocol filter overrides the
         group setting."
    ::= { cmEthernetAccPortCpdV2Entry 2 }

cmEthernetAccPortCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmEthernetAccPortCpdV2Entry 3 }

cmEthernetAccPortCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmEthernetAccPortCpdV2Entry 4 }

cmEthernetAccPortCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmEthernetAccPortCpdV2Entry 5 }

cmEthernetAccPortCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmEthernetAccPortCpdV2Entry 6 }

cmEthernetAccPortCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmEthernetAccPortCpdV2Entry 7 }

cmEthernetAccPortCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmEthernetAccPortCpdV2Entry 8 }

cmEthernetAccPortCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmEthernetAccPortCpdV2Entry 9 }

cmEthernetAccPortCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmEthernetAccPortCpdV2Entry 10 }

cmEthernetAccPortCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmEthernetAccPortCpdV2Entry 11 }

cmEthernetAccPortCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmEthernetAccPortCpdV2Entry 12 }

cmEthernetAccPortCpdV2BridgeGroupDispType OBJECT-TYPE
    SYNTAX      CmControlProtocolDispType 
    MAX-ACCESS  read-write
    STATUS      current
    DESCRIPTION
        "Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmEthernetAccPortCpdV2Entry 13 }

cmEthernetAccPortCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmEthernetAccPortCpdV2Entry 14 }

cmEthernetAccPortCpdV2PauseDispType OBJECT-TYPE
    SYNTAX      CmControlProtocolDispType 
    MAX-ACCESS  read-write
    STATUS      current
    DESCRIPTION
        "Control Protocol Disposition for IEEE 802.3x Flow Control 
         (PAUSE frames)."
    ::= { cmEthernetAccPortCpdV2Entry 15 }

cmEthernetAccPortCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmEthernetAccPortCpdV2Entry 16 }

cmEthernetAccPortCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmEthernetAccPortCpdV2Entry 17 }

cmEthernetAccPortCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmEthernetAccPortCpdV2Entry 18 }

cmEthernetAccPortCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmEthernetAccPortCpdV2Entry 19 }

cmEthernetAccPortCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmEthernetAccPortCpdV2Entry 20 }

cmEthernetAccPortCpdV2BridgeReservedDispType OBJECT-TYPE
    SYNTAX      CmControlProtocolDispType 
    MAX-ACCESS  read-write
    STATUS      current
    DESCRIPTION
        "Control Protocol Disposition for Range of MAC Addresses
         from 01:80:C2:00:00:04 to 01:80:C2:00:00:0F."
    ::= { cmEthernetAccPortCpdV2Entry 21 }

cmEthernetAccPortCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmEthernetAccPortCpdV2Entry 22 }

cmEthernetAccPortCpdV2GARPGroupDispType OBJECT-TYPE
    SYNTAX      CmControlProtocolDispType 
    MAX-ACCESS  read-write
    STATUS      current
    DESCRIPTION
        "Group Disposition type which includes GMRP, GVRP and
         MAC Address from range 01:80:C2:00:00:20 to 01:80:C2:00:00:2F."
    ::= { cmEthernetAccPortCpdV2Entry 23 }

cmEthernetAccPortCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmEthernetAccPortCpdV2Entry 24 }

cmEthernetAccPortCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmEthernetAccPortCpdV2Entry 25 }

cmEthernetAccPortCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmEthernetAccPortCpdV2Entry 26 }

cmEthernetAccPortCpdV2LLDPDispType OBJECT-TYPE
    SYNTAX      CmControlProtocolDispType 
    MAX-ACCESS  read-write
    STATUS      current
    DESCRIPTION
        "LLDP (Link Layer Discovery Protocol) Disposition type. 
         MAC Address 01:80:C2:00:00:0e, 01:80:C2:00:00:03, or
         01:80:C2:00:00:00."
    ::= { cmEthernetAccPortCpdV2Entry 27 }

cmEthernetAccPortCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmEthernetAccPortCpdV2Entry 28 }

cmEthernetAccPortCpdV2L2PTTunnelMac    OBJECT-TYPE
    SYNTAX      MacAddress 
    MAX-ACCESS  read-write
    STATUS      current
    DESCRIPTION
        "Configurable Layer 2 Protocol Tunneling MAC Address.  
         For protocols STP, CDP and VTP, with control protocol disposition as 
         pass-thru-l2pt, this configured MAC address replaces the DA, upon
         encapsulation.  For decapsulation, protocol signature and this 
         configured MAC address are matched and the MAC address is replaced
         with the protocol's inferred MAC address." 
    ::= { cmEthernetAccPortCpdV2Entry 29 }


--Flow CPDv2
cmFlowCpdV2Table  OBJECT-TYPE
    SYNTAX      SEQUENCE OF CmFlowCpdV2Entry
    MAX-ACCESS  not-accessible
    STATUS      current
    DESCRIPTION
            "A list of entries corresponding to Ethernet Flow 
             Control Protocol Disposition V2.
             This table is supported for the GE206/GE201 devices."
    ::= { cmFacilityObjects 14 }

cmFlowCpdV2Entry OBJECT-TYPE
    SYNTAX      CmFlowCpdV2Entry 
    MAX-ACCESS  not-accessible
    STATUS      current
    DESCRIPTION
            "A conceptual row in the cmFlowCpdV2Table. 
             These entries represent a Control Protocol Disposition 
             filtering criteria on the Ethernet Flow."
    INDEX { neIndex, shelfIndex, slotIndex, cmEthernetAccPortIndex, 
            cmFlowIndex, cmFlowCpdV2Index }
    ::= { cmFlowCpdV2Table 1 }

CmFlowCpdV2Entry ::= SEQUENCE {
    -- Index
    cmFlowCpdV2Index                    Integer32,

    -- Filtering Criteria
    cmFlowCpdV2CiscoGroupDispType        CmControlProtocolDispType,
    cmFlowCpdV2IslDispType               CmControlProtocolDispType,
    cmFlowCpdV2PagpDispType              CmControlProtocolDispType,
    cmFlowCpdV2UdldDispType              CmControlProtocolDispType,
    cmFlowCpdV2CdpDispType               CmControlProtocolDispType,
    cmFlowCpdV2VtpDispType               CmControlProtocolDispType,
    cmFlowCpdV2DtpDispType               CmControlProtocolDispType,
    cmFlowCpdV2PvstpPlusDispType         CmControlProtocolDispType,
    cmFlowCpdV2UplinkFastDispType        CmControlProtocolDispType,
    cmFlowCpdV2VlanBridgeDispType        CmControlProtocolDispType,
    cmFlowCpdV2L2PTDispType              CmControlProtocolDispType,
    cmFlowCpdV2BridgeGroupDispType       CmControlProtocolDispType,
    cmFlowCpdV2BPDUDispType              CmControlProtocolDispType,
    cmFlowCpdV2PauseDispType             CmControlProtocolDispType,
    cmFlowCpdV2LACPDispType              CmControlProtocolDispType,
    cmFlowCpdV2LACPMarkerDispType        CmControlProtocolDispType,
    cmFlowCpdV2EfmOamDispType            CmControlProtocolDispType,
    cmFlowCpdV2SSMDispType               CmControlProtocolDispType,
    cmFlowCpdV2PortAuthenDispType        CmControlProtocolDispType,
    cmFlowCpdV2BridgeReservedDispType    CmControlProtocolDispType,
    cmFlowCpdV2LANBridgesDispType        CmControlProtocolDispType,
    cmFlowCpdV2GARPGroupDispType         CmControlProtocolDispType,
    cmFlowCpdV2GMRPDispType              CmControlProtocolDispType,
    cmFlowCpdV2GVRPDispType              CmControlProtocolDispType,
    cmFlowCpdV2GARPDispType              CmControlProtocolDispType,
    cmFlowCpdV2ActiveControlProtocols    CmActiveControlProtocolsType,
    --
    cmFlowCpdV2LLDPDispType              CmControlProtocolDispType,
    cmFlowCpdV2ELMIDispType              CmControlProtocolDispType
}


cmFlowCpdV2Index OBJECT-TYPE
    SYNTAX      Integer32 
    MAX-ACCESS  read-only
    STATUS      current
    DESCRIPTION
        "Unique Index value to access the CPD row."
    ::= { cmFlowCpdV2Entry 1 }

cmFlowCpdV2CiscoGroupDispType OBJECT-TYPE
    SYNTAX      CmControlProtocolDispType 
    MAX-ACCESS  read-write
    STATUS      current
    DESCRIPTION
        "Control Protocol Disposition for Cisco Group.  This includes
         ISL, PAGP, UDLD, CDP, VTP, DTP, PSVTP+, UplinkFast, VLAN Bridge,
         L2PT.  Note that a specific protocol filter overrides the
         group setting."
    ::= { cmFlowCpdV2Entry 2 }

cmFlowCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmFlowCpdV2Entry 3 }

cmFlowCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmFlowCpdV2Entry 4 }

cmFlowCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmFlowCpdV2Entry 5 }

cmFlowCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmFlowCpdV2Entry 6 }

cmFlowCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmFlowCpdV2Entry 7 }

cmFlowCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmFlowCpdV2Entry 8 }

cmFlowCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmFlowCpdV2Entry 9 }

cmFlowCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmFlowCpdV2Entry 10 }

cmFlowCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmFlowCpdV2Entry 11 }

cmFlowCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmFlowCpdV2Entry 12 }

cmFlowCpdV2BridgeGroupDispType OBJECT-TYPE
    SYNTAX      CmControlProtocolDispType 
    MAX-ACCESS  read-write
    STATUS      current
    DESCRIPTION
        "Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmFlowCpdV2Entry 13 }

cmFlowCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmFlowCpdV2Entry 14 }

cmFlowCpdV2PauseDispType OBJECT-TYPE
    SYNTAX      CmControlProtocolDispType 
    MAX-ACCESS  read-write
    STATUS      current
    DESCRIPTION
        "Control Protocol Disposition for IEEE 802.3x Flow Control 
         (PAUSE frames)."
    ::= { cmFlowCpdV2Entry 15 }

cmFlowCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmFlowCpdV2Entry 16 }

cmFlowCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmFlowCpdV2Entry 17 }

cmFlowCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmFlowCpdV2Entry 18 }

cmFlowCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmFlowCpdV2Entry 19 }

cmFlowCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmFlowCpdV2Entry 20 }

cmFlowCpdV2BridgeReservedDispType OBJECT-TYPE
    SYNTAX      CmControlProtocolDispType 
    MAX-ACCESS  read-write
    STATUS      current
    DESCRIPTION
        "Control Protocol Disposition for Range of MAC Addresses
         from 01:80:C2:00:00:04 to 01:80:C2:00:00:0F."
    ::= { cmFlowCpdV2Entry 21 }

cmFlowCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmFlowCpdV2Entry 22 }

cmFlowCpdV2GARPGroupDispType OBJECT-TYPE
    SYNTAX      CmControlProtocolDispType 
    MAX-ACCESS  read-write
    STATUS      current
    DESCRIPTION
        "Group Disposition type which includes GMRP, GVRP and
         MAC Address from range 01:80:C2:00:00:20 to 01:80:C2:00:00:2F."
    ::= { cmFlowCpdV2Entry 23 }

cmFlowCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmFlowCpdV2Entry 24 }

cmFlowCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmFlowCpdV2Entry 25 }

cmFlowCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmFlowCpdV2Entry 26 }

cmFlowCpdV2ActiveControlProtocols OBJECT-TYPE
    SYNTAX  CmActiveControlProtocolsType
    MAX-ACCESS  read-only
    STATUS      current
    DESCRIPTION
        "List of Active Control Protocol Dispositions. Note that
         if the Port Level Disposition control is set to PEER or 
         DISCARD, the flow level disposition is no longer active.
         This object provides information on all the active
         dispositions."
    ::= { cmFlowCpdV2Entry 27 }

cmFlowCpdV2LLDPDispType OBJECT-TYPE
    SYNTAX      CmControlProtocolDispType 
    MAX-ACCESS  read-write
    STATUS      current
    DESCRIPTION
        "LLDP (Link Layer Discovery Protocol) Disposition type. 
         MAC Address 01:80:C2:00:00:0e, 01:80:C2:00:00:03, or
         01:80:C2:00:00:00."
    ::= { cmFlowCpdV2Entry 28 }

cmFlowCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmFlowCpdV2Entry 29 }


--
--  Ethernet Network Port Control Protocol Disposition V2
--
cmEthernetNetPortCpdV2Table  OBJECT-TYPE
    SYNTAX      SEQUENCE OF CmEthernetNetPortCpdV2Entry
    MAX-ACCESS  not-accessible
    STATUS      current
    DESCRIPTION
            "A list of entries corresponding to Ethernet Network Port 
             Control Protocol Disposition V2.
             This table is supported for the GE206/GE201 devices."
    ::= { cmFacilityObjects 15 }

cmEthernetNetPortCpdV2Entry OBJECT-TYPE
    SYNTAX      CmEthernetNetPortCpdV2Entry 
    MAX-ACCESS  not-accessible
    STATUS      current
    DESCRIPTION
            "A conceptual row in the cmEthernetNetPortCpdV2Table. 
             These entries represent a Control Protocol Disposition 
             filtering criteria on the Ethernet Network Port."
    INDEX { neIndex, shelfIndex, slotIndex, cmEthernetNetPortIndex, 
            cmEthernetNetPortCpdV2Index }
    ::= { cmEthernetNetPortCpdV2Table 1 }


CmEthernetNetPortCpdV2Entry ::= SEQUENCE {
    -- Index
    cmEthernetNetPortCpdV2Index                 Integer32,

    -- Filtering Criteria
    cmEthernetNetPortCpdV2CiscoGroupDispType      CmControlProtocolDispType,
    cmEthernetNetPortCpdV2IslDispType             CmControlProtocolDispType,
    cmEthernetNetPortCpdV2PagpDispType            CmControlProtocolDispType,
    cmEthernetNetPortCpdV2UdldDispType            CmControlProtocolDispType,
    cmEthernetNetPortCpdV2CdpDispType             CmControlProtocolDispType,
    cmEthernetNetPortCpdV2VtpDispType             CmControlProtocolDispType,
    cmEthernetNetPortCpdV2DtpDispType             CmControlProtocolDispType,
    cmEthernetNetPortCpdV2PvstpPlusDispType       CmControlProtocolDispType,
    cmEthernetNetPortCpdV2UplinkFastDispType      CmControlProtocolDispType,
    cmEthernetNetPortCpdV2VlanBridgeDispType      CmControlProtocolDispType,
    cmEthernetNetPortCpdV2L2PTDispType            CmControlProtocolDispType,
    cmEthernetNetPortCpdV2BridgeGroupDispType     CmControlProtocolDispType,
    cmEthernetNetPortCpdV2BPDUDispType            CmControlProtocolDispType,
    cmEthernetNetPortCpdV2PauseDispType           CmControlProtocolDispType,
    cmEthernetNetPortCpdV2LACPDispType            CmControlProtocolDispType,
    cmEthernetNetPortCpdV2LACPMarkerDispType      CmControlProtocolDispType,
    cmEthernetNetPortCpdV2EfmOamDispType          CmControlProtocolDispType,
    cmEthernetNetPortCpdV2SSMDispType             CmControlProtocolDispType,
    cmEthernetNetPortCpdV2PortAuthenDispType      CmControlProtocolDispType,
    cmEthernetNetPortCpdV2BridgeReservedDispType  CmControlProtocolDispType,
    cmEthernetNetPortCpdV2LANBridgesDispType      CmControlProtocolDispType,
    cmEthernetNetPortCpdV2GARPGroupDispType       CmControlProtocolDispType,
    cmEthernetNetPortCpdV2GMRPDispType            CmControlProtocolDispType,
    cmEthernetNetPortCpdV2GVRPDispType            CmControlProtocolDispType,
    cmEthernetNetPortCpdV2GARPDispType            CmControlProtocolDispType,
    --
    cmEthernetNetPortCpdV2LLDPDispType            CmControlProtocolDispType,
    cmEthernetNetPortCpdV2ELMIDispType            CmControlProtocolDispType,
    cmEthernetNetPortCpdV2L2PTTunnelMac           MacAddress 
}

cmEthernetNetPortCpdV2Index OBJECT-TYPE
    SYNTAX      Integer32 
    MAX-ACCESS  read-only
    STATUS      current
    DESCRIPTION
        "Unique Index value to access the CPD row."
    ::= { cmEthernetNetPortCpdV2Entry 1 }

cmEthernetNetPortCpdV2CiscoGroupDispType OBJECT-TYPE
    SYNTAX      CmControlProtocolDispType 
    MAX-ACCESS  read-write
    STATUS      current
    DESCRIPTION
        "Control Protocol Disposition for Cisco Group.  This includes
         ISL, PAGP, UDLD, CDP, VTP, DTP, PSVTP+, UplinkFast, VLAN Bridge,
         L2PT.  Note that a specific protocol filter overrides the
         group setting."
    ::= { cmEthernetNetPortCpdV2Entry 2 }

cmEthernetNetPortCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmEthernetNetPortCpdV2Entry 3 }

cmEthernetNetPortCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmEthernetNetPortCpdV2Entry 4 }

cmEthernetNetPortCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmEthernetNetPortCpdV2Entry 5 }

cmEthernetNetPortCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmEthernetNetPortCpdV2Entry 6 }

cmEthernetNetPortCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmEthernetNetPortCpdV2Entry 7 }

cmEthernetNetPortCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmEthernetNetPortCpdV2Entry 8 }

cmEthernetNetPortCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmEthernetNetPortCpdV2Entry 9 }

cmEthernetNetPortCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmEthernetNetPortCpdV2Entry 10 }

cmEthernetNetPortCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmEthernetNetPortCpdV2Entry 11 }

cmEthernetNetPortCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmEthernetNetPortCpdV2Entry 12 }

cmEthernetNetPortCpdV2BridgeGroupDispType OBJECT-TYPE
    SYNTAX      CmControlProtocolDispType 
    MAX-ACCESS  read-write
    STATUS      current
    DESCRIPTION
        "Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmEthernetNetPortCpdV2Entry 13 }

cmEthernetNetPortCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmEthernetNetPortCpdV2Entry 14 }

cmEthernetNetPortCpdV2PauseDispType OBJECT-TYPE
    SYNTAX      CmControlProtocolDispType 
    MAX-ACCESS  read-write
    STATUS      current
    DESCRIPTION
        "Control Protocol Disposition for IEEE 802.3x Flow Control 
         (PAUSE frames)."
    ::= { cmEthernetNetPortCpdV2Entry 15 }

cmEthernetNetPortCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmEthernetNetPortCpdV2Entry 16 }

cmEthernetNetPortCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmEthernetNetPortCpdV2Entry 17 }

cmEthernetNetPortCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmEthernetNetPortCpdV2Entry 18 }

cmEthernetNetPortCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmEthernetNetPortCpdV2Entry 19 }

cmEthernetNetPortCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmEthernetNetPortCpdV2Entry 20 }

cmEthernetNetPortCpdV2BridgeReservedDispType OBJECT-TYPE
    SYNTAX      CmControlProtocolDispType 
    MAX-ACCESS  read-write
    STATUS      current
    DESCRIPTION
        "Control Protocol Disposition for Range of MAC Addresses
         from 01:80:C2:00:00:04 to 01:80:C2:00:00:0F."
    ::= { cmEthernetNetPortCpdV2Entry 21 }

cmEthernetNetPortCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmEthernetNetPortCpdV2Entry 22 }

cmEthernetNetPortCpdV2GARPGroupDispType OBJECT-TYPE
    SYNTAX      CmControlProtocolDispType 
    MAX-ACCESS  read-write
    STATUS      current
    DESCRIPTION
        "Group Disposition type which includes GMRP, GVRP and
         MAC Address from range 01:80:C2:00:00:20 to 01:80:C2:00:00:2F."
    ::= { cmEthernetNetPortCpdV2Entry 23 }

cmEthernetNetPortCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmEthernetNetPortCpdV2Entry 24 }

cmEthernetNetPortCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmEthernetNetPortCpdV2Entry 25 }

cmEthernetNetPortCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmEthernetNetPortCpdV2Entry 26 }

cmEthernetNetPortCpdV2LLDPDispType OBJECT-TYPE
    SYNTAX      CmControlProtocolDispType 
    MAX-ACCESS  read-write
    STATUS      current
    DESCRIPTION
        "LLDP (Link Layer Discovery Protocol) Disposition type. 
         MAC Address 01:80:C2:00:00:0e, 01:80:C2:00:00:03, or
         01:80:C2:00:00:00."
    ::= { cmEthernetNetPortCpdV2Entry 27 }

cmEthernetNetPortCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmEthernetNetPortCpdV2Entry 28 }

cmEthernetNetPortCpdV2L2PTTunnelMac  OBJECT-TYPE
    SYNTAX      MacAddress 
    MAX-ACCESS  read-write
    STATUS      current
    DESCRIPTION
        "Configurable Layer 2 Protocol Tunneling MAC Address.  
         For protocols STP, CDP and VTP, with control protocol disposition as 
         pass-thru-l2pt, this configured MAC address replaces the DA, upon
         encapsulation.  For decapsulation, protocol signature and this 
         configured MAC address are matched and the MAC address is replaced
         with the protocol's inferred MAC address." 
    ::= { cmEthernetNetPortCpdV2Entry 29 }


--
--  BITS (Building Integrated Timing System) Port 
--
bitsPortTable OBJECT-TYPE
    SYNTAX      SEQUENCE OF BitsPortEntry
    MAX-ACCESS  not-accessible
    STATUS      current
    DESCRIPTION
            "A list of entries corresponding to BITS Port 
             Facilities for configuration purposes."
    ::= { cmFacilityObjects 16 }

bitsPortEntry OBJECT-TYPE
    SYNTAX      BitsPortEntry 
    MAX-ACCESS  not-accessible
    STATUS      current
    DESCRIPTION
            "A conceptual row in the bitsPortTable."
    INDEX { neIndex, shelfIndex, slotIndex, bitsPortTypeIndex, bitsPortIndex }
    ::= { bitsPortTable 1 }

BitsPortEntry ::= SEQUENCE {
    -- Port Indices 
    bitsPortTypeIndex                  Integer32,
    bitsPortIndex                      Integer32,
    bitsPortIfIndex                    InterfaceIndex,
    bitsPortEntityIndex                PhysicalIndex,

    -- State Management params
    bitsPortAdminState                 AdminState,
    bitsPortOperationalState           OperationalState,
    bitsPortSecondaryState             SecondaryState,

    -- bits port specific params 
    bitsPortType                       BitsPortType,
    bitsPortLineType                   BitsPortLineType,
    bitsPortLineCode                   BitsPortLineCode,
    bitsPortFrameFormat                BitsFrameFormat,
    bitsPortSaBitDesignation           SaBitDesignation,

    --Synchronous Port params
    bitsPortQLModeEnabled              TruthValue,
    bitsPortExpectedQL                 SSMQualityLevel,
    bitsPortAssumedQL                  SSMQualityLevel,
    bitsPortReceivedQL                 SSMQualityLevel,
    bitsPortTransmitQL                 SSMQualityLevel,
    bitsPortSquelchQL                  SSMQualityLevel,
    bitsPortLineBuildOut               LineBuildOut,
    bitsPortImpedance                  BitsPortImpedanceMode
}
    
-- Port Indices 
bitsPortTypeIndex OBJECT-TYPE
    SYNTAX      Integer32 (1..2)
    MAX-ACCESS  read-only
    STATUS      current
    DESCRIPTION
         "An integer index value used to uniquely identify
          this BITS Port within the card. Value 1 stands for
          BITS-IN, 2 for BITS-OUT."
    ::= { bitsPortEntry 1 }

bitsPortIndex OBJECT-TYPE
    SYNTAX      Integer32 (1..65535)
    MAX-ACCESS  read-only
    STATUS      current
    DESCRIPTION
         "An integer index value used to uniquely identify
          this BITS Port within the card.
          Note that each BITs Port is uniquely identified
          by the indices neIndex, shelfIndex, 
          slotIndex, bitsPortIndex." 
    ::= { bitsPortEntry 2 }

bitsPortIfIndex OBJECT-TYPE
    SYNTAX      InterfaceIndex
    MAX-ACCESS  read-only
    STATUS      current
    DESCRIPTION
         "This object has the same value as ifIndex for 
          Bits Port.  An integer index value used to 
          uniquely identify this Bits Port."
    ::= { bitsPortEntry 3 }

bitsPortEntityIndex OBJECT-TYPE
    SYNTAX      PhysicalIndex 
    MAX-ACCESS  read-only
    STATUS      current
    DESCRIPTION
           "Entity Index from ENTITY-MIB for this port."
    ::= { bitsPortEntry 4 }

-- State Management params
bitsPortAdminState OBJECT-TYPE
    SYNTAX      AdminState 
    MAX-ACCESS  read-write
    STATUS      current
    DESCRIPTION
            "This object represents the Administrative State of the BITS 
             Port."
    ::= { bitsPortEntry 5 }

bitsPortOperationalState OBJECT-TYPE
    SYNTAX      OperationalState 
    MAX-ACCESS  read-only
    STATUS      current
    DESCRIPTION
            "This object represents the Operational State of the BITS 
             Port."
    ::= { bitsPortEntry 6 }

bitsPortSecondaryState OBJECT-TYPE
    SYNTAX      SecondaryState 
    MAX-ACCESS  read-only
    STATUS      current
    DESCRIPTION
            "This object represents the Secondary State of the BITS 
             Port."
    ::= { bitsPortEntry 7 }

bitsPortType OBJECT-TYPE
    SYNTAX      BitsPortType 
    MAX-ACCESS  read-only
    STATUS      current
    DESCRIPTION
            "This object represents the BITS Port Type."
    ::= { bitsPortEntry 8 }

bitsPortLineType OBJECT-TYPE
    SYNTAX      BitsPortLineType 
    MAX-ACCESS  read-write
    STATUS      current
    DESCRIPTION
            "This object represents the BITS Port Line Type.
             Determines whether the T1/E1 BITS port operates in T1, E1, 
             or 2048kHz mode."
    ::= { bitsPortEntry 9 }

bitsPortLineCode OBJECT-TYPE
    SYNTAX      BitsPortLineCode 
    MAX-ACCESS  read-write
    STATUS      current
    DESCRIPTION
            "This object represents the BITS Port Line Code.
             When the port is configured for a Line Type of T1, 
             the valid values are t1-b8zs and t1-ami and the default value
             is t1-b8zs. When the port is configured for a Line Type of E1, 
             the valid values are e1-hdb3 and e1-ami and the default value 
             is e1-hdb3. When the port is configured for a Line Type of 
             2048kHz, the value is none."
    ::= { bitsPortEntry 10 }

bitsPortFrameFormat OBJECT-TYPE
    SYNTAX      BitsFrameFormat 
    MAX-ACCESS  read-write
    STATUS      current
    DESCRIPTION
            "This object represents the BITS Port Frame Format.
             When the port is configured for a Line Type of T1, the
             valid values are t1-sf and t1-esf and the default value is t1-esf.
             When the port is configured for a Line Type of E1, the
             valid values are e1-unframed, e1-crc4, and e1-dualFrame 
             and the default value is e1-crc4. When the port is configured 
             for a Line Type of 2048kHz, the value is none.

             R4.1CC and R4.3CC do not support e1-unframed."
    ::= { bitsPortEntry 11 }

bitsPortSaBitDesignation OBJECT-TYPE
    SYNTAX      SaBitDesignation 
    MAX-ACCESS  read-write
    STATUS      current
    DESCRIPTION
            "This object represents the BITS Port Sa Bit Designation.
             Determines which E1 Sa Bit is used to transmit/receive the SSM. 
             For T1 and 2048khz Line Types, the only allowed value is None. 
             For E1 Line Type, the default value is bit4 and it can 
             only have a value of None if QL Mode is disabled, otherwise, 
             None is an invalid value."
    ::= { bitsPortEntry 12 }

bitsPortQLModeEnabled OBJECT-TYPE 
    SYNTAX     TruthValue
    MAX-ACCESS read-write
    STATUS     current
    DESCRIPTION
         "This object allows to specify whether the BITS Port 
          can be enabled/disabled for QL Mode. 
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { bitsPortEntry 13 }

bitsPortExpectedQL OBJECT-TYPE 
    SYNTAX     SSMQualityLevel
    MAX-ACCESS read-write
    STATUS     current
    DESCRIPTION
         "This object allows to specify the expected QL when the 
          BITS Port is enabled for QL Mode. 
          This object allows the user to set a minimum
          expected received Quality Level on the port. 
          The default value shall be None."
     ::= { bitsPortEntry 14 }

bitsPortAssumedQL OBJECT-TYPE 
    SYNTAX     SSMQualityLevel
    MAX-ACCESS read-write
    STATUS     current
    DESCRIPTION
         "This object allows to specify the assumed QL on the 
          BITS Port.  The Assumed QL is only meaningful if the 
          Network Clock Type (see fsp150cm-sync.mib) is option1 and the 
          port's QL Mode is disabled and the port is being used as 
          an input reference source. Under these conditions, 
          the specified QL value is assumed to be the Quality Level of the
          non-failed reference."
     ::= { bitsPortEntry 15 }

bitsPortReceivedQL OBJECT-TYPE 
    SYNTAX     SSMQualityLevel
    MAX-ACCESS read-only
    STATUS     current
    DESCRIPTION
         "This object provides the Received QL value for the BITS port. 
          If the BITS port's QL Mode is disabled, then the received 
          QL value is not applicable."
     ::= { bitsPortEntry 16 }

bitsPortTransmitQL OBJECT-TYPE 
    SYNTAX     SSMQualityLevel
    MAX-ACCESS read-only
    STATUS     current
    DESCRIPTION
         "This object provides the Transmitted QL value for the BITS port. 
          If the BITS port's QL Mode is disabled, then the received 
          QL value is not applicable."
     ::= { bitsPortEntry 17 }

bitsPortSquelchQL OBJECT-TYPE 
    SYNTAX     SSMQualityLevel
    MAX-ACCESS read-write
    STATUS     current
    DESCRIPTION
         "This object allows to set the Squelch QL for the BITS-OUT port. 
          The Squelch QL is only meaningful if the QL Mode is Enabled. 
          The Squelch QL is used to determine whether or not to squelch 
          the output of the BITS-OUT port. If the system's QL is lower 
          than the Squelch QL, the output is squelched.
          If the BITS port's QL Mode is disabled, then the received 
          QL value is not applicable."
     ::= { bitsPortEntry 18 }

bitsPortLineBuildOut OBJECT-TYPE 
    SYNTAX     LineBuildOut
    MAX-ACCESS read-write
    STATUS     current
    DESCRIPTION
         "This object allows to manage the line build out on the BITS-OUT port when
          the Line Type is T1."
     ::= { bitsPortEntry 19 }

bitsPortImpedance OBJECT-TYPE 
    SYNTAX     BitsPortImpedanceMode
    MAX-ACCESS read-only
    STATUS     current
    DESCRIPTION
         "This object provides the impedance mode for the BITS-OUT port."
     ::= { bitsPortEntry 20 }

--
--  IEEE 1588 EthernetPort 
--
ieee1588EthernetPortTable OBJECT-TYPE
    SYNTAX      SEQUENCE OF IEEE1588EthernetPortEntry
    MAX-ACCESS  not-accessible
    STATUS      current
    DESCRIPTION
            "A list of entries corresponding to IEEE Ethernet Port
             Facilities for configuration purposes."
    ::= { cmFacilityObjects 17 }

ieee1588EthernetPortEntry OBJECT-TYPE
    SYNTAX      IEEE1588EthernetPortEntry 
    MAX-ACCESS  not-accessible
    STATUS      current
    DESCRIPTION
            "A conceptual row in the IEEE Ethernet Port Table."
    INDEX { neIndex, shelfIndex, slotIndex, ieee1588EthernetPortIndex }
    ::= { ieee1588EthernetPortTable 1 }

IEEE1588EthernetPortEntry ::= SEQUENCE {
    -- Port Indices 
    ieee1588EthernetPortIndex              Integer32,
    ieee1588EthernetPortIfIndex            InterfaceIndex,
    ieee1588EthernetPortEntityIndex        PhysicalIndex,

    -- State Management params
    ieee1588EthernetPortAdminState         AdminState,
    ieee1588EthernetPortOperationalState   OperationalState,
    ieee1588EthernetPortSecondaryState     SecondaryState,

    -- Port specific params
    ieee1588EthernetPortMTU                Integer32,

    -- Generic Ethernet Port params
    ieee1588EthernetPortMediaType          EthernetMediaType,
    ieee1588EthernetPortConfigSpeed        EthernetPortSpeed,
    ieee1588EthernetPortNegotiatedSpeed    EthernetPortSpeed,

    ieee1588EthernetPortMDIXType           CmEthernetMDIXType  
}
    
-- Port Indices 
ieee1588EthernetPortIndex OBJECT-TYPE
    SYNTAX      Integer32 
    MAX-ACCESS  read-only
    STATUS      current
    DESCRIPTION
         "An integer index value used to uniquely identify
          the IEEE Ethernet Port." 
    ::= { ieee1588EthernetPortEntry 1 }

ieee1588EthernetPortIfIndex OBJECT-TYPE
    SYNTAX      InterfaceIndex
    MAX-ACCESS  read-only
    STATUS      current
    DESCRIPTION
         "This object has the same value as ifIndex for 
          the IEEE Ethernet Port."
    ::= { ieee1588EthernetPortEntry 2 }

ieee1588EthernetPortEntityIndex OBJECT-TYPE
    SYNTAX      PhysicalIndex 
    MAX-ACCESS  read-only
    STATUS      current
    DESCRIPTION
           "Entity Index from ENTITY-MIB for this port."
    ::= { ieee1588EthernetPortEntry 3 }

-- State Management params
ieee1588EthernetPortAdminState OBJECT-TYPE
    SYNTAX      AdminState 
    MAX-ACCESS  read-write
    STATUS      current
    DESCRIPTION
            "This object represents the Administrative State of the 
             Port."
    ::= { ieee1588EthernetPortEntry 4 }

ieee1588EthernetPortOperationalState OBJECT-TYPE
    SYNTAX      OperationalState 
    MAX-ACCESS  read-only
    STATUS      current
    DESCRIPTION
            "This object represents the Operational State of the 
             Port."
    ::= { ieee1588EthernetPortEntry 5 }

ieee1588EthernetPortSecondaryState OBJECT-TYPE
    SYNTAX      SecondaryState 
    MAX-ACCESS  read-only
    STATUS      current
    DESCRIPTION
            "This object represents the Secondary State of the 
             Port."
    ::= { ieee1588EthernetPortEntry 6 }

ieee1588EthernetPortMTU OBJECT-TYPE
    SYNTAX      Integer32 
    MAX-ACCESS  read-write
    STATUS      current
    DESCRIPTION
            "This object provides the MTU on the Port."
    ::= { ieee1588EthernetPortEntry 7 }

ieee1588EthernetPortMediaType OBJECT-TYPE
    SYNTAX     EthernetMediaType
    MAX-ACCESS read-write
    STATUS     current
    DESCRIPTION
            "This object represents the type of Media."
    ::= { ieee1588EthernetPortEntry 8 }

ieee1588EthernetPortConfigSpeed OBJECT-TYPE
    SYNTAX     EthernetPortSpeed
    MAX-ACCESS read-write
    STATUS     current
    DESCRIPTION
            "This object allows to configure the speed of the Port."
    ::= { ieee1588EthernetPortEntry 9 }

ieee1588EthernetPortNegotiatedSpeed OBJECT-TYPE
    SYNTAX     EthernetPortSpeed
    MAX-ACCESS read-only
    STATUS     current
    DESCRIPTION
            "This object provides the negotiated speed of the 
             Port."
    ::= { ieee1588EthernetPortEntry 10 }

ieee1588EthernetPortMDIXType OBJECT-TYPE
    SYNTAX     CmEthernetMDIXType
    MAX-ACCESS read-write
    STATUS     current
    DESCRIPTION
            "This object allows management of MDIX property on  
             Port."
    ::= { ieee1588EthernetPortEntry 11 }


--
--  GPS 10MHz Port 
--
gps10MHzPortTable OBJECT-TYPE
    SYNTAX      SEQUENCE OF GPS10MHzPortEntry
    MAX-ACCESS  not-accessible
    STATUS      current
    DESCRIPTION
            "A list of entries corresponding to GPS 10MHz 
             Facilities for configuration purposes."
    ::= { cmFacilityObjects 18 }

gps10MHzPortEntry OBJECT-TYPE
    SYNTAX      GPS10MHzPortEntry 
    MAX-ACCESS  not-accessible
    STATUS      current
    DESCRIPTION
            "A conceptual row in the GPS 10MHz Port Table."
    INDEX { neIndex, shelfIndex, slotIndex, gps10MHzPortIndex }
    ::= { gps10MHzPortTable 1 }

GPS10MHzPortEntry ::= SEQUENCE {
    -- Port Indices 
    gps10MHzPortIndex              Integer32,
    gps10MHzPortIfIndex            InterfaceIndex,
    gps10MHzPortEntityIndex        PhysicalIndex,

    -- State Management params
    gps10MHzPortAdminState         AdminState,
    gps10MHzPortOperationalState   OperationalState,
    gps10MHzPortSecondaryState     SecondaryState,
    gps10MHzPortSignalDirection    SignalDirectionType,

    gps10MHzPortSquelchControl     SquelchControl,
    gps10MHzPortSquelchQL          SSMQualityLevel,

    gps10MHzPortFrequencySource    VariablePointer,
    gps10MHzPortClockClass         Unsigned32,
    gps10MHzPortClockAccuracy      Unsigned32,
    gps10MHzPortTimeSource         TimeSource,
    gps10MHzPortAssumedQL          SSMQualityLevel
}
    
-- Port Indices 
gps10MHzPortIndex OBJECT-TYPE
    SYNTAX      Integer32 
    MAX-ACCESS  read-only
    STATUS      current
    DESCRIPTION
         "An integer index value used to uniquely identify
          the IEEE Ethernet Port." 
    ::= { gps10MHzPortEntry 1 }

gps10MHzPortIfIndex OBJECT-TYPE
    SYNTAX      InterfaceIndex
    MAX-ACCESS  read-only
    STATUS      current
    DESCRIPTION
         "This object has the same value as ifIndex for 
          the IEEE Ethernet Port."
    ::= { gps10MHzPortEntry 2 }

gps10MHzPortEntityIndex OBJECT-TYPE
    SYNTAX      PhysicalIndex 
    MAX-ACCESS  read-only
    STATUS      current
    DESCRIPTION
           "Entity Index from ENTITY-MIB for this port."
    ::= { gps10MHzPortEntry 3 }

-- State Management params
gps10MHzPortAdminState OBJECT-TYPE
    SYNTAX      AdminState 
    MAX-ACCESS  read-write
    STATUS      current
    DESCRIPTION
            "This object represents the Administrative State of the 
             Port."
    ::= { gps10MHzPortEntry 4 }

gps10MHzPortOperationalState OBJECT-TYPE
    SYNTAX      OperationalState 
    MAX-ACCESS  read-only
    STATUS      current
    DESCRIPTION
            "This object represents the Operational State of the 
             Port."
    ::= { gps10MHzPortEntry 5 }

gps10MHzPortSecondaryState OBJECT-TYPE
    SYNTAX      SecondaryState 
    MAX-ACCESS  read-only
    STATUS      current
    DESCRIPTION
            "This object represents the Secondary State of the 
             Port."
    ::= { gps10MHzPortEntry 6 }

gps10MHzPortSignalDirection OBJECT-TYPE
    SYNTAX      SignalDirectionType 
    MAX-ACCESS  read-write
    STATUS      current
    DESCRIPTION
            "This object allows specification of the signal type 
             (i.e. input or output)."
    ::= { gps10MHzPortEntry 7 }

gps10MHzPortSquelchControl  OBJECT-TYPE 
    SYNTAX     SquelchControl
    MAX-ACCESS read-write
    STATUS     current
    DESCRIPTION
         "This object allows to set the Squelch Control for the 10MHz port. 
          The Squelch Control is used to determine the type of squelch control 
          used to squelch the output of the TOD port. Only option supported
          is squelch-ql."
     ::= { gps10MHzPortEntry 8 }

gps10MHzPortSquelchQL OBJECT-TYPE 
    SYNTAX     SSMQualityLevel
    MAX-ACCESS read-write
    STATUS     current
    DESCRIPTION
         "This object allows to set the Squelch QL for the 10MHz port. 
          This value is used when f310MHzClockPortSquelchControl is squelch-ql.
          The Squelch QL is used to determine whether or not to squelch 
          the output of the TOD port. If the system's QL is lower 
          than the Squelch QL, the output is squelched."
     ::= { gps10MHzPortEntry 9 }

gps10MHzPortFrequencySource OBJECT-TYPE 
    SYNTAX     VariablePointer
    MAX-ACCESS read-write
    STATUS     current
    DESCRIPTION
         "This object allows to set the Frequency Source for the Port." 
     ::= { gps10MHzPortEntry 10 }

gps10MHzPortClockClass OBJECT-TYPE
    SYNTAX      Unsigned32
    MAX-ACCESS  read-only
    STATUS      current
    DESCRIPTION
           "This object specify GPS port clock class."
    ::= { gps10MHzPortEntry 11 }

gps10MHzPortClockAccuracy OBJECT-TYPE
    SYNTAX      Unsigned32
    MAX-ACCESS  read-only
    STATUS      current
    DESCRIPTION
           "This object specify GPS port clock accuracy."
    ::= { gps10MHzPortEntry 12 }

gps10MHzPortTimeSource OBJECT-TYPE
    SYNTAX      TimeSource
    MAX-ACCESS  read-only
    STATUS      current
    DESCRIPTION
           "This object specify GPS port time source."
    ::= { gps10MHzPortEntry 13 }

gps10MHzPortAssumedQL OBJECT-TYPE 
    SYNTAX     SSMQualityLevel
    MAX-ACCESS read-write
    STATUS     current
    DESCRIPTION
         "This object allows to specify the assumed QL on the 
          GPS Port.  The Assumed QL is only meaningful if the 
          Network Clock Type (see fsp150cm-sync.mib) is option1 and the 
          port's QL Mode is disabled and the port is being used as 
          an input reference source. Under these conditions, 
          the specified QL value is assumed to be the Quality Level of the
          non-failed reference."
     ::= { gps10MHzPortEntry 14 }

--
--  Ethernet Network Port Cable Length Benchmark 
--
cmEthernetNetPortClbTable  OBJECT-TYPE
    SYNTAX      SEQUENCE OF CmEthernetNetPortClbEntry
    MAX-ACCESS  not-accessible
    STATUS      current
    DESCRIPTION
            "A list of entries corresponding to Ethernet Network Port 
             Cable Length Benchmark."
    ::= { cmFacilityObjects 19 }

cmEthernetNetPortClbEntry OBJECT-TYPE
    SYNTAX      CmEthernetNetPortClbEntry 
    MAX-ACCESS  not-accessible
    STATUS      current
    DESCRIPTION
            "A conceptual row in the cmEthernetNetPortClbTable. 
             These entries represent Cable Length Benchmarks 
             on the Ethernet Network Port."
    INDEX { neIndex, shelfIndex, slotIndex, cmEthernetNetPortIndex, 
            cmEthernetNetPortClbIndex }
    ::= { cmEthernetNetPortClbTable 1 }


CmEthernetNetPortClbEntry ::= SEQUENCE {
    cmEthernetNetPortClbIndex          Integer32,
    cmEthernetNetPortClbEnabled        TruthValue,
    cmEthernetNetPortClbLength         DisplayString,
    cmEthernetNetPortClbDescr          DisplayString
}

cmEthernetNetPortClbIndex OBJECT-TYPE
    SYNTAX      Integer32 (1..5)
    MAX-ACCESS  read-only
    STATUS      current
    DESCRIPTION
            "An integer index value used to uniquely identify
             this Cable Length Benchmark Entry specification."
    ::= { cmEthernetNetPortClbEntry 1 }

cmEthernetNetPortClbEnabled OBJECT-TYPE
    SYNTAX     TruthValue
    MAX-ACCESS read-write
    STATUS     current
    DESCRIPTION
            "This enables specification of Cable Length Benchmark entry."
    ::= { cmEthernetNetPortClbEntry 2 }

cmEthernetNetPortClbLength OBJECT-TYPE
    SYNTAX  DisplayString 
    MAX-ACCESS read-write
    STATUS     current
    DESCRIPTION
            "Cable length of Cable Points Entry. The cable length is of
             the form XXX[.YY] where XX can be any integer value and YY
             allows precision of 2 decimals after the floating point. Note
             that .YY is optional."
    ::= { cmEthernetNetPortClbEntry 3 }

cmEthernetNetPortClbDescr OBJECT-TYPE
    SYNTAX     DisplayString (SIZE (0..256))
    MAX-ACCESS read-write
    STATUS     current
    DESCRIPTION
         "A textual string containing description of cable span."
    ::= { cmEthernetNetPortClbEntry 4 }


--Network Port Priority Mapping
cmNetPortPrioMapTable  OBJECT-TYPE
    SYNTAX      SEQUENCE OF CmNetPortPrioMapEntry
    MAX-ACCESS  not-accessible
    STATUS      current
    DESCRIPTION
            "A list of entries corresponding to Ethernet Network Port Priority Mappings
             in multi Class of Service (COS) mode."
    ::= { cmFacilityObjects 20 }

cmNetPortPrioMapEntry OBJECT-TYPE
    SYNTAX      CmNetPortPrioMapEntry
    MAX-ACCESS  not-accessible
    STATUS      current
    DESCRIPTION
            "A conceptual row in the cmNetPortPrioMapTable."
    INDEX { neIndex, shelfIndex, slotIndex,
            cmEthernetNetPortIndex, cmNetPortPrioMapIndex }
    ::= { cmNetPortPrioMapTable 1 }

CmNetPortPrioMapEntry ::= SEQUENCE {
    cmNetPortPrioMapIndex            Integer32,
    cmNetPortPrioMapInPriority       Integer32,
    cmNetPortPrioMapCOS              Integer32,
    cmNetPortPrioMapOuterTagPriority VlanPriority
}

cmNetPortPrioMapIndex OBJECT-TYPE
    SYNTAX      Integer32 (1..8)
    MAX-ACCESS  read-only
    STATUS      current
    DESCRIPTION
            "The integer index value corresponding to a priority value."
    ::= { cmNetPortPrioMapEntry 1 }

cmNetPortPrioMapInPriority OBJECT-TYPE
    SYNTAX      Integer32 (0..7)
    MAX-ACCESS  read-write
    STATUS      current
    DESCRIPTION
            "The integer index value corresponding to a priority value."
    ::= { cmNetPortPrioMapEntry 2 }

cmNetPortPrioMapCOS OBJECT-TYPE
    SYNTAX      Integer32 (0..7)
    MAX-ACCESS  read-write
    STATUS      current
    DESCRIPTION
            "This allows specification of the COS Priority, i.e.
             this helps in determining the appropriate COS Policer for
             the Flow."
    ::= { cmNetPortPrioMapEntry 3 }

cmNetPortPrioMapOuterTagPriority OBJECT-TYPE
    SYNTAX      VlanPriority
    MAX-ACCESS  read-write
    STATUS      current
    DESCRIPTION
            "This allows specification of the VLAN priority that
             will replace the outgoing (N2A direction) outer-tag's priority.
             Note that, each flow participates or not in outer-tag
             priority mapping, using the object 'cmFlowN2AOuterTagPrioEnabled'."
    ::= { cmNetPortPrioMapEntry 4 }


--
-- Access Port PCP encoding table 
--
cmAccPortPcpDEEncTable  OBJECT-TYPE
    SYNTAX      SEQUENCE OF CmAccPortPcpDEEncEntry 
    MAX-ACCESS  not-accessible
    STATUS      current
    DESCRIPTION
        "Ethernet Access Port PCP drop eligibility encoding table. This
         is applied to a frame that is egressing at the Access port."
    ::= { cmFacilityObjects 21 }

cmAccPortPcpDEEncEntry OBJECT-TYPE
    SYNTAX      CmAccPortPcpDEEncEntry 
    MAX-ACCESS  not-accessible
    STATUS      current
    DESCRIPTION
            "A conceptual row in the ethernetPBPcpDEEncPortTable."
    INDEX { neIndex, shelfIndex, slotIndex, cmEthernetAccPortIndex, 
            cmAccPortPcpDEEncIndex }
    ::= { cmAccPortPcpDEEncTable 1 }

CmAccPortPcpDEEncEntry ::= SEQUENCE {
  cmAccPortPcpDEEncIndex              Integer32,
  cmAccPortPcpDEEncInPriority         VlanPriority,
  cmAccPortPcpDEEncDropIneligiblePrio VlanPriority,
  cmAccPortPcpDEEncDropEligiblePrio   VlanPriority
}

cmAccPortPcpDEEncIndex OBJECT-TYPE
    SYNTAX      Integer32 (1..8)
    MAX-ACCESS  read-only
    STATUS      current
    DESCRIPTION
            "An integer index value used to uniquely identify
             a row in the PCP drop eligible encoding table."
    ::= { cmAccPortPcpDEEncEntry 1 }

cmAccPortPcpDEEncInPriority OBJECT-TYPE
    SYNTAX     VlanPriority
    MAX-ACCESS read-write
    STATUS     current
    DESCRIPTION
         "This object is the input priority that is translated to a
          drop eligibility priority or a drop ineligibility priority."
     ::= { cmAccPortPcpDEEncEntry 2 }

cmAccPortPcpDEEncDropIneligiblePrio OBJECT-TYPE
    SYNTAX     VlanPriority
    MAX-ACCESS read-write
    STATUS     current
    DESCRIPTION
         "This object is the PCP value that has a priority value with
          implicit drop ineligibility encoded into it."
     ::= { cmAccPortPcpDEEncEntry 3 }

cmAccPortPcpDEEncDropEligiblePrio OBJECT-TYPE
    SYNTAX     VlanPriority
    MAX-ACCESS read-write
    STATUS     current
    DESCRIPTION
         "This object is the PCP value that has a priority value with
          implicit drop eligibility encoded into it."
     ::= { cmAccPortPcpDEEncEntry 4 }

--
-- Access Port PCP decoding table
--

cmAccPortPcpDEDecTable  OBJECT-TYPE
    SYNTAX      SEQUENCE OF CmAccPortPcpDEDecEntry
    MAX-ACCESS  not-accessible
    STATUS      current
    DESCRIPTION
            "Ethernet Access Port PCP drop eligibility decoding table. This
             is applied to a frame that is ingressing at a port."
    ::= { cmFacilityObjects 22 }

cmAccPortPcpDEDecEntry OBJECT-TYPE
    SYNTAX      CmAccPortPcpDEDecEntry 
    MAX-ACCESS  not-accessible
    STATUS      current
    DESCRIPTION
            "A conceptual row in the ethernetPBPcpDEDecPortTable."
    INDEX { neIndex, shelfIndex, slotIndex, cmEthernetAccPortIndex, 
            cmAccPortPcpDEDecIndex }
    ::= { cmAccPortPcpDEDecTable 1 }

CmAccPortPcpDEDecEntry ::= SEQUENCE {
    cmAccPortPcpDEDecIndex        Integer32,
    cmAccPortPcpDEDecInPriority   VlanPriority,
    cmAccPortPcpDEDecOutPriority  VlanPriority,
    cmAccPortPcpDEDecDropEligible TruthValue
}


cmAccPortPcpDEDecIndex OBJECT-TYPE
    SYNTAX      Integer32 (1..8)
    MAX-ACCESS  read-only
    STATUS      current
    DESCRIPTION
            "An integer index value used to uniquely identify
             a row in the PCP drop eligible decoding table."
    ::= { cmAccPortPcpDEDecEntry 1 }

cmAccPortPcpDEDecInPriority OBJECT-TYPE
    SYNTAX     VlanPriority
    MAX-ACCESS read-write
    STATUS     current
    DESCRIPTION
         "This object is the input priority that is decoded to get
          priority and the drop eligibility of a frame."
     ::= { cmAccPortPcpDEDecEntry 2 }

cmAccPortPcpDEDecOutPriority OBJECT-TYPE
    SYNTAX     VlanPriority
    MAX-ACCESS read-write
    STATUS     current
    DESCRIPTION
         "This object is the priority value decoded from a incoming PCP value."
     ::= { cmAccPortPcpDEDecEntry 3 }

cmAccPortPcpDEDecDropEligible OBJECT-TYPE
    SYNTAX     TruthValue
    MAX-ACCESS read-write
    STATUS     current
    DESCRIPTION
         "This object is the drop eligibility decoded from a incoming
          PCP value."
     ::= { cmAccPortPcpDEDecEntry 4 }

-- 
-- Access Port PCP pair table
--

cmAccPortPcpDEPairTable  OBJECT-TYPE
    SYNTAX      SEQUENCE OF CmAccPortPcpDEPairEntry
    MAX-ACCESS  not-accessible
    STATUS      current
    DESCRIPTION
            "Ethernet Access Port PCP drop eligibility priority pair table.
             The priority pair is encoded to same drop eligibility and
             drop ineligibility priority. Depending on the PCP DE Enc/Dec
             mode there can be upto 3 pairs in the table. There will one
             pair for 7P1D, two pairs for 6P2D and three pairs for 5P3D."
    ::= { cmFacilityObjects 23 }

cmAccPortPcpDEPairEntry OBJECT-TYPE
    SYNTAX      CmAccPortPcpDEPairEntry 
    MAX-ACCESS  not-accessible
    STATUS      current
    DESCRIPTION
            "A conceptual row in the cmAccPortPcpDEPairEntry."
    INDEX { neIndex, shelfIndex, slotIndex, cmEthernetAccPortIndex, 
            cmAccPortPcpDEPairIndex }
    ::= { cmAccPortPcpDEPairTable 1 }

CmAccPortPcpDEPairEntry ::= SEQUENCE {
    cmAccPortPcpDEPairIndex          Integer32,
    cmAccPortPcpDEDropIneligiblePrio VlanPriority,
    cmAccPortPcpDEDropEligiblePrio   VlanPriority
}

cmAccPortPcpDEPairIndex OBJECT-TYPE
    SYNTAX      Integer32 (1..3)
    MAX-ACCESS  read-only
    STATUS      current
    DESCRIPTION
            "An integer index value used to uniquely identify
             a row in the PCP drop eligible priority pair table."
    ::= { cmAccPortPcpDEPairEntry 1 }

cmAccPortPcpDEDropIneligiblePrio OBJECT-TYPE
    SYNTAX     VlanPriority
    MAX-ACCESS read-write
    STATUS     current
    DESCRIPTION
         "This object is the drop ineligible priority."
     ::= { cmAccPortPcpDEPairEntry 2 }

cmAccPortPcpDEDropEligiblePrio OBJECT-TYPE
    SYNTAX     VlanPriority
    MAX-ACCESS read-write
    STATUS     current
    DESCRIPTION
         "This object is the drop eligible priority."
     ::= { cmAccPortPcpDEPairEntry 3 }

--
-- Network Port PCP encoding table 
--
cmNetPortPcpDEEncTable  OBJECT-TYPE
    SYNTAX      SEQUENCE OF CmNetPortPcpDEEncEntry 
    MAX-ACCESS  not-accessible
    STATUS      current
    DESCRIPTION
        "Ethernet Network Port PCP drop eligibility encoding table. This
         is applied to a frame that is egressing at the Network port."
    ::= { cmFacilityObjects 24 }

cmNetPortPcpDEEncEntry OBJECT-TYPE
    SYNTAX      CmNetPortPcpDEEncEntry 
    MAX-ACCESS  not-accessible
    STATUS      current
    DESCRIPTION
            "A conceptual row in the ethernetPBPcpDEEncPortTable."
    INDEX { neIndex, shelfIndex, slotIndex, cmEthernetNetPortIndex, 
            cmNetPortPcpDEEncIndex }
    ::= { cmNetPortPcpDEEncTable 1 }

CmNetPortPcpDEEncEntry ::= SEQUENCE {
  cmNetPortPcpDEEncIndex              Integer32,
  cmNetPortPcpDEEncInPriority         VlanPriority,
  cmNetPortPcpDEEncDropIneligiblePrio VlanPriority,
  cmNetPortPcpDEEncDropEligiblePrio   VlanPriority
}

cmNetPortPcpDEEncIndex OBJECT-TYPE
    SYNTAX      Integer32 (1..8)
    MAX-ACCESS  read-only
    STATUS      current
    DESCRIPTION
            "An integer index value used to uniquely identify
             a row in the PCP drop eligible encoding table."
    ::= { cmNetPortPcpDEEncEntry 1 }

cmNetPortPcpDEEncInPriority OBJECT-TYPE
    SYNTAX     VlanPriority
    MAX-ACCESS read-write
    STATUS     current
    DESCRIPTION
         "This object is the input priority that is translated to a
          drop eligibility priority or a drop ineligibility priority."
     ::= { cmNetPortPcpDEEncEntry 2 }

cmNetPortPcpDEEncDropIneligiblePrio OBJECT-TYPE
    SYNTAX     VlanPriority
    MAX-ACCESS read-write
    STATUS     current
    DESCRIPTION
         "This object is the PCP value that has a priority value with
          implicit drop ineligibility encoded into it."
     ::= { cmNetPortPcpDEEncEntry 3 }

cmNetPortPcpDEEncDropEligiblePrio OBJECT-TYPE
    SYNTAX     VlanPriority
    MAX-ACCESS read-write
    STATUS     current
    DESCRIPTION
         "This object is the PCP value that has a priority value with
          implicit drop eligibility encoded into it."
     ::= { cmNetPortPcpDEEncEntry 4 }

--
-- Network Port PCP decoding table
--

cmNetPortPcpDEDecTable  OBJECT-TYPE
    SYNTAX      SEQUENCE OF CmNetPortPcpDEDecEntry
    MAX-ACCESS  not-accessible
    STATUS      current
    DESCRIPTION
            "Ethernet Network Port PCP drop eligibility decoding table. This
             is applied to a frame that is ingressing at a port."
    ::= { cmFacilityObjects 25 }

cmNetPortPcpDEDecEntry OBJECT-TYPE
    SYNTAX      CmNetPortPcpDEDecEntry 
    MAX-ACCESS  not-accessible
    STATUS      current
    DESCRIPTION
            "A conceptual row in the ethernetPBPcpDEDecPortTable."
    INDEX { neIndex, shelfIndex, slotIndex, cmEthernetNetPortIndex, 
            cmNetPortPcpDEDecIndex }
    ::= { cmNetPortPcpDEDecTable 1 }

CmNetPortPcpDEDecEntry ::= SEQUENCE {
    cmNetPortPcpDEDecIndex        Integer32,
    cmNetPortPcpDEDecInPriority   VlanPriority,
    cmNetPortPcpDEDecOutPriority  VlanPriority,
    cmNetPortPcpDEDecDropEligible TruthValue
}


cmNetPortPcpDEDecIndex OBJECT-TYPE
    SYNTAX      Integer32 (1..8)
    MAX-ACCESS  read-only
    STATUS      current
    DESCRIPTION
            "An integer index value used to uniquely identify
             a row in the PCP drop eligible decoding table."
    ::= { cmNetPortPcpDEDecEntry 1 }

cmNetPortPcpDEDecInPriority OBJECT-TYPE
    SYNTAX     VlanPriority
    MAX-ACCESS read-write
    STATUS     current
    DESCRIPTION
         "This object is the input priority that is decoded to get
          priority and the drop eligibility of a frame."
     ::= { cmNetPortPcpDEDecEntry 2 }

cmNetPortPcpDEDecOutPriority OBJECT-TYPE
    SYNTAX     VlanPriority
    MAX-ACCESS read-write
    STATUS     current
    DESCRIPTION
         "This object is the priority value decoded from a incoming PCP value."
     ::= { cmNetPortPcpDEDecEntry 3 }

cmNetPortPcpDEDecDropEligible OBJECT-TYPE
    SYNTAX     TruthValue
    MAX-ACCESS read-write
    STATUS     current
    DESCRIPTION
         "This object is the drop eligibility decoded from a incoming
          PCP value."
     ::= { cmNetPortPcpDEDecEntry 4 }

-- 
-- Network Port PCP pair table
--

cmNetPortPcpDEPairTable  OBJECT-TYPE
    SYNTAX      SEQUENCE OF CmNetPortPcpDEPairEntry
    MAX-ACCESS  not-accessible
    STATUS      current
    DESCRIPTION
            "Ethernet Network Port PCP drop eligibility priority pair table.
             The priority pair is encoded to same drop eligibility and
             drop ineligibility priority. Depending on the PCP DE Enc/Dec
             mode there can be upto 3 pairs in the table. There will one
             pair for 7P1D, two pairs for 6P2D and three pairs for 5P3D."
    ::= { cmFacilityObjects 26 }

cmNetPortPcpDEPairEntry OBJECT-TYPE
    SYNTAX      CmNetPortPcpDEPairEntry 
    MAX-ACCESS  not-accessible
    STATUS      current
    DESCRIPTION
            "A conceptual row in the cmNetPortPcpDEPairEntry."
    INDEX { neIndex, shelfIndex, slotIndex, cmEthernetNetPortIndex, 
            cmNetPortPcpDEPairIndex }
    ::= { cmNetPortPcpDEPairTable 1 }

CmNetPortPcpDEPairEntry ::= SEQUENCE {
    cmNetPortPcpDEPairIndex          Integer32,
    cmNetPortPcpDEDropIneligiblePrio VlanPriority,
    cmNetPortPcpDEDropEligiblePrio   VlanPriority
}

cmNetPortPcpDEPairIndex OBJECT-TYPE
    SYNTAX      Integer32 (1..3)
    MAX-ACCESS  read-only
    STATUS      current
    DESCRIPTION
            "An integer index value used to uniquely identify
             a row in the PCP drop eligible priority pair table."
    ::= { cmNetPortPcpDEPairEntry 1 }

cmNetPortPcpDEDropIneligiblePrio OBJECT-TYPE
    SYNTAX     VlanPriority
    MAX-ACCESS read-write
    STATUS     current
    DESCRIPTION
         "This object is the drop ineligible priority."
     ::= { cmNetPortPcpDEPairEntry 2 }

cmNetPortPcpDEDropEligiblePrio OBJECT-TYPE
    SYNTAX     VlanPriority
    MAX-ACCESS read-write
    STATUS     current
    DESCRIPTION
         "This object is the drop eligible priority."
     ::= { cmNetPortPcpDEPairEntry 3 }

--
--  Agg Ethernet Port 
--
cmEthernetTrafficPortTable  OBJECT-TYPE
    SYNTAX      SEQUENCE OF CmEthernetTrafficPortEntry
    MAX-ACCESS  not-accessible
    STATUS      current
    DESCRIPTION
            "A list of entries corresponding to Ethernet 
             Facilities for configuration purposes."
    ::= { cmFacilityObjects 27}

cmEthernetTrafficPortEntry OBJECT-TYPE
    SYNTAX      CmEthernetTrafficPortEntry 
    MAX-ACCESS  not-accessible
    STATUS      current
    DESCRIPTION
            "A conceptual row in the cmEthernetTrafficPortTable."
    INDEX { neIndex, shelfIndex, slotIndex, cmEthernetTrafficPortIndex }
    ::= { cmEthernetTrafficPortTable 1 }

CmEthernetTrafficPortEntry ::= SEQUENCE {
    -- Port Indices 
    cmEthernetTrafficPortIndex                           Integer32,
    cmEthernetTrafficPortIfIndex                         InterfaceIndex,
    cmEthernetTrafficPortEntityIndex                     PhysicalIndex,

    -- State Management params
    cmEthernetTrafficPortAdminState                      AdminState,
    cmEthernetTrafficPortOperationalState                OperationalState,
    cmEthernetTrafficPortSecondaryState                  SecondaryState,

    -- Generic Port params
    cmEthernetTrafficPortMTU                             Integer32,

    -- Generic Ethernet Port params
    cmEthernetTrafficPortMediaType                       EthernetMediaType,
    cmEthernetTrafficPortConfigSpeed                     EthernetPortSpeed,
    cmEthernetTrafficPortNegotiatedSpeed                 EthernetPortSpeed,
    cmEthernetTrafficPortMDIXType                        CmEthernetMDIXType,  
    cmEthernetTrafficPortMDIXStatus                      CmEthernetMDIXType,
    cmEthernetTrafficPortSfpVendorName                   DisplayString,
    cmEthernetTrafficPortSfpPartNumber                   DisplayString,
    cmEthernetTrafficPortSfpSerialNumber                 DisplayString,
    cmEthernetTrafficPortSfpDateOfManufacture            DateAndTime,
    cmEthernetTrafficPortSfpConnectorValue               SfpConnectorValue,
    cmEthernetTrafficPortSfpLinkLength                   Integer32,
    cmEthernetTrafficPortSfpLaserWaveLength              Integer32,
    cmEthernetTrafficPortSfpMediaType                    SfpMediaType,
    
    -- Ethernet Loopback params
    cmEthernetTrafficPortLoopbackConfig                  CmLoopbackType,
    cmEthernetTrafficPortLoopbackStatus                  CmLoopbackType,
    cmEthernetTrafficPortLoopbackTime                    Integer32,
    cmEthernetTrafficPortLoopbackSwapSADA                CmSwapSADAType,
    cmEthernetTrafficPortOuterVlanLoopbackMask           INTEGER,
    cmEthernetTrafficPortOuterVlanLoopback1              DisplayString,
    cmEthernetTrafficPortOuterVlanLoopback2              DisplayString,
    cmEthernetTrafficPortOuterVlanLoopback3              DisplayString,

    -- Link Loss Forwarding params 
    cmEthernetTrafficPortLinkLossFwdEnabled              TruthValue,
    cmEthernetTrafficPortLinkLossFwdSignalType           CmLinkLossFwdSignalType,
    cmEthernetTrafficPortLinkLossFwdTriggerTypes         CmLinkLossFwdTriggerTypes,
    cmEthernetTrafficPortLinkLossFwdDelay                Integer32,
    cmEthernetTrafficPortLinkLossFwdActive               TruthValue,
    cmEthernetTrafficPortLinkLossFwdPartnerEnabled       TruthValue,
    cmEthernetTrafficPortLinkLossFwdLocalLinkId          Integer32,
    cmEthernetTrafficPortLinkLossFwdRemoteLinkIds        DisplayString,
    cmEthernetTrafficPortLinkLossFwdTxActionType         CmLinkLossFwdTxActionType,
    cmEthernetTrafficPortLinkLossFwdRxRLDLinkIds         DisplayString,
    -- OAM params
    cmEthernetTrafficPortOamId                           Integer32,
    cmEthernetTrafficPortOamDiscoveryState               CmOamDiscoveryState,
    cmEthernetTrafficPortOamLocalVarRtrvsEnabled         TruthValue,
    cmEthernetTrafficPortOamLocalLinkEventsEnabled       TruthValue,
    cmEthernetTrafficPortOamLocalOamLoopbacksSupported   TruthValue,
    cmEthernetTrafficPortOamLocalUnidirSupportEnabled    TruthValue,
    cmEthernetTrafficPortOamLocalMaxPDUSize              Integer32,
    cmEthernetTrafficPortOamLocalMode                    CmOamMode,
    cmEthernetTrafficPortOamRemoteMacAddress             MacAddress,
    cmEthernetTrafficPortOamRemoteVarRtrvsEnabled        TruthValue,
    cmEthernetTrafficPortOamRemoteLinkEventsEnabled      TruthValue,
    cmEthernetTrafficPortOamRemoteOamLoopbacksSupported  TruthValue,
    cmEthernetTrafficPortOamRemoteUnidirSupportEnabled   TruthValue,
    cmEthernetTrafficPortOamRemoteMaxPDUSize             Integer32,
    cmEthernetTrafficPortOamRemoteMode                   CmOamMode,
    cmEthernetTrafficPortOamEnabled                      TruthValue,
    cmEthernetTrafficPortOamAdminState                   CmOamAdminState,
    -- Ethernet Port Service params
    cmEthernetTrafficPortSvcType                         CmEthernetTrafficSvcType,

    -- Ethernet Port Traffic params
    cmEthernetTrafficPortRxPauseEnabled                  TruthValue,
    cmEthernetTrafficPortTxPauseEnabled                  TruthValue,
    cmEthernetTrafficPortAfpType                         CmAfpType,

    -- Ethernet Port Traffic params
    cmEthernetTrafficPortShapingEnabled                  TruthValue,
    cmEthernetTrafficPortShapedSpeedLo                   Unsigned32,
    cmEthernetTrafficPortShapedSpeedHi                   Unsigned32,
    cmEthernetTrafficPortQinQEtherType                   Unsigned32,

    --Ethernet Port Services params
    cmEthernetTrafficPortTagFrameControl                 AfpTagControl,
    cmEthernetTrafficPortEgressVlanTrunkingEnabled       TruthValue,
    cmEthernetTrafficPortIngressPushPVIDEnabled          TruthValue,
    cmEthernetTrafficPortEgressPopPVIDEnabled            TruthValue,
    cmEthernetTrafficPortEgressPopPriorityVidEnabled     TruthValue,
    cmEthernetTrafficPortPortVlanId                      VlanId,
    cmEthernetTrafficPortPortVlanPriority                VlanPriority,     
    cmEthernetTrafficPortPriorityVlanId                  VlanId,     
    cmEthernetTrafficPortIngressPrioMapMode              PriorityMapMode,     
    cmEthernetTrafficPortIngressCOSPriority              VlanTagType,    
    --Synchronous Port params
    cmEthernetTrafficPortSyncEEnabled                    TruthValue,
    cmEthernetTrafficPortQLModeEnabled                   TruthValue,
    cmEthernetTrafficPortExpectedQL                      SSMQualityLevel,
    cmEthernetTrafficPortAssumedQL                       SSMQualityLevel,
    cmEthernetTrafficPortReceivedQL                      SSMQualityLevel,
    cmEthernetTrafficPortTransmitQL                      SSMQualityLevel,
    cmEthernetTrafficPortPhyType                         XgePhyType,
    cmEthernetTrafficPortSfpLaserWaveLengthPicometer     Unsigned32,
    cmEthernetTrafficPortRowStatus                       RowStatus,

    cmEthernetTrafficPortSSMRemoteMacAddress             MacAddress,
    cmEthernetTrafficPortInnerVlanLoopbackMask           INTEGER,
    cmEthernetTrafficPortInnerVlanLoopback1              DisplayString,
    cmEthernetTrafficPortInnerVlanLoopback2              DisplayString,
    cmEthernetTrafficPortInnerVlanLoopback3              DisplayString,
    cmEthernetTrafficPortLaserWDMChannel                 SfpChannelIdentifier,
    cmEthernetTrafficPortLaserIsTunable                  TruthValue,
    cmEthernetTrafficPortLaserFrequency                  Unsigned32,
    cmEthernetTrafficPortDeiEnable                       TruthValue,
    cmEthernetTrafficPortPcpDEEncType                    PcpDEEncType,
    cmEthernetTrafficPortPcpDEPairsAction                PcpDEPairsAction,
    cmEthernetTrafficPortInitiateDiag                    CmEthernetDiagAction,
    cmEthernetTrafficPortDiagnosePair1Cond               CmDiagCableCondType,
    cmEthernetTrafficPortDiagnosePair2Cond               CmDiagCableCondType,
    cmEthernetTrafficPortDiagnosePair3Cond               CmDiagCableCondType,
    cmEthernetTrafficPortDiagnosePair4Cond               CmDiagCableCondType,
    cmEthernetTrafficPortDiagnoseAutoNegCond             CmDiagAutoNegCondType,
    cmEthernetTrafficPortDiagnoseLpbkCond                CmDiagLpbkCondType,
    cmEthernetTrafficPortDiagnoseEfmLpbkCond             CmDiagEfmOamLpbkCondType,
    cmEthernetTrafficPortDiagnoseResult                  DisplayString,
    cmEthernetTrafficPortDiagnoseTestStatus              CmDiagTestStatus,
    cmEthernetTrafficPortDiagnoseTestTime                DateAndTime,
    cmEthernetTrafficPortAutoDiagEnabled                 TruthValue,
    cmEthernetTrafficPortDeleteEntitiesAction            TrafficPortDeleteEntitiesAction,
    cmEthernetTrafficPortMaxMpFpNum                      Integer32,
    cmEthernetTrafficPortJdsuLoopbackEnabled             TruthValue,
    cmEthernetTrafficPortJdsuLoopbackVlanId              VlanId,
    cmEthernetTrafficPortIngressPopPriorityVidEnabled    TruthValue,

    cmEthernetTrafficPortRxDeiAction                     RxDeiAction,
    cmEthernetTrafficPortTxDeiAction                     TxDeiAction,
    cmEthernetTrafficPortRxDeiOuterTagType               DeiOuterTagType,
    cmEthernetTrafficPortTxDeiOuterTagType               DeiOuterTagType
}

-- Port Indices 
cmEthernetTrafficPortIndex OBJECT-TYPE
    SYNTAX      Integer32 (1..65535)
    MAX-ACCESS  read-only
    STATUS      current
    DESCRIPTION
            "An integer index value used to uniquely identify
             this Ethernet Port within a card.
             Note that each Ethernet Port is uniquely identified
             by the indices neIndex, shelfIndex, 
             slotIndex, cmEthernetTrafficPortIndex." 
    ::= { cmEthernetTrafficPortEntry 1 }

cmEthernetTrafficPortIfIndex OBJECT-TYPE
    SYNTAX      InterfaceIndex 
    MAX-ACCESS  read-only
    STATUS      current
    DESCRIPTION
            "This object has the same value as ifIndex for 
             Ethernet Port.  An integer index value used to 
             uniquely identify this Ethernet Port."
    ::= { cmEthernetTrafficPortEntry 2 }

cmEthernetTrafficPortEntityIndex OBJECT-TYPE
    SYNTAX      PhysicalIndex 
    MAX-ACCESS  read-only
    STATUS      current
    DESCRIPTION
           "Entity Index from ENTITY-MIB for this port."
    ::= { cmEthernetTrafficPortEntry 3 }

-- State Management params
cmEthernetTrafficPortAdminState OBJECT-TYPE
    SYNTAX      AdminState 
    MAX-ACCESS  read-write
    STATUS      current
    DESCRIPTION
            "This object represents the Administrative State of the Ethernet Port."
    ::= { cmEthernetTrafficPortEntry 4 }

cmEthernetTrafficPortOperationalState OBJECT-TYPE
    SYNTAX      OperationalState 
    MAX-ACCESS  read-only
    STATUS      current
    DESCRIPTION
            "This object represents the Operational State of the Ethernet Port."
    ::= { cmEthernetTrafficPortEntry 5 }

cmEthernetTrafficPortSecondaryState OBJECT-TYPE
    SYNTAX      SecondaryState 
    MAX-ACCESS  read-only
    STATUS      current
    DESCRIPTION
            "This object represents the Secondary State of the Ethernet Port."
    ::= { cmEthernetTrafficPortEntry 6 }

-- Generic Port params
cmEthernetTrafficPortMTU OBJECT-TYPE
    SYNTAX      Integer32 
    MAX-ACCESS  read-write
    STATUS      current
    DESCRIPTION
            "This object provides the MTU on the Ethernet Port.
             The object is made read-write for FSP150CC devices."
    ::= { cmEthernetTrafficPortEntry 7 }

cmEthernetTrafficPortMediaType OBJECT-TYPE
    SYNTAX     EthernetMediaType
    MAX-ACCESS read-write
    STATUS     current
    DESCRIPTION
            "This object represents the type of Ethernet Media on the 
             Ethernet Port.
             The media type includes,
                 copper (1)
                 fiber (2)
                 coppersfp (3)
             CM Aggregation Product doesn't support copper."
    ::= { cmEthernetTrafficPortEntry 8 }

cmEthernetTrafficPortConfigSpeed OBJECT-TYPE
    SYNTAX     EthernetPortSpeed
    MAX-ACCESS read-write
    STATUS     current
    DESCRIPTION
            "This object allows to configure the speed of the 
             Ethernet Port."
    ::= { cmEthernetTrafficPortEntry 9 }

cmEthernetTrafficPortNegotiatedSpeed OBJECT-TYPE
    SYNTAX     EthernetPortSpeed
    MAX-ACCESS read-only
    STATUS     current
    DESCRIPTION
            "This object provides the negotiated speed of the 
             Ethernet Port."
    ::= { cmEthernetTrafficPortEntry 10 }

cmEthernetTrafficPortMDIXType OBJECT-TYPE
    SYNTAX     CmEthernetMDIXType
    MAX-ACCESS read-write
    STATUS     current
    DESCRIPTION
            "This object allows management of MDIX property on  
             Ethernet Port."
    ::= { cmEthernetTrafficPortEntry 11 }

cmEthernetTrafficPortMDIXStatus OBJECT-TYPE
    SYNTAX     CmEthernetMDIXType
    MAX-ACCESS read-only
    STATUS     current
    DESCRIPTION
         "This object provides the current MDIX status of the 
          Ethernet port."
     ::= { cmEthernetTrafficPortEntry 12 }
     
cmEthernetTrafficPortSfpVendorName OBJECT-TYPE
    SYNTAX  DisplayString (SIZE (0..16)) 
    MAX-ACCESS read-only
    STATUS     current
    DESCRIPTION
            "This object provides the vendor name of the SFP. 
             This is applicable when cmEthernetTrafficPortMediaType is fiber or coppersfp."
     ::= { cmEthernetTrafficPortEntry 13 }

cmEthernetTrafficPortSfpPartNumber OBJECT-TYPE
    SYNTAX  DisplayString (SIZE (0..16)) 
    MAX-ACCESS read-only
    STATUS     current
    DESCRIPTION
            "This object provides the part number of the SFP. 
             This is applicable when cmEthernetTrafficPortMediaType is fiber or coppersfp."
     ::= { cmEthernetTrafficPortEntry 14 }

cmEthernetTrafficPortSfpSerialNumber OBJECT-TYPE
    SYNTAX  DisplayString (SIZE (0..32)) 
    MAX-ACCESS read-only
    STATUS     current
    DESCRIPTION
            "This object provides the serial number of the SFP.  
             This is shown only when cmEthernetTrafficPortMediaType is fiber."
     ::= { cmEthernetTrafficPortEntry 15 }

cmEthernetTrafficPortSfpDateOfManufacture OBJECT-TYPE
    SYNTAX     DateAndTime 
    MAX-ACCESS read-only
    STATUS     current
    DESCRIPTION
            "This object provides the date of manufacture of the SFP.
             This is applicable when cmEthernetTrafficPortMediaType is fiber or coppersfp."
     ::= { cmEthernetTrafficPortEntry 16 }

cmEthernetTrafficPortSfpConnectorValue OBJECT-TYPE
    SYNTAX     SfpConnectorValue 
    MAX-ACCESS read-only
    STATUS     current
    DESCRIPTION
            "This object provides the SFP connector value.
             This is applicable when cmEthernetTrafficPortMediaType is fiber or coppersfp."
     ::= { cmEthernetTrafficPortEntry 17 }

-- Generic Ethernet Port params
cmEthernetTrafficPortSfpLinkLength OBJECT-TYPE
    SYNTAX     Integer32
    MAX-ACCESS read-only
    STATUS     current
    DESCRIPTION
         "This object provides the SFP Link Length.
          This is applicable only when cmEthernetTrafficPortMediaType is fiber or coppersfp."
     ::= { cmEthernetTrafficPortEntry 18 }

cmEthernetTrafficPortSfpLaserWaveLength OBJECT-TYPE
    SYNTAX     Integer32
    MAX-ACCESS read-only
    STATUS     current
    DESCRIPTION
         "This object provides the SFP Laser Wave Length in nano meters.
          This is applicable only when cmEthernetTrafficPortMediaType is fiber."
     ::= { cmEthernetTrafficPortEntry 19 }
     
cmEthernetTrafficPortSfpMediaType OBJECT-TYPE
    SYNTAX     SfpMediaType
    MAX-ACCESS read-only
    STATUS     current
    DESCRIPTION
         "This object provides the SFP Media Type.
          This is applicable only when cmEthernetTrafficPortMediaType is fiber or coppersfp."
     ::= { cmEthernetTrafficPortEntry 20 }

-- Ethernet Loopback params
cmEthernetTrafficPortLoopbackConfig OBJECT-TYPE
    SYNTAX     CmLoopbackType
    MAX-ACCESS read-write
    STATUS     current
    DESCRIPTION
            "This object allows to initiate loopbacks on 
             on the Ethernet Port."
     ::= { cmEthernetTrafficPortEntry 21 }

cmEthernetTrafficPortLoopbackStatus OBJECT-TYPE
    SYNTAX     CmLoopbackType
    MAX-ACCESS read-only
    STATUS     current
    DESCRIPTION
            "This object provides status of the current loopback 
             on the Ethernet Port."
     ::= { cmEthernetTrafficPortEntry 22 }

cmEthernetTrafficPortLoopbackTime OBJECT-TYPE                   
    SYNTAX     Integer32 (2..300)
    MAX-ACCESS read-write
    STATUS     current
    DESCRIPTION
            "This object allows to specify time for timed-loopbacks on 
             on the Ethernet Port."
     ::= { cmEthernetTrafficPortEntry 23 }

cmEthernetTrafficPortLoopbackSwapSADA OBJECT-TYPE
    SYNTAX     CmSwapSADAType
    MAX-ACCESS read-write
    STATUS     current
    DESCRIPTION
            "This object allows to specify whether or not the loopbacked
             frame will have the Source Address and Destination Address
             swapped."
     ::= { cmEthernetTrafficPortEntry 24 }

cmEthernetTrafficPortOuterVlanLoopbackMask OBJECT-TYPE
    SYNTAX     INTEGER (0..16)
    MAX-ACCESS read-write
    STATUS     current
    DESCRIPTION
             "This object allows specification of the outer VLANs to be 
              looped back when port is in vlan(terminal/facility) 
              loopback configuration. Only 3 VLANs can be specified 
              for vlan loopback. The various bit positions are:
                   1         Outer VLAN 1 Loopback Enabled
                   2         Outer VLAN 2 Loopback Enabled
                   4         Outer VLAN 3 Loopback Enabled"
     ::= { cmEthernetTrafficPortEntry 25 }

cmEthernetTrafficPortOuterVlanLoopback1 OBJECT-TYPE              
    SYNTAX  DisplayString (SIZE (0..6)) 
    MAX-ACCESS read-write
    STATUS     current
    DESCRIPTION
             "This object allows specification of the outer VLAN 1 to be 
              looped back when port is in vlan(terminal/facility) 
              loopback configuration. This is valid only if the
              corresponding bit in cmEthernetTrafficPortOuterVlanLoopbackMask
              is set.  The value to be specified should be in the form 
              X-Y where X is the VLAN Id and Y is the VLAN Priority.  
              If Y is specified as a *, all Priorities (0 to 7) 
              are looped back."
     ::= { cmEthernetTrafficPortEntry 26 }

cmEthernetTrafficPortOuterVlanLoopback2 OBJECT-TYPE
    SYNTAX  DisplayString (SIZE (0..6)) 
    MAX-ACCESS read-write
    STATUS     current
    DESCRIPTION
             "This object allows specification of the outer VLAN 2 to be 
              looped back when port is in vlan(terminal/facility) 
              loopback configuration. This is valid only if the
              corresponding bit in cmEthernetTrafficPortOuterVlanLoopbackMask
              is set.  The value to be specified should be in the form 
              X-Y where X is the VLAN Id and Y is the VLAN Priority.  
              If Y is specified as a *, all Priorities (0 to 7) 
              are looped back."
     ::= { cmEthernetTrafficPortEntry 27 }

cmEthernetTrafficPortOuterVlanLoopback3 OBJECT-TYPE
    SYNTAX  DisplayString (SIZE (0..6)) 
    MAX-ACCESS read-write
    STATUS     current
    DESCRIPTION
             "This object allows specification of the outer VLAN 3 to be 
              looped back when port is in vlan(terminal/facility) 
              loopback configuration. This is valid only if the
              corresponding bit in cmEthernetTrafficPortOuterVlanLoopbackMask
              is set.  The value to be specified should be in the form 
              X-Y where X is the VLAN Id and Y is the VLAN Priority.  
              If Y is specified as a *, all Priorities (0 to 7) 
              are looped back."
     ::= { cmEthernetTrafficPortEntry 28 }

-- Link Loss Forwarding params 
cmEthernetTrafficPortLinkLossFwdEnabled OBJECT-TYPE
    SYNTAX     TruthValue
    MAX-ACCESS read-write
    STATUS     current
    DESCRIPTION
             "This object allows enabling/disabling link loss forwarding 
              on the Ethernet Port." 
     ::= { cmEthernetTrafficPortEntry 29 }

cmEthernetTrafficPortLinkLossFwdSignalType  OBJECT-TYPE
    SYNTAX     CmLinkLossFwdSignalType
    MAX-ACCESS read-write
    STATUS     current
    DESCRIPTION
             "This object allows definition of the link loss forwarding
              signalling type.  This is applicable only if 
              cmEthernetTrafficPortLinkLossFwdEnabled is enabled."
     ::= { cmEthernetTrafficPortEntry 30 }

cmEthernetTrafficPortLinkLossFwdTriggerTypes  OBJECT-TYPE
    SYNTAX     CmLinkLossFwdTriggerTypes
    MAX-ACCESS read-write
    STATUS     current
    DESCRIPTION
             "This object allows definition of the link loss forwarding
              trigger types.  This is applicable only if 
              cmEthernetTrafficPortLinkLossFwdEnabled is enabled."
     ::= { cmEthernetTrafficPortEntry 31 }

cmEthernetTrafficPortLinkLossFwdDelay OBJECT-TYPE                
    SYNTAX     Integer32
    MAX-ACCESS read-write
    STATUS     current
    DESCRIPTION
             "This object allows specification of the delay between
              detection of link loss and signalling of link loss forwarding. 
              Time specified is in seconds."
     ::= { cmEthernetTrafficPortEntry 32 }

cmEthernetTrafficPortLinkLossFwdActive OBJECT-TYPE 
    SYNTAX     TruthValue
    MAX-ACCESS read-only
    STATUS     current
    DESCRIPTION
             "This object provides the link loss forwarding status indicating
              if link loss forwarding is currently being signaled via 
              the port." 
     ::= { cmEthernetTrafficPortEntry 33 }

cmEthernetTrafficPortLinkLossFwdPartnerEnabled OBJECT-TYPE 
    SYNTAX     TruthValue
    MAX-ACCESS read-only
    STATUS     current
    DESCRIPTION
             "This object provides the indication of a link partners ability
              to support link loss forwarding via EFM, i.e. from
              received organization specific OAMPDUs." 
     ::= { cmEthernetTrafficPortEntry 34 }

cmEthernetTrafficPortLinkLossFwdLocalLinkId OBJECT-TYPE 
    SYNTAX     Integer32
    MAX-ACCESS read-write
    STATUS     current
    DESCRIPTION
             "This object allows configuration of the Local Link Id on 
              Ethernet port." 
     ::= { cmEthernetTrafficPortEntry 35 }

cmEthernetTrafficPortLinkLossFwdRemoteLinkIds OBJECT-TYPE 
    SYNTAX     DisplayString (SIZE (0..512)) 
    MAX-ACCESS read-write
    STATUS     current
    DESCRIPTION
             "This object allows enabling/disabling Remote Link Ids 
              on Ethernet port. the Ethernet port is able to distinguish 
              the remote side client ports from the Remote Link Down
              PDUs coming from remote end. The cmEthernetTrafficPortLinkLossFwdLocalLinkId must
              be set before set cmEthernetTrafficPortLinkLossFwdRemoteLinkIds,
              By setting the Remote Link Ids seperated by the comma,
              e.g. 1,2,3,10,20..., up to 10 remote ID numbers 
              can be added, number ranger is from 1 to 256(for EGX8.1, max value is 554).
              By setting nothing or '' to disable the Remote Link Ids."
     ::= { cmEthernetTrafficPortEntry 36 }
     
cmEthernetTrafficPortLinkLossFwdTxActionType OBJECT-TYPE
    SYNTAX     CmLinkLossFwdTxActionType
    MAX-ACCESS read-write
    STATUS     current
    DESCRIPTION
         "This object allows to specify the Ethernet Port's behavior when
          link loss forwarding trigger events occur on the Port.
          This provides ability to configure per Ethernet port LLF behavior." 
     ::= { cmEthernetTrafficPortEntry 37 }

cmEthernetTrafficPortLinkLossFwdRxRLDLinkIds OBJECT-TYPE
    SYNTAX     DisplayString (SIZE (0..512))
    MAX-ACCESS read-only
    STATUS     current
    DESCRIPTION
         "This object provides the received Remote Link IDs in 
          EFM RLD messages on the Ethernet Port." 
     ::= { cmEthernetTrafficPortEntry 38 }
     
-- OAM params
cmEthernetTrafficPortOamId  OBJECT-TYPE
    SYNTAX     Integer32 
    MAX-ACCESS read-only
    STATUS     current
    DESCRIPTION
             "OAM Id.  This is unique EFM OAM sublayer port id." 
     ::= { cmEthernetTrafficPortEntry 39 }

cmEthernetTrafficPortOamDiscoveryState  OBJECT-TYPE
    SYNTAX     CmOamDiscoveryState
    MAX-ACCESS read-only
    STATUS     current
    DESCRIPTION
             "Ethernet Port's OAM discovery state." 
     ::= { cmEthernetTrafficPortEntry 40 }

cmEthernetTrafficPortOamLocalVarRtrvsEnabled  OBJECT-TYPE
    SYNTAX     TruthValue
    MAX-ACCESS read-only
    STATUS     current
    DESCRIPTION
             "This object allows specification of whether the Ethernet
              Port supports sending variable response OAMPDUs." 
     ::= { cmEthernetTrafficPortEntry 41 }

cmEthernetTrafficPortOamLocalLinkEventsEnabled  OBJECT-TYPE
    SYNTAX     TruthValue 
    MAX-ACCESS read-only
    STATUS     current
    DESCRIPTION
             "This object allows specification of whether the Ethernet
              Port supports interpreting Link Events."
     ::= { cmEthernetTrafficPortEntry 42 }

cmEthernetTrafficPortOamLocalOamLoopbacksSupported  OBJECT-TYPE
    SYNTAX     TruthValue 
    MAX-ACCESS read-write
    STATUS     current
    DESCRIPTION
             "This object allows specification of whether the Ethernet
              Port is capable of OAM remote loopback mode."
     ::= { cmEthernetTrafficPortEntry 43 }

cmEthernetTrafficPortOamLocalUnidirSupportEnabled  OBJECT-TYPE
    SYNTAX     TruthValue 
    MAX-ACCESS read-only
    STATUS     current
    DESCRIPTION
             "This object allows specification of whether the Ethernet
              Port is capable of sending OAMPDUs when the receive path 
              is non-operational."
     ::= { cmEthernetTrafficPortEntry 44 }

cmEthernetTrafficPortOamLocalMaxPDUSize  OBJECT-TYPE
    SYNTAX     Integer32
    MAX-ACCESS read-only
    STATUS     current
    DESCRIPTION
             "This object represents the largest OAMPDU, in octets, 
              supported by the Ethernet Port.  This value is
              compared to the remote Maximum PDU Size and the smaller of 
              the two is used." 
     ::= { cmEthernetTrafficPortEntry 45 }

cmEthernetTrafficPortOamLocalMode OBJECT-TYPE
    SYNTAX     CmOamMode 
    MAX-ACCESS read-write
    STATUS     current
    DESCRIPTION
             "This object allows to configure the OAM sublayer entity in
              either Active or Passive mode." 
     ::= { cmEthernetTrafficPortEntry 46 }

cmEthernetTrafficPortOamRemoteMacAddress OBJECT-TYPE
    SYNTAX     MacAddress
    MAX-ACCESS read-only
    STATUS     current
    DESCRIPTION
             "This object allows retrieval of the Remote Mac Address." 
     ::= { cmEthernetTrafficPortEntry 47 }

cmEthernetTrafficPortOamRemoteVarRtrvsEnabled OBJECT-TYPE
    SYNTAX     TruthValue
    MAX-ACCESS read-only
    STATUS     current
    DESCRIPTION
             "This object allows retrieval of whether the remote OAM 
              entity supports sending variable response OAMPDUs." 
     ::= { cmEthernetTrafficPortEntry 48 }

cmEthernetTrafficPortOamRemoteLinkEventsEnabled OBJECT-TYPE
    SYNTAX     TruthValue 
    MAX-ACCESS read-only
    STATUS     current
    DESCRIPTION
             "This object allows retrieval of whether the remote OAM 
              entity supports interpreting Link Events."
     ::= { cmEthernetTrafficPortEntry 49 }

cmEthernetTrafficPortOamRemoteOamLoopbacksSupported OBJECT-TYPE
    SYNTAX     TruthValue 
    MAX-ACCESS read-only
    STATUS     current
    DESCRIPTION
             "This object allows retrieval of whether the remote OAM 
              entity supports OAM remote loopback mode."
     ::= { cmEthernetTrafficPortEntry 50 }

cmEthernetTrafficPortOamRemoteUnidirSupportEnabled OBJECT-TYPE
    SYNTAX     TruthValue 
    MAX-ACCESS read-only
    STATUS     current
    DESCRIPTION
             "This object allows retrieval of whether the remote 
              OAM entity is capable of sending OAMPDUs when the receive path 
              is non-operational."
     ::= { cmEthernetTrafficPortEntry 51 }

cmEthernetTrafficPortOamRemoteMaxPDUSize OBJECT-TYPE
    SYNTAX     Integer32
    MAX-ACCESS read-only
    STATUS     current
    DESCRIPTION
             "This object allows retrieval of the remote OAM 
              entity maximum OAMPDU size."
     ::= { cmEthernetTrafficPortEntry 52 }

cmEthernetTrafficPortOamRemoteMode OBJECT-TYPE
    SYNTAX     CmOamMode 
    MAX-ACCESS read-only
    STATUS     current
    DESCRIPTION
             "This object allows to retrieve whether the remote OAM 
              sublayer entity is either in Active or Passive mode." 
     ::= { cmEthernetTrafficPortEntry 53 }

cmEthernetTrafficPortOamEnabled  OBJECT-TYPE
    SYNTAX     TruthValue
    MAX-ACCESS read-write 
    STATUS     current
    DESCRIPTION
             "This object allows to manage the EFM OAM on Ethernet Traffic Port."
     ::= { cmEthernetTrafficPortEntry 54 }

cmEthernetTrafficPortOamAdminState OBJECT-TYPE
    SYNTAX     CmOamAdminState
    MAX-ACCESS read-only 
    STATUS     current
    DESCRIPTION
             "This object provides the EFM OAM Admin State."
     ::= { cmEthernetTrafficPortEntry 55 }
     
-- Ethernet Port Service params
cmEthernetTrafficPortSvcType  OBJECT-TYPE 
    SYNTAX     CmEthernetTrafficSvcType 
    MAX-ACCESS read-write
    STATUS     current
    DESCRIPTION
             "This object allows specification of whether the 
              Ethernet Port is port based or vlan based." 
     ::= { cmEthernetTrafficPortEntry 56 }

-- Ethernet Port Traffic params
cmEthernetTrafficPortRxPauseEnabled OBJECT-TYPE 
    SYNTAX     TruthValue
    MAX-ACCESS read-write
    STATUS     current
    DESCRIPTION
         "This object defines the RxPause enable or disable of the port."
     ::= { cmEthernetTrafficPortEntry 57 }

cmEthernetTrafficPortTxPauseEnabled OBJECT-TYPE
    SYNTAX     TruthValue
    MAX-ACCESS read-write
    STATUS     current
    DESCRIPTION
         "This object allows enabling/disabling transmit pause frames on
          Ethernet port."
     ::= { cmEthernetTrafficPortEntry 58 }

cmEthernetTrafficPortAfpType OBJECT-TYPE
    SYNTAX     CmAfpType
    MAX-ACCESS read-write
    STATUS     current
    DESCRIPTION
         "This object allows specification of the Acceptable Frame Policy on
          Ethernet port. Users can specify whether the port supports
          only tagged frames, only untagged frames or both tagged and 
          untagged frames."
     ::= { cmEthernetTrafficPortEntry 59 }

-- Ethernet Port Traffic params
cmEthernetTrafficPortShapingEnabled OBJECT-TYPE
    SYNTAX     TruthValue
    MAX-ACCESS read-write
    STATUS     current
    DESCRIPTION
         "This object allows to manage the Ethernet Port Shaping.
          When enabled, values in cmEthernetTrafficPortShapedSpeedLo and
          cmEthernetTrafficPortShapedSpeedHi are applicable."
     ::= { cmEthernetTrafficPortEntry 60 }

cmEthernetTrafficPortShapedSpeedLo OBJECT-TYPE
    SYNTAX     Unsigned32
    MAX-ACCESS read-write
    STATUS     current
    DESCRIPTION
         "This object allows to specify the lower 32 bits of 
          the Ethernet Port Shaped speed. This value is applicable
          when cmEthernetTrafficPortShapingEnabled is enabled."
     ::= { cmEthernetTrafficPortEntry 61 }

cmEthernetTrafficPortShapedSpeedHi OBJECT-TYPE
    SYNTAX     Unsigned32
    MAX-ACCESS read-write
    STATUS     current
    DESCRIPTION
         "This object allows to specify the higher 32 bits of 
          the Port Shaped speed. This value is applicable
          when cmEthernetTrafficPortShapingEnabled is enabled."
     ::= { cmEthernetTrafficPortEntry 62 }

cmEthernetTrafficPortQinQEtherType OBJECT-TYPE
    SYNTAX     Unsigned32
    MAX-ACCESS read-write
    STATUS     current
    DESCRIPTION
         "This object allows to specify the Q-in-Q Ether Type 
          on the Port."
     ::= { cmEthernetTrafficPortEntry 63 }

--Ethernet Port Services params

cmEthernetTrafficPortTagFrameControl OBJECT-TYPE 
    SYNTAX     AfpTagControl
    MAX-ACCESS read-write
    STATUS     current
    DESCRIPTION
         "This object defines if c-tag/s-tag frame is allowed to pass through,
          available only when AFP is set to Tagged."
     ::= { cmEthernetTrafficPortEntry 64 }
     
cmEthernetTrafficPortEgressVlanTrunkingEnabled OBJECT-TYPE
    SYNTAX     TruthValue
    MAX-ACCESS read-write
    STATUS     current
    DESCRIPTION
         "This object allows to enable or disable the VLAN trunking on
          Ethernet port. Disabling VLAN trunking removes all
          VLAN tags before transmitting traffic out of the port. 
          This object is only applicable for connection-oriented, 
          evpl service type."
     ::= { cmEthernetTrafficPortEntry 65 }

cmEthernetTrafficPortIngressPushPVIDEnabled OBJECT-TYPE
    SYNTAX     TruthValue
    MAX-ACCESS read-write
    STATUS     current
    DESCRIPTION
         "This object allows to specify whether cmEthernetTrafficPortPortVlanId
          value will be PUSHed on untagged frames or not in the 
          ingress direction.  This object is only applicable 
          for connection-oriented, evpl service type."
     ::= { cmEthernetTrafficPortEntry 66 }

cmEthernetTrafficPortEgressPopPVIDEnabled OBJECT-TYPE
    SYNTAX     TruthValue
    MAX-ACCESS read-write
    STATUS     current
    DESCRIPTION
         "This object allows to specify whether cmEthernetTrafficPortPortVlanId
          value will be POPed in the 
          egress direction.  This object is only applicable 
          for connection-oriented, evpl service type."
     ::= { cmEthernetTrafficPortEntry 67 }

cmEthernetTrafficPortEgressPopPriorityVidEnabled OBJECT-TYPE 
    SYNTAX     TruthValue
    MAX-ACCESS read-write
    STATUS     current
    DESCRIPTION
         "This object defines the egress PopPriorityVid enable or disable of the port.
         If it is enabled, the outgoing packets with VID=Priority VLAN ID 
         will be swapped back to VID=0."
     ::= { cmEthernetTrafficPortEntry 68 }

cmEthernetTrafficPortPortVlanId OBJECT-TYPE
    SYNTAX     VlanId
    MAX-ACCESS read-write
    STATUS     current
    DESCRIPTION
         "This object allows to specify the Ethernet Port VLAN Id 
          to PUSH on untagged frames in the to Network
          direction.  This object is only applicable for connection-oriented,
          evpl service type, when cmEthernetTrafficPortIngressPushPVIDEnabled 
          is set to true."
     ::= { cmEthernetTrafficPortEntry 69 }

cmEthernetTrafficPortPortVlanPriority OBJECT-TYPE
    SYNTAX     VlanPriority
    MAX-ACCESS read-write
    STATUS     current
    DESCRIPTION
         "This object allows to specify the Ethernet Port VLAN Priority 
          for the PUSHed VLAN tag (specified by cmEthernetTrafficPortPortVlanId) 
          on untagged frames in the ingress direction.  
          This object is only applicable for connection-oriented,
          evpl service type, when cmEthernetTrafficPortIngressPushPVIDEnabled 
          is set to true."
     ::= { cmEthernetTrafficPortEntry 70 }

cmEthernetTrafficPortPriorityVlanId OBJECT-TYPE 
    SYNTAX     VlanId
    MAX-ACCESS read-write
    STATUS     current
    DESCRIPTION
         "This object allows to specify the Ethernet Priority VLAN Id 
          to replace the null-tagged or priority tagged frames in the 
          to ingress direction.  This object is only applicable 
          for connection-oriented, evpl service type."
     ::= { cmEthernetTrafficPortEntry 71 }

cmEthernetTrafficPortIngressPrioMapMode OBJECT-TYPE
    SYNTAX     PriorityMapMode
    MAX-ACCESS read-write
    STATUS     current
    DESCRIPTION
         "This object allows to specify the Ethernet Port 
          Priority Mapping Mode used for classification of frames.
          This object is only applicable for connection-oriented,
          evpl service type."
     ::= { cmEthernetTrafficPortEntry 72 }

cmEthernetTrafficPortIngressCOSPriority  OBJECT-TYPE
    SYNTAX     VlanTagType
    MAX-ACCESS read-create
    STATUS     current
    DESCRIPTION
         "This object is used to specify whether the EthernetTrafficPort
          uses the inner-tag or the outer-tag in determining the COS (Class of Service)." 
     ::= { cmEthernetTrafficPortEntry 73 }
     
--Synchronous Port params
cmEthernetTrafficPortSyncEEnabled OBJECT-TYPE 
    SYNTAX     TruthValue
    MAX-ACCESS read-write
    STATUS     current
    DESCRIPTION
         "This object allows to specify whether the Ethernet Port 
          can be enabled/disabled for Synchronous Ethernet. This object
          is only applicable for Synchronous Ethernet capable ports.
          When enabled, on receive side 
            -port can extract the frequency of its input signal
             and pass the recovered clock to the system clock
            -port processes the ESMC(Ethernet Synchronization Messaging
             Channel) and extracts the QL (when also QL enabled)   
            -port is eligible to be selected as a system clock reference
          When enabled, on transmit side 
            -port's transmit clock is locked to the system clock
            -port generates an ESMC to generate a QL (when also QL enabled)

          When disabled, on receive side,
            -port does not pass the recovered clock to the system clock 
            -port does not process the ESMC (if present) 
            -port is not eligible to be selected as a 
                     system clock reference
          When disabled, on transmit side 
            -port's output frequency may be synchronized to the system clock
            -port does not generate an ESMC."
     ::= { cmEthernetTrafficPortEntry 74 }

cmEthernetTrafficPortQLModeEnabled OBJECT-TYPE 
    SYNTAX     TruthValue
    MAX-ACCESS read-write
    STATUS     current
    DESCRIPTION
         "This object allows to specify whether the Ethernet Port 
          can be enabled/disabled for QL Mode. This object
          is only applicable for Synchronous Ethernet capable ports,
          when cmEthernetTrafficPortQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { cmEthernetTrafficPortEntry 75 }

cmEthernetTrafficPortExpectedQL OBJECT-TYPE 
    SYNTAX     SSMQualityLevel
    MAX-ACCESS read-write
    STATUS     current
    DESCRIPTION
         "This object allows to specify the expected QL when the 
          Ethernet Port is enabled for QL Mode. This object
          is only applicable for Synchronous Ethernet capable ports,
          when cmEthernetTrafficPortQLModeEnabled is set to true.
          This object allows the user to set a minimum
          expected received Quality Level on the port. The valid values
          depend upon the SYNC entity Network Clock Type. A value of
          None represents that a minimum Quality Level is not expected. 
          The default value shall be None."
     ::= { cmEthernetTrafficPortEntry 76 }

cmEthernetTrafficPortAssumedQL OBJECT-TYPE 
    SYNTAX     SSMQualityLevel
    MAX-ACCESS read-write
    STATUS     current
    DESCRIPTION
         "This object allows to specify the assumed QL on the 
          Ethernet Port. This object is only applicable for 
          Synchronous Ethernet capable ports. 
          The Assumed QL is only meaningful if the Network Clock Type
          (see fsp150cm-sync.mib) is option1 and the 
          port TransmitQL Mode is disabled and the port is being used as 
          an input reference source. Under these conditions, 
          the specified QL value is assumed to be the Quality Level of the
          non-failed reference."
     ::= { cmEthernetTrafficPortEntry 77 }

cmEthernetTrafficPortReceivedQL OBJECT-TYPE 
    SYNTAX     SSMQualityLevel
    MAX-ACCESS read-only
    STATUS     current
    DESCRIPTION
         "This object provides the Received QL value for the Ethernet port. 
          If the Ethernet port TransmitQL Mode is disabled, then the received 
          QL value is not applicable.This object is only applicable for 
          Synchronous Ethernet capable ports."
     ::= { cmEthernetTrafficPortEntry 78 }

cmEthernetTrafficPortTransmitQL OBJECT-TYPE 
    SYNTAX     SSMQualityLevel
    MAX-ACCESS read-only
    STATUS     current
    DESCRIPTION
         "This object provides the Transmitted QL value for the Ethernet port. 
          If the Ethernet port TransmitQL Mode is disabled, then the received 
          QL value is not applicable. This object is only applicable for 
          Synchronous Ethernet capable ports."
     ::= { cmEthernetTrafficPortEntry 79 }

cmEthernetTrafficPortPhyType OBJECT-TYPE 
    SYNTAX     XgePhyType
    MAX-ACCESS read-write
    STATUS     current
    DESCRIPTION
         "This object is valid only to XGE card. And the value should be LAN or WAN when 
         it is XGE card."
     ::= { cmEthernetTrafficPortEntry 80 }

cmEthernetTrafficPortSfpLaserWaveLengthPicometer OBJECT-TYPE 
    SYNTAX     Unsigned32
    MAX-ACCESS read-only
    STATUS     current
    DESCRIPTION
         "This object provide laser wavelength pico value.
          For example, laser wavelength is 1510.01,
          then cmEthernetTrafficPortSfpLaserWaveLength=1510 
          and cmTrafficPortSfpLaserWaveLengthPicometer=10."
     ::= { cmEthernetTrafficPortEntry 81 }

cmEthernetTrafficPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of cmEthernetTrafficPortRowStatus supported are
            createAndGo(4) and destroy(6).  All mandatory attributes
            must be specified in a single SNMP SET request with
            neRowStatus value as createAndGo(4).
            Upon successful row creation, this object has a
            value of active(1).

            The cmEthernetTrafficPortRowStatus object may be modified if
            the associated instance of this object is equal to active(1)."
    ::= { cmEthernetTrafficPortEntry 82 }

cmEthernetTrafficPortSSMRemoteMacAddress OBJECT-TYPE
    SYNTAX     MacAddress
    MAX-ACCESS read-only
    STATUS     current
    DESCRIPTION
             "This object allows retrieval of the Remote Mac Address, when
              the port is peering using SSM." 
     ::= { cmEthernetTrafficPortEntry 83 }

cmEthernetTrafficPortInnerVlanLoopbackMask OBJECT-TYPE
    SYNTAX     INTEGER (0..16)
    MAX-ACCESS read-write
    STATUS     current
    DESCRIPTION
             "This object allows specification of the inner VLANs to be 
              looped back when port is in vlan(terminal/facility) 
              loopback configuration. Only 3 VLANs can be specified 
              for vlan loopback. The various bit positions are:
                   1         Inner VLAN 1 Loopback Enabled
                   2         Inner VLAN 2 Loopback Enabled
                   4         Inner VLAN 3 Loopback Enabled"
     ::= { cmEthernetTrafficPortEntry 84 }

cmEthernetTrafficPortInnerVlanLoopback1 OBJECT-TYPE              
    SYNTAX  DisplayString (SIZE (0..6)) 
    MAX-ACCESS read-write
    STATUS     current
    DESCRIPTION
             "This object allows specification of the inner VLAN 1 to be 
              looped back when port is in vlan(terminal/facility) 
              loopback configuration. This is valid only if the
              corresponding bit in cmEthernetTrafficPortInnerVlanLoopbackMask
              is set.  The value to be specified should be in the form 
              X-Y where X is the VLAN Id and Y is the VLAN Priority.  
              If Y is specified as a *, all Priorities (0 to 7) 
              are looped back."
     ::= { cmEthernetTrafficPortEntry 85 }

cmEthernetTrafficPortInnerVlanLoopback2 OBJECT-TYPE
    SYNTAX  DisplayString (SIZE (0..6)) 
    MAX-ACCESS read-write
    STATUS     current
    DESCRIPTION
             "This object allows specification of the inner VLAN 2 to be 
              looped back when port is in vlan(terminal/facility) 
              loopback configuration. This is valid only if the
              corresponding bit in cmEthernetTrafficPortInnerVlanLoopbackMask
              is set.  The value to be specified should be in the form 
              X-Y where X is the VLAN Id and Y is the VLAN Priority.  
              If Y is specified as a *, all Priorities (0 to 7) 
              are looped back."
     ::= { cmEthernetTrafficPortEntry 86 }

cmEthernetTrafficPortInnerVlanLoopback3 OBJECT-TYPE
    SYNTAX  DisplayString (SIZE (0..6)) 
    MAX-ACCESS read-write
    STATUS     current
    DESCRIPTION
             "This object allows specification of the inner VLAN 3 to be 
              looped back when port is in vlan(terminal/facility) 
              loopback configuration. This is valid only if the
              corresponding bit in cmEthernetTrafficPortInnerVlanLoopbackMask
              is set.  The value to be specified should be in the form 
              X-Y where X is the VLAN Id and Y is the VLAN Priority.  
              If Y is specified as a *, all Priorities (0 to 7) 
              are looped back."
     ::= { cmEthernetTrafficPortEntry 87 }

cmEthernetTrafficPortLaserWDMChannel OBJECT-TYPE
    SYNTAX  SfpChannelIdentifier 
    MAX-ACCESS read-write
    STATUS     current
    DESCRIPTION
             "Channel number of WDM tunable XFP setting."
     ::= { cmEthernetTrafficPortEntry 88 }

cmEthernetTrafficPortLaserIsTunable OBJECT-TYPE
    SYNTAX  TruthValue 
    MAX-ACCESS read-only
    STATUS     current
    DESCRIPTION
             "This object means this module whether tunnable."
     ::= { cmEthernetTrafficPortEntry 89 }

cmEthernetTrafficPortLaserFrequency OBJECT-TYPE
    SYNTAX  Unsigned32 
    MAX-ACCESS read-only
    STATUS     current
    DESCRIPTION
             "This object describes this module's frequency, and the step is 1GHZ."
     ::= { cmEthernetTrafficPortEntry 90 }

cmEthernetTrafficPortDeiEnable OBJECT-TYPE
    SYNTAX  TruthValue 
    MAX-ACCESS read-write
    STATUS     deprecated
    DESCRIPTION
             "This object describes whether use DEI bit in S-tag to 
             recognize Drop Eligibility Parameter for ingress S-tag packets or Set 
             DEI bit for egress S-tag Packets. "
     ::= { cmEthernetTrafficPortEntry 91 }

cmEthernetTrafficPortPcpDEEncType OBJECT-TYPE
    SYNTAX  PcpDEEncType 
    MAX-ACCESS read-write
    STATUS     current
    DESCRIPTION
             "This object describes the PCP encoding mode for egress packets
             and the PCP decoding mode for ingress packets on this port."
     ::= { cmEthernetTrafficPortEntry 92 }

cmEthernetTrafficPortPcpDEPairsAction OBJECT-TYPE
    SYNTAX  PcpDEPairsAction 
    MAX-ACCESS read-write
    STATUS     current
    DESCRIPTION
             "This object describes this port pcp de pairs action."
     ::= { cmEthernetTrafficPortEntry 93 }

-- EtherJack Diagnosis params
cmEthernetTrafficPortInitiateDiag  OBJECT-TYPE
    SYNTAX     CmEthernetDiagAction
    MAX-ACCESS read-write
    STATUS     current
    DESCRIPTION
            "This object allows to initiate Etherjack diagnosis on the
             Ethernet Traffic Port."
     ::= { cmEthernetTrafficPortEntry 94 }

cmEthernetTrafficPortDiagnosePair1Cond OBJECT-TYPE
    SYNTAX     CmDiagCableCondType
    MAX-ACCESS read-only
    STATUS     current
    DESCRIPTION
            "This object provides diagnosis results for the cable Pair 1
             on Ethernet Traffic Port."
     ::= { cmEthernetTrafficPortEntry 95 }

cmEthernetTrafficPortDiagnosePair2Cond OBJECT-TYPE
    SYNTAX     CmDiagCableCondType
    MAX-ACCESS read-only
    STATUS     current
    DESCRIPTION
            "This object provides diagnosis results for the cable Pair 2
             on Ethernet Traffic Port."
     ::= { cmEthernetTrafficPortEntry 96 }

cmEthernetTrafficPortDiagnosePair3Cond OBJECT-TYPE
    SYNTAX     CmDiagCableCondType
    MAX-ACCESS read-only
    STATUS     current
    DESCRIPTION
            "This object provides diagnosis results for the cable Pair 3
             on Ethernet Traffic Port."
     ::= { cmEthernetTrafficPortEntry 97 }

cmEthernetTrafficPortDiagnosePair4Cond OBJECT-TYPE
    SYNTAX     CmDiagCableCondType
    MAX-ACCESS read-only
    STATUS     current
    DESCRIPTION
            "This object provides diagnosis results for the cable Pair 4
             on Ethernet Traffic Port."
     ::= { cmEthernetTrafficPortEntry 98 }

cmEthernetTrafficPortDiagnoseAutoNegCond OBJECT-TYPE
    SYNTAX     CmDiagAutoNegCondType
    MAX-ACCESS read-only
    STATUS     current
    DESCRIPTION
            "This object provides auto negotiation results of the diagnosis
             test on Ethernet Traffic Port."
     ::= { cmEthernetTrafficPortEntry 99 }

cmEthernetTrafficPortDiagnoseLpbkCond OBJECT-TYPE
    SYNTAX     CmDiagLpbkCondType
    MAX-ACCESS read-only
    STATUS     current
    DESCRIPTION
            "This object provides port loopback results of the diagnosis
             test on Ethernet Traffic Port."
     ::= { cmEthernetTrafficPortEntry 100 }

cmEthernetTrafficPortDiagnoseEfmLpbkCond OBJECT-TYPE
    SYNTAX     CmDiagEfmOamLpbkCondType
    MAX-ACCESS read-only
    STATUS     current
    DESCRIPTION
            "This object provides remote EFM loopback results of the diagnosis
             test on Ethernet Traffic Port."
     ::= { cmEthernetTrafficPortEntry 101 }

cmEthernetTrafficPortDiagnoseResult OBJECT-TYPE
    SYNTAX  DisplayString (SIZE (0..256)) 
    MAX-ACCESS read-only
    STATUS     current
    DESCRIPTION
            "This object provides results of the diagnosis
             test in string form on Ethernet Traffic Port."
     ::= { cmEthernetTrafficPortEntry 102 }

cmEthernetTrafficPortDiagnoseTestStatus OBJECT-TYPE
    SYNTAX  CmDiagTestStatus 
    MAX-ACCESS read-only
    STATUS     current
    DESCRIPTION
            "This object provides the current status of the diagnosis
             test on Ethernet Traffic Port."
     ::= { cmEthernetTrafficPortEntry 103 }

cmEthernetTrafficPortDiagnoseTestTime OBJECT-TYPE
    SYNTAX  DateAndTime 
    MAX-ACCESS read-only
    STATUS     current
    DESCRIPTION
       "This object provides the time when diagnosis test was last executed."
     ::= { cmEthernetTrafficPortEntry 104 }

cmEthernetTrafficPortAutoDiagEnabled OBJECT-TYPE
    SYNTAX     TruthValue
    MAX-ACCESS read-write
    STATUS     current
    DESCRIPTION
         "This object allows to enable or disable the automatic 
          Cable Diagnostic tests when the cable is removed from the port."
     ::= { cmEthernetTrafficPortEntry 105 }

cmEthernetTrafficPortDeleteEntitiesAction OBJECT-TYPE
    SYNTAX     TrafficPortDeleteEntitiesAction
    MAX-ACCESS read-write
    STATUS     current
    DESCRIPTION
         "This object allows to delete esa entities relate this port and 
         Cfm entities relate this port."
     ::= { cmEthernetTrafficPortEntry 106 }

cmEthernetTrafficPortMaxMpFpNum OBJECT-TYPE
    SYNTAX     Integer32
    MAX-ACCESS read-write
    STATUS     current
    DESCRIPTION
         "This object allows to set the mpflow max fp number, and now only the ports on ethernet10x1GCard,
	 ethernet1x10GCard, ethernet1x10GHighPerCard, ethernet10x1GHighPerCard support this attribute. for
	 others, cann't be set and will return 0."
     ::= { cmEthernetTrafficPortEntry 107 }

cmEthernetTrafficPortJdsuLoopbackEnabled OBJECT-TYPE
    SYNTAX     TruthValue
    MAX-ACCESS read-write
    STATUS     deprecated
    DESCRIPTION
         "This object allows to enable or disable jdsu loopback on this port.

         Note: This object is deprecated."
     ::= { cmEthernetTrafficPortEntry 108 }

cmEthernetTrafficPortJdsuLoopbackVlanId OBJECT-TYPE
    SYNTAX     VlanId
    MAX-ACCESS read-only
    STATUS     deprecated
    DESCRIPTION
         "This object allows to set the jdsu loopback vlan.
         if status is jdsu-terminal-port-tailend(19) or jdsu-facility-port-tailend(21), 
         then VID is 0 means not applicable.

         Note: This object is deprecated."
     ::= { cmEthernetTrafficPortEntry 109 }

cmEthernetTrafficPortIngressPopPriorityVidEnabled OBJECT-TYPE 
    SYNTAX     TruthValue
    MAX-ACCESS read-write
    STATUS     current
    DESCRIPTION
         "This object defines the Ingress PopPriorityVid enable or disable of the port.
          If it is enabled, then incoming priority tagged 
          packet's VID is swapped to Priority VLAN ID."
     ::= { cmEthernetTrafficPortEntry 110 }

cmEthernetTrafficPortRxDeiAction OBJECT-TYPE 
    SYNTAX     RxDeiAction
    MAX-ACCESS read-write
    STATUS     current
    DESCRIPTION
             "This object allows to specify
              the Receive DEI Action."
     ::= { cmEthernetTrafficPortEntry 111 }

cmEthernetTrafficPortTxDeiAction OBJECT-TYPE 
    SYNTAX     TxDeiAction
    MAX-ACCESS read-write
    STATUS     current
    DESCRIPTION
             "This object allows to specify
              the Transmit DEI Action."
     ::= { cmEthernetTrafficPortEntry 112 }

cmEthernetTrafficPortRxDeiOuterTagType OBJECT-TYPE 
    SYNTAX     DeiOuterTagType
    MAX-ACCESS read-write
    STATUS     current
    DESCRIPTION
             "This object allows to specify
              the Receive DEI Outer Tag Type."
     ::= { cmEthernetTrafficPortEntry 113 }

cmEthernetTrafficPortTxDeiOuterTagType OBJECT-TYPE 
    SYNTAX     DeiOuterTagType
    MAX-ACCESS read-write
    STATUS     current
    DESCRIPTION
             "This object allows to specify
              the Transmit DEI Outer Tag Type."
     ::= { cmEthernetTrafficPortEntry 114 }
--
--  Agg Flow Table
--
cmElineFlowTable  OBJECT-TYPE
    SYNTAX      SEQUENCE OF CmElineFlowEntry
    MAX-ACCESS  not-accessible
    STATUS      current
    DESCRIPTION
            "A list of entries corresponding to Flows 
             for configuration purposes."
    ::= { cmFacilityObjects 28 }

cmElineFlowEntry OBJECT-TYPE
    SYNTAX      CmElineFlowEntry 
    MAX-ACCESS  not-accessible
    STATUS      current
    DESCRIPTION
            "A conceptual row in the cmElineFlowTable. These entries represent
             an Flow."
    INDEX { neIndex, cmElineFlowIndex }
    ::= { cmElineFlowTable 1 }

CmElineFlowEntry ::= SEQUENCE {
    -- Flow Index/Id
    cmElineFlowIndex                           Integer32,
    cmElineFlowCircuitName                     DisplayString,

    -- State Management params
    cmElineFlowAdminState                      AdminState,
    cmElineFlowOperationalState                OperationalState,
    cmElineFlowSecondaryState                  SecondaryState,
    
    -- flow attributes
    cmElineFlowFP1                             VariablePointer,
    cmElineFlowFP2                             VariablePointer,
  
    --SNMP row creation 
    cmElineFlowStorageType                     StorageType,
    cmElineFlowRowStatus                       RowStatus
}

cmElineFlowIndex OBJECT-TYPE
    SYNTAX      Integer32 (1..65535)
    MAX-ACCESS  read-create
    STATUS      current
    DESCRIPTION
            "The integer index value corresponding to an Flow." 
    ::= { cmElineFlowEntry 1 }

cmElineFlowCircuitName    OBJECT-TYPE
    SYNTAX      DisplayString (SIZE(0..256))
    MAX-ACCESS  read-create
    STATUS      current
    DESCRIPTION
         "This object allows SNMP management entities to provide a
          circuit identifier with the Flow."
     ::= { cmElineFlowEntry 2 }

-- State Management params
cmElineFlowAdminState OBJECT-TYPE
    SYNTAX      AdminState 
    MAX-ACCESS  read-write
    STATUS      current
    DESCRIPTION
            "This object represents the Administrative State of the Flow." 
    ::= { cmElineFlowEntry 3 }

cmElineFlowOperationalState OBJECT-TYPE
    SYNTAX      OperationalState 
    MAX-ACCESS  read-only
    STATUS      current
    DESCRIPTION
            "This object represents the Operational State of the Flow." 
    ::= { cmElineFlowEntry 4 }

cmElineFlowSecondaryState OBJECT-TYPE
    SYNTAX      SecondaryState 
    MAX-ACCESS  read-only
    STATUS      current
    DESCRIPTION
            "This object represents the Secondary State of the Flow." 
    ::= { cmElineFlowEntry 5 }

cmElineFlowFP1    OBJECT-TYPE
    SYNTAX      VariablePointer
    MAX-ACCESS  read-create
    STATUS      current
    DESCRIPTION
         "This object allows SNMP management entities to provide a
          flowpoint with the Flow."
     ::= { cmElineFlowEntry 6 }

cmElineFlowFP2    OBJECT-TYPE
    SYNTAX      VariablePointer
    MAX-ACCESS  read-create
    STATUS      current
    DESCRIPTION
         "This object allows SNMP management entities to provide another
          flowpoint with the Flow."
     ::= { cmElineFlowEntry 7 }

cmElineFlowStorageType OBJECT-TYPE
    SYNTAX     StorageType
    MAX-ACCESS read-create
    STATUS     current
    DESCRIPTION
            "The type of storage configured for this entry."
    ::= { cmElineFlowEntry 8 }

cmElineFlowRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmElineFlowRowStatus supported are
            createAndGo(4) and destroy(6).  All mandatory attributes
            must be specified in a single SNMP SET request with
            cmElineFlowRowStatus value as createAndGo(4).
            Upon successful row creation, this object has a
            value of active(1).

            The cmElineFlowRowStatus object may be modified if
            the associated instance of this object is equal to active(1)."
    ::= { cmElineFlowEntry 9 }

--
--  Agg FlowPoint
--
cmFlowPointTable  OBJECT-TYPE
    SYNTAX      SEQUENCE OF CmFlowPointEntry
    MAX-ACCESS  not-accessible
    STATUS      current
    DESCRIPTION
            "A list of entries corresponding to FlowPoint
             for configuration purposes."
    ::= { cmFacilityObjects 29 }

cmFlowPointEntry OBJECT-TYPE
    SYNTAX      CmFlowPointEntry 
    MAX-ACCESS  not-accessible
    STATUS      current
    DESCRIPTION
            "A conceptual row in the cmFlowPointTable. These entries represent
             an FlowPoint.
             If the flowpoint attached to a lag, the slotIndex should 
             be 255(255 is used to identify the flowpoint belongs to lag), 
             and the cmEthernetTrafficPortIndex should be the f3LagIndex."
    INDEX { neIndex, shelfIndex, slotIndex, cmEthernetTrafficPortIndex, cmFlowPointIndex }
    ::= { cmFlowPointTable 1 }

CmFlowPointEntry ::= SEQUENCE {
    -- FlowPoint Index/Id
    cmFlowPointIndex                           Integer32,
    cmFlowPointCircuitName                     DisplayString,

    -- State Management params
    cmFlowPointAdminState                      AdminState,
    cmFlowPointOperationalState                OperationalState,
    cmFlowPointSecondaryState                  SecondaryState,
    
    cmFlowPointAssociatedFlowId                VariablePointer,

    cmFlowPointIngressMultiCOS                 TruthValue,
    cmFlowPointIngressCOS	                     Integer32,
    --flowpoint membership
    cmFlowPointIngressVlanMemberList           DisplayString, 
    cmFlowPointVlanMemberAction                FlowVlanActionType, 
    cmFlowPointVlanMemberActionVlan            DisplayString, 
    cmFlowPointIngressUntaggedFrameEnabled     TruthValue,

    --flowpoint tag management
    cmFlowPointCTagControl                     FlowTagControl,
    cmFlowPointCTagVlanId                      VlanId,
    cmFlowPointCTagVlanPriority                VlanPriority,

    cmFlowPointSTagControl                     FlowTagControl,
    cmFlowPointSTagVlanId                      VlanId,
    cmFlowPointSTagVlanPriority                VlanPriority,
        
    cmFlowPointEgressOuterTagPrioMapEnabled    TruthValue,
    cmFlowPointColorMarkingSupported           TruthValue,
    cmFlowPointAssociatedAclProfile            VariablePointer,
    cmFlowPointSESFramesLossThresholdRatio     Integer32,
    cmFlowPointStorageType                     StorageType,
    cmFlowPointRowStatus                       RowStatus,
    cmFlowPointDefaultMemberEnabled            TruthValue,
    cmFlowPointMcastRateLimitEnabled           TruthValue,
    cmFlowPointMcastRateLimitSpeedLo           Unsigned32,
    cmFlowPointMcastRateLimitSpeedHi           Unsigned32,
    cmFlowPointBcastRateLimitEnabled           TruthValue,
    cmFlowPointBcastRateLimitSpeedLo           Unsigned32,
    cmFlowPointBcastRateLimitSpeedHi           Unsigned32,
    cmFlowPointSplitHorizonGroupOID            VariablePointer,
    cmFlowPointLoopAvoidance                   VariablePointer,
    cmFlowPointHierarchicalCosEnabled          TruthValue,
    cmFlowPointWfqQid                          Integer32,
    cmFlowPointWfqOutPriority                  Integer32,
    cmFlowPointMaximumBWLo                     Unsigned32,
    cmFlowPointMaximumBWHi                     Unsigned32,
    cmFlowPointGuaranteedBWLo                  Unsigned32,
    cmFlowPointGuaranteedBWHi                  Unsigned32
}

cmFlowPointIndex OBJECT-TYPE
    SYNTAX      Integer32 (1..65535)
    MAX-ACCESS  read-create
    STATUS      current
    DESCRIPTION
            "The integer index value corresponding to an FlowPoint." 
    ::= { cmFlowPointEntry 1 }

cmFlowPointCircuitName    OBJECT-TYPE
    SYNTAX      DisplayString (SIZE(0..256))
    MAX-ACCESS  read-create
    STATUS      current
    DESCRIPTION
         "This object allows SNMP management entities to provide a
          circuit identifier with the FlowPoint."
     ::= { cmFlowPointEntry 2 }

-- State Management params
cmFlowPointAdminState OBJECT-TYPE
    SYNTAX      AdminState 
    MAX-ACCESS  read-write
    STATUS      current
    DESCRIPTION
            "This object represents the Administrative State of the FlowPoint." 
    ::= { cmFlowPointEntry 3 }

cmFlowPointOperationalState OBJECT-TYPE
    SYNTAX      OperationalState 
    MAX-ACCESS  read-only
    STATUS      current
    DESCRIPTION
            "This object represents the Operational State of the FlowPoint." 
    ::= { cmFlowPointEntry 4 }

cmFlowPointSecondaryState OBJECT-TYPE
    SYNTAX      SecondaryState 
    MAX-ACCESS  read-only
    STATUS      current
    DESCRIPTION
            "This object represents the Secondary State of the FlowPoint." 
    ::= { cmFlowPointEntry 5 }

cmFlowPointAssociatedFlowId OBJECT-TYPE
    SYNTAX      VariablePointer
    MAX-ACCESS  read-only
    STATUS      current
    DESCRIPTION
            "This object provides the association of an Flow with an FlowPoint." 
    ::= { cmFlowPointEntry 6 }

cmFlowPointIngressMultiCOS OBJECT-TYPE
    SYNTAX     TruthValue
    MAX-ACCESS read-create
    STATUS     current
    DESCRIPTION
         "This object allows specification of ingress multiple COS (Class of Service) FlowPoint." 
     ::= { cmFlowPointEntry 7 }

cmFlowPointIngressCOS OBJECT-TYPE
    SYNTAX     Integer32
    MAX-ACCESS read-create
    STATUS     current
    DESCRIPTION
         "This object allows specification of ingress COS (Class of Service) FlowPoint." 
     ::= { cmFlowPointEntry 8 }
     
cmFlowPointIngressVlanMemberList OBJECT-TYPE
    SYNTAX     DisplayString (SIZE (0..512))
    MAX-ACCESS read-create
    STATUS     current
    DESCRIPTION
         "It allows specification of VLAN members of the FlowPoint.
          VLAN members are comma separated, of the form X-Y where X is the
          VLAN Id and Y is the VLAN Priority.  VLAN members can be of
          the form X-* or X (vlan X with all priorities), 
          *-Y (all vlans with priority Y), and X1:X2 
          (range of vlans from X1 to X2, all priorities). Members 
          with specific VLAN Id and specific VLAN Priority are not supported.
          Once the flowpoint is created, this attribute can only be updated
          using cmFlowPointVlanMemberAction and cmFlowPointVlanMemberActionVlan objects."
     ::= { cmFlowPointEntry 9 }

cmFlowPointVlanMemberAction OBJECT-TYPE
    SYNTAX     FlowVlanActionType 
    MAX-ACCESS read-write
    STATUS     current
    DESCRIPTION
         "This object allows to add or remove the VLAN members specified by
          cmFlowPointVlanMemberActionVlan object.  SNMP manager must first
          configure the VLAN member to be added/removed in the object
          cmFlowPointVlanMemberActionVlan and then should specify
          cmFlowPointVlanMemberAction on whether to add/remove the specified
          VLAN member."
     ::= { cmFlowPointEntry 10 }

cmFlowPointVlanMemberActionVlan OBJECT-TYPE
    SYNTAX     DisplayString (SIZE (0..16))
    MAX-ACCESS read-create
    STATUS     current
    DESCRIPTION
         "This object allows adding/removing VLAN members
          to a flowpoint.
          VLAN member is of the form X-Y where X is the
          VLAN Id and Y is the VLAN Priority.  VLAN members can be of
          the form X-* (vlan X with all priorities), 
          *-Y (all vlans with priority Y), and X1:X2 
          (range of vlans from X1 to X2, all priorities).  
          Members with specific VLAN Id and 
          specific VLAN Priority are not supported.
          In order to add/remove VLAN member to a flow, user must
          specify this object with appropriate VLAN and then invoke
          cmFlowPointVlanMemberAction."
     ::= { cmFlowPointEntry 11 }
     
cmFlowPointIngressUntaggedFrameEnabled OBJECT-TYPE
    SYNTAX     TruthValue 
    MAX-ACCESS read-create
    STATUS     current
    DESCRIPTION
         "This object allows to specify whether or not the flowpoint
          supports untagged frame."
     ::= { cmFlowPointEntry 12 }

--flowpoint tag management
cmFlowPointCTagControl  OBJECT-TYPE
    SYNTAX     FlowTagControl
    MAX-ACCESS read-create
    STATUS     current
    DESCRIPTION
         "This object allows specification of the tag management 
          operation on the C-TAG.  Supported types are 'push', 'pushvid',
          'swaptag', 'swapvid' and 'none'. If the type is 'push', 
          the VLAN Id (cmFlowPointCTagVlanId) and priority
          (cmFlowPointCTagVlanPriority) are pushed onto the frame;
          if the type is 'pushvid', only the VLAN Id (12 bits) is pushed,
          the Priority is copied from incoming tag's priority;
          if the type is 'swaptag', both VLAN Id and Priority (15 bits) 
          are swapped with the specified cmFlowPointCTagVlanId and 
          cmFlowPointCTagVlanPriority;
          if the type is 'swapvid', only the VLAN Id (12 bits) are 
          swapped with the specified cmFlowPointCTagVlanId; 
          if the type is 'none', no C-TAG management is performed."
     ::= { cmFlowPointEntry 13 }

cmFlowPointCTagVlanId  OBJECT-TYPE
    SYNTAX     VlanId
    MAX-ACCESS read-create
    STATUS     current
    DESCRIPTION
         "This object allows specification of the VLAN Id to
          be pushed or swapped, based on the value of cmFlowPointIngressCTagControl.
          It is applicable for 'push', 'swaptag', 'swapvid' and 'pushvid'
          control types."
     ::= { cmFlowPointEntry 14 }

cmFlowPointCTagVlanPriority  OBJECT-TYPE
    SYNTAX     VlanPriority
    MAX-ACCESS read-create
    STATUS     current
    DESCRIPTION
         "This object allows specification of the VLAN Priority to
          be pushed or swapped, based on the value of cmFlowPointIngressCTagControl.
          It is applicable for 'push' and 'swaptag' control types."
     ::= { cmFlowPointEntry 15 }

cmFlowPointSTagControl  OBJECT-TYPE
    SYNTAX     FlowTagControl
    MAX-ACCESS read-create
    STATUS     current
    DESCRIPTION
         "This object allows specification of the tag management 
          operation on the S-TAG.  Supported types are 'push', 'pushvid',
          'swaptag', 'swapvid' and 'none'. If the type is 'push', 
          the VLAN Id (cmFlowPointSTagVlanId) and priority
          (cmFlowPointSTagVlanPriority) are pushed onto the frame;
          if the type is 'pushvid', only the VLAN Id (12 bits) is pushed,
          the Priority is copied from incoming tag's priority;
          if the type is 'swaptag', both VLAN Id and Priority (15 bits) 
          are swapped with the specified cmFlowPointSTagVlanId and 
          cmFlowPointSTagVlanPriority;
          if the type is 'swapvid', only the VLAN Id (12 bits) are 
          swapped with the specified cmFlowPointSTagVlanId; 
          if the type is 'none', no S-TAG management is performed."
     ::= { cmFlowPointEntry 16 }

cmFlowPointSTagVlanId  OBJECT-TYPE
    SYNTAX     VlanId
    MAX-ACCESS read-create
    STATUS     current
    DESCRIPTION
         "This object allows specification of the VLAN Id to
          be pushed or swapped, based on the value of cmFlowPointIngressSTagControl.
          It is applicable for 'push', 'swaptag', 'swapvid' and 'pushvid'
          control types."
     ::= { cmFlowPointEntry 17 }

cmFlowPointSTagVlanPriority  OBJECT-TYPE
    SYNTAX     VlanPriority
    MAX-ACCESS read-create
    STATUS     current
    DESCRIPTION
         "This object allows specification of the VLAN Priority to
          be pushed or swapped, based on the value of cmFlowPointIngressSTagControl.
          It is applicable for 'push' and 'swaptag' control types."
     ::= { cmFlowPointEntry 18 }

cmFlowPointEgressOuterTagPrioMapEnabled  OBJECT-TYPE
    SYNTAX     TruthValue
    MAX-ACCESS read-create
    STATUS     current
    DESCRIPTION
         "This object defines whether to use the Egress Prio Mapping to swap the priority of outer tag.
         When Enabled,it indicates that the operation specified in the EgressPrioMapTable would be 
         applied to Flow for specified COS.
         When Disabled,the EgressPrioMapTable operations are ignored for specified Flow COS."
     ::= { cmFlowPointEntry 19 }

cmFlowPointColorMarkingSupported  OBJECT-TYPE
    SYNTAX     TruthValue
    MAX-ACCESS read-create
    STATUS     current
    DESCRIPTION
         "This object defines the egress color marking. If set to Enabled, the DEI bit of S-tag pushed 
          will be remarked according the meter result. If set to Disabled, the DEI bit is forced to 0."
     ::= { cmFlowPointEntry 20 }

cmFlowPointAssociatedAclProfile OBJECT-TYPE
    SYNTAX      VariablePointer
    MAX-ACCESS  read-create
    STATUS      current
    DESCRIPTION
            "This object provides the association of an Flow with an ACL profile." 
    ::= { cmFlowPointEntry 21 }

cmFlowPointSESFramesLossThresholdRatio OBJECT-TYPE 
    SYNTAX     Integer32 (0..100)
    MAX-ACCESS read-write
    STATUS     current
    DESCRIPTION
         "This object is used to specify the frame-loss ratio 
          per flow that starts counting Severely Errored Seconds (SES) 
          on the flowpoint.
          This functionality is applicable if the flowpoint is monitored
          using the Y.1731 ESA functionality." 
     ::= { cmFlowPointEntry 22 }

cmFlowPointStorageType OBJECT-TYPE
    SYNTAX     StorageType
    MAX-ACCESS read-create
    STATUS     current
    DESCRIPTION
            "The type of storage configured for this entry."
    ::= { cmFlowPointEntry 23 }

cmFlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmFlowPointRowStatus supported are
            createAndGo(4) and destroy(6).  All mandatory attributes
            must be specified in a single SNMP SET request with
            cmFlowPointRowStatus value as createAndGo(4).
            Upon successful row creation, this object has a
            value of active(1).

            The cmFlowPointRowStatus object may be modified if
            the associated instance of this object is equal to active(1)."
    ::= { cmFlowPointEntry 24 }
    
cmFlowPointDefaultMemberEnabled OBJECT-TYPE
    SYNTAX      TruthValue
    MAX-ACCESS  read-write
    STATUS      current
    DESCRIPTION
            "defaultMemberEnabled with enabled means that on this FP, 
            the membership is all the tag packets without match any 
            other membership associated to the port. Untagged means 
            untagged flow. Default only care tagged flow." 
    ::= { cmFlowPointEntry 25 }

cmFlowPointMcastRateLimitEnabled OBJECT-TYPE
    SYNTAX      TruthValue
    MAX-ACCESS  read-write
    STATUS      current
    DESCRIPTION
            "Whether multicast packets need be limited per FP." 
    ::= { cmFlowPointEntry 26 }

cmFlowPointMcastRateLimitSpeedLo OBJECT-TYPE
    SYNTAX      Unsigned32
    MAX-ACCESS  read-write
    STATUS      current
    DESCRIPTION
            "The rate limiting for multicast packets per FP
             When cmFlowPointMcastRateLimitEnabled and the value is 0, 
             it means all multicast frame are dropped.

             This objects only represents low 32 bits." 
    ::= { cmFlowPointEntry 27 }

cmFlowPointMcastRateLimitSpeedHi OBJECT-TYPE
    SYNTAX      Unsigned32
    MAX-ACCESS  read-write
    STATUS      current
    DESCRIPTION
            "The rate limiting for multicast packets per FP
             When cmFlowPointMcastRateLimitEnabled and the value is 0, 
             it means all multicast frame are dropped.

             This objects only represents high 32 bits." 
    ::= { cmFlowPointEntry 28 }

cmFlowPointBcastRateLimitEnabled OBJECT-TYPE
    SYNTAX      TruthValue
    MAX-ACCESS  read-write
    STATUS      current
    DESCRIPTION
            "Whether broadcast packets need be limited per FP." 
    ::= { cmFlowPointEntry 29 }

cmFlowPointBcastRateLimitSpeedLo OBJECT-TYPE
    SYNTAX      Unsigned32
    MAX-ACCESS  read-write
    STATUS      current
    DESCRIPTION
            "The rate limiting for broadcast packets per FP
             When cmFlowPointBcastRateLimitEnabled and the value is 0, 
             it means all multicast frame are dropped.

             This objects only represents low 32 bits." 
    ::= { cmFlowPointEntry 30 }

cmFlowPointBcastRateLimitSpeedHi OBJECT-TYPE
    SYNTAX      Unsigned32
    MAX-ACCESS  read-write
    STATUS      current
    DESCRIPTION
            "The rate limiting for broadcast packets per FP
             When cmFlowPointBcastRateLimitEnabled and the value is 0, 
             it means all multicast frame are dropped.

             This objects only represents high 32 bits." 
    ::= { cmFlowPointEntry 31 }

cmFlowPointSplitHorizonGroupOID OBJECT-TYPE
    SYNTAX      VariablePointer
    MAX-ACCESS  read-write
    STATUS      current
    DESCRIPTION
            "Specifies the Split-Horizon Group EID. If there is no SHG, the value is none." 
    ::= { cmFlowPointEntry 32 }

cmFlowPointLoopAvoidance OBJECT-TYPE
    SYNTAX      VariablePointer
    MAX-ACCESS  read-write
    STATUS      current
    DESCRIPTION
            "EID of this associated Loop Avoidance protocol entity.
             A value of NONE indicates there is no loop avoidance protocol.
             Currently ERP EID is filled when ELAN service is created." 
    ::= { cmFlowPointEntry 33 }

cmFlowPointHierarchicalCosEnabled OBJECT-TYPE
    SYNTAX      TruthValue
    MAX-ACCESS  read-write
    STATUS      current
    DESCRIPTION
            "Enable or Disable Hierarchical COS shaping (flow shaping)." 
    ::= { cmFlowPointEntry 34 }

cmFlowPointWfqQid  OBJECT-TYPE
    SYNTAX      Integer32 (0..7)
    MAX-ACCESS  read-write
    STATUS      current
    DESCRIPTION
            "This attribute description the WFQ Qid." 
    ::= { cmFlowPointEntry 35 }

cmFlowPointWfqOutPriority  OBJECT-TYPE
    SYNTAX      Integer32 (0..7)
    MAX-ACCESS  read-write
    STATUS      current
    DESCRIPTION
            "This attribute description the WFQ out priority." 
    ::= { cmFlowPointEntry 36 }

cmFlowPointMaximumBWLo  OBJECT-TYPE
    SYNTAX      Unsigned32
    MAX-ACCESS  read-write
    STATUS      current
    DESCRIPTION
            "This attribute description the flow point maximum bandwidth.

             This objects only represents low 32 bits." 
    ::= { cmFlowPointEntry 37 }

cmFlowPointMaximumBWHi  OBJECT-TYPE
    SYNTAX      Unsigned32
    MAX-ACCESS  read-write
    STATUS      current
    DESCRIPTION
            "This attribute description the flow point maximum bandwidth.

             This objects only represents high 32 bits." 
    ::= { cmFlowPointEntry 38 }

cmFlowPointGuaranteedBWLo  OBJECT-TYPE
    SYNTAX      Unsigned32
    MAX-ACCESS  read-write
    STATUS      current
    DESCRIPTION
            "This attribute description the flow point guaranteed bandwidth.

             This objects only represents low 32 bits." 
    ::= { cmFlowPointEntry 39 }

cmFlowPointGuaranteedBWHi  OBJECT-TYPE
    SYNTAX      Unsigned32
    MAX-ACCESS  read-write
    STATUS      current
    DESCRIPTION
            "This attribute description the flow point guaranteed bandwidth.

             This objects only represents high 32 bits." 
    ::= { cmFlowPointEntry 40 }

--
--  Agg OAM FlowPoint
--
cmOAMFlowPointTable  OBJECT-TYPE
    SYNTAX      SEQUENCE OF CmOAMFlowPointEntry
    MAX-ACCESS  not-accessible
    STATUS      current
    DESCRIPTION
            "A list of entries corresponding to OAMFlowPoint
             for configuration purposes."
    ::= { cmFacilityObjects 30 }

cmOAMFlowPointEntry OBJECT-TYPE
    SYNTAX      CmOAMFlowPointEntry 
    MAX-ACCESS  not-accessible
    STATUS      current
    DESCRIPTION
            "A conceptual row in the cmOAMFlowPointTable. These entries represent
             an FlowPoint.
             If the oam flowpoint attached to a lag, the slotIndex should 
             be 255(255 is used to identify the oam flowpoint belongs to lag), 
             and the cmEthernetTrafficPortIndex should be the f3LagIndex."
    INDEX { neIndex, shelfIndex, slotIndex, cmEthernetTrafficPortIndex, cmOAMFlowPointIndex }
    ::= { cmOAMFlowPointTable 1 }
                    
--OAM FlowPoint 

CmOAMFlowPointEntry ::= SEQUENCE {
    -- FlowPoint Index/Id
    cmOAMFlowPointIndex                           Integer32,
    cmOAMFlowPointCircuitName                     DisplayString,

    -- State Management params
    cmOAMFlowPointAdminState                      AdminState,
    cmOAMFlowPointOperationalState                OperationalState,
    cmOAMFlowPointSecondaryState                  SecondaryState,
    
    --OAM flowpoint membership
    cmOAMFlowPointIngressVlanMemberList           DisplayString, 
    cmOAMFlowPointVlanMemberAction                FlowVlanActionType, 
    cmOAMFlowPointVlanMemberActionVlan            DisplayString, 
    cmOAMFlowPointIngressUntaggedFrameSupported   TruthValue,
    cmOAMFlowPointSESFramesLossThresholdRatio     Integer32,
    cmOAMFlowPointStorageType                     StorageType,
    cmOAMFlowPointRowStatus                       RowStatus
}

cmOAMFlowPointIndex OBJECT-TYPE
    SYNTAX      Integer32 (1..65535)
    MAX-ACCESS  read-create
    STATUS      current
    DESCRIPTION
            "The integer index value corresponding to an OAMFlowPoint." 
    ::= { cmOAMFlowPointEntry 1 }

cmOAMFlowPointCircuitName    OBJECT-TYPE
    SYNTAX      DisplayString (SIZE(0..64))
    MAX-ACCESS  read-create
    STATUS      current
    DESCRIPTION
         "This object allows SNMP management entities to provide a
          circuit identifier with the OAMFlowPoint."
     ::= { cmOAMFlowPointEntry 2 }

-- State Management params
cmOAMFlowPointAdminState OBJECT-TYPE
    SYNTAX      AdminState 
    MAX-ACCESS  read-write
    STATUS      current
    DESCRIPTION
            "This object represents the Administrative State of the OAMFlowPoint." 
    ::= { cmOAMFlowPointEntry 3 }

cmOAMFlowPointOperationalState OBJECT-TYPE
    SYNTAX      OperationalState 
    MAX-ACCESS  read-only
    STATUS      current
    DESCRIPTION
            "This object represents the Operational State of the OAMFlowPoint." 
    ::= { cmOAMFlowPointEntry 4 }

cmOAMFlowPointSecondaryState OBJECT-TYPE
    SYNTAX      SecondaryState 
    MAX-ACCESS  read-only
    STATUS      current
    DESCRIPTION
            "This object represents the Secondary State of the OAMFlowPoint." 
    ::= { cmOAMFlowPointEntry 5 }

    
cmOAMFlowPointIngressVlanMemberList OBJECT-TYPE
    SYNTAX     DisplayString (SIZE (0..512))
    MAX-ACCESS read-create
    STATUS     current
    DESCRIPTION
         "It allows specification of VLAN members of the OAMFlowPoint.
          VLAN members are comma separated, of the form X-Y where X is the
          VLAN Id and Y is the VLAN Priority.  VLAN members can be of
          the form X-* or X (vlan X with all priorities), 
          *-Y (all vlans with priority Y), and X1:X2 (range of vlans from X1 to X2, all priorities). 
          Members with specific VLAN Id and specific VLAN Priority are not supported.
          Once the flowpoint is created, this attribute can only be updated
          using cmOAMFlowPointVlanMemberAction and cmOAMFlowPointVlanMemberActionVlan objects."
     ::= { cmOAMFlowPointEntry 6 }    
  
cmOAMFlowPointVlanMemberAction OBJECT-TYPE
    SYNTAX     FlowVlanActionType 
    MAX-ACCESS read-write
    STATUS     current
    DESCRIPTION
         "This object allows to add or remove the VLAN members specified by
          cmOAMFlowPointVlanMemberActionVlan object.  SNMP manager must first
          configure the VLAN member to be added/removed in the object
          cmOAMFlowPointVlanMemberActionVlan and then should specify
          cmOAMFlowPointVlanMemberAction on whether to add/remove the specified
          VLAN member."
     ::= { cmOAMFlowPointEntry 7 }

cmOAMFlowPointVlanMemberActionVlan OBJECT-TYPE
    SYNTAX     DisplayString (SIZE (0..16))
    MAX-ACCESS read-create
    STATUS     current
    DESCRIPTION
         "This object allows adding/removing VLAN members
         to a oam flowpoint.
 	       VLAN member is of the form X-Y where X is the
 	       VLAN Id and Y is the VLAN Priority.  VLAN members can be of
 	       the form X-* (vlan X with all priorities), 
 	       *-Y (all vlans with priority Y), and X1:X2 
 	       (range of vlans from X1 to X2, all priorities).  
 	       Members with specific VLAN Id and 
 	       specific VLAN Priority are not supported.
 	       In order to add/remove VLAN member to a flow, user must
 	       specify this object with appropriate VLAN and then invoke
 	       cmOAMFlowPointVlanMemberAction."
     ::= { cmOAMFlowPointEntry 8 }
     
cmOAMFlowPointIngressUntaggedFrameSupported OBJECT-TYPE
    SYNTAX     TruthValue 
    MAX-ACCESS read-create
    STATUS     current
    DESCRIPTION
         "This object allows to specify whether or not the OAMFlowPoint
          supports untagged frame."
     ::= { cmOAMFlowPointEntry 9 }

cmOAMFlowPointSESFramesLossThresholdRatio OBJECT-TYPE 
    SYNTAX     Integer32 (1..100)
    MAX-ACCESS read-write
    STATUS     current
    DESCRIPTION
         "This object is used to specify the frame-loss ratio 
          per flow that starts counting Severely Errored Seconds (SES) 
          on the oam flowpoint.
          This functionality is applicable if the oam flowpoint is monitored
          using the Y.1731 ESA functionality." 
     ::= { cmOAMFlowPointEntry 10 }
     
cmOAMFlowPointStorageType OBJECT-TYPE
    SYNTAX     StorageType
    MAX-ACCESS read-create
    STATUS     current
    DESCRIPTION
            "The type of storage configured for this entry."
    ::= { cmOAMFlowPointEntry 11 }

cmOAMFlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmOAMFlowPointRowStatus supported are
            createAndGo(4) and destroy(6).  All mandatory attributes
            must be specified in a single SNMP SET request with
            cmOAMFlowPointRowStatus value as createAndGo(4).
            Upon successful row creation, this object has a
            value of active(1).

            The cmOAMFlowPointRowStatus object may be modified if
            the associated instance of this object is equal to active(1)."
    ::= { cmOAMFlowPointEntry 12 }

--
--Agg Ingress Map Table
--
cmIngressPrioMapTable  OBJECT-TYPE
    SYNTAX      SEQUENCE OF CmIngressPrioMapEntry
    MAX-ACCESS  not-accessible
    STATUS      current
    DESCRIPTION
            "A list of entries corresponding to Ingress Priority Mapping 
             for configuration purposes."
    ::= { cmFacilityObjects 31 }

cmIngressPrioMapEntry OBJECT-TYPE
    SYNTAX      CmIngressPrioMapEntry 
    MAX-ACCESS  not-accessible
    STATUS      current
    DESCRIPTION
            "A conceptual row in the cmIngressPrioMapTable."
    INDEX { neIndex, shelfIndex, slotIndex, cmEthernetTrafficPortIndex, cmIngressPrioMapIndex }
    ::= { cmIngressPrioMapTable 1 }

CmIngressPrioMapEntry ::= SEQUENCE {
    -- Flow Index/Id
    cmIngressPrioMapIndex                        Integer32,
    cmIngressPrioMapInPriority                   Integer32,
    cmIngressPrioMapCOS                          Integer32
}

cmIngressPrioMapIndex OBJECT-TYPE
    SYNTAX      Integer32 (1..64)
    MAX-ACCESS  read-only
    STATUS      current
    DESCRIPTION
            "The integer index value corresponding to a priority value
             based on the cmEthernetTrafficPortPrioMapMode.
             In case of TOS and 8021P, valid indices are 1 to 8,
             in case of DSCP, valid indices are 1 to 64."
    ::= { cmIngressPrioMapEntry 1 }

cmIngressPrioMapInPriority OBJECT-TYPE
    SYNTAX      Integer32 (0..63)
    MAX-ACCESS  read-write
    STATUS      current
    DESCRIPTION
            "The integer index value corresponding to a priority value
             based on the cmEthernetTrafficPortIngressPrioMapMode.
             In case of TOS and 8021P, valid indices are 0 to 7,
             in case of DSCP, valid indices are 0 to 63."
    ::= { cmIngressPrioMapEntry 2 }
    
cmIngressPrioMapCOS OBJECT-TYPE
    SYNTAX      Integer32 (0..7)
    MAX-ACCESS  read-write
    STATUS      current
    DESCRIPTION
            "This allows specification of the COS Priority, i.e.
             this helps in determining the appropriate COS Policer for
             the Flow."
    ::= { cmIngressPrioMapEntry 3 }


--
--Agg Egress Map Table
--
cmEgressPrioMapTable  OBJECT-TYPE
    SYNTAX      SEQUENCE OF CmEgressPrioMapEntry
    MAX-ACCESS  not-accessible
    STATUS      current
    DESCRIPTION
            "A list of entries corresponding to Egress Priority Mapping 
             for configuration purposes."
    ::= { cmFacilityObjects 32 }

cmEgressPrioMapEntry OBJECT-TYPE
    SYNTAX      CmEgressPrioMapEntry 
    MAX-ACCESS  not-accessible
    STATUS      current
    DESCRIPTION
            "A conceptual row in the cmEgressPrioMapTable."
    INDEX { neIndex, shelfIndex, slotIndex, cmEthernetTrafficPortIndex, cmEgressCOSIndex  }
    ::= { cmEgressPrioMapTable 1 }

CmEgressPrioMapEntry ::= SEQUENCE {
    -- Flow Index/Id
    cmEgressCOSIndex                     Integer32,
    cmEgressCOS                          Integer32,
    cmEgressOuterTagCtrl                 PrioMapControlType,
    cmEgressOuterTagPriority             VlanPriority
}

cmEgressCOSIndex OBJECT-TYPE
    SYNTAX      Integer32 (1..8)
    MAX-ACCESS  read-only
    STATUS      current
    DESCRIPTION
            "The integer index used to uniquely identify
 	           this Egress Priority Map Entry "
    ::= { cmEgressPrioMapEntry 1 }

cmEgressCOS OBJECT-TYPE
    SYNTAX      Integer32 (0..7)
    MAX-ACCESS  read-write
    STATUS      current
    DESCRIPTION
            "This allows specification of the COS Priority, i.e.
             this helps in determining the appropriate COS Policer for
             the Flow."
    ::= { cmEgressPrioMapEntry 2 }

cmEgressOuterTagCtrl OBJECT-TYPE
    SYNTAX      PrioMapControlType
    MAX-ACCESS  read-write
    STATUS      current
    DESCRIPTION
            "This object defines the behavior of the Priority portion of the frame transmit out. 
             If NONE is selected, the outgoing priority bits are left unchanged. 
             If SWAP is selected, the priority bits are changed by the value specified 
             in the Outer-Tag Priority parameter."
    ::= { cmEgressPrioMapEntry 3 }

cmEgressOuterTagPriority OBJECT-TYPE
    SYNTAX      VlanPriority
    MAX-ACCESS  read-write
    STATUS      current
    DESCRIPTION
            "This object defines the new priority bits to be used, 
             it is available only if Outer-Tag PRIOCTL is set to SWAP."
    ::= { cmEgressPrioMapEntry 4 }
    
--
--  Port Control Protocol Disposition V3 profile Table
--
cmPortCpdProfileTable  OBJECT-TYPE
    SYNTAX      SEQUENCE OF CmPortCpdProfileEntry
    MAX-ACCESS  not-accessible
    STATUS      current
    DESCRIPTION
            "A list of entries corresponding to System 
             Control Protocol Disposition V3 profile."
    ::= { cmFacilityObjects 33 }

cmPortCpdProfileEntry OBJECT-TYPE
    SYNTAX      CmPortCpdProfileEntry 
    MAX-ACCESS  not-accessible
    STATUS      current
    DESCRIPTION
            "A conceptual row in the cmPortCpdProfileTable. 
             These entries represent a Control Protocol Disposition 
             of a port filtering criteria of the System."
    INDEX { cmPortCpdProfileIndex }
    ::= { cmPortCpdProfileTable 1 }


CmPortCpdProfileEntry ::= SEQUENCE {
    -- Index
    cmPortCpdProfileIndex                 Integer32,
    cmPortCpdProfileName                  DisplayString,
    -- Filtering Criteria
    cmPortCpdProfileCiscoGroupDispType    CmControlProtocolDispType,
    cmPortCpdProfileIslDispType           CmControlProtocolDispType,
    cmPortCpdProfilePagpDispType          CmControlProtocolDispType,
    cmPortCpdProfileUdldDispType          CmControlProtocolDispType,
    cmPortCpdProfileCdpDispType           CmControlProtocolDispType,
    cmPortCpdProfileVtpDispType           CmControlProtocolDispType,
    cmPortCpdProfileDtpDispType           CmControlProtocolDispType,
    cmPortCpdProfilePvstpPlusDispType     CmControlProtocolDispType,
    cmPortCpdProfileUplinkFastDispType    CmControlProtocolDispType,
    cmPortCpdProfileVlanBridgeDispType    CmControlProtocolDispType,
    cmPortCpdProfileL2PTDispType          CmControlProtocolDispType,
    cmPortCpdProfileBridgeGroupDispType   CmControlProtocolDispType,
    cmPortCpdProfileBPDUDispType          CmControlProtocolDispType,
    cmPortCpdProfilePauseDispType         CmControlProtocolDispType,
    cmPortCpdProfileLACPDispType          CmControlProtocolDispType,
    cmPortCpdProfileLACPMarkerDispType    CmControlProtocolDispType,
    cmPortCpdProfileEfmOamDispType        CmControlProtocolDispType,
    cmPortCpdProfileSSMDispType           CmControlProtocolDispType,
    cmPortCpdProfilePortAuthenDispType    CmControlProtocolDispType,
    cmPortCpdProfileBridgeReservedDispType    CmControlProtocolDispType,
    cmPortCpdProfileLANBridgesDispType    CmControlProtocolDispType,
    cmPortCpdProfileGARPGroupDispType     CmControlProtocolDispType,
    cmPortCpdProfileGMRPDispType          CmControlProtocolDispType,
    cmPortCpdProfileGVRPDispType          CmControlProtocolDispType,
    cmPortCpdProfileGARPDispType          CmControlProtocolDispType,
    cmPortCpdProfileLldpDispType          CmControlProtocolDispType,
    cmPortCpdProfileStorageType           StorageType,
    cmPortCpdProfileRowStatus             RowStatus
}

cmPortCpdProfileIndex OBJECT-TYPE
    SYNTAX      Integer32 (1..65535)
    MAX-ACCESS  read-only
    STATUS      current
    DESCRIPTION
        "Unique Index value to access the CPD profile row."
    ::= { cmPortCpdProfileEntry 1 }
    
cmPortCpdProfileName OBJECT-TYPE
    SYNTAX   DisplayString (SIZE (0..64))
    MAX-ACCESS read-write
    STATUS   current
    DESCRIPTION
       "This object describes the alias of the cpd V3 profile entry."
    ::= { cmPortCpdProfileEntry 2 }
cmPortCpdProfileCiscoGroupDispType OBJECT-TYPE
    SYNTAX      CmControlProtocolDispType 
    MAX-ACCESS  read-write
    STATUS      current
    DESCRIPTION
        "Control Protocol Disposition for Cisco Group.  This includes
         ISL, PAGP, UDLD, CDP, VTP, DTP, PSVTP+, UplinkFast, VLAN Bridge,
         L2PT.  Note that a specific protocol filter overrides the
         group setting."
    ::= { cmPortCpdProfileEntry 3 }

cmPortCpdProfileIslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmPortCpdProfileEntry 4 }

cmPortCpdProfilePagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmPortCpdProfileEntry 5 }

cmPortCpdProfileUdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmPortCpdProfileEntry 6 }

cmPortCpdProfileCdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmPortCpdProfileEntry 7 }

cmPortCpdProfileVtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmPortCpdProfileEntry 8 }

cmPortCpdProfileDtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmPortCpdProfileEntry 9 }

cmPortCpdProfilePvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmPortCpdProfileEntry 10 }

cmPortCpdProfileUplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmPortCpdProfileEntry 11 }

cmPortCpdProfileVlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmPortCpdProfileEntry 12 }

cmPortCpdProfileL2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmPortCpdProfileEntry 13 }

cmPortCpdProfileBridgeGroupDispType OBJECT-TYPE
    SYNTAX      CmControlProtocolDispType 
    MAX-ACCESS  read-write
    STATUS      current
    DESCRIPTION
        "Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmPortCpdProfileEntry 14 }

cmPortCpdProfileBPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmPortCpdProfileEntry 15 }

cmPortCpdProfilePauseDispType OBJECT-TYPE
    SYNTAX      CmControlProtocolDispType 
    MAX-ACCESS  read-write
    STATUS      current
    DESCRIPTION
        "Control Protocol Disposition for IEEE 802.3x Flow Control 
         (PAUSE frames)."
    ::= { cmPortCpdProfileEntry 16 }

cmPortCpdProfileLACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmPortCpdProfileEntry 17 }

cmPortCpdProfileLACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmPortCpdProfileEntry 18 }

cmPortCpdProfileEfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmPortCpdProfileEntry 19 }

cmPortCpdProfileSSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmPortCpdProfileEntry 20 }

cmPortCpdProfilePortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmPortCpdProfileEntry 21 }

cmPortCpdProfileBridgeReservedDispType OBJECT-TYPE
    SYNTAX      CmControlProtocolDispType 
    MAX-ACCESS  read-write
    STATUS      current
    DESCRIPTION
        "Control Protocol Disposition for Range of MAC Addresses
         from 01:80:C2:00:00:04 to 01:80:C2:00:00:0F."
    ::= { cmPortCpdProfileEntry 22 }
    
cmPortCpdProfileLANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmPortCpdProfileEntry 23 }

cmPortCpdProfileGARPGroupDispType OBJECT-TYPE
    SYNTAX      CmControlProtocolDispType 
    MAX-ACCESS  read-write
    STATUS      current
    DESCRIPTION
        "Group Disposition type which includes GMRP, GVRP and
         MAC Address from range 01:80:C2:00:00:22 to 01:80:C2:00:00:2F."
    ::= { cmPortCpdProfileEntry 24 }

cmPortCpdProfileGMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmPortCpdProfileEntry 25 }

cmPortCpdProfileGVRPDispType OBJECT-TYPE
    SYNTAX      CmControlProtocolDispType 
    MAX-ACCESS  read-write
    STATUS      current
    DESCRIPTION
        "Control Protocol Disposition for GARP VLAN Registration
         Protocol. MAC Address (01:80:C2:00:00:22)."
    ::= { cmPortCpdProfileEntry 26 }

cmPortCpdProfileGARPDispType OBJECT-TYPE 
    SYNTAX      CmControlProtocolDispType 
    MAX-ACCESS  read-write     
    STATUS      current     
    DESCRIPTION     
        "Group Disposition type which includes GMRP, GVRP and
         MAC Address from range 01:80:C2:00:00:20 to 01:80:C2:00:00:2F."
    ::= { cmPortCpdProfileEntry 27 }     

cmPortCpdProfileLldpDispType OBJECT-TYPE 
    SYNTAX      CmControlProtocolDispType 
    MAX-ACCESS  read-write     
    STATUS      current     
    DESCRIPTION     
        "Control Protocol Disposition for LLDP."
    ::= { cmPortCpdProfileEntry 28 }

cmPortCpdProfileStorageType OBJECT-TYPE
    SYNTAX     StorageType
    MAX-ACCESS read-create
    STATUS     current
    DESCRIPTION
            "The type of storage configured for this entry."
    ::= { cmPortCpdProfileEntry 29 }
    
cmPortCpdProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmCpdProfileRowStatus supported are
            createAndGo(4) and destroy(6).  All mandatory attributes
            must be specified in a single SNMP SET request with
            cmCpdProfileRowStatus value as createAndGo(4).
            Upon successful row creation, this object has a
            value of active(1).

            The cmCpdProfileRowStatus object may be modified if
            the associated instance of this object is equal to active(1)."
    ::= { cmPortCpdProfileEntry 30 }

--
--  Flow Point Control Protocol Disposition profile Table
--
cmFlowPointCpdProfileTable  OBJECT-TYPE
    SYNTAX      SEQUENCE OF CmFlowPointCpdProfileEntry
    MAX-ACCESS  not-accessible
    STATUS      current
    DESCRIPTION
            "A list of entries corresponding to System 
             Control Protocol Disposition V3 profile."
    ::= { cmFacilityObjects 34 }

cmFlowPointCpdProfileEntry OBJECT-TYPE
    SYNTAX      CmFlowPointCpdProfileEntry 
    MAX-ACCESS  not-accessible
    STATUS      current
    DESCRIPTION
            "A conceptual row in the cmFlowPointCpdProfileTable. 
             These entries represent a Control Protocol Disposition 
             of a flow point filtering criteria of the System."
    INDEX { cmFlowPointCpdProfileIndex }
    ::= { cmFlowPointCpdProfileTable 1 }


CmFlowPointCpdProfileEntry ::= SEQUENCE {
    -- Index
    cmFlowPointCpdProfileIndex                 Integer32,
    cmFlowPointCpdProfileName                  DisplayString,
    -- Filtering Criteria
    cmFlowPointCpdProfileCiscoGroupDispType    CmControlProtocolDispType,
    cmFlowPointCpdProfileIslDispType           CmControlProtocolDispType,
    cmFlowPointCpdProfilePagpDispType          CmControlProtocolDispType,
    cmFlowPointCpdProfileUdldDispType          CmControlProtocolDispType,
    cmFlowPointCpdProfileCdpDispType           CmControlProtocolDispType,
    cmFlowPointCpdProfileVtpDispType           CmControlProtocolDispType,
    cmFlowPointCpdProfileDtpDispType           CmControlProtocolDispType,
    cmFlowPointCpdProfilePvstpPlusDispType     CmControlProtocolDispType,
    cmFlowPointCpdProfileUplinkFastDispType    CmControlProtocolDispType,
    cmFlowPointCpdProfileVlanBridgeDispType    CmControlProtocolDispType,
    cmFlowPointCpdProfileL2PTDispType          CmControlProtocolDispType,
    cmFlowPointCpdProfileBridgeGroupDispType   CmControlProtocolDispType,
    cmFlowPointCpdProfileBPDUDispType          CmControlProtocolDispType,
    cmFlowPointCpdProfilePauseDispType         CmControlProtocolDispType,
    cmFlowPointCpdProfileLACPDispType          CmControlProtocolDispType,
    cmFlowPointCpdProfileLACPMarkerDispType    CmControlProtocolDispType,
    cmFlowPointCpdProfileEfmOamDispType        CmControlProtocolDispType,
    cmFlowPointCpdProfileSSMDispType           CmControlProtocolDispType,
    cmFlowPointCpdProfilePortAuthenDispType    CmControlProtocolDispType,
    cmFlowPointCpdProfileBridgeReservedDispType    CmControlProtocolDispType,
    cmFlowPointCpdProfileLANBridgesDispType    CmControlProtocolDispType,
    cmFlowPointCpdProfileGARPGroupDispType     CmControlProtocolDispType,
    cmFlowPointCpdProfileGMRPDispType          CmControlProtocolDispType,
    cmFlowPointCpdProfileGVRPDispType          CmControlProtocolDispType,
    cmFlowPointCpdProfileGARPDispType          CmControlProtocolDispType,
    cmFlowPointCpdProfileLldpDispType          CmControlProtocolDispType,
    cmFlowPointCpdProfileStorageType           StorageType,
    cmFlowPointCpdProfileRowStatus             RowStatus
}

cmFlowPointCpdProfileIndex OBJECT-TYPE
    SYNTAX      Integer32 (1..65535)
    MAX-ACCESS  read-only
    STATUS      current
    DESCRIPTION
        "Unique Index value to access the CPD profile row."
    ::= { cmFlowPointCpdProfileEntry 1 }
    
cmFlowPointCpdProfileName OBJECT-TYPE
    SYNTAX   DisplayString (SIZE (0..64))
    MAX-ACCESS read-write
    STATUS   current
    DESCRIPTION
       "This object describes the alias of the cpd V3 profile entry."
    ::= { cmFlowPointCpdProfileEntry 2 }
cmFlowPointCpdProfileCiscoGroupDispType OBJECT-TYPE
    SYNTAX      CmControlProtocolDispType 
    MAX-ACCESS  read-write
    STATUS      current
    DESCRIPTION
        "Control Protocol Disposition for Cisco Group.  This includes
         ISL, PAGP, UDLD, CDP, VTP, DTP, PSVTP+, UplinkFast, VLAN Bridge,
         L2PT.  Note that a specific protocol filter overrides the
         group setting."
    ::= { cmFlowPointCpdProfileEntry 3 }

cmFlowPointCpdProfileIslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmFlowPointCpdProfileEntry 4 }

cmFlowPointCpdProfilePagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmFlowPointCpdProfileEntry 5 }

cmFlowPointCpdProfileUdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmFlowPointCpdProfileEntry 6 }

cmFlowPointCpdProfileCdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmFlowPointCpdProfileEntry 7 }

cmFlowPointCpdProfileVtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmFlowPointCpdProfileEntry 8 }

cmFlowPointCpdProfileDtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmFlowPointCpdProfileEntry 9 }

cmFlowPointCpdProfilePvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmFlowPointCpdProfileEntry 10 }

cmFlowPointCpdProfileUplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmFlowPointCpdProfileEntry 11 }

cmFlowPointCpdProfileVlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmFlowPointCpdProfileEntry 12 }

cmFlowPointCpdProfileL2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmFlowPointCpdProfileEntry 13 }

cmFlowPointCpdProfileBridgeGroupDispType OBJECT-TYPE
    SYNTAX      CmControlProtocolDispType 
    MAX-ACCESS  read-write
    STATUS      current
    DESCRIPTION
        "Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmFlowPointCpdProfileEntry 14 }

cmFlowPointCpdProfileBPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmFlowPointCpdProfileEntry 15 }

cmFlowPointCpdProfilePauseDispType OBJECT-TYPE
    SYNTAX      CmControlProtocolDispType 
    MAX-ACCESS  read-write
    STATUS      current
    DESCRIPTION
        "Control Protocol Disposition for IEEE 802.3x Flow Control 
         (PAUSE frames)."
    ::= { cmFlowPointCpdProfileEntry 16 }

cmFlowPointCpdProfileLACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmFlowPointCpdProfileEntry 17 }

cmFlowPointCpdProfileLACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmFlowPointCpdProfileEntry 18 }

cmFlowPointCpdProfileEfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmFlowPointCpdProfileEntry 19 }

cmFlowPointCpdProfileSSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmFlowPointCpdProfileEntry 20 }

cmFlowPointCpdProfilePortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmFlowPointCpdProfileEntry 21 }

cmFlowPointCpdProfileBridgeReservedDispType OBJECT-TYPE
    SYNTAX      CmControlProtocolDispType 
    MAX-ACCESS  read-write
    STATUS      current
    DESCRIPTION
        "Control Protocol Disposition for Range of MAC Addresses
         from 01:80:C2:00:00:04 to 01:80:C2:00:00:0F."
    ::= { cmFlowPointCpdProfileEntry 22 }
    
cmFlowPointCpdProfileLANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmFlowPointCpdProfileEntry 23 }

cmFlowPointCpdProfileGARPGroupDispType OBJECT-TYPE
    SYNTAX      CmControlProtocolDispType 
    MAX-ACCESS  read-write
    STATUS      current
    DESCRIPTION
        "Group Disposition type which includes GMRP, GVRP and
         MAC Address from range 01:80:C2:00:00:22 to 01:80:C2:00:00:2F."
    ::= { cmFlowPointCpdProfileEntry 24 }

cmFlowPointCpdProfileGMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmFlowPointCpdProfileEntry 25 }

cmFlowPointCpdProfileGVRPDispType OBJECT-TYPE
    SYNTAX      CmControlProtocolDispType 
    MAX-ACCESS  read-write
    STATUS      current
    DESCRIPTION
        "Control Protocol Disposition for GARP VLAN Registration
         Protocol. MAC Address (01:80:C2:00:00:22)."
    ::= { cmFlowPointCpdProfileEntry 26 }

cmFlowPointCpdProfileGARPDispType OBJECT-TYPE 
    SYNTAX      CmControlProtocolDispType 
    MAX-ACCESS  read-write     
    STATUS      current     
    DESCRIPTION     
        "Group Disposition type which includes GMRP, GVRP and
         MAC Address from range 01:80:C2:00:00:20 to 01:80:C2:00:00:2F."
    ::= { cmFlowPointCpdProfileEntry 27 }     

cmFlowPointCpdProfileLldpDispType OBJECT-TYPE 
    SYNTAX      CmControlProtocolDispType 
    MAX-ACCESS  read-write     
    STATUS      current     
    DESCRIPTION     
        "Control Protocol Disposition for LLDP."
    ::= { cmFlowPointCpdProfileEntry 28 }

cmFlowPointCpdProfileStorageType OBJECT-TYPE
    SYNTAX     StorageType
    MAX-ACCESS read-create
    STATUS     current
    DESCRIPTION
            "The type of storage configured for this entry."
    ::= { cmFlowPointCpdProfileEntry 29 }
    
cmFlowPointCpdProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmCpdProfileRowStatus supported are
            createAndGo(4) and destroy(6).  All mandatory attributes
            must be specified in a single SNMP SET request with
            cmCpdProfileRowStatus value as createAndGo(4).
            Upon successful row creation, this object has a
            value of active(1).

            The cmCpdProfileRowStatus object may be modified if
            the associated instance of this object is equal to active(1)."
    ::= { cmFlowPointCpdProfileEntry 30 }


--
--  Ethernet Agg Port CPD Table
--
cmEthernetTrafficPortCpdTable OBJECT-TYPE
    SYNTAX      SEQUENCE OF CmEthernetTrafficPortCpdEntry
    MAX-ACCESS  not-accessible
    STATUS      current
    DESCRIPTION
            "A list of entries corresponding to Ethernet Port 
             CPD for configuration purposes."
    ::= { cmFacilityObjects 35 }

cmEthernetTrafficPortCpdEntry OBJECT-TYPE
    SYNTAX      CmEthernetTrafficPortCpdEntry 
    MAX-ACCESS  not-accessible
    STATUS      current
    DESCRIPTION
            "A conceptual row in the cmEthernetTrafficPortCpdTable."
    INDEX { neIndex, shelfIndex, slotIndex, cmEthernetTrafficPortIndex, cmEthernetTrafficPortCpdIndex }
    ::= { cmEthernetTrafficPortCpdTable 1 }

CmEthernetTrafficPortCpdEntry ::= SEQUENCE {
    -- Port Indices 
    cmEthernetTrafficPortCpdIndex                  Integer32,
    cmEthernetTrafficPortAssociatedCpdProfile VariablePointer
}

cmEthernetTrafficPortCpdIndex OBJECT-TYPE
    SYNTAX      Integer32 (1..65535)
    MAX-ACCESS  read-only
    STATUS      current
    DESCRIPTION
         "An arbitrary integer index value used to uniquely identify this CPD Service Entry."
    ::= { cmEthernetTrafficPortCpdEntry 1 }

cmEthernetTrafficPortAssociatedCpdProfile OBJECT-TYPE
    SYNTAX      VariablePointer
    MAX-ACCESS  read-write
    STATUS      current
    DESCRIPTION
         "An integer index value used to apply cmCpdProfile configure, corresponding to cmCpdProfileIndex." 
    ::= { cmEthernetTrafficPortCpdEntry 2 }

--
--  Ethernet Flow Point CPD Table
--
cmEthernetFlowPointCpdTable OBJECT-TYPE
    SYNTAX      SEQUENCE OF CmEthernetFlowPointCpdEntry
    MAX-ACCESS  not-accessible
    STATUS      current
    DESCRIPTION
            "A list of entries corresponding to Ethernet Flow Point 
             CPD for configuration purposes."
    ::= { cmFacilityObjects 36 }

cmEthernetFlowPointCpdEntry OBJECT-TYPE
    SYNTAX      CmEthernetFlowPointCpdEntry 
    MAX-ACCESS  not-accessible
    STATUS      current
    DESCRIPTION
            "A conceptual row in the cmEthernetFlowPointCpdTable."
    INDEX { neIndex, shelfIndex, slotIndex, cmEthernetTrafficPortIndex, cmFlowPointIndex, cmEthernetFlowPointCpdIndex }
    ::= { cmEthernetFlowPointCpdTable 1 }

CmEthernetFlowPointCpdEntry ::= SEQUENCE {
    -- Port Indices 
    cmEthernetFlowPointCpdIndex                  Integer32,
    cmEthernetFlowPointAssociatedCpdProfile      VariablePointer
}

cmEthernetFlowPointCpdIndex OBJECT-TYPE
    SYNTAX      Integer32 (1..65535)
    MAX-ACCESS  read-only
    STATUS      current
    DESCRIPTION
         "An arbitrary integer index value used to uniquely identify this CPD Service Entry."
    ::= { cmEthernetFlowPointCpdEntry 1 }

cmEthernetFlowPointAssociatedCpdProfile OBJECT-TYPE
    SYNTAX      VariablePointer
    MAX-ACCESS  read-write
    STATUS      current
    DESCRIPTION
         "An integer index value used to apply cmCpdProfile configure, corresponding to cmCpdProfileIndex." 
    ::= { cmEthernetFlowPointCpdEntry 2 }


-- Traffic ACL Profile Table
cmTrafficAclProfileTable OBJECT-TYPE
    SYNTAX     SEQUENCE OF CmTrafficAclProfileEntry
    MAX-ACCESS not-accessible
    STATUS     current
    DESCRIPTION
            "A list of entries corresponding to the Traffic Profile Rules Entry. 
             It provides upto 4000 Traffic ACL Rules to be configured."
    ::= { cmFacilityObjects 37 }

cmTrafficAclProfileEntry OBJECT-TYPE
    SYNTAX     CmTrafficAclProfileEntry
    MAX-ACCESS not-accessible
    STATUS     current
    DESCRIPTION
            "An entry containing information applicable to a system ACL Profile that can be configured."
    INDEX { cmTrafficAclProfileIndex }
    ::= { cmTrafficAclProfileTable 1 }

CmTrafficAclProfileEntry ::= SEQUENCE {
    cmTrafficAclProfileIndex            Integer32,
    cmTrafficAclProfileName             DisplayString,
    cmTrafficAclProfileStorageType      StorageType,
    cmTrafficAclProfileRowStatus        RowStatus
    }

cmTrafficAclProfileIndex OBJECT-TYPE
    SYNTAX      Integer32 (1..65535)
    MAX-ACCESS  read-create
    STATUS      current
    DESCRIPTION
            "An arbitrary integer index value used to uniquely identify
             Traffic ACL profile entry."
    ::= { cmTrafficAclProfileEntry 1 }
    
cmTrafficAclProfileName OBJECT-TYPE
    SYNTAX   DisplayString (SIZE (0..64))
    MAX-ACCESS read-write
    STATUS   current
    DESCRIPTION
       "This object describes the alias of the Acl profile entry."
    ::= { cmTrafficAclProfileEntry 2 }

cmTrafficAclProfileStorageType OBJECT-TYPE
    SYNTAX     StorageType
    MAX-ACCESS read-create
    STATUS     current
    DESCRIPTION
            "The type of storage configured for this entry."
    ::= { cmTrafficAclProfileEntry 3 }
    
cmTrafficAclProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmTrafficAclProfileRowStatus supported are
            createAndGo(4) and destroy(6).  All mandatory attributes
            must be specified in a single SNMP SET request with
            cmTrafficAclProfileRowStatus value as createAndGo(4).
            Upon successful row creation, this object has a
            value of active(1).

            The cmTrafficAclProfileRowStatus object may be modified if
            the associated instance of this object is equal to active(1)."
    ::= { cmTrafficAclProfileEntry 4 }

-- Traffic ACL Rules Table
cmTrafficAclRulesTable OBJECT-TYPE
    SYNTAX     SEQUENCE OF CmTrafficAclRulesEntry
    MAX-ACCESS not-accessible
    STATUS     current
    DESCRIPTION
            "A list of entries corresponding to the Traffic ACL Rules Entry."
    ::= { cmFacilityObjects 38 }

cmTrafficAclRulesEntry OBJECT-TYPE
    SYNTAX     CmTrafficAclRulesEntry
    MAX-ACCESS not-accessible
    STATUS     current
    DESCRIPTION
            "An entry containing information applicable to a system ACL Rules that can be configured."
    INDEX { cmTrafficAclProfileIndex, cmTrafficAclRulesIndex }
    ::= { cmTrafficAclRulesTable 1 }

CmTrafficAclRulesEntry ::= SEQUENCE {
    cmTrafficAclRulesIndex              Integer32,
    cmTrafficAclFilterAction            CmTrafficAclFilterActionType,
    cmTrafficAclFilterType              CmTrafficAclFilterType,
    cmTrafficAclEnabled                 TruthValue,
    cmTrafficAclSrcMacAddr              MacAddress,
    cmTrafficAclSrcMacAddrEnabled       TruthValue,
    cmTrafficAclDstMacAddr              MacAddress,
    cmTrafficAclDstMacAddrEnabled       TruthValue,
    cmTrafficAclSrcIpFilterEnabled      TruthValue,
    cmTrafficAclDstIpFilterEnabled      TruthValue,
    cmTrafficAclSrcIpV4Addr             IpAddress,
    cmTrafficAclSrcIpV4AddrMask         IpAddress,
    cmTrafficAclDstIpV4Addr             IpAddress,
    cmTrafficAclDstIpV4AddrMask         IpAddress,
    cmTrafficAclSrcIpV6Addr             Ipv6Address,
    cmTrafficAclSrcIpV6AddrMask         Ipv6Address,
    cmTrafficAclDstIpV6Addr             Ipv6Address,
    cmTrafficAclDstIpV6AddrMask         Ipv6Address,
    cmTrafficAclTcpUdpSrcPortNum        Integer32,
    cmTrafficAclTcpUdpSrcPortMask       Integer32,
    cmTrafficAclTcpUdpSrcPortEnabled    TruthValue,
    cmTrafficAclTcpUdpDstPortNum        Integer32,
    cmTrafficAclTcpUdpDstPortMask       Integer32,
    cmTrafficAclTcpUdpDstPortEnabled    TruthValue,
    cmTrafficAclIpQosType               CmTrafficACLPriorityType,
    cmTrafficAclIpQosValue              Integer32,
    cmTrafficAclIpQosTypeEnabled        TruthValue,
    cmTrafficAclVlanId                  VlanId,
    cmTrafficAclVlanIdEnabled           TruthValue,
    cmTrafficAclVlanPriority            Integer32,
    cmTrafficAclVlanPriorityEnabled     TruthValue,
    cmTrafficAclProtocolType            CmTrafficAclProtocolType,
    cmTrafficAclProtocolTypeEnabled     TruthValue,
    cmTrafficAclStorageType             StorageType,
    cmTrafficAclRowStatus               RowStatus
}

cmTrafficAclRulesIndex OBJECT-TYPE
    SYNTAX      Integer32 (1..65535)
    MAX-ACCESS  read-create
    STATUS      current
    DESCRIPTION
            "An arbitrary integer index value used to uniquely identify
             Traffic ACL profile entry. The manager may not assume any
             particular semantics or meaning to this index, except that
             it identifies a logical row in the table."
    ::= { cmTrafficAclRulesEntry 1 }
    
cmTrafficAclFilterAction OBJECT-TYPE
    SYNTAX   CmTrafficAclFilterActionType 
    MAX-ACCESS read-write
    STATUS   current
    DESCRIPTION
       "Currently,  'permit' and 'deny' are supported."
    ::= { cmTrafficAclRulesEntry 2 }

cmTrafficAclFilterType OBJECT-TYPE
    SYNTAX   CmTrafficAclFilterType 
    MAX-ACCESS read-write
    STATUS   current
    DESCRIPTION
       "This object describes the Acl filter type."
    ::= { cmTrafficAclRulesEntry 3 }
cmTrafficAclEnabled OBJECT-TYPE
    SYNTAX   TruthValue 
    MAX-ACCESS read-write
    STATUS   current
    DESCRIPTION
       "This object enables/disables the Acl entity."
    ::= { cmTrafficAclRulesEntry 4 }

cmTrafficAclSrcMacAddr OBJECT-TYPE
    SYNTAX   MacAddress 
    MAX-ACCESS read-write
    STATUS   current
    DESCRIPTION
       "The source mac address of Acl entry."
    ::= { cmTrafficAclRulesEntry 5 }

cmTrafficAclSrcMacAddrEnabled OBJECT-TYPE
    SYNTAX   TruthValue 
    MAX-ACCESS read-write
    STATUS   current
    DESCRIPTION
       "This object enables/disables source MAC address of Acl entry."
    ::= { cmTrafficAclRulesEntry 6 }

cmTrafficAclDstMacAddr OBJECT-TYPE
    SYNTAX   MacAddress 
    MAX-ACCESS read-write
    STATUS   current
    DESCRIPTION
       "The destination MAC address of Acl entry."
    ::= { cmTrafficAclRulesEntry 7 }

cmTrafficAclDstMacAddrEnabled OBJECT-TYPE
    SYNTAX   TruthValue 
    MAX-ACCESS read-write
    STATUS   current
    DESCRIPTION
       "This object enables/disables destination MAC address  of Acl entry."
    ::= { cmTrafficAclRulesEntry 8 }

cmTrafficAclSrcIpFilterEnabled OBJECT-TYPE
    SYNTAX   TruthValue 
    MAX-ACCESS read-write
    STATUS   current
    DESCRIPTION
       "This object enable/disable Source IPV4 or IPV6 address filter criteria."
    ::= { cmTrafficAclRulesEntry 9 }

cmTrafficAclDstIpFilterEnabled OBJECT-TYPE
    SYNTAX   TruthValue 
    MAX-ACCESS read-write
    STATUS   current
    DESCRIPTION
       "This object enable/disable Destination IPV4 or IPV6 address filter criteria."
    ::= { cmTrafficAclRulesEntry 10 }

cmTrafficAclSrcIpV4Addr OBJECT-TYPE
    SYNTAX   IpAddress 
    MAX-ACCESS read-write
    STATUS   current
    DESCRIPTION
       "The source IP address of Acl entry."
    ::= { cmTrafficAclRulesEntry 11 }

cmTrafficAclSrcIpV4AddrMask OBJECT-TYPE
    SYNTAX   IpAddress 
    MAX-ACCESS read-write
    STATUS   current
    DESCRIPTION
       "The source IP mask of Acl entry."
    ::= { cmTrafficAclRulesEntry 12 }

cmTrafficAclDstIpV4Addr OBJECT-TYPE
    SYNTAX   IpAddress 
    MAX-ACCESS read-write
    STATUS   current
    DESCRIPTION
       "The destination IP address of Acl entry."
    ::= { cmTrafficAclRulesEntry 13 }

cmTrafficAclDstIpV4AddrMask OBJECT-TYPE
    SYNTAX   IpAddress 
    MAX-ACCESS read-write
    STATUS   current
    DESCRIPTION
       "The destination IP mask of Acl entry."
    ::= { cmTrafficAclRulesEntry 14 }

cmTrafficAclSrcIpV6Addr OBJECT-TYPE
    SYNTAX   Ipv6Address 
    MAX-ACCESS read-write
    STATUS   current
    DESCRIPTION
       "The source IPV6 address of Acl entry."
    ::= { cmTrafficAclRulesEntry 15 }

cmTrafficAclSrcIpV6AddrMask OBJECT-TYPE
    SYNTAX   Ipv6Address 
    MAX-ACCESS read-write
    STATUS   current
    DESCRIPTION
       "The source IPV6 mask of Acl entry."
    ::= { cmTrafficAclRulesEntry 16 }

cmTrafficAclDstIpV6Addr OBJECT-TYPE
    SYNTAX   Ipv6Address 
    MAX-ACCESS read-write
    STATUS   current
    DESCRIPTION
       "The destination IPV6 address of Acl entry."
    ::= { cmTrafficAclRulesEntry 17 }

cmTrafficAclDstIpV6AddrMask OBJECT-TYPE
    SYNTAX   Ipv6Address 
    MAX-ACCESS read-write
    STATUS   current
    DESCRIPTION
       "The destination IPV6 mask of Acl entry."
    ::= { cmTrafficAclRulesEntry 18 }

cmTrafficAclTcpUdpSrcPortNum OBJECT-TYPE
    SYNTAX   Integer32 (0..65535)
    MAX-ACCESS read-write
    STATUS   current
    DESCRIPTION
       "This object describes TCP/UDP minimum source port number of Acl entry."
    ::= { cmTrafficAclRulesEntry 19 }

cmTrafficAclTcpUdpSrcPortMask OBJECT-TYPE
    SYNTAX   Integer32 (0..65535)
    MAX-ACCESS read-write
    STATUS   current
    DESCRIPTION
       "This object describes TCP/UDP maximum source port number of Acl entry."
    ::= { cmTrafficAclRulesEntry 20 }

cmTrafficAclTcpUdpSrcPortEnabled OBJECT-TYPE
    SYNTAX   TruthValue
    MAX-ACCESS read-write
    STATUS   current
    DESCRIPTION
       "This object enables/disables TCP/UDP source port of Acl entry."
    ::= { cmTrafficAclRulesEntry 21 }

cmTrafficAclTcpUdpDstPortNum OBJECT-TYPE
    SYNTAX   Integer32 (0..65535)
    MAX-ACCESS read-write
    STATUS   current
    DESCRIPTION
       "This object describes TCP/UDP minimum destination port number of Acl entry."
    ::= { cmTrafficAclRulesEntry 22 }

cmTrafficAclTcpUdpDstPortMask OBJECT-TYPE
    SYNTAX   Integer32 (0..65535)
    MAX-ACCESS read-write
    STATUS   current
    DESCRIPTION
       "This object describes TCP/UDP maximum destination port number of Acl entry."
    ::= { cmTrafficAclRulesEntry 23 }

cmTrafficAclTcpUdpDstPortEnabled OBJECT-TYPE
    SYNTAX   TruthValue
    MAX-ACCESS read-write
    STATUS   current
    DESCRIPTION
       "This object enables/disables TCP/UDP destination port of Acl entry."
    ::= { cmTrafficAclRulesEntry 24 }

cmTrafficAclIpQosType OBJECT-TYPE
    SYNTAX   CmTrafficACLPriorityType
    MAX-ACCESS read-write
    STATUS   current
    DESCRIPTION
       "This object describes QosType Acl entry."
    ::= { cmTrafficAclRulesEntry 25 }

cmTrafficAclIpQosValue OBJECT-TYPE
    SYNTAX   Integer32
    MAX-ACCESS read-write
    STATUS   current
    DESCRIPTION
       "This object describes QOS value of Acl entry."
    ::= { cmTrafficAclRulesEntry 26 }

cmTrafficAclIpQosTypeEnabled OBJECT-TYPE
    SYNTAX   TruthValue
    MAX-ACCESS read-write
    STATUS   current
    DESCRIPTION
       "This object enables/disables qos type of acl entry."
    ::= { cmTrafficAclRulesEntry 27 }

cmTrafficAclVlanId OBJECT-TYPE
    SYNTAX   VlanId
    MAX-ACCESS read-write
    STATUS   current
    DESCRIPTION
       "This object describes the vlan Id of Acl entry."
    ::= { cmTrafficAclRulesEntry 28 }

cmTrafficAclVlanIdEnabled OBJECT-TYPE
    SYNTAX   TruthValue
    MAX-ACCESS read-write
    STATUS   current
    DESCRIPTION
       "This object enables/disables Vlan Id of Acl entry."
    ::= { cmTrafficAclRulesEntry 29 }

cmTrafficAclVlanPriority OBJECT-TYPE
    SYNTAX   Integer32 (0..7)
    MAX-ACCESS read-write
    STATUS   current
    DESCRIPTION
       "This object describes the Vlan Priority of Acl entry."
    ::= { cmTrafficAclRulesEntry 30 }

cmTrafficAclVlanPriorityEnabled OBJECT-TYPE
    SYNTAX   TruthValue
    MAX-ACCESS read-write
    STATUS   current
    DESCRIPTION
       "This object enables/disables Vlan Priority of Acl entry."
    ::= { cmTrafficAclRulesEntry 31 }

cmTrafficAclProtocolType OBJECT-TYPE
    SYNTAX   CmTrafficAclProtocolType
    MAX-ACCESS read-write
    STATUS   current
    DESCRIPTION
       "This object describes protocol type of Acl entry."
    ::= { cmTrafficAclRulesEntry 32 }
    
cmTrafficAclProtocolTypeEnabled OBJECT-TYPE
    SYNTAX   TruthValue
    MAX-ACCESS read-write
    STATUS   current
    DESCRIPTION
       "This object enables/disables protocol type of Acl entry."
    ::= { cmTrafficAclRulesEntry 33 }    

cmTrafficAclStorageType OBJECT-TYPE
    SYNTAX     StorageType
    MAX-ACCESS read-create
    STATUS     current
    DESCRIPTION
            "The type of storage configured for this entry."
    ::= { cmTrafficAclRulesEntry 34 }

cmTrafficAclRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmTrafficAclRowStatus supported are
            createAndGo(4) and destroy(6).  All mandatory attributes
            must be specified in a single SNMP SET request with
            cmTrafficAclRowStatus value as createAndGo(4).
            Upon successful row creation, this object has a
            value of active(1).

            The cmTrafficAclRowStatus object may be modified if
            the associated instance of this object is equal to active(1)."
    ::= { cmTrafficAclRulesEntry 35 }

--Qos Policer V2 Profile
cmQosPolicerProfileTable  OBJECT-TYPE
    SYNTAX      SEQUENCE OF CmQosPolicerProfileEntry
    MAX-ACCESS  not-accessible
    STATUS      current
    DESCRIPTION
        "A list of entries corresponding to Quality of Service 
         Policer for configuration purposes."
    ::= { cmFacilityObjects 39 }

cmQosPolicerProfileEntry OBJECT-TYPE
    SYNTAX      CmQosPolicerProfileEntry 
    MAX-ACCESS  not-accessible
    STATUS      current
    DESCRIPTION
         "A conceptual row in the cmQosPolicerProfileTable. 
          These entries represent a Quality of Service Policer."
    INDEX { cmQosPolicerProfileIndex }
    ::= { cmQosPolicerProfileTable 1 }

CmQosPolicerProfileEntry ::= SEQUENCE {
    cmQosPolicerProfileIndex            Integer32,
    cmQosPolicerProfileName             DisplayString,

    cmQosPolicerProfileCIRLo            Unsigned32,
    cmQosPolicerProfileCIRHi            Unsigned32,
    cmQosPolicerProfileEIRLo            Unsigned32,
    cmQosPolicerProfileEIRHi            Unsigned32,
    cmQosPolicerProfileCBS              Integer32,
    cmQosPolicerProfileEBS              Integer32,
    cmQosPolicerProfileColorMode        PolicerColorMode,
    cmQosPolicerProfileCouplingFlag     TruthValue,
    cmQosPolicerProfileStorageType      StorageType,
    cmQosPolicerProfileRowStatus        RowStatus 
}

cmQosPolicerProfileIndex OBJECT-TYPE
    SYNTAX      Integer32 (1..65535)
    MAX-ACCESS  read-create
    STATUS      current
    DESCRIPTION
            "This object defines the Policer profile ID. Up to 1000 profiles can be specified per system." 
    ::= { cmQosPolicerProfileEntry 1 }

cmQosPolicerProfileName OBJECT-TYPE
    SYNTAX      DisplayString (SIZE (0..64)) 
    MAX-ACCESS  read-create
    STATUS      current
    DESCRIPTION
            "This object defines the alias for this profile"
    ::= { cmQosPolicerProfileEntry 2 }

cmQosPolicerProfileCIRLo OBJECT-TYPE
    SYNTAX     Unsigned32
    MAX-ACCESS read-create
    STATUS     current
    DESCRIPTION
         "This object allows specification of the Commited Information
          Rate(CIR) on Policer Profile.  This represents the lower 32 bits of the
          CIR."
     ::= { cmQosPolicerProfileEntry 3 }

cmQosPolicerProfileCIRHi OBJECT-TYPE
    SYNTAX     Unsigned32
    MAX-ACCESS read-create
    STATUS     current
    DESCRIPTION
         "This object allows specification of the Commited Information
          Rate(CIR) on Policer Profile.  This represents the upper 32 bits of the
          CIR."
     ::= { cmQosPolicerProfileEntry 4 }

cmQosPolicerProfileEIRLo OBJECT-TYPE
    SYNTAX     Unsigned32
    MAX-ACCESS read-create
    STATUS     current
    DESCRIPTION
         "This object allows specification of the Excess Information
          Rate(EIR) on the Policer Profile.  This represents the lower 32 bits
          of the EIR."
     ::= { cmQosPolicerProfileEntry 5 }

cmQosPolicerProfileEIRHi OBJECT-TYPE
    SYNTAX     Unsigned32
    MAX-ACCESS read-create
    STATUS     current
    DESCRIPTION
         "This object allows specification of the Excess Information
          Rate(EIR) on the Policer Profile.  This represents the upper 32 bits
          of the EIR."
     ::= { cmQosPolicerProfileEntry 6 }

cmQosPolicerProfileCBS OBJECT-TYPE
    SYNTAX     Integer32
    MAX-ACCESS read-create
    STATUS     current
    DESCRIPTION
         "This object allows specification of the Commited Burst Size
          (CBS) on Policer Profile."
     ::= { cmQosPolicerProfileEntry 7 }

cmQosPolicerProfileEBS OBJECT-TYPE
    SYNTAX     Integer32
    MAX-ACCESS read-create
    STATUS     current
    DESCRIPTION
         "This object allows specification of the Excess Burst Size
          (EBS) on the Policer Profile."
     ::= { cmQosPolicerProfileEntry 8 }

cmQosPolicerProfileColorMode OBJECT-TYPE
    SYNTAX      PolicerColorMode 
    MAX-ACCESS  read-create
    STATUS      current
    DESCRIPTION
          "This object allows specification of Policer Color Mode as
           'color-aware' or 'color-blind'."
    ::= { cmQosPolicerProfileEntry 9 }

cmQosPolicerProfileCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow, which is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { cmQosPolicerProfileEntry 10 }

cmQosPolicerProfileStorageType OBJECT-TYPE
    SYNTAX     StorageType
    MAX-ACCESS read-create
    STATUS     current
    DESCRIPTION
            "The type of storage configured for this entry."
    ::= { cmQosPolicerProfileEntry 11 }

cmQosPolicerProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosPolicerProfileRowStatus supported are
            createAndGo(4) and destroy(6).  All mandatory attributes
            must be specified in a single SNMP SET request with
            cmQosPolicerProfileRowStatus value as createAndGo(4).
            Upon successful row creation, this object has a
            value of active(1).

            The cmQosPolicerProfileRowStatus object may be modified if
            the associated instance of this object is equal to active(1)."
    ::= { cmQosPolicerProfileEntry 12 }

--Qos Queue Profile
cmQosQueueProfileTable  OBJECT-TYPE
    SYNTAX      SEQUENCE OF CmQosQueueProfileEntry
    MAX-ACCESS  not-accessible
    STATUS      current
    DESCRIPTION
        "A list of entries corresponding to Quality of Service 
         Queue for configuration purposes."
    ::= { cmFacilityObjects 40 }

cmQosQueueProfileEntry OBJECT-TYPE
    SYNTAX      CmQosQueueProfileEntry 
    MAX-ACCESS  not-accessible
    STATUS      current
    DESCRIPTION
         "A conceptual row in the cmQosQueueProfileTable. 
          These entries represent a Quality of Service Queue."
    INDEX { cmQosQueueProfileIndex }
    ::= { cmQosQueueProfileTable 1 }

CmQosQueueProfileEntry ::= SEQUENCE {
    cmQosQueueProfileIndex            Integer32,
    cmQosQueueProfileName            DisplayString,

    cmQosQueueProfileBufferSize       Integer32,
    cmQosQueueProfileREDEnabled       TruthValue,
    cmQosQueueProfileStorageType      StorageType,
    cmQosQueueProfileRowStatus        RowStatus 
}

cmQosQueueProfileIndex OBJECT-TYPE
    SYNTAX      Integer32 (1..64)
    MAX-ACCESS  read-create
    STATUS      current
    DESCRIPTION
            "This object defines the Queue profile ID. Up to 64 profiles can be specified per system." 
    ::= { cmQosQueueProfileEntry 1 }

cmQosQueueProfileName OBJECT-TYPE
    SYNTAX      DisplayString (SIZE (0..64)) 
    MAX-ACCESS  read-create
    STATUS      current
    DESCRIPTION
            "This object defines the alias for this profile"
    ::= { cmQosQueueProfileEntry 2 }

cmQosQueueProfileBufferSize OBJECT-TYPE
    SYNTAX     Integer32
    MAX-ACCESS read-create
    STATUS     current
    DESCRIPTION
         "This object defines the buffer size of the selected queues."
     ::= { cmQosQueueProfileEntry 3 }

cmQosQueueProfileREDEnabled OBJECT-TYPE
    SYNTAX     TruthValue
    MAX-ACCESS read-create
    STATUS     current
    DESCRIPTION
         "This object defines whether the WRED is enabled as congestion algorithm or not.
          If disabled, then the following RED parameters (cmQueueProfileWREDDp0MinTh, 
          cmQueueProfileWREDDp0MaxTh and cmQueueProfileWREDDp0MaxProb) must not be specified."
     ::= { cmQosQueueProfileEntry 4 }

cmQosQueueProfileStorageType OBJECT-TYPE
    SYNTAX     StorageType
    MAX-ACCESS read-create
    STATUS     current
    DESCRIPTION
            "The type of storage configured for this entry."
    ::= { cmQosQueueProfileEntry 5 }

cmQosQueueProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosQueueProfileRowStatus supported are
            createAndGo(4) and destroy(6).  All mandatory attributes
            must be specified in a single SNMP SET request with
            cmQosQueueProfileRowStatus value as createAndGo(4).
            Upon successful row creation, this object has a
            value of active(1).

            The cmQosQueueProfileRowStatus object may be modified if
            the associated instance of this object is equal to active(1)."
    ::= { cmQosQueueProfileEntry 6 }    

--FlowPoint Policer
cmQosPolicerV2Table  OBJECT-TYPE
    SYNTAX      SEQUENCE OF CmQosPolicerV2Entry
    MAX-ACCESS  not-accessible
    STATUS      current
    DESCRIPTION
        "A list of entries corresponding to Quality of Service 
         Policer for configuration purposes."
    ::= { cmFacilityObjects 41 }

cmQosPolicerV2Entry OBJECT-TYPE
    SYNTAX      CmQosPolicerV2Entry 
    MAX-ACCESS  not-accessible
    STATUS      current
    DESCRIPTION
         "A conceptual row in the cmQosPolicerV2Table. 
          These entries represent a Quality of Service Policer."
    INDEX { neIndex, shelfIndex, slotIndex, cmEthernetTrafficPortIndex, 
            cmFlowPointIndex, cmQosPolicerV2Index }
    ::= { cmQosPolicerV2Table 1 }

CmQosPolicerV2Entry ::= SEQUENCE {
    cmQosPolicerV2Index         Integer32,

    -- State Management params
    cmQosPolicerV2AdminState          AdminState,
    cmQosPolicerV2OperationalState    OperationalState,
    cmQosPolicerV2SecondaryState      SecondaryState,
    cmQosPolicerV2ColorMarkingEnabled TruthValue,
    cmQosPolicerV2AssociatedProfile   VariablePointer,
    cmQosPolicerV2StorageType         StorageType,
    cmQosPolicerV2RowStatus           RowStatus,
    cmQosPolicerV2PolicingEnabled     TruthValue
}

cmQosPolicerV2Index OBJECT-TYPE
    SYNTAX      Integer32 (1..8)
    MAX-ACCESS  read-create
    STATUS      current
    DESCRIPTION
            "The Policer Index that represents the COS level. Index 1
             represents COS 0; Index 2 represents COS 1 and so on." 
    ::= { cmQosPolicerV2Entry 1 }

-- State Management params
cmQosPolicerV2AdminState OBJECT-TYPE
    SYNTAX      AdminState 
    MAX-ACCESS  read-write
    STATUS      current
    DESCRIPTION
            "This object represents the Administrative State of 
             the QOS Policer." 
    ::= { cmQosPolicerV2Entry 2 }

cmQosPolicerV2OperationalState OBJECT-TYPE
    SYNTAX      OperationalState 
    MAX-ACCESS  read-only
    STATUS      current
    DESCRIPTION
            "This object represents the Operational State of the QOS Policer." 
    ::= { cmQosPolicerV2Entry 3 }

cmQosPolicerV2SecondaryState OBJECT-TYPE
    SYNTAX      SecondaryState 
    MAX-ACCESS  read-only
    STATUS      current
    DESCRIPTION
            "This object represents the Secondary State of the QOS Policer." 
    ::= { cmQosPolicerV2Entry 4 }

cmQosPolicerV2ColorMarkingEnabled OBJECT-TYPE
    SYNTAX      TruthValue 
    MAX-ACCESS  read-only
    STATUS      current
    DESCRIPTION
            "This object indicates the colorMarking state of the QOS Policer." 
    ::= { cmQosPolicerV2Entry 5 }
    
cmQosPolicerV2AssociatedProfile OBJECT-TYPE
    SYNTAX     VariablePointer
    MAX-ACCESS read-create
    STATUS     current
    DESCRIPTION
         "This object define the queue profile ID to be used,
          it is associated with the cmQosPolicerProfileIndex."
     ::= { cmQosPolicerV2Entry 6 }

cmQosPolicerV2StorageType OBJECT-TYPE
    SYNTAX     StorageType
    MAX-ACCESS read-create
    STATUS     current
    DESCRIPTION
            "The type of storage configured for this entry."
    ::= { cmQosPolicerV2Entry 7 }

cmQosPolicerV2RowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosPolicerV2RowStatus supported are
            createAndGo(4) and destroy(6).  All mandatory attributes
            must be specified in a single SNMP SET request with
            cmQosPolicerV2RowStatus value as createAndGo(4).
            Upon successful row creation, this object has a
            value of active(1).

            The cmQosPolicerV2RowStatus object may be modified if
            the associated instance of this object is equal to active(1)."
    ::= { cmQosPolicerV2Entry 8 }

cmQosPolicerV2PolicingEnabled OBJECT-TYPE
    SYNTAX      TruthValue 
    MAX-ACCESS  read-write
    STATUS      current
    DESCRIPTION
            "Whether enable or disable the functionality of policing for this COS." 
    ::= { cmQosPolicerV2Entry 9 }

--FlowPoint Queue
cmQosShaperV2Table  OBJECT-TYPE
    SYNTAX      SEQUENCE OF CmQosShaperV2Entry
    MAX-ACCESS  not-accessible
    STATUS      current
    DESCRIPTION
        "A list of entries corresponding to Quality of Service 
         ShaperV2 for configuration purposes."
    ::= { cmFacilityObjects 42 }

cmQosShaperV2Entry OBJECT-TYPE
    SYNTAX      CmQosShaperV2Entry 
    MAX-ACCESS  not-accessible
    STATUS      current
    DESCRIPTION
         "A conceptual row in the cmQosShaperV2Table. 
          These entries represent a Quality of Service Shaper."
    INDEX { neIndex, shelfIndex, slotIndex, cmEthernetTrafficPortIndex, 
            cmFlowPointIndex, cmQosShaperV2Index }
    ::= { cmQosShaperV2Table 1 }

CmQosShaperV2Entry ::= SEQUENCE {
    cmQosShaperV2Index         Integer32,

    -- State Management params
    cmQosShaperV2AdminState         AdminState,
    cmQosShaperV2OperationalState   OperationalState,
    cmQosShaperV2SecondaryState     SecondaryState,
    
    cmQosShaperV2AssociatedQueueProfile  VariablePointer,
    --cmQosShaperV2BufferSize      Integer32,
    cmQosShaperV2CIRLo           Unsigned32,
    cmQosShaperV2CIRHi           Unsigned32,
    cmQosShaperV2EIRLo           Unsigned32,
    cmQosShaperV2EIRHi           Unsigned32,
--    cmQosShaperV2REDEnabled      TruthValue,
    cmQosShaperV2IngressAverageFrameSize Integer32,
    cmQosShaperV2StorageType     StorageType,
    cmQosShaperV2RowStatus       RowStatus,
    cmQosShaperV2AdditionalCIRLo Unsigned32,
    cmQosShaperV2AdditionalCIRHi Unsigned32,
    cmQosShaperV2WFQWeight       Integer32
}

cmQosShaperV2Index OBJECT-TYPE
    SYNTAX      Integer32 (1..8)
    MAX-ACCESS  read-create
    STATUS      current
    DESCRIPTION
            "The ShaperV2 Index that represents the COS level. Index 1
             represents COS 0; Index 2 represents COS 1 and so on." 
    ::= { cmQosShaperV2Entry 1 }

-- State Management params
cmQosShaperV2AdminState OBJECT-TYPE
    SYNTAX      AdminState 
    MAX-ACCESS  read-write
    STATUS      current
    DESCRIPTION
            "This object represents the Administrative State of 
             the QOS Shaper." 
    ::= { cmQosShaperV2Entry 2 }

cmQosShaperV2OperationalState OBJECT-TYPE
    SYNTAX      OperationalState 
    MAX-ACCESS  read-only
    STATUS      current
    DESCRIPTION
            "This object represents the Operational State of the QOS ShaperV2." 
    ::= { cmQosShaperV2Entry 3 }

cmQosShaperV2SecondaryState OBJECT-TYPE
    SYNTAX      SecondaryState 
    MAX-ACCESS  read-only
    STATUS      current
    DESCRIPTION
            "This object represents the Secondary State of the QOS QosShaperV2." 
    ::= { cmQosShaperV2Entry 4 }

cmQosShaperV2AssociatedQueueProfile OBJECT-TYPE
    SYNTAX     VariablePointer
    MAX-ACCESS read-create
    STATUS     current
    DESCRIPTION
         "This object defines the queue profile ID to be used,
          it is associated with the cmQosQueueProfileIndex."
     ::= { cmQosShaperV2Entry 5 }

--cmQosShaperV2BufferSize OBJECT-TYPE
--    SYNTAX     Integer32
--    MAX-ACCESS read-create
--    STATUS     current
--    DESCRIPTION
--         "This object defines the buffer size of ShaperV2."
--     ::= { cmQosShaperV2Entry 6 }

cmQosShaperV2CIRLo OBJECT-TYPE
    SYNTAX     Unsigned32 
    MAX-ACCESS read-write
    STATUS     current
    DESCRIPTION
         "This object specifies the Lower 32 bits of CIR."
     ::= { cmQosShaperV2Entry 6 }
     
cmQosShaperV2CIRHi OBJECT-TYPE
    SYNTAX     Unsigned32 
    MAX-ACCESS read-write
    STATUS     current
    DESCRIPTION
         "This object specifies the Higher 32 bits of CIR."
     ::= { cmQosShaperV2Entry 7 }

cmQosShaperV2EIRLo OBJECT-TYPE
    SYNTAX     Unsigned32 
    MAX-ACCESS read-write
    STATUS     current
    DESCRIPTION
         "This object specifies the Lower 32 bits of EIR."
     ::= { cmQosShaperV2Entry 8 }
     
cmQosShaperV2EIRHi OBJECT-TYPE
    SYNTAX     Unsigned32 
    MAX-ACCESS read-write
    STATUS     current
    DESCRIPTION
         "This object specifies the Higher 32 bits of EIR."
     ::= { cmQosShaperV2Entry 9 }

cmQosShaperV2IngressAverageFrameSize  OBJECT-TYPE
    SYNTAX     Integer32 (64..9600)
    MAX-ACCESS read-create
    STATUS     current
    DESCRIPTION
         "This object defines the average frame size for accounting for Meter/Shaping."
     ::= { cmQosShaperV2Entry 10 }

--cmQosShaperV2REDEnabled OBJECT-TYPE
--    SYNTAX     TruthValue 
--    MAX-ACCESS read-create
--    STATUS     current
--    DESCRIPTION
--         "This object specifies RED of ShaperV2."
--     ::= { cmQosShaperV2Entry 11 }
     
cmQosShaperV2StorageType OBJECT-TYPE
    SYNTAX     StorageType
    MAX-ACCESS read-create
    STATUS     current
    DESCRIPTION
            "The type of storage configured for this entry."
    ::= { cmQosShaperV2Entry 11 }

cmQosShaperV2RowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosShaperV2RowStatus supported are
            createAndGo(4) and destroy(6).  All mandatory attributes
            must be specified in a single SNMP SET request with
            cmQosShaperV2RowStatus value as createAndGo(4).
            Upon successful row creation, this object has a
            value of active(1).

            The cmQosShaperV2RowStatus object may be modified if
            the associated instance of this object is equal to active(1)."
    ::= { cmQosShaperV2Entry 12 }

cmQosShaperV2AdditionalCIRLo OBJECT-TYPE
    SYNTAX     Unsigned32 
    MAX-ACCESS read-write
    STATUS     current
    DESCRIPTION
         "This object specifies the Lower 32 bits of additional CIR."
     ::= { cmQosShaperV2Entry 13 }
     
cmQosShaperV2AdditionalCIRHi OBJECT-TYPE
    SYNTAX     Unsigned32 
    MAX-ACCESS read-write
    STATUS     current
    DESCRIPTION
         "This object specifies the Higher 32 bits of additional CIR."
     ::= { cmQosShaperV2Entry 14 }

cmQosShaperV2WFQWeight OBJECT-TYPE
    SYNTAX     Integer32 (1..64) 
    MAX-ACCESS read-write
    STATUS     current
    DESCRIPTION
         "Weight of queue to be scheduled by WFQ mechanism."
     ::= { cmQosShaperV2Entry 15 }



--Lag Shaper
cmTrafficPortQosShaperTable  OBJECT-TYPE
    SYNTAX      SEQUENCE OF CmTrafficPortQosShaperEntry
    MAX-ACCESS  not-accessible
    STATUS      current
    DESCRIPTION
        "A list of entries corresponding to Quality of Service 
         Shaper for configuration purposes."
    ::= { cmFacilityObjects 43 }

cmTrafficPortQosShaperEntry OBJECT-TYPE
    SYNTAX      CmTrafficPortQosShaperEntry 
    MAX-ACCESS  not-accessible
    STATUS      current
    DESCRIPTION
         "A conceptual row in the cmTrafficPortQosShaperTable. 
          These entries represent a Quality of Service Shaper."
    INDEX { neIndex, shelfIndex, slotIndex, cmEthernetTrafficPortIndex, cmTrafficPortQosShaperIndex }
    ::= { cmTrafficPortQosShaperTable 1 }

CmTrafficPortQosShaperEntry ::= SEQUENCE {
    cmTrafficPortQosShaperIndex                   Integer32,

    -- State Management params
    cmTrafficPortQosShaperAdminState              AdminState,
    cmTrafficPortQosShaperOperationalState        OperationalState,
    cmTrafficPortQosShaperSecondaryState          SecondaryState,
    
    cmTrafficPortQosShaperAssociatedQueueProfile  VariablePointer,
    cmTrafficPortQosShaperBufferSize              Integer32,
    cmTrafficPortQosShaperCIRLo                   Unsigned32,
    cmTrafficPortQosShaperCIRHi                   Unsigned32,
    cmTrafficPortQosShaperEIRLo                   Unsigned32,
    cmTrafficPortQosShaperEIRHi                   Unsigned32,
    --cmTrafficPortQosShaperREDEnabled      TruthValue,
    cmTrafficPortQosShaperStorageType             StorageType,
    cmTrafficPortQosShaperRowStatus               RowStatus,
    cmTrafficPortQosShaperIngressAverageFrameSize Integer32,
    cmTrafficPortQosShaperAdditionalCIRLo         Unsigned32,
    cmTrafficPortQosShaperAdditionalCIRHi         Unsigned32
}

cmTrafficPortQosShaperIndex OBJECT-TYPE
    SYNTAX      Integer32 (1..8)
    MAX-ACCESS  read-create
    STATUS      current
    DESCRIPTION
            "The ShaperV2 Index that represents the COS level. Index 1
             represents COS 0; Index 2 represents COS 1 and so on." 
    ::= { cmTrafficPortQosShaperEntry 1 }

-- State Management params
cmTrafficPortQosShaperAdminState OBJECT-TYPE
    SYNTAX      AdminState 
    MAX-ACCESS  read-write
    STATUS      current
    DESCRIPTION
            "This object represents the Administrative State of 
             the QOS Shaper." 
    ::= { cmTrafficPortQosShaperEntry 2 }

cmTrafficPortQosShaperOperationalState OBJECT-TYPE
    SYNTAX      OperationalState 
    MAX-ACCESS  read-only
    STATUS      current
    DESCRIPTION
            "This object represents the Operational State of the QOS ShaperV2." 
    ::= { cmTrafficPortQosShaperEntry 3 }

cmTrafficPortQosShaperSecondaryState OBJECT-TYPE
    SYNTAX      SecondaryState 
    MAX-ACCESS  read-only
    STATUS      current
    DESCRIPTION
            "This object represents the Secondary State of the QOS LagQosShaper." 
    ::= { cmTrafficPortQosShaperEntry 4 }

cmTrafficPortQosShaperAssociatedQueueProfile OBJECT-TYPE
    SYNTAX     VariablePointer
    MAX-ACCESS read-create
    STATUS     current
    DESCRIPTION
         "This object defines the queue profile ID to be used,
          it is associated with the cmQosQueueProfileIndex."
     ::= { cmTrafficPortQosShaperEntry 5 }

cmTrafficPortQosShaperBufferSize OBJECT-TYPE
    SYNTAX     Integer32
    MAX-ACCESS read-create
    STATUS     current
    DESCRIPTION
         "This object defines the buffer size of Shaper."
     ::= { cmTrafficPortQosShaperEntry 6 }

cmTrafficPortQosShaperCIRLo OBJECT-TYPE
    SYNTAX     Unsigned32 
    MAX-ACCESS read-create
    STATUS     current
    DESCRIPTION
         "This object specifies the Lower 32 bits of CIR."
     ::= { cmTrafficPortQosShaperEntry 7 }
     
cmTrafficPortQosShaperCIRHi OBJECT-TYPE
    SYNTAX     Unsigned32 
    MAX-ACCESS read-create
    STATUS     current
    DESCRIPTION
         "This object specifies the Higher 32 bits of CIR."
     ::= { cmTrafficPortQosShaperEntry 8 }

cmTrafficPortQosShaperEIRLo OBJECT-TYPE
    SYNTAX     Unsigned32 
    MAX-ACCESS read-create
    STATUS     current
    DESCRIPTION
         "This object specifies the Lower 32 bits of EIR."
     ::= { cmTrafficPortQosShaperEntry 9 }
     
cmTrafficPortQosShaperEIRHi OBJECT-TYPE
    SYNTAX     Unsigned32 
    MAX-ACCESS read-create
    STATUS     current
    DESCRIPTION
         "This object specifies the Higher 32 bits of EIR."
     ::= { cmTrafficPortQosShaperEntry 10 }

--cmTrafficPortQosShaperREDEnabled OBJECT-TYPE
--    SYNTAX     TruthValue 
--    MAX-ACCESS read-create
--    STATUS     current
--    DESCRIPTION
--         "This object specifies RED of Port Shaper."
--     ::= { cmTrafficPortQosShaperEntry 11 }

cmTrafficPortQosShaperStorageType OBJECT-TYPE
    SYNTAX     StorageType
    MAX-ACCESS read-create
    STATUS     current
    DESCRIPTION
            "The type of storage configured for this entry."
    ::= { cmTrafficPortQosShaperEntry 11 }

cmTrafficPortQosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmTrafficPortQosShaperRowStatus supported are
            createAndGo(4) and destroy(6).  All mandatory attributes
            must be specified in a single SNMP SET request with
            cmTrafficPortQosShaperRowStatus value as createAndGo(4).
            Upon successful row creation, this object has a
            value of active(1).

            The cmTrafficPortQosShaperRowStatus object may be modified if
            the associated instance of this object is equal to active(1)."
    ::= { cmTrafficPortQosShaperEntry 12 }

cmTrafficPortQosShaperIngressAverageFrameSize  OBJECT-TYPE
    SYNTAX     Integer32 (64..9600)
    MAX-ACCESS read-create
    STATUS     current
    DESCRIPTION
         "This object defines the average frame size for accounting for Meter/Shaping."
     ::= { cmTrafficPortQosShaperEntry 13 }

cmTrafficPortQosShaperAdditionalCIRLo OBJECT-TYPE
    SYNTAX     Unsigned32 
    MAX-ACCESS read-create
    STATUS     current
    DESCRIPTION
         "This object specifies the Lower 32 bits of additional CIR."
     ::= { cmTrafficPortQosShaperEntry 14 }
     
cmTrafficPortQosShaperAdditionalCIRHi OBJECT-TYPE
    SYNTAX     Unsigned32 
    MAX-ACCESS read-create
    STATUS     current
    DESCRIPTION
         "This object specifies the Higher 32 bits of additional CIR."
     ::= { cmTrafficPortQosShaperEntry 15 }

cmTrafficAclRscAllocation OBJECT-TYPE
    SYNTAX     CmAclConfiguration
    MAX-ACCESS read-write
    STATUS     current
    DESCRIPTION
        "This object is defined to set traffic acl resource allocation.

         Supported actions are:
         all-bk-l2(1)  - all bank allocated to l2. 
         all-bk-l2-ipv4(2)  - all bank allocated to l2/ipv4. 
         two-bk-l2-ipv4(3)  - two thirds allocated to l2/ipv4, the left belongs to ipv6.
         one-bk-l2-ipv4(4)  - one thirds allocated to l2/ipv4, the left belongs to ipv6.
         none-bk-l2-ipv4(5) - all bank allocated to ipv6. "
    ::= { cmFacilityObjects 44 }

--
--  Ethernet Network Port Quality of Service Shaper 
--
f3NetPortQosShaperTable  OBJECT-TYPE
    SYNTAX      SEQUENCE OF F3NetPortQosShaperEntry
    MAX-ACCESS  not-accessible
    STATUS      current
    DESCRIPTION
            "A list of entries corresponding to Ethernet Network Port 
             Quality of Service Shaper for configuration purposes.
             These shapers can be managed when the Network Port is
             in evpl mode and are relevant for traffic in the
             access to network direction."
    ::= { cmFacilityObjects 45 }

f3NetPortQosShaperEntry OBJECT-TYPE
    SYNTAX      F3NetPortQosShaperEntry
    MAX-ACCESS  not-accessible
    STATUS      current
    DESCRIPTION
            "A conceptual row in the f3NetPortQosShaperTable. 
             These entries represent a Quality of Service Shaper."
    INDEX { neIndex, shelfIndex, slotIndex, cmEthernetNetPortIndex, 
            f3NetPortQosShaperIndex }
    ::= { f3NetPortQosShaperTable 1 }

F3NetPortQosShaperEntry ::= SEQUENCE {
    -- QOS Shaper Index/Id
    f3NetPortQosShaperIndex               Integer32,
    f3NetPortQosShaperDirection           TrafficDirection,

    -- State Management params
    f3NetPortQosShaperAdminState          AdminState,
    f3NetPortQosShaperOperationalState    OperationalState,
    f3NetPortQosShaperSecondaryState      SecondaryState,

    -- QOS Shaper Properties
    f3NetPortQosShaperCIRLo               Unsigned32,
    f3NetPortQosShaperCIRHi               Unsigned32,
    f3NetPortQosShaperEIRLo               Unsigned32,
    f3NetPortQosShaperEIRHi               Unsigned32,
    f3NetPortQosShaperCBS                 Unsigned32,
    f3NetPortQosShaperEBS                 Unsigned32,
    f3NetPortQosShaperBufferSize          Unsigned32,
    f3NetPortQosShaperCOS                 Integer32,
    f3NetPortQosShaperSoamCIRLo           Unsigned32,
    f3NetPortQosShaperSoamCIRHi           Unsigned32,
    f3NetPortQosShaperSoamEIRLo           Unsigned32,
    f3NetPortQosShaperSoamEIRHi           Unsigned32
}

f3NetPortQosShaperIndex OBJECT-TYPE
    SYNTAX      Integer32 (1..8)
    MAX-ACCESS  read-create
    STATUS      current
    DESCRIPTION
            "The unique integer index value corresponding to a 
             Quality of Service Shaper."
    ::= { f3NetPortQosShaperEntry 1 }

f3NetPortQosShaperDirection OBJECT-TYPE
    SYNTAX      TrafficDirection 
    MAX-ACCESS  read-only
    STATUS      current
    DESCRIPTION
            "The direction of the Quality of Service Shaper."
    ::= { f3NetPortQosShaperEntry 2 }

-- State Management params
f3NetPortQosShaperAdminState OBJECT-TYPE
    SYNTAX      AdminState 
    MAX-ACCESS  read-write
    STATUS      current
    DESCRIPTION
            "This object represents the Administrative State of 
             the QOS Shaper." 
    ::= { f3NetPortQosShaperEntry 3 }

f3NetPortQosShaperOperationalState OBJECT-TYPE
    SYNTAX      OperationalState 
    MAX-ACCESS  read-only
    STATUS      current
    DESCRIPTION
            "This object represents the Operational State of the QOS Shaper." 
    ::= { f3NetPortQosShaperEntry 4 }

f3NetPortQosShaperSecondaryState OBJECT-TYPE
    SYNTAX      SecondaryState 
    MAX-ACCESS  read-only
    STATUS      current
    DESCRIPTION
            "This object represents the Secondary State of the QOS Shaper." 
    ::= { f3NetPortQosShaperEntry 5 }

f3NetPortQosShaperCIRLo OBJECT-TYPE
    SYNTAX     Unsigned32
    MAX-ACCESS read-create
    STATUS     current
    DESCRIPTION
         "This object represents the Commited Information
          Rate(CIR) (Lower 32 bits)of a Shaper."
     ::= { f3NetPortQosShaperEntry 6 }

f3NetPortQosShaperCIRHi OBJECT-TYPE
    SYNTAX     Unsigned32
    MAX-ACCESS read-create
    STATUS     current
    DESCRIPTION
         "This object represents the Commited Information
          Rate(CIR) (Higher 32 bits) of a Shaper."
     ::= { f3NetPortQosShaperEntry 7 }

f3NetPortQosShaperEIRLo OBJECT-TYPE
    SYNTAX     Unsigned32
    MAX-ACCESS read-create
    STATUS     current
    DESCRIPTION
         "This object represents the Excess Information
          Rate(EIR) (Higher 32 bits) on the Shaper."
     ::= { f3NetPortQosShaperEntry 8 }

f3NetPortQosShaperEIRHi OBJECT-TYPE
    SYNTAX     Unsigned32
    MAX-ACCESS read-create
    STATUS     current
    DESCRIPTION
         "This object represents the Excess Information
          Rate(EIR) (Higher 32 bits) on the Shaper."
     ::= { f3NetPortQosShaperEntry 9 }

f3NetPortQosShaperCBS OBJECT-TYPE
    SYNTAX     Unsigned32
    MAX-ACCESS read-create
    STATUS     current
    DESCRIPTION
         "This object represents the Commited Burst Size (CBS) of the Shaper."
     ::= { f3NetPortQosShaperEntry 10 }

f3NetPortQosShaperEBS OBJECT-TYPE
    SYNTAX     Unsigned32
    MAX-ACCESS read-create
    STATUS     current
    DESCRIPTION
         "This object represents the Excess Burst Size (EBS) of the Shaper."
     ::= { f3NetPortQosShaperEntry 11 }

f3NetPortQosShaperBufferSize OBJECT-TYPE
    SYNTAX     Unsigned32
    MAX-ACCESS read-create
    STATUS     current
    DESCRIPTION
         "This object represents the Buffer Size of the Shaper."
     ::= { f3NetPortQosShaperEntry 12 }

f3NetPortQosShaperCOS OBJECT-TYPE
    SYNTAX     Integer32 (0..7)
    MAX-ACCESS read-only
    STATUS     current
    DESCRIPTION
            "This object provides the COS (Class of Service)
             value for the QOS Shaper."
    ::= { f3NetPortQosShaperEntry 13 }

f3NetPortQosShaperSoamCIRLo OBJECT-TYPE
    SYNTAX     Unsigned32
    MAX-ACCESS read-create
    STATUS     current
    DESCRIPTION
         "This object represents the Soam Commited Information
          Rate(SOAM-CIR) (Lower 32 bits)of a Shaper."
     ::= { f3NetPortQosShaperEntry 14 }

f3NetPortQosShaperSoamCIRHi OBJECT-TYPE
    SYNTAX     Unsigned32
    MAX-ACCESS read-create
    STATUS     current
    DESCRIPTION
         "This object represents the Soam Commited Information
          Rate(SOAM-CIR) (Higher 32 bits) of a Shaper."
     ::= { f3NetPortQosShaperEntry 15 }

f3NetPortQosShaperSoamEIRLo OBJECT-TYPE
    SYNTAX     Unsigned32
    MAX-ACCESS read-create
    STATUS     current
    DESCRIPTION
         "This object represents the Soam Excess Information
          Rate(SOAM-EIR) (Higher 32 bits) on the Shaper."
     ::= { f3NetPortQosShaperEntry 16 }

f3NetPortQosShaperSoamEIRHi OBJECT-TYPE
    SYNTAX     Unsigned32
    MAX-ACCESS read-create
    STATUS     current
    DESCRIPTION
         "This object represents the Soam Excess Information
          Rate(SOAM-EIR) (Higher 32 bits) on the Shaper."
     ::= { f3NetPortQosShaperEntry 17 }

-- 
-- ge dcn port table
--
f3Usb3GDCNPortTable   OBJECT-TYPE
    SYNTAX      SEQUENCE OF F3Usb3GDCNPortEntry
    MAX-ACCESS  not-accessible
    STATUS      current
    DESCRIPTION
            "3G DCN Port table.
             The table contains parameters of 3G USB modem."
    ::= { cmFacilityObjects 46 }

f3Usb3GDCNPortEntry OBJECT-TYPE
    SYNTAX      F3Usb3GDCNPortEntry 
    MAX-ACCESS  not-accessible
    STATUS      current
    DESCRIPTION
            "A conceptual row in the f3Usb3GDCNPortTable."
    INDEX { neIndex, shelfIndex, slotIndex, f3UsbHostIndex }
    ::= { f3Usb3GDCNPortTable 1 }

F3Usb3GDCNPortEntry ::= SEQUENCE {
    f3Usb3GDCNPortIndex                Integer32,
    f3Usb3GDCNPortIfIndex              InterfaceIndex,
    f3Usb3GDCNPortEntityIndex          PhysicalIndex,
    f3Usb3GDCNPortAdminState           AdminState,
    f3Usb3GDCNPortOperationalState     OperationalState,
    f3Usb3GDCNPortSecondaryState       SecondaryState,
    f3Usb3GDCNPortVendorName           DisplayString,
    f3Usb3GDCNPortModel                DisplayString,
    f3Usb3GDCNPortFSN                  DisplayString,
    f3Usb3GDCNPortIMEI                 DisplayString,
    f3Usb3GDCNPortHardwareVersion      DisplayString,
    f3Usb3GDCNPortFirmwareVersion      DisplayString,
    f3Usb3GDCNPortSIMStatus            F3Usb3GSimCardState,
    f3Usb3GDCNPortPINLeftChances       Integer32,
    f3Usb3GDCNPortPUKLeftChances       Integer32,
    f3Usb3GDCNPortConnectionStatus     F3Usb3GNetworkConnectionState,
    f3Usb3GDCNPortRSSI                 F3Usb3GRecvSignalStrengthInd,
    f3Usb3GDCNPortSpeed                Integer32,
    f3Usb3GDCNPortMTU                  Integer32,
    f3Usb3GDCNPortProviderName         DisplayString,
    f3Usb3GDCNPortDNS1                 IpAddress,
    f3Usb3GDCNPortDNS2                 IpAddress,
    f3Usb3GDCNPortAPN                  DisplayString,
    f3Usb3GDCNPortUserName             DisplayString,
    f3Usb3GDCNPortPassword             DisplayString,
    f3Usb3GDCNPortDailNumber           DisplayString,
    f3Usb3GDCNPortRedialTimer          Integer32,
    f3Usb3GDCNPortCurrentPinCode       DisplayString,
    f3Usb3GDCNPortNewPinCode           DisplayString,
    f3Usb3GDCNPortConfirmPinCode       DisplayString,
    f3Usb3GDCNPortCurrentPukCode       DisplayString,
    f3Usb3GDCNPINCodeAction            F3Usb3GDCNPINCodeActionType,
    f3Usb3GDCNPortStorageType          StorageType,
    f3Usb3GDCNPortRowStatus            RowStatus,
    f3Usb3GDCNPortIMSI                 DisplayString,
    f3Usb3GDCNPortPINStatus            G3AuthStatus,
    f3UsbDCNPortMobileNetworkType      UsbDCNMobileNetworkType
}


f3Usb3GDCNPortIndex OBJECT-TYPE
    SYNTAX      Integer32
    MAX-ACCESS  read-only
    STATUS      current
    DESCRIPTION
            "An integer index value used to uniquely identify
             this Ethernet Access Port within a card.
             Note that each Ethernet Access Port is uniquely identified
             by the indices neIndex, shelfIndex, 
             slotIndex, f3Usb3GDCNPortIndex"
    ::= { f3Usb3GDCNPortEntry 1 }

f3Usb3GDCNPortIfIndex OBJECT-TYPE
    SYNTAX     InterfaceIndex
    MAX-ACCESS read-only
    STATUS     current
    DESCRIPTION
         "This object has the same value as ifIndex for 
             DCN Port.  An integer index value used to 
             uniquely identify this DCN Port."
     ::= { f3Usb3GDCNPortEntry 2 }

f3Usb3GDCNPortEntityIndex OBJECT-TYPE
    SYNTAX     PhysicalIndex
    MAX-ACCESS read-only
    STATUS     current
    DESCRIPTION
         "Entity Index from ENTITY-MIB for this port."
     ::= { f3Usb3GDCNPortEntry 3 }

f3Usb3GDCNPortAdminState OBJECT-TYPE
    SYNTAX     AdminState
    MAX-ACCESS read-write
    STATUS     current
    DESCRIPTION
         "This object represents the Administrative State of the DCN Port."
     ::= { f3Usb3GDCNPortEntry 4 }

f3Usb3GDCNPortOperationalState OBJECT-TYPE
    SYNTAX     OperationalState
    MAX-ACCESS read-only
    STATUS     current
    DESCRIPTION
         "This object represents the Operational State of the DCN Port."
     ::= { f3Usb3GDCNPortEntry 5 }

f3Usb3GDCNPortSecondaryState OBJECT-TYPE
    SYNTAX     SecondaryState
    MAX-ACCESS read-only
    STATUS     current
    DESCRIPTION
         "This object represents the Secondary State of the DCN Port."
     ::= { f3Usb3GDCNPortEntry 6 }

f3Usb3GDCNPortVendorName OBJECT-TYPE
    SYNTAX     DisplayString
    MAX-ACCESS read-only
    STATUS     current
    DESCRIPTION
         "This object provides the Vendor Name of the DCN Port."
     ::= { f3Usb3GDCNPortEntry 7 }

f3Usb3GDCNPortModel OBJECT-TYPE
    SYNTAX     DisplayString
    MAX-ACCESS read-only
    STATUS     current
    DESCRIPTION
         "This object provides the Model of the DCN Port."
     ::= { f3Usb3GDCNPortEntry 8 }

f3Usb3GDCNPortFSN OBJECT-TYPE
    SYNTAX     DisplayString
    MAX-ACCESS read-only
    STATUS     current
    DESCRIPTION
         "This object provides the Factory Serial Number of the DCN Port."
     ::= { f3Usb3GDCNPortEntry 9 }

f3Usb3GDCNPortIMEI OBJECT-TYPE
    SYNTAX     DisplayString
    MAX-ACCESS read-only
    STATUS     current
    DESCRIPTION
         "This object provides the International Mobile Equipment Identity of the DCN Port."
     ::= { f3Usb3GDCNPortEntry 10 }

f3Usb3GDCNPortHardwareVersion OBJECT-TYPE
    SYNTAX     DisplayString
    MAX-ACCESS read-only
    STATUS     current
    DESCRIPTION
         "This object provides the Hardware Version of the DCN Port."
     ::= { f3Usb3GDCNPortEntry 11 }

f3Usb3GDCNPortFirmwareVersion OBJECT-TYPE
    SYNTAX     DisplayString
    MAX-ACCESS read-only
    STATUS     current
    DESCRIPTION
         "This object provides the Firmware Version of the DCN Port.."
     ::= { f3Usb3GDCNPortEntry 12 }

f3Usb3GDCNPortSIMStatus OBJECT-TYPE
    SYNTAX     F3Usb3GSimCardState
    MAX-ACCESS read-only
    STATUS     current
    DESCRIPTION
         "This object provides the SIM card Status of the DCN Port."
     ::= { f3Usb3GDCNPortEntry 13 }

f3Usb3GDCNPortPINLeftChances OBJECT-TYPE
    SYNTAX     Integer32
    MAX-ACCESS read-only
    STATUS     current
    DESCRIPTION
         "This object provides the Left Chances for PIN input of the DCN Port."
     ::= { f3Usb3GDCNPortEntry 14 }

f3Usb3GDCNPortPUKLeftChances OBJECT-TYPE
    SYNTAX     Integer32
    MAX-ACCESS read-only
    STATUS     current
    DESCRIPTION
         "This object provides the Left Chances for PUK input of the DCN Port."
     ::= { f3Usb3GDCNPortEntry 15 }

f3Usb3GDCNPortConnectionStatus OBJECT-TYPE
    SYNTAX     F3Usb3GNetworkConnectionState
    MAX-ACCESS read-only
    STATUS     current
    DESCRIPTION
         "This object provides the Wirless Connection Status of the DCN Port."
     ::= { f3Usb3GDCNPortEntry 16 }

f3Usb3GDCNPortRSSI OBJECT-TYPE
    SYNTAX     F3Usb3GRecvSignalStrengthInd
    MAX-ACCESS read-only
    STATUS     current
    DESCRIPTION
         "This object provides the Received Signal Strength Indication of the DCN Port."
     ::= { f3Usb3GDCNPortEntry 17 }

f3Usb3GDCNPortSpeed OBJECT-TYPE
    SYNTAX     Integer32
    MAX-ACCESS read-only
    STATUS     current
    DESCRIPTION
         "This object provides the Connection Speed of the DCN Port."
     ::= { f3Usb3GDCNPortEntry 18 }

f3Usb3GDCNPortMTU OBJECT-TYPE
    SYNTAX     Integer32
    MAX-ACCESS read-only
    STATUS     current
    DESCRIPTION
         "This object provides the MTU of the DCN Port."
     ::= { f3Usb3GDCNPortEntry 19 }

f3Usb3GDCNPortProviderName OBJECT-TYPE
    SYNTAX     DisplayString
    MAX-ACCESS read-only
    STATUS     current
    DESCRIPTION
         "This object provides the Wireless Service Provider Name of the DCN Port."
     ::= { f3Usb3GDCNPortEntry 20 }

f3Usb3GDCNPortDNS1 OBJECT-TYPE
    SYNTAX      IpAddress 
    MAX-ACCESS  read-only
    STATUS      current
    DESCRIPTION
            "This first DNS of the interface." 
    ::= { f3Usb3GDCNPortEntry 21 }

f3Usb3GDCNPortDNS2 OBJECT-TYPE
    SYNTAX      IpAddress 
    MAX-ACCESS  read-only
    STATUS      current
    DESCRIPTION
            "This second DNS of the interface." 
    ::= { f3Usb3GDCNPortEntry 22 }

f3Usb3GDCNPortAPN OBJECT-TYPE
    SYNTAX     DisplayString (SIZE (0..64))
    MAX-ACCESS read-write
    STATUS     current
    DESCRIPTION
         "This object allows configure the Access Point Name of the DCN Port."
     ::= { f3Usb3GDCNPortEntry 23 }

f3Usb3GDCNPortUserName OBJECT-TYPE
    SYNTAX     DisplayString (SIZE (0..32))
    MAX-ACCESS read-write
    STATUS     current
    DESCRIPTION
         "This object allows configure the User Name of the DCN Port."
     ::= { f3Usb3GDCNPortEntry 24 }

f3Usb3GDCNPortPassword OBJECT-TYPE
    SYNTAX     DisplayString (SIZE (0..32))
    MAX-ACCESS read-write
    STATUS     current
    DESCRIPTION
         "This object allows configure the Password of the DCN Port."
     ::= { f3Usb3GDCNPortEntry 25 }

f3Usb3GDCNPortDailNumber OBJECT-TYPE
    SYNTAX     DisplayString (SIZE (0..32))
    MAX-ACCESS read-write
    STATUS     current
    DESCRIPTION
         "This object allows configure the Dail Number of the DCN Port."
     ::= { f3Usb3GDCNPortEntry 26 }

f3Usb3GDCNPortRedialTimer OBJECT-TYPE
    SYNTAX     Integer32
    MAX-ACCESS read-write
    STATUS     current
    DESCRIPTION
         "This object allows configure the Retail Timer of the DCN Port."
     ::= { f3Usb3GDCNPortEntry 27 }

f3Usb3GDCNPortCurrentPinCode OBJECT-TYPE
    SYNTAX     DisplayString (SIZE (0..64))
    MAX-ACCESS read-create
    STATUS     current
    DESCRIPTION
         "This object is the Current Pin Code."
     ::= { f3Usb3GDCNPortEntry 28 }

f3Usb3GDCNPortNewPinCode OBJECT-TYPE
    SYNTAX     DisplayString (SIZE (0..64))
    MAX-ACCESS read-create
    STATUS     current
    DESCRIPTION
         "This object is the New Pin code."
     ::= { f3Usb3GDCNPortEntry 29 }

f3Usb3GDCNPortConfirmPinCode OBJECT-TYPE
    SYNTAX     DisplayString (SIZE (0..64))
    MAX-ACCESS read-create
    STATUS     current
    DESCRIPTION
         "This object is the Confirm Pin Code."
     ::= { f3Usb3GDCNPortEntry 30 }

f3Usb3GDCNPortCurrentPukCode OBJECT-TYPE
    SYNTAX     DisplayString (SIZE (0..64))
    MAX-ACCESS read-create
    STATUS     current
    DESCRIPTION
         "This object is the Current Puk Code."
     ::= { f3Usb3GDCNPortEntry 31 }

f3Usb3GDCNPINCodeAction OBJECT-TYPE
    SYNTAX     F3Usb3GDCNPINCodeActionType
    MAX-ACCESS read-create
    STATUS     current
    DESCRIPTION
         "This Action is for PIN code operation."
     ::= { f3Usb3GDCNPortEntry 32 }

f3Usb3GDCNPortStorageType OBJECT-TYPE
    SYNTAX     StorageType
    MAX-ACCESS read-create
    STATUS     current
    DESCRIPTION
            "The type of storage configured for this entry."
    ::= { f3Usb3GDCNPortEntry 33 }

f3Usb3GDCNPortRowStatus OBJECT-TYPE
    SYNTAX      RowStatus
    MAX-ACCESS  read-write
    STATUS      current
    DESCRIPTION
            "The status of this row.
             The f3Usb3GDCNPortRowStatus object may be modified if
             the associated instance of this object is equal to active(1),
             notInService(2), or notReady(3)."
    ::= { f3Usb3GDCNPortEntry 34 }

f3Usb3GDCNPortIMSI OBJECT-TYPE
    SYNTAX     DisplayString
    MAX-ACCESS read-only
    STATUS     current
    DESCRIPTION
         "This object provides the International Mobile Subscriber Identity of the DCN Port."
     ::= { f3Usb3GDCNPortEntry 35 }

f3Usb3GDCNPortPINStatus OBJECT-TYPE
    SYNTAX     G3AuthStatus
    MAX-ACCESS read-only
    STATUS     current
    DESCRIPTION
         "This status of PIN/PUK"
     ::= { f3Usb3GDCNPortEntry 36 }

f3UsbDCNPortMobileNetworkType OBJECT-TYPE
    SYNTAX     UsbDCNMobileNetworkType
    MAX-ACCESS read-only
    STATUS     current
    DESCRIPTION
         "This object describe the mobile network type."
     ::= { f3Usb3GDCNPortEntry 37 }

--
-- For tdm tables
--


--
--  OCn/STM Table
--
ocnStmTable  OBJECT-TYPE
    SYNTAX      SEQUENCE OF OcnStmEntry
    MAX-ACCESS  not-accessible
    STATUS      current
    DESCRIPTION
            "A list of entries corresponding to OCn/STM interface."
    ::= { cmFacilityObjects 47 }

ocnStmEntry  OBJECT-TYPE
    SYNTAX      OcnStmEntry
    MAX-ACCESS  not-accessible
    STATUS      current
    DESCRIPTION
            "A conceptual row in the ocnStmTable."
    INDEX { neIndex, shelfIndex, slotIndex, ocnStmIndex }
    ::= { ocnStmTable 1 }

OcnStmEntry ::= SEQUENCE {
    ocnStmIndex                        Integer32,
    ocnStmIfIndex                      InterfaceIndex,
    ocnStmEntityIndex                  PhysicalIndex,
    ocnStmAdminState                   AdminState,
    ocnStmOperationalState             OperationalState,
    ocnStmSecondaryState               SecondaryState,
    ocnStmSfpVendorName                DisplayString,
    ocnStmSfpPartNumber                DisplayString,
    ocnStmSfpSerialNumber              DisplayString,
    ocnStmSfpDateOfManufacture         DateAndTime,
    ocnStmSfpConnectorValue            SfpConnectorValue,
    ocnStmSfpLinkLength                Integer32,
    ocnStmSfpLaserWaveLength           Integer32,
    ocnStmSfpLaserWaveLengthPicometer  Unsigned32,
    ocnStmSfpMediaType                 SfpMediaType,
    ocnStmMultiplexingStructures       MultiplexingStructure,
    ocnStmEoTDMMode                    EoTDMMode,
    ocnStmLoopbackConfig               CmLoopbackType,
    ocnStmLoopbackStatus               CmLoopbackType,
    ocnStmLoopbackTime                 Integer32,
    ocnStmInsertingAIS                 TruthValue,
    ocnStmBerExcThreshold              BitErrRate,
    ocnStmBerDegThreshold              BitErrRate,
    ocnStmRxTrailTrace                 DisplayString,
    ocnStmTxTrailTrace                 DisplayString,
    ocnStmExpectedTrailTrace           DisplayString,
    ocnStmTrailTraceFormat             TrailTraceFormat,
    ocnStmQLModeEnabled                TruthValue,
    ocnStmExpectedQL                   SSMQualityLevel,
    ocnStmAssumedQL                    SSMQualityLevel,
    ocnStmReceivedQL                   SSMQualityLevel,
    ocnStmTransmitQL                   SSMQualityLevel,
    ocnStmPortType                     OCNSTMPortType,
    ocnStmFreqSourceType               TDMFrequencySourceType,
    ocnStmHighOrderPathType            TDMPathType
}

ocnStmIndex OBJECT-TYPE
    SYNTAX      Integer32
    MAX-ACCESS  not-accessible 
    STATUS      current
    DESCRIPTION
            "Unique index value associated with the OCn/STM interface."
    ::= { ocnStmEntry 1 }

ocnStmIfIndex OBJECT-TYPE
    SYNTAX      InterfaceIndex
    MAX-ACCESS  read-only
    STATUS      current
    DESCRIPTION
            "This object has the same value as ifIndex for OCn/STM interface.
             An integer index value used to uniquely identify
             this OCn/STM interface."
    ::= { ocnStmEntry 2 }

ocnStmEntityIndex OBJECT-TYPE
    SYNTAX      PhysicalIndex 
    MAX-ACCESS  read-only
    STATUS      current
    DESCRIPTION
           "Entity Index from ENTITY-MIB for this OCn/STM interface."
    ::= { ocnStmEntry 3 }

ocnStmAdminState OBJECT-TYPE
    SYNTAX      AdminState 
    MAX-ACCESS  read-write
    STATUS      current
    DESCRIPTION
            "This object represents the Administrative State of the OCn/STM interface."
    ::= { ocnStmEntry 4 }

ocnStmOperationalState OBJECT-TYPE
    SYNTAX      OperationalState 
    MAX-ACCESS  read-only
    STATUS      current
    DESCRIPTION
            "This object represents the Operational State of the OCn/STM interface."
    ::= { ocnStmEntry 5 }

ocnStmSecondaryState OBJECT-TYPE
    SYNTAX      SecondaryState 
    MAX-ACCESS  read-only
    STATUS      current
    DESCRIPTION
            "This object represents the Secondary State of the OCn/STM interface."
    ::= { ocnStmEntry 6 }

ocnStmSfpVendorName OBJECT-TYPE
    SYNTAX  DisplayString (SIZE (0..16))
    MAX-ACCESS read-only
    STATUS     current
    DESCRIPTION
            "This object provides the vendor name of the SFP."
     ::= { ocnStmEntry 7 }

ocnStmSfpPartNumber OBJECT-TYPE
    SYNTAX  DisplayString (SIZE (0..16))
    MAX-ACCESS read-only
    STATUS     current
    DESCRIPTION
            "This object provides the part number of the SFP."
     ::= { ocnStmEntry 8 }

ocnStmSfpSerialNumber OBJECT-TYPE
    SYNTAX  DisplayString (SIZE (0..32)) 
    MAX-ACCESS read-only
    STATUS     current
    DESCRIPTION
            "This object provides the serial number of the SFP."
     ::= { ocnStmEntry 9 }

ocnStmSfpDateOfManufacture OBJECT-TYPE
    SYNTAX     DateAndTime 
    MAX-ACCESS read-only
    STATUS     current
    DESCRIPTION
            "This object provides the date of manufacture of the SFP."
     ::= { ocnStmEntry 10 }

ocnStmSfpConnectorValue OBJECT-TYPE
    SYNTAX     SfpConnectorValue 
    MAX-ACCESS read-only
    STATUS     current
    DESCRIPTION
            "This object provides the SFP connector value."
     ::= { ocnStmEntry 11 }

ocnStmSfpLinkLength OBJECT-TYPE
    SYNTAX     Integer32
    MAX-ACCESS read-only
    STATUS     current
    DESCRIPTION
         "This object provides the SFP Link Length."
     ::= { ocnStmEntry 12 }

ocnStmSfpLaserWaveLength OBJECT-TYPE
    SYNTAX     Integer32
    MAX-ACCESS read-only
    STATUS     current
    DESCRIPTION
         "This object provides the SFP Laser Wave Length in nano meters."
     ::= { ocnStmEntry 13 }

ocnStmSfpLaserWaveLengthPicometer OBJECT-TYPE 
    SYNTAX     Unsigned32
    MAX-ACCESS read-only
    STATUS     current
    DESCRIPTION
         "This object provide laser wavelength pico value. 
          For example, laser wavelength is 1510.01,
          then ocnStmSfpLaserWaveLength=1510 
          and ocnStmSfpLaserWaveLengthPicometer=10."
     ::= { ocnStmEntry 14 }

ocnStmSfpMediaType OBJECT-TYPE
    SYNTAX     SfpMediaType
    MAX-ACCESS read-only
    STATUS     current
    DESCRIPTION
         "This object provides the SFP Media Type."
     ::= { ocnStmEntry 15 }

ocnStmMultiplexingStructures OBJECT-TYPE
    SYNTAX     MultiplexingStructure 
    MAX-ACCESS read-write
    STATUS     current
    DESCRIPTION
            "This object provides the TDM Multiplexing Structure base on OCn/STM interface."
     ::= { ocnStmEntry 16 }

ocnStmEoTDMMode OBJECT-TYPE
    SYNTAX     EoTDMMode 
    MAX-ACCESS read-write
    STATUS     current
    DESCRIPTION
            "This object provides the TDM Mode base on OCn/STM interface. 
            EoPDH means VCG container is PDH; EoTDM means VCG container is VC of SDH/SONET"
     ::= { ocnStmEntry 17 }

ocnStmLoopbackConfig OBJECT-TYPE
    SYNTAX     CmLoopbackType
    MAX-ACCESS read-write
    STATUS     current
    DESCRIPTION
            "This object allows to initiate loopbacks on 
             on the OCn/STM interface."
     ::= { ocnStmEntry 18 }

ocnStmLoopbackStatus OBJECT-TYPE
    SYNTAX     CmLoopbackType
    MAX-ACCESS read-only
    STATUS     current
    DESCRIPTION
            "This object provides status of the current loopback 
             on the OCn/STM interface."
     ::= { ocnStmEntry 19 }

ocnStmLoopbackTime OBJECT-TYPE
    SYNTAX     Integer32 (2..300)
    MAX-ACCESS read-write
    STATUS     current
    DESCRIPTION
            "This object allows to specify time for timed-loopbacks on 
             on the OCn/STM interface."
     ::= { ocnStmEntry 20 }

ocnStmInsertingAIS OBJECT-TYPE
    SYNTAX     TruthValue
    MAX-ACCESS read-write
    STATUS     current
    DESCRIPTION
            "This object allows to insert AIS-L out from OCn/STM interface 
            when it is in maintenance state."
     ::= { ocnStmEntry 21 }

ocnStmBerExcThreshold OBJECT-TYPE
    SYNTAX     BitErrRate
    MAX-ACCESS read-write
    STATUS     current
    DESCRIPTION
            "This object provide the threshold of B2EXC."
     ::= { ocnStmEntry 22 }

ocnStmBerDegThreshold OBJECT-TYPE
    SYNTAX     BitErrRate
    MAX-ACCESS read-write
    STATUS     current
    DESCRIPTION
            "This object provides the threshold of B2DEG."
     ::= { ocnStmEntry 23 }

ocnStmRxTrailTrace OBJECT-TYPE
    SYNTAX     DisplayString (SIZE (0..128))
    MAX-ACCESS read-only
    STATUS     current
    DESCRIPTION
            "This object provides the recevied J0 on the OCn/STM interface."
     ::= { ocnStmEntry 24 }

ocnStmTxTrailTrace OBJECT-TYPE
    SYNTAX     DisplayString (SIZE (0..128))
    MAX-ACCESS read-write
    STATUS     current
    DESCRIPTION
            "This object provides the transmit J0 on the OCn/STM interface."
     ::= { ocnStmEntry 25 }

ocnStmExpectedTrailTrace OBJECT-TYPE
    SYNTAX     DisplayString (SIZE (0..128))
    MAX-ACCESS read-write
    STATUS     current
    DESCRIPTION
            "This object provides the expected J0 on the OCn/STM interface."
     ::= { ocnStmEntry 26 }

ocnStmTrailTraceFormat OBJECT-TYPE
    SYNTAX     TrailTraceFormat
    MAX-ACCESS read-write
    STATUS     current
    DESCRIPTION
            "This object provides the J0 length mode on the OCn/STM interface."
     ::= { ocnStmEntry 27 }

ocnStmQLModeEnabled OBJECT-TYPE 
    SYNTAX     TruthValue
    MAX-ACCESS read-write
    STATUS     current
    DESCRIPTION
         "This object allows to specify whether the OCn/STM interface 
          can be enabled/disabled for QL Mode. This object
          is only applicable for Synchronous OCn/STM interface,
          when ocnStmQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { ocnStmEntry 28 }

ocnStmExpectedQL OBJECT-TYPE 
    SYNTAX     SSMQualityLevel
    MAX-ACCESS read-write
    STATUS     current
    DESCRIPTION
         "This object allows to specify the expected QL when the 
          OCn/STM interface is enabled for QL Mode. This object
          is only applicable for Synchronous OCn/STM interface,
          when ocnStmQLModeEnabled is set to true.
          This object allows the user to set a minimum
          expected received Quality Level on the port. The valid values
          depend upon the SYNC entity Network Clock Type. A value of
          None represents that a minimum Quality Level is not expected. 
          The default value shall be None."
     ::= { ocnStmEntry 29 }

ocnStmAssumedQL OBJECT-TYPE 
    SYNTAX     SSMQualityLevel
    MAX-ACCESS read-write
    STATUS     current
    DESCRIPTION
         "This object allows to specify the assumed QL on the 
          OCn/STM interface. This object is only applicable for 
          Synchronous OCn/STM interface. 
          The Assumed QL is only meaningful if the Network Clock Type
          (see fsp150cm-sync.mib) is option1 and the 
          port TransmitQL Mode is disabled and the port is being used as 
          an input reference source. Under these conditions, 
          the specified QL value is assumed to be the Quality Level of the
          non-failed reference."
     ::= { ocnStmEntry 30 }

ocnStmReceivedQL OBJECT-TYPE 
    SYNTAX     SSMQualityLevel
    MAX-ACCESS read-only
    STATUS     current
    DESCRIPTION
         "This object provides the Received QL value for the OCn/STM interface. 
          If the OCn/STM interface TransmitQL Mode is disabled, then the received 
          QL value is not applicable.This object is only applicable for 
          Synchronous OCn/STM interface."
     ::= { ocnStmEntry 31 }

ocnStmTransmitQL OBJECT-TYPE 
    SYNTAX     SSMQualityLevel
    MAX-ACCESS read-only
    STATUS     current
    DESCRIPTION
         "This object provides the Transmitted QL value for the OCn/STM interface. 
          If the OCn/STM interface TransmitQL Mode is disabled, then the received 
          QL value is not applicable. This object is only applicable for 
          Synchronous OCn/STM interface."
     ::= { ocnStmEntry 32 }

ocnStmPortType OBJECT-TYPE 
    SYNTAX     OCNSTMPortType  
    MAX-ACCESS read-only
    STATUS     current
    DESCRIPTION
         "This object represents the OCN/STM Port Type.
          Determines whether the OCN/STM port operates in OC or STM mode."
     ::= { ocnStmEntry 33 }

ocnStmFreqSourceType OBJECT-TYPE 
    SYNTAX     TDMFrequencySourceType  
    MAX-ACCESS read-write
    STATUS     current
    DESCRIPTION
         "This object represents the TDM Frequency source of OCN/STM port."
     ::= { ocnStmEntry 34 }
 
ocnStmHighOrderPathType OBJECT-TYPE 
    SYNTAX     TDMPathType
    MAX-ACCESS read-write
    STATUS     current
    DESCRIPTION
         "This object provides the High Order Path Type of the OCn/STM interface."
     ::= { ocnStmEntry 35 }


--
--  OCn Path Table
--
stsVcPathTable  OBJECT-TYPE
    SYNTAX      SEQUENCE OF StsVcPathEntry
    MAX-ACCESS  not-accessible
    STATUS      current
    DESCRIPTION
            "A list of entries corresponding to OCn Path."
    ::= { cmFacilityObjects 48 }

stsVcPathEntry  OBJECT-TYPE
    SYNTAX      StsVcPathEntry
    MAX-ACCESS  not-accessible
    STATUS      current
    DESCRIPTION
            "A conceptual row in the stsVcPathTable."
    INDEX { neIndex, shelfIndex, slotIndex, ocnStmIndex,
            stsVcPathParentIfIndex, stsVcPathIndex }
    ::= { stsVcPathTable 1 }

StsVcPathEntry ::= SEQUENCE {
    stsVcPathParentIfIndex           InterfaceIndex,
    stsVcPathIndex                   Unsigned32,
    stsVcPathIfIndex                 InterfaceIndex,
    stsVcPathAdminState              AdminState,
    stsVcPathOperationalState        OperationalState,
    stsVcPathSecondaryState          SecondaryState,
    stsVcPathLoopbackConfig          CmLoopbackType,
    stsVcPathLoopbackStatus          CmLoopbackType,
    stsVcPathLoopbackTime            Integer32,
    stsVcPathInsertingAIS            TruthValue,
    stsVcPathBerExcThreshold         BitErrRate,
    stsVcPathBerDegThreshold         BitErrRate,
    stsVcPathTrailTraceFormat        TrailTraceFormat,
    stsVcPathRxTrailTrace            DisplayString,
    stsVcPathTxTrailTrace            DisplayString,
    stsVcPathExpectedTrailTrace      DisplayString,
    stsVcPathRxSignalLabel           Unsigned32,
    stsVcPathTxSignalLabel           Unsigned32,
    stsVcPathExpectedSignalLabel     Unsigned32,
    stsVcPathRowStatus               RowStatus,
    stsVcPathLowOrderPathType        TDMPathType
}

stsVcPathParentIfIndex OBJECT-TYPE
    SYNTAX      InterfaceIndex
    MAX-ACCESS  not-accessible
    STATUS      current
    DESCRIPTION
            "This object is its parent's ifindex. Based on the Multiplexing hierarchy,
             this object points to the container's interface index."
    ::= { stsVcPathEntry 1 }

stsVcPathIndex OBJECT-TYPE
    SYNTAX      Unsigned32
    MAX-ACCESS  not-accessible
    STATUS      current
    DESCRIPTION
            "This object is his index."
    ::= { stsVcPathEntry 2 }

stsVcPathIfIndex OBJECT-TYPE
    SYNTAX      InterfaceIndex
    MAX-ACCESS  read-only
    STATUS      current
    DESCRIPTION
            "This object has the same value as ifIndex for OCn Path.
             An integer index value used to uniquely identify
             this OCn Path interface."
    ::= { stsVcPathEntry 3 }

stsVcPathAdminState OBJECT-TYPE
    SYNTAX      AdminState 
    MAX-ACCESS  read-write
    STATUS      current
    DESCRIPTION
            "This object represents the Administrative State of the OCn Path."
    ::= { stsVcPathEntry 4 }

stsVcPathOperationalState OBJECT-TYPE
    SYNTAX      OperationalState 
    MAX-ACCESS  read-only
    STATUS      current
    DESCRIPTION
            "This object represents the Operational State of the OCn Path."
    ::= { stsVcPathEntry 5 }

stsVcPathSecondaryState OBJECT-TYPE
    SYNTAX      SecondaryState 
    MAX-ACCESS  read-only
    STATUS      current
    DESCRIPTION
            "This object represents the Secondary State of the OCn Path."
    ::= { stsVcPathEntry 6 }

stsVcPathLoopbackConfig OBJECT-TYPE
    SYNTAX     CmLoopbackType
    MAX-ACCESS read-write
    STATUS     current
    DESCRIPTION
            "This object allows to initiate loopbacks on 
             on the OCn Path."
     ::= { stsVcPathEntry 7 }

stsVcPathLoopbackStatus OBJECT-TYPE
    SYNTAX     CmLoopbackType
    MAX-ACCESS read-only
    STATUS     current
    DESCRIPTION
            "This object provides status of the current loopback 
             on the OCn Path."
     ::= { stsVcPathEntry 8 }

stsVcPathLoopbackTime OBJECT-TYPE
    SYNTAX     Integer32 (2..300)
    MAX-ACCESS read-write
    STATUS     current
    DESCRIPTION
            "This object allows to specify time for timed-loopbacks on 
             on the OCn Path."
     ::= { stsVcPathEntry 9 }

stsVcPathInsertingAIS OBJECT-TYPE
    SYNTAX     TruthValue
    MAX-ACCESS read-write
    STATUS     current
    DESCRIPTION
            "This object allows to insert AIS-P out from OCn Path 
            when it is in maintenance state."
     ::= { stsVcPathEntry 10 }

stsVcPathBerExcThreshold OBJECT-TYPE
    SYNTAX     BitErrRate
    MAX-ACCESS read-write
    STATUS     current
    DESCRIPTION
            "This object provide the threshold of B3EXC."
     ::= { stsVcPathEntry 11 }

stsVcPathBerDegThreshold OBJECT-TYPE
    SYNTAX     BitErrRate
    MAX-ACCESS read-write
    STATUS     current
    DESCRIPTION
            "This object provides the threshold of B3DEG."
     ::= { stsVcPathEntry 12 }

stsVcPathTrailTraceFormat OBJECT-TYPE
    SYNTAX     TrailTraceFormat
    MAX-ACCESS read-write
    STATUS     current
    DESCRIPTION
            "This object provides the J1 length mode on the OCn Path."
     ::= { stsVcPathEntry 13 }

stsVcPathRxTrailTrace OBJECT-TYPE
    SYNTAX     DisplayString (SIZE (0..128))
    MAX-ACCESS read-only
    STATUS     current
    DESCRIPTION
            "This object provides the recevied J1 on the OCn Path."
     ::= { stsVcPathEntry 14 }

stsVcPathTxTrailTrace OBJECT-TYPE
    SYNTAX     DisplayString (SIZE (0..128))
    MAX-ACCESS read-write
    STATUS     current
    DESCRIPTION
            "This object provides the transmit J1 on the OCn Path."
     ::= { stsVcPathEntry 15 }

stsVcPathExpectedTrailTrace OBJECT-TYPE
    SYNTAX     DisplayString (SIZE (0..128))
    MAX-ACCESS read-write
    STATUS     current
    DESCRIPTION
            "This object provides the expected J1 on the OCn Path."
     ::= { stsVcPathEntry 16 }

stsVcPathRxSignalLabel OBJECT-TYPE
    SYNTAX     Unsigned32 (0..255)
    MAX-ACCESS read-only
    STATUS     current
    DESCRIPTION
            "This object provides the recevied C2 on the OCn Path."
     ::= { stsVcPathEntry 17 }

stsVcPathTxSignalLabel OBJECT-TYPE
    SYNTAX     Unsigned32 (0..255)
    MAX-ACCESS read-write
    STATUS     current
    DESCRIPTION
            "This object provides the transmit C2 on the OCn Path."
     ::= { stsVcPathEntry 18 }

stsVcPathExpectedSignalLabel OBJECT-TYPE
    SYNTAX     Unsigned32 (0..255)
    MAX-ACCESS read-write
    STATUS     current
    DESCRIPTION
            "This object provides the expected C2 on the OCn Path."
     ::= { stsVcPathEntry 19 }

stsVcPathRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of stsVcPathRowStatus supported are
            createAndGo(4) and destroy(6).  All mandatory attributes
            must be specified in a single SNMP SET request with
            stsVcPathRowStatus value as createAndGo(4).
            Upon successful row creation, this object has a
            value of active(1).

            The stsVcPathRowStatus object may be modified if
            the associated instance of this object is equal to active(1)."
    ::= { stsVcPathEntry 20 }

stsVcPathLowOrderPathType OBJECT-TYPE 
    SYNTAX     TDMPathType
    MAX-ACCESS read-write
    STATUS     current
    DESCRIPTION
         "This object provides the low Order Path Type of the sts vc interface."
     ::= { stsVcPathEntry 21 }


--
--  VT/VC Table
--
vtVcPathTable  OBJECT-TYPE
    SYNTAX      SEQUENCE OF VtVcPathEntry
    MAX-ACCESS  not-accessible
    STATUS      current
    DESCRIPTION
            "A list of entries corresponding to VT1.5/VC12. These represent the
             lower order path (LOP) entities."
    ::= { cmFacilityObjects 49 }

vtVcPathEntry  OBJECT-TYPE
    SYNTAX      VtVcPathEntry
    MAX-ACCESS  not-accessible
    STATUS      current
    DESCRIPTION
            "A conceptual row in the vtVcPathTable."
    INDEX { neIndex, shelfIndex, slotIndex, ocnStmIndex, 
            vtVcPathParentIfIndex, vtVcPathIndex }
    ::= { vtVcPathTable 1 }

VtVcPathEntry ::= SEQUENCE {
    vtVcPathParentIfIndex           InterfaceIndex,
    vtVcPathIndex                   Unsigned32,
    vtVcPathIfIndex                 InterfaceIndex,
    vtVcPathAdminState              AdminState,
    vtVcPathOperationalState        OperationalState,
    vtVcPathSecondaryState          SecondaryState,
    vtVcPathLoopbackConfig          CmLoopbackType,
    vtVcPathLoopbackStatus          CmLoopbackType,
    vtVcPathLoopbackTime            Integer32,
    vtVcPathInsertingAIS            TruthValue,
    vtVcPathBerExcThreshold         BitErrRate,
    vtVcPathBerDegThreshold         BitErrRate,
    vtVcPathTrailTraceFormat        TrailTraceFormat,
    vtVcPathRxTrailTrace            DisplayString,
    vtVcPathTxTrailTrace            DisplayString,
    vtVcPathExpectedTrailTrace      DisplayString,
    vtVcPathRxSignalLabel           Unsigned32,
    vtVcPathTxSignalLabel           Unsigned32,
    vtVcPathExpectedSignalLabel     Unsigned32,
    vtVcPathRowStatus               RowStatus
}

vtVcPathParentIfIndex OBJECT-TYPE
    SYNTAX      InterfaceIndex
    MAX-ACCESS  not-accessible
    STATUS      current
    DESCRIPTION
            "This object is its parent's ifindex."
    ::= { vtVcPathEntry 1 }

vtVcPathIndex OBJECT-TYPE
    SYNTAX      Unsigned32
    MAX-ACCESS  not-accessible
    STATUS      current
    DESCRIPTION
            "This object represents the unique number of the Path within the
             parent container represented by vtvcPathParentIfIndex."
    ::= { vtVcPathEntry 2 }

vtVcPathIfIndex OBJECT-TYPE
    SYNTAX      InterfaceIndex
    MAX-ACCESS  read-only
    STATUS      current
    DESCRIPTION
            "This object has the same value as ifIndex for OCn VT1.5/VC12.
             An integer index value used to uniquely identify
             this OCn VT1.5/VC12 interface."
    ::= { vtVcPathEntry 3 }

vtVcPathAdminState OBJECT-TYPE
    SYNTAX      AdminState 
    MAX-ACCESS  read-write
    STATUS      current
    DESCRIPTION
            "This object represents the Administrative State of the OCn VT1.5/VC12."
    ::= { vtVcPathEntry 4 }

vtVcPathOperationalState OBJECT-TYPE
    SYNTAX      OperationalState 
    MAX-ACCESS  read-only
    STATUS      current
    DESCRIPTION
            "This object represents the Operational State of the OCn VT1.5/VC12."
    ::= { vtVcPathEntry 5 }

vtVcPathSecondaryState OBJECT-TYPE
    SYNTAX      SecondaryState 
    MAX-ACCESS  read-only
    STATUS      current
    DESCRIPTION
            "This object represents the Secondary State of the OCn VT1.5/VC12."
    ::= { vtVcPathEntry 6 }

vtVcPathLoopbackConfig OBJECT-TYPE
    SYNTAX     CmLoopbackType
    MAX-ACCESS read-write
    STATUS     current
    DESCRIPTION
            "This object allows to initiate loopbacks on 
             on the OCn VT1.5/VC12."
     ::= { vtVcPathEntry 7 }

vtVcPathLoopbackStatus OBJECT-TYPE
    SYNTAX     CmLoopbackType
    MAX-ACCESS read-only
    STATUS     current
    DESCRIPTION
            "This object provides status of the current loopback 
             on the OCn VT1.5/VC12."
     ::= { vtVcPathEntry 8 }

vtVcPathLoopbackTime OBJECT-TYPE
    SYNTAX     Integer32 (2..300)
    MAX-ACCESS read-write
    STATUS     current
    DESCRIPTION
            "This object allows to specify time for timed-loopbacks on 
             on the OCn VT1.5/VC12."
     ::= { vtVcPathEntry 9 }

vtVcPathInsertingAIS OBJECT-TYPE
    SYNTAX     TruthValue
    MAX-ACCESS read-write
    STATUS     current
    DESCRIPTION
            "This object allows to insert AIS-P out from OCn VT1.5/VC12 
            when it is in maintenance state."
     ::= { vtVcPathEntry 10 }

vtVcPathBerExcThreshold OBJECT-TYPE
    SYNTAX     BitErrRate
    MAX-ACCESS read-write
    STATUS     current
    DESCRIPTION
            "This object provide the threshold of BEREXC."
     ::= { vtVcPathEntry 11 }

vtVcPathBerDegThreshold OBJECT-TYPE
    SYNTAX     BitErrRate
    MAX-ACCESS read-write
    STATUS     current
    DESCRIPTION
            "This object provides the threshold of BERDEG."
     ::= { vtVcPathEntry 12 }

vtVcPathTrailTraceFormat OBJECT-TYPE
    SYNTAX     TrailTraceFormat
    MAX-ACCESS read-only
    STATUS     current
    DESCRIPTION
            "This object provides the J2 length mode on the OCn VT1.5/VC12."
     ::= { vtVcPathEntry 13 }

vtVcPathRxTrailTrace OBJECT-TYPE
    SYNTAX     DisplayString (SIZE (0..128))
    MAX-ACCESS read-only
    STATUS     current
    DESCRIPTION
            "This object provides the recevied J2 on the OCn VT1.5/VC12."
     ::= { vtVcPathEntry 14 }

vtVcPathTxTrailTrace OBJECT-TYPE
    SYNTAX     DisplayString (SIZE (0..128))
    MAX-ACCESS read-write
    STATUS     current
    DESCRIPTION
            "This object provides the transmit J2 on the OCn VT1.5/VC12."
     ::= { vtVcPathEntry 15 }

vtVcPathExpectedTrailTrace OBJECT-TYPE
    SYNTAX     DisplayString (SIZE (0..128))
    MAX-ACCESS read-write
    STATUS     current
    DESCRIPTION
            "This object provides the expected J2 on the OCn VT1.5/VC12."
     ::= { vtVcPathEntry 16 }

vtVcPathRxSignalLabel OBJECT-TYPE
    SYNTAX     Unsigned32 (0..7)
    MAX-ACCESS read-only
    STATUS     current
    DESCRIPTION
            "This object provides the recevied V5 byte(b5-b7) on the OCn VT1.5/VC12."
     ::= { vtVcPathEntry 17 }

vtVcPathTxSignalLabel OBJECT-TYPE
    SYNTAX     Unsigned32 (0..7)
    MAX-ACCESS read-write
    STATUS     current
    DESCRIPTION
            "This object provides the transmit V5 byte(b5-b7) on the OCn VT1.5/VC12."
     ::= { vtVcPathEntry 18 }

vtVcPathExpectedSignalLabel OBJECT-TYPE
    SYNTAX     Unsigned32 (0..7)
    MAX-ACCESS read-write
    STATUS     current
    DESCRIPTION
            "This object provides the expected V5 byte(b5-b7) on the OCn VT1.5/VC12."
     ::= { vtVcPathEntry 19 }

vtVcPathRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of vtVcPathRowStatus supported are
            createAndGo(4) and destroy(6).  All mandatory attributes
            must be specified in a single SNMP SET request with
            vtVcPathRowStatus value as createAndGo(4).
            Upon successful row creation, this object has a
            value of active(1).

            The vtVcPathRowStatus object may be modified if
            the associated instance of this object is equal to active(1)."
    ::= { vtVcPathEntry 20 }

--
--  OCn E1T1 Table
--
e1t1Table  OBJECT-TYPE
    SYNTAX      SEQUENCE OF E1T1Entry
    MAX-ACCESS  not-accessible
    STATUS      current
    DESCRIPTION
            "A list of entries corresponding to E1/T1."
    ::= { cmFacilityObjects 50 }

e1t1Entry  OBJECT-TYPE
    SYNTAX      E1T1Entry
    MAX-ACCESS  not-accessible
    STATUS      current
    DESCRIPTION
            "A conceptual row in the e1t1Table."
    INDEX { neIndex, shelfIndex, slotIndex,
            e1t1ParentIfIndex, e1t1Index }
    ::= { e1t1Table 1 }

E1T1Entry ::= SEQUENCE {
    e1t1ParentIfIndex           InterfaceIndex,
    e1t1Index                   Unsigned32,
    e1t1IfIndex                 InterfaceIndex,
    e1t1EntityIndex             PhysicalIndex,
    e1t1AdminState              AdminState,
    e1t1OperationalState        OperationalState,
    e1t1SecondaryState          SecondaryState,
    e1t1LoopbackConfig          CmLoopbackType,
    e1t1LoopbackStatus          CmLoopbackType,
    e1t1LoopbackTime            Integer32,
    e1t1RemoteLoopbackRequest   TruthValue,
    e1t1InsertingAIS            TruthValue,
    e1t1RowStatus               RowStatus,
    e1t1LineType                E1T1LineType,
    e1t1LineCode                E1T1LineCode,
    e1t1FrameFormat             E1T1FrameFormat,
    e1t1LineBuildOut            LineBuildOut,
    e1t1TimingDomain            VariablePointer,
    e1t1RcvSensitivity          E1T1RcvSensitivity,
    e1t1IdlePatternProfile      VariablePointer,
    e1t1LoopbackProfile         VariablePointer,
    e1t1RelatedContainerId      VariablePointer
}

e1t1ParentIfIndex OBJECT-TYPE
    SYNTAX      InterfaceIndex
    MAX-ACCESS  not-accessible
    STATUS      current
    DESCRIPTION
            "This object represents the parent (container) object's interface index.
             In the case when parent of E1T1Entry does not have a InterfaceIndex 
             then the e1t1ParentIfIndex shall have the value of 2147483647,
             e.g. if parent of E1T1Entry is a card represented in pseudoWireE1T1CardTable."
    ::= { e1t1Entry 1 }

e1t1Index OBJECT-TYPE
    SYNTAX      Unsigned32
    MAX-ACCESS  not-accessible
    STATUS      current
    DESCRIPTION
            "Index value used to uniquely identify
             this E1/T1 interface, within the parent container specified by
             e1t1ParentIfIndex."
    ::= { e1t1Entry 2 }

e1t1IfIndex OBJECT-TYPE
    SYNTAX      InterfaceIndex
    MAX-ACCESS  read-only
    STATUS      current
    DESCRIPTION
            "This object has the same value as ifIndex for E1/T1.
             An integer index value used to uniquely identify
             this E1/T1 interface."
    ::= { e1t1Entry 3 }

e1t1EntityIndex OBJECT-TYPE
    SYNTAX      PhysicalIndex 
    MAX-ACCESS  read-only
    STATUS      current
    DESCRIPTION
           "Entity Index from ENTITY-MIB for this port."
    ::= { e1t1Entry 4 }

e1t1AdminState OBJECT-TYPE
    SYNTAX      AdminState 
    MAX-ACCESS  read-write
    STATUS      current
    DESCRIPTION
            "This object represents the Administrative State of the E1/T1."
    ::= { e1t1Entry 5 }

e1t1OperationalState OBJECT-TYPE
    SYNTAX      OperationalState 
    MAX-ACCESS  read-only
    STATUS      current
    DESCRIPTION
            "This object represents the Operational State of the E1/T1."
    ::= { e1t1Entry 6 }

e1t1SecondaryState OBJECT-TYPE
    SYNTAX      SecondaryState 
    MAX-ACCESS  read-only
    STATUS      current
    DESCRIPTION
            "This object represents the Secondary State of the E1/T1."
    ::= { e1t1Entry 7 }

e1t1LoopbackConfig OBJECT-TYPE
    SYNTAX     CmLoopbackType
    MAX-ACCESS read-write
    STATUS     current
    DESCRIPTION
            "This object allows to initiate loopbacks on 
             on the E1/T1."
     ::= { e1t1Entry 8 }

e1t1LoopbackStatus OBJECT-TYPE
    SYNTAX     CmLoopbackType
    MAX-ACCESS read-only
    STATUS     current
    DESCRIPTION
            "This object provides status of the current loopback 
             on the E1/T1."
     ::= { e1t1Entry 9 }

e1t1LoopbackTime OBJECT-TYPE
    SYNTAX     Integer32 (2..300)
    MAX-ACCESS read-write
    STATUS     current
    DESCRIPTION
            "This object allows to specify time for timed-loopbacks on 
             on the E1/T1."
     ::= { e1t1Entry 10 }

e1t1RemoteLoopbackRequest OBJECT-TYPE
    SYNTAX     TruthValue
    MAX-ACCESS read-write
    STATUS     current
    DESCRIPTION
            "This object allows to specify to repond the remote loopback request or not."
     ::= { e1t1Entry 11 }

e1t1InsertingAIS OBJECT-TYPE
    SYNTAX     TruthValue
    MAX-ACCESS read-write
    STATUS     current
    DESCRIPTION
            "This object allows to insert AIS out from E1/T1 
            when it is in maintenance state."
     ::= { e1t1Entry 12 }

e1t1RowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of e1t1RowStatus supported are
            createAndGo(4) and destroy(6).  All mandatory attributes
            must be specified in a single SNMP SET request with
            e1t1RowStatus value as createAndGo(4).
            Upon successful row creation, this object has a
            value of active(1).

            The e1t1RowStatus object may be modified if
            the associated instance of this object is equal to active(1)."
    ::= { e1t1Entry 13 }

e1t1LineType OBJECT-TYPE
    SYNTAX      E1T1LineType
    MAX-ACCESS  read-only
    STATUS      current
    DESCRIPTION
            "This object represents the E1/T1 Line Type.
             Determines whether the E1/T1 interface operates in T1 or E1 mode."
    ::= { e1t1Entry 14 }

e1t1LineCode OBJECT-TYPE
    SYNTAX      E1T1LineCode
    MAX-ACCESS  read-write
    STATUS      current
    DESCRIPTION
            "This object represents the E1/T1 Port Line Code.
             When the port is configured for a Line Type of T1, 
             the valid values are t1-b8zs and t1-ami and the default value
             is t1-b8zs. When the port is configured for a Line Type of E1, 
             the valid values are e1-hdb3 and e1-ami and the default value 
             is e1-hdb3."
    ::= { e1t1Entry 15 }

e1t1FrameFormat OBJECT-TYPE
    SYNTAX      E1T1FrameFormat
    MAX-ACCESS  read-write
    STATUS      current
    DESCRIPTION
            "This object represents the E1/T1 Port Frame Format.
             When the port is configured for a Line Type of T1, the
             valid values are t1-sf, t1-esf and t1-unframed and the default 
             value is t1-unframed.
             When the port is configured for a Line Type of E1, the
             valid values are e1-unframed, e1-crc4, and e1-dualFrame 
             and the default value is e1-crc4. 

             R5.4CC supports only t1-unframed for T1 Line type."
    ::= { e1t1Entry 16 }

e1t1LineBuildOut OBJECT-TYPE
    SYNTAX      LineBuildOut
    MAX-ACCESS  read-write
    STATUS      current
    DESCRIPTION
            "This object represents Line Build Out on E1/T1 port."

    ::= { e1t1Entry 17 }

e1t1TimingDomain OBJECT-TYPE
    SYNTAX      VariablePointer
    MAX-ACCESS  read-write
    STATUS      current
    DESCRIPTION
         "This object represents Timing Domain that the E1/T1 interface uses as 
          timing source.  The Timing Domain is a Synchronization Entity 
          represented by an object in the f3SyncTable"
    ::= { e1t1Entry 18 }

e1t1RcvSensitivity OBJECT-TYPE
    SYNTAX      E1T1RcvSensitivity
    MAX-ACCESS  read-write
    STATUS      current
    DESCRIPTION
         "This object allows configuring the reciever sensitivity based on expected
          signal strength"
    ::= { e1t1Entry 19 }

e1t1IdlePatternProfile OBJECT-TYPE
    SYNTAX      VariablePointer
    MAX-ACCESS  read-write
    STATUS      current
    DESCRIPTION
         "This object allows selecting Idle Pattern Profile for the E1/T1 interface.
          Idle Patter Profile is represented by an object in the 
          f3Pwe3IdlePatternProfileTable"
    ::= { e1t1Entry 20 }

e1t1LoopbackProfile OBJECT-TYPE
    SYNTAX      VariablePointer
    MAX-ACCESS  read-write
    STATUS      current
    DESCRIPTION
         "This object allows selecting Loopback Profile for the E1/T1 interface.
          Loopback Profile is represented by an object in the 
          f3Pwe3LoopbackProfileTable"
    ::= { e1t1Entry 21 }

e1t1RelatedContainerId OBJECT-TYPE
    SYNTAX      VariablePointer
    MAX-ACCESS  read-only
    STATUS      current
    DESCRIPTION
         "This object describes the related container VCG."
    ::= { e1t1Entry 22 }

--
--  OCn E3T3 Table
--
E3T3Type ::= TEXTUAL-CONVENTION
    STATUS       current
    DESCRIPTION
        "Describes the type of the E3/T3."
    SYNTAX       INTEGER {
                   none (0),
                   e3 (1),
                   t3 (2)
                 }

e3t3Table  OBJECT-TYPE
    SYNTAX      SEQUENCE OF E3T3Entry
    MAX-ACCESS  not-accessible
    STATUS      current
    DESCRIPTION
            "A list of entries corresponding to E3/T3."
    ::= { cmFacilityObjects 51 }

e3t3Entry  OBJECT-TYPE
    SYNTAX      E3T3Entry
    MAX-ACCESS  not-accessible
    STATUS      current
    DESCRIPTION
            "A conceptual row in the e3t3Table."
    INDEX { neIndex, shelfIndex, slotIndex, 
            e3t3ParentIfIndex, e3t3Index }
    ::= { e3t3Table 1 }

E3T3Entry ::= SEQUENCE {
    e3t3ParentIfIndex           InterfaceIndex,
    e3t3Index                   Unsigned32,
    e3t3IfIndex                 InterfaceIndex,
    e3t3EntityIndex             PhysicalIndex,
    e3t3AdminState              AdminState,
    e3t3OperationalState        OperationalState,
    e3t3SecondaryState          SecondaryState,
    e3t3LoopbackConfig          CmLoopbackType,
    e3t3LoopbackStatus          CmLoopbackType,
    e3t3LoopbackTime            Integer32,
    e3t3RemoteLoopbackRequest   TruthValue,
    e3t3InsertingAIS            TruthValue,
    e3t3CBitEnable              TruthValue,
    e3t3T3Channelized           TruthValue,
    e3t3RowStatus               RowStatus,
    e3t3FrameFormat             E3T3FrameFormat,
    e3t3RelatedContainerId      VariablePointer
}

e3t3ParentIfIndex OBJECT-TYPE
    SYNTAX      InterfaceIndex
    MAX-ACCESS  not-accessible
    STATUS      current
    DESCRIPTION
            "This object is its parent's ifindex."
    ::= { e3t3Entry 1 }

e3t3Index OBJECT-TYPE
    SYNTAX      Unsigned32
    MAX-ACCESS  not-accessible
    STATUS      current
    DESCRIPTION
            "This object is his index."
    ::= { e3t3Entry 2 }

e3t3IfIndex OBJECT-TYPE
    SYNTAX      InterfaceIndex
    MAX-ACCESS  read-only
    STATUS      current
    DESCRIPTION
            "This object has the same value as ifIndex for E3/T3.
             An integer index value used to uniquely identify
             this E3/T3 interface."
    ::= { e3t3Entry 3 }

e3t3EntityIndex OBJECT-TYPE
    SYNTAX      PhysicalIndex 
    MAX-ACCESS  read-only
    STATUS      current
    DESCRIPTION
           "Entity Index from ENTITY-MIB for this port."
    ::= { e3t3Entry 4 }

e3t3AdminState OBJECT-TYPE
    SYNTAX      AdminState 
    MAX-ACCESS  read-write
    STATUS      current
    DESCRIPTION
            "This object represents the Administrative State of the E3/T3."
    ::= { e3t3Entry 5 }

e3t3OperationalState OBJECT-TYPE
    SYNTAX      OperationalState 
    MAX-ACCESS  read-only
    STATUS      current
    DESCRIPTION
            "This object represents the Operational State of the E3/T3."
    ::= { e3t3Entry 6 }

e3t3SecondaryState OBJECT-TYPE
    SYNTAX      SecondaryState 
    MAX-ACCESS  read-only
    STATUS      current
    DESCRIPTION
            "This object represents the Secondary State of the E3/T3."
    ::= { e3t3Entry 7 }

e3t3LoopbackConfig OBJECT-TYPE
    SYNTAX     CmLoopbackType
    MAX-ACCESS read-write
    STATUS     current
    DESCRIPTION
            "This object allows to initiate loopbacks on 
             on the E3/T3."
     ::= { e3t3Entry 8 }

e3t3LoopbackStatus OBJECT-TYPE
    SYNTAX     CmLoopbackType
    MAX-ACCESS read-only
    STATUS     current
    DESCRIPTION
            "This object provides status of the current loopback 
             on the E3/T3."
     ::= { e3t3Entry 9 }

e3t3LoopbackTime OBJECT-TYPE
    SYNTAX     Integer32 (2..300)
    MAX-ACCESS read-write
    STATUS     current
    DESCRIPTION
            "This object allows to specify time for timed-loopbacks on 
             on the E3/T3."
     ::= { e3t3Entry 10 }

e3t3RemoteLoopbackRequest OBJECT-TYPE
    SYNTAX     TruthValue
    MAX-ACCESS read-write
    STATUS     current
    DESCRIPTION
            "This object allows to specify to repond the remote loopback request or not."
     ::= { e3t3Entry 11 }

e3t3InsertingAIS OBJECT-TYPE
    SYNTAX     TruthValue
    MAX-ACCESS read-write
    STATUS     current
    DESCRIPTION
            "This object allows to insert AIS out from E3/T3 
            when it is in maintenance state."
     ::= { e3t3Entry 12 }

e3t3CBitEnable OBJECT-TYPE
    SYNTAX     TruthValue
    MAX-ACCESS read-write
    STATUS     current
    DESCRIPTION
            "The object provides whether C-Bit Parity is enabled/disabled."
     ::= { e3t3Entry 13 }

e3t3T3Channelized OBJECT-TYPE
    SYNTAX     TruthValue
    MAX-ACCESS read-write
    STATUS     current
    DESCRIPTION
            "The object provides whether the T3 tunnel is channlized with T1."
     ::= { e3t3Entry 14 }

e3t3RowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of e3t3RowStatus supported are
            createAndGo(4) and destroy(6).  All mandatory attributes
            must be specified in a single SNMP SET request with
            e3t3RowStatus value as createAndGo(4).
            Upon successful row creation, this object has a
            value of active(1).

            The e3t3RowStatus object may be modified if
            the associated instance of this object is equal to active(1)."
    ::= { e3t3Entry 15 }

e3t3FrameFormat OBJECT-TYPE
    SYNTAX     E3T3FrameFormat
    MAX-ACCESS read-write
    STATUS     current
    DESCRIPTION
            "This object represents the Frame Format of the E3/T3."
     ::= { e3t3Entry 16 }

e3t3RelatedContainerId OBJECT-TYPE
    SYNTAX      VariablePointer
    MAX-ACCESS  read-only
    STATUS      current
    DESCRIPTION
         "This object describe the related contained VCG."
    ::= { e3t3Entry 17 }

--
-- traffic port extense Table
--
cmEthernetTrafficPortExtTable OBJECT-TYPE
    SYNTAX      SEQUENCE OF CmEthernetTrafficPortExtEntry
    MAX-ACCESS  not-accessible
    STATUS      current
    DESCRIPTION
            "A list of entries corresponding to Ethernet 
            Facilities for configuration purposes."
    ::= { cmFacilityObjects 52 }

cmEthernetTrafficPortExtEntry OBJECT-TYPE
    SYNTAX      CmEthernetTrafficPortExtEntry
    MAX-ACCESS  not-accessible
    STATUS      current
    DESCRIPTION
            "A conceptual row in the cmEthernetTrafficPortExtTable."
    AUGMENTS { cmEthernetTrafficPortEntry }
    ::= { cmEthernetTrafficPortExtTable 1 }

CmEthernetTrafficPortExtEntry ::= SEQUENCE {
    cmEthernetTrafficPortTDMEncapsulation       GFPEncapsulationType,
    cmEthernetTrafficPortRelatedVCG             VariablePointer
}

cmEthernetTrafficPortTDMEncapsulation OBJECT-TYPE 
    SYNTAX     GFPEncapsulationType
    MAX-ACCESS read-write
    STATUS     current
    DESCRIPTION
         "This object describes the GFP Encapsulation type of the traffic port."
     ::= { cmEthernetTrafficPortExtEntry 1 }

cmEthernetTrafficPortRelatedVCG OBJECT-TYPE 
    SYNTAX     VariablePointer
    MAX-ACCESS read-only
    STATUS     current
    DESCRIPTION
         "This object describes the related VCG of the traffic port."
     ::= { cmEthernetTrafficPortExtEntry 2 }

--
--  Time Of Day Port 
--
f3PulsePerSecondPortTable OBJECT-TYPE
    SYNTAX      SEQUENCE OF F3PulsePerSecondPortEntry 
    MAX-ACCESS  not-accessible
    STATUS      current
    DESCRIPTION
            "A list of entries corresponding to Pulse Per Second 
             Port Facilities."
    ::= { cmFacilityObjects 53 }

f3PulsePerSecondPortEntry OBJECT-TYPE
    SYNTAX      F3PulsePerSecondPortEntry 
    MAX-ACCESS  not-accessible
    STATUS      current
    DESCRIPTION
            "A conceptual row in the f3PulsePerSecondPortTable."
    INDEX { neIndex, shelfIndex, slotIndex, f3PulsePerSecondPortIndex }
    ::= { f3PulsePerSecondPortTable 1 }

F3PulsePerSecondPortEntry ::= SEQUENCE {
    -- Port Indices 
    f3PulsePerSecondPortIndex                  Integer32,
    f3PulsePerSecondPortIfIndex                InterfaceIndex,
    f3PulsePerSecondPortEntityIndex            PhysicalIndex,

    -- State Management params
    f3PulsePerSecondPortAdminState             AdminState,
    f3PulsePerSecondPortOperationalState       OperationalState,
    f3PulsePerSecondPortSecondaryState         SecondaryState,

    -- port specific params
    f3PulsePerSecondPortSquelchControl         SquelchControl,
    f3PulsePerSecondPortSquelchQL              SSMQualityLevel,

    f3PulsePerSecondPortTODSource              VariablePointer,
    f3PulsePerSecondPortDirection              SignalDirectionType,
    f3PulsePerSecondPortInputRate              PPSInputRate,
    f3PulsePerSecondPortDelayCompensation      Integer32,
    f3PulsePerSecondPortClockClass             Unsigned32,
    f3PulsePerSecondPortClockAccuracy          Unsigned32,
    f3PulsePerSecondPortTimeSource             TimeSource
}
    
f3PulsePerSecondPortIndex OBJECT-TYPE
    SYNTAX      Integer32 (1..65535)
    MAX-ACCESS  not-accessible
    STATUS      current
    DESCRIPTION
         "An integer index value used to uniquely identify
          this Pulse Per Second Port within the card." 
    ::= { f3PulsePerSecondPortEntry 1 }

f3PulsePerSecondPortIfIndex OBJECT-TYPE
    SYNTAX      InterfaceIndex
    MAX-ACCESS  read-only
    STATUS      current
    DESCRIPTION
         "This object has the same value as ifIndex for 
          Pulse Per Second Port.  An integer index value used to 
          uniquely identify this Pulse Per Second Port."
    ::= { f3PulsePerSecondPortEntry 2 }

f3PulsePerSecondPortEntityIndex OBJECT-TYPE
    SYNTAX      PhysicalIndex 
    MAX-ACCESS  read-only
    STATUS      current
    DESCRIPTION
           "Entity Index from ENTITY-MIB for this port."
    ::= { f3PulsePerSecondPortEntry 3 }

-- State Management params
f3PulsePerSecondPortAdminState OBJECT-TYPE
    SYNTAX      AdminState 
    MAX-ACCESS  read-write
    STATUS      current
    DESCRIPTION
            "This object represents the Administrative State of the Pulse Per Second 
             Port."
    ::= { f3PulsePerSecondPortEntry 4 }

f3PulsePerSecondPortOperationalState OBJECT-TYPE
    SYNTAX      OperationalState 
    MAX-ACCESS  read-only
    STATUS      current
    DESCRIPTION
            "This object represents the Operational State of the Pulse Per Second 
             Port."
    ::= { f3PulsePerSecondPortEntry 5 }

f3PulsePerSecondPortSecondaryState OBJECT-TYPE
    SYNTAX      SecondaryState 
    MAX-ACCESS  read-only
    STATUS      current
    DESCRIPTION
            "This object represents the Secondary State of the Pulse Per Second 
             Port."
    ::= { f3PulsePerSecondPortEntry 6 }

f3PulsePerSecondPortSquelchControl  OBJECT-TYPE 
    SYNTAX     SquelchControl
    MAX-ACCESS read-write
    STATUS     current
    DESCRIPTION
         "This object allows to set the Squelch Control for the Pulse Per Second port. 
          The Squelch Control is used to determine the type of squelch control 
          used to squelch the output of the TOD port."
     ::= { f3PulsePerSecondPortEntry 7 }

f3PulsePerSecondPortSquelchQL OBJECT-TYPE 
    SYNTAX     SSMQualityLevel
    MAX-ACCESS read-write
    STATUS     current
    DESCRIPTION
         "This object allows to set the Squelch QL for the Pulse Per Second port. 
          This value is used when f3PulsePerSecondPortSquelchControl is squelch-ql.
          The Squelch QL is used to determine whether or not to squelch 
          the output of the TOD port. If the system's QL is lower 
          than the Squelch QL, the output is squelched."
     ::= { f3PulsePerSecondPortEntry 8 }

f3PulsePerSecondPortTODSource OBJECT-TYPE 
    SYNTAX     VariablePointer
    MAX-ACCESS read-write
    STATUS     current
    DESCRIPTION
         "This object allows to set the Pulse Per Second Source for the Port." 
     ::= { f3PulsePerSecondPortEntry 9 }

f3PulsePerSecondPortDirection OBJECT-TYPE
    SYNTAX      SignalDirectionType 
    MAX-ACCESS  read-write
    STATUS      current
    DESCRIPTION
            "This object allows specification of the signal type 
             (i.e. input or output)."
    ::= { f3PulsePerSecondPortEntry 10 }

f3PulsePerSecondPortInputRate OBJECT-TYPE
    SYNTAX      PPSInputRate 
    MAX-ACCESS  read-write
    STATUS      current
    DESCRIPTION
            "This object allows specification of the PPS Input Rate." 
    ::= { f3PulsePerSecondPortEntry 11 }

f3PulsePerSecondPortDelayCompensation OBJECT-TYPE
    SYNTAX      Integer32 (0..90)
    MAX-ACCESS  read-write
    STATUS      current
    DESCRIPTION
            "This object allows specification of the PPS external Delay
             Compensation in nanoseconds. The valid values are 0 to 96 in 
             8 nanoseconds steps. Values which are not multiple of 8 will
             be automatically rounded up to the next multiple of 8." 
    ::= { f3PulsePerSecondPortEntry 12 }

f3PulsePerSecondPortClockClass OBJECT-TYPE
    SYNTAX      Unsigned32
    MAX-ACCESS  read-only
    STATUS      current
    DESCRIPTION
           "This object specify PPS port clock class."
    ::= { f3PulsePerSecondPortEntry 13 }

f3PulsePerSecondPortClockAccuracy OBJECT-TYPE
    SYNTAX      Unsigned32
    MAX-ACCESS  read-only
    STATUS      current
    DESCRIPTION
           "This object specify PPS port clock accuracy."
    ::= { f3PulsePerSecondPortEntry 14 }

f3PulsePerSecondPortTimeSource OBJECT-TYPE
    SYNTAX      TimeSource
    MAX-ACCESS  read-only
    STATUS      current
    DESCRIPTION
           "This object specify PPS port time source."
    ::= { f3PulsePerSecondPortEntry 15 }


--
--  Time Of Day Port 
--
f3TimeOfDayPortTable OBJECT-TYPE
    SYNTAX      SEQUENCE OF F3TimeOfDayPortEntry 
    MAX-ACCESS  not-accessible
    STATUS      current
    DESCRIPTION
            "A list of entries corresponding to Time Of Day 
             Port Facilities."
    ::= { cmFacilityObjects 55 }

f3TimeOfDayPortEntry OBJECT-TYPE
    SYNTAX      F3TimeOfDayPortEntry 
    MAX-ACCESS  not-accessible
    STATUS      current
    DESCRIPTION
            "A conceptual row in the f3TimeOfDayPortTable."
    INDEX { neIndex, shelfIndex, slotIndex, f3TimeOfDayPortIndex }
    ::= { f3TimeOfDayPortTable 1 }

F3TimeOfDayPortEntry ::= SEQUENCE {
    -- Port Indices 
    f3TimeOfDayPortIndex                  Integer32,
    f3TimeOfDayPortIfIndex                InterfaceIndex,
    f3TimeOfDayPortEntityIndex            PhysicalIndex,

    -- State Management params
    f3TimeOfDayPortAdminState             AdminState,
    f3TimeOfDayPortOperationalState       OperationalState,
    f3TimeOfDayPortSecondaryState         SecondaryState,

    -- port specific params
    f3TimeOfDayPortSquelchControl         SquelchControl,
    f3TimeOfDayPortSquelchQL              SSMQualityLevel,

    f3TimeOfDayPortTODSource              VariablePointer
}
    
f3TimeOfDayPortIndex OBJECT-TYPE
    SYNTAX      Integer32 (1..65535)
    MAX-ACCESS  not-accessible
    STATUS      current
    DESCRIPTION
         "An integer index value used to uniquely identify
          this Time Of Day Port within the card." 
    ::= { f3TimeOfDayPortEntry 1 }

f3TimeOfDayPortIfIndex OBJECT-TYPE
    SYNTAX      InterfaceIndex
    MAX-ACCESS  read-only
    STATUS      current
    DESCRIPTION
         "This object has the same value as ifIndex for 
          Time Of Day Port.  An integer index value used to 
          uniquely identify this Time Of Day Port."
    ::= { f3TimeOfDayPortEntry 2 }

f3TimeOfDayPortEntityIndex OBJECT-TYPE
    SYNTAX      PhysicalIndex 
    MAX-ACCESS  read-only
    STATUS      current
    DESCRIPTION
           "Entity Index from ENTITY-MIB for this port."
    ::= { f3TimeOfDayPortEntry 3 }

-- State Management params
f3TimeOfDayPortAdminState OBJECT-TYPE
    SYNTAX      AdminState 
    MAX-ACCESS  read-write
    STATUS      current
    DESCRIPTION
            "This object represents the Administrative State of the Time Of Day 
             Port."
    ::= { f3TimeOfDayPortEntry 4 }

f3TimeOfDayPortOperationalState OBJECT-TYPE
    SYNTAX      OperationalState 
    MAX-ACCESS  read-only
    STATUS      current
    DESCRIPTION
            "This object represents the Operational State of the Time Of Day 
             Port."
    ::= { f3TimeOfDayPortEntry 5 }

f3TimeOfDayPortSecondaryState OBJECT-TYPE
    SYNTAX      SecondaryState 
    MAX-ACCESS  read-only
    STATUS      current
    DESCRIPTION
            "This object represents the Secondary State of the Time Of Day 
             Port."
    ::= { f3TimeOfDayPortEntry 6 }

f3TimeOfDayPortSquelchControl  OBJECT-TYPE 
    SYNTAX     SquelchControl
    MAX-ACCESS read-write
    STATUS     current
    DESCRIPTION
         "This object allows to set the Squelch Control for the Time Of Day port. 
          The Squelch Control is used to determine the type of squelch control 
          used to squelch the output of the TOD port."
     ::= { f3TimeOfDayPortEntry 7 }

f3TimeOfDayPortSquelchQL OBJECT-TYPE 
    SYNTAX     SSMQualityLevel
    MAX-ACCESS read-write
    STATUS     current
    DESCRIPTION
         "This object allows to set the Squelch QL for the Time Of Day port. 
          This value is used when f3TimeOfDayPortSquelchControl is squelch-ql.
          The Squelch QL is used to determine whether or not to squelch 
          the output of the TOD port. If the system's QL is lower 
          than the Squelch QL, the output is squelched."
     ::= { f3TimeOfDayPortEntry 8 }

f3TimeOfDayPortTODSource OBJECT-TYPE 
    SYNTAX     VariablePointer
    MAX-ACCESS read-write
    STATUS     current
    DESCRIPTION
         "This object allows to set the Time Of Day Source for the Port." 
     ::= { f3TimeOfDayPortEntry 9 }


--
-- network port extense Table
--
cmEthernetNetPortExtTable OBJECT-TYPE
    SYNTAX      SEQUENCE OF CmEthernetNetPortExtEntry
    MAX-ACCESS  not-accessible
    STATUS      current
    DESCRIPTION
            "A list of entries corresponding to Ethernet Network Port 
            Facilities for configuration purposes."
    ::= { cmFacilityObjects 56 }

cmEthernetNetPortExtEntry OBJECT-TYPE
    SYNTAX      CmEthernetNetPortExtEntry
    MAX-ACCESS  not-accessible
    STATUS      current
    DESCRIPTION
            "A conceptual row in the cmEthernetNetPortExtTable."
    AUGMENTS { cmEthernetNetPortEntry }
    ::= { cmEthernetNetPortExtTable 1 }

CmEthernetNetPortExtEntry ::= SEQUENCE {
    cmEthernetNetPortTDMEncapsulation          GFPEncapsulationType,
    cmEthernetNetPortAssociatedTdmEntity       VariablePointer
}

cmEthernetNetPortTDMEncapsulation OBJECT-TYPE 
    SYNTAX     GFPEncapsulationType
    MAX-ACCESS read-write
    STATUS     current
    DESCRIPTION
         "This object describes the GFP Encapsulation type of the TDM network port."
     ::= { cmEthernetNetPortExtEntry 1 }

cmEthernetNetPortAssociatedTdmEntity OBJECT-TYPE 
    SYNTAX     VariablePointer
    MAX-ACCESS read-write
    STATUS     current
    DESCRIPTION
         "This object describes the associated working path of TDM network port."
     ::= { cmEthernetNetPortExtEntry 2 }


--
--  GPS Receiver Port  
--
f3GPSReceiverPortTable OBJECT-TYPE
    SYNTAX      SEQUENCE OF F3GPSReceiverPortEntry 
    MAX-ACCESS  not-accessible
    STATUS      current
    DESCRIPTION
            "A list of entries corresponding to the GPS Receiver Port 
             Facilities."
    ::= { cmFacilityObjects 57 }

f3GPSReceiverPortEntry OBJECT-TYPE
    SYNTAX      F3GPSReceiverPortEntry 
    MAX-ACCESS  not-accessible
    STATUS      current
    DESCRIPTION
            "A conceptual row in the f3GPSReceiverPortTable."
    INDEX { neIndex, shelfIndex, slotIndex, f3GPSReceiverPortIndex }
    ::= { f3GPSReceiverPortTable 1 }

F3GPSReceiverPortEntry ::= SEQUENCE {
    -- Port Indices 
    f3GPSReceiverPortIndex                  Integer32,
    f3GPSReceiverPortIfIndex                InterfaceIndex,
    f3GPSReceiverPortEntityIndex            PhysicalIndex,

    -- State Management params
    f3GPSReceiverPortAdminState             AdminState,
    f3GPSReceiverPortOperationalState       OperationalState,
    f3GPSReceiverPortSecondaryState         SecondaryState,

    -- port specific params
    f3GPSReceiverPortPPSGenCondition        PPSGenCondition,
    f3GPSReceiverPortAntennaCableLength     Unsigned32,
    f3GPSReceiverPortAntennaStatus          GPSAntennaStatus,
    f3GPSReceiverPortSatellitesUsableFlag   TruthValue,
    f3GPSReceiverPortNumTrackingSatellites  Unsigned32,
    f3GPSReceiverPortSelfSurveyProgress     Unsigned32,
    f3GPSReceiverPortPPSGeneratedFlag       TruthValue 
}
    
f3GPSReceiverPortIndex OBJECT-TYPE
    SYNTAX      Integer32 (1..65535)
    MAX-ACCESS  not-accessible
    STATUS      current
    DESCRIPTION
         "An integer index value used to uniquely identify
          this GPS Receiver Port within the card." 
    ::= { f3GPSReceiverPortEntry 1 }

f3GPSReceiverPortIfIndex OBJECT-TYPE
    SYNTAX      InterfaceIndex
    MAX-ACCESS  read-only
    STATUS      current
    DESCRIPTION
         "This object has the same value as ifIndex for 
          Time Of Day Port.  An integer index value used to 
          uniquely identify this GPS Receiver Port."
    ::= { f3GPSReceiverPortEntry 2 }

f3GPSReceiverPortEntityIndex OBJECT-TYPE
    SYNTAX      PhysicalIndex 
    MAX-ACCESS  read-only
    STATUS      current
    DESCRIPTION
           "Entity Index from ENTITY-MIB for this port."
    ::= { f3GPSReceiverPortEntry 3 }

-- State Management params
f3GPSReceiverPortAdminState OBJECT-TYPE
    SYNTAX      AdminState 
    MAX-ACCESS  read-write
    STATUS      current
    DESCRIPTION
            "This object represents the Administrative State of the GPS
             Receiver Port." 
    ::= { f3GPSReceiverPortEntry 4 }

f3GPSReceiverPortOperationalState OBJECT-TYPE
    SYNTAX      OperationalState 
    MAX-ACCESS  read-only
    STATUS      current
    DESCRIPTION
            "This object represents the Operational State of the GPS 
             Receiver Port."
    ::= { f3GPSReceiverPortEntry 5 }

f3GPSReceiverPortSecondaryState OBJECT-TYPE
    SYNTAX      SecondaryState 
    MAX-ACCESS  read-only
    STATUS      current
    DESCRIPTION
            "This object represents the Secondary State of the GPS 
             Receiver Port."
    ::= { f3GPSReceiverPortEntry 6 }

f3GPSReceiverPortPPSGenCondition OBJECT-TYPE
    SYNTAX      PPSGenCondition 
    MAX-ACCESS  read-write
    STATUS      current
    DESCRIPTION
            "This object allows for configuration of the PPS generation
             condition.  PPS is generated when at least one satellite
             is tracked or when at least three satellites are tracked."
    ::= { f3GPSReceiverPortEntry 7 }

f3GPSReceiverPortAntennaCableLength OBJECT-TYPE
    SYNTAX      Unsigned32 
    MAX-ACCESS  read-write
    STATUS      current
    DESCRIPTION
            "This object allows for configuration of the GPS
             Antenna cable length in meters." 
    ::= { f3GPSReceiverPortEntry 8 }

f3GPSReceiverPortAntennaStatus OBJECT-TYPE
    SYNTAX      GPSAntennaStatus 
    MAX-ACCESS  read-only
    STATUS      current
    DESCRIPTION
            "This object provides the GPS Receiver Port Antenna status." 
    ::= { f3GPSReceiverPortEntry 9 }

f3GPSReceiverPortSatellitesUsableFlag OBJECT-TYPE
    SYNTAX      TruthValue 
    MAX-ACCESS  read-only
    STATUS      current
    DESCRIPTION
            "This object provides information on whether the satellites are
             usable.  It is set to TRUE, when ephemeris and health data for
             at least one satellite is available."
    ::= { f3GPSReceiverPortEntry 10 }

f3GPSReceiverPortNumTrackingSatellites OBJECT-TYPE
    SYNTAX      Unsigned32 
    MAX-ACCESS  read-only
    STATUS      current
    DESCRIPTION
            "This object provides information on the number of tracking 
             satellites." 
    ::= { f3GPSReceiverPortEntry 11 }

f3GPSReceiverPortSelfSurveyProgress OBJECT-TYPE
    SYNTAX      Unsigned32
    MAX-ACCESS  read-only
    STATUS      current
    DESCRIPTION
            "This object provides information on the percentage of
             fixes collected so far." 
    ::= { f3GPSReceiverPortEntry 12 }

f3GPSReceiverPortPPSGeneratedFlag OBJECT-TYPE 
    SYNTAX     TruthValue
    MAX-ACCESS read-only
    STATUS     current
    DESCRIPTION
         "This object indicates whether there are enough usable satellites
          to provide accurate PPS output."
     ::= { f3GPSReceiverPortEntry 13 }

cmPethPsePortExtTable  OBJECT-TYPE
    SYNTAX      SEQUENCE OF CmPethPsePortExtEntry
    MAX-ACCESS  not-accessible
    STATUS      current
    DESCRIPTION
            "A list of entries corresponding to PsePortExtEntry."
    ::= { cmFacilityObjects 58 }

cmPethPsePortExtEntry OBJECT-TYPE
    SYNTAX      CmPethPsePortExtEntry 
    MAX-ACCESS  not-accessible
    STATUS      current
    DESCRIPTION
            "A conceptual row in the cmPethPsePortExtEntry."
    INDEX { cmPethPsePortExtGroupIndex, cmPethPsePortExtIndex }
    ::= { cmPethPsePortExtTable 1 }

CmPethPsePortExtEntry ::= SEQUENCE {
    cmPethPsePortExtGroupIndex        Integer32,
    cmPethPsePortExtIndex             Integer32,
    cmPethPsePortExtAssociatedPort    VariablePointer,
    pethPsePortExtPowerConsumption    Unsigned32,
    pethPsePortExtAvailablePowerLevel PsePowerLevel
}

cmPethPsePortExtGroupIndex OBJECT-TYPE
    SYNTAX      Integer32
    MAX-ACCESS  not-accessible
    STATUS      current
    DESCRIPTION
            "This object has the same value with the group index in pethPsePortTalbe."
    ::= { cmPethPsePortExtEntry 1 }

cmPethPsePortExtIndex OBJECT-TYPE
    SYNTAX     Integer32
    MAX-ACCESS not-accessible
    STATUS     current
    DESCRIPTION
         "This object has the same value with the port index in pethPsePortTalbe."
     ::= { cmPethPsePortExtEntry 2 }

cmPethPsePortExtAssociatedPort OBJECT-TYPE
    SYNTAX     VariablePointer
    MAX-ACCESS read-write
    STATUS     current
    DESCRIPTION
         "This object means the oid of associated physical port."
     ::= { cmPethPsePortExtEntry 3 }

pethPsePortExtPowerConsumption OBJECT-TYPE
    SYNTAX     Unsigned32
    MAX-ACCESS read-only
    STATUS     current
    DESCRIPTION
         "This object means the power consumption of each port in mWatts."
     ::= { cmPethPsePortExtEntry 4 }

pethPsePortExtAvailablePowerLevel OBJECT-TYPE
    SYNTAX     PsePowerLevel
    MAX-ACCESS read-write
    STATUS     current
    DESCRIPTION
         "This object means the pse port available power level."
     ::= { cmPethPsePortExtEntry 5 }

pethMainPseEXTTable  OBJECT-TYPE
    SYNTAX      SEQUENCE OF PethMainPseEXTEntry
    MAX-ACCESS  not-accessible
    STATUS      current
    DESCRIPTION
            "A list of entries corresponding to PethMainPseEXTEntry."
    ::= { cmFacilityObjects 59 }

pethMainPseEXTEntry OBJECT-TYPE
    SYNTAX      PethMainPseEXTEntry 
    MAX-ACCESS  not-accessible
    STATUS      current
    DESCRIPTION
            "A conceptual row in the pethMainPseEXTEntry."
    INDEX { pethMainPseExtGroupIndex }
    ::= { pethMainPseEXTTable 1 }

PethMainPseEXTEntry ::= SEQUENCE {
    pethMainPseExtGroupIndex               Integer32,
    pethMainPseExtNonStandardPD            PSENonStandardPD
}

pethMainPseExtGroupIndex OBJECT-TYPE
    SYNTAX      Integer32
    MAX-ACCESS  not-accessible
    STATUS      current
    DESCRIPTION
            "This object has the same value with the group index in pethMainPseEXTTable."
    ::= { pethMainPseEXTEntry 1 }

pethMainPseExtNonStandardPD OBJECT-TYPE
    SYNTAX     PSENonStandardPD
    MAX-ACCESS read-write
    STATUS     current
    DESCRIPTION
         "disabled: don't support non-standard PD,
          enabled: support non-standard PD"
     ::= { pethMainPseEXTEntry 2 }

--
--  MPFlow Table 
--
cmMPFlowTable OBJECT-TYPE
    SYNTAX      SEQUENCE OF CmMPFlowEntry 
    MAX-ACCESS  not-accessible
    STATUS      current
    DESCRIPTION
            "A list of entries corresponding to MPFlow."
    ::= { cmFacilityObjects 60 }

cmMPFlowEntry OBJECT-TYPE
    SYNTAX      CmMPFlowEntry 
    MAX-ACCESS  not-accessible
    STATUS      current
    DESCRIPTION
            "A conceptual row in the cmMPFlowTable."
    INDEX { neIndex, cmMPFlowIndex }
    ::= { cmMPFlowTable 1 }

CmMPFlowEntry ::= SEQUENCE {
    cmMPFlowIndex                      Integer32,
    cmMPFlowCircuitName                F3DisplayString,
    cmMPFlowAdminState                 AdminState,
    cmMPFlowOperationalState           OperationalState,
    cmMPFlowSecondaryState             SecondaryState,
    cmMPFlowLearningEnabled            TruthValue,
    cmMPFlowAgingTimer                 Integer32,
    cmMPFlowFwdTableSizeProfileID      VariablePointer,
    cmMPFlowtableFullAction            LearningAction,
    cmMPFlowStorageType                StorageType,
    cmMPFlowRowStatus                  RowStatus,
    cmMPFlowLearningConfigAction       LearningConfigAction,
    cmMPFlowFPList                     F3DisplayString
}
    
cmMPFlowIndex OBJECT-TYPE
    SYNTAX      Integer32 (1..65535)
    MAX-ACCESS  not-accessible
    STATUS      current
    DESCRIPTION
         "An integer index value used to uniquely identify this MultiPointFlow." 
    ::= { cmMPFlowEntry 1 }

cmMPFlowCircuitName OBJECT-TYPE
    SYNTAX      F3DisplayString
    MAX-ACCESS  read-write
    STATUS      current
    DESCRIPTION
         "This object allows SNMP management entities to provide a
 	        circuit identifier with the MPFlow." 
    ::= { cmMPFlowEntry 2 }

cmMPFlowAdminState OBJECT-TYPE
    SYNTAX      AdminState
    MAX-ACCESS  read-write
    STATUS      current
    DESCRIPTION
         "This object represents the Administrative State of the Flow." 
    ::= { cmMPFlowEntry 3 }

cmMPFlowOperationalState OBJECT-TYPE
    SYNTAX      OperationalState
    MAX-ACCESS  read-only
    STATUS      current
    DESCRIPTION
         "This object represents the Operational State of the Flow." 
    ::= { cmMPFlowEntry 4 }

cmMPFlowSecondaryState OBJECT-TYPE
    SYNTAX      SecondaryState
    MAX-ACCESS  read-only
    STATUS      current
    DESCRIPTION
         "This object represents the Secondary State of the Flow." 
    ::= { cmMPFlowEntry 5 }

cmMPFlowLearningEnabled OBJECT-TYPE
    SYNTAX      TruthValue
    MAX-ACCESS  read-write
    STATUS      current
    DESCRIPTION
         "DISABLED: The forwarding function of the Flow does not 
         dynamically learn MAC address to flowpoint mapping.
         ENABLED: The forwarding function of the Flow dynamically 
         learns MAC address to flowpoint mapping based on ingress 
         flowpoing and source MAC address." 
    ::= { cmMPFlowEntry 6 }

cmMPFlowAgingTimer OBJECT-TYPE
    SYNTAX      Integer32
    MAX-ACCESS  read-write
    STATUS      current
    DESCRIPTION
         "MAC Table Entry will be removed from the forwarding table
          after an inactivity time represented by this entry.
          Not used in EG-X." 
    ::= { cmMPFlowEntry 7 }

cmMPFlowFwdTableSizeProfileID OBJECT-TYPE
    SYNTAX      VariablePointer
    MAX-ACCESS  read-write
    STATUS      current
    DESCRIPTION
         "Profile ID for Maximum number of MAC Table Entries for the flow" 
    ::= { cmMPFlowEntry 8 }

cmMPFlowtableFullAction OBJECT-TYPE
    SYNTAX      LearningAction
    MAX-ACCESS  read-write
    STATUS      current
    DESCRIPTION
         "Action on ingress frames when the number of MAC Table entires
          has reached the maximum defined by tableSize.
          BLOCK: A frame with a Source MAC address not in the MAC 
          Table will be discarded.
          FORWARD: A frame with a Source MAC address not in the MAC table 
          will not be learned and will be flooded to other flowpoints." 
    ::= { cmMPFlowEntry 9 }

cmMPFlowStorageType OBJECT-TYPE
    SYNTAX      StorageType
    MAX-ACCESS  read-create
    STATUS      current
    DESCRIPTION
         "The type of storage configured for this entry." 
    ::= { cmMPFlowEntry 10 }

cmMPFlowRowStatus OBJECT-TYPE
    SYNTAX      RowStatus
    MAX-ACCESS  read-create
    STATUS      current
    DESCRIPTION
         "The status of this row.
 	        An entry MUST NOT exist in the active state unless all
 	        objects in the entry have an appropriate value, as described
 	        in the description clause for each writable object.
 	        
 	        The values of cmMPFlowRowStatus supported are
 	        createAndGo(4) and destroy(6).  All mandatory attributes
 	        must be specified in a single SNMP SET request with
 	        cmFlowRowStatus value as createAndGo(4).
 	        Upon successful row creation, this object has a
 	        value of active(1).
 	        
 	        The cmMPFlowRowStatus object may be modified if
 	        the associated instance of this object is equal to active(1).
 	        
 	        Note that flow creation and deletion is only supported
 	        with access port in connection-oriented evpl mode." 
    ::= { cmMPFlowEntry 11 }

cmMPFlowLearningConfigAction OBJECT-TYPE
    SYNTAX      LearningConfigAction
    MAX-ACCESS  read-write
    STATUS      current
    DESCRIPTION
         "This objects allows performing user action on Learning Table." 
    ::= { cmMPFlowEntry 12 }

cmMPFlowFPList OBJECT-TYPE
    SYNTAX      F3DisplayString
    MAX-ACCESS  read-write
    STATUS      current
    DESCRIPTION
         "This object only used to display trap and Flow point list.
          Fp will be add in the cmMPFlowMemberTable." 
    ::= { cmMPFlowEntry 13 }

--
--  MP Flow Member Table 
--
cmMPFlowMemberTable OBJECT-TYPE
    SYNTAX      SEQUENCE OF CmMPFlowMemberEntry 
    MAX-ACCESS  not-accessible
    STATUS      current
    DESCRIPTION
            "A list of entries corresponding to MPFlowMember."
    ::= { cmFacilityObjects 61 }

cmMPFlowMemberEntry OBJECT-TYPE
    SYNTAX      CmMPFlowMemberEntry 
    MAX-ACCESS  not-accessible
    STATUS      current
    DESCRIPTION
            "A conceptual row in the cmMPFlowMemberTable."
    INDEX { neIndex, cmMPFlowIndex, cmMPFlowMemberFPIndex }
    ::= { cmMPFlowMemberTable 1 }

CmMPFlowMemberEntry ::= SEQUENCE {
    cmMPFlowMemberFPIndex            VariablePointer,
    cmMPFlowPointRowStatus           RowStatus
}
    
cmMPFlowMemberFPIndex OBJECT-TYPE
    SYNTAX      VariablePointer
    MAX-ACCESS  not-accessible
    STATUS      current
    DESCRIPTION
         "This object describes the relate Flow point." 
    ::= { cmMPFlowMemberEntry 1 }
    
cmMPFlowPointRowStatus OBJECT-TYPE
    SYNTAX      RowStatus
    MAX-ACCESS  read-create
    STATUS      current
    DESCRIPTION
         "The status of this row.
 	        An entry MUST NOT exist in the active state unless all
 	        objects in the entry have an appropriate value, as described
 	        in the description clause for each writable object.
 	        
 	        The values of cmMPFlowPointRowStatus supported are
 	        createAndGo(4) and destroy(6).  All mandatory attributes
 	        must be specified in a single SNMP SET request with
 	        cmFlowRowStatus value as createAndGo(4).
 	        Upon successful row creation, this object has a
 	        value of active(1).
 	        
 	        The cmMPFlowPointRowStatus object may be modified if
 	        the associated instance of this object is equal to active(1).
 	        
 	        Note that flow creation and deletion is only supported
 	        with access port in connection-oriented evpl mode."
    ::= { cmMPFlowMemberEntry 2 }

--
-- EthernetTraffic Port PCP encoding table 
--
cmEthernetTrafficPortPcpDEEncTable  OBJECT-TYPE
    SYNTAX      SEQUENCE OF CmEthernetTrafficPortPcpDEEncEntry 
    MAX-ACCESS  not-accessible
    STATUS      current
    DESCRIPTION
        "EthernetTraffic Port PCP drop eligibility encoding table. This
         is applied to a frame that is egressing at the EthernetTraffic port."
    ::= { cmFacilityObjects 62 }

cmEthernetTrafficPortPcpDEEncEntry OBJECT-TYPE
    SYNTAX      CmEthernetTrafficPortPcpDEEncEntry 
    MAX-ACCESS  not-accessible
    STATUS      current
    DESCRIPTION
            "A conceptual row in the ethernetPBPcpDEEncPortTable."
    INDEX { neIndex, shelfIndex, slotIndex, cmEthernetTrafficPortIndex, 
            cmEthernetTrafficPortPcpDEEncIndex }
    ::= { cmEthernetTrafficPortPcpDEEncTable 1 }

CmEthernetTrafficPortPcpDEEncEntry ::= SEQUENCE {
  cmEthernetTrafficPortPcpDEEncIndex              Integer32,
  cmEthernetTrafficPortPcpDEEncInPriority         VlanPriority,
  cmEthernetTrafficPortPcpDEEncDropIneligiblePrio VlanPriority,
  cmEthernetTrafficPortPcpDEEncDropEligiblePrio   VlanPriority
}

cmEthernetTrafficPortPcpDEEncIndex OBJECT-TYPE
    SYNTAX      Integer32 (1..8)
    MAX-ACCESS  read-only
    STATUS      current
    DESCRIPTION
            "An integer index value used to uniquely identify
             a row in the PCP drop eligible encoding table."
    ::= { cmEthernetTrafficPortPcpDEEncEntry 1 }

cmEthernetTrafficPortPcpDEEncInPriority OBJECT-TYPE
    SYNTAX     VlanPriority
    MAX-ACCESS read-write
    STATUS     current
    DESCRIPTION
         "This object is the input priority that is translated to a
          drop eligibility priority or a drop ineligibility priority."
     ::= { cmEthernetTrafficPortPcpDEEncEntry 2 }

cmEthernetTrafficPortPcpDEEncDropIneligiblePrio OBJECT-TYPE
    SYNTAX     VlanPriority
    MAX-ACCESS read-write
    STATUS     current
    DESCRIPTION
         "This object is the PCP value that has a priority value with
          implicit drop ineligibility encoded into it."
     ::= { cmEthernetTrafficPortPcpDEEncEntry 3 }

cmEthernetTrafficPortPcpDEEncDropEligiblePrio OBJECT-TYPE
    SYNTAX     VlanPriority
    MAX-ACCESS read-write
    STATUS     current
    DESCRIPTION
         "This object is the PCP value that has a priority value with
          implicit drop eligibility encoded into it."
     ::= { cmEthernetTrafficPortPcpDEEncEntry 4 }

--
-- EthernetTraffic Port PCP decoding table
--

cmEthernetTrafficPortPcpDEDecTable  OBJECT-TYPE
    SYNTAX      SEQUENCE OF CmEthernetTrafficPortPcpDEDecEntry
    MAX-ACCESS  not-accessible
    STATUS      current
    DESCRIPTION
            "EthernetTraffic Port PCP drop eligibility decoding table. This
             is applied to a frame that is ingressing at a port."
    ::= { cmFacilityObjects 63 }

cmEthernetTrafficPortPcpDEDecEntry OBJECT-TYPE
    SYNTAX      CmEthernetTrafficPortPcpDEDecEntry 
    MAX-ACCESS  not-accessible
    STATUS      current
    DESCRIPTION
            "A conceptual row in the ethernetPBPcpDEDecPortTable."
    INDEX { neIndex, shelfIndex, slotIndex, cmEthernetTrafficPortIndex, 
            cmEthernetTrafficPortPcpDEDecIndex }
    ::= { cmEthernetTrafficPortPcpDEDecTable 1 }

CmEthernetTrafficPortPcpDEDecEntry ::= SEQUENCE {
    cmEthernetTrafficPortPcpDEDecIndex        Integer32,
    cmEthernetTrafficPortPcpDEDecInPriority   VlanPriority,
    cmEthernetTrafficPortPcpDEDecOutPriority  VlanPriority,
    cmEthernetTrafficPortPcpDEDecDropEligible TruthValue
}


cmEthernetTrafficPortPcpDEDecIndex OBJECT-TYPE
    SYNTAX      Integer32 (1..8)
    MAX-ACCESS  read-only
    STATUS      current
    DESCRIPTION
            "An integer index value used to uniquely identify
             a row in the PCP drop eligible decoding table."
    ::= { cmEthernetTrafficPortPcpDEDecEntry 1 }

cmEthernetTrafficPortPcpDEDecInPriority OBJECT-TYPE
    SYNTAX     VlanPriority
    MAX-ACCESS read-write
    STATUS     current
    DESCRIPTION
         "This object is the input priority that is decoded to get
          priority and the drop eligibility of a frame."
     ::= { cmEthernetTrafficPortPcpDEDecEntry 2 }

cmEthernetTrafficPortPcpDEDecOutPriority OBJECT-TYPE
    SYNTAX     VlanPriority
    MAX-ACCESS read-write
    STATUS     current
    DESCRIPTION
         "This object is the priority value decoded from a incoming PCP value."
     ::= { cmEthernetTrafficPortPcpDEDecEntry 3 }

cmEthernetTrafficPortPcpDEDecDropEligible OBJECT-TYPE
    SYNTAX     TruthValue
    MAX-ACCESS read-write
    STATUS     current
    DESCRIPTION
         "This object is the drop eligibility decoded from a incoming
          PCP value."
     ::= { cmEthernetTrafficPortPcpDEDecEntry 4 }

-- 
-- EthernetTraffic Port PCP pair table
--

cmEthernetTrafficPortPcpDEPairTable  OBJECT-TYPE
    SYNTAX      SEQUENCE OF CmEthernetTrafficPortPcpDEPairEntry
    MAX-ACCESS  not-accessible
    STATUS      current
    DESCRIPTION
            "EthernetTraffic Port PCP drop eligibility priority pair table.
             The priority pair is encoded to same drop eligibility and
             drop ineligibility priority. Depending on the PCP DE Enc/Dec
             mode there can be upto 3 pairs in the table. There will one
             pair for 7P1D, two pairs for 6P2D and three pairs for 5P3D."
    ::= { cmFacilityObjects 64 }

cmEthernetTrafficPortPcpDEPairEntry OBJECT-TYPE
    SYNTAX      CmEthernetTrafficPortPcpDEPairEntry 
    MAX-ACCESS  not-accessible
    STATUS      current
    DESCRIPTION
            "A conceptual row in the cmAccPortPcpDEPairEntry."
    INDEX { neIndex, shelfIndex, slotIndex, cmEthernetTrafficPortIndex, 
            cmEthernetTrafficPortPcpDEPairIndex }
    ::= { cmEthernetTrafficPortPcpDEPairTable 1 }

CmEthernetTrafficPortPcpDEPairEntry ::= SEQUENCE {
    cmEthernetTrafficPortPcpDEPairIndex          Integer32,
    cmEthernetTrafficPortPcpDEDropIneligiblePrio VlanPriority,
    cmEthernetTrafficPortPcpDEDropEligiblePrio   VlanPriority
}

cmEthernetTrafficPortPcpDEPairIndex OBJECT-TYPE
    SYNTAX      Integer32 (1..3)
    MAX-ACCESS  read-only
    STATUS      current
    DESCRIPTION
            "An integer index value used to uniquely identify
             a row in the PCP drop eligible priority pair table."
    ::= { cmEthernetTrafficPortPcpDEPairEntry 1 }

cmEthernetTrafficPortPcpDEDropIneligiblePrio OBJECT-TYPE
    SYNTAX     VlanPriority
    MAX-ACCESS read-write
    STATUS     current
    DESCRIPTION
         "This object is the drop ineligible priority."
     ::= { cmEthernetTrafficPortPcpDEPairEntry 2 }

cmEthernetTrafficPortPcpDEDropEligiblePrio OBJECT-TYPE
    SYNTAX     VlanPriority
    MAX-ACCESS read-write
    STATUS     current
    DESCRIPTION
         "This object is the drop eligible priority."
     ::= { cmEthernetTrafficPortPcpDEPairEntry 3 }

--
--  Ethernet Traffic Port Cable Length Benchmark 
--
cmEthernetTrafficPortClbTable  OBJECT-TYPE
    SYNTAX      SEQUENCE OF CmEthernetTrafficPortClbEntry
    MAX-ACCESS  not-accessible
    STATUS      current
    DESCRIPTION
            "A list of entries corresponding to Ethernet Traffic Port 
             Cable Length Benchmark."
    ::= { cmFacilityObjects 65 }

cmEthernetTrafficPortClbEntry OBJECT-TYPE
    SYNTAX      CmEthernetTrafficPortClbEntry 
    MAX-ACCESS  not-accessible
    STATUS      current
    DESCRIPTION
            "A conceptual row in the cmEthernetTrafficPortClbTable. 
             These entries represent Cable Length Benchmarks 
             on the Ethernet Traffic Port."
    INDEX { neIndex, shelfIndex, slotIndex, cmEthernetTrafficPortIndex, 
            cmEthernetTrafficPortClbIndex }
    ::= { cmEthernetTrafficPortClbTable 1 }


CmEthernetTrafficPortClbEntry ::= SEQUENCE {
    cmEthernetTrafficPortClbIndex          Integer32,
    cmEthernetTrafficPortClbEnabled        TruthValue,
    cmEthernetTrafficPortClbLength         DisplayString,
    cmEthernetTrafficPortClbDescr          DisplayString
}

cmEthernetTrafficPortClbIndex OBJECT-TYPE
    SYNTAX      Integer32 (1..5)
    MAX-ACCESS  read-only
    STATUS      current
    DESCRIPTION
            "An integer index value used to uniquely identify
             this Cable Length Benchmark Entry specification."
    ::= { cmEthernetTrafficPortClbEntry 1 }

cmEthernetTrafficPortClbEnabled OBJECT-TYPE
    SYNTAX     TruthValue
    MAX-ACCESS read-write
    STATUS     current
    DESCRIPTION
            "This enables specification of Cable Length Benchmark entry."
    ::= { cmEthernetTrafficPortClbEntry 2 }

cmEthernetTrafficPortClbLength OBJECT-TYPE
    SYNTAX  DisplayString 
    MAX-ACCESS read-write
    STATUS     current
    DESCRIPTION
            "Cable length of Cable Points Entry. The cable length is of
             the form XXX[.YY] where XX can be any integer value and YY
             allows precision of 2 decimals after the floating point. Note
             that .YY is optional."
    ::= { cmEthernetTrafficPortClbEntry 3 }

cmEthernetTrafficPortClbDescr OBJECT-TYPE
    SYNTAX     DisplayString (SIZE (0..256))
    MAX-ACCESS read-write
    STATUS     current
    DESCRIPTION
         "A textual string containing description of cable span."
    ::= { cmEthernetTrafficPortClbEntry 4 }

--
--  cmNeTrafficElementTable
--
networkElementTMParamsTable  OBJECT-TYPE
    SYNTAX          SEQUENCE OF NetworkElementTMParamsEntry
    MAX-ACCESS  not-accessible
    STATUS          current
    DESCRIPTION
         "Entries may be auto discovered, or can be explicitly created by 
          SNMP Manager.  Each remotely discovered shelf is represented as 
          a row in this table." 
    ::= { cmFacilityObjects 66 }

networkElementTMParamsEntry  OBJECT-TYPE
    SYNTAX          NetworkElementTMParamsEntry
    MAX-ACCESS  not-accessible
    STATUS          current
    DESCRIPTION
            "A conceptual row in the networkElementTMParamsTable."
    AUGMENTS { networkElementEntry }
    ::= { networkElementTMParamsTable 1 }


NetworkElementTMParamsEntry ::= SEQUENCE {
    neTMParamsBandwidthProfileMode     BandwidthProfileMode, 
    neTMParamsAgingtime                Integer32
}

neTMParamsBandwidthProfileMode OBJECT-TYPE
    SYNTAX          BandwidthProfileMode  
    MAX-ACCESS      read-create
    STATUS          current
    DESCRIPTION
        "A Network Element level Bandwidth Profile Mode shall be supported 
         which will indicate if the CIR/EIR is interpreted as Information Rate (IR) 
         or Line Rate (LR). In IR mode BWP is enforced based on number of bytes beginning 
         with DA and ending with FCS as it was received at a port which is called the Service 
         Frame in MEF terminology. In LR mode the BWP is enforced based on the whole frame 
         including IFG, Preamble and SFD."
    ::= { networkElementTMParamsEntry 1 }

neTMParamsAgingtime OBJECT-TYPE
    SYNTAX     Integer32
    MAX-ACCESS read-create
    STATUS     current
    DESCRIPTION
            "The object describe the system aging time."
    ::= { networkElementTMParamsEntry 2 }

--
-- Access Port JDSU Ext Table
--

cmEthernetAccPortJdsuExtTable OBJECT-TYPE
    SYNTAX      SEQUENCE OF CmEthernetAccPortJdsuExtEntry
    MAX-ACCESS  not-accessible
    STATUS      current
    DESCRIPTION
            "A list of entries corresponding to Ethernet Access Port 
            Facilities for JDSU configuration purposes."
    ::= { cmFacilityObjects 67 }

cmEthernetAccPortJdsuExtEntry OBJECT-TYPE
    SYNTAX      CmEthernetAccPortJdsuExtEntry
    MAX-ACCESS  not-accessible
    STATUS      current
    DESCRIPTION
            "A conceptual row in the cmEthernetAccPortJdsuExtTable."
    AUGMENTS { cmEthernetAccPortEntry }
    ::= { cmEthernetAccPortJdsuExtTable 1 }

CmEthernetAccPortJdsuExtEntry ::= SEQUENCE {
    cmEthernetAccPortJDSUControlFramesSnoopingEnabled   TruthValue,
    cmEthernetAccPortJDSULoopbackVlan                   VlanId
}

cmEthernetAccPortJDSUControlFramesSnoopingEnabled OBJECT-TYPE
    SYNTAX      TruthValue  
    MAX-ACCESS  read-write
    STATUS      current
    DESCRIPTION
        "Enabled: reaction/response to JDSU in-band loopback requests and hallo requests.
         Disabled: Not reaction/response to JDSU in-band loopback requests and hallo requests. 
         FPGA shall not filter the JDSU control frames to processor.
         From enabled to disabled, if there is already a JDSU loopback on the port, 
         release current loopback.
         JDSU loopback doesn't need port in maintenance state."
     ::= { cmEthernetAccPortJdsuExtEntry 1 }

cmEthernetAccPortJDSULoopbackVlan OBJECT-TYPE
    SYNTAX      VlanId  
    MAX-ACCESS  read-only
    STATUS      current
    DESCRIPTION
        "Applicable when port in JDSU VLAN loopback."
     ::= { cmEthernetAccPortJdsuExtEntry 2 }

--
-- Network Port JDSU Ext Table
--

cmEthernetNetPortJdsuExtTable OBJECT-TYPE
    SYNTAX      SEQUENCE OF CmEthernetNetPortJdsuExtEntry
    MAX-ACCESS  not-accessible
    STATUS      current
    DESCRIPTION
            "A list of entries corresponding to Ethernet Network Port 
            Facilities for JDSU configuration purposes."
    ::= { cmFacilityObjects 68 }

cmEthernetNetPortJdsuExtEntry OBJECT-TYPE
    SYNTAX      CmEthernetNetPortJdsuExtEntry
    MAX-ACCESS  not-accessible
    STATUS      current
    DESCRIPTION
            "A conceptual row in the cmEthernetNetPortJdsuExtTable."
    AUGMENTS { cmEthernetNetPortEntry }
    ::= { cmEthernetNetPortJdsuExtTable 1 }

CmEthernetNetPortJdsuExtEntry ::= SEQUENCE {
    cmEthernetNetPortJDSUControlFramesSnoopingEnabled   TruthValue,
    cmEthernetNetPortJDSULoopbackVlan                   VlanId
}

cmEthernetNetPortJDSUControlFramesSnoopingEnabled OBJECT-TYPE
    SYNTAX      TruthValue  
    MAX-ACCESS  read-write
    STATUS      current
    DESCRIPTION
        "Enabled: reaction/response to JDSU in-band loopback requests and hallo requests.
         Disabled: Not reaction/response to JDSU in-band loopback requests and hallo requests. 
         FPGA shall not filter the JDSU control frames to processor.
         From enabled to disabled, if there is already a JDSU loopback on the port, 
         release current loopback.
         JDSU loopback doesn't need port in maintenance state."
     ::= { cmEthernetNetPortJdsuExtEntry 1 }

cmEthernetNetPortJDSULoopbackVlan OBJECT-TYPE
    SYNTAX      VlanId  
    MAX-ACCESS  read-only
    STATUS      current
    DESCRIPTION
        "Applicable when port in JDSU VLAN loopback."
     ::= { cmEthernetNetPortJdsuExtEntry 2 }
     

--
--  Ethernet Traffic Port LPBK entry 
--
cmEthernetTrafficPortLpbkTable  OBJECT-TYPE
    SYNTAX      SEQUENCE OF CmEthernetTrafficPortLpbkEntry
    MAX-ACCESS  not-accessible
    STATUS      current
    DESCRIPTION
            "A list of entries corresponding to Vlan loopback on
            Ethernet Traffic Port."
    ::= { cmFacilityObjects 69 }

cmEthernetTrafficPortLpbkEntry OBJECT-TYPE
    SYNTAX      CmEthernetTrafficPortLpbkEntry 
    MAX-ACCESS  not-accessible
    STATUS      current
    DESCRIPTION
            "A conceptual row in the cmEthernetTrafficPortLpbkTable. 
             These entries represent Vlan loopback 
             on the Ethernet Traffic Port."
    INDEX { neIndex, shelfIndex, slotIndex, cmEthernetTrafficPortIndex, 
            cmEthernetTrafficPortLpbkIndex }
    ::= { cmEthernetTrafficPortLpbkTable 1 }

CmEthernetTrafficPortLpbkEntry ::= SEQUENCE {
    cmEthernetTrafficPortLpbkIndex                    Integer32,
    cmEthernetTrafficPortLpbkInnerVlanEnabled         TruthValue,
    cmEthernetTrafficPortLpbkInnerVlanTag             DisplayString,
    cmEthernetTrafficPortLpbkOuterVlanEnabled         TruthValue,
    cmEthernetTrafficPortLpbkOuterVlanTag             DisplayString,
    cmEthernetTrafficPortLpbkTime                     Integer32,
    cmEthernetTrafficPortLpbkStatus                   CmLoopbackType,
    cmEthernetTrafficPortLpbkConfig                   CmLoopbackType
}

cmEthernetTrafficPortLpbkIndex OBJECT-TYPE
    SYNTAX      Integer32
    MAX-ACCESS  not-accessible
    STATUS      current
    DESCRIPTION
            "An integer index value used to uniquely identify
             this vlan loopback entry."
    ::= { cmEthernetTrafficPortLpbkEntry 1 }

cmEthernetTrafficPortLpbkInnerVlanEnabled OBJECT-TYPE
    SYNTAX      TruthValue
    MAX-ACCESS  read-write
    STATUS      current
    DESCRIPTION
            "This object represent the inner vlan whether enabled."
    ::= { cmEthernetTrafficPortLpbkEntry 2 }

cmEthernetTrafficPortLpbkInnerVlanTag OBJECT-TYPE
    SYNTAX      DisplayString
    MAX-ACCESS  read-write
    STATUS      current
    DESCRIPTION
            "This object represent the inner vlanid value and priority value.
            The value to be specified should be in the form 
            X-Y where X is the VLAN Id and Y is the VLAN Priority.  
            If Y is specified as a *, all Priorities (0 to 7) 
            are looped back."
    ::= { cmEthernetTrafficPortLpbkEntry 3 }

cmEthernetTrafficPortLpbkOuterVlanEnabled OBJECT-TYPE
    SYNTAX      TruthValue
    MAX-ACCESS  read-write
    STATUS      current
    DESCRIPTION
            "This object represent the outter vlan whether enabled."
    ::= { cmEthernetTrafficPortLpbkEntry 4 }

cmEthernetTrafficPortLpbkOuterVlanTag OBJECT-TYPE
    SYNTAX      DisplayString
    MAX-ACCESS  read-write
    STATUS      current
    DESCRIPTION
            "This object represent the outter vlanid value and priority value.
            The value to be specified should be in the form 
            X-Y where X is the VLAN Id and Y is the VLAN Priority.  
            If Y is specified as a *, all Priorities (0 to 7) 
            are looped back."
    ::= { cmEthernetTrafficPortLpbkEntry 5 }

cmEthernetTrafficPortLpbkTime OBJECT-TYPE
    SYNTAX      Integer32
    MAX-ACCESS  read-write
    STATUS      current
    DESCRIPTION
            "This object represent the vlan loopback time."
    ::= { cmEthernetTrafficPortLpbkEntry 6 }

cmEthernetTrafficPortLpbkStatus OBJECT-TYPE
    SYNTAX      CmLoopbackType
    MAX-ACCESS  read-only
    STATUS      current
    DESCRIPTION
            "This object represent the vlan loopback status."
    ::= { cmEthernetTrafficPortLpbkEntry 7 }

cmEthernetTrafficPortLpbkConfig OBJECT-TYPE
    SYNTAX      CmLoopbackType
    MAX-ACCESS  read-write
    STATUS      current
    DESCRIPTION
            "This object represent the vlan loopback action."
    ::= { cmEthernetTrafficPortLpbkEntry 8 }

--
-- Conformance
--
cmFacilityCompliances OBJECT IDENTIFIER ::= {cmFacilityConformance 1}
cmFacilityGroups      OBJECT IDENTIFIER ::= {cmFacilityConformance 2}

cmFacilityCompliance MODULE-COMPLIANCE
    STATUS  current
    DESCRIPTION
            "Describes the requirements for conformance to the CM Facility
             group."
    MODULE  -- this module
        MANDATORY-GROUPS {
              cmFacilityObjectGroup,
              ethernetAccessPortGroup, ethernetNetworkPortGroup, 
              ethernetMgmtPortGroup, bitsPortGroup,
              trafficGroup, prioMapGroup, pcpEncodeGroup, cpdV2Group,

              trafficGroupCmHub, ocnStmGroup, stsVcPathGroup,
              vtVcPathGroup, e1t1InterfaceGroup, e3t3InterfaceGroup,

              f3PulsePerSecondPortGroup, f3TimeOfDayPortGroup,
              
              f3Gps10MhzPortGroup,neTMParamsGroup  
        }
    ::= { cmFacilityCompliances 1 }

cmFacilityObjectGroup OBJECT-GROUP
    OBJECTS {
    cmEthernetAccPortIndex, cmEthernetAccPortIfIndex,
    cmEthernetAccPortOperationalState, cmEthernetAccPortSecondaryState,
    cmEthernetAccPortMTU, cmEthernetAccPortMediaType,
    cmEthernetAccPortConfigSpeed, cmEthernetAccPortNegotiatedSpeed,
    cmEthernetAccPortMDIXType,
    cmEthernetAccPortJumboFramesEnabled, cmEthernetAccPortSfpVendorName,
    cmEthernetAccPortSfpPartNumber, cmEthernetAccPortSfpSerialNumber,
    cmEthernetAccPortSfpDateOfManufacture,
    cmEthernetAccPortSfpConnectorValue,
    cmEthernetAccPortInitiateDiag, cmEthernetAccPortDiagnosePair1Cond,
    cmEthernetAccPortDiagnosePair2Cond, cmEthernetAccPortDiagnosePair3Cond,
    cmEthernetAccPortDiagnosePair4Cond, cmEthernetAccPortDiagnoseAutoNegCond,
    cmEthernetAccPortDiagnoseLpbkCond, cmEthernetAccPortDiagnoseEfmLpbkCond,
    cmEthernetAccPortDiagnoseResult,cmEthernetAccPortDiagnoseTestStatus,
    cmEthernetAccPortDiagnoseTestTime,
    cmEthernetAccPortLoopbackConfig, cmEthernetAccPortLoopbackStatus,
    cmEthernetAccPortLoopbackTime,
    cmEthernetAccPortLoopbackSwapSADA, cmEthernetAccPortOuterVlanLoopbackMask,
    cmEthernetAccPortOuterVlanLoopback1, cmEthernetAccPortOuterVlanLoopback2,
    cmEthernetAccPortOuterVlanLoopback3, 
    cmEthernetAccPortInnerVlanLoopbackMask,
    cmEthernetAccPortInnerVlanLoopback1, cmEthernetAccPortInnerVlanLoopback2,
    cmEthernetAccPortInnerVlanLoopback3,
    cmEthernetAccPortLinkLossFwdEnabled, 
    cmEthernetAccPortLinkLossFwdSignalType,
    cmEthernetAccPortLinkLossFwdTriggerTypes,
    cmEthernetAccPortLinkLossFwdDelay, cmEthernetAccPortLinkLossFwdActive,
    cmEthernetAccPortLinkLossFwdPartnerEnabled,
    cmEthernetAccPortLinkLossFwdLocalLinkId,
    cmEthernetAccPortLinkLossFwdRemoteLinkIds,
    cmEthernetAccPortOamId, cmEthernetAccPortOamAdminDisposition,
    cmEthernetAccPortOamDiscoveryState, 
    cmEthernetAccPortOamLocalVarRtrvsEnabled,
    cmEthernetAccPortOamLocalLinkEventsEnabled,
    cmEthernetAccPortOamLocalOamLoopbacksSupported,
    cmEthernetAccPortOamLocalUnidirSupportEnabled,
    cmEthernetAccPortOamLocalMaxPDUSize, cmEthernetAccPortOamLocalMode,
    cmEthernetAccPortOamRemoteMacAddress, 
    cmEthernetAccPortOamRemoteVarRtrvsEnabled,
    cmEthernetAccPortOamRemoteLinkEventsEnabled,
    cmEthernetAccPortOamRemoteOamLoopbacksSupported,
    cmEthernetAccPortOamRemoteUnidirSupportEnabled,
    cmEthernetAccPortOamRemoteMaxPDUSize,
    cmEthernetAccPortOamRemoteMode, cmEthernetAccPortMode, 
    cmEthernetAccPortSvcType, cmEthernetAccPortRxPauseDisposition, 
    cmEthernetAccPortTxPauseEnabled, cmEthernetAccPortAfpType,

    cmEthernetAccPortCpdIndex, cmEthernetAccPortCpdFilterType,
    cmEthernetAccPortCpdFilterDescr, cmEthernetAccPortCpdDispType,
    cmEthernetAccPortCpdMacAddressMatch, cmEthernetAccPortCpdMacAddressMask,
    cmEthernetAccPortCpdEthertype, cmEthernetAccPortCpdEthertypeMask,
    cmEthernetAccPortCpdSubtype, cmEthernetAccPortCpdSubtypeMask,

    cmEthernetAccPortClbIndex, cmEthernetAccPortClbEnabled,
    cmEthernetAccPortClbLength, cmEthernetAccPortClbDescr,

    cmEthernetAccPortMDIXStatus, cmEthernetAccPortSfpReach,
    cmEthernetAccPortSfpLaserWaveLength,
    cmEthernetAccPortSfpMediaType, cmEthernetAccPortOamEnabled,
    cmEthernetAccPortOamAdminState,
    cmEthernetAccPortShapingEnabled,
    cmEthernetAccPortShapedSpeedLo, cmEthernetAccPortShapedSpeedHi,
    cmEthernetAccPortQinQEtherType, cmEthernetAccPortRxPauseEnabled,
    cmEthernetAccPortAutoDiagEnabled, cmEthernetAccPortLinkLossFwdTxActionType,
    cmEthernetAccPortLinkLossFwdRxRLDLinkIds,
    cmEthernetAccPortN2AVlanTrunkingEnabled, 
    cmEthernetAccPortA2NPushPVIDEnabled,
    cmEthernetAccPortN2APopPVIDEnabled, cmEthernetAccPortPortVlanId,
    cmEthernetAccPortPortVlanPriority,   
    cmEthernetAccPortPrioMapMode, cmEthernetAccPortSyncEEnabled,
    cmEthernetAccPortQLModeEnabled, cmEthernetAccPortExpectedQL,
    cmEthernetAccPortAssumedQL, cmEthernetAccPortReceivedQL, 
    cmEthernetAccPortTransmitQL,

    cmFlowIndex, cmFlowCircuitName, cmFlowAdminState,
    cmFlowOperationalState, cmFlowSecondaryState,
    cmFlowType, cmFlowMultiCOS, cmFlowA2NCIR,
    cmFlowA2NEIR, cmFlowN2ARateLimitingEnabled,
    cmFlowN2ACIR, cmFlowN2AEIR, cmFlowStorageType, cmFlowRowStatus,

    cmFlowTrafficType, cmFlowCOS, cmFlowVlanMemberList,
    cmFlowAction, cmFlowActionVlan, cmFlowUntaggedMemberEnabled,
    cmFlowA2NCIRHi, cmFlowA2NEIRHi,
    cmFlowN2ACIRHi, cmFlowN2AEIRHi, 
    cmFlowHCOSMgmtEnabled, cmFlowGuaranteedA2NBandwidthLo,
    cmFlowGuaranteedA2NBandwidthHi, cmFlowMaximumA2NBandwidthLo,
    cmFlowMaximumA2NBandwidthHi, cmFlowCTagControl,
    cmFlowCTagVlanId, cmFlowCTagVlanPriority, cmFlowCTagMatchRxPrio,
    cmFlowSTagControl, cmFlowSTagVlanId, cmFlowSTagVlanPriority,
    cmFlowOuterTagPrioEnabled, cmFlowN2ACOSPriorityTagType,
    cmFlowESFramesLossThreshold, cmFlowSESFramesLossThresholdRatio, 
    cmFlowPolicingEnabled, cmFlowPreserveSTagProperties, cmFlowInnerTagPrioEnabled,
    cmFlowN2AOuterTagPrioEnabled,

    cmFlowCpdIndex, cmFlowCpdFilterType, cmFlowCpdFilterDescr, 
    cmFlowCpdDispType, cmFlowCpdMacAddressMatch, cmFlowCpdMacAddressMask,
    cmFlowCpdEthertype, cmFlowCpdEthertypeMask, cmFlowCpdSubtype, 
    cmFlowCpdSubtypeMask,

    cmQosShaperTypeIndex, cmQosShaperIndex, cmQosShaperDirection,
    cmQosShaperAdminState, cmQosShaperOperationalState,cmQosShaperSecondaryState,
    cmQosShaperCIR, cmQosShaperCBS, cmQosShaperEIR, cmQosShaperEBS,
    cmQosShaperBufferSize, cmQosShaperStorageType,
    cmQosShaperRowStatus, 

    cmQosShaperCOS, cmQosShaperCIRHi, cmQosShaperEIRHi,

    cmEthernetNetPortIndex, cmEthernetNetPortIfIndex,
    cmEthernetNetPortEntityIndex, cmEthernetNetPortAdminState,
    cmEthernetNetPortOperationalState, cmEthernetNetPortSecondaryState,
    cmEthernetNetPortMTU, cmEthernetNetPortMediaType,
    cmEthernetNetPortConfigSpeed, cmEthernetNetPortNegotiatedSpeed,
    cmEthernetNetPortMDIXType,
    cmEthernetNetPortJumboFramesEnabled, cmEthernetNetPortSfpVendorName,
    cmEthernetNetPortSfpPartNumber, cmEthernetNetPortSfpSerialNumber,
    cmEthernetNetPortSfpDateOfManufacture, cmEthernetNetPortSfpConnectorValue,
    cmEthernetNetPortInitiateDiag, cmEthernetNetPortDiagnosePair1Cond,
    cmEthernetNetPortDiagnosePair2Cond, cmEthernetNetPortDiagnosePair3Cond,
    cmEthernetNetPortDiagnosePair4Cond, cmEthernetNetPortDiagnoseAutoNegCond,
    cmEthernetNetPortDiagnoseLpbkCond, cmEthernetNetPortDiagnoseEfmLpbkCond,
    cmEthernetNetPortDiagnoseResult,cmEthernetNetPortDiagnoseTestStatus,
    cmEthernetNetPortDiagnoseTestTime,
    cmEthernetNetPortLoopbackConfig, cmEthernetNetPortLoopbackStatus,
    cmEthernetNetPortLoopbackTime,
    cmEthernetNetPortLoopbackSwapSADA, cmEthernetNetPortOuterVlanLoopbackMask,
    cmEthernetNetPortOuterVlanLoopback1, cmEthernetNetPortOuterVlanLoopback2,
    cmEthernetNetPortOuterVlanLoopback3, 
    cmEthernetNetPortInnerVlanLoopbackMask,
    cmEthernetNetPortInnerVlanLoopback1, cmEthernetNetPortInnerVlanLoopback2, 
    cmEthernetNetPortInnerVlanLoopback3,
    cmEthernetNetPortLinkLossFwdEnabled, cmEthernetNetPortLinkLossFwdSignalType,
    cmEthernetNetPortLinkLossFwdTriggerTypes,cmEthernetNetPortLinkLossFwdDelay,
    cmEthernetNetPortLinkLossFwdActive, 
    cmEthernetNetPortLinkLossFwdPartnerEnabled,
    cmEthernetNetPortLinkLossFwdLocalLinkId, 
    cmEthernetNetPortLinkLossFwdRemoteLinkIds,
    cmEthernetNetPortOamId, cmEthernetNetPortOamAdminDisposition,
    cmEthernetNetPortOamDiscoveryState,
    cmEthernetNetPortOamLocalVarRtrvsEnabled, 
    cmEthernetNetPortOamLocalLinkEventsEnabled,
    cmEthernetNetPortOamLocalOamLoopbacksSupported,
    cmEthernetNetPortOamLocalUnidirSupportEnabled,
    cmEthernetNetPortOamLocalMaxPDUSize,
    cmEthernetNetPortOamLocalMode, cmEthernetNetPortOamRemoteMacAddress,
    cmEthernetNetPortOamRemoteVarRtrvsEnabled,
    cmEthernetNetPortOamRemoteLinkEventsEnabled,
    cmEthernetNetPortOamRemoteOamLoopbacksSupported,
    cmEthernetNetPortOamRemoteUnidirSupportEnabled,
    cmEthernetNetPortOamRemoteMaxPDUSize, cmEthernetNetPortOamRemoteMode,
    cmEthernetNetPortRxPauseDisposition, cmEthernetNetPortTxPauseEnabled,
    cmEthernetNetPortAfpType,

    cmEthernetNetPortMDIXStatus, cmEthernetNetPortSfpReach,
    cmEthernetNetPortSfpLaserWaveLength,
    cmEthernetNetPortSfpMediaType, cmEthernetNetPortOamEnabled,
    cmEthernetNetPortOamAdminState,
    cmEthernetNetPortShapingEnabled,
    cmEthernetNetPortShapedSpeedLo, cmEthernetNetPortShapedSpeedHi,
    cmEthernetNetPortQinQEtherType, cmEthernetNetPortLinkLossFwdTxActionType,
    cmEthernetNetPortLinkLossFwdRxRLDLinkIds,
    cmEthernetNetPortAutoDiagEnabled,
    cmEthernetNetPortSyncEEnabled, cmEthernetNetPortQLModeEnabled,
    cmEthernetNetPortExpectedQL, cmEthernetNetPortAssumedQL,
    cmEthernetNetPortReceivedQL, cmEthernetNetPortTransmitQL,

    cmEthernetNetPortCpdIndex, cmEthernetNetPortCpdFilterType,
    cmEthernetNetPortCpdFilterDescr, cmEthernetNetPortCpdDispType,
    cmEthernetNetPortCpdMacAddressMatch, cmEthernetNetPortCpdMacAddressMask,
    cmEthernetNetPortCpdEthertype, cmEthernetNetPortCpdEthertypeMask,
    cmEthernetNetPortCpdSubtype, cmEthernetNetPortCpdSubtypeMask,

    cmEthernetMgmtPortIndex, cmEthernetMgmtPortEntityIndex,
    cmEthernetMgmtPortAdminState, cmEthernetMgmtPortOperationalState,
    cmEthernetMgmtPortSecondaryState, cmEthernetMgmtPortMTU,
    cmEthernetMgmtPortConfigSpeed, cmEthernetMgmtPortNegotiatedSpeed,
    cmEthernetMgmtPortMDIXType,
    cmEthernetMgmtPortMDIXStatus,

    cmPrioMapIndex, cmPrioMapInPriority, cmPrioMapXTagControl,
    cmPrioMapXTagPriority, cmPrioMapCOS, cmPrioMapOuterTagPriority,
    cmPrioMapInnerTagPriority,

    cmQosFlowPolicerTypeIndex, cmQosFlowPolicerIndex,
    cmQosFlowPolicerDirection, cmQosFlowPolicerAdminState, 
    cmQosFlowPolicerOperationalState,
    cmQosFlowPolicerSecondaryState,
    cmQosFlowPolicerCIRLo, cmQosFlowPolicerCIRHi, cmQosFlowPolicerEIRLo,
    cmQosFlowPolicerEIRHi, cmQosFlowPolicerCBS,
    cmQosFlowPolicerEBS, cmQosFlowPolicerAlgorithm,
    cmQosFlowPolicerColorMode, cmQosFlowPolicerColorMarkingFlag,
    cmQosFlowPolicerCouplingFlag, cmQosFlowPolicerAssociatedShaper,
    cmQosFlowPolicerStorageType, cmQosFlowPolicerRowStatus,

    cmAccPortQosShaperIndex, cmAccPortQosShaperDirection,
    cmAccPortQosShaperAdminState, cmAccPortQosShaperOperationalState,
    cmAccPortQosShaperSecondaryState, cmAccPortQosShaperCIRLo,
    cmAccPortQosShaperCIRHi, cmAccPortQosShaperEIRLo,
    cmAccPortQosShaperEIRHi, cmAccPortQosShaperCBS,
    cmAccPortQosShaperEBS, cmAccPortQosShaperBufferSize, cmAccPortQosShaperCOS,

    cmEthernetAccPortCpdV2Index, cmEthernetAccPortCpdV2CiscoGroupDispType,
    cmEthernetAccPortCpdV2IslDispType, cmEthernetAccPortCpdV2PagpDispType,
    cmEthernetAccPortCpdV2UdldDispType, cmEthernetAccPortCpdV2CdpDispType,
    cmEthernetAccPortCpdV2VtpDispType, cmEthernetAccPortCpdV2DtpDispType,
    cmEthernetAccPortCpdV2PvstpPlusDispType, 
    cmEthernetAccPortCpdV2UplinkFastDispType,
    cmEthernetAccPortCpdV2VlanBridgeDispType,
    cmEthernetAccPortCpdV2L2PTDispType, 
    cmEthernetAccPortCpdV2BridgeGroupDispType,
    cmEthernetAccPortCpdV2BPDUDispType, cmEthernetAccPortCpdV2PauseDispType,
    cmEthernetAccPortCpdV2LACPDispType,
    cmEthernetAccPortCpdV2LACPMarkerDispType,
    cmEthernetAccPortCpdV2EfmOamDispType,
    cmEthernetAccPortCpdV2SSMDispType,
    cmEthernetAccPortCpdV2PortAuthenDispType,
    cmEthernetAccPortCpdV2BridgeReservedDispType,
    cmEthernetAccPortCpdV2LANBridgesDispType,
    cmEthernetAccPortCpdV2GARPGroupDispType,
    cmEthernetAccPortCpdV2GMRPDispType, cmEthernetAccPortCpdV2GVRPDispType,
    cmEthernetAccPortCpdV2GARPDispType,

    cmFlowCpdV2Index, cmFlowCpdV2CiscoGroupDispType,
    cmFlowCpdV2IslDispType, cmFlowCpdV2PagpDispType,
    cmFlowCpdV2UdldDispType, cmFlowCpdV2CdpDispType,
    cmFlowCpdV2VtpDispType, cmFlowCpdV2DtpDispType,
    cmFlowCpdV2PvstpPlusDispType, 
    cmFlowCpdV2UplinkFastDispType,
    cmFlowCpdV2VlanBridgeDispType,
    cmFlowCpdV2L2PTDispType, 
    cmFlowCpdV2BridgeGroupDispType,
    cmFlowCpdV2BPDUDispType, cmFlowCpdV2PauseDispType,
    cmFlowCpdV2LACPDispType,
    cmFlowCpdV2LACPMarkerDispType,
    cmFlowCpdV2EfmOamDispType,
    cmFlowCpdV2SSMDispType,            
    cmFlowCpdV2PortAuthenDispType,
    cmFlowCpdV2BridgeReservedDispType,
    cmFlowCpdV2LANBridgesDispType,
    cmFlowCpdV2GARPGroupDispType,
    cmFlowCpdV2GMRPDispType, cmFlowCpdV2GVRPDispType, cmFlowCpdV2GARPDispType,
    cmFlowCpdV2ActiveControlProtocols, 

    cmEthernetNetPortCpdV2Index, cmEthernetNetPortCpdV2CiscoGroupDispType,
    cmEthernetNetPortCpdV2IslDispType, cmEthernetNetPortCpdV2PagpDispType,
    cmEthernetNetPortCpdV2UdldDispType, cmEthernetNetPortCpdV2CdpDispType,
    cmEthernetNetPortCpdV2VtpDispType, cmEthernetNetPortCpdV2DtpDispType,
    cmEthernetNetPortCpdV2PvstpPlusDispType, 
    cmEthernetNetPortCpdV2UplinkFastDispType,
    cmEthernetNetPortCpdV2VlanBridgeDispType,
    cmEthernetNetPortCpdV2L2PTDispType, 
    cmEthernetNetPortCpdV2BridgeGroupDispType,
    cmEthernetNetPortCpdV2BPDUDispType, cmEthernetNetPortCpdV2PauseDispType,
    cmEthernetNetPortCpdV2LACPDispType,
    cmEthernetNetPortCpdV2LACPMarkerDispType,
    cmEthernetNetPortCpdV2EfmOamDispType,
    cmEthernetNetPortCpdV2SSMDispType,
    cmEthernetNetPortCpdV2PortAuthenDispType,
    cmEthernetNetPortCpdV2BridgeReservedDispType,
    cmEthernetNetPortCpdV2LANBridgesDispType,
    cmEthernetNetPortCpdV2GARPGroupDispType,
    cmEthernetNetPortCpdV2GMRPDispType, cmEthernetNetPortCpdV2GVRPDispType,
    cmEthernetNetPortCpdV2GARPDispType,

    bitsPortTypeIndex, bitsPortIndex, bitsPortIfIndex, bitsPortEntityIndex,
    bitsPortAdminState, bitsPortOperationalState, bitsPortSecondaryState,
    bitsPortType, bitsPortLineType, bitsPortLineCode, bitsPortFrameFormat,
    bitsPortSaBitDesignation, bitsPortQLModeEnabled, bitsPortExpectedQL,
    bitsPortAssumedQL, bitsPortReceivedQL, bitsPortTransmitQL,
    bitsPortSquelchQL, bitsPortLineBuildOut, bitsPortImpedance,

    ieee1588EthernetPortIndex, ieee1588EthernetPortIfIndex,
    ieee1588EthernetPortEntityIndex, ieee1588EthernetPortAdminState,
    ieee1588EthernetPortOperationalState, ieee1588EthernetPortSecondaryState,
    ieee1588EthernetPortMTU, ieee1588EthernetPortMediaType,
    ieee1588EthernetPortConfigSpeed, ieee1588EthernetPortNegotiatedSpeed,
    ieee1588EthernetPortMDIXType,

    gps10MHzPortIndex, gps10MHzPortIfIndex, gps10MHzPortEntityIndex,
    gps10MHzPortAdminState, gps10MHzPortOperationalState,
    gps10MHzPortSecondaryState, gps10MHzPortSignalDirection,
    gps10MHzPortSquelchControl, gps10MHzPortSquelchQL,
    gps10MHzPortFrequencySource,
    gps10MHzPortClockClass,
    gps10MHzPortClockAccuracy,
    gps10MHzPortTimeSource, gps10MHzPortAssumedQL,

    cmEthernetNetPortClbIndex, cmEthernetNetPortClbEnabled, 
    cmEthernetNetPortClbLength, cmEthernetNetPortClbDescr,

    cmNetPortPrioMapIndex, cmNetPortPrioMapInPriority,
    cmNetPortPrioMapCOS, cmNetPortPrioMapOuterTagPriority,

    cmAccPortPcpDEEncIndex, cmAccPortPcpDEEncInPriority,
    cmAccPortPcpDEEncDropIneligiblePrio, cmAccPortPcpDEEncDropEligiblePrio,
    cmAccPortPcpDEDecIndex, cmAccPortPcpDEDecInPriority,
    cmAccPortPcpDEDecOutPriority, cmAccPortPcpDEDecDropEligible,
    cmAccPortPcpDEPairIndex, cmAccPortPcpDEDropIneligiblePrio,
    cmAccPortPcpDEDropEligiblePrio,

    cmNetPortPcpDEEncIndex, cmNetPortPcpDEEncInPriority,
    cmNetPortPcpDEEncDropIneligiblePrio, cmNetPortPcpDEEncDropEligiblePrio,
    cmNetPortPcpDEDecIndex, cmNetPortPcpDEDecInPriority,
    cmNetPortPcpDEDecOutPriority, cmNetPortPcpDEDecDropEligible,
    cmNetPortPcpDEPairIndex, cmNetPortPcpDEDropIneligiblePrio,
    cmNetPortPcpDEDropEligiblePrio,
    
    cmPortCpdProfileIndex, cmPortCpdProfileName,
    cmPortCpdProfileCiscoGroupDispType,
    cmPortCpdProfileIslDispType, cmPortCpdProfilePagpDispType,
    cmPortCpdProfileUdldDispType, cmPortCpdProfileCdpDispType,
    cmPortCpdProfileVtpDispType, cmPortCpdProfileDtpDispType,
    cmPortCpdProfilePvstpPlusDispType, cmPortCpdProfileUplinkFastDispType,
    cmPortCpdProfileVlanBridgeDispType, cmPortCpdProfileL2PTDispType,
    cmPortCpdProfileBridgeGroupDispType, cmPortCpdProfileBPDUDispType,
    cmPortCpdProfilePauseDispType, cmPortCpdProfileLACPDispType,
    cmPortCpdProfileLACPMarkerDispType, cmPortCpdProfileEfmOamDispType,
    cmPortCpdProfileSSMDispType, cmPortCpdProfilePortAuthenDispType, 
    cmPortCpdProfileBridgeReservedDispType, cmPortCpdProfileLANBridgesDispType,
    cmPortCpdProfileGARPGroupDispType, cmPortCpdProfileGMRPDispType,
    cmPortCpdProfileGVRPDispType, cmPortCpdProfileGARPDispType,
    cmPortCpdProfileLldpDispType,
    cmPortCpdProfileStorageType,cmPortCpdProfileRowStatus,

    cmFlowPointCpdProfileIndex, cmFlowPointCpdProfileName,
    cmFlowPointCpdProfileCiscoGroupDispType,
    cmFlowPointCpdProfileIslDispType, cmFlowPointCpdProfilePagpDispType,
    cmFlowPointCpdProfileUdldDispType, cmFlowPointCpdProfileCdpDispType,
    cmFlowPointCpdProfileVtpDispType, cmFlowPointCpdProfileDtpDispType,
    cmFlowPointCpdProfilePvstpPlusDispType, cmFlowPointCpdProfileUplinkFastDispType,
    cmFlowPointCpdProfileVlanBridgeDispType, cmFlowPointCpdProfileL2PTDispType,
    cmFlowPointCpdProfileBridgeGroupDispType, cmFlowPointCpdProfileBPDUDispType,
    cmFlowPointCpdProfilePauseDispType, cmFlowPointCpdProfileLACPDispType,
    cmFlowPointCpdProfileLACPMarkerDispType, cmFlowPointCpdProfileEfmOamDispType,
    cmFlowPointCpdProfileSSMDispType, cmFlowPointCpdProfilePortAuthenDispType, 
    cmFlowPointCpdProfileBridgeReservedDispType, cmFlowPointCpdProfileLANBridgesDispType,
    cmFlowPointCpdProfileGARPGroupDispType, cmFlowPointCpdProfileGMRPDispType,
    cmFlowPointCpdProfileGVRPDispType, cmFlowPointCpdProfileGARPDispType,
    cmFlowPointCpdProfileLldpDispType,
    cmFlowPointCpdProfileStorageType,cmFlowPointCpdProfileRowStatus,
    
    cmEthernetTrafficPortCpdIndex,cmEthernetTrafficPortAssociatedCpdProfile,
    
    cmEthernetFlowPointCpdIndex,cmEthernetFlowPointAssociatedCpdProfile,
    
    cmEthernetTrafficPortIndex,cmEthernetTrafficPortIfIndex,
    cmEthernetTrafficPortEntityIndex,cmEthernetTrafficPortAdminState,
    cmEthernetTrafficPortOperationalState,cmEthernetTrafficPortSecondaryState,
    cmEthernetTrafficPortMTU,cmEthernetTrafficPortMediaType,
    cmEthernetTrafficPortConfigSpeed,cmEthernetTrafficPortNegotiatedSpeed,
    cmEthernetTrafficPortMDIXType,cmEthernetTrafficPortMDIXStatus,
    cmEthernetTrafficPortSfpVendorName,cmEthernetTrafficPortSfpPartNumber,
    cmEthernetTrafficPortSfpSerialNumber,cmEthernetTrafficPortSfpDateOfManufacture,
    cmEthernetTrafficPortSfpConnectorValue,
    cmEthernetTrafficPortSfpLinkLength,cmEthernetTrafficPortSfpLaserWaveLength,
    cmEthernetTrafficPortSfpMediaType,cmEthernetTrafficPortLoopbackConfig,
    cmEthernetTrafficPortLoopbackStatus,cmEthernetTrafficPortLoopbackTime,
    cmEthernetTrafficPortLoopbackSwapSADA,cmEthernetTrafficPortOuterVlanLoopbackMask,
    cmEthernetTrafficPortOuterVlanLoopback1,cmEthernetTrafficPortOuterVlanLoopback2,
    cmEthernetTrafficPortOuterVlanLoopback3,cmEthernetTrafficPortLinkLossFwdEnabled,
    cmEthernetTrafficPortLinkLossFwdSignalType,cmEthernetTrafficPortLinkLossFwdTriggerTypes,
    cmEthernetTrafficPortLinkLossFwdDelay,cmEthernetTrafficPortLinkLossFwdActive,
    cmEthernetTrafficPortLinkLossFwdPartnerEnabled,cmEthernetTrafficPortLinkLossFwdLocalLinkId,
    cmEthernetTrafficPortLinkLossFwdRemoteLinkIds,cmEthernetTrafficPortLinkLossFwdTxActionType,
    cmEthernetTrafficPortLinkLossFwdRxRLDLinkIds,cmEthernetTrafficPortOamId,
    cmEthernetTrafficPortOamDiscoveryState,
    cmEthernetTrafficPortOamLocalVarRtrvsEnabled,cmEthernetTrafficPortOamLocalLinkEventsEnabled,
    cmEthernetTrafficPortOamLocalOamLoopbacksSupported,cmEthernetTrafficPortOamLocalUnidirSupportEnabled,
    cmEthernetTrafficPortOamLocalMaxPDUSize,cmEthernetTrafficPortOamLocalMode,
    cmEthernetTrafficPortOamRemoteMacAddress,cmEthernetTrafficPortOamRemoteVarRtrvsEnabled,
    cmEthernetTrafficPortOamRemoteLinkEventsEnabled,cmEthernetTrafficPortOamRemoteOamLoopbacksSupported,
    cmEthernetTrafficPortOamRemoteUnidirSupportEnabled,cmEthernetTrafficPortOamRemoteMaxPDUSize,
    cmEthernetTrafficPortOamRemoteMode,cmEthernetTrafficPortOamEnabled,
    cmEthernetTrafficPortOamAdminState,
    cmEthernetTrafficPortSvcType,
    cmEthernetTrafficPortTxPauseEnabled,cmEthernetTrafficPortAfpType,
    cmEthernetTrafficPortShapingEnabled,cmEthernetTrafficPortShapedSpeedLo,
    cmEthernetTrafficPortShapedSpeedHi,cmEthernetTrafficPortQinQEtherType,
    cmEthernetTrafficPortEgressVlanTrunkingEnabled,cmEthernetTrafficPortIngressPushPVIDEnabled,
    cmEthernetTrafficPortEgressPopPVIDEnabled,cmEthernetTrafficPortPortVlanId,
    cmEthernetTrafficPortPortVlanPriority,cmEthernetTrafficPortPriorityVlanId,
    cmEthernetTrafficPortIngressPrioMapMode,cmEthernetTrafficPortIngressCOSPriority,
    cmEthernetTrafficPortEgressPopPriorityVidEnabled,
    cmEthernetTrafficPortSyncEEnabled,
    cmEthernetTrafficPortQLModeEnabled,cmEthernetTrafficPortExpectedQL,
    cmEthernetTrafficPortAssumedQL,cmEthernetTrafficPortReceivedQL,
    cmEthernetTrafficPortTransmitQL,cmEthernetTrafficPortTagFrameControl,
    cmEthernetTrafficPortRxPauseEnabled, cmEthernetTrafficPortPhyType,
    cmEthernetTrafficPortSfpLaserWaveLengthPicometer, cmEthernetTrafficPortRowStatus,
    cmEthernetTrafficPortSSMRemoteMacAddress, cmEthernetTrafficPortInnerVlanLoopbackMask,
    cmEthernetTrafficPortInnerVlanLoopback1, cmEthernetTrafficPortInnerVlanLoopback2,
    cmEthernetTrafficPortInnerVlanLoopback3,
    
    cmIngressPrioMapIndex, cmIngressPrioMapInPriority,cmIngressPrioMapCOS,
    
    cmEgressCOSIndex, cmEgressOuterTagCtrl,
    cmEgressCOS,cmEgressOuterTagPriority,
    
    cmElineFlowIndex,cmElineFlowCircuitName,
    cmElineFlowAdminState, cmElineFlowOperationalState,
    cmElineFlowSecondaryState,cmElineFlowFP1,cmElineFlowFP2,
    cmElineFlowStorageType,cmElineFlowRowStatus,
    
    cmFlowPointIndex,cmFlowPointCircuitName,
    cmFlowPointAdminState,cmFlowPointOperationalState,
    cmFlowPointSecondaryState,cmFlowPointAssociatedFlowId,
    cmFlowPointIngressMultiCOS,cmFlowPointIngressCOS,
    cmFlowPointIngressVlanMemberList,cmFlowPointVlanMemberAction,
    cmFlowPointAssociatedAclProfile,cmFlowPointSESFramesLossThresholdRatio,
    cmFlowPointVlanMemberActionVlan,cmFlowPointIngressUntaggedFrameEnabled,
    cmFlowPointCTagControl,cmFlowPointCTagVlanId,
    cmFlowPointCTagVlanPriority,cmFlowPointSTagControl,
    cmFlowPointSTagVlanId,cmFlowPointSTagVlanPriority,
    cmFlowPointEgressOuterTagPrioMapEnabled,cmFlowPointColorMarkingSupported, 
    cmFlowPointStorageType,
    cmFlowPointRowStatus,
    
    cmQosPolicerV2Index,cmQosPolicerV2AdminState,
    cmQosPolicerV2OperationalState,cmQosPolicerV2SecondaryState,
    cmQosPolicerV2ColorMarkingEnabled,cmQosPolicerV2AssociatedProfile,
    cmQosPolicerV2StorageType,cmQosPolicerV2RowStatus,
    
    cmQosShaperV2Index, cmQosShaperV2AdminState,
    cmQosShaperV2OperationalState, cmQosShaperV2SecondaryState,
    cmQosShaperV2AssociatedQueueProfile, 
    cmQosShaperV2CIRLo, cmQosShaperV2CIRHi,
    cmQosShaperV2EIRLo, cmQosShaperV2EIRHi,cmQosShaperV2IngressAverageFrameSize,
    cmQosShaperV2StorageType, cmQosShaperV2RowStatus, 
    cmQosShaperV2AdditionalCIRLo, cmQosShaperV2AdditionalCIRHi,
    
    cmTrafficPortQosShaperIndex, cmTrafficPortQosShaperAdminState,
    cmTrafficPortQosShaperOperationalState, cmTrafficPortQosShaperSecondaryState,
    cmTrafficPortQosShaperAssociatedQueueProfile, cmTrafficPortQosShaperBufferSize,
    cmTrafficPortQosShaperCIRLo, cmTrafficPortQosShaperCIRHi,
    cmTrafficPortQosShaperEIRLo, cmTrafficPortQosShaperEIRHi,
    cmTrafficPortQosShaperStorageType, cmTrafficPortQosShaperRowStatus, 
    cmTrafficPortQosShaperIngressAverageFrameSize, cmTrafficPortQosShaperAdditionalCIRLo,
    cmTrafficPortQosShaperAdditionalCIRHi,
    
    cmQosPolicerProfileIndex,cmQosPolicerProfileName,
    cmQosPolicerProfileCIRLo,cmQosPolicerProfileCIRHi,
    cmQosPolicerProfileEIRLo,cmQosPolicerProfileEIRHi,
    cmQosPolicerProfileCBS,cmQosPolicerProfileEBS,
    cmQosPolicerProfileColorMode,
    cmQosPolicerProfileCouplingFlag,
    cmQosPolicerProfileStorageType,cmQosPolicerProfileRowStatus,

    cmQosQueueProfileIndex,cmQosQueueProfileName,
    cmQosQueueProfileBufferSize,cmQosQueueProfileREDEnabled,
    cmQosQueueProfileStorageType,cmQosQueueProfileRowStatus,
    
    cmOAMFlowPointIndex,cmOAMFlowPointCircuitName,
    cmOAMFlowPointAdminState,cmOAMFlowPointOperationalState,
    cmOAMFlowPointSecondaryState,cmOAMFlowPointIngressVlanMemberList,
    cmOAMFlowPointVlanMemberAction,cmOAMFlowPointIngressUntaggedFrameSupported,
    cmOAMFlowPointSESFramesLossThresholdRatio,
    cmOAMFlowPointStorageType,cmOAMFlowPointRowStatus,

    cmTrafficAclRulesIndex, cmTrafficAclFilterAction,
    cmTrafficAclFilterType,
    cmTrafficAclEnabled, cmTrafficAclSrcMacAddr,
    cmTrafficAclSrcMacAddrEnabled, cmTrafficAclDstMacAddr,
    cmTrafficAclDstMacAddrEnabled, 
    cmTrafficAclSrcIpFilterEnabled, cmTrafficAclDstIpFilterEnabled, 
    cmTrafficAclSrcIpV4Addr, cmTrafficAclSrcIpV4AddrMask,
    cmTrafficAclDstIpV4Addr, cmTrafficAclDstIpV4AddrMask,
    cmTrafficAclSrcIpV6Addr, cmTrafficAclSrcIpV6AddrMask,
    cmTrafficAclDstIpV6Addr, cmTrafficAclDstIpV6AddrMask, 
    cmTrafficAclTcpUdpSrcPortNum, cmTrafficAclTcpUdpSrcPortMask,
    cmTrafficAclTcpUdpSrcPortEnabled, cmTrafficAclTcpUdpDstPortNum,
    cmTrafficAclTcpUdpDstPortMask, cmTrafficAclTcpUdpDstPortEnabled,
    cmTrafficAclIpQosType, cmTrafficAclIpQosValue,
    cmTrafficAclIpQosTypeEnabled, cmTrafficAclVlanId ,
    cmTrafficAclVlanIdEnabled, cmTrafficAclVlanPriority,
    cmTrafficAclVlanPriorityEnabled, cmTrafficAclProtocolType,
    cmTrafficAclProtocolTypeEnabled, cmTrafficAclStorageType,
    cmTrafficAclRowStatus,
    
    f3NetPortQosShaperIndex, f3NetPortQosShaperDirection,
    f3NetPortQosShaperAdminState, f3NetPortQosShaperOperationalState,
    f3NetPortQosShaperSecondaryState, f3NetPortQosShaperCIRLo,
    f3NetPortQosShaperCIRHi, f3NetPortQosShaperEIRLo,
    f3NetPortQosShaperEIRHi, f3NetPortQosShaperCBS,
    f3NetPortQosShaperEBS, f3NetPortQosShaperBufferSize,
    f3NetPortQosShaperCOS, f3NetPortQosShaperSoamCIRLo,
    f3NetPortQosShaperSoamCIRHi, f3NetPortQosShaperSoamEIRLo,
    f3NetPortQosShaperSoamEIRHi,
    
    f3Usb3GDCNPortIndex, f3Usb3GDCNPortIfIndex,
    f3Usb3GDCNPortEntityIndex, f3Usb3GDCNPortAdminState,
    f3Usb3GDCNPortOperationalState, f3Usb3GDCNPortSecondaryState,
    f3Usb3GDCNPortVendorName, f3Usb3GDCNPortModel,
    f3Usb3GDCNPortFSN, f3Usb3GDCNPortIMEI,
    f3Usb3GDCNPortHardwareVersion, f3Usb3GDCNPortFirmwareVersion,
    f3Usb3GDCNPortSIMStatus, f3Usb3GDCNPortPINLeftChances,
    f3Usb3GDCNPortPUKLeftChances, f3Usb3GDCNPortConnectionStatus,
    f3Usb3GDCNPortRSSI, f3Usb3GDCNPortSpeed,
    f3Usb3GDCNPortMTU, f3Usb3GDCNPortProviderName,
    f3Usb3GDCNPortDNS1, f3Usb3GDCNPortDNS2,
    f3Usb3GDCNPortAPN, f3Usb3GDCNPortUserName,
    f3Usb3GDCNPortPassword, f3Usb3GDCNPortDailNumber,
    f3Usb3GDCNPortRedialTimer, f3Usb3GDCNPortCurrentPinCode,
    f3Usb3GDCNPortNewPinCode, f3Usb3GDCNPortConfirmPinCode,
    f3Usb3GDCNPortCurrentPukCode, f3Usb3GDCNPINCodeAction,
    f3Usb3GDCNPortStorageType, f3Usb3GDCNPortRowStatus,
    f3Usb3GDCNPortIMSI, f3Usb3GDCNPortPINStatus, f3UsbDCNPortMobileNetworkType,
    
    ocnStmIndex, ocnStmIfIndex,
    ocnStmEntityIndex, ocnStmAdminState, 
    ocnStmOperationalState, ocnStmSecondaryState, 
    ocnStmSfpVendorName, ocnStmSfpPartNumber, 
    ocnStmSfpSerialNumber, ocnStmSfpDateOfManufacture, 
    ocnStmSfpConnectorValue, ocnStmSfpLinkLength,
    ocnStmSfpLaserWaveLength, ocnStmSfpLaserWaveLengthPicometer,
    ocnStmSfpMediaType, ocnStmMultiplexingStructures, 
    ocnStmEoTDMMode, ocnStmLoopbackConfig, 
    ocnStmLoopbackStatus, ocnStmLoopbackTime, 
    ocnStmInsertingAIS, ocnStmBerExcThreshold, 
    ocnStmBerDegThreshold, ocnStmRxTrailTrace, 
    ocnStmTxTrailTrace, ocnStmExpectedTrailTrace, 
    ocnStmTrailTraceFormat, ocnStmQLModeEnabled, 
    ocnStmExpectedQL, ocnStmAssumedQL, 
    ocnStmReceivedQL, ocnStmTransmitQL,
    
    stsVcPathParentIfIndex, stsVcPathIndex,
    stsVcPathIfIndex, stsVcPathAdminState,
    stsVcPathOperationalState, stsVcPathSecondaryState,
    stsVcPathLoopbackConfig, stsVcPathLoopbackStatus,
    stsVcPathLoopbackTime, stsVcPathInsertingAIS,
    stsVcPathBerExcThreshold, stsVcPathBerDegThreshold,
    stsVcPathTrailTraceFormat, stsVcPathRxTrailTrace,
    stsVcPathTxTrailTrace, stsVcPathExpectedTrailTrace,
    stsVcPathRxSignalLabel, stsVcPathTxSignalLabel,
    stsVcPathExpectedSignalLabel, stsVcPathRowStatus,
    vtVcPathRowStatus,
    
    vtVcPathParentIfIndex, 
    vtVcPathIndex, vtVcPathIfIndex, 
    vtVcPathAdminState, vtVcPathOperationalState, 
    vtVcPathSecondaryState, vtVcPathLoopbackConfig, 
    vtVcPathLoopbackStatus, vtVcPathLoopbackTime, 
    vtVcPathInsertingAIS, vtVcPathBerExcThreshold, 
    vtVcPathBerDegThreshold, vtVcPathTrailTraceFormat, 
    vtVcPathRxTrailTrace, vtVcPathTxTrailTrace, 
    vtVcPathExpectedTrailTrace, vtVcPathRxSignalLabel, 
    vtVcPathTxSignalLabel, vtVcPathExpectedSignalLabel,
    
    e1t1ParentIfIndex, e1t1Index,
    e1t1IfIndex, e1t1AdminState,
    e1t1OperationalState, e1t1SecondaryState,
    e1t1LoopbackConfig, e1t1LoopbackStatus,
    e1t1LoopbackTime, e1t1RemoteLoopbackRequest,
    e1t1InsertingAIS, e1t1RowStatus,

    e3t3ParentIfIndex, e3t3Index,
    e3t3IfIndex, e3t3EntityIndex,
    e3t3AdminState, e3t3OperationalState, 
    e3t3SecondaryState, e3t3LoopbackConfig, 
    e3t3LoopbackStatus, e3t3LoopbackTime, 
    e3t3RemoteLoopbackRequest, e3t3InsertingAIS, 
    e3t3CBitEnable, e3t3T3Channelized, 
    e3t3RowStatus,
    
    cmEthernetTrafficPortTDMEncapsulation, cmEthernetTrafficPortRelatedVCG
    
    }
    STATUS  deprecated
    DESCRIPTION
            "*********************THIS GROUP IS NOW DEPRECATED *********************
             A collection of objects used to manage the CM Facility
             group."
    ::= { cmFacilityGroups 1 }

ethernetAccessPortGroup OBJECT-GROUP
    OBJECTS {
        cmEthernetAccPortIndex, cmEthernetAccPortIfIndex,
        cmEthernetAccPortOperationalState, cmEthernetAccPortSecondaryState,
        cmEthernetAccPortMTU, cmEthernetAccPortMediaType,
        cmEthernetAccPortConfigSpeed, cmEthernetAccPortNegotiatedSpeed,
        cmEthernetAccPortMDIXType,
        cmEthernetAccPortJumboFramesEnabled, cmEthernetAccPortSfpVendorName,
        cmEthernetAccPortSfpPartNumber, cmEthernetAccPortSfpSerialNumber,
        cmEthernetAccPortSfpDateOfManufacture,
        cmEthernetAccPortSfpConnectorValue,
        cmEthernetAccPortInitiateDiag, cmEthernetAccPortDiagnosePair1Cond,
        cmEthernetAccPortDiagnosePair2Cond, cmEthernetAccPortDiagnosePair3Cond,
        cmEthernetAccPortDiagnosePair4Cond, cmEthernetAccPortDiagnoseAutoNegCond,
        cmEthernetAccPortDiagnoseLpbkCond, cmEthernetAccPortDiagnoseEfmLpbkCond,
        cmEthernetAccPortDiagnoseResult,cmEthernetAccPortDiagnoseTestStatus,
        cmEthernetAccPortDiagnoseTestTime,
        cmEthernetAccPortLoopbackConfig, cmEthernetAccPortLoopbackStatus,
        cmEthernetAccPortLoopbackTime,
        cmEthernetAccPortLoopbackSwapSADA, cmEthernetAccPortOuterVlanLoopbackMask,
        cmEthernetAccPortOuterVlanLoopback1, cmEthernetAccPortOuterVlanLoopback2,
        cmEthernetAccPortOuterVlanLoopback3, 
        cmEthernetAccPortInnerVlanLoopbackMask,
        cmEthernetAccPortInnerVlanLoopback1, cmEthernetAccPortInnerVlanLoopback2,
        cmEthernetAccPortInnerVlanLoopback3,
        cmEthernetAccPortLinkLossFwdEnabled, 
        cmEthernetAccPortLinkLossFwdSignalType,
        cmEthernetAccPortLinkLossFwdTriggerTypes,
        cmEthernetAccPortLinkLossFwdDelay, cmEthernetAccPortLinkLossFwdActive,
        cmEthernetAccPortLinkLossFwdPartnerEnabled,
        cmEthernetAccPortLinkLossFwdLocalLinkId,
        cmEthernetAccPortLinkLossFwdRemoteLinkIds,
        cmEthernetAccPortOamId, cmEthernetAccPortOamAdminDisposition,
        cmEthernetAccPortOamDiscoveryState, 
        cmEthernetAccPortOamLocalVarRtrvsEnabled,
        cmEthernetAccPortOamLocalLinkEventsEnabled,
        cmEthernetAccPortOamLocalOamLoopbacksSupported,
        cmEthernetAccPortOamLocalUnidirSupportEnabled,
        cmEthernetAccPortOamLocalMaxPDUSize, cmEthernetAccPortOamLocalMode,
        cmEthernetAccPortOamRemoteMacAddress, 
        cmEthernetAccPortOamRemoteVarRtrvsEnabled,
        cmEthernetAccPortOamRemoteLinkEventsEnabled,
        cmEthernetAccPortOamRemoteOamLoopbacksSupported,
        cmEthernetAccPortOamRemoteUnidirSupportEnabled,
        cmEthernetAccPortOamRemoteMaxPDUSize,
        cmEthernetAccPortOamRemoteMode, cmEthernetAccPortMode, 
        cmEthernetAccPortSvcType, cmEthernetAccPortRxPauseDisposition, 
        cmEthernetAccPortTxPauseEnabled, cmEthernetAccPortAfpType,

        cmEthernetAccPortMDIXStatus, cmEthernetAccPortSfpReach,
        cmEthernetAccPortSfpLaserWaveLength,
        cmEthernetAccPortSfpMediaType, cmEthernetAccPortOamEnabled,
        cmEthernetAccPortOamAdminState,
        cmEthernetAccPortShapingEnabled,
        cmEthernetAccPortShapedSpeedLo, cmEthernetAccPortShapedSpeedHi,
        cmEthernetAccPortQinQEtherType, cmEthernetAccPortRxPauseEnabled,
        cmEthernetAccPortAutoDiagEnabled, cmEthernetAccPortLinkLossFwdTxActionType,
        cmEthernetAccPortLinkLossFwdRxRLDLinkIds,
        cmEthernetAccPortN2AVlanTrunkingEnabled, 
        cmEthernetAccPortA2NPushPVIDEnabled,
        cmEthernetAccPortN2APopPVIDEnabled, cmEthernetAccPortPortVlanId,
        cmEthernetAccPortPortVlanPriority,
        cmEthernetAccPortPrioMapMode, cmEthernetAccPortSyncEEnabled,
        cmEthernetAccPortQLModeEnabled, cmEthernetAccPortExpectedQL,
        cmEthernetAccPortAssumedQL, cmEthernetAccPortReceivedQL, 
        cmEthernetAccPortTransmitQL,cmEthernetAccPortDeiEnable,
        cmEthernetAccPortPcpDEEncType,cmEthernetAccPortPcpDEPairsAction,
        cmEthernetAccPortClbIndex, cmEthernetAccPortClbEnabled,
        cmEthernetAccPortClbLength, cmEthernetAccPortClbDescr,
        cmEthernetAccPortSSMRemoteMacAddress, cmEthernetAccPortXgePhyType,
        cmEthernetAccPortLoopbackSourceMacControlEnabled, cmEthernetAccPortLoopbackDestMacControlEnabled,
        cmEthernetAccPortLoopbackSourceMacAddress, cmEthernetAccPortLoopbackDestMacAddress,
        cmEthernetAccPortLoopbackBlockingEnabled
    }
    STATUS  current
    DESCRIPTION
            "A collection of objects used to manage the F3 Ethernet Access Port 
             function."
    ::= { cmFacilityGroups 2 }

ethernetNetworkPortGroup OBJECT-GROUP
    OBJECTS {
        cmEthernetNetPortIndex, cmEthernetNetPortIfIndex,
        cmEthernetNetPortEntityIndex, cmEthernetNetPortAdminState,
        cmEthernetNetPortOperationalState, cmEthernetNetPortSecondaryState,
        cmEthernetNetPortMTU, cmEthernetNetPortMediaType,
        cmEthernetNetPortConfigSpeed, cmEthernetNetPortNegotiatedSpeed,
        cmEthernetNetPortMDIXType,
        cmEthernetNetPortJumboFramesEnabled, cmEthernetNetPortSfpVendorName,
        cmEthernetNetPortSfpPartNumber, cmEthernetNetPortSfpSerialNumber,
        cmEthernetNetPortSfpDateOfManufacture, cmEthernetNetPortSfpConnectorValue,
        cmEthernetNetPortInitiateDiag, cmEthernetNetPortDiagnosePair1Cond,
        cmEthernetNetPortDiagnosePair2Cond, cmEthernetNetPortDiagnosePair3Cond,
        cmEthernetNetPortDiagnosePair4Cond, cmEthernetNetPortDiagnoseAutoNegCond,
        cmEthernetNetPortDiagnoseLpbkCond, cmEthernetNetPortDiagnoseEfmLpbkCond,
        cmEthernetNetPortDiagnoseResult,cmEthernetNetPortDiagnoseTestStatus,
        cmEthernetNetPortDiagnoseTestTime,
        cmEthernetNetPortLoopbackConfig, cmEthernetNetPortLoopbackStatus,
        cmEthernetNetPortLoopbackTime,
        cmEthernetNetPortLoopbackSwapSADA, cmEthernetNetPortOuterVlanLoopbackMask,
        cmEthernetNetPortOuterVlanLoopback1, cmEthernetNetPortOuterVlanLoopback2,
        cmEthernetNetPortOuterVlanLoopback3, 
        cmEthernetNetPortInnerVlanLoopbackMask,
        cmEthernetNetPortInnerVlanLoopback1, cmEthernetNetPortInnerVlanLoopback2, 
        cmEthernetNetPortInnerVlanLoopback3,
        cmEthernetNetPortLinkLossFwdEnabled, cmEthernetNetPortLinkLossFwdSignalType,
        cmEthernetNetPortLinkLossFwdTriggerTypes,cmEthernetNetPortLinkLossFwdDelay,
        cmEthernetNetPortLinkLossFwdActive, 
        cmEthernetNetPortLinkLossFwdPartnerEnabled,
        cmEthernetNetPortLinkLossFwdLocalLinkId, 
        cmEthernetNetPortLinkLossFwdRemoteLinkIds,
        cmEthernetNetPortOamId, cmEthernetNetPortOamAdminDisposition,
        cmEthernetNetPortOamDiscoveryState,
        cmEthernetNetPortOamLocalVarRtrvsEnabled, 
        cmEthernetNetPortOamLocalLinkEventsEnabled,
        cmEthernetNetPortOamLocalOamLoopbacksSupported,
        cmEthernetNetPortOamLocalUnidirSupportEnabled,
        cmEthernetNetPortOamLocalMaxPDUSize,
        cmEthernetNetPortOamLocalMode, cmEthernetNetPortOamRemoteMacAddress,
        cmEthernetNetPortOamRemoteVarRtrvsEnabled,
        cmEthernetNetPortOamRemoteLinkEventsEnabled,
        cmEthernetNetPortOamRemoteOamLoopbacksSupported,
        cmEthernetNetPortOamRemoteUnidirSupportEnabled,
        cmEthernetNetPortOamRemoteMaxPDUSize, cmEthernetNetPortOamRemoteMode,
        cmEthernetNetPortRxPauseDisposition, cmEthernetNetPortTxPauseEnabled,
        cmEthernetNetPortAfpType,
    
        cmEthernetNetPortMDIXStatus, cmEthernetNetPortSfpReach,
        cmEthernetNetPortSfpLaserWaveLength,
        cmEthernetNetPortSfpMediaType, cmEthernetNetPortOamEnabled,
        cmEthernetNetPortOamAdminState,
        cmEthernetNetPortShapingEnabled,
        cmEthernetNetPortShapedSpeedLo, cmEthernetNetPortShapedSpeedHi,
        cmEthernetNetPortQinQEtherType, cmEthernetNetPortLinkLossFwdTxActionType,
        cmEthernetNetPortLinkLossFwdRxRLDLinkIds,
        cmEthernetNetPortAutoDiagEnabled,
        cmEthernetNetPortSyncEEnabled, cmEthernetNetPortQLModeEnabled,
        cmEthernetNetPortExpectedQL, cmEthernetNetPortAssumedQL,
        cmEthernetNetPortReceivedQL, cmEthernetNetPortTransmitQL,
        cmEthernetNetPortDeiEnable, cmEthernetNetPortPcpDEEncType,
        cmEthernetNetPortPcpDEPairsAction,cmEthernetNetPortClbIndex, 
        cmEthernetNetPortClbEnabled, cmEthernetNetPortClbLength, 
        cmEthernetNetPortClbDescr, cmEthernetNetPortSSMRemoteMacAddress,       
        cmEthernetNetPortXgePhyType, cmEthernetNetPortLoopbackSourceMacControlEnabled, 
        cmEthernetNetPortLoopbackDestMacControlEnabled, cmEthernetNetPortLoopbackSourceMacAddress, 
        cmEthernetNetPortLoopbackDestMacAddress, cmEthernetNetPortLoopbackBlockingEnabled
    }
    STATUS  current
    DESCRIPTION
            " A collection of objects used to manage the F3 Ethernet Network Port 
              function."
    ::= { cmFacilityGroups 3 }

ethernetMgmtPortGroup OBJECT-GROUP
    OBJECTS {
        cmEthernetMgmtPortIndex, cmEthernetMgmtPortEntityIndex,
        cmEthernetMgmtPortAdminState, cmEthernetMgmtPortOperationalState,
        cmEthernetMgmtPortSecondaryState, cmEthernetMgmtPortMTU,
        cmEthernetMgmtPortConfigSpeed, cmEthernetMgmtPortNegotiatedSpeed,
        cmEthernetMgmtPortMDIXType,
        cmEthernetMgmtPortMDIXStatus,
        cmEthernetMgmtPortMediaType 
    }
    STATUS  current
    DESCRIPTION
            "A collection of objects used to manage the F3 Ethernet Management Port
             function."
    ::= { cmFacilityGroups 4 }

bitsPortGroup OBJECT-GROUP
    OBJECTS {
        bitsPortTypeIndex, bitsPortIndex, bitsPortIfIndex, bitsPortEntityIndex,
        bitsPortAdminState, bitsPortOperationalState, bitsPortSecondaryState,
        bitsPortType, bitsPortLineType, bitsPortLineCode, bitsPortFrameFormat,
        bitsPortSaBitDesignation, bitsPortQLModeEnabled, bitsPortExpectedQL,
        bitsPortAssumedQL, bitsPortReceivedQL, bitsPortTransmitQL,
        bitsPortSquelchQL, bitsPortLineBuildOut
    }
    STATUS  current
    DESCRIPTION
            "A collection of objects used to manage the F3 Bits Port 
             function."
    ::= { cmFacilityGroups 5 }

trafficGroup OBJECT-GROUP
    OBJECTS {
        cmFlowIndex, cmFlowCircuitName, cmFlowAdminState,
        cmFlowOperationalState, cmFlowSecondaryState,
        cmFlowType, cmFlowMultiCOS, cmFlowA2NCIR,
        cmFlowA2NEIR, cmFlowN2ARateLimitingEnabled,
        cmFlowN2ACIR, cmFlowN2AEIR, cmFlowStorageType, cmFlowRowStatus,
    
        cmFlowTrafficType, cmFlowCOS, cmFlowVlanMemberList,
        cmFlowAction, cmFlowActionVlan, cmFlowUntaggedMemberEnabled,
        cmFlowA2NCIRHi, cmFlowA2NEIRHi,
        cmFlowN2ACIRHi, cmFlowN2AEIRHi, 
        cmFlowHCOSMgmtEnabled, cmFlowGuaranteedA2NBandwidthLo,
        cmFlowGuaranteedA2NBandwidthHi, cmFlowMaximumA2NBandwidthLo,
        cmFlowMaximumA2NBandwidthHi, cmFlowCTagControl,
        cmFlowCTagVlanId, cmFlowCTagVlanPriority, cmFlowCTagMatchRxPrio,
        cmFlowSTagControl, cmFlowSTagVlanId, cmFlowSTagVlanPriority,
        cmFlowOuterTagPrioEnabled, cmFlowN2ACOSPriorityTagType,
        cmFlowESFramesLossThreshold, cmFlowSESFramesLossThresholdRatio, 
        cmFlowPolicingEnabled, cmFlowPreserveSTagProperties, cmFlowInnerTagPrioEnabled,
        cmFlowA2NShapingType, cmFlowN2AShapingType,
        cmFlowN2AOuterTagPrioEnabled, cmFlowSTagMatchRxPrio, 
        cmFlowAutoBandwidthConfigEnabled,
        cmFlowPort1, cmFlowPort2,
        cmFlowPolicingControl,
        cmFlowAutoCIRPercentage,
        cmFlowLoopAvoidanceObject,
        cmFlowConfigType,
        cmFlowN2NForwardingEnabled,
    
        cmQosShaperTypeIndex, cmQosShaperIndex, cmQosShaperDirection,
        cmQosShaperAdminState, cmQosShaperOperationalState,cmQosShaperSecondaryState,
        cmQosShaperCIR, cmQosShaperCBS, cmQosShaperEIR, cmQosShaperEBS,
        cmQosShaperBufferSize, cmQosShaperStorageType,
        cmQosShaperRowStatus, cmQosShaperSoamCIRLo, cmQosShaperSoamCIRHi,
        cmQosShaperSoamEIRLo, cmQosShaperSoamEIRHi,
    
        cmQosShaperCOS, cmQosShaperCIRHi, cmQosShaperEIRHi,
    
        cmQosFlowPolicerTypeIndex, cmQosFlowPolicerIndex,
        cmQosFlowPolicerDirection, cmQosFlowPolicerAdminState, 
        cmQosFlowPolicerOperationalState,
        cmQosFlowPolicerSecondaryState,
        cmQosFlowPolicerCIRLo, cmQosFlowPolicerCIRHi, cmQosFlowPolicerEIRLo,
        cmQosFlowPolicerEIRHi, cmQosFlowPolicerCBS,
        cmQosFlowPolicerEBS, cmQosFlowPolicerAlgorithm,
        cmQosFlowPolicerColorMode, cmQosFlowPolicerColorMarkingFlag,
        cmQosFlowPolicerCouplingFlag, cmQosFlowPolicerAssociatedShaper,
        cmQosFlowPolicerStorageType, cmQosFlowPolicerRowStatus,
    
        cmAccPortQosShaperIndex, cmAccPortQosShaperDirection,
        cmAccPortQosShaperAdminState, cmAccPortQosShaperOperationalState,
        cmAccPortQosShaperSecondaryState, cmAccPortQosShaperCIRLo,
        cmAccPortQosShaperCIRHi, cmAccPortQosShaperEIRLo,
        cmAccPortQosShaperEIRHi, cmAccPortQosShaperCBS,
        cmAccPortQosShaperEBS, cmAccPortQosShaperBufferSize, cmAccPortQosShaperCOS,
        cmAccPortQosShaperSoamCIRLo, cmAccPortQosShaperSoamCIRHi,
        cmAccPortQosShaperSoamEIRLo, cmAccPortQosShaperSoamEIRHi
    }
    STATUS  current
    DESCRIPTION
            "A collection of objects used to manage the F3 traffic path, consists of
             Flows, Policers and Shapers." 
    ::= { cmFacilityGroups 6 }

prioMapGroup OBJECT-GROUP
    OBJECTS {
        cmPrioMapIndex, cmPrioMapInPriority, cmPrioMapXTagControl,
        cmPrioMapXTagPriority, cmPrioMapCOS, cmPrioMapOuterTagPriority,
        cmPrioMapInnerTagPriority,
    
        cmNetPortPrioMapIndex, cmNetPortPrioMapInPriority,
        cmNetPortPrioMapCOS, cmNetPortPrioMapOuterTagPriority
    }
    STATUS  current
    DESCRIPTION
            "A collection of objects used to manage the F3 Priority Mapping function." 
    ::= { cmFacilityGroups 7 }

pcpEncodeGroup OBJECT-GROUP
    OBJECTS {
        cmAccPortPcpDEEncIndex, cmAccPortPcpDEEncInPriority,
        cmAccPortPcpDEEncDropIneligiblePrio, cmAccPortPcpDEEncDropEligiblePrio,
        cmAccPortPcpDEDecIndex, cmAccPortPcpDEDecInPriority,
        cmAccPortPcpDEDecOutPriority, cmAccPortPcpDEDecDropEligible,
        cmAccPortPcpDEPairIndex, cmAccPortPcpDEDropIneligiblePrio,
        cmAccPortPcpDEDropEligiblePrio,
    
        cmNetPortPcpDEEncIndex, cmNetPortPcpDEEncInPriority,
        cmNetPortPcpDEEncDropIneligiblePrio, cmNetPortPcpDEEncDropEligiblePrio,
        cmNetPortPcpDEDecIndex, cmNetPortPcpDEDecInPriority,
        cmNetPortPcpDEDecOutPriority, cmNetPortPcpDEDecDropEligible,
        cmNetPortPcpDEPairIndex, cmNetPortPcpDEDropIneligiblePrio,
        cmNetPortPcpDEDropEligiblePrio
    }
    STATUS  current
    DESCRIPTION
            "A collection of objects used to manage the F3 Priority Mapping function." 
    ::= { cmFacilityGroups 8 }

cpdV2Group OBJECT-GROUP
    OBJECTS {
    cmEthernetAccPortCpdV2Index, cmEthernetAccPortCpdV2CiscoGroupDispType,
    cmEthernetAccPortCpdV2IslDispType, cmEthernetAccPortCpdV2PagpDispType,
    cmEthernetAccPortCpdV2UdldDispType, cmEthernetAccPortCpdV2CdpDispType,
    cmEthernetAccPortCpdV2VtpDispType, cmEthernetAccPortCpdV2DtpDispType,
    cmEthernetAccPortCpdV2PvstpPlusDispType, 
    cmEthernetAccPortCpdV2UplinkFastDispType,
    cmEthernetAccPortCpdV2VlanBridgeDispType,
    cmEthernetAccPortCpdV2L2PTDispType, 
    cmEthernetAccPortCpdV2BridgeGroupDispType,
    cmEthernetAccPortCpdV2BPDUDispType, cmEthernetAccPortCpdV2PauseDispType,
    cmEthernetAccPortCpdV2LACPDispType,
    cmEthernetAccPortCpdV2LACPMarkerDispType,
    cmEthernetAccPortCpdV2EfmOamDispType,
    cmEthernetAccPortCpdV2SSMDispType,
    cmEthernetAccPortCpdV2PortAuthenDispType,
    cmEthernetAccPortCpdV2BridgeReservedDispType,
    cmEthernetAccPortCpdV2LANBridgesDispType,
    cmEthernetAccPortCpdV2GARPGroupDispType,
    cmEthernetAccPortCpdV2GMRPDispType, cmEthernetAccPortCpdV2GVRPDispType,
    cmEthernetAccPortCpdV2GARPDispType,

    cmFlowCpdV2Index, cmFlowCpdV2CiscoGroupDispType,
    cmFlowCpdV2IslDispType, cmFlowCpdV2PagpDispType,
    cmFlowCpdV2UdldDispType, cmFlowCpdV2CdpDispType,
    cmFlowCpdV2VtpDispType, cmFlowCpdV2DtpDispType,
    cmFlowCpdV2PvstpPlusDispType, 
    cmFlowCpdV2UplinkFastDispType,
    cmFlowCpdV2VlanBridgeDispType,
    cmFlowCpdV2L2PTDispType, 
    cmFlowCpdV2BridgeGroupDispType,
    cmFlowCpdV2BPDUDispType, cmFlowCpdV2PauseDispType,
    cmFlowCpdV2LACPDispType,
    cmFlowCpdV2LACPMarkerDispType,
    cmFlowCpdV2EfmOamDispType,
    cmFlowCpdV2SSMDispType,            
    cmFlowCpdV2PortAuthenDispType,
    cmFlowCpdV2BridgeReservedDispType,
    cmFlowCpdV2LANBridgesDispType,
    cmFlowCpdV2GARPGroupDispType,
    cmFlowCpdV2GMRPDispType, cmFlowCpdV2GVRPDispType, cmFlowCpdV2GARPDispType,
    cmFlowCpdV2ActiveControlProtocols, 

    cmEthernetNetPortCpdV2Index, cmEthernetNetPortCpdV2CiscoGroupDispType,
    cmEthernetNetPortCpdV2IslDispType, cmEthernetNetPortCpdV2PagpDispType,
    cmEthernetNetPortCpdV2UdldDispType, cmEthernetNetPortCpdV2CdpDispType,
    cmEthernetNetPortCpdV2VtpDispType, cmEthernetNetPortCpdV2DtpDispType,
    cmEthernetNetPortCpdV2PvstpPlusDispType, 
    cmEthernetNetPortCpdV2UplinkFastDispType,
    cmEthernetNetPortCpdV2VlanBridgeDispType,
    cmEthernetNetPortCpdV2L2PTDispType, 
    cmEthernetNetPortCpdV2BridgeGroupDispType,
    cmEthernetNetPortCpdV2BPDUDispType, cmEthernetNetPortCpdV2PauseDispType,
    cmEthernetNetPortCpdV2LACPDispType,
    cmEthernetNetPortCpdV2LACPMarkerDispType,
    cmEthernetNetPortCpdV2EfmOamDispType,
    cmEthernetNetPortCpdV2SSMDispType,
    cmEthernetNetPortCpdV2PortAuthenDispType,
    cmEthernetNetPortCpdV2BridgeReservedDispType,
    cmEthernetNetPortCpdV2LANBridgesDispType,
    cmEthernetNetPortCpdV2GARPGroupDispType,
    cmEthernetNetPortCpdV2GMRPDispType, cmEthernetNetPortCpdV2GVRPDispType,
    cmEthernetNetPortCpdV2GARPDispType
    }
    STATUS  current
    DESCRIPTION
            "A collection of objects used to manage the 
             Control Protocol Disposition version 2 function."
    ::= { cmFacilityGroups 9 }
    
trafficGroupCmHub OBJECT-GROUP
    OBJECTS {
        cmFlowIndex, cmFlowCircuitName, cmFlowAdminState,
        cmFlowOperationalState, cmFlowSecondaryState,
        cmFlowType, cmFlowMultiCOS, cmFlowA2NCIR,
        cmFlowA2NEIR, cmFlowN2ARateLimitingEnabled,
        cmFlowN2ACIR, cmFlowN2AEIR, cmFlowStorageType, cmFlowRowStatus,
    
        cmFlowTrafficType, cmFlowCOS, cmFlowVlanMemberList,
        cmFlowAction, cmFlowActionVlan, cmFlowUntaggedMemberEnabled,
        cmFlowA2NCIRHi, cmFlowA2NEIRHi,
        cmFlowN2ACIRHi, cmFlowN2AEIRHi, 
        cmFlowHCOSMgmtEnabled, cmFlowGuaranteedA2NBandwidthLo,
        cmFlowGuaranteedA2NBandwidthHi, cmFlowMaximumA2NBandwidthLo,
        cmFlowMaximumA2NBandwidthHi, cmFlowCTagControl,
        cmFlowCTagVlanId, cmFlowCTagVlanPriority, cmFlowCTagMatchRxPrio,
        cmFlowSTagControl, cmFlowSTagVlanId, cmFlowSTagVlanPriority,
        cmFlowOuterTagPrioEnabled, cmFlowN2ACOSPriorityTagType,
        cmFlowESFramesLossThreshold, cmFlowSESFramesLossThresholdRatio, 
        cmFlowPolicingEnabled, cmFlowPreserveSTagProperties, cmFlowInnerTagPrioEnabled,
        cmFlowA2NShapingType, cmFlowN2AShapingType,
        cmFlowN2AOuterTagPrioEnabled, cmFlowSTagMatchRxPrio,
    
        cmQosShaperTypeIndex, cmQosShaperIndex, cmQosShaperDirection,
        cmQosShaperAdminState, cmQosShaperOperationalState,cmQosShaperSecondaryState,
        cmQosShaperCIR, cmQosShaperCBS, cmQosShaperEIR, cmQosShaperEBS,
        cmQosShaperBufferSize, cmQosShaperStorageType,
        cmQosShaperRowStatus, cmQosShaperCOS, cmQosShaperCIRHi, 
        cmQosShaperEIRHi

    }
    STATUS  current
    DESCRIPTION
            "A collection of objects used to manage the F3 traffic path, consists of
             Flows, Policers and Shapers." 
    ::= { cmFacilityGroups 10 }


ocnStmGroup OBJECT-GROUP
    OBJECTS {
        ocnStmIndex, ocnStmIfIndex, ocnStmEntityIndex,
        ocnStmAdminState, ocnStmOperationalState,
        ocnStmSecondaryState, ocnStmSfpVendorName,
        ocnStmSfpPartNumber, ocnStmSfpSerialNumber,
        ocnStmSfpDateOfManufacture, ocnStmMultiplexingStructures,
        ocnStmEoTDMMode, ocnStmLoopbackConfig,
        ocnStmLoopbackStatus, ocnStmLoopbackTime,
        ocnStmInsertingAIS, ocnStmBerExcThreshold,
        ocnStmBerDegThreshold, ocnStmRxTrailTrace,
        ocnStmTxTrailTrace, ocnStmExpectedTrailTrace,
        ocnStmTrailTraceFormat, ocnStmQLModeEnabled,
        ocnStmExpectedQL, ocnStmAssumedQL, ocnStmReceivedQL,
        ocnStmTransmitQL, ocnStmPortType, ocnStmFreqSourceType 
    }
    STATUS  current
    DESCRIPTION
            "A collection of objects used to manage the OCN/STM Line."
    ::= { cmFacilityGroups 11 }

stsVcPathGroup OBJECT-GROUP
    OBJECTS {
        stsVcPathParentIfIndex, stsVcPathIndex,
        stsVcPathIfIndex, stsVcPathAdminState, stsVcPathOperationalState,
        stsVcPathSecondaryState, stsVcPathLoopbackConfig,
        stsVcPathLoopbackStatus, stsVcPathLoopbackTime,
        stsVcPathInsertingAIS, stsVcPathBerExcThreshold,
        stsVcPathBerDegThreshold, stsVcPathTrailTraceFormat,
        stsVcPathRxTrailTrace, stsVcPathTxTrailTrace,
        stsVcPathExpectedTrailTrace, stsVcPathRxSignalLabel,
        stsVcPathTxSignalLabel, stsVcPathExpectedSignalLabel,
        stsVcPathRowStatus, stsVcPathLowOrderPathType
    }
    STATUS  current
    DESCRIPTION
            "A collection of objects used to manage the STS/VC Higher Order Path."
    ::= { cmFacilityGroups 12 }

vtVcPathGroup OBJECT-GROUP
    OBJECTS {
        vtVcPathParentIfIndex, vtVcPathIndex, vtVcPathIfIndex,
        vtVcPathAdminState, vtVcPathOperationalState,
        vtVcPathSecondaryState, vtVcPathLoopbackConfig,
        vtVcPathLoopbackStatus, vtVcPathLoopbackTime,
        vtVcPathInsertingAIS, vtVcPathBerExcThreshold,
        vtVcPathBerDegThreshold, vtVcPathTrailTraceFormat,
        vtVcPathRxTrailTrace, vtVcPathTxTrailTrace,
        vtVcPathExpectedTrailTrace, vtVcPathRxSignalLabel,
        vtVcPathTxSignalLabel, vtVcPathExpectedSignalLabel,
        vtVcPathRowStatus
    }
    STATUS  current
    DESCRIPTION
            "A collection of objects used to manage the VT/VC Lower Order Path."
    ::= { cmFacilityGroups 13 }

e1t1InterfaceGroup OBJECT-GROUP
    OBJECTS {
        e1t1ParentIfIndex, e1t1Index, e1t1IfIndex,
        e1t1EntityIndex, e1t1AdminState,
        e1t1OperationalState, e1t1SecondaryState, e1t1LoopbackConfig,
        e1t1LoopbackStatus, e1t1LoopbackTime,
        e1t1RemoteLoopbackRequest, e1t1InsertingAIS, e1t1RowStatus,
        e1t1LineType, e1t1LineCode, e1t1FrameFormat,
        e1t1LineBuildOut, e1t1TimingDomain, e1t1RcvSensitivity,
        e1t1IdlePatternProfile, e1t1LoopbackProfile, e1t1RelatedContainerId
    }
    STATUS  current
    DESCRIPTION
            "A collection of objects used to manage the E1/T1 Interface Group."
    ::= { cmFacilityGroups 14 }

e3t3InterfaceGroup OBJECT-GROUP
    OBJECTS {
        e3t3ParentIfIndex, e3t3Index, e3t3IfIndex,
        e3t3EntityIndex, e3t3AdminState,
        e3t3OperationalState, e3t3SecondaryState, e3t3LoopbackConfig,
        e3t3LoopbackStatus, e3t3LoopbackTime,
        e3t3RemoteLoopbackRequest, e3t3InsertingAIS, e3t3CBitEnable,
        e3t3T3Channelized, e3t3RowStatus, 
        e3t3FrameFormat, e3t3RelatedContainerId
    }
    STATUS  current
    DESCRIPTION
            "A collection of objects used to manage the E3/T3 Interface Group."
    ::= { cmFacilityGroups 15 }

f3PulsePerSecondPortGroup OBJECT-GROUP
    OBJECTS {
        f3PulsePerSecondPortIndex, f3PulsePerSecondPortIfIndex,
        f3PulsePerSecondPortEntityIndex, f3PulsePerSecondPortAdminState,
        f3PulsePerSecondPortOperationalState, f3PulsePerSecondPortSecondaryState,
        f3PulsePerSecondPortSquelchControl, f3PulsePerSecondPortSquelchQL,
        f3PulsePerSecondPortTODSource, f3PulsePerSecondPortDirection, 
        f3PulsePerSecondPortInputRate, f3PulsePerSecondPortDelayCompensation,
        f3PulsePerSecondPortClockClass, f3PulsePerSecondPortClockAccuracy,
        f3PulsePerSecondPortTimeSource
    }
    STATUS  current
    DESCRIPTION
            "A collection of objects used to manage the F3 Pulse Per Second Group."
    ::= { cmFacilityGroups 16 }

f3TimeOfDayPortGroup OBJECT-GROUP
    OBJECTS {
        f3TimeOfDayPortIndex, f3TimeOfDayPortIfIndex, f3TimeOfDayPortEntityIndex, 
        f3TimeOfDayPortAdminState, f3TimeOfDayPortOperationalState,
        f3TimeOfDayPortSecondaryState, f3TimeOfDayPortSquelchControl,
        f3TimeOfDayPortSquelchQL, f3TimeOfDayPortTODSource
    }
    STATUS  current
    DESCRIPTION
            "A collection of objects used to manage the F3 Time of Day Port Group."
    ::= { cmFacilityGroups 17 }

f3Gps10MhzPortGroup OBJECT-GROUP
    OBJECTS {
        gps10MHzPortIndex, gps10MHzPortIfIndex, gps10MHzPortEntityIndex,
        gps10MHzPortAdminState, gps10MHzPortOperationalState,
        gps10MHzPortSecondaryState, gps10MHzPortSignalDirection,
        gps10MHzPortSquelchControl, gps10MHzPortSquelchQL,
        gps10MHzPortFrequencySource, gps10MHzPortClockClass,
        gps10MHzPortClockAccuracy, gps10MHzPortTimeSource,
        gps10MHzPortAssumedQL
    }
    STATUS  current
    DESCRIPTION
            "A collection of objects used to manage the F3 GPS 10 Mhz Port Group."
    ::= { cmFacilityGroups 18 }

ethernetNetworkPortExtGroup OBJECT-GROUP
    OBJECTS {
        cmEthernetNetPortTDMEncapsulation, cmEthernetNetPortAssociatedTdmEntity
    }
    STATUS  current
    DESCRIPTION
            " A collection of objects used to manage the F3 Ethernet Network Port 
              extense function."
    ::= { cmFacilityGroups 19 }


f3GPSReceiverPortGroup OBJECT-GROUP
    OBJECTS { 
        f3GPSReceiverPortIndex, f3GPSReceiverPortIfIndex,
        f3GPSReceiverPortEntityIndex, f3GPSReceiverPortAdminState,
        f3GPSReceiverPortOperationalState, f3GPSReceiverPortSecondaryState,
        f3GPSReceiverPortPPSGenCondition, f3GPSReceiverPortAntennaCableLength,
        f3GPSReceiverPortAntennaStatus, f3GPSReceiverPortSatellitesUsableFlag,
        f3GPSReceiverPortNumTrackingSatellites, f3GPSReceiverPortSelfSurveyProgress,
        f3GPSReceiverPortPPSGeneratedFlag
    }
    STATUS  current
    DESCRIPTION
            "A collection of objects used to manage the F3 GPS Receiver Port Group."
    ::= { cmFacilityGroups 20 }

cmPsePortGroup OBJECT-GROUP
    OBJECTS{
    cmPethPsePortExtGroupIndex,
    cmPethPsePortExtIndex,
    cmPethPsePortExtAssociatedPort,
    pethPsePortExtPowerConsumption,
    pethPsePortExtAvailablePowerLevel
    }
    STATUS  current
    DESCRIPTION
            "A collection of objects used to manage the pse port ext entry Group."
    ::= { cmFacilityGroups 21 }

cmPseEXTGroup OBJECT-GROUP
    OBJECTS{
    pethMainPseExtGroupIndex,
    pethMainPseExtNonStandardPD
    }
    STATUS  current
    DESCRIPTION
            "A collection of objects used to manage the pse group ext entry Group."
    ::= { cmFacilityGroups 22 }

cmMPFlowGroup OBJECT-GROUP
    OBJECTS{
    cmMPFlowIndex,
    cmMPFlowCircuitName,
    cmMPFlowAdminState,
    cmMPFlowOperationalState,
    cmMPFlowSecondaryState,
    cmMPFlowLearningEnabled,
    cmMPFlowAgingTimer,
    cmMPFlowFwdTableSizeProfileID,
    cmMPFlowtableFullAction,
    cmMPFlowStorageType,
    cmMPFlowRowStatus,
    cmMPFlowLearningConfigAction,
    cmMPFlowFPList
    }
    STATUS  current
    DESCRIPTION
            "A collection of objects used to manage the MP flow entry Group."
    ::= { cmFacilityGroups 23 }

cmMPFlowMemberGroup OBJECT-GROUP
    OBJECTS{
    cmMPFlowMemberFPIndex,
    cmMPFlowPointRowStatus
    }
    STATUS  current
    DESCRIPTION
            "A collection of objects used to manage the MP flow Member entry Group."
    ::= { cmFacilityGroups 24 }

cmEthernetTrafficPortPcpGroup OBJECT-GROUP
    OBJECTS{
    cmEthernetTrafficPortPcpDEEncIndex,
    cmEthernetTrafficPortPcpDEEncInPriority,
    cmEthernetTrafficPortPcpDEEncDropIneligiblePrio,
    cmEthernetTrafficPortPcpDEEncDropEligiblePrio,
    cmEthernetTrafficPortPcpDEDecIndex,
    cmEthernetTrafficPortPcpDEDecInPriority,
    cmEthernetTrafficPortPcpDEDecOutPriority,
    cmEthernetTrafficPortPcpDEDecDropEligible,
    cmEthernetTrafficPortPcpDEPairIndex,
    cmEthernetTrafficPortPcpDEDropIneligiblePrio,
    cmEthernetTrafficPortPcpDEDropEligiblePrio,
    cmEthernetTrafficPortClbIndex,
    cmEthernetTrafficPortClbEnabled,
    cmEthernetTrafficPortClbLength,
    cmEthernetTrafficPortClbDescr
    }
    STATUS  current
    DESCRIPTION
            "A collection of objects used to manage the traffic port pcp Group."
    ::= { cmFacilityGroups 25 }

neTMParamsGroup OBJECT-GROUP
    OBJECTS{
    neTMParamsBandwidthProfileMode,
    neTMParamsAgingtime
    }
    STATUS  current
    DESCRIPTION
            "A collection of objects used to manage the ne facility entry Group."
    ::= { cmFacilityGroups 26 }

cmEthernetTrafficPortGroup OBJECT-GROUP
    OBJECTS{
    cmEthernetTrafficPortIndex,cmEthernetTrafficPortIfIndex,
    cmEthernetTrafficPortEntityIndex,cmEthernetTrafficPortAdminState,
    cmEthernetTrafficPortOperationalState,cmEthernetTrafficPortSecondaryState,
    cmEthernetTrafficPortMTU,cmEthernetTrafficPortMediaType,
    cmEthernetTrafficPortConfigSpeed,cmEthernetTrafficPortNegotiatedSpeed,
    cmEthernetTrafficPortMDIXType,cmEthernetTrafficPortMDIXStatus,
    cmEthernetTrafficPortSfpVendorName,cmEthernetTrafficPortSfpPartNumber,
    cmEthernetTrafficPortSfpSerialNumber,cmEthernetTrafficPortSfpDateOfManufacture,
    cmEthernetTrafficPortSfpConnectorValue,
    cmEthernetTrafficPortSfpLinkLength,cmEthernetTrafficPortSfpLaserWaveLength,
    cmEthernetTrafficPortSfpMediaType,cmEthernetTrafficPortLoopbackConfig,
    cmEthernetTrafficPortLoopbackStatus,cmEthernetTrafficPortLoopbackTime,
    cmEthernetTrafficPortLoopbackSwapSADA,cmEthernetTrafficPortOuterVlanLoopbackMask,
    cmEthernetTrafficPortOuterVlanLoopback1,cmEthernetTrafficPortOuterVlanLoopback2,
    cmEthernetTrafficPortOuterVlanLoopback3,cmEthernetTrafficPortLinkLossFwdEnabled,
    cmEthernetTrafficPortLinkLossFwdSignalType,cmEthernetTrafficPortLinkLossFwdTriggerTypes,
    cmEthernetTrafficPortLinkLossFwdDelay,cmEthernetTrafficPortLinkLossFwdActive,
    cmEthernetTrafficPortLinkLossFwdPartnerEnabled,cmEthernetTrafficPortLinkLossFwdLocalLinkId,
    cmEthernetTrafficPortLinkLossFwdRemoteLinkIds,cmEthernetTrafficPortLinkLossFwdTxActionType,
    cmEthernetTrafficPortLinkLossFwdRxRLDLinkIds,cmEthernetTrafficPortOamId,
    cmEthernetTrafficPortOamDiscoveryState,
    cmEthernetTrafficPortOamLocalVarRtrvsEnabled,cmEthernetTrafficPortOamLocalLinkEventsEnabled,
    cmEthernetTrafficPortOamLocalOamLoopbacksSupported,cmEthernetTrafficPortOamLocalUnidirSupportEnabled,
    cmEthernetTrafficPortOamLocalMaxPDUSize,cmEthernetTrafficPortOamLocalMode,
    cmEthernetTrafficPortOamRemoteMacAddress,cmEthernetTrafficPortOamRemoteVarRtrvsEnabled,
    cmEthernetTrafficPortOamRemoteLinkEventsEnabled,cmEthernetTrafficPortOamRemoteOamLoopbacksSupported,
    cmEthernetTrafficPortOamRemoteUnidirSupportEnabled,cmEthernetTrafficPortOamRemoteMaxPDUSize,
    cmEthernetTrafficPortOamRemoteMode,cmEthernetTrafficPortOamEnabled,
    cmEthernetTrafficPortOamAdminState,
    cmEthernetTrafficPortSvcType,
    cmEthernetTrafficPortTxPauseEnabled,cmEthernetTrafficPortAfpType,
    cmEthernetTrafficPortShapingEnabled,cmEthernetTrafficPortShapedSpeedLo,
    cmEthernetTrafficPortShapedSpeedHi,cmEthernetTrafficPortQinQEtherType,
    cmEthernetTrafficPortEgressVlanTrunkingEnabled,cmEthernetTrafficPortIngressPushPVIDEnabled,
    cmEthernetTrafficPortEgressPopPVIDEnabled,cmEthernetTrafficPortPortVlanId,
    cmEthernetTrafficPortPortVlanPriority,cmEthernetTrafficPortPriorityVlanId,
    cmEthernetTrafficPortIngressPrioMapMode,cmEthernetTrafficPortIngressCOSPriority,
    cmEthernetTrafficPortEgressPopPriorityVidEnabled,
    cmEthernetTrafficPortSyncEEnabled,
    cmEthernetTrafficPortQLModeEnabled,cmEthernetTrafficPortExpectedQL,
    cmEthernetTrafficPortAssumedQL,cmEthernetTrafficPortReceivedQL,
    cmEthernetTrafficPortTransmitQL,cmEthernetTrafficPortTagFrameControl,
    cmEthernetTrafficPortRxPauseEnabled, cmEthernetTrafficPortPhyType,
    cmEthernetTrafficPortSfpLaserWaveLengthPicometer, cmEthernetTrafficPortRowStatus,
    cmEthernetTrafficPortSSMRemoteMacAddress, cmEthernetTrafficPortInnerVlanLoopbackMask,
    cmEthernetTrafficPortInnerVlanLoopback1, cmEthernetTrafficPortInnerVlanLoopback2,
    cmEthernetTrafficPortInnerVlanLoopback3,
    cmEthernetTrafficPortLaserWDMChannel,
    cmEthernetTrafficPortLaserIsTunable,
    cmEthernetTrafficPortLaserFrequency,
    cmEthernetTrafficPortDeiEnable,
    cmEthernetTrafficPortPcpDEEncType,
    cmEthernetTrafficPortPcpDEPairsAction,
    cmEthernetTrafficPortInitiateDiag,
    cmEthernetTrafficPortDiagnosePair1Cond,
    cmEthernetTrafficPortDiagnosePair2Cond,
    cmEthernetTrafficPortDiagnosePair3Cond,
    cmEthernetTrafficPortDiagnosePair4Cond,
    cmEthernetTrafficPortDiagnoseAutoNegCond,
    cmEthernetTrafficPortDiagnoseLpbkCond,
    cmEthernetTrafficPortDiagnoseEfmLpbkCond,
    cmEthernetTrafficPortDiagnoseResult,
    cmEthernetTrafficPortDiagnoseTestStatus,
    cmEthernetTrafficPortDiagnoseTestTime,
    cmEthernetTrafficPortAutoDiagEnabled, cmEthernetTrafficPortDeleteEntitiesAction,
    cmEthernetTrafficPortMaxMpFpNum, cmEthernetTrafficPortJdsuLoopbackEnabled, cmEthernetTrafficPortJdsuLoopbackVlanId,
    cmEthernetTrafficPortIngressPopPriorityVidEnabled, cmEthernetTrafficPortRxDeiAction,
    cmEthernetTrafficPortTxDeiAction, cmEthernetTrafficPortRxDeiOuterTagType,
    cmEthernetTrafficPortTxDeiOuterTagType
    }
    STATUS  current
    DESCRIPTION
            "A collection of objects used to manage the traffic port entry Group."
    ::= { cmFacilityGroups 27 }

cmFlowPointGroup OBJECT-GROUP
    OBJECTS{
    cmFlowPointIndex,cmFlowPointCircuitName,
    cmFlowPointAdminState,cmFlowPointOperationalState,
    cmFlowPointSecondaryState,cmFlowPointAssociatedFlowId,
    cmFlowPointIngressMultiCOS,cmFlowPointIngressCOS,
    cmFlowPointIngressVlanMemberList,cmFlowPointVlanMemberAction,
    cmFlowPointAssociatedAclProfile,cmFlowPointSESFramesLossThresholdRatio,
    cmFlowPointVlanMemberActionVlan,cmFlowPointIngressUntaggedFrameEnabled,
    cmFlowPointCTagControl,cmFlowPointCTagVlanId,
    cmFlowPointCTagVlanPriority,cmFlowPointSTagControl,
    cmFlowPointSTagVlanId,cmFlowPointSTagVlanPriority,
    cmFlowPointEgressOuterTagPrioMapEnabled,cmFlowPointColorMarkingSupported, 
    cmFlowPointStorageType, cmFlowPointRowStatus,
    cmFlowPointDefaultMemberEnabled,
    cmFlowPointMcastRateLimitEnabled,
    cmFlowPointMcastRateLimitSpeedLo,
    cmFlowPointMcastRateLimitSpeedHi,
    cmFlowPointBcastRateLimitEnabled,
    cmFlowPointBcastRateLimitSpeedLo,
    cmFlowPointBcastRateLimitSpeedHi,
    cmFlowPointSplitHorizonGroupOID,
    cmFlowPointLoopAvoidance,
    cmFlowPointHierarchicalCosEnabled,
    cmFlowPointWfqQid,
    cmFlowPointWfqOutPriority,
    cmFlowPointMaximumBWLo,
    cmFlowPointGuaranteedBWLo,
    cmFlowPointMaximumBWHi,
    cmFlowPointGuaranteedBWHi
    }
    STATUS  current
    DESCRIPTION
            "A collection of objects used to manage the flow point entry Group."
    ::= { cmFacilityGroups 28 }

ethernetAccessPortJdsuExtGroup OBJECT-GROUP
    OBJECTS {
        cmEthernetAccPortJDSUControlFramesSnoopingEnabled,
        cmEthernetAccPortJDSULoopbackVlan
    }
    STATUS  current
    DESCRIPTION
            " A collection of objects used to manage the F3 Ethernet Access Port 
              JDSU extense function."
    ::= { cmFacilityGroups 29 }

ethernetNetworkPortJdsuExtGroup OBJECT-GROUP
    OBJECTS {
        cmEthernetNetPortJDSUControlFramesSnoopingEnabled,
        cmEthernetNetPortJDSULoopbackVlan
    }
    STATUS  current
    DESCRIPTION
            " A collection of objects used to manage the F3 Ethernet Network Port 
              JDSU extense function."
    ::= { cmFacilityGroups 30 }

cmTrafficPortLpbkGroup OBJECT-GROUP
    OBJECTS{
    cmEthernetTrafficPortLpbkIndex,
    cmEthernetTrafficPortLpbkInnerVlanEnabled,
    cmEthernetTrafficPortLpbkInnerVlanTag,
    cmEthernetTrafficPortLpbkOuterVlanEnabled,
    cmEthernetTrafficPortLpbkOuterVlanTag,
    cmEthernetTrafficPortLpbkTime,
    cmEthernetTrafficPortLpbkStatus,
    cmEthernetTrafficPortLpbkConfig
    }
    STATUS  current
    DESCRIPTION
            "A collection of objects used to manage the traffic port lpbk group."
    ::= { cmFacilityGroups 31 }


END
