F3-PORTMIRROR-MIB DEFINITIONS ::= BEGIN

IMPORTS
    MODULE-COMPLIANCE, OBJECT-GROUP 
             FROM SNMPv2-CONF
    MODULE-IDENTITY, OBJECT-TYPE, Integer32, Unsigned32
             FROM SNMPv2-SMI
    TruthValue, RowStatus, StorageType, 
    VariablePointer, TEXTUAL-CONVENTION
             FROM SNMPv2-TC
    TrafficDirection, PerfCounter64
             FROM CM-COMMON-MIB
    neIndex, shelfIndex, slotIndex
             FROM CM-ENTITY-MIB
    cmEthernetAccPortEntry
             FROM CM-FACILITY-MIB
    fsp150cm
             FROM  ADVA-MIB;

f3PortMirrorMIB MODULE-IDENTITY
    LAST-UPDATED        "201309200000Z"
    ORGANIZATION    "ADVA Optical Networking"
    CONTACT-INFO
            "        Marek Romaniuk
                     ADVA Optical Networking, Inc.
                Tel: +48 58 7716 414
             E-mail: mromaniuk@advaoptical.com
             Postal: ul. Slaska 35/37
                     81-310 Gdynia, Poland"
    DESCRIPTION
            "This module defines the Port Mirror MIB definitions 
             used by the F3 (FSP150CM/CC) product lines.  
             Copyright (C) ADVA Optical Networking."
    REVISION        "201310140000Z"
    DESCRIPTION
        "
         Notes from release 201310210000Z,
         (1) Added table: 
             - f3PortMirrorAccPortExtTable.
         Notes from release 201310140000Z,
         (1) MIB version ready for release FSP150CC 6.1.CC." 

    ::= {fsp150cm 29}


-- 
-- OID definitions
-- 

f3PortMirrorConfigObjects      OBJECT IDENTIFIER ::= {f3PortMirrorMIB 1}
f3PortMirrorStatsObjects       OBJECT IDENTIFIER ::= {f3PortMirrorMIB 2}
f3PortMirrorConformance        OBJECT IDENTIFIER ::= {f3PortMirrorMIB 3}

--
--  Mirror Session
--

f3MirrorSessionTable  OBJECT-TYPE
    SYNTAX      SEQUENCE OF F3MirrorSessionEntry
    MAX-ACCESS  not-accessible
    STATUS      current
    DESCRIPTION
            "A list of entries corresponding to Mirror Session 
             instance for configuration purposes."
    ::= { f3PortMirrorConfigObjects 1 }

f3MirrorSessionEntry OBJECT-TYPE
    SYNTAX      F3MirrorSessionEntry
    MAX-ACCESS  not-accessible
    STATUS      current
    DESCRIPTION
            "A conceptual row in the f3MirrorSessionTable."
    INDEX { neIndex, f3MirrorSessionIndex }
    ::= { f3MirrorSessionTable 1 }

F3MirrorSessionEntry ::= SEQUENCE {
    f3MirrorSessionIndex                      Integer32,
    f3MirrorSessionSourcePort                 VariablePointer,
    f3MirrorSessionMonitorPort                VariablePointer,
    f3MirrorSessionSourcePortDir              TrafficDirection,
    f3MirrorSessionTruncationCtrl             TruthValue,
    f3MirrorSessionTruncationLength           Unsigned32,
    f3MirrorSessionTimestampControl           TruthValue,
    f3MirrorSessionStorageType                StorageType,
    f3MirrorSessionRowStatus                  RowStatus
}

f3MirrorSessionIndex OBJECT-TYPE
    SYNTAX        Integer32 (1..255)
    MAX-ACCESS    not-accessible
    STATUS        current
    DESCRIPTION
         "An integer index value used to uniquely identify
          this Port Mirror Session within Network Element."
    ::= { f3MirrorSessionEntry 1 }

f3MirrorSessionSourcePort OBJECT-TYPE
    SYNTAX        VariablePointer
    MAX-ACCESS    read-create
    STATUS        current
    DESCRIPTION
         "Pointer to a Port instance which represents 
          Monitored Port with the Mirror Session.
          
          The pointer must be set to cmEthernetAccPortIndex 
          or cmEthernetNetPortIndex instance."
    ::= { f3MirrorSessionEntry 2 }

f3MirrorSessionMonitorPort OBJECT-TYPE
    SYNTAX        VariablePointer
    MAX-ACCESS    read-create
    STATUS        current
    DESCRIPTION
         "Pointer to a Port instance which represents 
          Port where mirrored frames are transmitted. 
          
          The pointer must be set to cmEthernetAccPortIndex 
          instance."
    ::= { f3MirrorSessionEntry 3 }

f3MirrorSessionSourcePortDir OBJECT-TYPE
    SYNTAX        TrafficDirection
    MAX-ACCESS    read-create
    STATUS        current
    DESCRIPTION
         "Indicates the SourcePort traffic flow direction 
          to be copied for transmit on the MonitorPort:
          
          1) INGRESS: frames received by the SourcePort 
                     are mirrored to the transmit direction of the 
                     MonitorPort.
            
          2) EGRESS: frames to be transmitted by the SourcePort 
                    are mirrored to the transmit direction of the 
                    MonitorPort."
    ::= { f3MirrorSessionEntry 4 }

f3MirrorSessionTruncationCtrl OBJECT-TYPE
    SYNTAX        TruthValue
    MAX-ACCESS    read-write
    STATUS        current
    DESCRIPTION
         "Indicates if frame is truncated to TruncationLength 
          before being transmitted on the Monitor Port:
          
          1) DISABLED: the frame is transmitted on the MonitorPort 
                      without length modification.
          2) ENABLED: the frame is truncated to TruncationLength 
                     before being transmitted on the MonitorPort. 
                     FCS is relaculated based on the truncated length."
    ::= { f3MirrorSessionEntry 5 }

f3MirrorSessionTruncationLength OBJECT-TYPE
    SYNTAX        Unsigned32(64..1500)
    MAX-ACCESS    read-write
    STATUS        current
    DESCRIPTION
         "Length of mirrored frame truncation when TruncationControl is ENABLED. 
          Possible values are 64 bytes to 1500 bytes.
          
          All mirrored frames transmitted on the MonitorPort will have a frame 
          length equal to the TruncationLength where frame length is from first 
          byte of the Destination MAC Address to last bye of the newly calculated FCS."
    ::= { f3MirrorSessionEntry 6 }

f3MirrorSessionTimestampControl OBJECT-TYPE
    SYNTAX        TruthValue
    MAX-ACCESS    read-write
    STATUS        current
    DESCRIPTION
         "Indicates if timestamp information is added 
          to a frame transmitted on the MonitorPort:
          
          1) DISABLED: no timestamp information is added 
                      to a frame transmitted on the MonitorPort.
                      
          2) ENABLED: a timestamp is added to the frame frame 
                     in the 10 bytes before the FCS:
                     - For mirrored frames ingressing the SourcePort, 
                       the timestamp is the TOD when the frame was 
                       received on the SourcePort. 
                     - For mirrored frames egressing the SourcePort, 
                       the timestamp is the TOD when the frames 
                       was transmitted on the SourcePort."
    ::= { f3MirrorSessionEntry 7 }

f3MirrorSessionStorageType OBJECT-TYPE
    SYNTAX        StorageType
    MAX-ACCESS    read-create
    STATUS        current
    DESCRIPTION
         "The type of storage configured for this entry."
    ::= { f3MirrorSessionEntry 8 }

f3MirrorSessionRowStatus OBJECT-TYPE
    SYNTAX        RowStatus
    MAX-ACCESS    read-create
    STATUS        current
    DESCRIPTION
         "The status of this row.  An entry MUST NOT exist in the 
          active state unless all objects in the entry have an 
          appropriate value, as described
          in the description clause for each writable object.

          The values of f3MirrorSessionRowStatus supported are
          createAndGo(4) and destroy(6).  All mandatory attributes
          must be specified in a single SNMP SET request with
          neRowStatus value as createAndGo(4).
          Upon successful row creation, this object has a
          value of active(1).
          
          The f3MirrorSessionRowStatus object may be modified if
          the associated instance of this object is equal to active(1)."
    ::= { f3MirrorSessionEntry 9 }

--
--  Access Port Port Mirror Ext Table
--

f3PortMirrorAccPortExtTable  OBJECT-TYPE
    SYNTAX      SEQUENCE OF F3PortMirrorAccPortExtEntry
    MAX-ACCESS  not-accessible
    STATUS      current
    DESCRIPTION
            "A list of entries corresponding to Ethernet Access Port 
            Facilities for Port Mirror configuration purposes."
    ::= { f3PortMirrorConfigObjects 2 }

f3PortMirrorAccPortExtEntry OBJECT-TYPE
    SYNTAX      F3PortMirrorAccPortExtEntry
    MAX-ACCESS  not-accessible
    STATUS      current
    DESCRIPTION
            "A conceptual row in the f3PortMirrorAccPortExtTable."
    AUGMENTS { cmEthernetAccPortEntry }
    ::= { f3PortMirrorAccPortExtTable 1 }

F3PortMirrorAccPortExtEntry ::= SEQUENCE {
    f3PortMirrorAccPortExtMonitorEnabled        TruthValue,
    f3PortMirrorAccPortExtBufferSize            Integer32
}

f3PortMirrorAccPortExtMonitorEnabled OBJECT-TYPE
    SYNTAX      TruthValue  
    MAX-ACCESS  read-write
    STATUS      current
    DESCRIPTION
        "This object allows to Enable/Disable Monitor Mode on Port."
    ::= { f3PortMirrorAccPortExtEntry 1 }

f3PortMirrorAccPortExtBufferSize OBJECT-TYPE
    SYNTAX      Integer32 (10..15360)
    MAX-ACCESS  read-write
    STATUS      current
    DESCRIPTION
        "Applicable when port is in Monitor Mode."
    ::= { f3PortMirrorAccPortExtEntry 2 }

--
--  Monitor Port Statistics Table 
--

f3MonitorPortStatsTable  OBJECT-TYPE
    SYNTAX      SEQUENCE OF F3MonitorPortStatsEntry
    MAX-ACCESS  not-accessible
    STATUS      current
    DESCRIPTION
            "A list of entries corresponding to the Access Port 
             related Monitor Port Statistics."
    ::= { f3PortMirrorStatsObjects 1 }

f3MonitorPortStatsEntry OBJECT-TYPE
    SYNTAX      F3MonitorPortStatsEntry
    MAX-ACCESS  not-accessible
    STATUS      current
    DESCRIPTION
            "A conceptual row in the f3MonitorPortStatsTable."
    INDEX { neIndex, shelfIndex, slotIndex, f3MonitorPortStatsIndex }
    ::= { f3MonitorPortStatsTable 1 }

F3MonitorPortStatsEntry ::= SEQUENCE {
    f3MonitorPortStatsIndex                      Integer32,
    f3MonitorPortStatsTailDropped                PerfCounter64
}

f3MonitorPortStatsIndex OBJECT-TYPE
    SYNTAX        Integer32 (1..255)
    MAX-ACCESS    not-accessible
    STATUS        current
    DESCRIPTION
         "An integer index value used to uniquely identify
          this Ethernet Access Port (Monitor Port) statistics"
    ::= { f3MonitorPortStatsEntry 1 }

f3MonitorPortStatsTailDropped OBJECT-TYPE
    SYNTAX        PerfCounter64
    MAX-ACCESS    read-only
    STATUS        current
    DESCRIPTION
         "64-bit rollover count for taildrops"
    ::= { f3MonitorPortStatsEntry 2 }

--
-- Conformance
--
f3PortMirrorCompliances OBJECT IDENTIFIER ::= {f3PortMirrorConformance 1}
f3PortMirrorGroups    OBJECT IDENTIFIER ::= {f3PortMirrorConformance 2}

f3PortMirrorCompliance MODULE-COMPLIANCE
    STATUS  current
    DESCRIPTION
            "Describes the requirements for conformance to the F3-PORTMIRROR-MIB compilance."
    MODULE  -- this module
        MANDATORY-GROUPS {
              f3MirrorSessionGroup, f3PortMirrorAccPortExtGroup, f3MonitorPortStatsGroup
        }
    ::= { f3PortMirrorCompliances 1 }

f3MirrorSessionGroup OBJECT-GROUP
    OBJECTS {
       f3MirrorSessionIndex,
       f3MirrorSessionSourcePort,
       f3MirrorSessionMonitorPort,
       f3MirrorSessionSourcePortDir,
       f3MirrorSessionTruncationCtrl,
       f3MirrorSessionTruncationLength,
       f3MirrorSessionTimestampControl,
       f3MirrorSessionStorageType,
       f3MirrorSessionRowStatus
    }
    STATUS  current
    DESCRIPTION
             "A collection of objects used to manage the Port Mirror Session."
    ::= { f3PortMirrorGroups 1 }

f3PortMirrorAccPortExtGroup OBJECT-GROUP
    OBJECTS {
       f3PortMirrorAccPortExtMonitorEnabled,
       f3PortMirrorAccPortExtBufferSize
    }
    STATUS  current
    DESCRIPTION
             "A collection of objects used to manage the Access Port
              attributes related with Port Mirror feature."
    ::= { f3PortMirrorGroups 2 }


f3MonitorPortStatsGroup OBJECT-GROUP
    OBJECTS {
       f3MonitorPortStatsIndex,
       f3MonitorPortStatsTailDropped
    }
    STATUS  current
    DESCRIPTION
             "A collection of Monitor Port statistic objects."
    ::= { f3PortMirrorGroups 3 }

END
