BRCD-FCIP-EXT-MIB DEFINITIONS ::= BEGIN
IMPORTS
       OBJECT-TYPE,
       MODULE-IDENTITY,
       Unsigned32,
       Counter32,
       mib-2               FROM SNMPv2-SMI
       bcsi FROM Brocade-REG-MIB
       TEXTUAL-CONVENTION,
       TruthValue, RowStatus, TimeStamp  FROM SNMPv2-TC
       InetAddressType,
       InetAddress,
       InetPortNumber FROM INET-ADDRESS-MIB
       InterfaceIndex FROM IF-MIB
       MODULE-COMPLIANCE,
       OBJECT-GROUP FROM SNMPv2-CONF;

fcipExtMIB MODULE-IDENTITY
       LAST-UPDATED "200704080000Z"
       ORGANIZATION "Brocade Communications Systems, Inc."
       CONTACT-INFO "Customer Support Group
		  Brocade Communications Systems,
		  1745 Technology Drive,
		  San Jose, CA 95110 U.S.A
		  Tel: +1-408-392-6061
		  Fax: +1-408-392-6656
		  Email: support@Brocade.COM
		  WEB: www.brocade.com"
       DESCRIPTION
           "The module defines management information specific to FCIP devices."

       REVISION	"200906191505Z" -- Jul 06, 2009 2:37pm	
       DESCRIPTION	"Removed duplicate entry of fcipExtendedLinkTable"

	::= { bcsi 4}

   -- ******************************************************************
   -- Textual conventions
   --
BrcdCompressionRatio ::= TEXTUAL-CONVENTION 
	DISPLAY-HINT "d" 
	STATUS current 
	DESCRIPTION "A number indicating a compression ratio over a set of bytes. 
		The value is defined as a set of bytes. The value is defined as 1000 * bytes(compressed) / 
		bytes(original) rounded to the next integer value. Note that compressed sets of bytes can 
		be larger than the corresponding uncompressed ones. Therefore, the number can be greater than 1000." 
	SYNTAX Unsigned32

   -- ******************************************************************
   -- The FCIP Link Extention Table
   --
fcipExtendedLinkTable OBJECT-TYPE 
	SYNTAX SEQUENCE OF FcipExtendedLinkEntry 
	MAX-ACCESS not-accessible 
	STATUS current 
	DESCRIPTION "The stats of fcip tunnel compression, retransmission, packet 
		loss, and latency details" 
	::= { fcipExtMIB 1} 

fcipExtendedLinkEntry OBJECT-TYPE 
	SYNTAX FcipExtendedLinkEntry 
	MAX-ACCESS not-accessible 
	STATUS current 
	DESCRIPTION "A conceptual row of the FCIP Extended Link Table containing additional stats." 
	INDEX { fcipExtendedLinkIfIndex } 
	::= { fcipExtendedLinkTable 1 } 

FcipExtendedLinkEntry ::= 
	SEQUENCE { 
	 fcipExtendedLinkIfIndex InterfaceIndex,
	 fcipExtendedLinkTcpRetransmits Counter64,
	 fcipExtendedLinkTcpDroppedPackets Counter64,
	 fcipExtendedLinkTcpSmoothedRTT Integer32,
	 fcipExtendedLinkCompressionRatio BrcdCompressionRatio,
	 fcipExtendedLinkRawBytes Counter64,
	 fcipExtendedLinkCompressedBytes Counter64,
	 fcipExtendedLinkConnectedCount Counter64,
	 fcipExtendedLinkRtxRtxTO Counter64,
	 fcipExtendedLinkRtxDupAck Counter64,
	 fcipExtendedLinkDupAck Counter64,
	 fcipExtendedLinkRtt Integer32,
	 fcipExtendedLinkOoo Counter64,
	 fcipExtendedLinkSlowStarts Counter64
	 }

fcipExtendedLinkIfIndex     OBJECT-TYPE
       SYNTAX InterfaceIndex
       MAX-ACCESS read-only
       STATUS current
       DESCRIPTION
           "The ifIndex value of the virtual interface corresponding to
            the FCIP Link running over TCP/IP."
       ::= { fcipExtendedLinkEntry 1 }

fcipExtendedLinkTcpRetransmits OBJECT-TYPE 
	SYNTAX Counter64 
	MAX-ACCESS read-only 
	STATUS current 
	DESCRIPTION "Number of segments retransmitted." 
	::= { fcipExtendedLinkEntry 2 }

fcipExtendedLinkTcpDroppedPackets OBJECT-TYPE 
	SYNTAX Counter64 
	MAX-ACCESS read-only 
	STATUS current 
	DESCRIPTION "Number of TCP packets dropped" 
	::= { fcipExtendedLinkEntry 3 }

fcipExtendedLinkCompressionRatio OBJECT-TYPE 
	SYNTAX BrcdCompressionRatio
	UNITS "milliseconds"
	MAX-ACCESS read-only 
	STATUS current 
	DESCRIPTION "Compression ratio" 
	::= { fcipExtendedLinkEntry 4 }

fcipExtendedLinkTcpSmoothedRTT OBJECT-TYPE 
	SYNTAX Integer32
	UNITS "milliseconds"
	MAX-ACCESS read-only 
	STATUS current 
	DESCRIPTION "Round trip time (latency) in milliseconds" 
	::= { fcipExtendedLinkEntry 5 }

fcipExtendedLinkRawBytes OBJECT-TYPE 
	SYNTAX Counter64
	MAX-ACCESS read-only 
	STATUS current 
	DESCRIPTION "Total number of raw bytes sent or received." 
	::= { fcipExtendedLinkEntry 6 }

fcipExtendedLinkCompressedBytes OBJECT-TYPE 
	SYNTAX Counter64
	MAX-ACCESS read-only 
	STATUS current 
	DESCRIPTION "The total number of compressed bytes sent or received" 
	::= { fcipExtendedLinkEntry 7 }

fcipExtendedLinkConnectedCount OBJECT-TYPE 
	SYNTAX Counter64
	MAX-ACCESS read-only 
	STATUS current 
	DESCRIPTION "TCP session connection count" 
	::= { fcipExtendedLinkEntry 8 }

fcipExtendedLinkRtxRtxTO OBJECT-TYPE 
	SYNTAX Counter64
	MAX-ACCESS read-only 
	STATUS current 
	DESCRIPTION "Counter of retransmit packets due to timeout" 
	::= { fcipExtendedLinkEntry 9 }

fcipExtendedLinkRtxDupAck OBJECT-TYPE 
	SYNTAX Counter64
	MAX-ACCESS read-only 
	STATUS current 
	DESCRIPTION "Counter of retransmit packets due to duplicate acknowledgement" 
	::= { fcipExtendedLinkEntry 10 }

fcipExtendedLinkDupAck OBJECT-TYPE 
	SYNTAX Counter64
	MAX-ACCESS read-only 
	STATUS current 
	DESCRIPTION "Counter of duplicate acknowledgement packets" 
	::= { fcipExtendedLinkEntry 11 }

fcipExtendedLinkRtt OBJECT-TYPE 
	SYNTAX Integer32 
	MAX-ACCESS read-only 
	STATUS current 
	DESCRIPTION "Round trip time in milliseconds" 
	::= { fcipExtendedLinkEntry 12 }

fcipExtendedLinkOoo OBJECT-TYPE 
	SYNTAX Counter64
	MAX-ACCESS read-only 
	STATUS current 
	DESCRIPTION "Counter of TCP out-of-order" 
	::= { fcipExtendedLinkEntry 13 }

fcipExtendedLinkSlowStarts OBJECT-TYPE 
	SYNTAX Counter64
	MAX-ACCESS read-only 
	STATUS current 
	DESCRIPTION "Counter of slow starts" 
	::= { fcipExtendedLinkEntry 14 }


   -- ******************************************************************
   -- The FCIP Link conn stats  Table
   --
fcipConnStatsTable OBJECT-TYPE
    SYNTAX SEQUENCE OF FcipConnStatsEntry
    MAX-ACCESS not-accessible
    STATUS current
    DESCRIPTION "The stats of fcip tunnel compression, retransmission, packet 
        loss, and latency details"
    ::= { fcipExtMIB 2}

fcipConnStatsEntry OBJECT-TYPE
    SYNTAX FcipConnStatsEntry
    MAX-ACCESS not-accessible
    STATUS current
    DESCRIPTION "A conceptual row of the FCIP Extended Link Table containing
additional stats."
    INDEX {xfcipEntityId, xfcipLinkIndex }
    ::= { fcipConnStatsTable 1 }


FcipConnStatsEntry ::=
    SEQUENCE {
     xfcipEntityId   OCTET STRING,
     xfcipLinkIfIndex InterfaceIndex,
     xfcipLinkIndex   Unsigned32,
     xfcipExtendedLinkTcpRetransmits Counter64,
     xfcipExtendedLinkTcpDroppedPackets Counter64,
     xfcipExtendedLinkTcpSmoothedRTT Integer32,
     xfcipExtendedLinkCompressionRatio BrcdCompressionRatio,
     xfcipExtendedLinkRawBytes Counter64,
     xfcipExtendedLinkCompressedBytes Counter64
     }

xfcipEntityId   OBJECT-TYPE
       SYNTAX OCTET STRING (SIZE (8))
       MAX-ACCESS not-accessible
       STATUS current
       DESCRIPTION
           "The FCIP entity identifier."
       REFERENCE
           "RFC 3821, Section 7.1, FCIP Special Frame Format"
       ::= { fcipConnStatsEntry 1 }

xfcipLinkIfIndex     OBJECT-TYPE
       SYNTAX InterfaceIndex
       MAX-ACCESS read-only
       STATUS current
       DESCRIPTION
           "The ifIndex value of the virtual interface corresponding to
            the FCIP Link running over TCP/IP."
       ::= { fcipConnStatsEntry 2 }

xfcipLinkIndex     OBJECT-TYPE
       SYNTAX Unsigned32 (1..4294967295)
       MAX-ACCESS not-accessible
       STATUS current
       DESCRIPTION
           "An arbitrary integer that uniquely identifies one FCIP link
            within an FCIP entity."
       ::= {  fcipConnStatsEntry 3 }

xfcipExtendedLinkTcpRetransmits OBJECT-TYPE
    SYNTAX Counter64
    MAX-ACCESS read-only
    STATUS current
    DESCRIPTION "Number of segments retransmitted."
    ::= { fcipConnStatsEntry 4 }

xfcipExtendedLinkTcpDroppedPackets OBJECT-TYPE
    SYNTAX Counter64
    MAX-ACCESS read-only
    STATUS current
    DESCRIPTION "Number of TCP packets dropped"
    ::= { fcipConnStatsEntry 5 }

xfcipExtendedLinkCompressionRatio OBJECT-TYPE
    SYNTAX BrcdCompressionRatio
    UNITS "milliseconds"
    MAX-ACCESS read-only
    STATUS current
    DESCRIPTION "Compression ratio"
    ::= { fcipConnStatsEntry 6 }

xfcipExtendedLinkTcpSmoothedRTT OBJECT-TYPE
    SYNTAX Integer32
    UNITS "milliseconds"
    MAX-ACCESS read-only
    STATUS current
    DESCRIPTION "Round trip time (latency) in milliseconds"
    ::= { fcipConnStatsEntry 7 }


xfcipExtendedLinkRawBytes OBJECT-TYPE
    SYNTAX Counter64
    MAX-ACCESS read-only
    STATUS current
    DESCRIPTION "Total number of raw bytes sent or received."
    ::= {  fcipConnStatsEntry 8 }

xfcipExtendedLinkCompressedBytes OBJECT-TYPE
    SYNTAX Counter64
    MAX-ACCESS read-only
    STATUS current
    DESCRIPTION "The total number of compressed bytes sent or received"
    ::= { fcipConnStatsEntry 9 }

END
