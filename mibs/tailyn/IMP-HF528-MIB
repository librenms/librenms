-- File Name : IMP-HF528_v1.4_Y2024.mib
-- *****************************************************************
-- Product Name: IMP-HF528/828 Industrial Switch
-- Version: v1.4
-- Update and Release Notes:
-- Data(Y/M/D) | MIB version | Note
-- 2022-10-11   v1.4         add iswGVRP
--                           add iswDHCPRelay, iswDHCPSnooping
--                           add iswDvmrpConf, iswPimConf, iswDvmrpIfConfTable
--                           remove
--                             export-cliconfig-binary(9),
--                             import-cliconfig-binary(12),
--                             import-cliconfig-binary-restart(13),
-- 2021-12-30	v1.3         1. Add iswEventDdmiTraps and iswDDM.
-- 2021-12-20   v1.2         1. Add full10gbps(8) for iswPortEnetLinkStatus. 
-- 2020-09-08   v1.1         1. Revision for specific vendor
-- 2019-01-03   v1.1         1. Alignment with current firmware.
-- *****************************************************************

IMP-HF528-MIB	DEFINITIONS ::= BEGIN
	IMPORTS
		PhysicalIndex
			FROM ENTITY-MIB
		PhysAddress, RowStatus, TAddress, TEXTUAL-CONVENTION, TruthValue
			FROM SNMPv2-TC
		Integer32, IpAddress, Unsigned32, Counter32, Counter64, 
		NOTIFICATION-TYPE, MODULE-IDENTITY, OBJECT-TYPE, enterprises
			FROM SNMPv2-SMI
		InterfaceIndex
			FROM IF-MIB;

--
--
	IswGbeIndex	::=	TEXTUAL-CONVENTION
		DISPLAY-HINT	""
		STATUS		current
		DESCRIPTION     "The Gigabit Ethernet Port."
		SYNTAX		INTEGER	 {
                        iswGEPort-1(1),
                        iswGEPort-2(2),
                        iswGEPort-3(3),
                        iswGEPort-4(4),
                        iswGEPort-5(5),
                        iswGEPort-6(6),
                        iswGEPort-7(7),
                        iswGEPort-8(8),
                        iswGEPort-9(9),
                        iswGEPort-10(10),
                        iswGEPort-11(11),
                        iswGEPort-12(12),
                        iswGEPort-13(13),
                        iswGEPort-14(14),
                        iswGEPort-15(15),
                        iswGEPort-16(16),
                        iswGEPort-17(17),
                        iswGEPort-18(18),
                        iswGEPort-19(19),
                        iswGEPort-20(20),
                        iswGEPort-21(21),
                        iswGEPort-22(22),
                        iswGEPort-23(23),
                        iswGEPort-24(24),
                        iswGEPort-25(25),
                        iswGEPort-26(26),
                        iswGEPort-27(27),
                        iswGEPort-28(28),
                        }
	IswPFIndex	::=	TEXTUAL-CONVENTION
		DISPLAY-HINT	""
		STATUS		current
		DESCRIPTION     "The Profile Index."
		SYNTAX		INTEGER	 {
                        iswProfile-1(1),
                        iswProfile-2(2),
                        iswProfile-3(3),
                        iswProfile-4(4),
                        iswProfile-5(5),
                        iswProfile-6(6),
                        iswProfile-7(7)
                        }
	IswIgmpPortIndex	::=	TEXTUAL-CONVENTION
		DISPLAY-HINT	""
		STATUS		current
		DESCRIPTION     "The Igmp Gigabit Ethernet Port."
		SYNTAX		INTEGER	 {
                        iswGEPort-1(1),
                        iswGEPort-2(2),
                        iswGEPort-3(3),
                        iswGEPort-4(4),
                        iswGEPort-5(5),
                        iswGEPort-6(6),
                        iswGEPort-7(7),
                        iswGEPort-8(8),
                        iswGEPort-9(9),
                        iswGEPort-10(10),
                        iswGEPort-11(11),
                        iswGEPort-12(12),
                        iswGEPort-13(13),
                        iswGEPort-14(14),
                        iswGEPort-15(15),
                        iswGEPort-16(16),
                        iswGEPort-17(17),
                        iswGEPort-18(18),
                        iswGEPort-19(19),
                        iswGEPort-20(20),
                        iswGEPort-21(21),
                        iswGEPort-22(22),
                        iswGEPort-23(23),
                        iswGEPort-24(24),
                        iswGEPort-25(25),
                        iswGEPort-26(26),
                        iswGEPort-27(27),
                        iswGEPort-28(28),
                        auto(255)
                        }
	IswGbeAndTrunkPortsIndex	::=	TEXTUAL-CONVENTION
		DISPLAY-HINT	""
		STATUS		current
		DESCRIPTION     "The Gigabit Ethernet Port and Trunk Port."
		SYNTAX		INTEGER	 {
                        iswGEPort-1(1),
                        iswGEPort-2(2),
                        iswGEPort-3(3),
                        iswGEPort-4(4),
                        iswGEPort-5(5),
                        iswGEPort-6(6),
                        iswGEPort-7(7),
                        iswGEPort-8(8),
                        iswGEPort-9(9),
                        iswGEPort-10(10),
                        iswGEPort-11(11),
                        iswGEPort-12(12),
                        iswGEPort-13(13),
                        iswGEPort-14(14),
                        iswGEPort-15(15),
                        iswGEPort-16(16),
                        iswGEPort-17(17),
                        iswGEPort-18(18),
                        iswGEPort-19(19),
                        iswGEPort-20(20),
                        iswGEPort-21(21),
                        iswGEPort-22(22),
                        iswGEPort-23(23),
                        iswGEPort-24(24),
                        iswGEPort-25(25),
                        iswGEPort-26(26),
                        iswGEPort-27(27),
                        iswGEPort-28(28),
                        iswLAG-1(29),
                        iswLAG-2(30),
                        iswLAG-3(31),
                        iswLAG-4(32),
                        iswLAG-5(33),
                        iswLAG-6(34),
                        iswLAG-7(35),
                        iswLAG-8(36),
                        iswLAG-9(37),
                        iswLAG-10(38),
                        iswLAG-11(39),
                        iswLAG-12(40),
                        iswLAG-13(41),
                        iswLAG-14(42),
                        iswLAG-15(43),
                        iswLAG-16(44),
                        iswLAG-17(45),
                        iswLAG-18(46),
                        iswLAG-19(47),
                        iswLAG-20(48),
                        iswLAG-21(49),
                        iswLAG-22(50),
                        iswLAG-23(51),
                        iswLAG-24(52),
                        iswLAG-25(53),
                        iswLAG-26(54),
                        iswLAG-27(55),
                        iswLAG-28(56)
                        }

	IswEntIndex	::=	TEXTUAL-CONVENTION
		DISPLAY-HINT	""
		STATUS		current
		DESCRIPTION     "The Entity index to indicate the event physical inerface."
		SYNTAX		INTEGER	 {
                        system(1),
                        main-card(2),
                        gbe-card(3)
                        }

	IswEventType	::=	TEXTUAL-CONVENTION
		DISPLAY-HINT	""
		STATUS		current
		DESCRIPTION     "The event type identifier number."
		SYNTAX		INTEGER	 {
                        iswSystemRestart(1),
                        iswSystemDownloadBegin(2),
                        iswSystemDownloadSuccess(3),
                        iswSystemDownloadFail(4),
                        iswSystemProvisiondataExport(5),
                        iswSystemProvisiondataImport(6),
                        iswSystemProvisiondataSetdefault(7),
                        iswSystemAlarmLogClear(9),
                        iswSystemEventLogClear(10),
                        iswSystemRTCDateTimeChange(11),
                        iswSystemAlarmProfileChange(14),
                        iswSystemFTPReceptionStart(17),
                        iswSystemFTPReceptionComplete(18),
                        iswSystemFTPReceptionIncomplete(19),
                        iswSystemSNTPTimeZoneChange(21),
                        iswSystemSNTPProvisionChanged(23),
                        iswSystemDatabaseSavingFailed(25),
                        iswSystemUserLoginSuccess(26),
                        iswSystemUserLoginFailure(27),
                        iswSystemLoginSessionLogout(28),
                        iswSystemLoginSessionTimeout(29),
                        iswSystemDDMIEnabled(301),
                        iswSystemDDMIDisabled(302),
                        iswGEPortSFPTemperatureReachesHighAlarm(303),
                        iswGEPortSFPTemperatureReachesLowAlarm(304),
                        iswGEPortSFPTemperatureReachesHighWarning(305),
                        iswGEPortSFPTemperatureReachesLowWarning(306),
                        iswGEPortSFPTemperatureReturnsToNormal(307),
                        iswGEPortLinkup(501),
                        iswGEPortLinkdown(502),
                        iswSystemAlarmLEDOn(601),
                        iswSystemAlarmLEDOff(602),
                        iswSystemAlarmOutputOn(603),
                        iswSystemAlarmOutputOff(604),
                        iswClusterInformationchanged(701)
                        }

	IswAlarmType	::=	TEXTUAL-CONVENTION
		DISPLAY-HINT	""
		STATUS		current
		DESCRIPTION     "The alarm type identifier number."
		SYNTAX		INTEGER	 {
                        iswAlarmGE1PortLinkDown(101),
                        iswAlarmGE2PortLinkDown(102),
                        iswAlarmGE3PortLinkDown(103),
                        iswAlarmGE4PortLinkDown(104),
                        iswAlarmGE5PortLinkDown(105),
                        iswAlarmGE6PortLinkDown(106),
                        iswAlarmGE7PortLinkDown(107),
                        iswAlarmGE8PortLinkDown(108),
                        iswAlarmGE9PortLinkDown(109),
                        iswAlarmGE10PortLinkDown(110),
                        iswAlarmGE11PortLinkDown(111),
                        iswAlarmGE12PortLinkDown(112),
                        iswAlarmGE13PortLinkDown(113),
                        iswAlarmGE14PortLinkDown(114),
                        iswAlarmGE15PortLinkDown(115),
                        iswAlarmGE16PortLinkDown(116),
                        iswAlarmGE17PortLinkDown(117),
                        iswAlarmGE18PortLinkDown(118),
                        iswAlarmGE19PortLinkDown(119),
                        iswAlarmGE20PortLinkDown(120),
                        iswAlarmGE21PortLinkDown(121),
                        iswAlarmGE22PortLinkDown(122),
                        iswAlarmGE23PortLinkDown(123),
                        iswAlarmGE24PortLinkDown(124),
                        iswAlarmGE25PortLinkDown(125),
                        iswAlarmGE26PortLinkDown(126),
                        iswAlarmGE27PortLinkDown(127),
                        iswAlarmGE28PortLinkDown(128),
                        iswAlarmPowerAlarm(151),
                        iswAlarmSystemTemperatureAbove(201),
                        iswAlarmSystemTemperatureBelow(202),
                        iswAlarmClusterMasterDuplication(301),
                        iswAlarmClusteMasterOutofCapacity(302),
                        iswAlarmClusterHostUnmangaged(303)
                        }

	IswAlarmLevel	::=	TEXTUAL-CONVENTION
		DISPLAY-HINT	""
		STATUS		current
		DESCRIPTION    	"The alarm level identifier number."
		SYNTAX		INTEGER  {
                        iswAlm-minor(1),
                        iswAlm-major(2)
                        }

	IswAlarmMask	::=	TEXTUAL-CONVENTION
		DISPLAY-HINT	""
		STATUS		current
		DESCRIPTION    	"The alarm level identifier number."
		SYNTAX		INTEGER  {
                        iswAlm-Mask(0),
                        iswAlm-UnMask(1)
                        }

	IswAlarmState	::=	TEXTUAL-CONVENTION
		DISPLAY-HINT	""
		STATUS		current
		DESCRIPTION    	"The alarm level identifier number."
		SYNTAX		INTEGER  {
                        iswAlm-Set(1),
                        iswAlm-Cleared(2)
                        }
	IswAlarmIfIndex	::=	TEXTUAL-CONVENTION
		DISPLAY-HINT	""
		STATUS		current
		DESCRIPTION     "The Alarm IfIndex definition."
		SYNTAX		INTEGER	 {
                        system(0),
                        iswGEPort-1(1),
                        iswGEPort-2(2),
                        iswGEPort-3(3),
                        iswGEPort-4(4),
                        iswGEPort-5(5),
                        iswGEPort-6(6),
                        iswGEPort-7(7),
                        iswGEPort-8(8),
                        iswGEPort-9(9),
                        iswGEPort-10(10),
                        iswGEPort-11(11),
                        iswGEPort-12(12),
                        iswGEPort-13(13),
                        iswGEPort-14(14),
                        iswGEPort-15(15),
                        iswGEPort-16(16),
                        iswGEPort-17(17),
                        iswGEPort-18(18),
                        iswGEPort-19(19),
                        iswGEPort-20(20),
                        iswGEPort-21(21),
                        iswGEPort-22(22),
                        iswGEPort-23(23),
                        iswGEPort-24(24),
                        iswGEPort-25(25),   --todo 10GPort-1
                        iswGEPort-26(26),
                        iswGEPort-27(27),
                        iswGEPort-28(28),
                        }
	IswEventIfIndex	::=	TEXTUAL-CONVENTION
		DISPLAY-HINT	""
		STATUS		current
		DESCRIPTION     "The Event Ifindex definition."
		SYNTAX		INTEGER	 {
                        system(0),
                        iswGEPort-1(1),
                        iswGEPort-2(2),
                        iswGEPort-3(3),
                        iswGEPort-4(4),
                        iswGEPort-5(5),
                        iswGEPort-6(6),
                        iswGEPort-7(7),
                        iswGEPort-8(8),
                        iswGEPort-9(9),
                        iswGEPort-10(10),
                        iswGEPort-11(11),
                        iswGEPort-12(12),
                        iswGEPort-13(13),
                        iswGEPort-14(14),
                        iswGEPort-15(15),
                        iswGEPort-16(16),
                        iswGEPort-17(17),
                        iswGEPort-18(18),
                        iswGEPort-19(19),
                        iswGEPort-20(20),
                        iswGEPort-21(21),
                        iswGEPort-22(22),
                        iswGEPort-23(23),
                        iswGEPort-24(24),
                        iswGEPort-25(25),
                        iswGEPort-26(26),
                        iswGEPort-27(27),
                        iswGEPort-28(28),
--                      iswAlarmGE1PortLinkDown(101),
--                        iswAlarmGE2PortLinkDown(102),
--                        iswAlarmGE3PortLinkDown(103),
--                        iswAlarmGE4PortLinkDown(104),
--                        iswAlarmGE5PortLinkDown(105),
--                        iswAlarmGE6PortLinkDown(106),
--                        iswAlarmGE7PortLinkDown(107),
--                        iswAlarmGE8PortLinkDown(108),
--                        iswAlarmGE9PortLinkDown(109),
--                        iswAlarmGE10PortLinkDown(110),
--                        iswAlarmGE11PortLinkDown(111),
--                        iswAlarmGE12PortLinkDown(112),
--                        iswAlarmGE13PortLinkDown(113),
--                        iswAlarmGE14PortLinkDown(114),
--                        iswAlarmGE15PortLinkDown(115),
--                        iswAlarmGE16PortLinkDown(116),
--                        iswAlarmGE17PortLinkDown(117),
--                        iswAlarmGE18PortLinkDown(118),
--                        iswAlarmGE19PortLinkDown(119),
--                        iswAlarmGE20PortLinkDown(120),
--                        iswAlarmGE21PortLinkDown(121),
--                        iswAlarmGE22PortLinkDown(122),
--                        iswAlarmGE23PortLinkDown(123),
--                        iswAlarmGE24PortLinkDown(124),
--                        iswAlarmGE25PortLinkDown(125),
--                        iswAlarmGE26PortLinkDown(126),
--                        iswAlarmGE27PortLinkDown(127),
--                        iswAlarmGE28PortLinkDown(128),
--                        iswAlarmPowerAlarm(151),
--                        iswAlarmSystemTemperatureAbove(201),
--                        iswAlarmSystemTemperatureBelow(202),
--                        iswAlarmClusterMasterDuplication(301),
--                        iswAlarmClusteMasterOutofCapacity(302),
--                        iswAlarmClusterHostUnmangaged(303)
                        }
-- TEXTUAL-CONVENTIONS --

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	switch	OBJECT IDENTIFIER
		::=  { enterprises 5833 }   
		
	imp-HF528-mib	MODULE-IDENTITY
		LAST-UPDATED	"202112200000Z"
		ORGANIZATION	""
		CONTACT-INFO	""
		DESCRIPTION	"Industrial Ethernet Switch root MIB module."
		REVISION	"201801030000Z"
		DESCRIPTION	"The modified revision : v1.1"
		REVISION	"202112200000Z"
		DESCRIPTION	"The modified revision : v1.2"
		::=  { switch 2017 }

	iswNextIndexQuery	OBJECT IDENTIFIER
		::=  { imp-HF528-mib 1 }
	iswConfMgt	OBJECT IDENTIFIER
		::=  { imp-HF528-mib 2 }
	iswSysMgt	OBJECT IDENTIFIER
		::=  { imp-HF528-mib 3 }
	iswMtnMgt	OBJECT IDENTIFIER
		::=  { imp-HF528-mib 4 }
	iswPerform	OBJECT IDENTIFIER
		::=  { imp-HF528-mib 5 }
	iswEvtMgt	OBJECT IDENTIFIER
		::=  { imp-HF528-mib 6 }
	iswAlmMgt	OBJECT IDENTIFIER
		::=  { imp-HF528-mib 7 }
	iswTraps	OBJECT IDENTIFIER
		::=  { imp-HF528-mib 8 }

--
-- ## Config Group --
	iswBridge					OBJECT IDENTIFIER
		::=  { iswConfMgt 1 }
	iswStpGrp					OBJECT IDENTIFIER
		::=  { iswConfMgt 2 }
	iswIgmp						OBJECT IDENTIFIER
		::=  { iswConfMgt 3 }
	iswQos						OBJECT IDENTIFIER
		::=  { iswConfMgt 4 }
	iswAcl						OBJECT IDENTIFIER
		::=  { iswConfMgt 5 }
	iswEnetPort					OBJECT IDENTIFIER
		::=  { iswConfMgt 6 } 
	iswRingProtect				OBJECT IDENTIFIER
		::=  { iswConfMgt 7 }
	iswLayer3					OBJECT IDENTIFIER
		::=  { iswConfMgt 8 }
	isw8021x					OBJECT IDENTIFIER
		::=  { iswConfMgt 9 }
	iswLinkAgg					OBJECT IDENTIFIER
		::=  { iswConfMgt 10 }
	iswPTP						OBJECT IDENTIFIER
		::=  { iswConfMgt 11 }
	iswSyncE					OBJECT IDENTIFIER
		::=  { iswConfMgt 12 }		
	iswDHCPServer				OBJECT IDENTIFIER
		::=  { iswConfMgt 14 }
	iswGRingProtect				OBJECT IDENTIFIER
		::=  { iswConfMgt 15 }
--	iswDHCPClient				OBJECT IDENTIFIER
--		::=  { iswConfMgt 16 }
	iswLLDP				OBJECT IDENTIFIER
		::=  { iswConfMgt 17 }
	iswDHCPClass				OBJECT IDENTIFIER
		::=  { iswConfMgt 18 }	
	iswDHCPRelay				OBJECT IDENTIFIER
		::=  { iswConfMgt 19 }	
	iswDHCPSnooping				OBJECT IDENTIFIER
		::=  { iswConfMgt 20 }
	iswErps						OBJECT IDENTIFIER
		::=  { iswConfMgt 21 }
	iswGVRP						OBJECT IDENTIFIER
		::=  { iswConfMgt 22 } 
	iswIPSG						OBJECT IDENTIFIER
		::=  { iswConfMgt 23 }
	iswDRouteTbl                OBJECT IDENTIFIER
		::=  { iswConfMgt 50 }
	iswLACP						OBJECT IDENTIFIER
		::=  { iswConfMgt 51 }
	iswPRG						OBJECT IDENTIFIER
		::=  { iswConfMgt 52 }
	iswSnmp						OBJECT IDENTIFIER
		::=  { iswConfMgt 53 }
	iswLoopProtection					OBJECT IDENTIFIER
		::=  { iswConfMgt 55 }
--
	iswStp						OBJECT IDENTIFIER
		::=  { iswStpGrp 1 } 
	
	iswJumboFrame				OBJECT IDENTIFIER
		::=  { iswEnetPort 2 } 
	iswVlan						OBJECT IDENTIFIER
		::= { iswBridge 3 }
	iswFdb						OBJECT IDENTIFIER
		::= { iswBridge 4 }
	iswStormCtrl				OBJECT IDENTIFIER
		::= { iswBridge 5 }
	
	iswAclMirrorAnalyzerPort	OBJECT IDENTIFIER
		::= { iswAcl 4 }

	iswPolicer					OBJECT IDENTIFIER 
		::= { iswQos 1 }		
	iswShaper					OBJECT IDENTIFIER 
		::= { iswQos 2 }
	iswQueScheduler				OBJECT IDENTIFIER 
		::= { iswQos 3 }
	
	iswVlanMember				OBJECT IDENTIFIER 
		::= { iswVlan 1 }
		
	iswPolicerIngressColor		OBJECT IDENTIFIER 
		::= { iswPolicer 1 }
	iswPolicerColorMarking		OBJECT IDENTIFIER 
		::= { iswPolicer 2 }
			
	iswCosQueMapping			OBJECT IDENTIFIER 
		::= { iswQueScheduler 1 }
		
	iswGateway					OBJECT IDENTIFIER
		::=  { iswLayer3 1 }
	iswTrackObjectConfig		OBJECT IDENTIFIER
		::=  { iswLayer3 9 }
	iswRipConfig				OBJECT IDENTIFIER
		::=  { iswLayer3 5 }
	iswOspfConfig				OBJECT IDENTIFIER
		::=  { iswLayer3 6 }
	iswVrrpGroupConfig		OBJECT IDENTIFIER
		::=  { iswLayer3 7 }
	iswLayer3Status			OBJECT IDENTIFIER
		::=  { iswLayer3 8 }
	iswDvmrpConf			OBJECT IDENTIFIER
		::=  { iswLayer3 10 }
	iswPimConf              OBJECT IDENTIFIER
		::=  { iswLayer3 11 }
	iswIPv6StaticRoute			OBJECT IDENTIFIER
		::=  { iswLayer3 12 }
	iswMc						OBJECT IDENTIFIER
		::=  { iswLayer3 13 }

	iswRipRoute					OBJECT IDENTIFIER
		::=  { iswLayer3Status 1 }

	iswRipRouteDeleteCtrl		OBJECT IDENTIFIER
		::=  { iswRipRoute 2 }		
	
	iswGRingV2Ring1		OBJECT IDENTIFIER
		--DESCRIPTION		"G-Ring v2, Ring Group 1"
		::=  { iswGRingProtect 1 }
	iswGRingV2Ring2		OBJECT IDENTIFIER
		--DESCRIPTION		"G-Ring v2, Ring Group 2"
		::=  { iswGRingProtect 2 }
	iswGRingV2Ring3		OBJECT IDENTIFIER
		--DESCRIPTION		"G-Ring v2, Ring Group 3"
		::=  { iswGRingProtect 3 }
--
	iswIPSGPort						OBJECT IDENTIFIER
		::=  { iswIPSG 	1 }
	iswIPSGStaticBinding			OBJECT IDENTIFIER
		::=  { iswIPSG 	2 }
	iswIPSGBinding					OBJECT IDENTIFIER
		::=  { iswIPSG 	3 }
	iswIPSGBindingDeleteCtrl		OBJECT IDENTIFIER
		::=  { iswIPSG 	4 }
--
	iswLACPSystem		OBJECT IDENTIFIER
		::=  { iswLACP	1 }
	iswLACPPort			OBJECT IDENTIFIER
		::=  { iswLACP 	2 }
	iswLACPAggr			OBJECT IDENTIFIER
		::=  { iswLACP 	3 }
--
	iswPRGSystem		OBJECT IDENTIFIER
		::=  { iswPRG	1 }
	iswPRGPort			OBJECT IDENTIFIER
		::=  { iswPRG	2 }
	iswPRGGroup			OBJECT IDENTIFIER
		::=  { iswPRG	3 }
--
	iswDHCPSnoopingBindingDeleteCtrl		OBJECT IDENTIFIER
		::=  { iswDHCPSnooping 4 }
--
	iswEcfmGlobal		OBJECT IDENTIFIER
		::=  { iswErps 1 }
	
	iswEcfmDomain		OBJECT IDENTIFIER
		::=  { iswErps 2 }
		
	iswEcfmService		OBJECT IDENTIFIER
		::=  { iswErps 3 }
		
	iswEcfmMep		OBJECT IDENTIFIER
		::=  { iswErps 4 }
		
	iswEcfmPort		OBJECT IDENTIFIER
		::=  { iswErps 5 }
		
	iswEcfmCcm		OBJECT IDENTIFIER
		::=  { iswErps 6 }
		
	iswEcfmStatus		OBJECT IDENTIFIER
		::=  { iswErps 7 }
		
	iswEcfmStatusErrors		OBJECT IDENTIFIER
		::=  { iswErps 8 }
	
	iswErpsGlobal		OBJECT IDENTIFIER
		::=  { iswErps 9 }
	
	iswErpsRing		OBJECT IDENTIFIER
		::=  { iswErps 10 }
		
	iswErpsRingActionCtrl	OBJECT IDENTIFIER
		::=  { iswErpsRing 2 }
		
	iswErpsStatus		OBJECT IDENTIFIER
		::=  { iswErps 11 }
--
	iswGVRPConf						OBJECT IDENTIFIER
		::=  { iswGVRP 	1 }
	iswGVRPPortConf					OBJECT IDENTIFIER
		::=  { iswGVRP 	2 }
--
	iswMcConf						OBJECT IDENTIFIER
		::=  { iswMc 	1 }
	iswMcIfConf						OBJECT IDENTIFIER
		::=  { iswMc	2 }
	iswMcRoute						OBJECT IDENTIFIER
		::=  { iswMc 	3 }
	iswMRoute					OBJECT IDENTIFIER
		::=  { iswMc 	5 }

--
	iswSnmpUSMUser						OBJECT IDENTIFIER
		::=  { iswSnmp 	1 }
	iswSnmpVACMGroup					OBJECT IDENTIFIER
		::=  { iswSnmp 	2 }
	iswSnmpCommunity					OBJECT IDENTIFIER
		::=  { iswSnmp 	3 }
	iswSnmpVACMView						OBJECT IDENTIFIER
		::=  { iswSnmp 	4 }
	iswSnmpVersion						OBJECT IDENTIFIER
		::=  { iswSnmp 	5 }		
		
	iswSnmpVACMViewDeleteCtrl		OBJECT IDENTIFIER
		::=  { iswSnmpVACMView 2 }
		
	iswLoopProtectSystemConfig		OBJECT IDENTIFIER
		::=  { iswLoopProtection 1 }
	
	iswLoopProtectPortConfig		OBJECT IDENTIFIER
		::=  { iswLoopProtection 2 }

	iswLoopProtectPortStatus		OBJECT IDENTIFIER
		::=  { iswLoopProtection 3 }
		
-- ## System Group --	
	--iswMgmtLink				OBJECT IDENTIFIER
	--	::=  { iswSysMgt 1 }
	iswCli						OBJECT IDENTIFIER
		::=  { iswSysMgt 5 }
	iswSntpGrp					OBJECT IDENTIFIER
		::=  { iswSysMgt 6 } 
	iswSyslog					OBJECT IDENTIFIER
		::=  { iswSysMgt 7 }
	iswSysLedStatus				OBJECT IDENTIFIER
		::=  { iswSysMgt 8 }
	iswInventory				OBJECT IDENTIFIER
		::=  { iswSysMgt 9 }
	iswHttp 					OBJECT IDENTIFIER
		::=  { iswSysMgt 10 }
	iswSdp	 					OBJECT IDENTIFIER
		::=  { iswSysMgt 11 }
	iswUser						OBJECT IDENTIFIER
		::=  { iswSysMgt 12 }
	iswLedState					OBJECT IDENTIFIER
		::=  { iswSysMgt 13 }
	iswNtp						OBJECT IDENTIFIER
		::=  { iswSysMgt 14 }
	iswAlmSystemUsage			OBJECT IDENTIFIER
		::=  { iswSysMgt 15 }	
	iswBandwidth				OBJECT IDENTIFIER
		::=  { iswSysMgt 16 }
	iswFlashInfo				OBJECT IDENTIFIER
		::=  { iswSysMgt 17 }
--

	--iswCliConfig				OBJECT IDENTIFIER
	--	::= { iswCli 1 }
	iswCLISettings				OBJECT IDENTIFIER
		::= { iswCli 1 }

	iswSntp						OBJECT IDENTIFIER
		::= { iswSntpGrp 1 }
	iswSysDateTime				OBJECT IDENTIFIER
		::= { iswSntpGrp 2 }

	iswNtpServer				OBJECT IDENTIFIER
		::= { iswNtp 1 }
	iswNtpClient				OBJECT IDENTIFIER
		::= { iswNtp 2 }

-- ## Maintenance Group --
	iswDBSaveRestore			OBJECT IDENTIFIER
		::=  { iswMtnMgt 5 }
	iswMtnFirmware				OBJECT IDENTIFIER
		::=  { iswMtnMgt 6 }
	iswFTPServer				OBJECT IDENTIFIER
		::=  { iswMtnMgt 8 }
	iswSysTemperature			OBJECT IDENTIFIER
		::=  { iswMtnMgt 11 }
	iswDDM						OBJECT IDENTIFIER
		::=  { iswMtnMgt 12 }
	
	iswFWDownload				OBJECT IDENTIFIER
		::=  { iswMtnFirmware 1 }
--	iswFWDownloadStatus			OBJECT IDENTIFIER
--		::=  { iswMtnFirmware 2 }
		
-- ## Performance Group -- 
	iswPortStats				OBJECT IDENTIFIER
		::= { iswPerform 1 }

-- ## 
	iswIgmpAcl					OBJECT IDENTIFIER
		::= { iswIgmp 7 }
	iswIgmpMvr					OBJECT IDENTIFIER
		::= { iswIgmp 8 }

--
	iswIgmpSystem	OBJECT-TYPE
		SYNTAX		Integer32 { disable (0), enable (1) }
		MAX-ACCESS	read-write
		STATUS		current
		DESCRIPTION	"Enable/Disable system IGMP Snooping."
		DEFVAL		{0}
		::= { iswIgmp 9 }


-- ## MIB object details

-- ## NextIndexQuery Group --    
--    There are many tables need "Next Index" hint, before create new entry.
--	iswNextVlanIndex		OBJECT-TYPE
--		SYNTAX			Integer32   (0..4094)
--		MAX-ACCESS		read-only
--		STATUS			current
--		DESCRIPTION		"Next available VID of iswVlanTable, query it before create new entry.
--						 0 means no more index."
--		::=	 { iswNextIndexQuery 1 }

	iswNextFdbStaticIndex	OBJECT-TYPE
		SYNTAX			Integer32   ( 0 .. 512 )
		MAX-ACCESS		read-only
		STATUS			current
		DESCRIPTION		"Next available entry index of iswFdbStaticTable, query it before create new entry. 
						0 means no more index."
		::=	 { iswNextIndexQuery 1 }

	iswNextStaticMcFdbIndex	OBJECT-TYPE
		SYNTAX			Integer32   ( 0 .. 128 )
		MAX-ACCESS		read-only
		STATUS			current
		DESCRIPTION		"Next available entry index of iswStaticMcastFdbTable, query it before create new entry.
						0 means no more index."
		::=	 { iswNextIndexQuery 2 }

	iswNextAclProfileIndex	OBJECT-TYPE
		SYNTAX			Integer32   ( 0 .. 20 )
		MAX-ACCESS		read-only
		STATUS			current
		DESCRIPTION		"Next available entry index of iswAclProfileTable, query it before create new entry.
                         0 means no more index. Profile Index 1 is default profile, can't be set."
		::=	 { iswNextIndexQuery 3 }

	iswNextStaticRouteIndex	OBJECT-TYPE
		SYNTAX			Integer32   ( 0 .. 32 )
		MAX-ACCESS		read-only
		STATUS			current
		DESCRIPTION		"Next available entry index of iswStaticRouteTable, query it before create new entry.
						0 means no more index."
		::=	 { iswNextIndexQuery 4 }

	iswNextIgmpAclProfileIndex	OBJECT-TYPE
		SYNTAX			Integer32   ( 0 .. 15 )
		MAX-ACCESS		read-only
		STATUS			current
		DESCRIPTION		"Next available entry index of iswIgmpAclProfileTable, query it before create new entry. 
						0 means no more index. Profile Index 1 is default profile, can't be set."
		::=	 { iswNextIndexQuery 5 }

	iswNextIgmpMvrProfileIndex	OBJECT-TYPE
		SYNTAX			Integer32   ( 0 .. 15 )
		MAX-ACCESS		read-only
		STATUS			current
		DESCRIPTION		"Next available entry index of iswIgmpMvrProfileTable, query it before create new entry. 
						0 means no more index. Profile Index 1 is default profile, can't be set."
		::=	 { iswNextIndexQuery 6 }

	iswNextProtocolVlanIndex	OBJECT-TYPE
		SYNTAX			Integer32   ( 0 .. 20 )
		MAX-ACCESS		read-only
		STATUS			current
		DESCRIPTION		"Next available entry index of iswProtocolBaseVlanTable, query it before create new entry. 
						0 means no more index."
		::=	 { iswNextIndexQuery 7 }

	iswNextVlanTranslationIndex	OBJECT-TYPE
		SYNTAX			Integer32   ( 0 .. 20 )
		MAX-ACCESS		read-only
		STATUS			current
		DESCRIPTION		"Next available entry index of iswVlanTranslationTable, query it before create new entry. 
						0 means no more index."
		::=	 { iswNextIndexQuery 8 }

	iswNextMstpInstanceIndex	OBJECT-TYPE
		SYNTAX			Integer32   ( 0 .. 10 )
		MAX-ACCESS		read-only
		STATUS			current
		DESCRIPTION		"Next available entry index of iswMstpInstanceTable, query it before create new entry.
						0 means no more index."
		::=	 { iswNextIndexQuery 9 }
--
--  Bridge
	iswBridgePortTable	OBJECT-TYPE
		SYNTAX		SEQUENCE OF IswBridgePortEntry
		MAX-ACCESS	not-accessible 
		STATUS		current
		DESCRIPTION	"Bridge port table. Max entry size: port number."
		::= { iswBridge 1 }
		
	iswBridgePortEntry	OBJECT-TYPE
		SYNTAX		IswBridgePortEntry
		MAX-ACCESS	not-accessible
		STATUS		current
		DESCRIPTION	"Bridge port entry."
		INDEX		{ iswBridgePortIfcIndex }
		::= { iswBridgePortTable 1 }
		
	IswBridgePortEntry ::= SEQUENCE{
		iswBridgePortIfcIndex			IswGbeIndex,
		iswBridgePortDefaultVlan		Integer32,
		iswBridgePortDefaultPriority	Integer32,
		iswBridgePortAcceptFrameType	Integer32,
		--iswBridgePortMaxMacLimitMode	Integer32,
		--iswBridgePortMaxMac				Integer32
		--iswBridgePortLinkMode			Integer32,
	}
--1	
	iswBridgePortIfcIndex	OBJECT-TYPE
		SYNTAX		IswGbeIndex
		MAX-ACCESS	not-accessible
		STATUS		current
		DESCRIPTION	"Bridge port index."
		::= { iswBridgePortEntry 1 }  
--2
	iswBridgePortDefaultVlan	OBJECT-TYPE
		SYNTAX		Integer32 ( 1..4094 )
		MAX-ACCESS	read-write
		STATUS		current
		DESCRIPTION	"Bridge port default vlan. Default value is 1."
		DEFVAL		{ 1 }
		::= { iswBridgePortEntry 2 } 
--3
	iswBridgePortDefaultPriority	OBJECT-TYPE
		SYNTAX		Integer32 ( 0..7 )
		MAX-ACCESS	read-write
		STATUS		current
		DESCRIPTION	"Bridge port default priority. Default value is 0." 
		DEFVAL		{ 0 }
		::= { iswBridgePortEntry 3 }  
--4
	iswBridgePortAcceptFrameType	OBJECT-TYPE
		SYNTAX		Integer32 { all (1), onlyValnTagged (2), onlyUntagged (3) }
		MAX-ACCESS	read-write
		STATUS		current
		DESCRIPTION	"Bridge port accept frame type. Default value is all (1)."  
		DEFVAL		{ 1 }
		::= { iswBridgePortEntry 4 }
--5	
	--iswBridgePortMaxMacLimitMode	OBJECT-TYPE
	--	SYNTAX		Integer32 { disable (0), enable (1) }
	--	MAX-ACCESS	read-write
	--	STATUS		current
	--	DESCRIPTION	"Bridge port max mac limit mode. Default value is disable (0)."
	--	DEFVAL		{ 0 }
	--	::= { iswBridgePortEntry 5 }
--6
	--iswBridgePortMaxMac	OBJECT-TYPE
	--	SYNTAX		Integer32 ( 0..32 )
	--	MAX-ACCESS	read-write
	--	STATUS		current
	--	DESCRIPTION	"Bridge port max mac. Default value is 8."   
	--	DEFVAL		{ 8 }
	--	::= { iswBridgePortEntry 6 } 
--7
	--iswBridgePortLinkMode	OBJECT-TYPE
	--	SYNTAX		Integer32 { upLink(1), downLink(2) }
	--	MAX-ACCESS	read-write
	--	STATUS		current
	--	DESCRIPTION	"Bridge port link mode."
	--	::= { iswBridgePortEntry 7 }
--
	iswBridgePortIsoTable		OBJECT-TYPE
		SYNTAX		SEQUENCE OF IswBridgePortIsoEntry
		MAX-ACCESS	not-accessible
		STATUS		current
		DESCRIPTION	"Bridge port isolation table. Max entry size: port number."
		::= { iswBridge 2 }
		
	iswBridgePortIsoEntry	OBJECT-TYPE
		SYNTAX		IswBridgePortIsoEntry
		MAX-ACCESS	not-accessible
		STATUS		current
		DESCRIPTION	"Bridge port isolation entry."
		INDEX		{ iswBportIsolationSrcPort }
		::= { iswBridgePortIsoTable 1 }
		  
	IswBridgePortIsoEntry ::= SEQUENCE{
		iswBportIsolationSrcPort		IswGbeIndex,
		--iswBportIsolationDstPort		Integer32,
		--iswBportIsolationDstPortValue	Integer32,
		iswBportIsolationDstBitMap		OCTET STRING
	}
--1 
	iswBportIsolationSrcPort	OBJECT-TYPE
		SYNTAX		IswGbeIndex
		MAX-ACCESS	not-accessible
		STATUS		current
		DESCRIPTION	"Bridge port isolation source port."
		::= { iswBridgePortIsoEntry 1 }
--2       
	--iswBportIsolationDstPort	OBJECT-TYPE
	--	SYNTAX		Integer32 ( 1 .. 10 )
	--	MAX-ACCESS	read-write
	--	STATUS		current
	--	DESCRIPTION	"Bridge port isolation destination port."
	--	::= { iswBridgePortIsoEntry 2 }
--3     
	--iswBportIsolationDstPortValue	OBJECT-TYPE
	--	SYNTAX		Integer32 { enable (0), disable (1) }
	--	MAX-ACCESS	read-write
	--	STATUS		current
	--	DESCRIPTION	"Bridge port isolation destination port value."
	--	::= { iswBridgePortIsoEntry 3 }
--4
	iswBportIsolationDstBitMap	OBJECT-TYPE
		SYNTAX		OCTET STRING ( SIZE ( 4 ) )
		MAX-ACCESS	read-write
		STATUS		current
		DESCRIPTION	"Bridge port isolation destination bitmap.
					Byte[0] for port 7 ~ port 0, but port 0 not support.
					Byte[1] for port 15 ~ port 8.
					Byte[2] for port 23 ~ port 16.
					Byte[3] for port 28 ~ port 24.
					Byte[0] = 0x0 .. 0xFE
					Byte[1] = 0x0 .. 0xFF
					Byte[2] = 0x0 .. 0xFF
					Byte[3] = 0x0 .. 0x1F 
					Default 0x1FFFFFFE means port 1..28 are all disable port isolation.
					"
		--DEFVAL	{ "0x1FFFFFFE" }
		::= { iswBridgePortIsoEntry 2 }
--	
--1
	iswVlanMemberPort	OBJECT-TYPE
		SYNTAX		IswGbeIndex
		MAX-ACCESS	read-write
		STATUS		current
		DESCRIPTION	"Dot1q vlan memberset config: port index."
		::= { iswVlanMember 1 } 
--2
	iswVlanMemberVID	OBJECT-TYPE
		SYNTAX		Integer32 ( 1 .. 4094 )
		MAX-ACCESS	read-write
		STATUS		current
		DESCRIPTION	"Dot1q vlan memberset config: VLAN ID"
		::= { iswVlanMember 2 } 
--3 
	iswVlanMemberEgress	OBJECT-TYPE
		SYNTAX		Integer32 { leaveVlan (0), joinVlan (1) }
		MAX-ACCESS	read-write
		STATUS		current
		DESCRIPTION	"Dot1q vlan memberset config: join vlan or leave vlan."
		::= { iswVlanMember 3 }
--4 
	iswVlanMemberUntagged	OBJECT-TYPE
		SYNTAX		Integer32 { tag (0), untag (1) }
		MAX-ACCESS	read-write
		STATUS		current
		DESCRIPTION	"Dot1q vlan memberset config: tag or untagged port.
					If want to set untag, please set iswVlanEgressPorts to joinVlan first."
		::= { iswVlanMember 4 }
--
	iswVlanTable		OBJECT-TYPE
		SYNTAX		SEQUENCE OF IswVlanEntry
		MAX-ACCESS	not-accessible 
		STATUS		current
		DESCRIPTION	"VLAN table. Max entry size: 2048."
		::= { iswVlan 2 }
		
	iswVlanEntry	OBJECT-TYPE
		SYNTAX		IswVlanEntry
		MAX-ACCESS	not-accessible
		STATUS		current
		DESCRIPTION	"Vlan entry."
		INDEX		{ iswVlanIndex }
		::= { iswVlanTable 1 }
		
	IswVlanEntry ::= SEQUENCE{
		iswVlanIndex			Integer32,
		iswVlanName				OCTET STRING,
		iswVlanEgressPorts		OCTET STRING,
		iswVlanUntaggedPorts	OCTET STRING,
		iswVlanRowStatus		RowStatus
	}
--1
	iswVlanIndex	OBJECT-TYPE
		SYNTAX		Integer32 ( 1 .. 4094 )
		MAX-ACCESS	not-accessible
		STATUS		current
		DESCRIPTION	"Dot1q VLAN ID. Use iswNextVlanIndex to get next available VLAN ID."
		::= { iswVlanEntry 1 } 
--2
	iswVlanName	OBJECT-TYPE
		SYNTAX		OCTET STRING ( SIZE ( 0..32 ) )
		MAX-ACCESS	read-write
		STATUS		current
		DESCRIPTION	"Dot1q vlan name."
		DEFVAL		{ "" }
		::= { iswVlanEntry 2 }
--3
	iswVlanEgressPorts	OBJECT-TYPE
		SYNTAX		OCTET STRING ( SIZE ( 4 ) )
		MAX-ACCESS	read-write
		STATUS		current
		DESCRIPTION	"Dot1q vlan egress ports.
					Byte[0] for port 7 ~ port 0, but port 0 not support.
					Byte[1] for port 15 ~ port 8.
					Byte[2] for port 23 ~ port 16.
					Byte[3] for port 28 ~ port 24.
					Byte[0] = 0x0 .. 0xFE
					Byte[1] = 0x0 .. 0xFF
					Byte[2] = 0x0 .. 0xFF
					Byte[3] = 0x0 .. 0x1F
					Bit value is leaveVlan(0) or joinVlan(1).
					Default value is leaveVlan(0) for each bit.
					"
		--DEFVAL	{ 0 }
		::= { iswVlanEntry 3 }
--4
	iswVlanUntaggedPorts	OBJECT-TYPE
		SYNTAX		OCTET STRING ( SIZE ( 4 ) )
		MAX-ACCESS	read-write
		STATUS		current
		DESCRIPTION	"Dot1q vlan untagged ports.
					Byte[0] for port 7 ~ port 0, but port 0 not support.
					Byte[1] for port 15 ~ port 8.
					Byte[2] for port 23 ~ port 16.
					Byte[3] for port 28 ~ port 24.
					Byte[0] = 0x0 .. 0xFE
					Byte[1] = 0x0 .. 0xFF
					Byte[2] = 0x0 .. 0xFF
					Byte[3] = 0x0 .. 0x1F
					Bit value is tag(0) or untag(1).
					Default value is tag(0) for each bit.
					If want to set untag, please set iswVlanEgressPorts to joinVlan first.
					"
		--DEFVAL	{ 0 }
		::= { iswVlanEntry 4 } 
--5	
	iswVlanRowStatus	OBJECT-TYPE
		SYNTAX		RowStatus
		MAX-ACCESS	read-create
		STATUS		current
		DESCRIPTION	"Dot1q vlan static rowstatus."
		::= { iswVlanEntry 5 }
--
	iswVlanStackingTable	OBJECT-TYPE
		SYNTAX		SEQUENCE OF IswVlanStackingEntry
		MAX-ACCESS	not-accessible 
		STATUS		current
		DESCRIPTION	"VLAN Stacking table. Max entry size: port number."
		::= { iswVlan 3 }
		
	iswVlanStackingEntry	OBJECT-TYPE
		SYNTAX		IswVlanStackingEntry
		MAX-ACCESS	not-accessible
		STATUS		current
		DESCRIPTION	"Vlan Stacking entry."
		INDEX		{ iswVlanStackingPortId }
		
		::= { iswVlanStackingTable 1 }  
	IswVlanStackingEntry ::= SEQUENCE{
		iswVlanStackingPortId		IswGbeIndex,
		iswVlanStackingQinQMode		Integer32
	}		
--1
	iswVlanStackingPortId	OBJECT-TYPE
		SYNTAX		IswGbeIndex
		MAX-ACCESS	not-accessible
		STATUS		current
		DESCRIPTION	"Port ID."
		::= { iswVlanStackingEntry 1 }
--2
	iswVlanStackingQinQMode	OBJECT-TYPE
		SYNTAX		Integer32 { disable (0), enable (1) }
		MAX-ACCESS	read-write
		STATUS		current
		DESCRIPTION	"Enable/Disable VLAN QinQ mode. Default valuse is disable."
		DEFVAL		{ 0 }          
		::= { iswVlanStackingEntry 2 }

	iswOuterVlanTagTpid	OBJECT-TYPE
		SYNTAX		Integer32 ( 1 .. 65535 )
		MAX-ACCESS	read-write
		STATUS		current
		DESCRIPTION	"The extern TPID for the outer VLAN Tag. 
					The range is 1 to 0xffff. The default value is 0x8100."
		DEFVAL		{ 33024 }
		::= { iswVlan 4 }
--
--
	iswProtocolBaseVlanTable	OBJECT-TYPE
		SYNTAX		SEQUENCE OF IswProtocolBaseVlanEntry
		MAX-ACCESS	not-accessible 
		STATUS		current
		DESCRIPTION	"Protocol-base VLAN table. Max entry size: 20."
		::= { iswVlan 5 }

	iswProtocolBaseVlanEntry	OBJECT-TYPE
		SYNTAX		IswProtocolBaseVlanEntry
		MAX-ACCESS	not-accessible
		STATUS		current
		DESCRIPTION	"Protocol-base VLAN entry."
		INDEX		{ iswProtocolVlanIndex }
		::= { iswProtocolBaseVlanTable 1 }  

	IswProtocolBaseVlanEntry ::= SEQUENCE{
		iswProtocolVlanIndex		Integer32,
		iswProtocolVlanPort			IswGbeIndex,
		iswProtocolVlanEthType		Integer32,
		iswProtocolVlanSVlanId		Integer32,
		iswProtocolVlanPrio			Integer32,
		iswProtocolVlanRowStatus	RowStatus
	}		
--1
	iswProtocolVlanIndex	OBJECT-TYPE
		SYNTAX		Integer32 ( 1 .. 20 )
		MAX-ACCESS	not-accessible
		STATUS		current
		DESCRIPTION	"Protocol-base VLAN index. Use iswNextProtocolVlanIndex to get next available index."
		::= { iswProtocolBaseVlanEntry 1 } 
--2
	iswProtocolVlanPort	OBJECT-TYPE
		SYNTAX		IswGbeIndex
		MAX-ACCESS	read-create
		STATUS		current
		DESCRIPTION	"Protocol-base VLAN config port number."            
		::= { iswProtocolBaseVlanEntry 2 }
--3
	iswProtocolVlanEthType	OBJECT-TYPE
		SYNTAX		Integer32 ( 0 .. 65535 )
		MAX-ACCESS	read-create
		STATUS		current
		DESCRIPTION	"The Ether Type that the system will assign the VID to.
					0..0xFFFF
					0x8863:PPPoE Discovery Stage
					0x8864:PPPoE Session Stage
					0x0800:Internet Protocol
					0x0806:Address Resolution Protocol
					Other ... etc."
		::= { iswProtocolBaseVlanEntry 3 }
--4
	iswProtocolVlanSVlanId	OBJECT-TYPE
		SYNTAX		Integer32 ( 1 .. 4094 )
		MAX-ACCESS	read-create
		STATUS		current
		DESCRIPTION	"Protocol-base Service VLAN ID."
		::= { iswProtocolBaseVlanEntry 4 }
--5
	iswProtocolVlanPrio	OBJECT-TYPE
		SYNTAX		Integer32 ( 0 .. 8 )
		MAX-ACCESS	read-create
		STATUS		current
		DESCRIPTION	"Protocol-base CoS of Service VLAN. Range: 0 .. 7, 8 is reserve ingress priority."        
		::= { iswProtocolBaseVlanEntry 5 }
--6
	iswProtocolVlanRowStatus	OBJECT-TYPE
		SYNTAX		RowStatus
		MAX-ACCESS	read-create
		STATUS		current
		DESCRIPTION	"Protocol-base VLAN table RowStatus."
		::= { iswProtocolBaseVlanEntry 6 }
--
	iswVlanTranslationTable		OBJECT-TYPE
		SYNTAX		SEQUENCE OF IswVlanTranslationEntry
		MAX-ACCESS	not-accessible 
		STATUS		current
		DESCRIPTION	"VLAN translation table. Max entry size: 20."
		::= { iswVlan 6 }

	iswVlanTranslationEntry	OBJECT-TYPE
		SYNTAX		IswVlanTranslationEntry
		MAX-ACCESS	not-accessible
		STATUS		current
		DESCRIPTION	"VLAN translation entry."
		INDEX		{ iswVlanTranslationIndex }
		::= { iswVlanTranslationTable 1 }  

	IswVlanTranslationEntry ::= SEQUENCE{
		iswVlanTranslationIndex			Integer32,
		iswVlanTranslationPort			IswGbeIndex,
		iswVlanTranslationCVlanId		Integer32,
		iswVlanTranslationCPriority		Integer32,
		iswVlanTranslationSVlanId		Integer32,
		iswVlanTranslationSPriority		Integer32,
		iswVlanTranslationVlanMode		Integer32,
		iswVlanTranslationRowStatus		RowStatus
	}
--1
	iswVlanTranslationIndex		OBJECT-TYPE
		SYNTAX		Integer32 ( 1 .. 20 )
		MAX-ACCESS	not-accessible
		STATUS		current
		DESCRIPTION	"VLAN translation index. Use iswNextVlanTranslationIndex to get next available index."
		::= { iswVlanTranslationEntry 1 }
--2
	iswVlanTranslationPort		OBJECT-TYPE
		SYNTAX		IswGbeIndex
		MAX-ACCESS	read-create
		STATUS		current
		DESCRIPTION	"VLAN translation port number."
		::= { iswVlanTranslationEntry 2 }
--3
	iswVlanTranslationCVlanId	OBJECT-TYPE
		SYNTAX		Integer32 ( 1 .. 4094 )
		MAX-ACCESS	read-create
		STATUS		current
		DESCRIPTION	"Customer VLAN ID."
		::= { iswVlanTranslationEntry 3 }
--4
	iswVlanTranslationCPriority	OBJECT-TYPE
		SYNTAX		Integer32 ( 0 .. 8 )
		MAX-ACCESS	read-create
		STATUS		current
		DESCRIPTION	"CoS of Customer VLAN. Range: 0 .. 7, 8 is reserve."
		::= { iswVlanTranslationEntry 4 }
--5
	iswVlanTranslationSVlanId	OBJECT-TYPE
		SYNTAX		Integer32 ( 1 .. 4094 )
		MAX-ACCESS	read-create
		STATUS		current
		DESCRIPTION	"Service VLAN ID."
		::= { iswVlanTranslationEntry 5 }
--6
	iswVlanTranslationSPriority	OBJECT-TYPE
		SYNTAX		Integer32 ( 0 .. 8 )
		MAX-ACCESS	read-create
		STATUS		current
		DESCRIPTION	"CoS of Service VLAN. Range: 0 .. 7, 8 is reserve ingress priority."
		::= { iswVlanTranslationEntry 6 }
--7
	iswVlanTranslationVlanMode	OBJECT-TYPE
		SYNTAX		Integer32 { replace-Nto1 (0) }
		MAX-ACCESS	read-create
		STATUS		current
		DESCRIPTION	"VLAN translation mode. replace-Nto1(0): replace N to 1"
		::= { iswVlanTranslationEntry 7 }
--8
	iswVlanTranslationRowStatus	OBJECT-TYPE
		SYNTAX		RowStatus
		MAX-ACCESS	read-create
		STATUS		current
		DESCRIPTION	"VLAN translation table RowStatus."
		::= { iswVlanTranslationEntry 8 }
--
--		
	iswFdbStaticTable	OBJECT-TYPE
		SYNTAX		SEQUENCE OF IswFdbStaticEntry
		MAX-ACCESS	not-accessible
		STATUS		current
		DESCRIPTION	"FDB static table. Max entry size: 512."
		::= { iswFdb 1 }
			
	iswFdbStaticEntry	OBJECT-TYPE
		SYNTAX		IswFdbStaticEntry
		MAX-ACCESS	not-accessible
		STATUS		current
		DESCRIPTION	"FDB static entry."
		INDEX		{ iswFdbStaticIndex }
		::= { iswFdbStaticTable 1 }
		
	IswFdbStaticEntry ::= SEQUENCE{
		iswFdbStaticIndex		Integer32,
		iswFdbStaticMac			PhysAddress,
		iswFdbStaticVlanID		Integer32,
		iswFdbStaticPort		IswGbeIndex,
		iswFdbStaticRowStatus	RowStatus
	}
--1
	iswFdbStaticIndex	OBJECT-TYPE
		SYNTAX		Integer32 ( 1 .. 512 )
		MAX-ACCESS	not-accessible
		STATUS		current
		DESCRIPTION	"Dot1q FDB static entry index. Use iswNextFdbStaticIndex to get next available index."
		::= { iswFdbStaticEntry 1 }
--2
	iswFdbStaticMac	        OBJECT-TYPE
		SYNTAX		PhysAddress
		MAX-ACCESS	read-create
		STATUS		current
		DESCRIPTION	"Dot1q FDB static mac."
		::= { iswFdbStaticEntry 2 }
--3 
	iswFdbStaticVlanID	OBJECT-TYPE
		SYNTAX		Integer32 ( 1 .. 4094 )
		MAX-ACCESS	read-create
		STATUS		current
		DESCRIPTION	"Dot1q FDB static vlan ID."
		::= { iswFdbStaticEntry 3 }
--4 
	iswFdbStaticPort	OBJECT-TYPE
		SYNTAX		IswGbeIndex
		MAX-ACCESS	read-create
		STATUS		current
		DESCRIPTION	"Dot1q FDB static port."
		::= { iswFdbStaticEntry 4 }
--5	
	iswFdbStaticRowStatus	OBJECT-TYPE
		SYNTAX		RowStatus
		MAX-ACCESS	read-create
		STATUS		current
		DESCRIPTION	"Dot1q FDB static rowstatus."
		::= { iswFdbStaticEntry 5 }

-- FdbStaticDeleteControl 
	iswFdbStaticDeleteCtrl	OBJECT IDENTIFIER
		::= { iswFdb 2 }	

	iswFdbStaticDeleteIndex	OBJECT-TYPE
		SYNTAX		Integer32 ( 1 .. 512 )
		MAX-ACCESS	read-write
		STATUS		current
		DESCRIPTION	"Dot1q FDB static entry index"
		::= { iswFdbStaticDeleteCtrl 1 }
                         
	iswFdbStaticDeleteVlan	OBJECT-TYPE
		SYNTAX		Integer32 ( 1 .. 4094 )
		MAX-ACCESS	read-write
		STATUS		current
		DESCRIPTION	"VLAN ID"
		::= { iswFdbStaticDeleteCtrl 2 }

	iswFdbStaticDeletePort	OBJECT-TYPE
		SYNTAX		IswGbeIndex 
		MAX-ACCESS	read-write
		STATUS		current
		DESCRIPTION	"Port Index"
		::= { iswFdbStaticDeleteCtrl 3 }

	iswFdbStaticDeleteType	OBJECT-TYPE
		SYNTAX		Integer32 { deleteByIndex(0), deleteByVlan(1), deleteByPort(2), deleteAll(3) }
		MAX-ACCESS	read-write
		STATUS		current
		DESCRIPTION	"Dot1q FDB static delete type."
		::= { iswFdbStaticDeleteCtrl 4 }

--
	iswTpFdbTable		OBJECT-TYPE
		SYNTAX		SEQUENCE OF IswTpFdbEntry
		MAX-ACCESS	not-accessible
		STATUS		current
		DESCRIPTION	"forwarding table. Max entry size: 8192."
		::= { iswFdb 3 }
			
	iswTpFdbEntry	OBJECT-TYPE
		SYNTAX		IswTpFdbEntry
		MAX-ACCESS	not-accessible
		STATUS		current
		DESCRIPTION	"forwarding table entry."
		INDEX		{ iswDot1qTpFdbIndex }
		::= { iswTpFdbTable 1 }
		
	IswTpFdbEntry ::= SEQUENCE{
		iswDot1qTpFdbIndex			Integer32,
		iswDot1qTpFdbAddress		PhysAddress,
		iswDot1qTpFdbPort			IswGbeAndTrunkPortsIndex,
		iswDot1qTpFdbStatus			Integer32,
		iswDot1qTpFdbVlan			Integer32,
		--iswDot1qTpFdbAging		Integer32,
		--iswDot1TpFdbSessionKey	Integer32,
		--iswDot1TpFdbActionType	Integer32,
		--iswDot1TpFdbRowStatus		RowStatus
	}
--1 	
	iswDot1qTpFdbIndex	OBJECT-TYPE
		SYNTAX		Integer32 ( 1 .. 16384 )
		MAX-ACCESS	not-accessible
		STATUS		current
		DESCRIPTION	"forwarding table entry index."
		::= { iswTpFdbEntry 1 }  
--2 	
	iswDot1qTpFdbAddress	OBJECT-TYPE
		SYNTAX		PhysAddress
		MAX-ACCESS	read-only
		STATUS		current
		DESCRIPTION	"forwarding address."
		::= { iswTpFdbEntry 2 }  
--3 	
	iswDot1qTpFdbPort	OBJECT-TYPE
		SYNTAX		IswGbeAndTrunkPortsIndex
		MAX-ACCESS	read-only
		STATUS		current
		DESCRIPTION	"forwarding port.
					GEPort-1 ~ GEPort-28, and all Trunk ports"
		::= { iswTpFdbEntry 3 }
--4
	iswDot1qTpFdbStatus	OBJECT-TYPE
		SYNTAX		Integer32 { dynamic(0), static(1) }
		MAX-ACCESS	read-only
		STATUS		current
		DESCRIPTION	"forwarding entry status (type)."
		::= { iswTpFdbEntry 4 }  
--5
	iswDot1qTpFdbVlan	OBJECT-TYPE
		SYNTAX		Integer32 ( 1 .. 4094 )
		MAX-ACCESS	read-only
		STATUS		current
		DESCRIPTION	"forwarding vlan."
		::= { iswTpFdbEntry 5 }  
--6
	--iswDot1qTpFdbAging	OBJECT-TYPE
	--	SYNTAX		Integer32 ( 0 .. 1000000 )
	--	MAX-ACCESS	read-only
	--	STATUS		current
	--	DESCRIPTION	"forwarding entry aging."
	--	::= { iswTpFdbEntry 6 }
--7
	--iswDot1TpFdbSessionKey	OBJECT-TYPE
	--	SYNTAX		Integer32
	--	MAX-ACCESS	not-accessible
	--	STATUS		current
	--	DESCRIPTION	"Dot1q tp FDB sessionKey."
	--	::= { iswTpFdbEntry 7 }
--8
	--iswDot1TpFdbActionType	OBJECT-TYPE
	--	SYNTAX		Integer32 { one (0), valn (1), port(2), all (3) }
	--	MAX-ACCESS	write-only
	--	STATUS		current
	--	DESCRIPTION	"Dot1q tp FDB action type."
	--	::= { iswTpFdbEntry 7 }
--9
	--iswDot1TpFdbRowStatus	OBJECT-TYPE
	--	SYNTAX		RowStatus
	--	MAX-ACCESS	read-create
	--	STATUS		current
	--	DESCRIPTION	"Dot1q tp FDB rowstatus."
	--	::= { iswTpFdbEntry 6 }
		
-- FdbDeleteControl 
	iswFdbDeleteCtrl	OBJECT IDENTIFIER
		::= { iswFdb 4 }

	--iswFdbDeleteIndex	OBJECT-TYPE
	--	SYNTAX		Integer32 ( 1 .. 512 )
	--	MAX-ACCESS	read-write
	--	STATUS		current
	--	DESCRIPTION	"forwarding entry index"
	--	::= { iswFdbDeleteCtrl 1 }
                         
	iswFdbDeleteVlan	OBJECT-TYPE
		SYNTAX		Integer32 ( 1 .. 4094 ) 
		MAX-ACCESS	read-write
		STATUS		current
		DESCRIPTION	"VLAN ID, to delete forwarding entry by VLAN."
		::= { iswFdbDeleteCtrl 1 }

	iswFdbDeletePort	OBJECT-TYPE
		SYNTAX		IswGbeAndTrunkPortsIndex
		MAX-ACCESS	read-write
		STATUS		current
		DESCRIPTION	"Port Index, to delete forwarding entry by Port.
					GEPort-1 ~ GEPort-28, and all Trunk ports"
		::= { iswFdbDeleteCtrl 2 }

	iswFdbDeleteType	OBJECT-TYPE
		SYNTAX		Integer32 { deleteByVlan(1), deleteByPort(2), deleteAll(3) }
		MAX-ACCESS	read-write
		STATUS		current
		DESCRIPTION	"delete type of forwarding table."
		::= { iswFdbDeleteCtrl 3 } 
--
	iswAgingTime	OBJECT-TYPE
		SYNTAX		Integer32 ( 10 .. 400 )
		UNITS		"second"
		MAX-ACCESS	read-write
		STATUS		current
		DESCRIPTION	"Aging time. Default value is 300."     
		DEFVAL		{ 300 }
		::= { iswFdb 5 }
--
	iswPortUnknownUcCtrlTable	OBJECT-TYPE
		SYNTAX		SEQUENCE OF IswPortUnknownUcCtrlEntry
		MAX-ACCESS	not-accessible
		STATUS		current
		DESCRIPTION	"Port unknown unicast control table. Max entry size: port number."
		::= { iswStormCtrl 1 }
		
	iswPortUnknownUcCtrlEntry	OBJECT-TYPE
		SYNTAX		IswPortUnknownUcCtrlEntry
		MAX-ACCESS	not-accessible
		STATUS		current
		DESCRIPTION	"Port Unknown unicast control entry."
		INDEX		{ iswPortUnknownUcPortID }
		::= { iswPortUnknownUcCtrlTable 1 }
		
	IswPortUnknownUcCtrlEntry ::= SEQUENCE{
		iswPortUnknownUcPortID		IswGbeIndex,
		iswPortUnknownUcRate		Integer32,
		iswPortUnknownUcMode		Integer32
	}
--1
	iswPortUnknownUcPortID	OBJECT-TYPE
		SYNTAX		IswGbeIndex
		MAX-ACCESS	not-accessible
		STATUS		current
		DESCRIPTION	"Port unknown unicast port ID."
		::= { iswPortUnknownUcCtrlEntry 1 }
--2
	iswPortUnknownUcRate	OBJECT-TYPE
		SYNTAX		Integer32 ( 1 .. 1000000 )
		UNITS		"kbps"
		MAX-ACCESS	read-write
		STATUS		current
		DESCRIPTION	"Port unknown unicast port ID. Default value is 1000000 Kbps."  
		DEFVAL		{ 1000000 }
		::= { iswPortUnknownUcCtrlEntry 2 }
--3
	iswPortUnknownUcMode	OBJECT-TYPE
		SYNTAX		Integer32 { forward (0), block (1), rateLimit (2) }
		MAX-ACCESS	read-write
		STATUS		current
		DESCRIPTION	"Port unknown unicast port ID."
		::= { iswPortUnknownUcCtrlEntry 3 }
--
	iswPortUnknownMcCtrlTable	OBJECT-TYPE
		SYNTAX		SEQUENCE OF IswPortUnknownMcCtrlEntry
		MAX-ACCESS	not-accessible
		STATUS		current
		DESCRIPTION	"Port Unknown multicast control table. Max entry size: port number."
		::= { iswStormCtrl 2 }
		
	iswPortUnknownMcCtrlEntry	OBJECT-TYPE
		SYNTAX		IswPortUnknownMcCtrlEntry
		MAX-ACCESS	not-accessible
		STATUS		current
		DESCRIPTION	"Port Unknown multicast control entry."
		INDEX		{ iswPortUnknownMcPortID }
		::= { iswPortUnknownMcCtrlTable 1 }
		
	IswPortUnknownMcCtrlEntry ::= SEQUENCE{
		iswPortUnknownMcPortID		IswGbeIndex,
		iswPortUnknownMcRate 		Integer32,
		iswPortUnknownMcMode 		Integer32
	} 
--1  
	iswPortUnknownMcPortID	OBJECT-TYPE
		SYNTAX		IswGbeIndex
		MAX-ACCESS	not-accessible
		STATUS		current
		DESCRIPTION	"Port index."
		::= { iswPortUnknownMcCtrlEntry 1 }
--2   
	iswPortUnknownMcRate	OBJECT-TYPE
		SYNTAX		Integer32 ( 1 .. 1000000 )
		UNITS		"kbps"
		MAX-ACCESS	read-write
		STATUS		current
		DESCRIPTION	"Port unknown multicast rate. Default value is 1000000 Kbps." 
		DEFVAL		{ 1000000 }
		::= { iswPortUnknownMcCtrlEntry 2 }
--3  
	iswPortUnknownMcMode	OBJECT-TYPE
		SYNTAX		Integer32 { forward (0), block (1), rateLimit (2) }
		MAX-ACCESS	read-write
		STATUS		current
		DESCRIPTION	"Port unknown multicast mode."
		::= { iswPortUnknownMcCtrlEntry 3 }
--
	iswPortBroadcastCtrlTable	OBJECT-TYPE
		SYNTAX		SEQUENCE OF IswPortBroadcastCtrlEntry
		MAX-ACCESS	not-accessible
		STATUS		current
		DESCRIPTION	"Port broadcast control table. Max entry size: port number."
		::= { iswStormCtrl 3 }
		
	iswPortBroadcastCtrlEntry	OBJECT-TYPE
		SYNTAX		IswPortBroadcastCtrlEntry
		MAX-ACCESS	not-accessible
		STATUS		current
		DESCRIPTION	"Port broadcast control entry."
		INDEX		{ iswPortBroadcastPortID }
		::= { iswPortBroadcastCtrlTable 1 }
		
	IswPortBroadcastCtrlEntry ::= SEQUENCE{
		iswPortBroadcastPortID			IswGbeIndex,
		iswPortBroadcastRate 			Integer32,
		iswPortBroadcastMode 			Integer32
	} 
--1    
	iswPortBroadcastPortID	OBJECT-TYPE
		SYNTAX		IswGbeIndex
		MAX-ACCESS	not-accessible
		STATUS		current
		DESCRIPTION	"Port broadcast port ID."
		::= { iswPortBroadcastCtrlEntry 1 }
--2     
	iswPortBroadcastRate	OBJECT-TYPE
		SYNTAX		Integer32 ( 1 .. 1000000 )
		UNITS		"kbps"
		MAX-ACCESS	read-write
		STATUS		current
		DESCRIPTION	"Port broadcast rate. Default value is 1000000."
		DEFVAL		{ 1000000 }
		::= { iswPortBroadcastCtrlEntry 2 }
--3     
	iswPortBroadcastMode	OBJECT-TYPE
		SYNTAX		Integer32 {  forward (0), block (1),  rateLimit (2)}
		MAX-ACCESS	read-write
		STATUS		current
		DESCRIPTION	"Port broadcast mode."
		::= { iswPortBroadcastCtrlEntry 3 }
--
	iswVlanUnknownUcCtrlTable	OBJECT-TYPE
		SYNTAX		SEQUENCE OF IswVlanUnknownUcCtrlEntry
		MAX-ACCESS	not-accessible
		STATUS		current
		DESCRIPTION	"Vlan unknown unicast control table. Max entry size: 2048."
		::= { iswStormCtrl 4 }    
			
	iswVlanUnknownUcCtrlEntry	OBJECT-TYPE
		SYNTAX		IswVlanUnknownUcCtrlEntry
		MAX-ACCESS	not-accessible
		STATUS		current
		DESCRIPTION	"Vlan unknown unicast control entry."
		INDEX		{ iswVlanUnknownUcVlanID }
		::= { iswVlanUnknownUcCtrlTable 1 }
		
	IswVlanUnknownUcCtrlEntry ::= SEQUENCE{
		iswVlanUnknownUcVlanID			Integer32,
		iswVlanUnknownUcMode			Integer32
	} 
--1    
	iswVlanUnknownUcVlanID	OBJECT-TYPE
		SYNTAX		Integer32 ( 1 .. 4094 )
		MAX-ACCESS	not-accessible
		STATUS		current
		DESCRIPTION	"Vlan unknown unicast vlan ID."
		::= { iswVlanUnknownUcCtrlEntry 1 }  
--2    
	iswVlanUnknownUcMode	OBJECT-TYPE
		SYNTAX		Integer32 { forward (0), block (1) }
		MAX-ACCESS	read-only
		STATUS		current
		DESCRIPTION	"Vlan unknown unicast mode. Only blocked VLAN will be shown."
		::= { iswVlanUnknownUcCtrlEntry 2 }
--
	iswVlanUnknownMcCtrlTable	OBJECT-TYPE
		SYNTAX		SEQUENCE OF IswVlanUnknownMcCtrlEntry
		MAX-ACCESS	not-accessible
		STATUS		current
		DESCRIPTION	"Vlan unknown multicast control table. Max entry size: 2048."
		::= { iswStormCtrl 5 }
		
	iswVlanUnknownMcCtrlEntry	OBJECT-TYPE
		SYNTAX		IswVlanUnknownMcCtrlEntry
		MAX-ACCESS	not-accessible
		STATUS		current
		DESCRIPTION	"Vlan unknown multicast control entry."
		INDEX		{ iswVlanUnknownMcVlanID }
		::= { iswVlanUnknownMcCtrlTable 1 }
		
	IswVlanUnknownMcCtrlEntry ::= SEQUENCE{
		iswVlanUnknownMcVlanID			Integer32,
		iswVlanUnknownMcMode			Integer32
	}
--1
	iswVlanUnknownMcVlanID	OBJECT-TYPE
		SYNTAX		Integer32 ( 1 .. 4094 )
		MAX-ACCESS	not-accessible
		STATUS		current
		DESCRIPTION	"Vlan unknown multicast vlan ID."
		::= { iswVlanUnknownMcCtrlEntry 1 }
--2
	iswVlanUnknownMcMode	OBJECT-TYPE
		SYNTAX		Integer32 { forward (0), block (1) }
		MAX-ACCESS	read-only
		STATUS		current
		DESCRIPTION	"Vlan unknown multicast mode. Only blocked VLAN will be shown."
		::= { iswVlanUnknownMcCtrlEntry 2 }
--
	iswVlanBroadcastCtrlTable	OBJECT-TYPE
		SYNTAX		SEQUENCE OF IswVlanBroadcastCtrlEntry
		MAX-ACCESS	not-accessible
		STATUS		current
		DESCRIPTION	"Vlan broadcast control table. Max entry size: 2048."
		::= { iswStormCtrl 6 }    
			
	iswVlanBroadcastCtrlEntry	OBJECT-TYPE
		SYNTAX		IswVlanBroadcastCtrlEntry
		MAX-ACCESS	not-accessible
		STATUS		current
		DESCRIPTION	"Vlan broadcast control entry."
		INDEX		{ iswVlanBroadcastVlanID }
		::= { iswVlanBroadcastCtrlTable 1 }
		
	IswVlanBroadcastCtrlEntry ::= SEQUENCE{
		iswVlanBroadcastVlanID			Integer32,
		iswVlanBroadcastMode			Integer32
	} 
--1    
	iswVlanBroadcastVlanID	OBJECT-TYPE
		SYNTAX		Integer32 ( 1 .. 4094 )
		MAX-ACCESS	not-accessible
		STATUS		current
		DESCRIPTION	"Vlan broadcast vlan ID."
		::= { iswVlanBroadcastCtrlEntry 1 }  
--2    
	iswVlanBroadcastMode	OBJECT-TYPE
		SYNTAX		Integer32 { forward (0), block (1) }
		MAX-ACCESS	read-only
		STATUS		current
		DESCRIPTION	"Vlan broadcast mode. Only blocked VLAN will be shown."
		::= { iswVlanBroadcastCtrlEntry 2 } 
--
	iswVlanUnknownUcCtrlSet	OBJECT IDENTIFIER
		::= { iswStormCtrl 7 }

	iswVlanUnknownUcVlanIndex	OBJECT-TYPE
		SYNTAX		Integer32 ( 1 .. 4094 )
		MAX-ACCESS	read-write
		STATUS		current
		DESCRIPTION	"Vlan unknown unicast vlan ID."
		::= { iswVlanUnknownUcCtrlSet 1 }
                         
	iswVlanUnknownUcModeSet	OBJECT-TYPE
		SYNTAX		Integer32 { forward (0), block (1) }
		MAX-ACCESS	read-write
		STATUS		current
		DESCRIPTION	"Vlan unknown unicast mode."
		::= { iswVlanUnknownUcCtrlSet 2 }
----
	iswVlanUnknownMcCtrlSet	OBJECT IDENTIFIER
		::= { iswStormCtrl 8 }

	iswVlanUnknownMcVlanIndex	OBJECT-TYPE
		SYNTAX		Integer32 ( 1 .. 4094 )
		MAX-ACCESS	read-write
		STATUS		current
		DESCRIPTION	"Vlan unknown multicast vlan ID."
		::= { iswVlanUnknownMcCtrlSet 1 }
                         
	iswVlanUnknownMcModeSet	OBJECT-TYPE
		SYNTAX		Integer32 { forward (0), block (1) }
		MAX-ACCESS	read-write
		STATUS		current
		DESCRIPTION	"Vlan unknown multicast mode."
		::= { iswVlanUnknownMcCtrlSet 2 }
----
	iswVlanBroadcastCtrlSet	OBJECT IDENTIFIER
		::= { iswStormCtrl 9 }

	iswVlanBroadcastVlanIndex	OBJECT-TYPE
		SYNTAX		Integer32 ( 1 .. 4094 )
		MAX-ACCESS	read-write
		STATUS		current
		DESCRIPTION	"Vlan broadcast vlan ID."
		::= { iswVlanBroadcastCtrlSet 1 }  
                         
	iswVlanBroadcastModeSet	OBJECT-TYPE
		SYNTAX		Integer32 { forward (0), block (1) }
		MAX-ACCESS	read-write
		STATUS		current
		DESCRIPTION	"Vlan broadcast mode."
		::= { iswVlanBroadcastCtrlSet 2 }
--1
	iswStpProtocol	OBJECT-TYPE
		SYNTAX		Integer32 { stp (0), rstp (1), mstp (2) }
		MAX-ACCESS	read-write
		STATUS		current
		DESCRIPTION	"STP protocol specification. Default value is stp (0)."
		DEFVAL		{ 0 }
		::= { iswStp 1 }
--2 
	iswStpPriority	OBJECT-TYPE
		SYNTAX		Integer32 ( 0 | 4096 | 8192 | 12288 | 16384 | 20480 | 24576 | 28672 | 
								32768 | 36864 | 40960 | 45056 | 49152 | 53248 | 57344 | 61440 )
		MAX-ACCESS	read-write
		STATUS		current
		DESCRIPTION	"STP priority. Default is 32768(0x8000). Step is 4096."
		DEFVAL		{ 32768 }
		::= { iswStp 2 }
--3
	iswStpTimeSinceTopologyChange	OBJECT-TYPE
		SYNTAX		Gauge32  
		UNITS		"second"
		MAX-ACCESS	read-only
		STATUS		current
		DESCRIPTION	"STP time since topology change."
		::= { iswStp 3 } 
--4 
	iswStpTopChanges	OBJECT-TYPE
		SYNTAX		Gauge32
		MAX-ACCESS	read-only
		STATUS		current
		DESCRIPTION	"STP top changes."
		::= { iswStp 4 } 
--5 
	iswStpDesignatedRoot	OBJECT-TYPE
		SYNTAX		OCTET STRING ( SIZE (8) )
		MAX-ACCESS	read-only
		STATUS		current
		DESCRIPTION	"STP designated root."
		::= { iswStp 5 } 
--6
	iswStpBridgeID	OBJECT-TYPE
		SYNTAX		OCTET STRING ( SIZE (8) )
		MAX-ACCESS	read-only
		STATUS		current
		DESCRIPTION	"STP bridge port ID."
		::= { iswStp 6 } 
--7   
	iswStpRootCost	OBJECT-TYPE
		SYNTAX		Integer32
		MAX-ACCESS	read-only
		STATUS		current
		DESCRIPTION	"STP root cost."
		::= { iswStp 7 } 
--8
	iswStpRootPort	OBJECT-TYPE
		SYNTAX		Integer32
		MAX-ACCESS	read-only
		STATUS		current
		DESCRIPTION	"STP root port. 0 means NA(no root port)."
		::= { iswStp 8 } 
--9   
	iswStpMaxAge	OBJECT-TYPE
		SYNTAX		Integer32
		MAX-ACCESS	read-only
		STATUS		current
		DESCRIPTION	"STP max age."
		::= { iswStp 9 } 
--10  
	iswStpHellowTime	OBJECT-TYPE
		SYNTAX		Integer32
		UNITS		"second"
		MAX-ACCESS	read-only
		STATUS		current
		DESCRIPTION	"STP hellow time."
		::= { iswStp 10 } 
--11    
	iswStpHoldTime	OBJECT-TYPE
		SYNTAX		Integer32   
		UNITS		"second"
		MAX-ACCESS	read-only
		STATUS		current
		DESCRIPTION	"STP hold time."
		::= { iswStp 11 } 
--12
	iswStpForwardDelay	OBJECT-TYPE
		SYNTAX		Integer32
		UNITS		"second"
		MAX-ACCESS	read-only
		STATUS		current
		DESCRIPTION	"STP forward delay."
		::= { iswStp 12 } 
--13    
	iswStpBridgeMaxAge	OBJECT-TYPE
		SYNTAX		Integer32 ( 6 .. 40 ) 
		UNITS		"second"
		MAX-ACCESS	read-write
		STATUS		current
		DESCRIPTION	"STP bridge max age. Default value is 20.
					The iswStpBridgeMaxAge, iswStpBridgeHellowTime and iswStpBridgeForwardDelay times are constrained as follows:
					2 x (iswStpBridgeForwardDelay - 1) >= iswStpBridgeMaxAge >= 2 x (iswStpBridgeHellowTime + 1)"
		DEFVAL		{ 20 }
		::= { iswStp 13 } 
--14 
	iswStpBridgeHellowTime	OBJECT-TYPE
		SYNTAX		Integer32 ( 1 .. 10 )
		UNITS		"second"
		MAX-ACCESS	read-write
		STATUS		current
		DESCRIPTION	"STP bridge hellow time. Default value is 2.
					The iswStpBridgeMaxAge, iswStpBridgeHellowTime and iswStpBridgeForwardDelay times are constrained as follows:
					2 x (iswStpBridgeForwardDelay - 1) >= iswStpBridgeMaxAge >= 2 x (iswStpBridgeHellowTime + 1)"    
		DEFVAL		{ 2 }
		::= { iswStp 14 } 
--15  
	iswStpBridgeForwardDelay	OBJECT-TYPE
		SYNTAX		Integer32 ( 4 .. 30 )
		UNITS		"second"
		MAX-ACCESS	read-write
		STATUS		current
		DESCRIPTION	"STP bridge forward delay. Default value is 15.
					The iswStpBridgeMaxAge, iswStpBridgeHellowTime and iswStpBridgeForwardDelay times are constrained as follows:
					2 x (iswStpBridgeForwardDelay - 1) >= iswStpBridgeMaxAge >= 2 x (iswStpBridgeHellowTime + 1)"
		DEFVAL		{ 15 }
		::= { iswStp 15 } 
--16    
	iswStpBridgeModeSet	OBJECT-TYPE
		SYNTAX		Integer32 { disable (0), enable (1) }
		MAX-ACCESS	read-write
		STATUS		current
		DESCRIPTION	"STP bridge mode set. Default value is disable (0).
					If any ring group is enabled (iswRingProtectRingMode is enable), set this field to enable will be rejected."
		DEFVAL		{ 0 }
		::= { iswStp 16 } 
--17    
	iswStpBpduFilter	OBJECT-TYPE
		SYNTAX		Integer32 { deny (1), flooding (2) }
		MAX-ACCESS	read-write
		STATUS		current
		DESCRIPTION	"STP bpdu filter. Default value is deny (1)."  
		DEFVAL		{ 1 }
		::= { iswStp 17 } 
--18    
	--iswStpPathCostMethod	OBJECT-TYPE
	--	SYNTAX		Integer32 { long (1), short (2) }
	--	MAX-ACCESS	read-write
	--	STATUS		current
	--	DESCRIPTION	"STP path cost method . Default value is long (1)."
	--	DEFVAL		{ 1 }
	--	::= { iswStp 18 }
--18
	iswStpRegionName	OBJECT-TYPE
		SYNTAX		OCTET STRING ( SIZE ( 0 .. 32 ) )
		MAX-ACCESS	read-write
		STATUS		current
		DESCRIPTION	"STP Region Name. Default value is emtpy. Max size is 32 chars, preferably in human-readable form."  
		::= { iswStp 18 } 
--19
	iswStpMSTRevLevel	OBJECT-TYPE
		SYNTAX		Integer32 ( 0 .. 65535 )
		MAX-ACCESS	read-write
		STATUS		current
		DESCRIPTION	"MST Revision Level. Default value is 0."  
		DEFVAL		{ 0 }
		::= { iswStp 19 } 
--
	iswStpPortTable		OBJECT-TYPE
		SYNTAX		SEQUENCE OF IswStpPortEntry
		MAX-ACCESS	not-accessible
		STATUS		current
		DESCRIPTION	"STP port table. Max entry size: port number."
		::= { iswStpGrp 2 }
		
	iswStpPortEntry	OBJECT-TYPE
		SYNTAX		IswStpPortEntry
		MAX-ACCESS	not-accessible
		STATUS		current
		DESCRIPTION	"STP port entry."
		INDEX		{ iswStpPortIndex }
		::= { iswStpPortTable 1 }
		
	IswStpPortEntry ::= SEQUENCE{
		iswStpPortIndex					IswGbeIndex,
		iswStpPortPriority				Integer32,
		iswStpPortState					Integer32,
		iswStpPortEnable				Integer32,
		iswStpPortPathCost				Integer32,
		iswStpPortEdgeType				Integer32,
		iswStpPortDesignatedRoot		OCTET STRING,
		iswStpPortDesignatedCost		Gauge32,
		iswStpPortDesignatedBridge		OCTET STRING,
		iswStpPortDesignatedPort		Integer32,
		iswStpPortForwardTransitions	Gauge32
		--iswStpPortP2PType				Integer32
	}
--1
	iswStpPortIndex	OBJECT-TYPE
		SYNTAX		IswGbeIndex
		MAX-ACCESS	not-accessible
		STATUS		current
		DESCRIPTION	"STP port index."
		::= { iswStpPortEntry 1 }
--2
	iswStpPortPriority	OBJECT-TYPE
		SYNTAX		Integer32 ( 0 | 16 | 32 | 48 | 64 | 80 | 96 | 112 | 128 | 144 | 160 |
								176 | 192 | 208 | 224 | 240 )
		MAX-ACCESS	read-write
		STATUS		current
		DESCRIPTION	"STP port priority. Default is 0x80(128). Step is 16. 0x0, 0x10, 0x20 ... 0xF0."
		DEFVAL		{ 128 }
		::= { iswStpPortEntry 2 }
--3
	iswStpPortState 	OBJECT-TYPE
		SYNTAX		Integer32 { disable (1), blocking (2), listening (3), learning (4), forwarding (5), broken (6) }
		MAX-ACCESS	read-only
		STATUS		current
		DESCRIPTION	"STP port state."
		::= { iswStpPortEntry 3 }  
--4
	iswStpPortEnable 	OBJECT-TYPE
		SYNTAX		Integer32 { disable (0), enable (1) }
		MAX-ACCESS	read-write
		STATUS		current
		DESCRIPTION	"STP port enable. Default value is enable (1)." 
		DEFVAL		{ 1 }
		::= { iswStpPortEntry 4 }  
--5	
	iswStpPortPathCost 	OBJECT-TYPE
		SYNTAX		Integer32 ( 1 .. 200000000 )
		MAX-ACCESS	read-write
		STATUS		current
		DESCRIPTION	"STP port path cost. Default value is 20000." 
		DEFVAL		{ 20000 }
		::= { iswStpPortEntry 5 }
--6
	iswStpPortEdgeType 	OBJECT-TYPE
		SYNTAX		Integer32 { disable (0), enable (1) }
		MAX-ACCESS	read-write
		STATUS		current
		DESCRIPTION	"STP port edge type. Default value is disable (0)."
		DEFVAL		{ 0 }
		::= { iswStpPortEntry 6 }
--7	
	iswStpPortDesignatedRoot	OBJECT-TYPE
		SYNTAX		OCTET STRING ( SIZE (8) )
		MAX-ACCESS	read-only
		STATUS		current
		DESCRIPTION	"STP port designated root."
		::= { iswStpPortEntry 7 }
--8
	iswStpPortDesignatedCost	OBJECT-TYPE
		SYNTAX		Gauge32
		MAX-ACCESS	read-only
		STATUS		current
		DESCRIPTION	"STP port designated cost."
		::= { iswStpPortEntry 8 }
--9
	iswStpPortDesignatedBridge	OBJECT-TYPE
		SYNTAX		OCTET STRING ( SIZE (8) )
		MAX-ACCESS	read-only
		STATUS		current
		DESCRIPTION	"STP port designated bridge."
		::= { iswStpPortEntry 9 }
--10
	iswStpPortDesignatedPort	OBJECT-TYPE
		SYNTAX		Integer32
		MAX-ACCESS	read-only
		STATUS		current
		DESCRIPTION	"STP port designated port."
		::= { iswStpPortEntry 10 }
--11
	iswStpPortForwardTransitions	OBJECT-TYPE
		SYNTAX		Gauge32
		MAX-ACCESS	read-only
		STATUS		current
		DESCRIPTION	"STP port forward transitions."
		::= { iswStpPortEntry 11 } 
--12
	--iswStpPortP2PType	OBJECT-TYPE
	--	SYNTAX		Integer32 { p2p (0), shared (1) }
	--	MAX-ACCESS	read-write
	--	STATUS		current
	--	DESCRIPTION	"STP port P2P type. Default value is p2p (0)."
	--	DEFVAL		{ 0 }
	--	::= { iswStpPortEntry 12 }
--
	iswMstpInstanceTable	OBJECT-TYPE
		SYNTAX		SEQUENCE OF IswMstpInstanceEntry
		MAX-ACCESS	not-accessible
		STATUS		current
		DESCRIPTION	"MSTP instance table. Max entry size: 10."
		::= { iswStpGrp 3 }
		
	iswMstpInstanceEntry	OBJECT-TYPE
		SYNTAX		IswMstpInstanceEntry
		MAX-ACCESS	not-accessible
		STATUS		current
		DESCRIPTION	"MSTP instance entry."
		INDEX		{ iswMstpInstIndex }
		::= { iswMstpInstanceTable 1 }
		
	IswMstpInstanceEntry ::= SEQUENCE{
		iswMstpInstIndex			Integer32,
		iswMstpInstVlanBitMap		OCTET STRING,  
		iswMstpInstName				OCTET STRING,  
		iswMstpInstPriority			Integer32,     
		iswMstpInstBridgeId			OCTET STRING,  
		iswMstpInstDesignatedRoot	OCTET STRING,  
		iswMstpInstRootPathCost		Integer32,   
		iswMstpInstRootPort			Integer32,   
		iswMstpInstRowStatus		RowStatus   
	}

	iswMstpInstIndex	OBJECT-TYPE
		SYNTAX		Integer32 (1..10)
		MAX-ACCESS	not-accessible
		STATUS		current
		DESCRIPTION	"MSTP instance index. Can use iswNextMstpInstanceIndex to query next available index."
		::= { iswMstpInstanceEntry 1 }
		
	iswMstpInstVlanBitMap	OBJECT-TYPE
		SYNTAX		OCTET STRING ( SIZE (512) )
		MAX-ACCESS	read-only
		STATUS		current
		DESCRIPTION	"MSTP instance Vlan bitmap. Default all bits are 0.
					Byte[0] for vlan 7 ~ vlan 0, but vlan 0 not support.
					Byte[1] for vlan 15 ~ vlan 8.
					..
					..
					..
					Byte[511] for vlan 4095 ~ vlan 4088, but vlan 4095 not support.
					vlan range :0..4094
					Default all bits are 0.
					It is read-only object. Can use iswMstpInstVlanAction to add/delete vlan into/from this mstp instance.
					Please refer to the usage of iswMstpInstVlanAction.
					
					If vlan is not created, it can be add to MSTI first.
					If vlan id is add to one MSTI, it can not be add to another MSTI until this vlan id is deleted from first MSTI."
		::= { iswMstpInstanceEntry 2 }
		
	iswMstpInstName	OBJECT-TYPE
		SYNTAX		OCTET STRING ( SIZE (1..30) )
		MAX-ACCESS	read-create
		STATUS		current
		DESCRIPTION	"Name of MSTP instance. Can't be empty."
		::= { iswMstpInstanceEntry 3 }
		
	iswMstpInstPriority	OBJECT-TYPE
		SYNTAX		Integer32 ( 0 | 4096 | 8192 | 12288 | 16384 | 20480 | 24576 | 28672 | 32768 | 36864 | 40960 |
								45056 | 49152 | 53248 | 57344 | 61440 )
		MAX-ACCESS	read-create
		STATUS		current
		DESCRIPTION	"MSTP instance priority. Default is 32768 (0x8000). Step is 4096. 0x000, 0x1000, 0x2000, ... 0xF000."
		DEFVAL		{ 32768 }
		::= { iswMstpInstanceEntry 4 }

	iswMstpInstBridgeId		OBJECT-TYPE
		SYNTAX		OCTET STRING ( SIZE (8) )
		MAX-ACCESS	read-only
		STATUS		current
		DESCRIPTION	"MSTP instance bridge ID."
		::= { iswMstpInstanceEntry 5 }

	iswMstpInstDesignatedRoot	OBJECT-TYPE
		SYNTAX		OCTET STRING ( SIZE (8) )
		MAX-ACCESS	read-only
		STATUS		current
		DESCRIPTION	"MSTP instance designated root."
		::= { iswMstpInstanceEntry 6 }

	iswMstpInstRootPathCost	OBJECT-TYPE
		SYNTAX		Integer32
		MAX-ACCESS	read-only
		STATUS		current
		DESCRIPTION	"MSTP instance root cost."
		::= { iswMstpInstanceEntry 7 }

	iswMstpInstRootPort	OBJECT-TYPE
		SYNTAX		Integer32
		MAX-ACCESS	read-only
		STATUS		current
		DESCRIPTION	"MSTP instance root port. 0 means NA(no root port)."
		::= { iswMstpInstanceEntry 8 }

	iswMstpInstRowStatus	OBJECT-TYPE
		SYNTAX		RowStatus
		MAX-ACCESS	read-create
		STATUS		current
		DESCRIPTION	"MSTP instance RowStatus."
		::= { iswMstpInstanceEntry 9 }

	iswMstpInstancePortTable		OBJECT-TYPE
		SYNTAX		SEQUENCE OF IswMstpInstancePortEntry
		MAX-ACCESS	not-accessible
		STATUS		current
		DESCRIPTION	"MSTP instance port table. Max entry size: 280 (MSTP Instance number * Port number)."
		::= { iswStpGrp 4 }

	iswMstpInstancePortEntry	OBJECT-TYPE
		SYNTAX		IswMstpInstancePortEntry
		MAX-ACCESS	not-accessible
		STATUS		current
		DESCRIPTION	"MSTP instance port entry."
		INDEX		{ iswMstpInstPortMstiId,iswMstpInstPortId }
		::= { iswMstpInstancePortTable 1 }

	IswMstpInstancePortEntry ::= SEQUENCE{
		iswMstpInstPortMstiId			Integer32,
		iswMstpInstPortId				IswGbeIndex,
		iswMstpInstPortPriority			Integer32,
		iswMstpInstPortPathCost			Integer32,
		iswMstpInstPortState			Integer32,
		iswMstpInstPortRole				Integer32,
		iswMstpInstPortDesignatedRoot	OCTET STRING,
		iswMstpInstPortDesignatedCost	Unsigned32,
		iswMstpInstPortDesignatedBridge	OCTET STRING,
		iswMstpInstPortDesignatedPort	Integer32
	}

	iswMstpInstPortMstiId	OBJECT-TYPE
		SYNTAX		Integer32 (1..10)
		MAX-ACCESS	not-accessible
		STATUS		current
		DESCRIPTION	"MSTP instance index."
		::= { iswMstpInstancePortEntry 1 }

	iswMstpInstPortId	OBJECT-TYPE
		SYNTAX		IswGbeIndex
		MAX-ACCESS	not-accessible
		STATUS		current
		DESCRIPTION	"MSTP instance port index."
		::= { iswMstpInstancePortEntry 2 }

	iswMstpInstPortPriority	OBJECT-TYPE
		SYNTAX		Integer32 ( 0 | 16 | 32 | 48 | 64 | 80 | 96 | 112 | 128 | 144 | 160 |
								176 | 192 | 208 | 224 | 240 )
		MAX-ACCESS	read-write
		STATUS		current
		DESCRIPTION	"MSTP instance port priority. Default is 0x80(128). Step is 16. 0x0, 0x10, 0x20 ... 0xF0."
		DEFVAL		{ 128 }
		::= { iswMstpInstancePortEntry 3 }

	iswMstpInstPortPathCost 	OBJECT-TYPE
		SYNTAX		Integer32 ( 1 .. 200000000 )
		MAX-ACCESS	read-write
		STATUS		current
		DESCRIPTION	"MSTP instance port path cost. Default value is 20000."
		DEFVAL		{ 20000 }
		::= { iswMstpInstancePortEntry 4 }

	iswMstpInstPortState	OBJECT-TYPE
		SYNTAX		Integer32 { disable (1), blocking (2), listening (3), learning (4), forwarding (5), broken (6) }
		MAX-ACCESS	read-only
		STATUS		current
		DESCRIPTION	"MSTP instance port state."
		::= { iswMstpInstancePortEntry 5 }

	iswMstpInstPortRole	OBJECT-TYPE
		SYNTAX		Integer32 { disable (0), root (1), designated (2), alternate (3), backup (4), master (5), unknown (6) }
		MAX-ACCESS	read-only
		STATUS		current
		DESCRIPTION	"MSTP instance port role."
		::= { iswMstpInstancePortEntry 6 }

	iswMstpInstPortDesignatedRoot	OBJECT-TYPE
		SYNTAX		OCTET STRING ( SIZE (8) )
		MAX-ACCESS	read-only
		STATUS		current
		DESCRIPTION	"MSTP instance port designated root."
		::= { iswMstpInstancePortEntry 7 }

	iswMstpInstPortDesignatedCost	OBJECT-TYPE
		SYNTAX		Unsigned32
		MAX-ACCESS	read-only
		STATUS		current
		DESCRIPTION	"MSTP instance port designated cost."
		::= { iswMstpInstancePortEntry 8 }

	iswMstpInstPortDesignatedBridge	OBJECT-TYPE
		SYNTAX		OCTET STRING ( SIZE (8) )
		MAX-ACCESS	read-only
		STATUS		current
		DESCRIPTION	"MSTP instance port designated bridge."
		::= { iswMstpInstancePortEntry 9 }

	iswMstpInstPortDesignatedPort	OBJECT-TYPE
		SYNTAX		Integer32
		MAX-ACCESS	read-only
		STATUS		current
		DESCRIPTION	"MSTP instance port designated port."
		::= { iswMstpInstancePortEntry 10 }

	iswMstpInstVlanCtrl	OBJECT IDENTIFIER
		::= { iswStpGrp 5 }

	iswMstpInstVlanMSTIID	OBJECT-TYPE
		SYNTAX		Integer32 ( 1 .. 10 )
		MAX-ACCESS	read-write
		STATUS		current
		DESCRIPTION	"MSTI ID for add/delete vlan."
		::= { iswMstpInstVlanCtrl 1 }  
                         
	iswMstpInstVlanStartID	OBJECT-TYPE
		SYNTAX		Integer32 ( 1 .. 4094 )
		MAX-ACCESS	read-write
		STATUS		current
		DESCRIPTION	"Start VLAN ID for add/delete vlan into/from specific MSTI ID.
					After set iswMstpInstVlanStartID, both iswMstpInstVlanStartID and iswMstpInstVlanEndID will be changed to same value.
					In other words, if want to add/delete one vlan, just need to set iswMstpInstVlanStartID. 
					If want to add/delete multiple vlan, need to set iswMstpInstVlanStartID and then set iswMstpInstVlanEndID. 
					Finally, set the iswMstpInstVlanAction and vlan will be add/delete."
		::= { iswMstpInstVlanCtrl 2 }
                         
	iswMstpInstVlanEndID	OBJECT-TYPE
		SYNTAX		Integer32 ( 1 .. 4094 )
		MAX-ACCESS	read-write
		STATUS		current
		DESCRIPTION	"End VLAN ID for add/delete vlan into/from specific MSTI ID.
					Limitation: iswMstpInstVlanStartID <= iswMstpInstVlanEndID."
		::= { iswMstpInstVlanCtrl 3 }
                                             
	iswMstpInstVlanAction	OBJECT-TYPE
		SYNTAX		Integer32 { add(0), delete(1) }
		MAX-ACCESS	read-write
		STATUS		current
		DESCRIPTION	"Use iswMstpInstVlanMSTIID, iswMstpInstVlanStartID, iswMstpInstVlanEndID and iswMstpInstVlanAction
					to add/delete one or multiple vlan id into/from specific MSTI ID.
					If iswMstpInstVlanStartID equals to iswMstpInstVlanEndID, it means one vlan id will be add/delete.
					If iswMstpInstVlanStartID less than iswMstpInstVlanEndID, it means multiple vlan id (range:startid..endid) will be add/delete.
					
					After set iswMstpInstVlanAction, can get the value of iswMstpInstVlanBitMap to check if the vlan id is add/delete successfully.
					
					If vlan is not created, it can be add to MSTI first.
					If vlan id is add to one MSTI, it can not be add to another MSTI until this vlan id is deleted from first MSTI."
		::= { iswMstpInstVlanCtrl 4 }
		
	iswIgmpVlanIntfTable	OBJECT-TYPE
		SYNTAX		SEQUENCE OF IswIgmpVlanIntfEntry
		MAX-ACCESS	not-accessible
		STATUS		current
		DESCRIPTION	"IGMP vlan interface table. Max entry size: 64."
		::= { iswIgmp 1 }

	iswIgmpVlanIntfEntry	OBJECT-TYPE
		SYNTAX		IswIgmpVlanIntfEntry
		MAX-ACCESS	not-accessible
		STATUS		current
		DESCRIPTION	"IGMP vlan interface entry."
		INDEX		{ iswIgmpVlanIntfvlan }
		::= { iswIgmpVlanIntfTable 1 }

	IswIgmpVlanIntfEntry ::= SEQUENCE{
		iswIgmpVlanIntfvlan				Integer32,
		iswIgmpVlanIntfbport				IswIgmpPortIndex,
		iswIgmpVlanIntfversion				Integer32,
		iswIgmpVlanIntfaccessMode			Integer32,
		iswIgmpVlanIntfleaveMode			Integer32,
		iswIgmpVlanIntfrobustness			Integer32,
		iswIgmpVlanIntfqueryInterval			Integer32,
		iswIgmpVlanIntfmaxRespTime			Integer32,
		iswIgmpVlanIntfgroupMembershipTime		Integer32,
		iswIgmpVlanIntfLMQI				Integer32,
		iswIgmpVlanIntfLMQC				Integer32,
		iswIgmpVlanIntfRTRALTSend			Integer32,
		iswIgmpVlanIntfRTRALTCheck			Integer32,
		iswIgmpVlanIntfquerierSrcIpAddr			IpAddress,
		iswIgmpVlanIntfv2PresentTime			Unsigned32,
		iswIgmpVlanIntfRunVersion			Integer32,
		iswIgmpVlanIntfRunRobustness			Integer32,
		iswIgmpVlanIntfRunQueryInterval			Integer32,
		iswIgmpVlanIntfActquerierIpAddr			IpAddress,
		iswIgmpVlanIntfrowStatus			RowStatus
	}
--1   
	iswIgmpVlanIntfvlan	OBJECT-TYPE
		SYNTAX		Integer32 ( 1 .. 4094 )
		MAX-ACCESS	not-accessible
		STATUS		current
		DESCRIPTION	"IGMP vlan interface: vlan."
		::= { iswIgmpVlanIntfEntry 1 }
--2    
	iswIgmpVlanIntfbport	OBJECT-TYPE
		SYNTAX		IswIgmpPortIndex
		MAX-ACCESS	read-create
		STATUS		current
		DESCRIPTION	"IGMP vlan interface: bridge port. Default value is 255." 
		DEFVAL		{ 255 }
		::= { iswIgmpVlanIntfEntry 2 }  
--3    
	iswIgmpVlanIntfversion	OBJECT-TYPE
		SYNTAX		Integer32 { igmpV2(2), igmpV3(3), igmpV2V3Compatible(4) }
		MAX-ACCESS	read-create
		STATUS		current
		DESCRIPTION	"IGMP vlan interface: version. Default value is igmpV2(2)." 
		DEFVAL		{ 2 }
		::= { iswIgmpVlanIntfEntry 3 }  
--4   
	iswIgmpVlanIntfaccessMode	OBJECT-TYPE
		SYNTAX		Integer32 { snoopingMode (1),querierMode(2),proxyMode (3) }
		MAX-ACCESS	read-create
		STATUS		current
		DESCRIPTION	"IGMP vlan interface: access mode. Default value is snoopingMode(1)."
		DEFVAL		{ 1 }
		::= { iswIgmpVlanIntfEntry 4 }
--5
	iswIgmpVlanIntfleaveMode	OBJECT-TYPE
		SYNTAX		Integer32 { normalLeave (0), fastLeave (1) }
		MAX-ACCESS	read-create
		STATUS		current
		DESCRIPTION	"IGMP vlan interface: leave mode. Default value is normalLeave(0)."
		DEFVAL		{ 0 }
		::= { iswIgmpVlanIntfEntry 5 }  
--6    
	iswIgmpVlanIntfrobustness	OBJECT-TYPE
		SYNTAX		Integer32 ( 1 .. 3 )
		MAX-ACCESS	read-create
		STATUS		current
		DESCRIPTION	"IGMP vlan interface: robustness. Default value is 2."  
		DEFVAL		{ 2 }
		::= { iswIgmpVlanIntfEntry 6 }
--7    
	iswIgmpVlanIntfqueryInterval	OBJECT-TYPE
		SYNTAX		Integer32 ( 1 .. 1800 ) 
		UNITS		"second"
		MAX-ACCESS	read-create
		STATUS		current
		DESCRIPTION	"IGMP vlan interface: query interval. Default value is 125 seconds.
					Limitation: iswIgmpVlanIntfqueryInterval > iswIgmpVlanIntfmaxRespTime in the same unit :second
					"
		DEFVAL		{ 125 }
		::= { iswIgmpVlanIntfEntry 7 }
--8   
	iswIgmpVlanIntfmaxRespTime	OBJECT-TYPE
		SYNTAX		Integer32 ( 1 .. 255 )
		UNITS		"0.1 second"
		MAX-ACCESS	read-create
		STATUS		current
		DESCRIPTION	"IGMP vlan interface: max response time. Default value is 100. (unit: 0.1 seconds)
					If get or set value is 100, it means 10 seconds.
					iswIgmpVlanIntfqueryInterval > iswIgmpVlanIntfmaxRespTime in the same unit :second
					"
		DEFVAL		{ 100 }
		::= { iswIgmpVlanIntfEntry 8 }
--9    
	iswIgmpVlanIntfgroupMembershipTime	OBJECT-TYPE
		SYNTAX		Integer32
		UNITS		"0.1 second"
		MAX-ACCESS	read-only
		STATUS		current
		DESCRIPTION	"IGMP vlan interface: group membership time. (unit: 0.1 seconds)
					If get value is 1, it means 0.1 second. "
		::= { iswIgmpVlanIntfEntry 9 }
--10
	iswIgmpVlanIntfLMQI	OBJECT-TYPE
		SYNTAX		Integer32 ( 1 .. 255 )
		UNITS		"0.1 second"
		MAX-ACCESS	read-create
		STATUS		current
		DESCRIPTION	"IGMP vlan interface: last member query interval. Default value is 1. (unit: 0.1 seconds)
					If get value is 1, it means 0.1 second."
		DEFVAL		{ 1 }
		::= { iswIgmpVlanIntfEntry 10 }
--11   
	iswIgmpVlanIntfLMQC	OBJECT-TYPE
		SYNTAX		Integer32 ( 1 .. 3)
		MAX-ACCESS	read-create
		STATUS		current
		DESCRIPTION	"IGMP vlan interface: last member query count. Default value is 2." 
		DEFVAL		{ 2 }
		::= { iswIgmpVlanIntfEntry 11 }
--12
	iswIgmpVlanIntfRTRALTSend	OBJECT-TYPE
		SYNTAX		Integer32 { disable(0), enable(1) }
		MAX-ACCESS	read-create
		STATUS		current
		DESCRIPTION	"Enable/disable to carry router-alert option on IGMP packet."
		DEFVAL		{ 1 }
		::= { iswIgmpVlanIntfEntry 12 }
--13
	iswIgmpVlanIntfRTRALTCheck	OBJECT-TYPE
		SYNTAX		Integer32 { disable(0), enable(1) }
		MAX-ACCESS	read-create
		STATUS		current
		DESCRIPTION	"Enable/disable to check router-alert option of received IGMP packet."
		DEFVAL		{ 1 }
		::= { iswIgmpVlanIntfEntry 13 }

--14    
	iswIgmpVlanIntfquerierSrcIpAddr	OBJECT-TYPE
		SYNTAX		IpAddress 
		MAX-ACCESS	read-create
		STATUS		current
		DESCRIPTION	"IGMP vlan interface: querier source ip address.
					(0.0.0.0 ~ 223.255.255.255, default:0.0.0.0).
					"
		::= { iswIgmpVlanIntfEntry 14 }
--15
	iswIgmpVlanIntfv2PresentTime	OBJECT-TYPE
		SYNTAX		Unsigned32 
		UNITS		"0.1 second"
		MAX-ACCESS	read-only
		STATUS		current
		DESCRIPTION	"It can be tuned by
					(last iswIgmpVlanIntfqueryInterval*10*iswIgmpVlanIntfrobustness + iswIgmpVlanIntfmaxRespTime)
					"
		::= { iswIgmpVlanIntfEntry 15 }
--16   
	iswIgmpVlanIntfRunVersion	OBJECT-TYPE
		SYNTAX		Integer32 { igmpV2(2), igmpV3(3) }
		MAX-ACCESS	read-only
		STATUS		current
		DESCRIPTION	"Display current running version."
		::= { iswIgmpVlanIntfEntry 16 }
--17   
	iswIgmpVlanIntfRunRobustness	OBJECT-TYPE
		SYNTAX		Integer32 ( 1 .. 3 )
		MAX-ACCESS	read-only
		STATUS		current
		DESCRIPTION	"Display QRV value or configured value.
		To support QRV and QQIC in IGMPv3 mode. Industrial Ethernet Switch
		support 2 parameters to represent the running Robustness Variable and running Query Interval.
		These 2 parameters is support for each IGMP VLAN interface. When IGMPv3
		proxy mode, these 2 value will apply the value which get from IGMPv3 Query
		packet. In other mode, the value is applied the configured value.
		"
		::= { iswIgmpVlanIntfEntry 17}  
--18    
	iswIgmpVlanIntfRunQueryInterval	OBJECT-TYPE
		SYNTAX		Integer32 ( 1 .. 1800 )
		UNITS		"second"
		MAX-ACCESS	read-only
		STATUS		current
		DESCRIPTION	"Display QQIC value or configured value.
		To support QRV and QQIC in IGMPv3 mode. Industrial Ethernet Switch
		support 2 parameters to represent the running Robustness Variable and running Query Interval.
		These 2 parameters is support for each IGMP VLAN interface. When IGMPv3
		proxy mode, these 2 value will apply the value which get from IGMPv3 Query
		packet. In other mode, the value is applied the configured value.
		"
		::= { iswIgmpVlanIntfEntry 18 }
--19
	iswIgmpVlanIntfActquerierIpAddr	OBJECT-TYPE
		SYNTAX		IpAddress 
		MAX-ACCESS	read-only
		STATUS		current
		DESCRIPTION	"IGMP vlan interface: Active Querier ip address.
					(0.0.0.0 ~ 223.255.255.255, default:0.0.0.0).
					"
		::= { iswIgmpVlanIntfEntry 19 }
--20    
	iswIgmpVlanIntfrowStatus	OBJECT-TYPE
		SYNTAX		RowStatus
		MAX-ACCESS	read-create
		STATUS		current
		DESCRIPTION	"IGMP vlan interface: RowStatus."
		::= { iswIgmpVlanIntfEntry 20 }
--
	iswStaticMcastFdbTable 		OBJECT-TYPE
		SYNTAX		SEQUENCE OF IswStaticMcastFdbEntry
		MAX-ACCESS	not-accessible
		STATUS		current
		DESCRIPTION	"Static multicast FDB table. Max entry size: 128."
		::= { iswIgmp 2 }
		
	iswStaticMcastFdbEntry	OBJECT-TYPE
		SYNTAX		IswStaticMcastFdbEntry
		MAX-ACCESS	not-accessible
		STATUS		current
		DESCRIPTION	"Static multicast FDB entry."
		INDEX		{ iswStaticMcastFdbIndex }
		::= { iswStaticMcastFdbTable 1 }
		
	IswStaticMcastFdbEntry ::= SEQUENCE{
		iswStaticMcastFdbIndex			Integer32,
		iswStaticMcastFdbGroupAddr		IpAddress,
		iswStaticMcastFdbVlan			Integer32,
		iswStaticMcastFdbPort			IswGbeIndex,
		--iswStaticMcastFdbActionType		Integer32,
		iswStaticMcastFdbRowStatus		RowStatus
	}
--1
	iswStaticMcastFdbIndex	OBJECT-TYPE
		SYNTAX		Integer32 ( 1 .. 128 )
		MAX-ACCESS	not-accessible
		STATUS		current
		DESCRIPTION	"Static multicast FDB index. Use iswNextStaticMcFdbIndex to get next available index."
		::= { iswStaticMcastFdbEntry 1 }
--2  
	iswStaticMcastFdbGroupAddr	OBJECT-TYPE
		SYNTAX		IpAddress
		MAX-ACCESS	read-create
		STATUS		current
		DESCRIPTION	"Static multicast FDB group address. 224.0.0.0 ~ 239.255.255.255"
		::= { iswStaticMcastFdbEntry 2 }
--3   
	iswStaticMcastFdbVlan	OBJECT-TYPE
		SYNTAX		Integer32 ( 1 .. 4094 )
		MAX-ACCESS	read-create
		STATUS		current
		DESCRIPTION	"Static multicast FDB vlan."
		::= { iswStaticMcastFdbEntry 3 }
--4   
	iswStaticMcastFdbPort	OBJECT-TYPE
		SYNTAX		IswGbeIndex
		MAX-ACCESS	read-create
		STATUS		current
		DESCRIPTION	"Static multicast FDB port."
		::= { iswStaticMcastFdbEntry 4 }
--5  
	iswStaticMcastFdbRowStatus	OBJECT-TYPE
		SYNTAX		RowStatus
		MAX-ACCESS	read-create
		STATUS		current
		DESCRIPTION	"Static multicast FDB RowStatus."
		::= { iswStaticMcastFdbEntry 5 }

-- StaticMcastFdbDeleteCtrl
	iswStaticMcastFdbDeleteCtrl	OBJECT IDENTIFIER
		::= { iswIgmp 3 }	

	iswStaticMcastFdbDeleteIndex	OBJECT-TYPE
		SYNTAX		Integer32 ( 1 .. 128 )
		MAX-ACCESS	read-write
		STATUS		current
		DESCRIPTION	"Static multicast FDB entry index to be deleted."
		::= { iswStaticMcastFdbDeleteCtrl 1 }
                         
	iswStaticMcastFdbDeleteVlan	OBJECT-TYPE
		SYNTAX		Integer32 ( 1 .. 4094 )
		MAX-ACCESS	read-write
		STATUS		current
		DESCRIPTION	"To delete Static multicast FDB entry by VLAN ID."
		::= { iswStaticMcastFdbDeleteCtrl 2 }
                         
	iswStaticMcastFdbDeletePort	OBJECT-TYPE
		SYNTAX		IswGbeIndex 
		MAX-ACCESS	read-write
		STATUS		current
		DESCRIPTION	"To delete Static multicast FDB entry by Port Index."
		::= { iswStaticMcastFdbDeleteCtrl 3 }
                                             
	iswStaticMcastFdbDeleteType	OBJECT-TYPE
		SYNTAX		Integer32 { deleteByIndex (0), deleteByVlan (1), deleteByPort (2), deleteAll (3) }
		MAX-ACCESS	read-write
		STATUS		current
		DESCRIPTION	"Static multicast FDB delete type."
		::= { iswStaticMcastFdbDeleteCtrl 5 }
--
--
	iswMulticastFdbTable	OBJECT-TYPE
		SYNTAX		SEQUENCE OF IswMulticastFdbEntry
		MAX-ACCESS	not-accessible
		STATUS		current
		DESCRIPTION	"Multicast FDB table. Max entry size: 512."
		::= { iswIgmp 4 } 
		
	iswMulticastFdbEntry	OBJECT-TYPE
		SYNTAX		IswMulticastFdbEntry
		MAX-ACCESS	not-accessible
		STATUS		current
		DESCRIPTION	"Multicast FDB entry."
		INDEX		{ iswMcastFdbIndx }
		::= { iswMulticastFdbTable 1 } 

	IswMulticastFdbEntry ::= SEQUENCE{
		iswMcastFdbIndx				Integer32,
		iswMcastFdbGroupAddr		IpAddress,
		iswMcastFdbVlan				Integer32,
		--iswMcastFdbPortKeyValue	Integer32,
		iswMcastFdbPort				OCTET STRING,
		iswMcastFdbFilterMode		Integer32,
		iswMcastFdbRemainTime		OCTET STRING,
		iswMcastFdbStatus			OCTET STRING
		--iswMcastFdbSessionKey		Integer32,
		--iswMcastFdbActionType		Integer32,
	}
--1
	iswMcastFdbIndx	OBJECT-TYPE
		SYNTAX		Integer32 ( 1 .. 512 )
		MAX-ACCESS	not-accessible
		STATUS		current
		DESCRIPTION	"Multicast FDB index."
		::= { iswMulticastFdbEntry 1 }
--2
	iswMcastFdbGroupAddr	OBJECT-TYPE
		SYNTAX		IpAddress
		MAX-ACCESS	read-only
		STATUS		current
		DESCRIPTION	"Multicast FDB group address."
		::= { iswMulticastFdbEntry 2 }
--3
	iswMcastFdbVlan	OBJECT-TYPE
		SYNTAX		Integer32 ( 1 .. 4094 )
		MAX-ACCESS	read-only
		STATUS		current
		DESCRIPTION	"Multicast FDB vlan."
		::= { iswMulticastFdbEntry 3 }
--4
	--iswMcastFdbPortKeyValue	OBJECT-TYPE
	--	SYNTAX		Integer32 ( 1 .. 10 )
	--	MAX-ACCESS	write-only
	--	STATUS		current
	--	DESCRIPTION	"Multicast FDB port key value."
	--	::= { iswMulticastFdbEntry 4 } 
--4 
	iswMcastFdbPort	OBJECT-TYPE
		SYNTAX		OCTET STRING ( SIZE (28) )
		MAX-ACCESS	read-only
		STATUS		current
		DESCRIPTION	"Multicast FDB port. Port 1~28. Each 1 byte for single port."
		::= { iswMulticastFdbEntry 4 } 
--5 
	iswMcastFdbFilterMode	OBJECT-TYPE
		SYNTAX		Integer32 { disable(0), include(1), exclude(2) }
		MAX-ACCESS	read-only
		STATUS		current
		DESCRIPTION	"Multicast FDB filter mode."
		::= { iswMulticastFdbEntry 5 }
--6 
	iswMcastFdbRemainTime	OBJECT-TYPE
		SYNTAX		OCTET STRING ( SIZE (112) )
		UNITS       "0.1 second"
		MAX-ACCESS	read-only
		STATUS		current
		DESCRIPTION	"Remaining Time for multicast forwarding table. (unit :0.1 sec)
					Each 4 bytes for single port. Total 112 bytes for 28 ports."
		::= { iswMulticastFdbEntry 6 } 
--7 
	iswMcastFdbStatus	OBJECT-TYPE
		SYNTAX		OCTET STRING ( SIZE (28) )
		MAX-ACCESS	read-only
		STATUS		current
		DESCRIPTION	"Multicast FDB status. Each 1 byte for single port. Mapping: invalid (0), dynamic (1), static (2)"
		::= { iswMulticastFdbEntry 7 } 

-- StaticMcastFdbDeleteCtrl
	iswMcastFdbDeleteCtrl	OBJECT IDENTIFIER
		::= { iswIgmp 5 }

	--iswMcastFdbDeleteIndex	OBJECT-TYPE
	--	SYNTAX		Integer32 ( 1 .. 512 )
	--	MAX-ACCESS	read-write
	--	STATUS		current
	--	DESCRIPTION	"Dot1q FDB entry index"
	--	::= { iswMcastFdbDeleteCtrl 1 }
                         
	iswMcastFdbDeleteVlan	OBJECT-TYPE
		SYNTAX		Integer32 ( 1 .. 4094 ) 
		MAX-ACCESS	read-write
		STATUS		current
		DESCRIPTION	"VLAN ID"
		::= { iswMcastFdbDeleteCtrl 1 }

	iswMcastFdbDeletePort	OBJECT-TYPE
		SYNTAX		IswGbeIndex
		MAX-ACCESS	read-write
		STATUS		current
		DESCRIPTION	"Port Index."
		::= { iswMcastFdbDeleteCtrl 2 }

	iswMcastFdbDeleteType	OBJECT-TYPE
		SYNTAX		Integer32 { deleteByVlan (1), deleteByPort (2), deleteAll (3) }
		MAX-ACCESS	read-write
		STATUS		current
		DESCRIPTION	"multicast FDB delete type.
					It will delete dynamic multicase FDB."
		::= { iswMcastFdbDeleteCtrl 3 }

	iswMulticastSrcFdbTable	OBJECT-TYPE
		SYNTAX		SEQUENCE OF IswMulticastSrcFdbEntry
		MAX-ACCESS	not-accessible
		STATUS		current
		DESCRIPTION	"Multicast Source FDB table. Max entry size: 64."
		::= { iswIgmp 6 } 
		
	iswMulticastSrcFdbEntry	OBJECT-TYPE
		SYNTAX		IswMulticastSrcFdbEntry
		MAX-ACCESS	not-accessible
		STATUS		current
		DESCRIPTION	"Multicast Source FDB entry."
		INDEX		{ iswMcastSrcFdbIndex }
		::= { iswMulticastSrcFdbTable 1 }
		
	IswMulticastSrcFdbEntry ::= SEQUENCE{
		iswMcastSrcFdbIndex				Integer32,
		iswMcastSrcFdbGroupAddr			IpAddress,
		iswMcastSrcFdbVlan				Integer32,
		iswMcastSrcFdbFilterMode		Integer32,
		iswMcastSrcFdbGroupRemainTime	Unsigned32,
		iswMcastSrcFdbSrcIP				IpAddress,
		iswMcastSrcFdbSrcRemainTime		Unsigned32,
		iswMcastSrcFdbSrcFilter			Integer32
	}
--1 
	iswMcastSrcFdbIndex	OBJECT-TYPE
		SYNTAX		Integer32 ( 1..64 )
		MAX-ACCESS	not-accessible
		STATUS		current
		DESCRIPTION	"Multicast Source FDB index."
		::= { iswMulticastSrcFdbEntry 1 } 
--2 
	iswMcastSrcFdbGroupAddr	OBJECT-TYPE
		SYNTAX		IpAddress
		MAX-ACCESS	read-only
		STATUS		current
		DESCRIPTION	"Multicast Source FDB group address. 224.0.0.0 - 239.255.255.255."
		::= { iswMulticastSrcFdbEntry 2 } 
--3 
	iswMcastSrcFdbVlan	OBJECT-TYPE
		SYNTAX		Integer32 ( 1 .. 4094 )
		MAX-ACCESS	read-only
		STATUS		current
		DESCRIPTION	"Multicast Source FDB vlan."
		::= { iswMulticastSrcFdbEntry 3 }
--4 
	iswMcastSrcFdbFilterMode	OBJECT-TYPE
		SYNTAX		Integer32 { disable(0), include(1), exclude(2) }
		MAX-ACCESS	read-only
		STATUS		current
		DESCRIPTION	"Multicast Source FDB filter mode."
		::= { iswMulticastSrcFdbEntry 4 }
--5 
	iswMcastSrcFdbGroupRemainTime	OBJECT-TYPE
		SYNTAX		Unsigned32
		UNITS           "0.1 second"
		MAX-ACCESS	read-only
		STATUS		current
		DESCRIPTION	"0 is meaning no timeout.
					In include mode, the iswMcastSrcFdbGroupRemainTime is no timeout."
		::= { iswMulticastSrcFdbEntry 5 } 
--6 
	iswMcastSrcFdbSrcIP	OBJECT-TYPE
		SYNTAX		IpAddress
		MAX-ACCESS	read-only
		STATUS		current
		DESCRIPTION	"Source IP address."
		::= { iswMulticastSrcFdbEntry 6 }
--7 
	iswMcastSrcFdbSrcRemainTime	OBJECT-TYPE
		SYNTAX		Unsigned32
		UNITS       "0.1 second"
		MAX-ACCESS	read-only
		STATUS		current
		DESCRIPTION	"0 is meaning no timeout.
					In exclude mode, if the iswMcastSrcFdbSrcFilter is block, the iswMcastSrcFdbSrcRemainTime is no timeout."
		::= { iswMulticastSrcFdbEntry 7 } 
--8 
	iswMcastSrcFdbSrcFilter	OBJECT-TYPE
		SYNTAX		Integer32 { allow(1), block(2) }
		MAX-ACCESS	read-only
		STATUS		current
		DESCRIPTION	"Multicast Source FDB filter."
		::= { iswMulticastSrcFdbEntry 8 }
--
	iswIgmpAclProfileTable	OBJECT-TYPE
		SYNTAX		SEQUENCE OF IswIgmpAclProfileEntry
		MAX-ACCESS	not-accessible
		STATUS		current
		DESCRIPTION	"IGMP Acl profile table. Max entry size: 15. 
					Each entry will be referred to from iswIgmpAclBindTable.
					Once Profile is binded in iswIgmpAclBindProfileIndex, it means the relative entries on profile table and entry table can't be deleted/modified.
					If entries are deleted, the relative entries on iswIgmpAclEntryTable will be deleted too.
					Profile 1 is a default entry and can't be modified and can't be deleted."
		::= { iswIgmpAcl 1 }
					 
	iswIgmpAclProfileEntry	OBJECT-TYPE
		SYNTAX		IswIgmpAclProfileEntry
		MAX-ACCESS	not-accessible
		STATUS		current
		DESCRIPTION	"IGMP Acl profile entry."
		INDEX		{ iswIgmpAclProfileIndex }   
		::= { iswIgmpAclProfileTable 1 } 
		 
	IswIgmpAclProfileEntry ::= SEQUENCE{
		iswIgmpAclProfileIndex		Integer32,
		iswIgmpAclProfileDefRule	Integer32,
		iswIgmpAclProfileRowStatus	RowStatus
	}
--1	
	iswIgmpAclProfileIndex	OBJECT-TYPE
		SYNTAX		Integer32 ( 1 .. 15 )
		MAX-ACCESS	not-accessible
		STATUS		current
		DESCRIPTION	"IGMP Acl profile index. Use iswNextIgmpAclProfileIndex to get next available index."
		::= { iswIgmpAclProfileEntry 1 }
--2	
	iswIgmpAclProfileDefRule	OBJECT-TYPE
		SYNTAX		Integer32 { permit (0), deny (1) }
		MAX-ACCESS	read-create
		STATUS		current
		DESCRIPTION	"IGMP Acl profile default rule. Default is permit(0)."
		DEFVAL		{ 0 }
		::= { iswIgmpAclProfileEntry 2 } 
--3
	iswIgmpAclProfileRowStatus	OBJECT-TYPE
		SYNTAX		RowStatus
		MAX-ACCESS	read-create
		STATUS		current
		DESCRIPTION	"IGMP Acl profile RowStatus."
		::= { iswIgmpAclProfileEntry 3 }
--
	iswIgmpAclEntryTable		OBJECT-TYPE
		SYNTAX		SEQUENCE OF IswIgmpAclEntryEntry
		MAX-ACCESS	not-accessible
		STATUS		current
		DESCRIPTION	"IGMP Acl entry table. Max entry size: 448(14x32). 
					1 IGMP Acl profile contains max 32 IGMP Acl entries. But profile 1 has no entry."
		::= { iswIgmpAcl 2 }  
				
	iswIgmpAclEntryEntry	OBJECT-TYPE
		SYNTAX		IswIgmpAclEntryEntry
		MAX-ACCESS	not-accessible
		STATUS		current
		DESCRIPTION	"IGMP Acl entry entry."
		INDEX		{ iswIgmpAclEntryProfileIndex, iswIgmpAclEntryIndex }
		::= { iswIgmpAclEntryTable 1 }      
		
	IswIgmpAclEntryEntry ::= SEQUENCE{
		iswIgmpAclEntryProfileIndex	Integer32,
		iswIgmpAclEntryIndex		Integer32,
		iswIgmpAclEntryStartIP		IpAddress,
		iswIgmpAclEntryEndIP		IpAddress,
		iswIgmpAclEntrySVlan		Integer32,
		iswIgmpAclEntryRule			Integer32,
		iswIgmpAclEntryRowStatus	RowStatus
	}
--1
	iswIgmpAclEntryProfileIndex	OBJECT-TYPE
		SYNTAX		Integer32 ( 2 .. 15 )
		MAX-ACCESS	not-accessible
		STATUS		current
		DESCRIPTION	"IGMP Acl profile index."
		::= { iswIgmpAclEntryEntry 1 }
--2
	iswIgmpAclEntryIndex	OBJECT-TYPE
		SYNTAX		Integer32 ( 1 .. 32 )
		MAX-ACCESS	not-accessible
		STATUS		current
		DESCRIPTION	"IGMP Acl entry index."
		::= { iswIgmpAclEntryEntry 2 }
--3
	iswIgmpAclEntryStartIP	OBJECT-TYPE
		SYNTAX		IpAddress
		MAX-ACCESS	read-create
		STATUS		current
		DESCRIPTION	"IGMP Acl Start IP address. Range: 224.0.1.0 - 239.255.255.255.
					Start IP address <= End IP address."
		::= { iswIgmpAclEntryEntry 3 }
--4
	iswIgmpAclEntryEndIP	OBJECT-TYPE
		SYNTAX		IpAddress
		MAX-ACCESS	read-create
		STATUS		current
		DESCRIPTION	"IGMP Acl End IP address. Range: 224.0.1.0 - 239.255.255.255.
					Start IP address <= End IP address."
		::= { iswIgmpAclEntryEntry 4 }
--5
	iswIgmpAclEntrySVlan	OBJECT-TYPE
		SYNTAX		Integer32 ( 0 .. 4094 )
		MAX-ACCESS	read-create
		STATUS		current
		DESCRIPTION	"IGMP Acl entry SVlan. 0 is any vlan."
		::= { iswIgmpAclEntryEntry 5 }
--6
	iswIgmpAclEntryRule	OBJECT-TYPE
		SYNTAX		Integer32 { permit (0), deny (1) }
		MAX-ACCESS	read-create
		STATUS		current
		DESCRIPTION	"IGMP Acl entry parameter. Default is permit(0)."
		DEFVAL		{ 0 }
		::= { iswIgmpAclEntryEntry 6 }
--7	
	iswIgmpAclEntryRowStatus	OBJECT-TYPE
		SYNTAX		RowStatus
		MAX-ACCESS	read-create
		STATUS		current
		DESCRIPTION	"IGMP Acl entry RowStatus."
		::= { iswIgmpAclEntryEntry 7 }
--
	iswIgmpAclBindTable		OBJECT-TYPE
		SYNTAX		SEQUENCE OF IswIgmpAclBindEntry
		MAX-ACCESS	not-accessible
		STATUS		current
		DESCRIPTION	"IGMP Acl bind table. Max entry size: 10."
		::= { iswIgmpAcl 3 }  
		
	iswIgmpAclBindEntry	OBJECT-TYPE
		SYNTAX		IswIgmpAclBindEntry
		MAX-ACCESS	not-accessible
		STATUS		current
		DESCRIPTION	"IGMP Acl bind entry."
		INDEX		{ iswIgmpAclBindPortIndex }
		::= { iswIgmpAclBindTable 1 } 
		  
	IswIgmpAclBindEntry ::= SEQUENCE{
		iswIgmpAclBindPortIndex			IswGbeIndex,
		iswIgmpAclBindProfileIndex		Integer32,
		iswIgmpAclBindConfMaxChannel	Integer32
	}
--1
	iswIgmpAclBindPortIndex		OBJECT-TYPE
		SYNTAX		IswGbeIndex
		MAX-ACCESS	not-accessible
		STATUS		current
		DESCRIPTION	"Port index."
		::= { iswIgmpAclBindEntry 1 }
--2   
	iswIgmpAclBindProfileIndex		OBJECT-TYPE
		SYNTAX		Integer32 ( 1 .. 15 )
		MAX-ACCESS	read-write
		STATUS		current
		DESCRIPTION	"IGMP ACL profile index. Default value is 1."
		DEFVAL		{ 1 }
		::= { iswIgmpAclBindEntry 2 }
--3     
	iswIgmpAclBindConfMaxChannel		OBJECT-TYPE
		SYNTAX		Integer32 ( 1 .. 512 )
		MAX-ACCESS	read-write
		STATUS		current
		DESCRIPTION	"IGMP Acl port Max channel. Default value is 512."
		DEFVAL		{ 512 }
		::= { iswIgmpAclBindEntry 3 }
--
--
	iswIgmpMvrProfileTable	OBJECT-TYPE
		SYNTAX		SEQUENCE OF IswIgmpMvrProfileEntry
		MAX-ACCESS	not-accessible
		STATUS		current
		DESCRIPTION	"IGMP MVR profile table. Max entry size: 15. 
					Each entry will be referred to from iswIgmpMvrBindTable.
					Once Profile is binded in iswIgmpMvrBindProfileIndex, it means the relative entries on profile table and entry table can't be deleted/modified.
					If entries are deleted, the relative entries on iswIgmpMvrEntryTable will be deleted too.
					Profile 1 is a default entry and can't be modified and can't be deleted."
		::= { iswIgmpMvr 1 }

	iswIgmpMvrProfileEntry	OBJECT-TYPE
		SYNTAX		IswIgmpMvrProfileEntry
		MAX-ACCESS	not-accessible
		STATUS		current
		DESCRIPTION	"IGMP MVR profile entry."
		INDEX		{ iswIgmpMvrProfileIndex }
		::= { iswIgmpMvrProfileTable 1 } 
		 
	IswIgmpMvrProfileEntry ::= SEQUENCE{
		iswIgmpMvrProfileIndex		Integer32,
		iswIgmpMvrProfileRowStatus	RowStatus
	}
--1	
	iswIgmpMvrProfileIndex	OBJECT-TYPE
		SYNTAX		Integer32 ( 1 .. 15 )
		MAX-ACCESS	not-accessible
		STATUS		current
		DESCRIPTION	"IGMP MVR profile index. Use iswNextIgmpMvrProfileIndex to get next available index."
		::= { iswIgmpMvrProfileEntry 1 }
--2
	iswIgmpMvrProfileRowStatus	OBJECT-TYPE
		SYNTAX		RowStatus
		MAX-ACCESS	read-create
		STATUS		current
		DESCRIPTION	"IGMP MVR profile RowStatus."
		::= { iswIgmpMvrProfileEntry 2 }
--
	iswIgmpMvrEntryTable	OBJECT-TYPE
		SYNTAX		SEQUENCE OF IswIgmpMvrEntryEntry
		MAX-ACCESS	not-accessible
		STATUS		current
		DESCRIPTION	"IGMP MVR entry table. Max entry size: 448(14x32). 
					1 IGMP Mvr profile contains max 32 IGMP Mvr entries. But profile 1 has no entry."
		::= { iswIgmpMvr 2 }  
				
	iswIgmpMvrEntryEntry	OBJECT-TYPE
		SYNTAX		IswIgmpMvrEntryEntry
		MAX-ACCESS	not-accessible
		STATUS		current
		DESCRIPTION	"IGMP MVR entry entry."
		INDEX		{ iswIgmpMvrEntryProfileIndex, iswIgmpMvrEntryIndex }
		::= { iswIgmpMvrEntryTable 1 }      

	IswIgmpMvrEntryEntry ::= SEQUENCE{
		iswIgmpMvrEntryProfileIndex	Integer32,
		iswIgmpMvrEntryIndex		Integer32,
		iswIgmpMvrEntryStartIP		IpAddress,
		iswIgmpMvrEntryEndIP		IpAddress,
		iswIgmpMvrEntrySVlan		Integer32,
		iswIgmpMvrEntryRowStatus	RowStatus
	}
--1
	iswIgmpMvrEntryProfileIndex	OBJECT-TYPE
		SYNTAX		Integer32 ( 2 .. 15 )
		MAX-ACCESS	not-accessible
		STATUS		current
		DESCRIPTION	"IGMP MVR profile index."
		::= { iswIgmpMvrEntryEntry 1 }  
--2
	iswIgmpMvrEntryIndex	OBJECT-TYPE
		SYNTAX		Integer32 ( 1 .. 32 )
		MAX-ACCESS	not-accessible
		STATUS		current
		DESCRIPTION	"IGMP MVR entry index."
		::= { iswIgmpMvrEntryEntry 2 }
--3
	iswIgmpMvrEntryStartIP	OBJECT-TYPE
		SYNTAX		IpAddress
		MAX-ACCESS	read-create
		STATUS		current
		DESCRIPTION	"IGMP Mvr Start IP address. Range: 224.0.1.0 - 239.255.255.255
					Start IP address <= End IP address."
		::= { iswIgmpMvrEntryEntry 3 }
--4
	iswIgmpMvrEntryEndIP	OBJECT-TYPE
		SYNTAX		IpAddress
		MAX-ACCESS	read-create
		STATUS		current
		DESCRIPTION	"IGMP Mvr End IP address. Range: 224.0.1.0 - 239.255.255.255
					Start IP address <= End IP address."
		::= { iswIgmpMvrEntryEntry 4 }
--5
	iswIgmpMvrEntrySVlan	OBJECT-TYPE
		SYNTAX		Integer32 ( 1 .. 4094 )
		MAX-ACCESS	read-create
		STATUS		current
		DESCRIPTION	"IGMP MVR entry SVlan."
		::= { iswIgmpMvrEntryEntry 5 }
--6	
	iswIgmpMvrEntryRowStatus	OBJECT-TYPE
		SYNTAX		RowStatus
		MAX-ACCESS	read-create
		STATUS		current
		DESCRIPTION	"IGMP MVR entry RowStatus."
		::= { iswIgmpMvrEntryEntry 6 }
--
	iswIgmpMvrBindTable	OBJECT-TYPE
		SYNTAX		SEQUENCE OF IswIgmpMvrBindEntry
		MAX-ACCESS	not-accessible
		STATUS		current
		DESCRIPTION	"IGMP MVR bind table. Max entry size: 10."
		::= { iswIgmpMvr 3 }  
		
	iswIgmpMvrBindEntry	OBJECT-TYPE
		SYNTAX		IswIgmpMvrBindEntry
		MAX-ACCESS	not-accessible
		STATUS		current
		DESCRIPTION	"IGMP MVR bind entry."
		INDEX		{ iswIgmpMvrBindPortIndex }
		::= { iswIgmpMvrBindTable 1 } 
		  
	IswIgmpMvrBindEntry ::= SEQUENCE{
		iswIgmpMvrBindPortIndex		IswGbeIndex,
		iswIgmpMvrBindProfileIndex	Integer32
	}
--1
	iswIgmpMvrBindPortIndex		OBJECT-TYPE
		SYNTAX		IswGbeIndex
		MAX-ACCESS	not-accessible
		STATUS		current
		DESCRIPTION	"Port index."
		::= { iswIgmpMvrBindEntry 1 }
--2   
	iswIgmpMvrBindProfileIndex		OBJECT-TYPE
		SYNTAX		Integer32 ( 1 .. 15 )
		MAX-ACCESS	read-write
		STATUS		current
		DESCRIPTION	"IGMP MVR profile index. Default value is 1."
		DEFVAL		{ 1 }          
		::= { iswIgmpMvrBindEntry 2 }

--1
	iswPolicerInColorAwareMode	OBJECT-TYPE
		SYNTAX		Integer32 { blind (0), aware (1) }
		MAX-ACCESS	read-write
		STATUS		current
		DESCRIPTION	"Policer Income color aware mode. Default value is blind (0)."  
		DEFVAL		{ 0 }
		::= { iswPolicerIngressColor 1 } 
--2
	iswPolicerIngressColorCoS0	OBJECT-TYPE
		SYNTAX		Integer32 { green (0), yellow (1), red (2) }
		MAX-ACCESS	read-write
		STATUS		current
		DESCRIPTION	"Policer ingress color CoS 0. Default value is green (0)."   
		DEFVAL		{ 0 }
		::= { iswPolicerIngressColor 2 } 
--3
	iswPolicerIngressColorCoS1	OBJECT-TYPE
		SYNTAX		Integer32 { green (0), yellow (1), red (2) }
		MAX-ACCESS	read-write
		STATUS		current
		DESCRIPTION	"Policer ingress color CoS 1. Default value is green (0)."  
		DEFVAL		{ 0 }
		::= { iswPolicerIngressColor 3 } 
--4
	iswPolicerIngressColorCoS2	OBJECT-TYPE
		SYNTAX		Integer32 { green (0), yellow (1), red (2) }
		MAX-ACCESS	read-write
		STATUS		current
		DESCRIPTION	"Policer ingress color CoS 2. Default value is green (0)."   
		DEFVAL		{ 0 }
		::= { iswPolicerIngressColor 4 }
--5
	iswPolicerIngressColorCoS3	OBJECT-TYPE
		SYNTAX		Integer32 { green (0), yellow (1), red (2) }
		MAX-ACCESS	read-write
		STATUS		current
		DESCRIPTION	"Policer ingress color CoS 3. Default value is green (0)."  
		DEFVAL		{ 0 }
		::= { iswPolicerIngressColor 5 }
--6
	iswPolicerIngressColorCoS4	OBJECT-TYPE
		SYNTAX		Integer32 { green (0), yellow (1), red (2) }
		MAX-ACCESS	read-write
		STATUS		current
		DESCRIPTION	"Policer ingress color CoS 4. Default value is green (0)."  
		DEFVAL		{ 0 }
		::= { iswPolicerIngressColor 6 }
--7
	iswPolicerIngressColorCoS5	OBJECT-TYPE
		SYNTAX		Integer32 { green (0), yellow (1), red (2) }
		MAX-ACCESS	read-write
		STATUS		current
		DESCRIPTION	"Policer ingress color CoS 5. Default value is green (0)."  
		DEFVAL		{ 0 }
		::= { iswPolicerIngressColor 7 }
--8
	iswPolicerIngressColorCoS6	OBJECT-TYPE
		SYNTAX		Integer32 { green (0), yellow (1), red (2) }
		MAX-ACCESS	read-write
		STATUS		current
		DESCRIPTION	"Policer ingress color CoS 6. Default value is green (0)."  
		DEFVAL		{ 0 }
		::= { iswPolicerIngressColor 8 }
--9
	iswPolicerIngressColorCoS7	OBJECT-TYPE
		SYNTAX		Integer32 { green (0), yellow (1), red (2) }
		MAX-ACCESS	read-write
		STATUS		current
		DESCRIPTION	"Policer ingress color CoS 7. Default value is green (0)."  
		DEFVAL		{ 0 }
		::= { iswPolicerIngressColor 9 }
--
--1
	iswPolicerCoSMarkingGreen	OBJECT-TYPE
		SYNTAX		Integer32 ( 0 .. 7 )
		MAX-ACCESS	read-write
		STATUS		current
		DESCRIPTION	"Policer CoS marking green. Default value is 7." 
		DEFVAL		{ 7 }
		::= { iswPolicerColorMarking 1 }  
--2
	iswPolicerCoSMarkingYellow	OBJECT-TYPE
		SYNTAX		Integer32 ( 0 .. 7 )
		MAX-ACCESS	read-write
		STATUS		current
		DESCRIPTION	"Policer CoS marking green. Default value is 5."  
		DEFVAL		{ 5 }
		::= { iswPolicerColorMarking 2 }
--3
	iswPolicerCoSMarkingRed	OBJECT-TYPE
		SYNTAX		Integer32 ( 0 .. 7 )
		MAX-ACCESS	read-write
		STATUS		current
		DESCRIPTION	"Policer CoS marking green. Default value is 3."  
		DEFVAL		{ 3 }
		::= { iswPolicerColorMarking 3 }
--4
	iswPolicerDSCPMarkingGreen	OBJECT-TYPE
		SYNTAX		Integer32 ( 0 .. 63 )
		MAX-ACCESS	read-write
		STATUS		current
		DESCRIPTION	"Policer CoS marking green. Default value is 56." 
		DEFVAL		{ 56 }
		::= { iswPolicerColorMarking 4 }  
--5
	iswPolicerDSCPMarkingYellow	OBJECT-TYPE
		SYNTAX		Integer32 ( 0 .. 63 )
		MAX-ACCESS	read-write
		STATUS		current
		DESCRIPTION	"Policer CoS marking green. Default value is 40." 
		DEFVAL		{ 40 }
		::= { iswPolicerColorMarking 5 }  
--6
	iswPolicerDSCPMarkingRed	OBJECT-TYPE
		SYNTAX		Integer32 ( 0 .. 63 )
		MAX-ACCESS	read-write
		STATUS		current
		DESCRIPTION	"Policer CoS marking green. Default value is 24." 
		DEFVAL		{ 24 }
		::= { iswPolicerColorMarking 6 }
--
	iswIngressPolicerTable		OBJECT-TYPE
		SYNTAX		SEQUENCE OF IswIngressPolicerEntry
		MAX-ACCESS	not-accessible
		STATUS		current
		DESCRIPTION	"Ingress policer table. Max entry size: 10."
		::= { iswPolicer 3 }
		
	iswIngressPolicerEntry	OBJECT-TYPE
		SYNTAX		IswIngressPolicerEntry
		MAX-ACCESS	not-accessible
		STATUS		current
		DESCRIPTION	"Ingress policer entry."
		INDEX		{ iswIngressPolicerPortId }
		::= { iswIngressPolicerTable 1 }
		
	IswIngressPolicerEntry ::= SEQUENCE{
		iswIngressPolicerPortId			IswGbeIndex,
		iswIngressPolicerMode			Integer32,
		iswIngressPolicerPIR			Integer32,
		iswIngressPolicerPBS			Integer32,
		iswIngressPolicerCIR			Integer32,
		iswIngressPolicerCBS			Integer32,
		iswIngressPolicerExceedAction	Integer32
	}	
--1  	
	iswIngressPolicerPortId	OBJECT-TYPE
		SYNTAX		IswGbeIndex
		MAX-ACCESS	not-accessible
		STATUS		current
		DESCRIPTION	"Ingress policer port ID."
		::= { iswIngressPolicerEntry 1 }  
--2   
	iswIngressPolicerMode	OBJECT-TYPE
		SYNTAX		Integer32 { disable (0), enable (1) }
		MAX-ACCESS	read-write
		STATUS		current
		DESCRIPTION	"Ingress policer mode. Default value is disable (0)." 
		DEFVAL		{ 0 }
		::= { iswIngressPolicerEntry 2 }  
--3   
	iswIngressPolicerPIR	OBJECT-TYPE
		SYNTAX		Integer32 ( 1 .. 1000000)  
		UNITS		"kbps"
		MAX-ACCESS	read-write
		STATUS		current
		DESCRIPTION	"Ingress policer PIR. Default value is 1000000."   
		DEFVAL		{ 1000000 }
		::= { iswIngressPolicerEntry 3 }  
--4   
	iswIngressPolicerPBS	OBJECT-TYPE
		SYNTAX		Integer32 ( 10240 .. 65535 )  
		UNITS		"bytes"
		MAX-ACCESS	read-write
		STATUS		current
		DESCRIPTION	"Ingress policer PBS. Default value is 10240."  
		DEFVAL		{ 10240 }
		::= { iswIngressPolicerEntry 4 }  
--5  
	iswIngressPolicerCIR	OBJECT-TYPE
		SYNTAX		Integer32  ( 1 .. 1000000)
		UNITS		"kbps"
		MAX-ACCESS	read-write
		STATUS		current
		DESCRIPTION	"Ingress policer CIR. Default value is 500000." 
		DEFVAL		{ 500000 }
		::= { iswIngressPolicerEntry 5 }  
--6   
	iswIngressPolicerCBS	OBJECT-TYPE
		SYNTAX		Integer32 ( 10240 .. 65535 )
		UNITS		"bytes"
		MAX-ACCESS	read-write
		STATUS		current
		DESCRIPTION	"Ingress policer CBS. Default value is 10240."
		DEFVAL		{ 10240 }
		::= { iswIngressPolicerEntry 6 }  
--7  
	iswIngressPolicerExceedAction	OBJECT-TYPE
		SYNTAX		Integer32 { drop (0), cosMark (1), dscpMark (2) }
		MAX-ACCESS	read-write
		STATUS		current
		DESCRIPTION	"Ingress policer exceed action. Default value is drop (0)."   
		DEFVAL		{ 0 }
		::= { iswIngressPolicerEntry 7 }
--
	iswPortShaperTable	OBJECT-TYPE
		SYNTAX		SEQUENCE OF IswPortShaperEntry
		MAX-ACCESS	not-accessible
		STATUS		current
		DESCRIPTION	"Port shaper table. Max entry size: port number."
		::= { iswShaper 1 }	
	iswPortShaperEntry	OBJECT-TYPE
		SYNTAX		IswPortShaperEntry
		MAX-ACCESS	not-accessible
		STATUS		current
		DESCRIPTION	"Port shaper entry."
		INDEX		{ iswPortShaperPortId }
		::= { iswPortShaperTable 1 }
		
	IswPortShaperEntry ::= SEQUENCE{
		iswPortShaperPortId		IswGbeIndex,
		iswPortShaperMode		Integer32,
		iswPortShaperPortRate	Integer32
	}
--1 
	iswPortShaperPortId	OBJECT-TYPE
		SYNTAX		IswGbeIndex
		MAX-ACCESS	not-accessible
		STATUS		current
		DESCRIPTION	"Port shaper port ID."
		::= { iswPortShaperEntry 1 }  
--2
	iswPortShaperMode	OBJECT-TYPE
		SYNTAX		Integer32 { disable (0), enable (1) }
		MAX-ACCESS	read-write
		STATUS		current
		DESCRIPTION	"Port shaper port ID. Default is disable (0)."
		DEFVAL		{ 0 }
		::= { iswPortShaperEntry 2 }  
--3
	iswPortShaperPortRate	OBJECT-TYPE
		SYNTAX		Integer32  ( 1 .. 10000000 )
		UNITS		"kbps"
		MAX-ACCESS	read-write
		STATUS		current
		DESCRIPTION	"Port shaper rate. Range for GE port : 1 ~ 1000000.
					 for 10GE port : 1 ~ 10000000.
					 Default value is 1000000, Unit is Kpbs."
		DEFVAL		{ 1000000 }
		::= { iswPortShaperEntry 3 }
--
	iswQueShaperTable	OBJECT-TYPE
		SYNTAX		SEQUENCE OF IswQueShaperEntry
		MAX-ACCESS	not-accessible
		STATUS		current
		DESCRIPTION	"Queue shaper table. Max entry size: port number."
		::= { iswShaper 2 }
				
	iswQueShaperEntry	OBJECT-TYPE
		SYNTAX		IswQueShaperEntry
		MAX-ACCESS	not-accessible
		STATUS		current
		DESCRIPTION	"Queue shaper entry."
		INDEX		{ iswQueueShaperPortId }
		::= { iswQueShaperTable 1 }
		
	IswQueShaperEntry ::= SEQUENCE{
		iswQueueShaperPortId		IswGbeIndex,
		iswQueueShaperMode			Integer32,
		iswQueueShaperQ7Rate		Integer32,
		iswQueueShaperQ6Rate		Integer32,
		iswQueueShaperQ5Rate		Integer32,
		iswQueueShaperQ4Rate		Integer32,
		iswQueueShaperQ3Rate		Integer32,
		iswQueueShaperQ2Rate		Integer32,
		iswQueueShaperQ1Rate		Integer32,
		iswQueueShaperQ0Rate		Integer32
	}
--1   
	iswQueueShaperPortId	OBJECT-TYPE
		SYNTAX		IswGbeIndex
		MAX-ACCESS	not-accessible
		STATUS		current
		DESCRIPTION	"Queue shaper port ID."
		::= { iswQueShaperEntry 1 }  
--2   
	iswQueueShaperMode	OBJECT-TYPE
		SYNTAX		Integer32 { disable (0), enable (1) }
		MAX-ACCESS	read-write
		STATUS		current
		DESCRIPTION	"Queue shaper mode. Default value is disable (0)."  
		DEFVAL		{ 0 }
		::= { iswQueShaperEntry 2 }  
--3 
	iswQueueShaperQ7Rate	OBJECT-TYPE
		SYNTAX		Integer32 ( 1 .. 10000000 )   
		UNITS		"kbps"
		MAX-ACCESS	read-write
		STATUS		current
		DESCRIPTION	"Queue shaper queue 7 rate. Range for GE port : 1 ~ 1000000.
					 for 10GE port : 1 ~ 10000000.
					 Default value is 1000000."   
		DEFVAL		{ 1000000 }
		::= { iswQueShaperEntry 3 }
--4   
	iswQueueShaperQ6Rate	OBJECT-TYPE
		SYNTAX		Integer32 ( 1 .. 10000000 )
		UNITS		"kbps"
		MAX-ACCESS	read-write
		STATUS		current
		DESCRIPTION	"Queue shaper queue 6 rate. Range for GE port : 1 ~ 1000000.
					 for 10GE port : 1 ~ 10000000.
					 Default value is 1000000."  
		DEFVAL		{ 1000000 }
		::= { iswQueShaperEntry 4 }
--5
	iswQueueShaperQ5Rate	OBJECT-TYPE
		SYNTAX		Integer32 ( 1 .. 10000000 )
		UNITS		"kbps"
		MAX-ACCESS	read-write
		STATUS		current
		DESCRIPTION	"Queue shaper queue 5 rate. Range for GE port : 1 ~ 1000000.
					 for 10GE port : 1 ~ 10000000.
					 Default value is 1000000."     
		DEFVAL		{ 1000000 }
		::= { iswQueShaperEntry 5 }
--6
	iswQueueShaperQ4Rate	OBJECT-TYPE
		SYNTAX		Integer32 ( 1 .. 10000000 )
		UNITS		"kbps"
		MAX-ACCESS	read-write
		STATUS		current
		DESCRIPTION	"Queue shaper queue 4 rate. Range for GE port : 1 ~ 1000000.
					 for 10GE port : 1 ~ 10000000.
					 Default value is 1000000."    
		DEFVAL		{ 1000000 }
		::= { iswQueShaperEntry 6 }
--7
	iswQueueShaperQ3Rate	OBJECT-TYPE
		SYNTAX		Integer32 ( 1 .. 10000000 )
		UNITS		"kbps"
		MAX-ACCESS	read-write
		STATUS		current
		DESCRIPTION	"Queue shaper queue 3 rate. Range for GE port : 1 ~ 1000000.
					 for 10GE port : 1 ~ 10000000.
					 Default value is 1000000."    
		DEFVAL		{ 1000000 }
		::= { iswQueShaperEntry 7 }
--8
	iswQueueShaperQ2Rate	OBJECT-TYPE
		SYNTAX		Integer32 ( 1 .. 10000000 )
		UNITS		"kbps"
		MAX-ACCESS	read-write
		STATUS		current
		DESCRIPTION	"Queue shaper queue 2 rate. Range for GE port : 1 ~ 1000000.
					 for 10GE port : 1 ~ 10000000.
					 Default value is 1000000."  
		DEFVAL		{ 1000000 }
		::= { iswQueShaperEntry 8 }
--9    
	iswQueueShaperQ1Rate	OBJECT-TYPE
		SYNTAX		Integer32 ( 1 .. 10000000 )
		UNITS		"kbps"
		MAX-ACCESS	read-write
		STATUS		current
		DESCRIPTION	"Queue shaper queue 1 rate. Range for GE port : 1 ~ 1000000.
					 for 10GE port : 1 ~ 10000000.
					 Default value is 1000000."    
		DEFVAL		{ 1000000 }
		::= { iswQueShaperEntry 9 }
--10
	iswQueueShaperQ0Rate	OBJECT-TYPE
		SYNTAX		Integer32 ( 1 .. 1000000 )
		UNITS		"kbps"
		MAX-ACCESS	read-write
		STATUS		current
		DESCRIPTION	"Queue shaper queue 0 rate. Default value is 1000000."     
		DEFVAL		{ 1000000 }
		::= { iswQueShaperEntry 10 }
--1
	iswCosQueueMappingCos0	OBJECT-TYPE
		SYNTAX		Integer32 ( 0 .. 7 )
		MAX-ACCESS	read-write
		STATUS		current
		DESCRIPTION	"CoS queue mapping. Default is 0"     
		DEFVAL		{ 0 }
		::= { iswCosQueMapping 1 }
--2  
	iswCosQueueMappingCos1	OBJECT-TYPE
		SYNTAX		Integer32 ( 0 .. 7 )
		MAX-ACCESS	read-write
		STATUS		current
		DESCRIPTION	"CoS queue mapping. Default is 1."    
		DEFVAL		{ 1 }
		::= { iswCosQueMapping 2 }  
--3   
	iswCosQueueMappingCos2	OBJECT-TYPE
		SYNTAX		Integer32 ( 0 .. 7 )
		MAX-ACCESS	read-write
		STATUS		current
		DESCRIPTION	"CoS queue mapping. Default is 2."       
		DEFVAL		{ 2 }
		::= { iswCosQueMapping 3 }  
--4   
	iswCosQueueMappingCos3	OBJECT-TYPE
		SYNTAX		Integer32 ( 0 .. 7 )
		MAX-ACCESS	read-write
		STATUS		current
		DESCRIPTION	"CoS queue mapping. Default is 3."     
		DEFVAL		{ 3 }
		::= { iswCosQueMapping 4 }  
--5    
	iswCosQueueMappingCos4	OBJECT-TYPE
		SYNTAX		Integer32 ( 0 .. 7 )
		MAX-ACCESS	read-write
		STATUS		current
		DESCRIPTION	"CoS queue mapping. Default is 4."    
		DEFVAL		{ 4 }
		::= { iswCosQueMapping 5 }  
--6   
	iswCosQueueMappingCos5	OBJECT-TYPE
		SYNTAX		Integer32 ( 0 .. 7 )
		MAX-ACCESS	read-write
		STATUS		current
		DESCRIPTION	"CoS queue mapping. Default is 5."    
		DEFVAL		{ 5 }
		::= { iswCosQueMapping 6 }  
--7	  
	iswCosQueueMappingCos6	OBJECT-TYPE
		SYNTAX		Integer32 ( 0 .. 7 )
		MAX-ACCESS	read-write
		STATUS		current
		DESCRIPTION	"CoS queue mapping. Default is 6."     
		DEFVAL		{ 6 }
		::= { iswCosQueMapping 7 }  
--8	  
	iswCosQueueMappingCos7	OBJECT-TYPE
		SYNTAX		Integer32 ( 0 .. 7 )
		MAX-ACCESS	read-write
		STATUS		current
		DESCRIPTION	"CoS queue mapping. Default is 7."    
		DEFVAL		{ 7 }
		::= { iswCosQueMapping 8 }
--
	iswSchedulingProfileTable	OBJECT-TYPE
		SYNTAX		SEQUENCE OF IswSchedulingProfileEntry
		MAX-ACCESS	not-accessible
		STATUS		current
		DESCRIPTION	"Scheduling profile table. Max entry size: 8."
		::= { iswQueScheduler 2 }
		
	iswSchedulingProfileEntry	OBJECT-TYPE
		SYNTAX		IswSchedulingProfileEntry
		MAX-ACCESS	not-accessible
		STATUS		current
		DESCRIPTION	"Scheduling profile entry."
		INDEX		{ iswSchedulingProfileId }
		::= { iswSchedulingProfileTable 1 }
		
	IswSchedulingProfileEntry ::= SEQUENCE{
		iswSchedulingProfileId		Integer32,
		iswSchedulingMode			Integer32,
		iswSchedulingQ7Weight		Integer32,
		iswSchedulingQ6Weight		Integer32,
		iswSchedulingQ5Weight		Integer32,
		iswSchedulingQ4Weight		Integer32,
		iswSchedulingQ3Weight		Integer32,
		iswSchedulingQ2Weight		Integer32,
		iswSchedulingQ1Weight		Integer32,
		iswSchedulingQ0Weight		Integer32
	} 
--1
	iswSchedulingProfileId	OBJECT-TYPE
		SYNTAX		Integer32 ( 1 .. 8 ) 
		MAX-ACCESS	not-accessible
		STATUS		current
		DESCRIPTION	"Scheduling profile ID. Profile ID 1 is default profile and read-only, can't be set."
		::= { iswSchedulingProfileEntry 1 }
--2    
	iswSchedulingMode	OBJECT-TYPE
		SYNTAX		Integer32 { sp (1), sp-wrr (2), wrr (3) }
		MAX-ACCESS	read-write
		STATUS		current
		DESCRIPTION	"Scheduling mode. Default value is sp (1)."      
		DEFVAL		{ 1 }
		::= { iswSchedulingProfileEntry 2 }
--3
	iswSchedulingQ7Weight	OBJECT-TYPE
		SYNTAX		Integer32 ( 1 .. 255 )
		MAX-ACCESS	read-write
		STATUS		current
		DESCRIPTION	"Scheduling queue 7 weight. Default value is 1."     
		DEFVAL		{ 1 }
		::= { iswSchedulingProfileEntry 3 }
--4  
	iswSchedulingQ6Weight	OBJECT-TYPE
		SYNTAX		Integer32 ( 1 .. 255 )
		MAX-ACCESS	read-write
		STATUS		current
		DESCRIPTION	"Scheduling queue 6 weight. Default value is 1."     
		DEFVAL		{ 1 }
		::= { iswSchedulingProfileEntry 4 }
--5  
	iswSchedulingQ5Weight	OBJECT-TYPE
		SYNTAX		Integer32 ( 1 .. 255 )
		MAX-ACCESS	read-write
		STATUS		current
		DESCRIPTION	"Scheduling queue 5 weight. Default value is 1."       
		DEFVAL		{ 1 }
		::= { iswSchedulingProfileEntry 5 }  
--6  
	iswSchedulingQ4Weight	OBJECT-TYPE
		SYNTAX		Integer32 ( 1 .. 255 )
		MAX-ACCESS	read-write
		STATUS		current
		DESCRIPTION	"Scheduling queue 4 weight. Default value is 1."     
		DEFVAL		{ 1 }
		::= { iswSchedulingProfileEntry 6 }  
--7 
	iswSchedulingQ3Weight	OBJECT-TYPE
		SYNTAX		Integer32 ( 1 .. 255 )
		MAX-ACCESS	read-write
		STATUS		current
		DESCRIPTION	"Scheduling queue 3 weight. Default value is 1."       
		DEFVAL		{ 1 }
		::= { iswSchedulingProfileEntry 7 }  
--8  
	iswSchedulingQ2Weight	OBJECT-TYPE
		SYNTAX		Integer32 ( 1 .. 255 )
		MAX-ACCESS	read-write
		STATUS		current
		DESCRIPTION	"Scheduling queue 1 weight. Default value is 1."     
		DEFVAL		{ 1 }
		::= { iswSchedulingProfileEntry 8 }
--9   
	iswSchedulingQ1Weight	OBJECT-TYPE
		SYNTAX		Integer32 ( 1 .. 255 )
		MAX-ACCESS	read-write
		STATUS		current
		DESCRIPTION	"Scheduling queue 1 weight. Default value is 1."      
		DEFVAL		{ 1 }
		::= { iswSchedulingProfileEntry 9 }
--10   
	iswSchedulingQ0Weight	OBJECT-TYPE
		SYNTAX		Integer32 ( 1 .. 255 )
		MAX-ACCESS	read-write
		STATUS		current
		DESCRIPTION	"Scheduling queue 0 weight. Default value is 1."     
		DEFVAL		{ 1 }
		::= { iswSchedulingProfileEntry 10 }
--
	iswSchedulingBindTable		OBJECT-TYPE
		SYNTAX		SEQUENCE OF IswSchedulingBindEntry
		MAX-ACCESS	not-accessible
		STATUS		current
		DESCRIPTION	"Scheduling bind table. Max entry size: port number."
		::= { iswQueScheduler 3 }
		
	iswSchedulingBindEntry	OBJECT-TYPE
		SYNTAX		IswSchedulingBindEntry
		MAX-ACCESS	not-accessible
		STATUS		current
		DESCRIPTION	"Scheduling bind entry."
		INDEX		{ iswSchedulingBindPortId }
		::= { iswSchedulingBindTable 1 }
		
	IswSchedulingBindEntry ::= SEQUENCE{
		iswSchedulingBindPortId			IswGbeIndex,
		iswSchedulingBindProfileId		Integer32
	}	
--1    
	iswSchedulingBindPortId	OBJECT-TYPE
		SYNTAX		IswGbeIndex
		MAX-ACCESS	not-accessible
		STATUS		current
		DESCRIPTION	"Scheduling bind port ID."
		::= { iswSchedulingBindEntry 1 }
--2     
	iswSchedulingBindProfileId	OBJECT-TYPE
		SYNTAX		Integer32 ( 1 .. 8 )
		MAX-ACCESS	read-write
		STATUS		current
		DESCRIPTION	"Scheduling profile ID. Default value is 1."    
		DEFVAL		{ 1 }
		::= { iswSchedulingBindEntry 2 }
--
	iswAclProfileTable	OBJECT-TYPE
		SYNTAX		SEQUENCE OF IswAclProfileEntry
		MAX-ACCESS	not-accessible
		STATUS		current
		DESCRIPTION	"Acl profile table. Max entry size: 20.
					Each entry will be referred to from iswAclBindTable.
					Once Profile is binded in iswAclBindProfileIndex, it means the relative entries on profile table and entry table can't be deleted/modified.
					If entries are deleted, the relative entries on iswAclEntryTable will be deleted too.
					Profile 1 is a default entry and can't be modified and can't be deleted.
					"
		::= { iswAcl 1 }
		
	iswAclProfileEntry	OBJECT-TYPE
		SYNTAX		IswAclProfileEntry
		MAX-ACCESS	not-accessible
		STATUS		current
		DESCRIPTION	"Acl profile entry."
		INDEX		{ iswAclProfileIndex }
		::= { iswAclProfileTable 1 }  
		
	IswAclProfileEntry ::= SEQUENCE{
		iswAclProfileIndex			Integer32,
		iswAclProfileName			OCTET STRING,
		iswAclProfileRowStatus		RowStatus
	}
--1	
	iswAclProfileIndex	OBJECT-TYPE
		SYNTAX		Integer32 ( 1 .. 10 )
		MAX-ACCESS	not-accessible
		STATUS		current
		DESCRIPTION	"Acl profile index. Use iswNextAclProfileIndex to get next available index."
		::= { iswAclProfileEntry 1 }  
--2	
	iswAclProfileName	OBJECT-TYPE
		SYNTAX		OCTET STRING ( SIZE ( 0..31 ) )
		MAX-ACCESS	read-create
		STATUS		current
		DESCRIPTION	"Acl profile name. Default is empty."
		::= { iswAclProfileEntry 2 } 
--3
	iswAclProfileRowStatus	OBJECT-TYPE
		SYNTAX		RowStatus
		MAX-ACCESS	read-create
		STATUS		current
		DESCRIPTION	"Acl profile RowStatus."
		::= { iswAclProfileEntry 3 } 
--
	iswAclEntryTable	OBJECT-TYPE
		SYNTAX		SEQUENCE OF IswAclEntryEntry
		MAX-ACCESS	not-accessible
		STATUS		current
		DESCRIPTION	"Acl entry table. Max entry size: 608(19x32). 
					1 ACL profile contains max 32 ACL entries. But profile 1 has no entry.
					Once Profile is binded in iswAclBindProfileIndex, it means the relative entries on profile table and entry table can't be deleted/modified.
				"
		::= { iswAcl 2 }
		
	iswAclEntryEntry	OBJECT-TYPE
		SYNTAX		IswAclEntryEntry
		MAX-ACCESS	not-accessible
		STATUS		current
		DESCRIPTION	"Acl entry entry."
		INDEX		{ iswAclEntryProfileIndex, iswAclEntryIndex }
		::= { iswAclEntryTable 1 }    
		
	IswAclEntryEntry ::= SEQUENCE{
		iswAclEntryProfileIndex		Integer32,
		iswAclEntryIndex			Integer32,
		iswAclEntryType				Integer32,
		iswAclEntryParam1			Gauge32,
		iswAclEntryParam2			Gauge32,
		iswAclEntryParam3			Gauge32,
		iswAclEntryParam4			Gauge32,
		iswAclEntryParam5			Gauge32,
		iswAclEntryParam6			Gauge32,
		iswAclEntryParam7			Gauge32,
		iswAclEntryParam8			Gauge32,
		iswAclEntryParam9			Gauge32,
		iswAclEntryParam10			Gauge32,
		iswAclEntryAction			Integer32,
		iswAclEntryActionParam1		Integer32,
		iswAclEntryRowStatus		RowStatus
	}
--1
	iswAclEntryProfileIndex	OBJECT-TYPE
		SYNTAX		Integer32 ( 2 .. 10 )
		MAX-ACCESS	not-accessible
		STATUS		current
		DESCRIPTION	"Acl profile index."
		::= { iswAclEntryEntry 1 }
--2
	iswAclEntryIndex	OBJECT-TYPE
		SYNTAX		Integer32 ( 1 .. 16 )
		MAX-ACCESS	not-accessible
		STATUS		current
		DESCRIPTION	"Acl entry index."
		::= { iswAclEntryEntry 2 }
--3
	iswAclEntryType		OBJECT-TYPE
		SYNTAX		Integer32 { mac (0), ipv4 (1), l4port (2), tos (3) }
		MAX-ACCESS	read-create
		STATUS		current
		DESCRIPTION	"Acl entry type.
					mac type need to set iswAclEntryParam1~iswAclEntryParam10.
					ipv4 type need to set iswAclEntryParam1~iswAclEntryParam5.
					l4port type need to set iswAclEntryParam1~iswAclEntryParam7.
					tos type need to set iswAclEntryParam1~iswAclEntryParam6.
					"
		DEFVAL		{ 0 }
		::= { iswAclEntryEntry 3 }
--4
	iswAclEntryParam1	OBJECT-TYPE
		SYNTAX		Gauge32
		MAX-ACCESS	read-create
		STATUS		current
		DESCRIPTION	"Acl entry parameter 1.
					If aclEntryType is MAC, this parameter means VLAN ID. range is 0 ~ 4094.
					The default value is 0, means Any (Don't care).
					
					If aclEntryType is IPv4, this parameter means Source IP.
					Range is 0 ~ 0xffffffff, 0.0.0.0 ~ 255.255.255.255.
					
					If aclEntryType is L4PORT, this parameter means Protocol.
					Allow value is 6(TCP) and 17(UDP)
					
					If aclEntryType is TOS, this parameter means Source IP.
					Range is 0 ~ 0xffffffff, 0.0.0.0 ~ 255.255.255.255
					"
		DEFVAL		{ 0 }
		::= { iswAclEntryEntry 4 }
--5
	iswAclEntryParam2	OBJECT-TYPE
		SYNTAX		Gauge32
		MAX-ACCESS	read-write
		STATUS		current
		DESCRIPTION	"Acl entry parameter 2.
					If aclEntryType is MAC, this parameter means High 3 bytes of Source MAC.
					Range is 0 ~ 0x00ffffff. For example: 00:11:22:33:44:55.
					The High 3 bytes are 00:11:22 as 0x00001122. The first high byte is ignored.
					
					If aclEntryType is IPv4, this parameter means Source IP mask.
					Range is 0 ~ 0xffffffff, 0.0.0.0 ~ 255.255.255.255.
					When mask is 0 is meaning Any.
					
					If aclEntryType is L4PORT, this parameter means Source IP.
					Range is 0 ~ 0xffffffff, 0.0.0.0 ~ 255.255.255.255.
					
					If aclEntryType is TOS, this parameter means Source IP mask
					range is 0 ~ 0xffffffff, 0.0.0.0 ~ 255.255.255.255.
					If mask is 0, means Any (Don't care).
					"
		DEFVAL		{ 0 }
		::= { iswAclEntryEntry 5 }
--6
	iswAclEntryParam3	OBJECT-TYPE
		SYNTAX		Gauge32
		MAX-ACCESS	read-write
		STATUS		current
		DESCRIPTION	"Acl entry parameter 3.
					If aclEntryType is MAC, this parameter means Low 3 bytes of Source MAC.
					Range is 0 ~ 0x00ffffff. For example: 00:11:22:33:44:55.
					The Low 3 bytes are 33:44:55 as 0x00334455. The first high byte is ignored.

					If aclEntryType is IPv4, this parameter means destination IP.
					Range is 0 ~ 0xffffffff, 0.0.0.0 ~ 255.255.255.255

					If aclEntryType is L4PORT, this parameter means source IP mask.
					Range is 0 ~ 0xffffffff, 0.0.0.0 ~ 255.255.255.255.
					When mask is 0, means Any (Don't care).

					If aclEntryType is TOS, this parameter means destination IP.
					Range is 0 ~ 0xffffffff, 0.0.0.0 ~ 255.255.255.255
					"
		DEFVAL		{ 0 }
		::= { iswAclEntryEntry 6 }  
--7
	iswAclEntryParam4	OBJECT-TYPE
		SYNTAX		Gauge32
		MAX-ACCESS	read-write
		STATUS		current
		DESCRIPTION	"Acl entry parameter 4.
					If aclEntryType is MAC, this parameter is meaning High 3 bytes of Source MAC mask.
					Range is 0 ~ 0x00ffffff. For example: FF:FF:FF:00:00:00.
					The High 3 bytes are FF:FF:FF as 0x00ffffff. The first high byte is ignored.

					If aclEntryType is IPv4, this parameter means destination IP mask.
					Range is 0 ~ 0xffffffff, 0.0.0.0 ~ 255.255.255.255
					When mask is 0, means Any (Don't care).

					If aclEntryType is L4PORT, this parameter means destination IP.
					Range is 0 ~ 0xffffffff, 0.0.0.0 ~ 255.255.255.255

					If aclEntryType is TOS, this parameter means destination IP mask.
					Range is 0 ~ 0xffffffff, 0.0.0.0 ~ 255.255.255.255
					When mask is 0, means Any (Don't care).
					"
		DEFVAL		{ 0 }
		::= { iswAclEntryEntry 7 }
--8
	iswAclEntryParam5	OBJECT-TYPE
		SYNTAX		Gauge32
		MAX-ACCESS	read-write
		STATUS		current
		DESCRIPTION	"Acl entry parameter 5.
					If aclEntryType is MAC, this parameter means Low 3 bytes of Source MAC mask.
					Range is 0 ~ 0x00ffffff. For example: FF:FF:FF:00:00:00.
					The Low 3 bytes are 00:00:00 as 0x00000000. The first high byte is ignored.
                                
					If aclEntryType is IPv4, this parameter means Protocol
					Range is 0..255, the default value is 0, means Any (Don't care).

					If aclEntryType is L4PORT, this parameter means destination IP mask.
					Range is 0 ~ 0xffffffff, 0.0.0.0 ~ 255.255.255.255
					When mask is 0 means Any.

					If aclEntryType is TOS, this parameter means ToS Type
					allow range is Precedence(0),TOS(1),DSCP(2) [When aclEntryType is TOS, the default value is Precedence]
					When bind acl profile to bridge port should check if the ToS Type and coresponding ToS value
					range is valid. Precedence range is 0~7|255, ToS range is 0~15|255, DSCP range is 0~63|255.
					"
		DEFVAL		{ 0 }
		::= { iswAclEntryEntry 8 }
--9
	iswAclEntryParam6	OBJECT-TYPE
		SYNTAX		Gauge32
		MAX-ACCESS	read-write
		STATUS		current
		DESCRIPTION	"Acl entry parameter 6.
					If aclEntryType is MAC, this parameter means High 3 bytes of Destination MAC.
					Range is 0 ~ 0x00ffffff. For example: 00:11:22:33:44:55.
					The High 3 bytes are 00:11:22 as 0x00001122. The first high byte is ignored.

					If aclEntryType is L4PORT, this parameter means L4 source port number.
					Range is 0 ~ 65535
					The default value is 0 which means Any (Don't care)

					If aclEntryType is TOS, this parameter means ToS Value
					When aclEntryParam5 is TOSTYPE_PRECEDENCE, allow range is (0..7 | 255).
					When aclEntryParam5 is TOSTYPE_TOS, allow range is (0..15 | 255).
					When aclEntryParam5 is TOSTYPE_DSCP, allow range is (0..63 | 255).
					When aclEntryParam6 is 255, it means aclEntryParam5 is any.
					"
		DEFVAL		{ 0 }
		::= { iswAclEntryEntry 9 }
--10
	iswAclEntryParam7	OBJECT-TYPE
		SYNTAX		Gauge32
		MAX-ACCESS	read-write
		STATUS		current
		DESCRIPTION	"Acl entry parameter 7.
					If aclEntryType is MAC, this parameter means Low 3 bytes of Destination MAC.
					Range is 0 ~ 0x00ffffff. For example: 00:11:22:33:44:55.
					The Low 3 bytes are 33:44:55 as 0x00334455. The first high byte is ignored.

					If aclEntryType is L4PORT, this parameter means L4 destination port number.
					Range is 0 ~ 65535
					The default value is 0, it means Any (Don't care).
					"
		DEFVAL		{ 0 }
		::= { iswAclEntryEntry 10 }
--11
	iswAclEntryParam8	OBJECT-TYPE
		SYNTAX		Gauge32
		MAX-ACCESS	read-write
		STATUS		current
		DESCRIPTION	"Acl entry parameter 8.
					If aclEntryType is MAC, this parameter means High 3 bytes of Destination MAC mask.
					Range is 0 ~ 0x00ffffff. For example: FF:FF:FF:00:00:00.
					The High 3 bytes are FF:FF:FF as 0x00ffffff. The first high byte is ignored."        
		DEFVAL		{ 0 }
		::= { iswAclEntryEntry 11 }
--12
	iswAclEntryParam9	OBJECT-TYPE
		SYNTAX		Gauge32
		MAX-ACCESS	read-write
		STATUS		current
		DESCRIPTION	"Acl entry parameter 9.
					If aclEntryType is MAC, this parameter means Low 3 bytes of Destination MAC mask.
					Range is 0 ~ 0x00ffffff. For example: FF:FF:FF:00:00:00.
					The Low 3 bytes are 00:00:00 as 0x00000000. The first high byte is ignored."
		DEFVAL		{ 0 }
		::= { iswAclEntryEntry 12 }
--13
	iswAclEntryParam10	OBJECT-TYPE
		SYNTAX		Gauge32
		MAX-ACCESS	read-write
		STATUS		current
		DESCRIPTION	"Acl entry parameter 10.
					If aclEntryType is MAC, this parameter means EtherType.
					Range is 0 and 0x05dd ~ 0xfffe. Use Hex format for UI input.
					The default value is 0, it means Any (Don't care)."
		DEFVAL		{ 0 }
		::= { iswAclEntryEntry 13 }
--14
	iswAclEntryAction	OBJECT-TYPE
		SYNTAX		Integer32 { deny (0), permit (1), queue (2), cos (3), copyFrame (4) }
		MAX-ACCESS	read-write
		STATUS		current
		DESCRIPTION	"Acl entry action type.
					tos type need to set iswAclEntryActionParam1.
					queue type need to set iswAclEntryActionParam1.
					"
		DEFVAL		{ 0 }
		::= { iswAclEntryEntry 14 }
--15	
	iswAclEntryActionParam1 OBJECT-TYPE
		SYNTAX		Integer32 ( 0 .. 7 )
		MAX-ACCESS	read-write
		STATUS		current
		DESCRIPTION	"Acl entry action parameter. CoS 0 ~ 7 for action type is CoS, Queue 0 ~ 7 for action type is Queue."           
		DEFVAL		{ 0 }
		::= { iswAclEntryEntry 15 }
--16
	iswAclEntryRowStatus	OBJECT-TYPE
		SYNTAX		RowStatus
		MAX-ACCESS	read-create
		STATUS		current
		DESCRIPTION	"Acl entry RowStatus."
		::= { iswAclEntryEntry 16 }
--
	iswAclBindTable		OBJECT-TYPE
		SYNTAX		SEQUENCE OF IswAclBindEntry
		MAX-ACCESS	not-accessible
		STATUS		current
		DESCRIPTION	"Acl bind table. Max entry size: port number."
		::= { iswAcl 3 }
		
	iswAclBindEntry	OBJECT-TYPE
		SYNTAX		IswAclBindEntry
		MAX-ACCESS	not-accessible
		STATUS		current
		DESCRIPTION	"Acl bind entry."
		INDEX		{ iswAclBindPortIndex }
		::= { iswAclBindTable 1 }
		
	IswAclBindEntry ::= SEQUENCE{
		iswAclBindPortIndex				IswGbeIndex,
		iswAclBindProfileIndex			Integer32,
		iswAclBindDefaultAclRule		Integer32
	}
--1
	iswAclBindPortIndex	OBJECT-TYPE
		SYNTAX		IswGbeIndex
		MAX-ACCESS	not-accessible
		STATUS		current
		DESCRIPTION	"Port index."
		::= { iswAclBindEntry 1 }  
--2   
	iswAclBindProfileIndex	OBJECT-TYPE
		SYNTAX		Integer32 ( 1 .. 10 )
		MAX-ACCESS	read-write
		STATUS		current
		DESCRIPTION	"ACL profile index. Default value is 1."
		DEFVAL		{ 1 }
		::= { iswAclBindEntry 2 }  
--3     
	iswAclBindDefaultAclRule	OBJECT-TYPE
		SYNTAX		Integer32 { permit (0), deny (1) }
		MAX-ACCESS	read-write
		STATUS		current
		DESCRIPTION	"Acl bind default Acl rule. Default value is permit (0)." 
		DEFVAL		{ 0 }
		::= { iswAclBindEntry 3 }  
--
--1
	iswMirrorAnalyzerPortMode	OBJECT-TYPE
		SYNTAX		Integer32 { disable (0), enable (1) }
		MAX-ACCESS	read-write
		STATUS		current
		DESCRIPTION	"Mirror analyzer port mode. Default is disable (0)."    
		DEFVAL		{ 0 }
		::= { iswAclMirrorAnalyzerPort 1 }
--2
	iswMirrorAnalyzerPortId		OBJECT-TYPE
		SYNTAX		IswGbeIndex
		MAX-ACCESS	read-write
		STATUS		current
		DESCRIPTION	"Mirror analyzer port ID. Default value is 1."     
		DEFVAL		{ 1 }
		::= { iswAclMirrorAnalyzerPort 2 }
--
--1
	iswMtuJumboMode	OBJECT-TYPE
		SYNTAX		Integer32 { disable (0), enable (1) }
		MAX-ACCESS	read-write
		STATUS		current
		DESCRIPTION	"Mtu jumbo frame mode. Default value is disable (0)."   
		DEFVAL		{ 0 }
		::= { iswJumboFrame 1 }  
--2
	iswMtuJumboSize	OBJECT-TYPE
		SYNTAX		Integer32 ( 1536 .. 10240 )
		MAX-ACCESS	read-write
		STATUS		current
		DESCRIPTION	"Mtu jumbo frame size. Default value is 1536."   
		DEFVAL		{ 1536 }
		::= { iswJumboFrame 2 } 
--
	iswPortMirrorTable		OBJECT-TYPE
		SYNTAX		SEQUENCE OF IswPortMirrorEntry
		MAX-ACCESS	not-accessible
		STATUS		current
		DESCRIPTION	"PortMirror table. Max entry size: port number."
		::= { iswEnetPort 3 }
		
	iswPortMirrorEntry	OBJECT-TYPE
		SYNTAX		IswPortMirrorEntry
		MAX-ACCESS	not-accessible
		STATUS		current
		DESCRIPTION	"PortMirror entry."
		INDEX		{ iswProfileIndex }
		::= { iswPortMirrorTable 1 }
		
	IswPortMirrorEntry ::= SEQUENCE{
		iswProfileIndex					IswPFIndex,
		iswPortMirrorMode				Integer32,
		iswPortMirrorAnalyzerPortID		IswGbeIndex
	}
--1
	iswProfileIndex	OBJECT-TYPE
		SYNTAX		IswPFIndex
		MAX-ACCESS	not-accessible
		STATUS		current
		DESCRIPTION	"Profile Index."   
		::= { iswPortMirrorEntry 1 } 
--2
	iswPortMirrorMode	OBJECT-TYPE
		SYNTAX		Integer32 { disable (0), enable (1) }
		MAX-ACCESS	read-write
		STATUS		current
		DESCRIPTION	"Port mirror mode. Default value is disable (0).
					 When mode is enable (1), iswPortMirrorPortID should not equal as iswPortMirrorTxAnalyzerPortID or iswPortMirrorRxAnalyzerPortID."   
		DEFVAL		{ 0 }
		::= { iswPortMirrorEntry 2 } 
--3
	iswPortMirrorAnalyzerPortID	OBJECT-TYPE
		SYNTAX		IswGbeIndex
		MAX-ACCESS	read-write
		STATUS		current
		DESCRIPTION	"Port mirror port ID. Default value is 1."   
		DEFVAL		{ 1 }
		::= { iswPortMirrorEntry 3 } 

	iswPortMirrorTxRxTable	OBJECT-TYPE  
		SYNTAX      SEQUENCE OF IswPortMirrorTxRxEntry
		MAX-ACCESS	not-accessible
		STATUS		current
		DESCRIPTION	"iswPortMirrorTxRxTable"
		::= { iswEnetPort 4 }
---
	iswPortMirrorTxRxEntry OBJECT-TYPE
		SYNTAX		IswPortMirrorTxRxEntry
		MAX-ACCESS	not-accessible
		STATUS		current
		DESCRIPTION	"iswPortMirrorTxRxEntry"
		INDEX		{ iswPortMirrorSourcePortIndex }
		::= { iswPortMirrorTxRxTable 1 }
---    
	IswPortMirrorTxRxEntry ::= SEQUENCE{
		iswPortMirrorSourcePortIndex		IswGbeIndex,
		iswPortMirrorTxProfileIndex		Integer32,
		iswPortMirrorRxProfileIndex		Integer32
	}
---
	iswPortMirrorSourcePortIndex	OBJECT-TYPE
		SYNTAX		IswGbeIndex
		MAX-ACCESS	not-accessible	
		STATUS		current
		DESCRIPTION	"Port index to be monitored."
		::= { iswPortMirrorTxRxEntry 1 }
---
	iswPortMirrorTxProfileIndex	OBJECT-TYPE
		SYNTAX		Integer32 ( 0 .. 7 )
		MAX-ACCESS	read-write	
		STATUS		current
		DESCRIPTION	"Set Tx profile index, Tx frames of current port would be the source being monitored by Analyzer Port.
					Value range is 1~7 and none(0). Default is none."
		DEFVAL { 0 }
		::= { iswPortMirrorTxRxEntry 2 }
---
	iswPortMirrorRxProfileIndex	OBJECT-TYPE
		SYNTAX		Integer32 ( 0 .. 7 )
		MAX-ACCESS	read-write	
		STATUS		current
		DESCRIPTION	"Set Rx profile index, Rx frames of current port would be the source being monitored by Analyzer Port.
					Value range is 1~7 and none(0). Default is none."
		DEFVAL { 0 }
		::= { iswPortMirrorTxRxEntry 3 }
---
--1
	iswRingProtectionTable		OBJECT-TYPE
		SYNTAX		SEQUENCE OF IswRingProtectionEntry
		MAX-ACCESS	not-accessible
		STATUS		current
		DESCRIPTION	"Ring Protection Table. Max entry size: 3."
		::= { iswRingProtect 1 }
		
	iswRingProtectionEntry	OBJECT-TYPE
		SYNTAX		IswRingProtectionEntry
		MAX-ACCESS	not-accessible
		STATUS		current
		DESCRIPTION	"Ring Protection entry."
		INDEX		{ iswRingProtectRingIndex }
		::= { iswRingProtectionTable 1 }
		
	IswRingProtectionEntry ::= SEQUENCE{
		iswRingProtectRingIndex				Integer32,
		iswRingProtectRingId				Integer32,  
		iswRingProtectRingMode				Integer32,
		iswRingProtectRingRole				Integer32,
		iswRingProtectInterConnectMode			Integer32,
		iswRingProtectRingNode1				IswGbeIndex,
		iswRingProtectRingNode2				IswGbeIndex,
		iswRingProtectRingNode1SFmode			Integer32,
		iswRingProtectRingNode2SFmode			Integer32,
		iswRingProtectCurrentMasterProtectPort		Integer32,
		iswRingProtectGuardTimerDef			Integer32,
		iswRingProtectRingState				Integer32,
		iswRingProtectRingNode1Behavior			Integer32,
		iswRingProtectRingNode2Behavior			Integer32,
		iswRingProtectRingNode1LinkStatus		Integer32,
		iswRingProtectRingNode2LinkStatus		Integer32
	}

	iswRingProtectRingIndex	OBJECT-TYPE
		SYNTAX		Integer32  ( 1 .. 3 )
		MAX-ACCESS	not-accessible
		STATUS		current
		DESCRIPTION	"Index of Ring group. The range is 1, 2 or 3."
		::= { iswRingProtectionEntry 1 }  

	iswRingProtectRingId	OBJECT-TYPE
		SYNTAX		Integer32  ( 0..255 )
		MAX-ACCESS	read-write
		STATUS		current
		DESCRIPTION	"Ring id for the ring group. Default value is 1 for Ring group 1, 2 for Ring group 2 and 3 for Ring group 3.
					RingId for All Ring group can not be the same when iswRingProtectRingMode is enable."
		::= { iswRingProtectionEntry 2 }

	iswRingProtectRingMode	OBJECT-TYPE
		SYNTAX		Integer32 { disable (0), enable (1) }
		MAX-ACCESS	read-write
		STATUS		current
		DESCRIPTION	"Enable/Disable Ring Protect on the specify ring group.
					If iswStpBridgeModeSet is enabled, set this field to enable will be rejected."
		DEFVAL		{ 0 }
		::= { iswRingProtectionEntry 3 }

	iswRingProtectRingRole	OBJECT-TYPE
		SYNTAX		Integer32 { master (1), slave (2) }
		MAX-ACCESS	read-write
		STATUS		current
		DESCRIPTION	"The Ring role, master or slave."
		DEFVAL		{ 2 }
		::= { iswRingProtectionEntry 4 }

	iswRingProtectInterConnectMode	OBJECT-TYPE
		SYNTAX		Integer32 { disable (0), enable (1) }
		MAX-ACCESS	read-write
		STATUS		current
		DESCRIPTION	"Enable/Disable Inter-connect mode on the specify ring group.
					If two ring's inter-connect mode is enable both, one of the ring node could be the same port."
		DEFVAL		{ 0 }
		::= { iswRingProtectionEntry 5 }
		
	iswRingProtectRingNode1	OBJECT-TYPE
		SYNTAX		IswGbeIndex
		MAX-ACCESS	read-write
		STATUS		current
		DESCRIPTION	"The port which connect to Ring topology as Node1.
					Default:1 for Ring group 1
					Default:3 for Ring group 2
					Default:5 for Ring group 3
					All the ring nodes should not be the same port for the ring mode is enable.
					Only if two ring's inter-connect mode is enable both, one of the ring node could be the same port.
					Port will be set to forward when iswRingProtectRingState is normal."
		::= { iswRingProtectionEntry 6 }
		
	iswRingProtectRingNode2		OBJECT-TYPE
		SYNTAX		IswGbeIndex
		MAX-ACCESS	read-write
		STATUS		current
		DESCRIPTION	"The port which connect to Ring topology as Node2.
					Default:2 for Ring group 1
					Default:4 for Ring group 2
					Default:6 for Ring group 3
					All the ring nodes should not be the same port for the ring mode is enable.
					Only if two ring's inter-connect mode is enable both, one of the ring node could be the same port.
					Port will be set to block when iswRingProtectRingState is normal."
		::= { iswRingProtectionEntry 7 }

	iswRingProtectRingNode1SFmode	OBJECT-TYPE
		SYNTAX		Integer32 { sf (0), non-sf (1) }
		MAX-ACCESS	read-write
		STATUS		current
		DESCRIPTION	"When iswRingProtectInterConnectMode is enable mode, iswRingProtectRingNode1SFmode could be set as sf or non-sf.
					When iswRingProtectInterConnectMode is disable mode, iswRingProtectRingNode1SFmode only accept non-sf."
		DEFVAL		{ 0 }
		::= { iswRingProtectionEntry 8 }

	iswRingProtectRingNode2SFmode	OBJECT-TYPE
		SYNTAX		Integer32 { sf (0), non-sf (1) }
		MAX-ACCESS	read-write
		STATUS		current
		DESCRIPTION	"When iswRingProtectInterConnectMode is enable mode, iswRingProtectRingNode2SFmode could be set as sf or non-sf.
					When iswRingProtectInterConnectMode is disable mode, iswRingProtectRingNode2SFmode only accept non-sf."
		DEFVAL		{ 0 }
		::= { iswRingProtectionEntry 9 }

	iswRingProtectCurrentMasterProtectPort	OBJECT-TYPE
		SYNTAX		Integer32 { node-one (1), node-two (2) }
		MAX-ACCESS	read-write
		STATUS		current
		DESCRIPTION	"When iswRingProtectRingRole is master mode, iswRingProtectCurrentMasterProtectPort only accept as node-two."
		DEFVAL		{ 2 }
		::= { iswRingProtectionEntry 10 }

	iswRingProtectGuardTimerDef	OBJECT-TYPE
		SYNTAX		Integer32 ( 10 .. 3600 )
		UNITS			"second"
		MAX-ACCESS	read-write
		STATUS		current
		DESCRIPTION	"A timer for ring group change back from protect state to normal state.
					The timer is working when all of the port are link up not broken. 
					 Range is 10 ~ 3600, Default is 10 seconds."
		DEFVAL		{ 10 }
		::= { iswRingProtectionEntry 11 }

	iswRingProtectRingState		OBJECT-TYPE
		SYNTAX		Integer32 { normal (1), protect (2) }
		MAX-ACCESS	read-only
		STATUS		current
		DESCRIPTION	"Ring protection state of the specify ring group.
					Normal means no link error and protection link is blocking.
					Protect means link error occurs and protection link is forwarding."
		::= { iswRingProtectionEntry 12 }

	iswRingProtectRingNode1Behavior		OBJECT-TYPE
		SYNTAX		Integer32 { blocking (1), forwarding (2) }
		MAX-ACCESS	read-only
		STATUS		current
		DESCRIPTION	"Ring note 1 port behavior."
		::= { iswRingProtectionEntry 13 }

	iswRingProtectRingNode2Behavior		OBJECT-TYPE
		SYNTAX		Integer32 { blocking (1), forwarding (2) }
		MAX-ACCESS	read-only
		STATUS		current
		DESCRIPTION	"Ring note 2 port behavior."
		::= { iswRingProtectionEntry 14 }

	iswRingProtectRingNode1LinkStatus		OBJECT-TYPE
		SYNTAX		Integer32 { link-down (0), link-up (2) }
		MAX-ACCESS	read-only
		STATUS		current
		DESCRIPTION	"Ring note 1 port status."
		::= { iswRingProtectionEntry 15 }

	iswRingProtectRingNode2LinkStatus		OBJECT-TYPE
		SYNTAX		Integer32 { link-down (0), link-up (2) }
		MAX-ACCESS	read-only
		STATUS		current
		DESCRIPTION	"Ring note 2 port status."
		::= { iswRingProtectionEntry 16 }
--2
	iswRingDiscoveryTable		OBJECT-TYPE
		SYNTAX		SEQUENCE OF IswRingDiscoveryEntry
		MAX-ACCESS	not-accessible
		STATUS		current
		DESCRIPTION	"Ring Protection Table. Max entry size: 3."
		::= { iswRingProtect 2 }
		
	iswRingDiscoveryEntry	OBJECT-TYPE
		SYNTAX		IswRingDiscoveryEntry
		MAX-ACCESS	not-accessible
		STATUS		current
		DESCRIPTION	"Ring Protection entry."
		INDEX		{ iswRingDiscoveryRingIndex }
		::= { iswRingDiscoveryTable 1 }
		
	IswRingDiscoveryEntry ::= SEQUENCE{
		iswRingDiscoveryRingIndex			Integer32,
		iswRingDiscoveryTopologyTimerMode		Integer32,
		iswRingDiscoveryTopologyTimerDef		Integer32,
		iswRingDiscoveryPort1NeighborMac		PhysAddress,
		iswRingDiscoveryPort1NeighborPort		IswGbeIndex,
		iswRingDiscoveryPort2NeighborMac		PhysAddress,
		iswRingDiscoveryPort2NeighborPort		IswGbeIndex,
		iswRingDiscoveryMasterMac			PhysAddress,
	}

	iswRingDiscoveryRingIndex	OBJECT-TYPE
		SYNTAX		Integer32  ( 1 .. 3 )
		MAX-ACCESS	not-accessible
		STATUS		current
		DESCRIPTION	"Index of Ring group. The range is 1, 2 or 3."
		::= { iswRingDiscoveryEntry 1 }  

	iswRingDiscoveryTopologyTimerMode	OBJECT-TYPE
		SYNTAX		Integer32 { disable (0), enable (1) }
		MAX-ACCESS	read-write
		STATUS		current
		DESCRIPTION	"Enable/Disable the ring neighbor discovery protocol. This parameter only for management purpose."
		DEFVAL		{ 0 }
		::= { iswRingDiscoveryEntry 2 }

	iswRingDiscoveryTopologyTimerDef	OBJECT-TYPE
		SYNTAX		Integer32 ( 10 .. 300 )
		MAX-ACCESS	read-write
		STATUS		current
		DESCRIPTION	"Discovery timer is the timeout value for count down to send ring neighbor.
				Discovery protocol to other ring nodes for ring topology discovery purpose."
		DEFVAL		{ 10 }
		::= { iswRingDiscoveryEntry 3 }

	iswRingDiscoveryPort1NeighborMac		OBJECT-TYPE
		SYNTAX		PhysAddress
		MAX-ACCESS	read-only
		STATUS		current
		DESCRIPTION	"The MAC address of the Node1's neighbor Switch in the ring
					If all octets are 0, then treat Neighbor MAC is Unknown.
					(Maybe the discovery mode is disabled or Neighbor is not found.)"
		::= { iswRingDiscoveryEntry 4 }

	iswRingDiscoveryPort1NeighborPort		OBJECT-TYPE
		SYNTAX		IswGbeIndex
		MAX-ACCESS	read-only
		STATUS		current
		DESCRIPTION	"The Port-id of Node1's neighbor switch in the ring.
					If iswRingDiscoveryPort1NeighborMac is 0x00, then this parameter is Unknown."
		::= { iswRingDiscoveryEntry 5 }

	iswRingDiscoveryPort2NeighborMac		OBJECT-TYPE
		SYNTAX		PhysAddress
		MAX-ACCESS	read-only
		STATUS		current
		DESCRIPTION	"The MAC address of the Node2's neighbor Switch in the ring
					If all octets are 0, then treat Neighbor MAC is Unknown.
					(Maybe the discovery mode is disabled or Neighbor is not found.)"
		::= { iswRingDiscoveryEntry 6 }

	iswRingDiscoveryPort2NeighborPort		OBJECT-TYPE
		SYNTAX		IswGbeIndex
		MAX-ACCESS	read-only
		STATUS		current
		DESCRIPTION	"The Port-id of Node2's neighbor switch in the ring.
					If iswRingDiscoveryPort1NeighborMac is 0x00, then this parameter is Unknown."
		::= { iswRingDiscoveryEntry 7 }

	iswRingDiscoveryMasterMac		OBJECT-TYPE
		SYNTAX		PhysAddress
		MAX-ACCESS	read-only
		STATUS		current
		DESCRIPTION	"The MAC address of the master Switch in the ring
					If all octets are 0, then treat master MAC is Unknown."
		::= { iswRingDiscoveryEntry 8 }

--		
	iswMgmtDefaultGateway	OBJECT-TYPE
		SYNTAX		IpAddress
		MAX-ACCESS	read-write
		STATUS		current
		DESCRIPTION	"Management default gateway. Be careful, if change it, the connection maybe broken."
		::= { iswGateway 1 }
--
	iswStaticRouteTable	OBJECT-TYPE
		SYNTAX		SEQUENCE OF IswStaticRouteEntry
		MAX-ACCESS	not-accessible
		STATUS		current
		DESCRIPTION	"Static Route table. Max entry size: 32."
		::= { iswLayer3 2 }
		
	iswStaticRouteEntry	OBJECT-TYPE
		SYNTAX		IswStaticRouteEntry
		MAX-ACCESS	not-accessible
		STATUS		current
		DESCRIPTION	"Static Route entry."
		INDEX		{ iswStaticRouteIndex }
		::= { iswStaticRouteTable 1 }
		
	IswStaticRouteEntry ::= SEQUENCE{
		iswStaticRouteIndex			Integer32,
		iswStaticRouteDstIp			IpAddress,
		iswStaticRouteNetmask		IpAddress,
		iswStaticRouteGateway		IpAddress,
		iswStaticRouteRowStatus		RowStatus
	}
--1 
	iswStaticRouteIndex	OBJECT-TYPE
		SYNTAX		Integer32 ( 1 .. 64 )
		MAX-ACCESS	not-accessible
		STATUS		current
		DESCRIPTION	"Static Route table index. Use iswNextStaticRouteIndex to get next available index."
		::= { iswStaticRouteEntry 1 }
--2  
	iswStaticRouteDstIp	OBJECT-TYPE
		SYNTAX		IpAddress
		MAX-ACCESS	read-create
		STATUS		current
		DESCRIPTION	"Static Route destination IP."
		::= { iswStaticRouteEntry 2 }
--3   
	iswStaticRouteNetmask	OBJECT-TYPE
		SYNTAX		IpAddress
		MAX-ACCESS	read-create
		STATUS		current
		DESCRIPTION	"Static Route netmask."
		::= { iswStaticRouteEntry 3 }  
--4      
	iswStaticRouteGateway	OBJECT-TYPE
		SYNTAX		IpAddress
		MAX-ACCESS	read-create
		STATUS		current
		DESCRIPTION	"Static Route gateway."
		::= { iswStaticRouteEntry 4 } 
--5      
	iswStaticRouteRowStatus	OBJECT-TYPE
		SYNTAX		RowStatus
		MAX-ACCESS	read-create
		STATUS		current
		DESCRIPTION	"Static Route RowStatus."
		::= { iswStaticRouteEntry 5 } 
--
	iswLayer3IpForward	OBJECT-TYPE
		SYNTAX		Integer32 { disable (0), enable (1) }
		MAX-ACCESS	read-write
		STATUS		current
		DESCRIPTION	"Enable/Disable Layer 3 ip routing/forward.
					This parameter is optional feature."
		DEFVAL		{0}
		::= { iswLayer3 3 }
-- 
	iswVrrpSystem	OBJECT-TYPE
		SYNTAX		Integer32 { none (0), v2 (2), v3 (3) }
		MAX-ACCESS	read-write
		STATUS		current
		DESCRIPTION	"Configure VRRP running version on the system.
                        0 : (default) disable system VRRP. 
                        2 : process VRRP version 2 on the device.
                        3 : process VRRP version 3 on the device."
		DEFVAL		{0}
		::= { iswVrrpGroupConfig 2 }
--
    	iswDvmrpConfMode	OBJECT-TYPE
		SYNTAX		Integer32 { disable (0), enable (1)}
		MAX-ACCESS	read-write
		STATUS		current
		DESCRIPTION	"Enable/Disable DVMRP protocol.
                    To enable this feature, igmp snooping must be enabled.
                    VLAN requires setting the VLAN IP and turning on multicast routing."
		DEFVAL		{0}
		::= { iswDvmrpConf 1 }

    	iswDvmrpIfCreateDelete  OBJECT IDENTIFIER
    	::= { iswDvmrpConf 2 }

    	iswDvmrpIfCreate	OBJECT-TYPE
		SYNTAX		Integer32 ( 1 .. 4094 )
		MAX-ACCESS	read-write
		STATUS		current
        DESCRIPTION	"To enable DVMRP MODE for a VLAN(1 ~ 4094), please make sure that the VLAN has a given ip address.
                    (Need to enable igmp snooping first.)
                    (Need to enable mc-routing of the corresponding VLAN interface.)
                    (Need to enable dvmrp      of the coressponding VLAN interface.)
                    
                    When enable DVMRP mode default metric(Refresh Interval) is 1.
                    (Get always return 0)"
		::= { iswDvmrpIfCreateDelete 1 }
    	iswDvmrpIfDelete	OBJECT-TYPE
		SYNTAX		Integer32 ( 1 .. 4094 )
		MAX-ACCESS	read-write
		STATUS		current
		DESCRIPTION	"Disable VLAN DVMRP mode. According to the given VID(1 ~ 4094).
					(Get always return 0)"
		::= { iswDvmrpIfCreateDelete 2 }

	iswDvmrpIfConfTable	OBJECT-TYPE
		SYNTAX		SEQUENCE OF IswDvmrpIfConfEntry
		MAX-ACCESS	not-accessible
		STATUS		current
		DESCRIPTION	"(Required enable IGMP Snooping and multicast routng for the interface VLAN first.
					Interface VLAN must assigned ip Address.)
					Enable/Disable DVMRP protocol."
		::= { iswDvmrpIfCreateDelete 3 }
-- 
	iswDvmrpIfConfEntry	OBJECT-TYPE
		SYNTAX		IswDvmrpIfConfEntry
		MAX-ACCESS	not-accessible
		STATUS		current
		DESCRIPTION	"(Required enable IGMP Snooping and multicast routng for the interface VLAN first.
					Interface VLAN must assigned ip Address.)
					Enable/Disable DVMRP protocol."
		INDEX		{ iswDvmrpIfVlanId }
		::= { iswDvmrpIfConfTable 1 }
		
	IswDvmrpIfConfEntry ::= SEQUENCE{
		iswDvmrpIfVlanId	Integer32,
		iswDvmrpIfMode		Integer32,
		iswDvmrpIfMetric	Integer32
        }
    -- 1 
	iswDvmrpIfVlanId	OBJECT-TYPE
		SYNTAX		Integer32 ( 1 .. 4094 )
		MAX-ACCESS	not-accessible
		STATUS		current
		DESCRIPTION	"The identity for the DVMRP interface VLAN.
					Range 1 - 4094.
					1st DVMRP interface VLAN always exist for VLAN 1. (Only support set can't be deleted)"
		::= { iswDvmrpIfConfEntry 1 }
    -- 2  
	iswDvmrpIfMode	OBJECT-TYPE
		SYNTAX		Integer32 { enable (1) }
		MAX-ACCESS	read-only
		STATUS		current
		DESCRIPTION	"Support DVMRP mode."
		DEFVAL      {1}
		::= { iswDvmrpIfConfEntry 2 }
    -- 3
	iswDvmrpIfMetric	OBJECT-TYPE
		SYNTAX		Integer32 ( 1 .. 32 )
		MAX-ACCESS	read-write
		STATUS		current
		DESCRIPTION	"Start metric for the interface VLAN.
					Range 1 to 32. 32 indicates infinity."
		DEFVAL      {1}
        ::= { iswDvmrpIfConfEntry 3 }
-- 
	iswDvmrpNeighborTable	OBJECT-TYPE
		SYNTAX      SEQUENCE OF IswDvmrpNeighborEntry
		MAX-ACCESS	not-accessible
		STATUS		current
		DESCRIPTION	"iswDvmrpNeighborTable"
		::= { iswDvmrpConf 3 }

	iswDvmrpNeighborEntry	OBJECT-TYPE
		SYNTAX		IswDvmrpNeighborEntry
		MAX-ACCESS	not-accessible
		STATUS		current
		DESCRIPTION	"iswDvmrpNeighbor entry."
		INDEX		{ iswDvmrpNeighborIdx }
		::= { iswDvmrpNeighborTable 1 }
--
	IswDvmrpNeighborEntry ::= SEQUENCE{
		iswDvmrpNeighborIdx Integer32,
		iswDvmrpNeighborIp IpAddress,
		iswDvmrpNeighborIfType Integer32,
		iswDvmrpNeighborIfIdx Integer32,
		iswDvmrpNeighborGenerationId Integer32,
		iswDvmrpNeighborUptime TimeTicks,
		iswDvmrpNeighborExpire TimeTicks,
		iswDvmrpNeighborVersion Integer32,
		iswDvmrpNeighborCapabilities OCTET STRING
	}
-- 1
	iswDvmrpNeighborIdx	OBJECT-TYPE
		SYNTAX		Integer32
		MAX-ACCESS	not-accessible
		STATUS		current
		DESCRIPTION	"DVMRP neighbor index for get data."
		::= { iswDvmrpNeighborEntry 1 }
-- 2
	iswDvmrpNeighborIp	OBJECT-TYPE
		SYNTAX		IpAddress
		MAX-ACCESS	read-only
		STATUS		current
		DESCRIPTION	"DVMRP Neighbor IP Address."
		::= { iswDvmrpNeighborEntry 2 }
-- 3
	iswDvmrpNeighborIfType	OBJECT-TYPE
		SYNTAX		Integer32 { none (0), port (1), vlan (2) }
		MAX-ACCESS	read-only
		STATUS		current
		DESCRIPTION	"An interface type where a DVMRP neighbor was discovered.
					none (0), port (1), vlan (2)"
		::= { iswDvmrpNeighborEntry 3 }
-- 4
	iswDvmrpNeighborIfIdx	OBJECT-TYPE
		SYNTAX		Integer32
		MAX-ACCESS	read-only
		STATUS		current
		DESCRIPTION	"An interface index where a DVMRP neighbor was discovered."
		::= { iswDvmrpNeighborEntry 4 }
-- 5
	iswDvmrpNeighborGenerationId	OBJECT-TYPE
		SYNTAX		Integer32
		MAX-ACCESS	read-only
		STATUS		current
		DESCRIPTION	"DVMRP neighbor generation ID."
		::= { iswDvmrpNeighborEntry 5 }
-- 6
	iswDvmrpNeighborUptime	OBJECT-TYPE
		SYNTAX		TimeTicks
		MAX-ACCESS	read-only
		STATUS		current
		DESCRIPTION	"The total uptime of neighbor."
		::= { iswDvmrpNeighborEntry 6 }
-- 7
	iswDvmrpNeighborExpire	OBJECT-TYPE
		SYNTAX		TimeTicks
		MAX-ACCESS	read-only
		STATUS		current
		DESCRIPTION	"The total expire of neighbor."
		::= { iswDvmrpNeighborEntry 7 }
-- 8
	iswDvmrpNeighborVersion	OBJECT-TYPE
		SYNTAX		Integer32
		MAX-ACCESS	read-only
		STATUS		current
		DESCRIPTION	"The version of DVMRP on neighbor's interface."
		::= { iswDvmrpNeighborEntry 8 }
-- 9
	iswDvmrpNeighborCapabilities	OBJECT-TYPE
		SYNTAX		OCTET STRING ( SIZE(1) )
		MAX-ACCESS	read-only
		STATUS		current
		DESCRIPTION	"Information about neighbor capabilities. This is a bitmap variable.
                    bit[0]: DVMRP_NEIGHBOR_CAP_LEAF,
                    bit[1]: DVMRP_NEIGHBOR_CAP_PRUNE,
                    bit[2]: DVMRP_NEIGHBOR_CAP_GENID,
                    bit[3]: DVMRP_NEIGHBOR_CAP_MTRACE,
                    bit[4]: DVMRP_NEIGHBOR_CAP_SNMP,
                    bit[5]: DVMRP_NEIGHBOR_CAP_NETMASK,
                    bit[6]: DVMRP_NEIGHBOR_CAP_MAX"
		::= { iswDvmrpNeighborEntry 9 }
--

-- 
	iswPimConfMode	OBJECT-TYPE
		SYNTAX		Integer32 { disable (0), enable (1)}
		MAX-ACCESS	read-write
		STATUS		current
		DESCRIPTION	"PIM protocol mode.
                        Allow Disabled/Enabled.
                        Default value is Disabled."
		DEFVAL		{0}
		::= { iswPimConf 1 }
--
	iswPimIfConfTable       OBJECT-TYPE
		SYNTAX      SEQUENCE OF IswPimIfConfEntry
		MAX-ACCESS	not-accessible
		STATUS		current
		DESCRIPTION	"iswPimIfConfTable"
		::= { iswPimConf 2 }
    ---
	iswPimIfConfEntry OBJECT-TYPE
		SYNTAX		IswPimIfConfEntry
		MAX-ACCESS	not-accessible
		STATUS		current
		DESCRIPTION	"PimIfConfEntry entry."
		INDEX		{ iswPimIfVlanId }
		::= { iswPimIfConfTable 1 }
    ---
	IswPimIfConfEntry ::= SEQUENCE{
		iswPimIfVlanId          Integer32,
		iswPimIfMode            Integer32,
		iswPimIfHelloInterval   Unsigned32,
		iswPimIfRefreshInterval Unsigned32,
		iswPimIfRowStatus       RowStatus
	}
    ---  
	iswPimIfVlanId	OBJECT-TYPE
		SYNTAX		Integer32 (1..4094)
		MAX-ACCESS	not-accessible
		STATUS		current
		DESCRIPTION	"The identity for the PIM interface VLAN.
					Range 1 - 4094."
		::= { iswPimIfConfEntry 1 }
    ---
	iswPimIfMode	OBJECT-TYPE
		SYNTAX		Integer32 { pimDm (1) }
		MAX-ACCESS	read-write
		STATUS		current
		DESCRIPTION	"PIM mode, default pimDm (1)."
		DEFVAL { 1 }
		::= { iswPimIfConfEntry 2 }
	---
	iswPimIfHelloInterval OBJECT-TYPE
		SYNTAX		Unsigned32 ( 30..180 )
		MAX-ACCESS	read-write
		STATUS		current
		DESCRIPTION	"PIM hello Interval.
					Range is 30 - 180.
					Default value is 30 sec."
		DEFVAL { 30 }
		::= { iswPimIfConfEntry 3 }
	---
	iswPimIfRefreshInterval	OBJECT-TYPE
		SYNTAX		Unsigned32 ( 1..100 )
		MAX-ACCESS	read-write
		STATUS		current
		DESCRIPTION	"PIM refresh Interval.
					Range is 1 - 100.
					Default value is 60 sec."
		DEFVAL { 60 }
		::= { iswPimIfConfEntry 4 }
    ---
	iswPimIfRowStatus OBJECT-TYPE
		SYNTAX		RowStatus
		MAX-ACCESS	read-create
		STATUS		current
		DESCRIPTION	 "iswPimIfConfEntry Row Status"
		::= { iswPimIfConfEntry 5 }
		--- </iswPimIfConfEntry>
		---
	iswPimNeighborTable	OBJECT-TYPE
		SYNTAX      SEQUENCE OF IswPimNeighborEntry
		MAX-ACCESS	not-accessible
		STATUS		current
		DESCRIPTION	"iswPimNeighborTable"
		::= { iswPimConf 3 }
	---
	iswPimNeighborEntry OBJECT-TYPE
		SYNTAX		IswPimNeighborEntry
		MAX-ACCESS	not-accessible
		STATUS		current
		DESCRIPTION	"iswPimNeighborEntry entry"
		INDEX		{ iswPimNeighborIdx }
		::= { iswPimNeighborTable 1 }
	---
	IswPimNeighborEntry ::= SEQUENCE{
		iswPimNeighborIdx 			Integer32,
		iswPimNeighborIp 			IpAddress,
		iswPimNeighborIfType 			Integer32,
		iswPimNeighborIfIdx			Integer32,
		iswPimNeighborGenerationId		Integer32,
		iswPimNeighborUptime 			TimeTicks,
		iswPimNeighborExpire 			TimeTicks,
		iswPimNeighborVersion			Integer32,
		iswPimNeighborTbit			Integer32,
		iswPimNeighborPropagationDelay		Integer32,
		iswPimNeighborOverrideInternal 		Integer32,
		iswPimNeighborDrPriority		Integer32,
		iswPimNeighborHelloOptionMask		OCTET STRING,
		iswPimNeighborMode			OCTET STRING
	}
    ---  
	iswPimNeighborIdx	OBJECT-TYPE
		SYNTAX		Integer32
		MAX-ACCESS	not-accessible	
		STATUS		current
		DESCRIPTION	"PIM neighbor index for get data."
		::= { iswPimNeighborEntry 1 }
    ---
	iswPimNeighborIp	OBJECT-TYPE
		SYNTAX		IpAddress
		MAX-ACCESS	read-only
		STATUS		current
		DESCRIPTION	"Specifies a PIM neighbor's IP address."
		::= { iswPimNeighborEntry 2 }
    ---
	iswPimNeighborIfType	OBJECT-TYPE
		SYNTAX		Integer32 { none (0), port(1), vlan (2) }
		MAX-ACCESS	read-only
		STATUS		current
		DESCRIPTION	"An interface type where a PIM neighbor was discovered."
		::= { iswPimNeighborEntry 3 }
    ---
	iswPimNeighborIfIdx	OBJECT-TYPE
		SYNTAX		Integer32
		MAX-ACCESS	read-only
		STATUS		current
		DESCRIPTION	"An interface index where a PIM neighbor was discovered."
		::= { iswPimNeighborEntry 4 }
    ---
	iswPimNeighborGenerationId	OBJECT-TYPE
		SYNTAX		Integer32
		MAX-ACCESS	read-only
		STATUS		current
		DESCRIPTION	"PIM neighbor generation ID."
		::= { iswPimNeighborEntry 5 }
	---
	iswPimNeighborUptime	OBJECT-TYPE
		SYNTAX		TimeTicks
		MAX-ACCESS	read-only
		STATUS		current
		DESCRIPTION	 "The total uptime of neighbor."
		::= { iswPimNeighborEntry 6 }
    ---
	iswPimNeighborExpire	OBJECT-TYPE
		SYNTAX		TimeTicks  
		MAX-ACCESS	read-only
		STATUS		current
		DESCRIPTION	"The time before a neighbor is timed out(holdtime) and until next PIM hello is received."
		::= { iswPimNeighborEntry 7 }
    ---
	iswPimNeighborVersion	OBJECT-TYPE
		SYNTAX		Integer32 
		MAX-ACCESS	read-only
		STATUS		current
		DESCRIPTION	"The version of PIM on neighbor's interface."
		::= { iswPimNeighborEntry 8 }
	---
	iswPimNeighborTbit	OBJECT-TYPE
		SYNTAX		Integer32 
		MAX-ACCESS	read-only
		STATUS		current
		DESCRIPTION	"The T bit was set in the LAN Prune Delay option received from this neighbor."
		::= { iswPimNeighborEntry 9 }
	---
	iswPimNeighborPropagationDelay	OBJECT-TYPE
		SYNTAX		Integer32 
		MAX-ACCESS	read-only
		STATUS		current
		DESCRIPTION	"Prune propagation delay."
		::= { iswPimNeighborEntry 10 }
    ---
	iswPimNeighborOverrideInternal	OBJECT-TYPE
		SYNTAX		Integer32 
		MAX-ACCESS	read-only					
		STATUS		current
		DESCRIPTION	"Prune override internal."
		::= { iswPimNeighborEntry 11 }
	---
	iswPimNeighborDrPriority	OBJECT-TYPE
		SYNTAX		Integer32 
		MAX-ACCESS	read-only
		STATUS		current
		DESCRIPTION	"DR Priority of PIM neighbor."
		::= { iswPimNeighborEntry 12 }
	---
	iswPimNeighborHelloOptionMask	OBJECT-TYPE
		SYNTAX		OCTET STRING ( SIZE(1) ) 
		MAX-ACCESS	read-only
		STATUS		current
		DESCRIPTION	"Neighbor option mask which is a bitmap.
                    bit[0]: PIM_OPTION_MASK_HOLDTIME                     
                    bit[1]: PIM_OPTION_MASK_LAN_PRUNE_DELAY              
                    bit[2]: PIM_OPTION_MASK_DR_PRIORITY                  
                    bit[3]: PIM_OPTION_MASK_GENERATION_ID                
                    bit[4]: PIM_OPTION_MASK_ADDRESS_LIST                 
                    bit[5]: PIM_OPTION_MASK_CAN_DISABLE_JOIN_SUPPRESSION 
                    bit[6]: PIM_OPTION_MASK_DM_STATE_REFRESH"             
		::= { iswPimNeighborEntry 13 }
	---
	iswPimNeighborMode	OBJECT-TYPE
		SYNTAX		OCTET STRING ( SIZE(1) )
		MAX-ACCESS	read-only
		STATUS		current
		DESCRIPTION	"Information about the DR and other PIM neighbor capabilities.
                    bit[0]: S - State Refresh Capable
                    bit[1]: N - Default DR Priority"
		::= { iswPimNeighborEntry 14 }
	--- </iswPimNeighborTable>
--
--
	iswIPv6StaticRouteTable	 	OBJECT-TYPE
		SYNTAX SEQUENCE OF IswIPv6StaticRouteEntry
		MAX-ACCESS not-accessible
		STATUS current
		DESCRIPTION "IPv6 Router table table."
		::= { iswIPv6StaticRoute 1 }
	iswIPv6StaticRouteEntry 	OBJECT-TYPE
		SYNTAX IswIPv6StaticRouteEntry
		MAX-ACCESS not-accessible
		STATUS current
		DESCRIPTION "IPv6 Router table entry."
		INDEX { iswIPv6StaticRouteIndex }
		::= { iswIPv6StaticRouteTable 1 }
	IswIPv6StaticRouteEntry ::= SEQUENCE{
		iswIPv6StaticRouteIndex 		Integer32,
		iswIPv6StaticRouteDstAddr 		OCTET STRING,
		iswIPv6StaticRouteDstPrefixlen		Integer32,
		iswIPv6StaticRouteNexthop 		OCTET STRING,
		iswIPv6StaticRouteOutputVlan 		Integer32,
		iswIPv6StaticRouteRowStatus 		RowStatus
	}
	--1
	iswIPv6StaticRouteIndex		OBJECT-TYPE
		SYNTAX		Integer32
		MAX-ACCESS	not-accessible
		STATUS		current
		DESCRIPTION	"IPv6 static route index."
		::= { iswIPv6StaticRouteEntry 1 }
--2
	iswIPv6StaticRouteDstAddr		OBJECT-TYPE
		SYNTAX		OCTET STRING
		MAX-ACCESS	read-write
		STATUS		current
		DESCRIPTION	"Destination  IPv6 prefix address."
--		DEFVAL		{0, 0, 0, 0, 0, 0, 0, 0, 0, 0, 0, 0, 0, 0, 0, 0}
		::= { iswIPv6StaticRouteEntry 2 }
--3
	iswIPv6StaticRouteDstPrefixlen		OBJECT-TYPE
		SYNTAX		Integer32
		MAX-ACCESS	read-write
		STATUS		current
		DESCRIPTION	"Prefix length of IPv6 address."
		::= { iswIPv6StaticRouteEntry 3 }
--4
	iswIPv6StaticRouteNexthop		OBJECT-TYPE
		SYNTAX		OCTET STRING
		MAX-ACCESS	read-write
		STATUS		current
		DESCRIPTION	"IPv6 StaticRoute address of next_hop."
--		DEFVAL		{0, 0, 0, 0, 0, 0, 0, 0, 0, 0, 0, 0, 0, 0, 0, 0}
		::= { iswIPv6StaticRouteEntry 4 }
--5
	iswIPv6StaticRouteOutputVlan		OBJECT-TYPE
		SYNTAX		Integer32
		MAX-ACCESS	read-write
		STATUS		current
		DESCRIPTION	"Direct output vlan of the route on the device."
		::= { iswIPv6StaticRouteEntry 5 }
--6
	iswIPv6StaticRouteRowStatus		OBJECT-TYPE
		SYNTAX		RowStatus
		MAX-ACCESS	read-create
		STATUS		current
		DESCRIPTION	"IPv6 route Row Status"
		::= { iswIPv6StaticRouteEntry 6 }

	iswIPv6UnicastRouting	OBJECT-TYPE
		SYNTAX		INTEGER { disable (0), enable (1) }
		MAX-ACCESS	read-write
		STATUS		current
		DESCRIPTION	"Enable/Disable IPv6 unicast routing."
		::= { iswIPv6StaticRoute 2 }
--

	iswVlanIntfTable	OBJECT-TYPE
		SYNTAX		SEQUENCE OF IswVlanIntfEntry
		MAX-ACCESS	not-accessible
		STATUS		current
		DESCRIPTION	"Interface Vlan table. Max entry size: 5.
						1st entry is created by default and assign for VLAN 1. (Only support set and can't be deleted.)"
		::= { iswLayer3 4 }
		
	iswVlanIntfEntry	OBJECT-TYPE
		SYNTAX		IswVlanIntfEntry
		MAX-ACCESS	not-accessible
		STATUS		current
		DESCRIPTION	"Static Route entry."
		INDEX		{ iswVlanIfConfIntVlan }
		::= { iswVlanIntfTable 1 }
		
	IswVlanIntfEntry ::= SEQUENCE{
		iswVlanIfConfIntVlan			Integer32,
		iswVlanIfConfIPAddr				IpAddress,
		iswVlanIfConfNetmask			IpAddress,
		iswVlanIfConfMac				PhysAddress,
		iswVlanIfConfIPv6PrefixSize		Integer32,
		iswVlanIfConfIPv6Addr			OCTET STRING,
		iswVlanIfConfIPv6LLPrefixSize	Integer32,
		iswVlanIfConfIPv6LLAddr			OCTET STRING,
		iswVlanIfConfRowStatus			RowStatus
	}
--1 
	iswVlanIfConfIntVlan	OBJECT-TYPE
		SYNTAX		Integer32 ( 1 .. 4094 )
		MAX-ACCESS	not-accessible
		STATUS		current
		DESCRIPTION	"Vlan interface: vlan.
					Vlan 1 always exist and can not be deleted."
		::= { iswVlanIntfEntry 1 }

	iswVlanIfConfIPAddr	OBJECT-TYPE
		SYNTAX		IpAddress
		MAX-ACCESS	read-create
		STATUS		current
		DESCRIPTION	"IP address for the vlan interface.
					Default value is 0.0.0.0. "
		::= { iswVlanIntfEntry 2 }

	iswVlanIfConfNetmask	OBJECT-TYPE
		SYNTAX		IpAddress
		MAX-ACCESS	read-create
		STATUS		current
		DESCRIPTION	"Subnet mask for the vlan interface. The default value is 0.0.0.0."
		::= { iswVlanIntfEntry 3 }

	iswVlanIfConfMac	OBJECT-TYPE
		SYNTAX		PhysAddress
		MAX-ACCESS	read-only
		STATUS		current
		DESCRIPTION	"MAC address for the vlan interface."
		::= { iswVlanIntfEntry 4 }
    -- <alter add>
	iswVlanIfConfIPv6PrefixSize OBJECT-TYPE
		SYNTAX      Integer32 ( 1 .. 128 )
		MAX-ACCESS  read-create
		STATUS      current
		DESCRIPTION "The prefix length is accepted in range of 1 to 128."
		::= { iswVlanIntfEntry 5 }
	iswVlanIfConfIPv6Addr   OBJECT-TYPE
		SYNTAX      OCTET STRING
		MAX-ACCESS  read-create
		STATUS      current
		DESCRIPTION "IPv6 Address is generally IPv6 unicast addresses are aggregatable with prefixes of arbitrary bit-length, 
                    similar to IPv4 addresses under Classless Inter-Domain Routing. Here only Global Unicast address is considered, 
                    others type of unicast addresses (ex: site-local unicast, Link-Local unicast ...etc) are not.

                        The general format for IPv6 Global Unicast addresses is as follows:
                        |         n bits         |   m bits  |       128-n-m bits         |
                        +------------------------+-----------+----------------------------+
                        | global routing prefix  | subnet ID |       interface ID         |
                        +------------------------+-----------+----------------------------+

                    where the global routing prefix is a (typically hierarchically- structured) value assigned to a site 
                    (a cluster of subnets/links), the subnet ID is an identifier of a link within the site, and the interface 
                    identifiers in IPv6 unicast addresses are used to identify interfaces on a link.
                    The symbol :: is a special syntax that can be used as a shorthand way of representing multiple 16-bit 
                    groups of contiguous zeros; but it can appear only once. It can also represent a legally valid IPv4 address. 
                    For example, ::192.1.2.34. The field may be left blank if IPv6 operation on the interface is not desired."
		::= { iswVlanIntfEntry 6 }
	iswVlanIfConfIPv6LLPrefixSize   OBJECT-TYPE
		SYNTAX      Integer32 ( 64 .. 128)
		MAX-ACCESS  read-create
		STATUS      current
		DESCRIPTION "The prefix length is accepted in range of 64 to 128."
		::= { iswVlanIntfEntry 7 }
	iswVlanIfConfIPv6LLAddr OBJECT-TYPE
		SYNTAX      OCTET STRING
		MAX-ACCESS  read-create
		STATUS      current
		DESCRIPTION "IPv6 Link-Local addresses are for use on a single link.
                    Link-Local addresses have the following format:

                    |   10     |
                    |  bits    |         54 bits         |          64 bits           |
                    +----------+-------------------------+----------------------------+
                    |1111111010|           0             |       interface ID         |
                    +----------+-------------------------+----------------------------+

                    Link-Local addresses are designed to be used for addressing on a single link for purposes such as 
                    automatic address configuration, neighbor discovery, or when no routers are present. Automatically 
                    generate an link-local address in format of EUI-64 while it is not specified."
		::= { iswVlanIntfEntry 8 }
	-- </alter add>
	iswVlanIfConfRowStatus	OBJECT-TYPE
		SYNTAX		RowStatus
		MAX-ACCESS	read-create
		STATUS		current
		DESCRIPTION	"Vlan interface: RowStatus."
		::= { iswVlanIntfEntry 9 } -- 5 > 9

	iswTrackObjectTable	OBJECT-TYPE
		SYNTAX		SEQUENCE OF IswTrackObjectEntry
		MAX-ACCESS	not-accessible
		STATUS		current
		DESCRIPTION	"Track object table. Max entry size: 64."
		::= { iswTrackObjectConfig 1 }

	iswTrackObjectEntry	OBJECT-TYPE
		SYNTAX		IswTrackObjectEntry
		MAX-ACCESS	not-accessible
		STATUS		current
		DESCRIPTION	"Track object entry."
		INDEX		{ iswTrackObjectIdx }
		::= { iswTrackObjectTable 1 }

	IswTrackObjectEntry ::= SEQUENCE{
		iswTrackObjectIdx			Integer32,
		iswTrackObjectType			Integer32,
		iswTrackObjectTarget		Unsigned32,
		iswTrackObjectPolling		Integer32,
		iswTrackObjectThreshold		Integer32, 
		iswTrackObjectStatus		Integer32,
		iswTrackObjectRowStatus		RowStatus
	}

	iswTrackObjectIdx	OBJECT-TYPE
		SYNTAX		Integer32 ( 1 .. 64 )
		MAX-ACCESS	not-accessible
		STATUS		current
		DESCRIPTION	"Track object index."
		::= { iswTrackObjectEntry 1 }

	iswTrackObjectType	OBJECT-TYPE
		SYNTAX		Integer32 { vlan (1), port (2), route (3), vrrp (4) }
		MAX-ACCESS	read-create
		STATUS		current
		DESCRIPTION	"Track object type."
		::= { iswTrackObjectEntry 2 }

	iswTrackObjectTarget	OBJECT-TYPE
		SYNTAX		Unsigned32
		MAX-ACCESS	read-create
		STATUS		current
		DESCRIPTION	"Track object target.
					When iswTrackObjectType is vlan, it means VLAN.
					When iswTrackObjectType is port, it means Port.
					When iswTrackObjectType is route, it means IP address.
					When iswTrackObjectType is vrrp, it means vrrp."
		::= { iswTrackObjectEntry 3 }

	iswTrackObjectPolling	OBJECT-TYPE
		SYNTAX		Integer32 ( 1 .. 600 )
		MAX-ACCESS	read-create
		STATUS		current
		DESCRIPTION	"Track object polling time. 
					It is only available when iswTrackObjectType is route."
		DEFVAL		{10}
		::= { iswTrackObjectEntry 4 }

	iswTrackObjectThreshold	OBJECT-TYPE
		SYNTAX		Integer32 ( 1 .. 3000 )
		MAX-ACCESS	read-create
		STATUS		current
		DESCRIPTION	"Track object threshold time.
					It is only available when iswTrackObjectType is route."
        DEFVAL		{60}
		::= { iswTrackObjectEntry 5 }

	iswTrackObjectStatus	OBJECT-TYPE
		SYNTAX		Integer32 { up (1), down (2), reachable (3), unreachable (4) }
		MAX-ACCESS	read-only
		STATUS		current
		DESCRIPTION	"Track object type."
		::= { iswTrackObjectEntry 6 }

	iswTrackObjectRowStatus	OBJECT-TYPE
		SYNTAX		RowStatus
		MAX-ACCESS	read-create
		STATUS		current
		DESCRIPTION	"Track Object index: RowStatus."
		::= { iswTrackObjectEntry 7 }

--
--1
	iswRipConfRipMode	OBJECT-TYPE
		SYNTAX		Integer32 { disable (0), enable (1) }
		MAX-ACCESS	read-write
		STATUS		current
		DESCRIPTION	"Enable/Disable RIP protocol."
		DEFVAL		{0}
		::= { iswRipConfig 1 } 
--2
	iswRipUpdateTime	OBJECT-TYPE
		SYNTAX		Integer32 ( 20 .. 3600 )
		UNITS		"second"
		MAX-ACCESS	read-write
		STATUS		current
		DESCRIPTION	"Routing table update time."
		DEFVAL		{30}
		::= { iswRipConfig 2 }  
--3		
	iswRipGCTimeout	OBJECT-TYPE
		SYNTAX		Integer32 ( 20 .. 3600 )
		UNITS		"second"
		MAX-ACCESS	read-write
		STATUS		current
		DESCRIPTION	"Garbage collection time."
		DEFVAL		{120}
		::= { iswRipConfig 3 }
--4
	iswRipRouteTimeout	OBJECT-TYPE
		SYNTAX		Integer32 ( 20 .. 3600 )
		UNITS		"second"
		MAX-ACCESS	read-write
		STATUS		current
		DESCRIPTION	"Routing information timeout."
		DEFVAL		{180}
		::= { iswRipConfig 4 }
--5
	iswRipVlanIntfTable	OBJECT-TYPE
		SYNTAX		SEQUENCE OF IswRipVlanIntfEntry
		MAX-ACCESS	not-accessible
		STATUS		current
		DESCRIPTION	"RIP vlan interface table.
					For RIP interface configuration. Max interface(entry) size: 5."
		::= { iswRipConfig 5 }
		
	iswRipVlanIntfEntry	OBJECT-TYPE
		SYNTAX		IswRipVlanIntfEntry
		MAX-ACCESS	not-accessible
		STATUS		current
		DESCRIPTION	"RIP vlan interface entry."
		INDEX		{ iswRipIfConfIntVlan }
		::= { iswRipVlanIntfTable 1 }
		
	IswRipVlanIntfEntry ::= SEQUENCE{
		iswRipIfConfIntVlan				Integer32,
		iswRipIfConfAuthType			Integer32,
		iswRipIfConfAuthKey				OCTET STRING,
		iswRipIfConfSend				Integer32,
		iswRipIfConfReceive				Integer32,
		iswRipIfConfSplitHorizon		Integer32,
		iswRipIfConfTrackUpBitmap		OCTET STRING,
		iswRipIfConfTrackDownBitmap		OCTET STRING,
		iswRipIfConfTrackThreshold		Integer32,
		iswRipIfConfRowStatus			RowStatus
	}

	iswRipIfConfIntVlan	OBJECT-TYPE
		SYNTAX		Integer32 ( 1 .. 4094 )
		MAX-ACCESS	not-accessible
		STATUS		current
		DESCRIPTION	"RIP vlan interface: vlan."
		::= { iswRipVlanIntfEntry 1 }

	iswRipIfConfAuthType	OBJECT-TYPE
		SYNTAX		Integer32 { no (1), cleartext (2) }
		MAX-ACCESS	read-create
		STATUS		current
		DESCRIPTION	"The type of Authentication used on this interface.
					The default value is no authentication.
					This parameter is optional feature."
		DEFVAL		{1}
		::= { iswRipVlanIntfEntry 2 }

	iswRipIfConfAuthKey	OBJECT-TYPE
		SYNTAX		OCTET STRING  ( SIZE ( 0..16 ) )
		MAX-ACCESS	read-create
		STATUS		current
		DESCRIPTION	"The Authentication Key.
					The default value is empty string which is all nulls (0x00).
					This parameter is optional feature."
		::= { iswRipVlanIntfEntry 3 }

	iswRipIfConfSend	OBJECT-TYPE
		SYNTAX		Integer32 { nosend (1), rip-v1 (2), rip-v2 (3), rip-v1andv2 (4) }
		MAX-ACCESS	read-create
		STATUS		current
		DESCRIPTION	"The version of RIP packet sent from this interface.
					The default value is rip-v1.
					This parameter is optional feature."
		DEFVAL		{2}
		::= { iswRipVlanIntfEntry 4 }

	iswRipIfConfReceive	OBJECT-TYPE
		SYNTAX		Integer32 { norecv (1), rip-v1 (2), rip-v2 (3), rip-v1orv2 (4) }
		MAX-ACCESS	read-create
		STATUS		current
		DESCRIPTION	"The version of RIP packet which will be received by this interface.
					The default value is rip-v1orv2.
					This parameter is optional feature."
		DEFVAL		{4}
		::= { iswRipVlanIntfEntry 5 }

	iswRipIfConfSplitHorizon	OBJECT-TYPE
		SYNTAX		Integer32 { disable (1), simple (2), poison (3) }
		MAX-ACCESS	read-create
		STATUS		current
		DESCRIPTION	"It is used to control split horizon routing update behavior.
					The default value is simple.
					This parameter is optional feature."
		DEFVAL		{2}
		::= { iswRipVlanIntfEntry 6 }

	iswRipIfConfTrackUpBitmap	OBJECT-TYPE
		SYNTAX		OCTET STRING  ( SIZE ( 8 ) )
		MAX-ACCESS	read-create
		STATUS		current
		DESCRIPTION	"Up-list Track object bitmap.
					Byte[0] for track 8  ~ track 1, bit 1 for track object 1, bit 2  for track object 2  and so on.
					Byte[1] for track 16 ~ track 9, bit 9 for track object 9, bit 10 for track object 10 and so on.
					Byte[2] for track 24 ~ track 17, bit 17 for track object 17, bit 18 for track object 18 and so on.
					Byte[3] for track 32 ~ track 25, bit 25 for track object 25, bit 26 for track object 26 and so on.
					Byte[4] for track 40 ~ track 33, bit 33 for track object 33, bit 34 for track object 34 and so on.
					Byte[5] for track 48 ~ track 41, bit 41 for track object 41, bit 42 for track object 42 and so on.
					Byte[6] for track 56 ~ track 49, bit 49 for track object 49, bit 50 for track object 50 and so on.
					Byte[7] for track 64 ~ track 57, bit 57 for track object 57, bit 58 for track object 58 and so on.
					Byte[0] = 0x0 .. 0xFF
					Byte[1] = 0x0 .. 0xFF
					Byte[2] = 0x0 .. 0xFF
					Byte[3] = 0x0 .. 0xFF
					Byte[4] = 0x0 .. 0xFF
					Byte[5] = 0x0 .. 0xFF
					Byte[6] = 0x0 .. 0xFF
					Byte[7] = 0x0 .. 0xFF
					Default 0x0 means no track entry binding on RIP of the interface vlan."
		::= { iswRipVlanIntfEntry 7 }
	iswRipIfConfTrackDownBitmap	OBJECT-TYPE
		SYNTAX		OCTET STRING  ( SIZE ( 8 ) )
		MAX-ACCESS	read-create
		STATUS		current
		DESCRIPTION	"Down-list Track object bitmap.
					Byte[0] for track 8  ~ track 1, bit 1 for track object 1, bit 2  for track object 2  and so on.
					Byte[1] for track 16 ~ track 9, bit 9 for track object 9, bit 10 for track object 10 and so on.
					Byte[2] for track 24 ~ track 17, bit 17 for track object 17, bit 18 for track object 18 and so on.
					Byte[3] for track 32 ~ track 25, bit 25 for track object 25, bit 26 for track object 26 and so on.
					Byte[4] for track 40 ~ track 33, bit 33 for track object 33, bit 34 for track object 34 and so on.
					Byte[5] for track 48 ~ track 41, bit 41 for track object 41, bit 42 for track object 42 and so on.
					Byte[6] for track 56 ~ track 49, bit 49 for track object 49, bit 50 for track object 50 and so on.
					Byte[7] for track 64 ~ track 57, bit 57 for track object 57, bit 58 for track object 58 and so on.
					Byte[0] = 0x0 .. 0xFF
					Byte[1] = 0x0 .. 0xFF
					Byte[2] = 0x0 .. 0xFF
					Byte[3] = 0x0 .. 0xFF
					Byte[4] = 0x0 .. 0xFF
					Byte[5] = 0x0 .. 0xFF
					Byte[6] = 0x0 .. 0xFF
					Byte[7] = 0x0 .. 0xFF
					Default 0x0 means no track entry binding on RIP of the interface vlan."
		::= { iswRipVlanIntfEntry 8 }
	iswRipIfConfTrackThreshold	OBJECT-TYPE
		SYNTAX		Integer32 (1 .. 16)
		MAX-ACCESS	read-create
		STATUS		current
		DESCRIPTION	"Threshold to indicate track status is up or down."
		DEFVAL		{1}
		::= { iswRipVlanIntfEntry 9 }
	iswRipIfConfRowStatus	OBJECT-TYPE
		SYNTAX		RowStatus
		MAX-ACCESS	read-create
		STATUS		current
		DESCRIPTION	"RIP vlan interface: RowStatus."
		::= { iswRipVlanIntfEntry 10 }
--
	iswRipRedistConfTable	OBJECT-TYPE
		SYNTAX		SEQUENCE OF IswRipRedistConfEntry
		MAX-ACCESS	not-accessible
		STATUS		current
		DESCRIPTION	"Rip Redistribute configuration. Support 3 entries."
		::= { iswRipConfig 6 }
		
	iswRipRedistConfEntry	OBJECT-TYPE
		SYNTAX		IswRipRedistConfEntry
		MAX-ACCESS	not-accessible
		STATUS		current
		DESCRIPTION	"RIP vlan interface entry."
		INDEX		{ iswRipRedistSource }
		::= { iswRipRedistConfTable 1 }
		
	IswRipRedistConfEntry ::= SEQUENCE{
		iswRipRedistSource			Integer32,
		iswRipRedistMetric			Integer32,
		iswRipRedistRowStatus		RowStatus
	}
	
	iswRipRedistSource	OBJECT-TYPE
		SYNTAX		Integer32   { connect(1), static(2), ospf(4) }
		MAX-ACCESS	not-accessible
		STATUS		current
		DESCRIPTION	"Rip Redistribute system entry Protocol."
		::= { iswRipRedistConfEntry 1 }

	iswRipRedistMetric	OBJECT-TYPE
		SYNTAX		Integer32   (0..16)
		MAX-ACCESS	read-create
		STATUS		current
		DESCRIPTION	"Rip Redistribute metric."
		DEFVAL		{0}
		::= { iswRipRedistConfEntry 2 }

	iswRipRedistRowStatus	OBJECT-TYPE
		SYNTAX		RowStatus
		MAX-ACCESS	read-create
		STATUS		current
		DESCRIPTION	"RIP Redistribute: RowStatus."
		::= { iswRipRedistConfEntry 3 }
--
--1
	iswOspfEnable	OBJECT-TYPE
		SYNTAX		Integer32 { disable (0), enable (1) }
		MAX-ACCESS	read-write
		STATUS		current
		DESCRIPTION	"Enable/Disable OSPF protocol."
		DEFVAL		{0}
		::= { iswOspfConfig 1 } 
--2
	iswOspfAbrType	OBJECT-TYPE
		SYNTAX		Integer32 { standard(1), cisco(3), shortcut(4) }
		MAX-ACCESS	read-write
		STATUS		current
		DESCRIPTION	"OSPF ABR Type. Default is cisco type."
		DEFVAL		{3}
		::= { iswOspfConfig 2 }  
--3		
	iswOspfRFC1583Compatible	OBJECT-TYPE
		SYNTAX		Integer32 { disable (0), enable (1) }
		MAX-ACCESS	read-write
		STATUS		current
		DESCRIPTION	"Enabled/Disabled RFC1583 compatibility."
		DEFVAL		{0}
		::= { iswOspfConfig 3 }
--4
	iswOspfRouterId	OBJECT-TYPE
		SYNTAX		Unsigned32 ( 0 .. 4294967295 )
		MAX-ACCESS	read-write
		STATUS		current
		DESCRIPTION	"Router-ID for the OSPF Process."
		DEFVAL		{0}
		::= { iswOspfConfig 4 }
--5
	iswOspfRedistConfTable	OBJECT-TYPE
		SYNTAX		SEQUENCE OF IswOspfRedistConfEntry
		MAX-ACCESS	not-accessible
		STATUS		current
		DESCRIPTION	"OSPF Redistribute configuration. Support 3 entries."
		::= { iswOspfConfig 5 }
		
	iswOspfRedistConfEntry	OBJECT-TYPE
		SYNTAX		IswOspfRedistConfEntry
		MAX-ACCESS	not-accessible
		STATUS		current
		DESCRIPTION	"RIP vlan interface entry."
		INDEX		{ iswOspfRedistSource }
		::= { iswOspfRedistConfTable 1 }
		
	IswOspfRedistConfEntry ::= SEQUENCE{
		iswOspfRedistSource			Integer32,
		iswOspfRedistMetricType		Integer32,
		iswOspfRedistMetric			Integer32,
		iswOspfRedistRowStatus		RowStatus
	}
	
	iswOspfRedistSource	OBJECT-TYPE
		SYNTAX		Integer32   { connect(1), static(2), rip(3) }
		MAX-ACCESS	not-accessible
		STATUS		current
		DESCRIPTION	"OSPF Redistribute system entry Protocol."
		::= { iswOspfRedistConfEntry 1 }

	iswOspfRedistMetricType	OBJECT-TYPE
		SYNTAX		Integer32   { type1(0), type2(1) }
		MAX-ACCESS	read-create
		STATUS		current
		DESCRIPTION	"External Type"
		DEFVAL		{1}
		::= { iswOspfRedistConfEntry 2 }

	iswOspfRedistMetric	OBJECT-TYPE
		SYNTAX		Integer32   (1 .. 16777214)
		MAX-ACCESS	read-create
		STATUS		current
		DESCRIPTION	"OSPF Redistribute metric."
		DEFVAL		{20}
		::= { iswOspfRedistConfEntry 3 }

	iswOspfRedistRowStatus	OBJECT-TYPE
		SYNTAX		RowStatus
		MAX-ACCESS	read-create
		STATUS		current
		DESCRIPTION	"OSPF Redistribute: RowStatus."
		::= { iswOspfRedistConfEntry 4 }
--6
	iswOspfAreaConfTable	OBJECT-TYPE
		SYNTAX		SEQUENCE OF IswOspfAreaConfEntry
		MAX-ACCESS	not-accessible
		STATUS		current
		DESCRIPTION	"OSPF Area configure table. Max size: 8."
		::= { iswOspfConfig 6 }
		
	iswOspfAreaConfEntry	OBJECT-TYPE
		SYNTAX		IswOspfAreaConfEntry
		MAX-ACCESS	not-accessible
		STATUS		current
		DESCRIPTION	"OSPF Area configure entry."
		INDEX		{ iswOspfAreaId }
		::= { iswOspfAreaConfTable 1 }
		
	IswOspfAreaConfEntry ::= SEQUENCE{
		iswOspfAreaId				Unsigned32,
		iswOspfAreaType				Integer32,
		iswOspfAreaNssaEnableTranslateLSA	Integer32,
		iswOspfAreaRowStatus			RowStatus
	}
	
	iswOspfAreaId	OBJECT-TYPE
		SYNTAX		Unsigned32 ( 1 .. 4294967295 )
		MAX-ACCESS	not-accessible
		STATUS		current
		DESCRIPTION	"OSPF Area Id. Id is unique, and show not equal as iswOspfVLinkAreaId"
		::= { iswOspfAreaConfEntry 1 }

	iswOspfAreaType	OBJECT-TYPE
		SYNTAX		Integer32   { stub(1), stub-no-summary(2), nssa(3), nssa-no-summary(4) }
		MAX-ACCESS	read-create
		STATUS		current
		DESCRIPTION	"External Type"
		DEFVAL		{1}
		::= { iswOspfAreaConfEntry 2 }

	iswOspfAreaNssaEnableTranslateLSA	OBJECT-TYPE
		SYNTAX		Integer32 { disable (0), enable (1) }
		MAX-ACCESS	read-create
		STATUS		current
		DESCRIPTION	"Enable NSSA translate LSA.
				This parameter is only valid when ospfAreaType is NSSA or NSSA_NO_SUMMARY"
		DEFVAL		{0}
		::= { iswOspfAreaConfEntry 3 }

	iswOspfAreaRowStatus	OBJECT-TYPE
		SYNTAX		RowStatus
		MAX-ACCESS	read-create
		STATUS		current
		DESCRIPTION	"OSPF Area: RowStatus."
		::= { iswOspfAreaConfEntry 4 }
--7
	iswOspfVLinkConfTable	OBJECT-TYPE
		SYNTAX		SEQUENCE OF IswOspfVLinkConfEntry
		MAX-ACCESS	not-accessible
		STATUS		current
		DESCRIPTION	"OSPF virtual-link configure table. Max size: 8."
		::= { iswOspfConfig 7 }
		
	iswOspfVLinkConfEntry	OBJECT-TYPE
		SYNTAX		IswOspfVLinkConfEntry
		MAX-ACCESS	not-accessible
		STATUS		current
		DESCRIPTION	"OSPF virtual-link configure entry."
		INDEX		{ iswOspfVLinkAreaId, iswOspfVLinkNeighbor }
		::= { iswOspfVLinkConfTable 1 }
		
	IswOspfVLinkConfEntry ::= SEQUENCE{
		iswOspfVLinkAreaId		Unsigned32,
		iswOspfVLinkNeighbor		Unsigned32,
		iswOspfVLinkRowStatus		RowStatus
	}
	
	iswOspfVLinkAreaId	OBJECT-TYPE
		SYNTAX		Unsigned32 ( 1 .. 4294967295 )
		MAX-ACCESS	not-accessible
		STATUS		current
		DESCRIPTION	"OSPF virtual-link Area Id. Id is unique, and show not equal as iswOspfAreaId"
		::= { iswOspfVLinkConfEntry 1 }

	iswOspfVLinkNeighbor	OBJECT-TYPE
		SYNTAX		Unsigned32 ( 0 .. 4294967295 )
		MAX-ACCESS	not-accessible
		STATUS		current
		DESCRIPTION	"OSPF virtual-link neighbor Id (Address)"
		::= { iswOspfVLinkConfEntry 2 }

	iswOspfVLinkRowStatus	OBJECT-TYPE
		SYNTAX		RowStatus
		MAX-ACCESS	read-create
		STATUS		current
		DESCRIPTION	"OSPF virtual-link: RowStatus."
		::= { iswOspfVLinkConfEntry 3 }
--8
	iswOspfNeighborConfTable	OBJECT-TYPE
		SYNTAX		SEQUENCE OF IswOspfNeighborConfEntry
		MAX-ACCESS	not-accessible
		STATUS		current
		DESCRIPTION	"OSPF neighbor configure table. Max size: 16."
		::= { iswOspfConfig 8 }
		
	iswOspfNeighborConfEntry	OBJECT-TYPE
		SYNTAX		IswOspfNeighborConfEntry
		MAX-ACCESS	not-accessible
		STATUS		current
		DESCRIPTION	"OSPF neighbor configure entry."
		INDEX		{ iswOspfNeighAddress }
		::= { iswOspfNeighborConfTable 1 }
		
	IswOspfNeighborConfEntry ::= SEQUENCE{
		iswOspfNeighAddress		Unsigned32,
		iswOspfNeighPollInterval	Integer32,
		iswOspfNeighPriority		Integer32,
		iswOspfNeighRowStatus		RowStatus
	}
	
	iswOspfNeighAddress	OBJECT-TYPE
		SYNTAX		Unsigned32 ( 1 .. 4294967295 )
		MAX-ACCESS	not-accessible
		STATUS		current
		DESCRIPTION	"OSPF neighbor Id"
		::= { iswOspfNeighborConfEntry 1 }

	iswOspfNeighPollInterval	OBJECT-TYPE
		SYNTAX		Integer32 ( 1 .. 65535 )
		MAX-ACCESS	read-create
		STATUS		current
		DESCRIPTION	"OSPF neighbor poll-interval, default is 60"
		DEFVAL		{60}
		::= { iswOspfNeighborConfEntry 2 }

	iswOspfNeighPriority	OBJECT-TYPE
		SYNTAX		Integer32 ( 0 .. 255 )
		MAX-ACCESS	read-create
		STATUS		current
		DESCRIPTION	"OSPF neighbor priority, default is 0"
		DEFVAL		{0}
		::= { iswOspfNeighborConfEntry 3 }

	iswOspfNeighRowStatus	OBJECT-TYPE
		SYNTAX		RowStatus
		MAX-ACCESS	read-create
		STATUS		current
		DESCRIPTION	"OSPF neighbor: RowStatus."
		::= { iswOspfNeighborConfEntry 4 }
--9
	iswOspfVlanIntfTable	OBJECT-TYPE
		SYNTAX		SEQUENCE OF IswOspfVlanIntfEntry
		MAX-ACCESS	not-accessible
		STATUS		current
		DESCRIPTION	"OSPF vlan interface table.
					For OSPF interface configuration. Max interface(entry) size: 5."
		::= { iswOspfConfig 9 }
		
	iswOspfVlanIntfEntry	OBJECT-TYPE
		SYNTAX		IswOspfVlanIntfEntry
		MAX-ACCESS	not-accessible
		STATUS		current
		DESCRIPTION	"OSPF vlan interface entry."
		INDEX		{ iswOspfIfVlanId }
		::= { iswOspfVlanIntfTable 1 }
		
	IswOspfVlanIntfEntry ::= SEQUENCE{
		iswOspfIfVlanId				Integer32,
		iswOspfIfAreaId				Unsigned32,
		iswOspfIfPriority 			Integer32,
		iswOspfIfCost				Integer32,
		iswOspfIfHelloInterval		Integer32,
		iswOspfIfDeadInterval		Integer32,
		iswOspfIfRetransmitInterval	Integer32,
		iswOspfIfTransmitDelay		Integer32,
		iswOspfIfNetworkType		Integer32,
		iswOspfIfMTUIgnoreEnable	Integer32,
		iswOspfIfAuthMode			Integer32,
		iswOspfIfAuthKey			OCTET STRING,
		iswOspfIfMsgDigestKeyId		Integer32,
		iswOspfIfMsgDigestKey		OCTET STRING,
		iswOspfIfTrackUpBitmap		OCTET STRING,
		iswOspfIfTrackDownBitmap	OCTET STRING,
		iswOspfIfTrackThreshold		Integer32,
		iswOspfIfRowStatus			RowStatus
	}

	iswOspfIfVlanId	OBJECT-TYPE
		SYNTAX		Integer32 ( 1 .. 4094 )
		MAX-ACCESS	not-accessible
		STATUS		current
		DESCRIPTION	"OSPF vlan interface: vlan."
		::= { iswOspfVlanIntfEntry 1 }

	iswOspfIfAreaId	OBJECT-TYPE
		SYNTAX		Unsigned32 ( 0 .. 4294967295 )
		MAX-ACCESS	read-create
		STATUS		current
		DESCRIPTION	"OSPF Vlan Interface Area Id, default is 0"
		DEFVAL		{0}
		::= { iswOspfVlanIntfEntry 2 }

	iswOspfIfPriority	OBJECT-TYPE
		SYNTAX		Integer32 ( 0 .. 255 )
		MAX-ACCESS	read-create
		STATUS		current
		DESCRIPTION	"OSPF Vlan Interface priority, default is 1"
		DEFVAL		{1}
		::= { iswOspfVlanIntfEntry 3 }

	iswOspfIfCost	OBJECT-TYPE
		SYNTAX		Integer32 ( 1 .. 65535 )
		MAX-ACCESS	read-create
		STATUS		current
		DESCRIPTION	"OSPF Vlan Interface cost, default is 10"
		DEFVAL		{10}
		::= { iswOspfVlanIntfEntry 4 }

	iswOspfIfHelloInterval	OBJECT-TYPE
		SYNTAX		Integer32 ( 1 .. 65535 )
		UNITS       "second"
		MAX-ACCESS	read-create
		STATUS		current
		DESCRIPTION	"OSPF Vlan Interface Time between HELLO packets, default is 10"
		DEFVAL		{10}
		::= { iswOspfVlanIntfEntry 5 }

	iswOspfIfDeadInterval	OBJECT-TYPE
		SYNTAX		Integer32 ( 1 .. 65535 )
		UNITS       "second"
		MAX-ACCESS	read-create
		STATUS		current
		DESCRIPTION	"OSPF Vlan Interface Interval after which a neighbor is declared dead, default is 40"
		DEFVAL		{40}
		::= { iswOspfVlanIntfEntry 6 }

	iswOspfIfRetransmitInterval	OBJECT-TYPE
		SYNTAX		Integer32 ( 3 .. 65535 )
		UNITS       "second"
		MAX-ACCESS	read-create
		STATUS		current
		DESCRIPTION	"OSPF Vlan Interface Time between retransmitting lost link state advertisements, default is 5"
		DEFVAL		{5}
		::= { iswOspfVlanIntfEntry 7 }

	iswOspfIfTransmitDelay	OBJECT-TYPE
		SYNTAX		Integer32 ( 1 .. 65535 )
		UNITS       "second"
		MAX-ACCESS	read-create
		STATUS		current
		DESCRIPTION	"OSPF Vlan Interface Link state transmit delay, default is 1"
		DEFVAL		{1}
		::= { iswOspfVlanIntfEntry 8 }

	iswOspfIfNetworkType	OBJECT-TYPE
		SYNTAX		Integer32 { point-to-point(1), broadcast(2), no-broadcast(3), point-to-multipoint(4) }
		MAX-ACCESS	read-create
		STATUS		current
		DESCRIPTION	"OSPF Vlan Interface network type, default is broadcast(2)"
		DEFVAL		{2}
		::= { iswOspfVlanIntfEntry 9 }

	iswOspfIfMTUIgnoreEnable	OBJECT-TYPE
		SYNTAX		Integer32 { disable (0), enable (1) }
		MAX-ACCESS	read-create
		STATUS		current
		DESCRIPTION	"OSPF Vlan Interface Link state transmit delay, default is disable"
		DEFVAL		{0}
		::= { iswOspfVlanIntfEntry 10 }

	iswOspfIfAuthMode	OBJECT-TYPE
		SYNTAX		Integer32 { disable(0), null(1), simple(2), crypt(3) }
		MAX-ACCESS	read-create
		STATUS		current
		DESCRIPTION	"OSPF Vlan Interface Authentication-key Config, default is disable(0)"
		DEFVAL		{0}
		::= { iswOspfVlanIntfEntry 11 }

	iswOspfIfAuthKey	OBJECT-TYPE
		SYNTAX		OCTET STRING  ( SIZE ( 0..8 ) )
		MAX-ACCESS	read-create
		STATUS		current
		DESCRIPTION	"OSPF Vlan Interface The Authentication Key.
					The default value is empty string which is all nulls (0x00)."
		::= { iswOspfVlanIntfEntry 12 }

	iswOspfIfMsgDigestKeyId	OBJECT-TYPE
		SYNTAX		Integer32 ( 1 .. 255 )
		MAX-ACCESS	read-create
		STATUS		current
		DESCRIPTION	"OSPF Vlan Interface Message Digest Key-ID, default is 1"
		DEFVAL		{1}
		::= { iswOspfVlanIntfEntry 13 }

	iswOspfIfMsgDigestKey	OBJECT-TYPE
		SYNTAX		OCTET STRING  ( SIZE ( 0..16 ) )
		MAX-ACCESS	read-create
		STATUS		current
		DESCRIPTION	"OSPF Vlan Interface Message Digest Key.
					The default value is empty string which is all nulls (0x00)."
		::= { iswOspfVlanIntfEntry 14 }

	iswOspfIfTrackUpBitmap	OBJECT-TYPE
		SYNTAX		OCTET STRING  ( SIZE ( 8 ) )
		MAX-ACCESS	read-create
		STATUS		current
		DESCRIPTION	"Up-list Track object bitmap.
					Byte[0] for track 8  ~ track 1 , bit 1 for track object 1, bit 2 for track object 2 and so on.
					Byte[1] for track 16 ~ track 9 , bit 9 for track object 9, bit 10 for track object 10 and so on.
					Byte[2] for track 24 ~ track 17, bit 17 for track object 17, bit 18 for track object 18 and so on.
					Byte[3] for track 32 ~ track 25, bit 25 for track object 25, bit 26 for track object 26 and so on.
					Byte[4] for track 40 ~ track 33, bit 33 for track object 33, bit 34 for track object 34 and so on.
					Byte[5] for track 48 ~ track 41, bit 41 for track object 41, bit 42 for track object 42 and so on.
					Byte[6] for track 56 ~ track 49, bit 49 for track object 49, bit 50 for track object 50 and so on.
					Byte[7] for track 64 ~ track 57, bit 57 for track object 57, bit 58 for track object 58 and so on.
					Byte[0] = 0x0 .. 0xFF
					Byte[1] = 0x0 .. 0xFF
					Byte[2] = 0x0 .. 0xFF
					Byte[3] = 0x0 .. 0xFF
					Byte[4] = 0x0 .. 0xFF
					Byte[5] = 0x0 .. 0xFF
					Byte[6] = 0x0 .. 0xFF
					Byte[7] = 0x0 .. 0xFF
					Default 0x0 means no track entry binding on OSPF of the interface vlan."
		::= { iswOspfVlanIntfEntry 15 }

	iswOspfIfTrackDownBitmap	OBJECT-TYPE
		SYNTAX		OCTET STRING  ( SIZE ( 8 ) )
		MAX-ACCESS	read-create
		STATUS		current
		DESCRIPTION	"Down-list Track object bitmap.
					Byte[0] for track 8  ~ track 1 , bit 1 for track object 1, bit 2 for track object 2 and so on.
					Byte[1] for track 16 ~ track 9 , bit 9 for track object 9, bit 10 for track object 10 and so on.
					Byte[2] for track 24 ~ track 17, bit 17 for track object 17, bit 18 for track object 18 and so on.
					Byte[3] for track 32 ~ track 25, bit 25 for track object 25, bit 26 for track object 26 and so on.
					Byte[4] for track 40 ~ track 33, bit 33 for track object 33, bit 34 for track object 34 and so on.
					Byte[5] for track 48 ~ track 41, bit 41 for track object 41, bit 42 for track object 42 and so on.
					Byte[6] for track 56 ~ track 49, bit 49 for track object 49, bit 50 for track object 50 and so on.
					Byte[7] for track 64 ~ track 57, bit 57 for track object 57, bit 58 for track object 58 and so on.
					Byte[0] = 0x0 .. 0xFF
					Byte[1] = 0x0 .. 0xFF
					Byte[2] = 0x0 .. 0xFF
					Byte[3] = 0x0 .. 0xFF
					Byte[4] = 0x0 .. 0xFF
					Byte[5] = 0x0 .. 0xFF
					Byte[6] = 0x0 .. 0xFF
					Byte[7] = 0x0 .. 0xFF
					Default 0x0 means no track entry binding on OSPF of the interface vlan."
		::= { iswOspfVlanIntfEntry 16 }
	
	iswOspfIfTrackThreshold	OBJECT-TYPE
		SYNTAX		Integer32 ( 1 .. 16 )
		MAX-ACCESS	read-create
		STATUS		current
		DESCRIPTION	"Threshold to indicate track status is up or down, default is 1"
		DEFVAL		{1}
		::= { iswOspfVlanIntfEntry 17 }
		
	iswOspfIfRowStatus	OBJECT-TYPE
		SYNTAX		RowStatus
		MAX-ACCESS	read-create
		STATUS		current
		DESCRIPTION	"OSPF Vlan Interfacee: RowStatus."
		::= { iswOspfVlanIntfEntry 18 }
--
--1
	iswVrrpVlanIntfTable	OBJECT-TYPE
		SYNTAX		SEQUENCE OF IswVrrpVlanIntfEntry
		MAX-ACCESS	not-accessible
		STATUS		current
		DESCRIPTION	"VRRP vlan interface table.
					For VRRP interface configuration. Max interface(entry) size: 5."
		::= { iswVrrpGroupConfig 1 }
		
	iswVrrpVlanIntfEntry	OBJECT-TYPE
		SYNTAX		IswVrrpVlanIntfEntry
		MAX-ACCESS	not-accessible
		STATUS		current
		DESCRIPTION	"VRRP vlan interface entry."
		INDEX		{ iswVrrpGroupVifId, iswVrrpGroupVrid }
		::= { iswVrrpVlanIntfTable 1 }
		
	IswVrrpVlanIntfEntry ::= SEQUENCE{
		iswVrrpGroupVifId			Integer32,
		iswVrrpGroupVrid			Integer32,
		iswVrrpGroupVirtualRouterIPAddr		IpAddress,
		iswVrrpGroupAdvInterval			Integer32,
		iswVrrpGroupPriority			Integer32,
		iswVrrpGroupPreempt			Integer32,
		iswVrrpGroupLearnMasterAdvInt		Integer32,
		iswVrrpGroupAuthMode			Integer32,
		iswVrrpGroupAuthData			OCTET STRING,
		iswVrrpGroupTrackThreshold		Integer32,
		iswVrrpGroupTrackUpBitmap		OCTET STRING,
		iswVrrpGroupTrackDownBitmap		OCTET STRING,
		iswVrrpGroupRowStatus			RowStatus
	}

	iswVrrpGroupVifId	OBJECT-TYPE
		SYNTAX		Integer32 ( 1 .. 4094 )
		MAX-ACCESS	not-accessible
		STATUS		current
		DESCRIPTION	"VRRP vlan interface: vlan."
		::= { iswVrrpVlanIntfEntry 1 }

	iswVrrpGroupVrid	OBJECT-TYPE
		SYNTAX		Integer32 ( 1 .. 255 )
		MAX-ACCESS	not-accessible
		STATUS		current
		DESCRIPTION	"VRRP Vlan Interface VRRP Id, default is 0"
		DEFVAL		{0}
		::= { iswVrrpVlanIntfEntry 2 }

	iswVrrpGroupVirtualRouterIPAddr	OBJECT-TYPE
		SYNTAX		IpAddress
		MAX-ACCESS	read-create
		STATUS		current
		DESCRIPTION	"VRRP Vlan Interface Router Address. Virtual router IP should be in same subnet with VLAN interface.
				The default value is 0.0.0.0."
		::= { iswVrrpVlanIntfEntry 3 }

	iswVrrpGroupAdvInterval	OBJECT-TYPE
		SYNTAX		Integer32 ( 1 .. 4095 )
		-- UNITS       "0.1 second"
		MAX-ACCESS	read-create
		STATUS		current
		DESCRIPTION	"VRRP Vlan Interface Adv-Interval. When VRRP is processing on V3, it can be setting in the range of 1~4095, unit is 0.01 second. Default value is 100.
In other case, it can be setting in the range of 1~255, unit is 1 second. Default value is 1."
		-- DEFVAL		{10}
		::= { iswVrrpVlanIntfEntry 4 }

	iswVrrpGroupPriority	OBJECT-TYPE
		SYNTAX		Integer32 ( 1 .. 254 )
		MAX-ACCESS	read-create
		STATUS		current
		DESCRIPTION	"VRRP Vlan Interface priority, default is 100"
		DEFVAL		{100}
		::= { iswVrrpVlanIntfEntry 5 }

	iswVrrpGroupPreempt	OBJECT-TYPE
		SYNTAX		Integer32 { disable (0), enable (1) }
		MAX-ACCESS	read-create
		STATUS		current
		DESCRIPTION	"VRRP Vlan Interface Group Preempt, default is enable(1)"
		DEFVAL		{1}
		::= { iswVrrpVlanIntfEntry 6 }

	iswVrrpGroupLearnMasterAdvInt	OBJECT-TYPE
		SYNTAX		Integer32 { disable (0), enable (1) }
		MAX-ACCESS	read-create
		STATUS		current
		DESCRIPTION	"VRRP Vlan Interface Group learn master Adv-interval, default is disable(0)"
		DEFVAL		{0}
		::= { iswVrrpVlanIntfEntry 7 }

	iswVrrpGroupAuthMode	OBJECT-TYPE
		SYNTAX		Integer32 { disable (0), enable (1) }
		MAX-ACCESS	read-create
		STATUS		current
		DESCRIPTION	"VRRP Vlan Interface Group Preempt, default is disable(0)"
		DEFVAL		{0}
		::= { iswVrrpVlanIntfEntry 8 }

	iswVrrpGroupAuthData	OBJECT-TYPE
		SYNTAX		OCTET STRING  ( SIZE ( 0..8 ) )
		MAX-ACCESS	read-create
		STATUS		current
		DESCRIPTION	"VRRP Vlan Interface Authentication Key.
					The default value is empty string which is all nulls (0x00)."
		::= { iswVrrpVlanIntfEntry 9 }
	iswVrrpGroupTrackThreshold	OBJECT-TYPE
		SYNTAX		Integer32 ( 1 .. 16 )
		MAX-ACCESS	read-create
		STATUS		current
		DESCRIPTION	"Threshold to indicate track status id up or down.default is 1"
		DEFVAL		{1}
		::= { iswVrrpVlanIntfEntry 10 }
	iswVrrpGroupTrackUpBitmap	OBJECT-TYPE
		SYNTAX		OCTET STRING  ( SIZE ( 8 ) )
		MAX-ACCESS	read-create
		STATUS		current
		DESCRIPTION	"Up-list track object bitmap.
					Byte[0] for track 8  ~ track 1 , bit 1 for track object 1, bit 2 for track object 2 and so on.
					Byte[1] for track 16 ~ track 9 , bit 9 for track object 9, bit 10 for track object 10 and so on.
					Byte[2] for track 24 ~ track 17, bit 17 for track object 17, bit 18 for track object 18 and so on.
					Byte[3] for track 32 ~ track 25, bit 25 for track object 25, bit 26 for track object 26 and so on.
					Byte[4] for track 40 ~ track 33, bit 33 for track object 33, bit 34 for track object 34 and so on.
					Byte[5] for track 48 ~ track 41, bit 41 for track object 41, bit 42 for track object 42 and so on.
					Byte[6] for track 56 ~ track 49, bit 49 for track object 49, bit 50 for track object 50 and so on.
					Byte[7] for track 64 ~ track 57, bit 57 for track object 57, bit 58 for track object 58 and so on.
					Byte[0] = 0x0 .. 0xFF
					Byte[1] = 0x0 .. 0xFF
					Byte[2] = 0x0 .. 0xFF
					Byte[3] = 0x0 .. 0xFF
					Byte[4] = 0x0 .. 0xFF
					Byte[5] = 0x0 .. 0xFF
					Byte[6] = 0x0 .. 0xFF
					Byte[7] = 0x0 .. 0xFF
					Default 0x0 means no track entry binding on the VRRP entry of the interface vlan."
		::= { iswVrrpVlanIntfEntry 11 }
	iswVrrpGroupTrackDownBitmap	OBJECT-TYPE
		SYNTAX		OCTET STRING  ( SIZE ( 8 ) )
		MAX-ACCESS	read-create
		STATUS		current
		DESCRIPTION	"Down-list track object bitmap.
					Byte[0] for track 8  ~ track 1 , bit 1 for track object 1, bit 2 for track object 2 and so on.
					Byte[1] for track 16 ~ track 9 , bit 9 for track object 9, bit 10 for track object 10 and so on.
					Byte[2] for track 24 ~ track 17, bit 17 for track object 17, bit 18 for track object 18 and so on.
					Byte[3] for track 32 ~ track 25, bit 25 for track object 25, bit 26 for track object 26 and so on.
					Byte[4] for track 40 ~ track 33, bit 33 for track object 33, bit 34 for track object 34 and so on.
					Byte[5] for track 48 ~ track 41, bit 41 for track object 41, bit 42 for track object 42 and so on.
					Byte[6] for track 56 ~ track 49, bit 49 for track object 49, bit 50 for track object 50 and so on.
					Byte[7] for track 64 ~ track 57, bit 57 for track object 57, bit 58 for track object 58 and so on.
					Byte[0] = 0x0 .. 0xFF
					Byte[1] = 0x0 .. 0xFF
					Byte[2] = 0x0 .. 0xFF
					Byte[3] = 0x0 .. 0xFF
					Byte[4] = 0x0 .. 0xFF
					Byte[5] = 0x0 .. 0xFF
					Byte[6] = 0x0 .. 0xFF
					Byte[7] = 0x0 .. 0xFF
					Default 0x0 means no track entry binding on the VRRP entry of the interface vlan."
		::= { iswVrrpVlanIntfEntry 12 }

	iswVrrpGroupRowStatus	OBJECT-TYPE
		SYNTAX		RowStatus
		MAX-ACCESS	read-create
		STATUS		current
		DESCRIPTION	"VRRP Vlan Interfacee: RowStatus."
		::= { iswVrrpVlanIntfEntry 13 }
--
	iswRipRouteTable	OBJECT-TYPE
		SYNTAX		SEQUENCE OF IswRipRouteEntry
		MAX-ACCESS	not-accessible
		STATUS		current
		DESCRIPTION	"RIP Route table. Max entry size: 512."
		::= { iswRipRoute 1 }
		
	iswRipRouteEntry	OBJECT-TYPE
		SYNTAX		IswRipRouteEntry
		MAX-ACCESS	not-accessible
		STATUS		current
		DESCRIPTION	"Rip Route entry."
		INDEX		{ iswRipRouteIndex }
		::= { iswRipRouteTable 1 }
		
	IswRipRouteEntry ::= SEQUENCE{
		iswRipRouteIndex	Integer32,
		iswRipRouteVlan 	Integer32,
		iswRipRouteNetwork	IpAddress,
		iswRipRouteNetmask	IpAddress,
		iswRipRouteGateway	IpAddress,
		iswRipRouteMetric	Integer32,
		iswRipRouteAging	Integer32,
		iswRipRouteStatus	Integer32
	}

	iswRipRouteIndex	OBJECT-TYPE
		SYNTAX		Integer32 ( 1 .. 512 )
		MAX-ACCESS	not-accessible
		STATUS		current
		DESCRIPTION	"The row index of the RIP routing table."
		::= { iswRipRouteEntry 1 }  

	iswRipRouteVlan 	OBJECT-TYPE
		SYNTAX		Integer32   (1..4094)
		MAX-ACCESS	read-only
		STATUS		current
		DESCRIPTION	"It is the VLAN interface ID also same as the VLAN ID which is
					the Route of the RIP packet come from VLAN ID."
		::= { iswRipRouteEntry 2 }

	iswRipRouteNetwork	OBJECT-TYPE
		SYNTAX		IpAddress
		MAX-ACCESS	read-only
		STATUS		current
		DESCRIPTION	"The destination network address for the RIP route."
		::= { iswRipRouteEntry 3 }

	iswRipRouteNetmask	OBJECT-TYPE
		SYNTAX		IpAddress
		MAX-ACCESS	read-only
		STATUS		current
		DESCRIPTION	"The network subnet mask for the RIP route."
		::= { iswRipRouteEntry 4 }

	iswRipRouteGateway	OBJECT-TYPE
		SYNTAX		IpAddress
		MAX-ACCESS	read-only
		STATUS		current
		DESCRIPTION	"The next hop gateway address of the RIP route."
		::= { iswRipRouteEntry 5 }

	iswRipRouteMetric	OBJECT-TYPE
		SYNTAX		Integer32   (1..16)
		MAX-ACCESS	read-only
		STATUS		current
		DESCRIPTION	"It is the metric of the RIP route. The value range is 1 to 16."
		::= { iswRipRouteEntry 6 }

	iswRipRouteAging 	OBJECT-TYPE
		SYNTAX		Integer32   (0..3600)
		UNITS           "second"
		MAX-ACCESS	read-only
		STATUS		current
		DESCRIPTION	"It is the timeout value of Routing information timeout timer
					or Garbage collection timer. The timeout type relate to iswRipRouteStatus."
		::= { iswRipRouteEntry 7 }

  	iswRipRouteStatus 	OBJECT-TYPE
		SYNTAX		Integer32   { aging(1), gc(2)  }
		MAX-ACCESS	read-only
		STATUS		current
		DESCRIPTION	"It is the type of iswRipRouteAging.
					aging is for Routing information timer stage
					gc is for Garbage collection timer stage."
		::= { iswRipRouteEntry 8 }
--

	iswRipRouteDeleteVlan	OBJECT-TYPE
		SYNTAX		Integer32 ( 1 .. 4094 ) 
		MAX-ACCESS	read-write
		STATUS		current
		DESCRIPTION	"Vlan id for Rip route delete. (deleteByVlan)"
		::= { iswRipRouteDeleteCtrl 1 }

	iswRipRouteDeleteType	OBJECT-TYPE
		SYNTAX		Integer32 { deleteAll(0),deleteByVlan(1)  }
		MAX-ACCESS	read-write
		STATUS		current
		DESCRIPTION	"Rip route delete type."
		::= { iswRipRouteDeleteCtrl 2 }
--
	iswOspfRouteTable	OBJECT-TYPE
		SYNTAX		SEQUENCE OF IswOspfRouteEntry
		MAX-ACCESS	not-accessible
		STATUS		current
		DESCRIPTION	"OSPF Route table. Max entry size: 512."
		::= { iswLayer3Status 2 }
		
	iswOspfRouteEntry	OBJECT-TYPE
		SYNTAX		IswOspfRouteEntry
		MAX-ACCESS	not-accessible
		STATUS		current
		DESCRIPTION	"OSPF Route entry."
		INDEX		{ iswOspfRouteIndex }
		::= { iswOspfRouteTable 1 }
		
	IswOspfRouteEntry ::= SEQUENCE{
		iswOspfRouteIndex			Integer32,
		iswOspfRouteType			Integer32,
		iswOspfRouteNetworkPrefix		IpAddress,
		iswOspfRouteNetworkPrefixLen		IpAddress,
		iswOspfRouteNetworkArea			IpAddress,
		iswOspfRouteNetworkPathType		Integer32,
		iswOspfRouteNetworkCost			Integer32,
		iswOspfRouteNetworkNextHopsCount	Integer32,
		iswOspfRouteNetworkNextHops		OCTET STRING,
		iswOspfRouteRouterAddress		IpAddress,
		iswOspfRouteRouterArea			IpAddress,
		iswOspfRouteRouterPathType		Integer32,
		iswOspfRouteRouterCost			Integer32,
		iswOspfRouteRouterFlag			Integer32,
		iswOspfRouteRouterNextHopsCount		Integer32,
		iswOspfRouteRouterNextHops		OCTET STRING,
		iswOspfRouteExternalPrefix		IpAddress,
		iswOspfRouteExternalPrefixLen		IpAddress,
		iswOspfRouteExternalArea		IpAddress,
		iswOspfRouteExternalPathType		Integer32,
		iswOspfRouteExternalCost		Integer32,
		iswOspfRouteExternalExtCost		Integer32,
		iswOspfRouteExternalTag			Integer32,
		iswOspfRouteExternalNextHopsCount	Integer32,
		iswOspfRouteExternalNextHops		OCTET STRING
	}

	iswOspfRouteIndex	OBJECT-TYPE
		SYNTAX		Integer32 ( 1 .. 512 )
		MAX-ACCESS	not-accessible
		STATUS		current
		DESCRIPTION	"The row index of the OSPF routing table."
		::= { iswOspfRouteEntry 1 }  

	iswOspfRouteType 	OBJECT-TYPE
		SYNTAX		Integer32   (1..3)
		MAX-ACCESS	read-only
		STATUS		current
		DESCRIPTION	" 1: network, Type 2: router, Type 3: external" 
		::= { iswOspfRouteEntry 2 }

	iswOspfRouteNetworkPrefix	OBJECT-TYPE
		SYNTAX		IpAddress
		MAX-ACCESS	read-only
		STATUS		current
		DESCRIPTION	"The network address of network for the OSPF route."
		::= { iswOspfRouteEntry 3 }

	iswOspfRouteNetworkPrefixLen	OBJECT-TYPE
		SYNTAX		IpAddress
		MAX-ACCESS	read-only
		STATUS		current
		DESCRIPTION	"The network mask of network for the OSPF route."
		::= { iswOspfRouteEntry 4 }

	iswOspfRouteNetworkArea	OBJECT-TYPE
		SYNTAX		IpAddress
		MAX-ACCESS	read-only
		STATUS		current
		DESCRIPTION	"The area Id of network for the OSPF route."
		::= { iswOspfRouteEntry 5 }

	iswOspfRouteNetworkPathType	OBJECT-TYPE
		SYNTAX		Integer32
		MAX-ACCESS	read-only
		STATUS		current
		DESCRIPTION	"The path type of network for the OSPF route."
		::= { iswOspfRouteEntry 6 }

	iswOspfRouteNetworkCost	OBJECT-TYPE
		SYNTAX		Integer32
		MAX-ACCESS	read-only
		STATUS		current
		DESCRIPTION	"The cost of network for the OSPF route."
		::= { iswOspfRouteEntry 7 }

	iswOspfRouteNetworkNextHopsCount	OBJECT-TYPE
		SYNTAX		Integer32   (0..16)
		MAX-ACCESS	read-only
		STATUS		current
		DESCRIPTION	"The hops number of network for the OSPF route."
		::= { iswOspfRouteEntry 8 }

	iswOspfRouteNetworkNextHops	OBJECT-TYPE
		SYNTAX		OCTET STRING  ( SIZE ( 0..96 ) )
		MAX-ACCESS	read-only
		STATUS		current
		DESCRIPTION	"The hops (address and vlan-interface) of network for the OSPF route."
		::= { iswOspfRouteEntry 9 }

	iswOspfRouteRouterAddress	OBJECT-TYPE
		SYNTAX		IpAddress
		MAX-ACCESS	read-only
		STATUS		current
		DESCRIPTION	"The address of router for the OSPF route."
		::= { iswOspfRouteEntry 10 }

	iswOspfRouteRouterArea	OBJECT-TYPE
		SYNTAX		IpAddress
		MAX-ACCESS	read-only
		STATUS		current
		DESCRIPTION	"The area Id of router for the OSPF route."
		::= { iswOspfRouteEntry 11 }

	iswOspfRouteRouterPathType 	OBJECT-TYPE
		SYNTAX		Integer32
		MAX-ACCESS	read-only
		STATUS		current
		DESCRIPTION	"The path type of router type for the OSPF route."
		::= { iswOspfRouteEntry 12 }

	iswOspfRouteRouterCost 	OBJECT-TYPE
		SYNTAX		Integer32
		MAX-ACCESS	read-only
		STATUS		current
		DESCRIPTION	"The cost of router type for the OSPF route."
		::= { iswOspfRouteEntry 13 }

	iswOspfRouteRouterFlag 	OBJECT-TYPE
		SYNTAX		Integer32
		MAX-ACCESS	read-only
		STATUS		current
		DESCRIPTION	"The flag of router type for the OSPF route."
		::= { iswOspfRouteEntry 14 }

	iswOspfRouteRouterNextHopsCount	OBJECT-TYPE
		SYNTAX		Integer32   (0..16)
		MAX-ACCESS	read-only
		STATUS		current
		DESCRIPTION	"The hops number of network for the OSPF route."
		::= { iswOspfRouteEntry 15 }

	iswOspfRouteRouterNextHops	OBJECT-TYPE
		SYNTAX		OCTET STRING  ( SIZE ( 0..96 ) )
		MAX-ACCESS	read-only
		STATUS		current
		DESCRIPTION	"The hops (address and vlan-interface) of network for the OSPF route."
		::= { iswOspfRouteEntry 16 }

	iswOspfRouteExternalPrefix	OBJECT-TYPE
		SYNTAX		IpAddress
		MAX-ACCESS	read-only
		STATUS		current
		DESCRIPTION	"The network address of external type for the OSPF route."
		::= { iswOspfRouteEntry 17 }

	iswOspfRouteExternalPrefixLen	OBJECT-TYPE
		SYNTAX		IpAddress
		MAX-ACCESS	read-only
		STATUS		current
		DESCRIPTION	"The network mask of external type for the OSPF route."
		::= { iswOspfRouteEntry 18 }

	iswOspfRouteExternalArea	OBJECT-TYPE
		SYNTAX		IpAddress
		MAX-ACCESS	read-only
		STATUS		current
		DESCRIPTION	"The area Id of external type for the OSPF route."
		::= { iswOspfRouteEntry 19 }

	iswOspfRouteExternalPathType 	OBJECT-TYPE
		SYNTAX		Integer32
		MAX-ACCESS	read-only
		STATUS		current
		DESCRIPTION	"The path type of external type for the OSPF route."
		::= { iswOspfRouteEntry 20 }

	iswOspfRouteExternalCost 	OBJECT-TYPE
		SYNTAX		Integer32
		MAX-ACCESS	read-only
		STATUS		current
		DESCRIPTION	"The cost of external type for the OSPF route."
		::= { iswOspfRouteEntry 21 }

	iswOspfRouteExternalExtCost 	OBJECT-TYPE
		SYNTAX		Integer32
		MAX-ACCESS	read-only
		STATUS		current
		DESCRIPTION	"The ext-cost of external type for the OSPF route."
		::= { iswOspfRouteEntry 22 }

	iswOspfRouteExternalTag 	OBJECT-TYPE
		SYNTAX		Integer32
		MAX-ACCESS	read-only
		STATUS		current
		DESCRIPTION	"The tag of external type for the OSPF route."
		::= { iswOspfRouteEntry 23 }

	iswOspfRouteExternalNextHopsCount	OBJECT-TYPE
		SYNTAX		Integer32   (0..16)
		MAX-ACCESS	read-only
		STATUS		current
		DESCRIPTION	"The hops number of external for the OSPF route."
		::= { iswOspfRouteEntry 24 }

	iswOspfRouteExternalNextHops	OBJECT-TYPE
		SYNTAX		OCTET STRING  ( SIZE ( 0..96 ) )
		MAX-ACCESS	read-only
		STATUS		current
		DESCRIPTION	"The hops (address and vlan-interface) of external for the OSPF route."
		::= { iswOspfRouteEntry 25 }
--
	iswOspfDatabaseTable	OBJECT-TYPE
		SYNTAX		SEQUENCE OF IswOspfDatabaseEntry
		MAX-ACCESS	not-accessible
		STATUS		current
		DESCRIPTION	"OSPF Database table. Max entry size: 512*4."
		::= { iswLayer3Status 3 }
		
	iswOspfDatabaseEntry	OBJECT-TYPE
		SYNTAX		IswOspfDatabaseEntry
		MAX-ACCESS	not-accessible
		STATUS		current
		DESCRIPTION	"OSPF Database entry."
		INDEX		{ iswOspfDatabaseIndex }
		::= { iswOspfDatabaseTable 1 }
		
	IswOspfDatabaseEntry ::= SEQUENCE{
		iswOspfDatabaseIndex					Integer32,
		iswOspfDatabaseRouterId					Integer32,
		iswOspfDatabaseAreaId					Integer32,
		iswOspfDatabaseLSAAge					Integer32,
		iswOspfDatabaseOptions					Integer32,
		iswOspfDatabaseLSAFlag					Integer32,
		iswOspfDatabaseLSAType					Integer32,
		iswOspfDatabaseLinkStateId				IpAddress,
		iswOspfDatabaseAdvRouter				IpAddress,
		iswOspfDatabaseLSASeqNumber				Unsigned32,
		iswOspfDatabaseChecksum					Integer32,
		iswOspfDatabaseLength					Integer32,
		iswOspfDatabaseRouterLinks				Integer32,
		iswOspfDatabaseRouterLinkData			OCTET STRING,
		iswOspfDatabaseNetworkMask				IpAddress,
		iswOspfDatabaseNetworkRouters			OCTET STRING,
		iswOspfDatabaseNetworkRouterNumber		Integer32,
		iswOspfDatabaseSummaryMask				IpAddress,
		iswOspfDatabaseSummaryTos				Integer32,
		iswOspfDatabaseSummaryMetric			Integer32,
		iswOspfDatabaseExternalMask				IpAddress,
		iswOspfDatabaseExternalTos				Integer32,
		iswOspfDatabaseExternalMetric			Integer32,
		iswOspfDatabaseExternalForwardAddr		IpAddress,
		iswOspfDatabaseExternalRouterTag		Integer32
	}

	iswOspfDatabaseIndex	OBJECT-TYPE
		SYNTAX		Integer32 ( 1 .. 2048 )
		MAX-ACCESS	not-accessible
		STATUS		current
		DESCRIPTION	"The row index of the OSPF database table."
		::= { iswOspfDatabaseEntry 1 }  

	iswOspfDatabaseRouterId 	OBJECT-TYPE
		SYNTAX		Integer32
		MAX-ACCESS	read-only
		STATUS		current
		DESCRIPTION	"The router Id for the OSPF database."
		::= { iswOspfDatabaseEntry 2 }

	iswOspfDatabaseAreaId 	OBJECT-TYPE
		SYNTAX		Integer32
		MAX-ACCESS	read-only
		STATUS		current
		DESCRIPTION	"The area Id for the OSPF database."
		::= { iswOspfDatabaseEntry 3 }

	iswOspfDatabaseLSAAge 	OBJECT-TYPE
		SYNTAX		Integer32
		MAX-ACCESS	read-only
		STATUS		current
		DESCRIPTION	"The LSA age for the OSPF database."
		::= { iswOspfDatabaseEntry 4 }

	iswOspfDatabaseOptions 	OBJECT-TYPE
		SYNTAX		Integer32
		MAX-ACCESS	read-only
		STATUS		current
		DESCRIPTION	"The options for the OSPF database."
		::= { iswOspfDatabaseEntry 5 }

	iswOspfDatabaseLSAFlag 	OBJECT-TYPE
		SYNTAX		Integer32
		MAX-ACCESS	read-only
		STATUS		current
		DESCRIPTION	"The LSA flag for the OSPF database."
		::= { iswOspfDatabaseEntry 6 }

	iswOspfDatabaseLSAType 	OBJECT-TYPE
		SYNTAX		Integer32
		MAX-ACCESS	read-only
		STATUS		current
		DESCRIPTION	"The LSA type for the OSPF database."
		::= { iswOspfDatabaseEntry 7 }

	iswOspfDatabaseLinkStateId 	OBJECT-TYPE
		SYNTAX		IpAddress
		MAX-ACCESS	read-only
		STATUS		current
		DESCRIPTION	"The link state Id for the OSPF database."
		::= { iswOspfDatabaseEntry 8 }

	iswOspfDatabaseAdvRouter 	OBJECT-TYPE
		SYNTAX		IpAddress
		MAX-ACCESS	read-only
		STATUS		current
		DESCRIPTION	"The adv-router for the OSPF database."
		::= { iswOspfDatabaseEntry 9 }

	iswOspfDatabaseLSASeqNumber 	OBJECT-TYPE
		SYNTAX		Unsigned32
		MAX-ACCESS	read-only
		STATUS		current
		DESCRIPTION	"The LSA sequence number for the OSPF database."
		::= { iswOspfDatabaseEntry 10 }

	iswOspfDatabaseChecksum 	OBJECT-TYPE
		SYNTAX		Integer32
		MAX-ACCESS	read-only
		STATUS		current
		DESCRIPTION	"The checksum for the OSPF database."
		::= { iswOspfDatabaseEntry 11 }

	iswOspfDatabaseLength 	OBJECT-TYPE
		SYNTAX		Integer32
		MAX-ACCESS	read-only
		STATUS		current
		DESCRIPTION	"The length for the OSPF database."
		::= { iswOspfDatabaseEntry 12 }

	iswOspfDatabaseRouterLinks 	OBJECT-TYPE
		SYNTAX		Integer32
		MAX-ACCESS	read-only
		STATUS		current
		DESCRIPTION	"The links number of database for the OSPF database."
		::= { iswOspfDatabaseEntry 13 }

	iswOspfDatabaseRouterLinkData	OBJECT-TYPE
		SYNTAX		OCTET STRING  ( SIZE ( 0..192 ) )
		MAX-ACCESS	read-only
		STATUS		current
		DESCRIPTION	"The links data of database for the OSPF database.
					Data format: [ID/Data/Type/Tos/Metric, ...]"
		::= { iswOspfDatabaseEntry 14 }

	iswOspfDatabaseNetworkMask	OBJECT-TYPE
		SYNTAX		IpAddress
		MAX-ACCESS	read-only
		STATUS		current
		DESCRIPTION	"The network maskfor the OSPF database."
		::= { iswOspfDatabaseEntry 15 }

	iswOspfDatabaseNetworkRouters	OBJECT-TYPE
		SYNTAX		OCTET STRING  ( SIZE ( 0..128 ) )
		MAX-ACCESS	read-only
		STATUS		current
		DESCRIPTION	"The netowrk attached routers for the OSPF database.
					Data format: [router address, ...]"
		::= { iswOspfDatabaseEntry 16 }

	iswOspfDatabaseNetworkRouterNumber	OBJECT-TYPE
		SYNTAX		Integer32
		MAX-ACCESS	read-only
		STATUS		current
		DESCRIPTION	"The network router number for the OSPF database."
		::= { iswOspfDatabaseEntry 17 }

	iswOspfDatabaseSummaryMask	OBJECT-TYPE
		SYNTAX		IpAddress
		MAX-ACCESS	read-only
		STATUS		current
		DESCRIPTION	"The netwrok mask of summary for the OSPF database."
		::= { iswOspfDatabaseEntry 18 }

	iswOspfDatabaseSummaryTos	OBJECT-TYPE
		SYNTAX		Integer32
		MAX-ACCESS	read-only
		STATUS		current
		DESCRIPTION	"The tos of summary for the OSPF database."
		::= { iswOspfDatabaseEntry 19 }

	iswOspfDatabaseSummaryMetric	OBJECT-TYPE
		SYNTAX		Integer32
		MAX-ACCESS	read-only
		STATUS		current
		DESCRIPTION	"The metirc of summary for the OSPF database."
		::= { iswOspfDatabaseEntry 20 }

	iswOspfDatabaseExternalMask	OBJECT-TYPE
		SYNTAX		IpAddress
		MAX-ACCESS	read-only
		STATUS		current
		DESCRIPTION	"The mask of external information for the OSPF database."
		::= { iswOspfDatabaseEntry 21 }

	iswOspfDatabaseExternalTos	OBJECT-TYPE
		SYNTAX		Integer32
		MAX-ACCESS	read-only
		STATUS		current
		DESCRIPTION	"The tos of external information for the OSPF database."
		::= { iswOspfDatabaseEntry 22 }

	iswOspfDatabaseExternalMetric	OBJECT-TYPE
		SYNTAX		Integer32
		MAX-ACCESS	read-only
		STATUS		current
		DESCRIPTION	"The metirc of external information for the OSPF database."
		::= { iswOspfDatabaseEntry 23 }

	iswOspfDatabaseExternalForwardAddr	OBJECT-TYPE
		SYNTAX		IpAddress
		MAX-ACCESS	read-only
		STATUS		current
		DESCRIPTION	"The forward address of external information for the OSPF database."
		::= { iswOspfDatabaseEntry 24 }

	iswOspfDatabaseExternalRouterTag	OBJECT-TYPE
		SYNTAX		Integer32
		MAX-ACCESS	read-only
		STATUS		current
		DESCRIPTION	"The router tag of external information for the OSPF database."
		::= { iswOspfDatabaseEntry 25 }
--
	iswOspfNeighborTable	OBJECT-TYPE
		SYNTAX		SEQUENCE OF IswOspfNeighborEntry
		MAX-ACCESS	not-accessible
		STATUS		current
		DESCRIPTION	"OSPF Database table. Max entry size: 512*2."
		::= { iswLayer3Status 4 }
		
	iswOspfNeighborEntry	OBJECT-TYPE
		SYNTAX		IswOspfNeighborEntry
		MAX-ACCESS	not-accessible
		STATUS		current
		DESCRIPTION	"OSPF Database entry."
		INDEX		{ iswOspfNeighborIndex }
		::= { iswOspfNeighborTable 1 }
		
	IswOspfNeighborEntry ::= SEQUENCE{
		iswOspfNeighborIndex		Integer32,
		iswOspfNeighborVlan		Integer32,
		iswOspfNeighborId		IpAddress,
		iswOspfNeighborPriority		Integer32,
		iswOspfNeighborNSM		Integer32,
		iswOspfNeighborISM		Integer32,
		iswOspfNeighborDeadTimer	Integer32,
		iswOspfNeighborSource		IpAddress,
		iswOspfNeighborLSRetansCnt	Integer32,
		iswOspfNeighborLSReqCnt		Integer32,
		iswOspfNeighborDBSumCnt		Integer32
	}

	iswOspfNeighborIndex	OBJECT-TYPE
		SYNTAX		Integer32 ( 1 .. 1024 )
		MAX-ACCESS	not-accessible
		STATUS		current
		DESCRIPTION	"The row index of the OSPF neighbor table."
		::= { iswOspfNeighborEntry 1 }  

	iswOspfNeighborVlan 	OBJECT-TYPE
		SYNTAX		Integer32
		MAX-ACCESS	read-only
		STATUS		current
		DESCRIPTION	"The neighbor vlan for the OSPF database."
		::= { iswOspfNeighborEntry 2 }

	iswOspfNeighborId 	OBJECT-TYPE
		SYNTAX		IpAddress
		MAX-ACCESS	read-only
		STATUS		current
		DESCRIPTION	"The neighbor Id for the OSPF database."
		::= { iswOspfNeighborEntry 3 }

	iswOspfNeighborPriority 	OBJECT-TYPE
		SYNTAX		Integer32
		MAX-ACCESS	read-only
		STATUS		current
		DESCRIPTION	"The neighbor priority for the OSPF database."
		::= { iswOspfNeighborEntry 4 }

	iswOspfNeighborNSM 	OBJECT-TYPE
		SYNTAX		Integer32   { down(2), attempt(3), init(4), two-way(5), exstart(6), exchange(7), loading(8), full(9) }
		MAX-ACCESS	read-only
		STATUS		current
		DESCRIPTION	"The neighbor NSM for the OSPF database."
		::= { iswOspfNeighborEntry 5 }

	iswOspfNeighborISM 	OBJECT-TYPE
		SYNTAX		Integer32   { down(1), loopback(2), waiting(3), point2point(4), dr-other(5), backup(6), dr(7) }
		MAX-ACCESS	read-only
		STATUS		current
		DESCRIPTION	"The neighbor ISM for the OSPF database."
		::= { iswOspfNeighborEntry 6 }

	iswOspfNeighborDeadTimer 	OBJECT-TYPE
		SYNTAX		Integer32
		MAX-ACCESS	read-only
		STATUS		current
		DESCRIPTION	"The neighbor deat time for the OSPF database."
		::= { iswOspfNeighborEntry 7 }

	iswOspfNeighborSource	OBJECT-TYPE
		SYNTAX		IpAddress
		MAX-ACCESS	read-only
		STATUS		current
		DESCRIPTION	"The neighbor source address for the OSPF database."
		::= { iswOspfNeighborEntry 8 }

	iswOspfNeighborLSRetansCnt 	OBJECT-TYPE
		SYNTAX		Integer32
		MAX-ACCESS	read-only
		STATUS		current
		DESCRIPTION	"The neighbor LS retans cnt for the OSPF database."
		::= { iswOspfNeighborEntry 9 }

	iswOspfNeighborLSReqCnt 	OBJECT-TYPE
		SYNTAX		Integer32
		MAX-ACCESS	read-only
		STATUS		current
		DESCRIPTION	"The neighbor LS req cnt for the OSPF database."
		::= { iswOspfNeighborEntry 10 }

	iswOspfNeighborDBSumCnt 	OBJECT-TYPE
		SYNTAX		Integer32
		MAX-ACCESS	read-only
		STATUS		current
		DESCRIPTION	"The neighbor DB sum cnt for the OSPF database."
		::= { iswOspfNeighborEntry 11 }
--
	iswVrrpGroupStateTable	OBJECT-TYPE
		SYNTAX		SEQUENCE OF IswVrrpGroupStateEntry
		MAX-ACCESS	not-accessible
		STATUS		current
		DESCRIPTION	"OSPF Database table. Max entry size: 8."
		::= { iswLayer3Status 5 }
		
	iswVrrpGroupStateEntry	OBJECT-TYPE
		SYNTAX		IswVrrpGroupStateEntry
		MAX-ACCESS	not-accessible
		STATUS		current
		DESCRIPTION	"OSPF Database entry."
		INDEX		{ iswVrrpGroupStateIndex }
		::= { iswVrrpGroupStateTable 1 }
		
	IswVrrpGroupStateEntry ::= SEQUENCE{
		iswVrrpGroupStateIndex					Integer32,
		iswVrrpGroupStateVifId					Integer32,
		iswVrrpGroupStateVrid					Integer32,
		iswVrrpGroupStateVIpaddr				IpAddress,
		iswVrrpGroupStateMac					PhysAddress,
		iswVrrpGroupStateState					Integer32,
		iswVrrpGroupStatePrio					Integer32,
		iswVrrpGroupStatePreempt				Integer32,
		iswVrrpGroupStateLearnMasterAdvInt		Integer32,
		iswVrrpGroupStateAdvInt					Integer32,
		iswVrrpGroupStateRemainTime				Integer32,
		iswVrrpGroupStateMasterAddr				IpAddress,
		iswVrrpGroupStateMasterAdvInt			Integer32,
		iswVrrpGroupStateMasterDownInt			Integer32,
		iswVrrpGroupStateMasterPrio				Integer32
	}

	iswVrrpGroupStateIndex	OBJECT-TYPE
		SYNTAX		Integer32 ( 1 .. 8 )
		MAX-ACCESS	not-accessible
		STATUS		current
		DESCRIPTION	"The row index of the VRRP Group status table."
		::= { iswVrrpGroupStateEntry 1 }  

	iswVrrpGroupStateVifId 	OBJECT-TYPE
		SYNTAX		Integer32
		MAX-ACCESS	read-only
		STATUS		current
		DESCRIPTION	"The interface vlan Id for the VRRP Group status"
		::= { iswVrrpGroupStateEntry 2 }

	iswVrrpGroupStateVrid 	OBJECT-TYPE
		SYNTAX		Integer32
		MAX-ACCESS	read-only
		STATUS		current
		DESCRIPTION	"The group Id for the VRRP Group status"
		::= { iswVrrpGroupStateEntry 3 }

	iswVrrpGroupStateVIpaddr	OBJECT-TYPE
		SYNTAX		IpAddress
		MAX-ACCESS	read-only
		STATUS		current
		DESCRIPTION	"The virtual IP address for the VRRP Group status"
		::= { iswVrrpGroupStateEntry 4 }

	iswVrrpGroupStateMac 	OBJECT-TYPE
		SYNTAX		PhysAddress
		MAX-ACCESS	read-only
		STATUS		current
		DESCRIPTION	"The virtual MAC address for the VRRP Group status"
		::= { iswVrrpGroupStateEntry 5 }

	iswVrrpGroupStateState 	OBJECT-TYPE
		SYNTAX		Integer32   { ini(1), master(2), backup(3) }
		MAX-ACCESS	read-only
		STATUS		current
		DESCRIPTION	"The group status for the VRRP Group status"
		::= { iswVrrpGroupStateEntry 6 }

	iswVrrpGroupStatePrio 	OBJECT-TYPE
		SYNTAX		Integer32
		MAX-ACCESS	read-only
		STATUS		current
		DESCRIPTION	"The priority for the VRRP Group status"
		::= { iswVrrpGroupStateEntry 7 }

	iswVrrpGroupStatePreempt 	OBJECT-TYPE
		SYNTAX		Integer32	{ disable(0), enable(1) }
		MAX-ACCESS	read-only
		STATUS		current
		DESCRIPTION	"The preemption for the VRRP Group status"
		::= { iswVrrpGroupStateEntry 8 }

	iswVrrpGroupStateLearnMasterAdvInt 	OBJECT-TYPE
		SYNTAX		Integer32
		UNITS		"1 cs = 0.01 second(v3)/1 second(others)"
		MAX-ACCESS	read-only
		STATUS		current
		DESCRIPTION	"The learn master advertisement interval for the VRRP Group status.
					When VRRP version is v3, the unit is 1 cs (0.01s).
					Others unit is 1 s"
		::= { iswVrrpGroupStateEntry 9 }

	iswVrrpGroupStateAdvInt 	OBJECT-TYPE
		SYNTAX		Integer32
		UNITS		"1 cs = 0.01 second(v3)/1 second(others)"
		MAX-ACCESS	read-only
		STATUS		current
		DESCRIPTION	"The advertisement interval for the VRRP Group status.
					When VRRP version is v3, the unit is 1 cs (0.01s).
					Others unit is 1 s"
		::= { iswVrrpGroupStateEntry 10 }

	iswVrrpGroupStateRemainTime 	OBJECT-TYPE
		SYNTAX		Integer32
		UNITS		"1 cs = 0.01 second(v3)/1 second(others)"
		MAX-ACCESS	read-only
		STATUS		current
		DESCRIPTION	"The state remain time for the VRRP Group status.
					When VRRP version is v3, the unit is 1 cs (0.01s).
					Others unit is 1 s"
		::= { iswVrrpGroupStateEntry 11 }

	iswVrrpGroupStateMasterAddr	OBJECT-TYPE
		SYNTAX		IpAddress
		MAX-ACCESS	read-only
		STATUS		current
		DESCRIPTION	"The master router address for the VRRP Group status"
		::= { iswVrrpGroupStateEntry 12 }

	iswVrrpGroupStateMasterAdvInt 	OBJECT-TYPE
		SYNTAX		Integer32
		UNITS		"1 cs = 0.01 second(v3)/1 second(others)"
		MAX-ACCESS	read-only
		STATUS		current
		DESCRIPTION	"The master advertisement interval for the VRRP Group status.
					When VRRP version is v3, the unit is 1 cs (0.01s).
					Others unit is 1 s"
		::= { iswVrrpGroupStateEntry 13 }

	iswVrrpGroupStateMasterDownInt 	OBJECT-TYPE
		SYNTAX		Integer32
		UNITS		"1 cs = 0.01 second(v3)/1 second(others)"
		MAX-ACCESS	read-only
		STATUS		current
		DESCRIPTION	"The master down interval for the VRRP Group status.
					When VRRP version is v3, the unit is 1 cs (0.01s).
					Others unit is 1 s"
		::= { iswVrrpGroupStateEntry 14 }

	iswVrrpGroupStateMasterPrio 	OBJECT-TYPE
		SYNTAX		Integer32
		MAX-ACCESS	read-only
		STATUS		current
		DESCRIPTION	"The master priority for the VRRP Group status"
		::= { iswVrrpGroupStateEntry 15 }

--8021x
	iswDot1xConfig		OBJECT IDENTIFIER
		::=  { isw8021x 1 }
		
	iswDot1xSystemAuthControl	OBJECT-TYPE
		SYNTAX		Integer32 { disable (0), enable (1) }
		MAX-ACCESS	read-write
		STATUS		current
		DESCRIPTION	"Enable/Disable system dot1x function."
		DEFVAL		{0}         
		::= { iswDot1xConfig 1 }
		
	iswDot1xRadiusServer	OBJECT IDENTIFIER
		::=  { isw8021x 2 }

	iswDot1xServerIp	OBJECT-TYPE
		SYNTAX		IpAddress
		MAX-ACCESS	read-write
		STATUS		current
		DESCRIPTION	"The IP address of RADIUS server.
					0.0.0.0 is 0 which is meaning disable Radius Server.
					Default is 0.0.0.0."
		::= { iswDot1xRadiusServer 1 }
		
	iswDot1xServerAuthPort	OBJECT-TYPE
		SYNTAX		Integer32 (1..65535)
		MAX-ACCESS	read-write
		STATUS		current
		DESCRIPTION	"The UDP port of RADIUS server for authentication. Default value is 1812."
		DEFVAL		{1812}
		::= { iswDot1xRadiusServer 2 }
		
	iswDot1xServerSecret	OBJECT-TYPE
		SYNTAX		OCTET STRING ( SIZE ( 0..16 ) )
		MAX-ACCESS	read-write
		STATUS		current
		DESCRIPTION	"The key is to be used between RADIUS server and Authenticator.
					The max char size is 16."
		::= { iswDot1xRadiusServer 3 }
		
	iswDot1xPaePort		OBJECT IDENTIFIER
		::=  { isw8021x 3 }
	
	iswDot1xPaePortConfigTable	OBJECT-TYPE
		SYNTAX		SEQUENCE OF IswDot1xPaePortConfigEntry
		MAX-ACCESS	not-accessible
		STATUS		current
		DESCRIPTION	"Pae port authentication configuration table. Max entry size: port number."
		::= { iswDot1xPaePort 1 }
		
	iswDot1xPaePortConfigEntry	OBJECT-TYPE
		SYNTAX		IswDot1xPaePortConfigEntry
		MAX-ACCESS	not-accessible
		STATUS		current
		DESCRIPTION	"Pae port authentication configuration entry."
		INDEX		{ iswDot1xAuthPaePortId }
		::= { iswDot1xPaePortConfigTable 1 } 
		
	IswDot1xPaePortConfigEntry ::= SEQUENCE{
		iswDot1xAuthPaePortId				IswGbeIndex,
		iswDot1xAuthControlledPortControl	Integer32,
		iswDot1xAuthQuietPeriod				Integer32,
		iswDot1xAuthTxPeriod				Integer32,
		iswDot1xAuthMaxReq					Integer32,
		iswDot1xAuthSuppTimeout 			Integer32,
		iswDot1xAuthServerTimeout 			Integer32,
		iswDot1xAuthReAuthEnabled 			Integer32,
		iswDot1xAuthReAuthPeriod			Integer32
                }
--1 
	iswDot1xAuthPaePortId	OBJECT-TYPE
		SYNTAX		IswGbeIndex
		MAX-ACCESS	not-accessible
		STATUS		current
		DESCRIPTION	"The index of PAE port."
		::= { iswDot1xPaePortConfigEntry 1 }
--2
	iswDot1xAuthControlledPortControl	OBJECT-TYPE
		SYNTAX		Integer32 { forceUnauthorized(1),forceAuthorized(2),auto(3)}
		MAX-ACCESS	read-write
		STATUS		current
		DESCRIPTION	"The authentication type of PAE port.
					forceUnauthorized (1):
							The Controlled Port is unauthorized unconditionally and ignore all the
							authentication operation on this Port.
					forceAuthorized (2):
							Disable 802.1x on the Port.
					auto(3):
							Enable 802.1x on the Port. Allow the Authenticator PAE state machine to
							control the value of AuthControlledPortStatus to reflect the outcome of the
							authentication Server. When configure Auto mode, then Port state will be
							reflect by Authenticator PAE state machine.
					"
		DEFVAL          {2}
		::= { iswDot1xPaePortConfigEntry 2 } 
--3    
	iswDot1xAuthQuietPeriod	OBJECT-TYPE
		SYNTAX		Integer32 (1..255)
		UNITS		"second"
		MAX-ACCESS	read-write
		STATUS		current
		DESCRIPTION	"The quiet period of PAE port." 
		DEFVAL		{60}
		::= { iswDot1xPaePortConfigEntry 3 }
--4		
	iswDot1xAuthTxPeriod	OBJECT-TYPE
		SYNTAX		Integer32 (1..255)
		UNITS		"second"
		MAX-ACCESS	read-write
		STATUS		current
		DESCRIPTION	"The timeout of authenticator waiting for EAP-Response/Identity from supplication of PAE port."
		DEFVAL		{30}
		::= { iswDot1xPaePortConfigEntry 4 } 
--5    
	iswDot1xAuthMaxReq	OBJECT-TYPE
		SYNTAX		Integer32 (1..10)
		MAX-ACCESS	read-write
		STATUS		current
		DESCRIPTION	"The max times of backend Authenticator send EAP-Request to supplicant before restarting the authentication process."
		DEFVAL		{2}
		::= { iswDot1xPaePortConfigEntry 5 } 
--6    
	iswDot1xAuthSuppTimeout	OBJECT-TYPE
		SYNTAX		Integer32 (1..255)
		UNITS		"second"
		MAX-ACCESS	read-write
		STATUS		current
		DESCRIPTION	"The timeout of authenticator wait for EAP-Response(exclude EAP-Request/Identify) after sending EAP-Request."
		DEFVAL		{30}
		::= { iswDot1xPaePortConfigEntry 6 } 
--7    
	iswDot1xAuthServerTimeout	OBJECT-TYPE
		SYNTAX		Integer32 (1..255)
		UNITS		"second"
		MAX-ACCESS	read-write
		STATUS		current
		DESCRIPTION	"The timeout of Authenticator wait Access-Challenge/Access-Accept/Access-Reject after sending Access-Request."
		DEFVAL		{30}
		::= { iswDot1xPaePortConfigEntry 7 } 
--8    
	iswDot1xAuthReAuthEnabled	OBJECT-TYPE
		SYNTAX		Integer32 { disable (0), enable (1) }
		MAX-ACCESS	read-write
		STATUS		current
		DESCRIPTION	"Enable/Disable re-authenticant of APE port."
		DEFVAL		{0}
		::= { iswDot1xPaePortConfigEntry 8 } 
--9    
	iswDot1xAuthReAuthPeriod	OBJECT-TYPE
		SYNTAX		Integer32 (30..3600)
		UNITS		"second"
		MAX-ACCESS	read-write
		STATUS		current
		DESCRIPTION	"The period of re-authenticant of PAE port."
		DEFVAL		{3600}
		::= { iswDot1xPaePortConfigEntry 9 }
--		
	iswDot1xPaePortCommandTable	OBJECT-TYPE
		SYNTAX		SEQUENCE OF IswDot1xPaePortCommandEntry
		MAX-ACCESS	not-accessible
		STATUS		current
		DESCRIPTION	"Pae port Command table. Max entry size: port number."
		::= { iswDot1xPaePort 2 }
		
	iswDot1xPaePortCommandEntry	OBJECT-TYPE
		SYNTAX		IswDot1xPaePortCommandEntry
		MAX-ACCESS	not-accessible
		STATUS		current
		DESCRIPTION	"Pae port Command entry."
		INDEX		{ iswDot1xCommandPaePortId }
		::= { iswDot1xPaePortCommandTable 1 } 
		
	IswDot1xPaePortCommandEntry ::= SEQUENCE{
		iswDot1xCommandPaePortId		IswGbeIndex,
		iswDot1xPaePortInitialize		Integer32,
		iswDot1xPaePortReauthenticate	Integer32
    } 
--1 
	iswDot1xCommandPaePortId	OBJECT-TYPE
		SYNTAX		IswGbeIndex
		MAX-ACCESS	not-accessible
		STATUS		current
		DESCRIPTION	"The index of PAE port."
		::= { iswDot1xPaePortCommandEntry 1 }  
--2    
	iswDot1xPaePortInitialize	OBJECT-TYPE
		SYNTAX		Integer32 { disable (0), enable (1) }
		MAX-ACCESS	read-write
		STATUS		current
		DESCRIPTION	"Set Enable to force PAE port re-initialize. Disable no action.
					When read this parameter, it presents port is in Initialize state or not in the stage.
					To set enable, please set iswDot1xSystemAuthControl to enable and set iswDot1xAuthControlledPortControl to auto."
		DEFVAL          {0}
		::= { iswDot1xPaePortCommandEntry 2 }
--3    
	iswDot1xPaePortReauthenticate	OBJECT-TYPE
		SYNTAX		Integer32 { disable (0), enable (1) }
		MAX-ACCESS	read-write
		STATUS		current
		DESCRIPTION	"Set Enable to PAE port re-authenticate. Disable no action.
					To set enable, please set iswDot1xSystemAuthControl to enable and set iswDot1xAuthControlledPortControl to auto."
		DEFVAL		{0}
		::= { iswDot1xPaePortCommandEntry 3 }
--
	iswDot1xPaePortInfoTable	OBJECT-TYPE
		SYNTAX		SEQUENCE OF IswDot1xPaePortInfoEntry
		MAX-ACCESS	not-accessible
		STATUS		current
		DESCRIPTION	"Pae port Info table. Max entry size: port number."
		::= { iswDot1xPaePort 3 }
		
	iswDot1xPaePortInfoEntry	OBJECT-TYPE
		SYNTAX		IswDot1xPaePortInfoEntry
		MAX-ACCESS	not-accessible
		STATUS		current
		DESCRIPTION	"Pae port Info entry."
		INDEX		{ iswDot1xInfoPaePortId }
		::= { iswDot1xPaePortInfoTable 1 } 
		
	IswDot1xPaePortInfoEntry ::= SEQUENCE{
		iswDot1xInfoPaePortId			IswGbeIndex,
		iswDot1xPaePortProtocolVersion	Integer32,
		iswDot1xPaePortCapabilities		Integer32
    } 
--1 
	iswDot1xInfoPaePortId	OBJECT-TYPE
		SYNTAX		IswGbeIndex
		MAX-ACCESS	not-accessible
		STATUS		current
		DESCRIPTION	"The index of PAE port."
		::= { iswDot1xPaePortInfoEntry 1 }
--2    
	iswDot1xPaePortProtocolVersion	OBJECT-TYPE
		SYNTAX		Integer32 (2)
		MAX-ACCESS	read-only
		STATUS		current
		DESCRIPTION	"The protocol version of PAE port."
		::= { iswDot1xPaePortInfoEntry 2 } 
--3    
	iswDot1xPaePortCapabilities	OBJECT-TYPE
		SYNTAX		Integer32 { authenticator(128) }
		MAX-ACCESS	read-only
		STATUS		current
		DESCRIPTION	"The capabilities of the PAE port."
		::= { iswDot1xPaePortInfoEntry 3 }
--
	iswDot1xPaePortStateTable	OBJECT-TYPE
		SYNTAX		SEQUENCE OF IswDot1xPaePortStateEntry
		MAX-ACCESS	not-accessible
		STATUS		current
		DESCRIPTION	"Pae port State table. Max entry size: port number."
		::= { iswDot1xPaePort 4 }
		
	iswDot1xPaePortStateEntry	OBJECT-TYPE
		SYNTAX		IswDot1xPaePortStateEntry
		MAX-ACCESS	not-accessible
		STATUS		current
		DESCRIPTION	"Pae port State entry."
		INDEX		{ iswDot1xStatePaePortId }
		::= { iswDot1xPaePortStateTable 1 } 
		
	IswDot1xPaePortStateEntry ::= SEQUENCE{
		iswDot1xStatePaePortId				IswGbeIndex,
		iswDot1xAuthPaeState				Integer32,
		iswDot1xAuthBackendAuthState		Integer32,
		iswDot1xAuthControlledPortStatus	Integer32
        }
--1 
	iswDot1xStatePaePortId	OBJECT-TYPE
		SYNTAX		IswGbeIndex
		MAX-ACCESS	not-accessible
		STATUS		current
		DESCRIPTION	"The index of PAE port."
		::= { iswDot1xPaePortStateEntry 1 }  
--2    
	iswDot1xAuthPaeState	OBJECT-TYPE
		SYNTAX		Integer32 {initialize(1),
								disconnected(2),
								connecting(3),
								authenticating(4),
								authenticated(5),
								aborting(6),
								held(7),
								force-auth(8),
								force-unauth(9)}
		MAX-ACCESS	read-only
		STATUS		current
		DESCRIPTION	"The authenticator status of PAE port."
		::= { iswDot1xPaePortStateEntry 2 } 
--3    
	iswDot1xAuthBackendAuthState	OBJECT-TYPE
		SYNTAX		Integer32 {initialize(1),
								idle(2),
								request(3),
								response(4),
								success(5),
								fail(6),
								timeout(7),
								ignore(8) }
		MAX-ACCESS	read-only
		STATUS		current
		DESCRIPTION	"The backend authenticator status of PAE port."
		::= { iswDot1xPaePortStateEntry 3 }
--4    
	iswDot1xAuthControlledPortStatus	OBJECT-TYPE
		SYNTAX		Integer32 { authorized(1),unauthorized(2) }
		MAX-ACCESS	read-only
		STATUS		current
		DESCRIPTION	"The authentication status of PAE port.
					Authorized (1) : Allowing all traffic be accessed by the Supplicant end.
					Unauthorized (2) : Supplicant end is not granted access to the Port. Both In/Out traffic will be denied.
					"
		::= { iswDot1xPaePortStateEntry 4 }
--
	iswLinkAggTable	        OBJECT-TYPE
		SYNTAX		SEQUENCE OF IswLinkAggEntry
		MAX-ACCESS	not-accessible
		STATUS		current                                                     
		DESCRIPTION	"Link Aggregation table. Max entry size: 4."
		::= { iswLinkAgg 1 }
		
	iswLinkAggEntry	OBJECT-TYPE
		SYNTAX		IswLinkAggEntry
		MAX-ACCESS	not-accessible
		STATUS		current
		DESCRIPTION	"Link Aggregation entry."
		INDEX		{ iswLinkAggTrunkId }
		::= { iswLinkAggTable 1 } 
		
	IswLinkAggEntry ::= SEQUENCE{
		iswLinkAggTrunkId		Integer32,
		iswLinkAggMaxActiveLinks	Integer32,
		iswLinkAggMember		OCTET STRING,
		iswLinkAggActiveMember	        OCTET STRING,
		iswLinkAggMode 			Integer32
		}
--1
	iswLinkAggTrunkId	OBJECT-TYPE
		SYNTAX		Integer32
		MAX-ACCESS	not-accessible
		STATUS		current
		DESCRIPTION	"Link Aggregation trunk id. Up to Max trunk id."
		::= { iswLinkAggEntry 1 }
--2
	iswLinkAggMaxActiveLinks	OBJECT-TYPE
		SYNTAX		Integer32 (1 .. 8)
		MAX-ACCESS	read-write
		STATUS		current
		DESCRIPTION	"Max active links of link aggregation group.Default value is 8."
		DEFVAL		{8}
		::= { iswLinkAggEntry 2 }
--3
	iswLinkAggMember	OBJECT-TYPE
		SYNTAX		OCTET STRING ( SIZE(4) )
		MAX-ACCESS	read-write
		STATUS		current
		DESCRIPTION	"Port bitmap in the Link Aggregation group.
				bit0 is not used.
				bit1 is meaning GEPort-1,
				bit2 is meaning GEPort-2,
				bit3 is meaning GEPort-3,  
				...
				bit27 is meaning GEPort-27,
				bit28 is meaning GEPort-28
				other bits are not used.
				
				iswLinkAggTrunkId 1 ~ iswLinkAggTrunkId 28 can't have same ports in iswLinkAggMember.
				
				Default value is 0 which is meaning all ports do not added in the Link Agg group.
				"
		::= { iswLinkAggEntry 3 }
--4
	iswLinkAggActiveMember	OBJECT-TYPE
		SYNTAX		OCTET STRING ( SIZE(4) )
		MAX-ACCESS	read-only
		STATUS		current
		DESCRIPTION	"Port bitmap in the Link Aggregation group which is active.
				bit0 is not used.
				bit1 is meaning GEPort-1,
				bit2 is meaning GEPort-2,
				bit3 is meaning GEPort-3,  
				...
				bit27 is meaning GEPort-27,
				bit28 is meaning GEPort-28
				other bits are not used."
		::= { iswLinkAggEntry 4 }
--5    
	iswLinkAggMode	OBJECT-TYPE
		SYNTAX		Integer32 { disable (0), static (1), lacp (2) }
		MAX-ACCESS	read-write
		STATUS		current
		DESCRIPTION	"Per LAG supports different mode for doing link aggregation, as follows:
						Disable : No link aggregation process on this LAG.
						Static : Process static link aggregation on this LAG.
						LACP : Process LACP to do link aggregation on this LAG."
		DEFVAL		{0}
		::= { iswLinkAggEntry 5 }
--
	iswLinkAggPortTable	        OBJECT-TYPE
		SYNTAX		SEQUENCE OF IswLinkAggPortEntry
		MAX-ACCESS	not-accessible
		STATUS		current                                                     
		DESCRIPTION	"Link Aggregation Port table. Max entry size: 4."
		::= { iswLinkAgg 2 }
		
	iswLinkAggPortEntry	OBJECT-TYPE
		SYNTAX		IswLinkAggPortEntry
		MAX-ACCESS	not-accessible
		STATUS		current
		DESCRIPTION	"Link Aggregation entry."
		INDEX		{ iswLinkAggPortId }
		::= { iswLinkAggPortTable 1 } 
		
	IswLinkAggPortEntry ::= SEQUENCE{
		iswLinkAggPortId			IswGbeIndex,
		iswLinkAggPortGroupId		Integer32,
		}
--1
	iswLinkAggPortId			OBJECT-TYPE
		SYNTAX		IswGbeIndex 
		MAX-ACCESS	not-accessible
		STATUS		current
		DESCRIPTION	"Member port of link aggregation group."
		::= { iswLinkAggPortEntry 1 }
--2
	iswLinkAggPortGroupId			OBJECT-TYPE
		SYNTAX		Integer32 
		MAX-ACCESS	read-write
		STATUS		current
		DESCRIPTION	"Link aggregation group id. 0 means disable. Range is 0 and 1~Max Group id."
		DEFVAL		{0}  
		::= { iswLinkAggPortEntry 2 }
--
	iswPtpSystemConfMode	OBJECT-TYPE
		SYNTAX		Integer32 { disable (0), e2ebc (1) }
		MAX-ACCESS	read-write
		STATUS		current
		DESCRIPTION	"
					disable : Pass through mode, the PTP packets as normal multicast traffic.
					e2ebc : PTP clock mode is End-to-End boundary clock mode.
					The default value is disable.
					When iswPtpSystemConfMode is disable, then PTP protocol layer must reset all dynamic parameters to default value."
		DEFVAL		{0}
		::= { iswPTP 1 }
		
	iswDefaultDB		OBJECT IDENTIFIER
		::= { iswPTP 2 }

	iswPtpClockDefaultDSDomainType		OBJECT-TYPE
		SYNTAX		Integer32 ( 0..3 )
		MAX-ACCESS	read-write
		STATUS		current
		DESCRIPTION	"The domain attribute of local clock.
					The default value is 0."
		DEFVAL		{ 0 }
		::= { iswDefaultDB 1 }

	iswPtpClockDefaultDSTwoStepFlag		OBJECT-TYPE
		SYNTAX		Integer32 { false (0), true (1)}
		MAX-ACCESS	read-only
		STATUS		current
		DESCRIPTION	"This parameter specifies whether the two-step clock is used.
					The default value is true(1)."
		::= { iswDefaultDB 2 }

	iswPtpClockDefaultDSClockIdentity		OBJECT-TYPE
		SYNTAX		PhysAddress
		MAX-ACCESS	read-only
		STATUS		current
		DESCRIPTION	"The default dataset clock identity.
					The default value is similar to the default MAC address."
		::= { iswDefaultDB 3 }

	iswPtpClockDefaultDSQualityClass		OBJECT-TYPE
		SYNTAX		Integer32
		MAX-ACCESS	read-only
		STATUS		current
		DESCRIPTION	"The default dataset quality class.
				 The default value is 248."
		::= { iswDefaultDB 4 }

	iswPtpClockDefaultDSQualityAccuracy		OBJECT-TYPE
		SYNTAX		Integer32
		MAX-ACCESS	read-only
		STATUS		current
		DESCRIPTION	"The default dataset quality accuracy.
					The default value is 254."
		::= { iswDefaultDB 5 }

	iswPtpClockDefaultDSQualityOffset		OBJECT-TYPE
		SYNTAX		Integer32
		MAX-ACCESS	read-only
		STATUS		current
		DESCRIPTION	"The default dataset quality offset.
				 The default value is 28768."
		::= { iswDefaultDB 6 }

	iswPtpClockDefaultDSPriority1		OBJECT-TYPE
		SYNTAX		Integer32 (0..255)
		MAX-ACCESS	read-write
		STATUS		current
		DESCRIPTION	"The default dataset clock priority1.
					The default value is 128. The range is 0 ~ 255."
		DEFVAL		{128}
		::= { iswDefaultDB 7 }

	iswPtpClockDefaultDSPriority2		OBJECT-TYPE
		SYNTAX		Integer32 (0..255)
		MAX-ACCESS	read-write
		STATUS		current
		DESCRIPTION	"The default dataset clock priority2.
					The default value is 128. The range is 0 ~ 255."
		DEFVAL		{128}
		::= { iswDefaultDB 8 }

	iswPtpClockDefaultDSSlaveOnly		OBJECT-TYPE
		SYNTAX		Integer32 { false (0), true (1)}
		MAX-ACCESS	read-only
		STATUS		current
		DESCRIPTION	"This parameter specifies whether the SlaveOnly flag is set."
		::= { iswDefaultDB 9 }

		iswCurrentDB		OBJECT IDENTIFIER
		::= { iswPTP 3 }

	iswPtpClockCurrentDSStepsRemoved		OBJECT-TYPE
		SYNTAX		Integer32
		MAX-ACCESS	read-only
		STATUS		current
		DESCRIPTION	"The number of communication paths traversed between the local clock and the grandmaster clock.
					The default value is 0."
		::= { iswCurrentDB 1 }

	iswPtpClockCurrentDSOffsetFromMasterSec		OBJECT-TYPE
		SYNTAX		Integer32
		MAX-ACCESS	read-only
		STATUS		current
		DESCRIPTION	"The value of currentDS.offsetFromMaster is an implementation-specific
					representation of the current value of the time difference between a master
					and a slave as computed by the salve.

					The default value is 0.
					Support Positive or negative time value.

					Some examples for dispaly as below:
					Case1:
					iswPtpClockCurrentDSOffsetFromMasterSec = 3;
					iswPtpClockCurrentDSOffsetFromMasterNanoSec = 5;

					The real OffsetFromMaster is 3.000000005 Second

					Case2:
					iswPtpClockCurrentDSOffsetFromMasterSec = -3;
					iswPtpClockCurrentDSOffsetFromMasterNanoSec = -5;

					The real OffsetFromMaster is -3.000000005 Second

					In Layer2 protocol layer will not happen sec is positive value but nanosec is negative value.
					and also will not happen sec is negative value but nanosec is positive value.

					The max value of iswPtpClockCurrentDSOffsetFromMasterNanoSec is +999999999 ~ -999999999."
		::= { iswCurrentDB 2 }

	iswPtpClockCurrentDSOffsetFromMasterNanoSec		OBJECT-TYPE
		SYNTAX		Integer32
		MAX-ACCESS	read-only
		STATUS		current
		DESCRIPTION	"The value of currentDS.offsetFromMaster is an implementation-specific
					representation of the current value of the time difference between a master
					and a slave as computed by the salve.

					The default value is 0.
					Support Positive or negative time value.
					
					Some examples for dispaly as below:
					Case1:
						iswPtpClockCurrentDSOffsetFromMasterSec = 3;
						iswPtpClockCurrentDSOffsetFromMasterNanoSec = 5;
					
					The real OffsetFromMaster is 3.000000005 Second

					Case2:
						iswPtpClockCurrentDSOffsetFromMasterSec = -3;
						iswPtpClockCurrentDSOffsetFromMasterNanoSec = -5;

					The real OffsetFromMaster is -3.000000005 Second

					In Layer2 protocol layer will not happen sec is positive value but nanosec is negative value.
					and also will not happen sec is negative value but nanosec is positive value.

					The max value of iswPtpClockCurrentDSOffsetFromMasterNanoSec is +999999999 ~ -999999999."
		::= { iswCurrentDB 3 }

	iswPtpClockCurrentDSMeanPathDelaySec		OBJECT-TYPE
		SYNTAX		Integer32
		MAX-ACCESS	read-only
		STATUS		current
		DESCRIPTION	"The mean path delay between a pair of ports as measure by the delay request-response mechanism.

					The default value is 0.

					Some examples for dispaly as below:
					Case1:
						iswPtpClockCurrentDSMeanPathDelaySec = 3;
						iswPtpClockCurrentDSMeanPathDelayNanoSec = 5;

					The real MeanPathDelay is 3.000000005 Second.
					Both value are positive values."
		::= { iswCurrentDB 4 }

	iswPtpClockCurrentDSMeanPathDelayNanoSec		OBJECT-TYPE
		SYNTAX		Integer32
		MAX-ACCESS	read-only
		STATUS		current
		DESCRIPTION	"The mean path delay between a pair of ports as measure by the delay request-response mechanism.

					The default value is 0.

					Some examples for dispaly as below:
					Case1:
						iswPtpClockCurrentDSMeanPathDelaySec = 3;
						iswPtpClockCurrentDSMeanPathDelayNanoSec = 5;

					The real MeanPathDelay is 3.000000005 Second.
					Both value are positive values."
		::= { iswCurrentDB 5 }

	iswParentDB		OBJECT IDENTIFIER
		::= { iswPTP 4 }

	iswPtpClockParentDSClockIdentity		OBJECT-TYPE
		SYNTAX		PhysAddress
		MAX-ACCESS	read-only
		STATUS		current
		DESCRIPTION	"The value of clock identity of the port on the master that
					issues the Sync messages used in synchronizing this clock.
					The Sync messages are sent from the master of Ebest.

					The display format as below:
					00:11:22:FF:FE:33:44:55

					By default the value is iswPtpClockDefaultDSClockIdentity."
		::= { iswParentDB 1 }

	iswPtpClockParentDSPortNumber		OBJECT-TYPE
		SYNTAX		Integer32 (0|1..8)
		MAX-ACCESS	read-only
		STATUS		current
		DESCRIPTION	"The value of portNumber of the port on the master that issue the
					Sync messages used in synchronizing this clock.
					The Sync message are sent from the master of Ebest.

					By default the value is 0. (When the Ebest is not found, the GM will be switch to itself.)"
		::= { iswParentDB 2 }

	iswPtpClockParentDSGMClockIdentity		OBJECT-TYPE
		SYNTAX		PhysAddress
		MAX-ACCESS	read-only
		STATUS		current
		DESCRIPTION	"The value is the clockIdentity attribute of the grandmaster clock.
					The default value is iswPtpClockDefaultDSClockIdentity.
					This parameter is updated when receive an Announce message when get new Ebest.

					The display format as below:
					00:11:22:FF:FE:33:44:55
					"
		::= { iswParentDB 3 }

	iswPtpClockParentDSGMQualityClass		OBJECT-TYPE
		SYNTAX		Integer32
		MAX-ACCESS	read-only
		STATUS		current
		DESCRIPTION	"This value is the Quality class attribute of the grandmaster clock.
					The default value is iswPtpClockDefaultDSQualityClass (248).
					This parameter is updated when receive an Announce message when get new Ebest."
		::= { iswParentDB 4 }

	iswPtpClockParentDSGMQualityAccuracy		OBJECT-TYPE
		SYNTAX		Integer32
		MAX-ACCESS	read-only
		STATUS		current
		DESCRIPTION	"This value is the Quality accuracy attribute of the grandmaster clock.
					The default value is iswPtpClockDefaultDSQualityAccuracy (254).
					This parameter is updated when receive an Announce message when get new Ebest."
		::= { iswParentDB 5 }

	iswPtpClockParentDSGMQualityOffset		OBJECT-TYPE
		SYNTAX		Integer32
		MAX-ACCESS	read-only
		STATUS		current
		DESCRIPTION	"This value is the Quality offset attribute of the grandmaster clock.
					The default value is iswPtpClockDefaultDSQualityOffset (28768).
					This parameter is updated when receive an Announce message when get new Ebest."
		::= { iswParentDB 6 }

	iswPtpClockParentDSGMPriority1		OBJECT-TYPE
		SYNTAX		Integer32 (0..255)
		MAX-ACCESS	read-only
		STATUS		current
		DESCRIPTION	"The value is the Priority1 attribute of the grandmaster clock.
					The default value is iswPtpClockDefaultDSPriority1 (128).
					This parameter is updated when receive an Announce message when get new Ebest."
		::= { iswParentDB 7 }

	iswPtpClockParentDSGMPriority2		OBJECT-TYPE
		SYNTAX		Integer32 (0..255)
		MAX-ACCESS	read-only
		STATUS		current
		DESCRIPTION	"The value is the Priority2 attribute of the grandmaster clock.
					The default value is iswPtpClockDefaultDSPriority2 (128).
					This parameter is updated when receive an Announce message when get new Ebest."
		::= { iswParentDB 8 }

	iswTimePropertiesDS	OBJECT IDENTIFIER
		::= { iswPTP 5 }

	iswPtpClockTimePropertiesDSCurrentUTCOffset		OBJECT-TYPE
		SYNTAX		INTEGER
		UNITS		"second"
		MAX-ACCESS	read-only
		STATUS		current
		DESCRIPTION	"The value of clockThe offset between TAI and UTC.
					The default value is 0 second.
					This parameter is updated when receive an Announce message when get new Ebest."
		::= { iswTimePropertiesDS 1 }

	iswPtpClockTimePropertiesDSCurrentUTCOffsetValid		OBJECT-TYPE
		SYNTAX		Integer32 { false (0), true (1)}
		MAX-ACCESS	read-only
		STATUS		current
		DESCRIPTION	"This parameter specifies whether current UTC offset is valid.
					The default value is false(0).
					This parameter is updated when receive an Announce message when get new Ebest."
		::= { iswTimePropertiesDS 2 }

	iswPtpClockTimePropertiesDSLeap59		OBJECT-TYPE
		SYNTAX		Integer32 { false (0), true (1)}
		MAX-ACCESS	read-only
		STATUS		current
		DESCRIPTION	"A true(1) value for Leap59 shall indicate that the last minute of the current UTC day contains 59 seconds.
					The default value is false(0).
					This parameter is updated when receive an Announce message when get new Ebest."
		::= { iswTimePropertiesDS 3 }

	iswPtpClockTimePropertiesDSLeap61		OBJECT-TYPE
		SYNTAX		Integer32 { false (0), true (1)}
		MAX-ACCESS	read-only
		STATUS		current
		DESCRIPTION	"A true(1) value for Leap61 shall indicate that the last minute of the current UTC day contains 61 seconds.
					The default value is false(0).
					This parameter is updated when receive an Announce message when get new Ebest."
		::= { iswTimePropertiesDS 4 }

	iswPtpClockTimePropertiesDSTimeTraceable		OBJECT-TYPE
		SYNTAX		Integer32 { false (0), true (1)}
		MAX-ACCESS	read-only
		STATUS		current
		DESCRIPTION	"A true(1) value of TimeTraceable indicates the timescale and the current UTC Offset are
					traceable to a primary reference; otherwise, the value shall be false(0).
					The default value is false(0).
					This parameter is updated when receive an Announce message when get new Ebest."
		::= { iswTimePropertiesDS 5 }

	iswPtpClockTimePropertiesDSFreqTraceable		OBJECT-TYPE
		SYNTAX		Integer32 { false (0), true (1)}
		MAX-ACCESS	read-only
		STATUS		current
		DESCRIPTION	"A true(1) value of FreTraceable indicates the frequency determining the timescale is
					traceable to a primary reference; otherwise, the value shall be false(0).
					The default value is false(0).
					This parameter is updated when receive an Announce message when get new Ebest."
		::= { iswTimePropertiesDS 6 }

	iswPtpClockTimePropertiesDSPTPTimeScale		OBJECT-TYPE
		SYNTAX		Integer32 { false (0), true (1)}
		MAX-ACCESS	read-only
		STATUS		current
		DESCRIPTION	"A true(1) value of PTPTimeScale indicates the clock timescale of the grandmaster
					clock is PTP; otherwise, the value shall be false(0).
					The default value is true(1).
					This parameter is updated when receive an Announce message when get new Ebest."
		::= { iswTimePropertiesDS 7 }

	iswPtpClockTimePropertiesDSGMClockSource		OBJECT-TYPE
		SYNTAX		Integer32 (0..255)
		MAX-ACCESS	read-only
		STATUS		current
		DESCRIPTION	"The source of time used by the grandmaster clock.
					The default value is 0xA0.
					This parameter is updated when receive an Announce message when get new Ebest."
		::= { iswTimePropertiesDS 8 }

	iswPtpClockPortTable	OBJECT-TYPE
		SYNTAX		SEQUENCE OF IswPtpClockPortEntry
		MAX-ACCESS	not-accessible
		STATUS		current
		DESCRIPTION	"Ptp Clock Port table. Max entry size: 8."
		::= { iswPTP 6 }

	iswPtpClockPortEntry	OBJECT-TYPE
		SYNTAX		IswPtpClockPortEntry
		MAX-ACCESS	not-accessible
		STATUS		current
		DESCRIPTION	"Ptp Clock Port entry."
		INDEX		{ iswPtpClockPortId }
		::= { iswPtpClockPortTable 1 }

	IswPtpClockPortEntry ::= SEQUENCE{
		iswPtpClockPortId			Integer32,
		iswPtpLogAnnounceInterval	Integer32,
		iswPtpAnnounceRctTimeout	Integer32,
		iswPtpSyncInterval			Integer32,
		iswPtpMinDelayReqInterval	Integer32,
		iswPtpMechanism				Integer32,
		iswPtpPTPVersion			Integer32,
		iswPtpPTPProtocolMode		Integer32,
	}

	iswPtpClockPortId	OBJECT-TYPE
		SYNTAX		Integer32 (1..8)
		MAX-ACCESS	not-accessible
		STATUS		current
		DESCRIPTION	"Range is 1..8. (GE-1~GE-8)"
		::= { iswPtpClockPortEntry 1 }

	iswPtpLogAnnounceInterval	OBJECT-TYPE
		SYNTAX		Integer32 ( 0..4 )
		MAX-ACCESS	read-write
		STATUS		current
		DESCRIPTION	"The parameter specifies the Announce message transmission interval associated with this port.
					The value of iswPtpLogAnnounceInterval shall be the logarithm to the base 2 of the mean Announce Interval.
					Default value is 1. (2 seconds)
				 Range : 0 (1 second), 1 (2 seconds), 2 (4 seconds), 3 (8 seconds), 4 (16 seconds)."
		DEFVAL		{ 1 }
		::= { iswPtpClockPortEntry 2 }

	iswPtpAnnounceRctTimeout	OBJECT-TYPE
		SYNTAX		Integer32 ( 2..10 )
		MAX-ACCESS	read-write
		STATUS		current
		DESCRIPTION	"The parameter specifies the Announce receipt timeout associated with this port.
					It means the times of iswPtpLogAnnounceInterval.
					Default value is 3.
					Range is 2 ~ 10."
		DEFVAL		{ 3 }
		::= { iswPtpClockPortEntry 3 }

	iswPtpSyncInterval	OBJECT-TYPE
		SYNTAX		Integer32 ( 0..2 )
		MAX-ACCESS	read-write
		STATUS		current
		DESCRIPTION	"This parameter specifies the Sync message transmission interval.

					Default value is 1. (1 seconds)
					The range is 0 (0.5 second), 1 (1 second), 2 (2 seconds)."
		DEFVAL		{ 1 }
		::= { iswPtpClockPortEntry 4 }

	iswPtpMinDelayReqInterval	OBJECT-TYPE
		SYNTAX		Integer32 ( 0..5 )
		MAX-ACCESS	read-write
		STATUS		current
		DESCRIPTION	"This parameter specifies the Delay_Req message transmission interval.

					Default value is 0 (1 second).
					The range is 0 (1 second), 1 (2 seconds), 2 (4 seconds), 3 (8 seconds),
					4 (16 seconds), 5 (32 seconds)."
		DEFVAL		{ 0 }
		::= { iswPtpClockPortEntry 5 }

	iswPtpMechanism	OBJECT-TYPE
		SYNTAX		Integer32 { e2e(1) }
		MAX-ACCESS	read-only
		STATUS		current
		DESCRIPTION	"The parameter specifies the delay mechanism used.
					The default value is e2e mode.(End-to-End)"
		::= { iswPtpClockPortEntry 6 }

	iswPtpPTPVersion	OBJECT-TYPE
		SYNTAX		Integer32 { v2(2) }
		MAX-ACCESS	read-only
		STATUS		current
		DESCRIPTION	"This parameter specifies the PTP version being used on the port.
					The default value is v2."
		::= { iswPtpClockPortEntry 7 }

	iswPtpPTPProtocolMode	OBJECT-TYPE
		SYNTAX		Integer32 { disable (0), enable (1) }
		MAX-ACCESS	read-write
		STATUS		current
		DESCRIPTION	"Enable/Disable PTP protocol on the specify port.

					The default value is disable(0)."
		DEFVAL		{ 0 }
		::= { iswPtpClockPortEntry 8 }

	iswPtpPortStateTable	OBJECT-TYPE
		SYNTAX		SEQUENCE OF IswPtpPortStateEntry
		MAX-ACCESS	not-accessible
		STATUS		current
		DESCRIPTION	"Ptp Port state table. Max entry size: 8."
		::= { iswPTP 7 }

	iswPtpPortStateEntry	OBJECT-TYPE
		SYNTAX		IswPtpPortStateEntry
		MAX-ACCESS	not-accessible
		STATUS		current
		DESCRIPTION	"Ptp Port state entry."
		INDEX		{ iswPtpPortStatePortId }
		::= { iswPtpPortStateTable 1 }

	IswPtpPortStateEntry ::= SEQUENCE{
		iswPtpPortStatePortId	 Integer32,
		iswPtpRunningPortState   Integer32
	}

	iswPtpPortStatePortId	OBJECT-TYPE
		SYNTAX		Integer32 (1..8)
		MAX-ACCESS	not-accessible
		STATUS		current
		DESCRIPTION	"Range is 1..8. (GE-1~GE-8)"
		::= { iswPtpPortStateEntry 1 }

	iswPtpRunningPortState	OBJECT-TYPE
		SYNTAX		Integer32 {
							initializing(1),
							faulty(2),
							disabled(3),
							listening(4),
							preMaster(5),
							master(6),
							passive(7),
							uncalibrated(8),
							slave(9)
							}
		MAX-ACCESS	read-only
		STATUS		current
		DESCRIPTION	"This parameter specifies the port state returned by PTP engine.
					The default value is disabled."
		DEFVAL		{ 3 }
		::= { iswPtpPortStateEntry 2 }
--
	iswPtpClock		OBJECT IDENTIFIER
		::= { iswPTP 8 }
		
	iswPtpDateTime 	OBJECT-TYPE
		SYNTAX		OCTET STRING ( SIZE ( 19 ) )
		MAX-ACCESS	read-write
		STATUS		current
		DESCRIPTION	"PTP date and time. Format: MM/DD/YYYY HH:MM:SS. Fix length. The YYYY range is 2000~2036."
		::= { iswPtpClock 1 }

	iswPtpNanosecond 	OBJECT-TYPE
		SYNTAX		Unsigned32
		UNITS		"Nanosecond"
		MAX-ACCESS	read-only
		STATUS		current
		DESCRIPTION	"PTP Nanosecond."
		::= { iswPtpClock 2 }
--
--1
	iswSyncEEnable	OBJECT-TYPE
		SYNTAX		Integer32 { disable (0), enable (1) }
		MAX-ACCESS	read-write
		STATUS		current
		DESCRIPTION	"SyncE mode. Default value is disable (0)."   
		DEFVAL		{ 0 }
		::= { iswSyncE 1 } 
--2
	iswSyncEPrimaryPort	OBJECT-TYPE
		SYNTAX		Integer32 (1..8)
		MAX-ACCESS	read-write
		STATUS		current
		DESCRIPTION	"SyncE Primary Port ID. Default value is 1." 
		DEFVAL		{ 1 }
		::= { iswSyncE 2 } 
--3
	iswSyncESecondaryPort	OBJECT-TYPE
		SYNTAX		Integer32 (1..8)
		MAX-ACCESS	read-write
		STATUS		current
		DESCRIPTION	"SyncE Secondary Port ID. Default value is 2." 
		DEFVAL		{ 2 }
		::= { iswSyncE 3 } 
--
--
	iswPoEControlTable	OBJECT-TYPE
		SYNTAX		SEQUENCE OF IswPoEControlEntry
		MAX-ACCESS	not-accessible
		STATUS		current
		DESCRIPTION	"PoE enable/disable control and status"
		::=	 { iswConfMgt 13 }

	iswPoEControlEntry	OBJECT-TYPE
		SYNTAX		IswPoEControlEntry
		MAX-ACCESS	not-accessible
		STATUS		current
		DESCRIPTION	"PoE enable/disable control and status"
		INDEX		{ iswpoeCtlPortID }
		::=	 { iswPoEControlTable 1 }

	IswPoEControlEntry	::=	SEQUENCE {
		iswpoeCtlPortID			Integer32,
		iswpoeCtlPortAdmin		Integer32,
		iswpoeCtlPortStatus		Integer32,
		iswpoeCtlPortClass		Integer32,
		iswportCtlPortPWRConsumption       OCTET STRING,
		}
--1
	iswpoeCtlPortID	OBJECT-TYPE
		SYNTAX		Integer32 (1..8)
		MAX-ACCESS	not-accessible
		STATUS		current
		DESCRIPTION	"Range is 1..8. (GE-1~GE-8)"
		::= { iswPoEControlEntry 1 } 
--2
	iswpoeCtlPortAdmin	OBJECT-TYPE
		SYNTAX		Integer32 { off (0), on (1)}
		MAX-ACCESS	read-write
		STATUS		current
		DESCRIPTION	"Port PoE admin status. Default is ON"
		::= { iswPoEControlEntry 2 }
--3
	iswpoeCtlPortStatus	OBJECT-TYPE
		SYNTAX		Integer32 { off (0), on (1), unknown (2)}
		MAX-ACCESS	read-only
		STATUS		current
		DESCRIPTION	"Port PoE power delivery status.
					OFF means meaning PoE admin status is OFF or PoE Device is not connected to PSE.
					ON means meaning power is delivered.
					UNKNOWN means can't get the operation status of PoE."
		::= { iswPoEControlEntry 3 }
--4
	iswpoeCtlPortClass	OBJECT-TYPE
		SYNTAX		Integer32 { class-0 (0), class-1 (1), class-2 (2), class-3 (3), class-4 (4), unknown (5)}
		MAX-ACCESS	read-only
		STATUS		current
		DESCRIPTION	"PoE class level of Port. The class level is detected from PoE classification.
					 If PoE status is off or unknown, the value would be empty(255)." 
		::= { iswPoEControlEntry 4 }
--5
	iswportCtlPortPWRConsumption	OBJECT-TYPE
		SYNTAX		OCTET STRING ( SIZE (11) )
		UNITS		"mW (milli Watt)"
		MAX-ACCESS	read-only
		STATUS		current
		DESCRIPTION	"PoE power consumption per Port. If PoE status is off or unknown, the value would be zero." 
		::= { iswPoEControlEntry 5 }
--1
	iswDHCPSystemMode	OBJECT-TYPE
		SYNTAX		Integer32 { disable (0), enable (1) }
		MAX-ACCESS	read-write
		STATUS		current
		DESCRIPTION	"DHCP Server mode. Default value is disable (0)."   
		DEFVAL		{ 0 }
		::= { iswDHCPServer 1 } 
--2
-- 		iswDHCPSystemLeasesTime	OBJECT-TYPE
-- 		SYNTAX		Integer32 (1..31536000)
-- 		UNITS		"second"
-- 		MAX-ACCESS	read-write
-- 		STATUS		current
-- 		DESCRIPTION	"DHCP Server Lease time. Default value is 86400(1 day)." 
-- 		DEFVAL		{ 86400 }
-- 		::= { iswDHCPServer 2 }
--3
	iswDHCPPoolTable	OBJECT-TYPE
		SYNTAX		SEQUENCE OF IswDHCPPoolEntry
		MAX-ACCESS	not-accessible
		STATUS		current
		DESCRIPTION	"DHCP Pool setting"
		::=	 { iswDHCPServer 3 }

	iswDHCPPoolEntry	OBJECT-TYPE
		SYNTAX		IswDHCPPoolEntry
		MAX-ACCESS	not-accessible
		STATUS		current
		DESCRIPTION	"DHCP Pool setting"
		INDEX		{ iswDHCPPoolIndex }
		::=	 { iswDHCPPoolTable 1 }

	IswDHCPPoolEntry	::=	SEQUENCE {
		iswDHCPPoolIndex			Integer32,
		iswDHCPPoolSubnet			IpAddress,
		iswDHCPPoolNetmask			IpAddress,
		iswDHCPPoolRangeStart		IpAddress,
		iswDHCPPoolRangeEnd			IpAddress,
		iswDHCPPoolRangeStart1		IpAddress,
		iswDHCPPoolRangeEnd1		IpAddress,
		iswDHCPPoolRangeStart2		IpAddress,
		iswDHCPPoolRangeEnd2		IpAddress,
		iswDHCPPoolRangeStart3		IpAddress,
		iswDHCPPoolRangeEnd3		IpAddress,
		iswDHCPPoolRangeStart4		IpAddress,
		iswDHCPPoolRangeEnd4		IpAddress,
		iswDHCPPoolRangeStart5		IpAddress,
		iswDHCPPoolRangeEnd5		IpAddress,
		iswDHCPPoolRouter			IpAddress,
		iswDHCPPoolDomainName		OCTET STRING,
		iswDHCPPoolDNSServer		IpAddress,
		iswDHCPPoolLeaseTime		Integer32,
		iswDHCPPoolRowStatus		RowStatus
		}

	iswDHCPPoolIndex	OBJECT-TYPE
		SYNTAX		Integer32 (1..20)
		MAX-ACCESS	not-accessible
		STATUS		current
		DESCRIPTION	"One VLAN Interface can only bind with one DHCP pool.
			When a DHCP pool matches network subnet of specific VLAN interface,
			the DHCP pool would be bound to the VLAN interface automatically"
		::= { iswDHCPPoolEntry 1 }

	iswDHCPPoolSubnet	OBJECT-TYPE
		SYNTAX		IpAddress
		MAX-ACCESS	read-write
		STATUS		current
		DESCRIPTION	"Subnet / Netmask must be the same subnet of one of the VLAN interface.
					Subnet / Netmask are necessary to create a DHCP pool.
					DHCP Pool DOES NOT allow to change Subnet / Netmask. If modification is necessary, delete the pool and create new one."
		::= { iswDHCPPoolEntry 2 }

	iswDHCPPoolNetmask	OBJECT-TYPE
		SYNTAX		IpAddress
		MAX-ACCESS	read-write
		STATUS		current
		DESCRIPTION	"Subnet / Netmask must be the same subnet of one of the VLAN interface.
					Subnet / Netmask are necessary to create a DHCP pool.
					DHCP Pool DOES NOT allow to change Subnet / Netmask. If modification is necessary, delete the pool and create new one."
		::= { iswDHCPPoolEntry 3 }

	iswDHCPPoolRangeStart1	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 4 }

	iswDHCPPoolRangeEnd1	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 5 }

	iswDHCPPoolRangeStart2	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 6 }

	iswDHCPPoolRangeEnd2	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 7 }

	iswDHCPPoolRangeStart3	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 8 }

	iswDHCPPoolRangeEnd3	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 9 }

	iswDHCPPoolRangeStart4	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 10 }

	iswDHCPPoolRangeEnd4	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 11 }

	iswDHCPPoolRangeStart5	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 12 }

	iswDHCPPoolRangeEnd5	OBJECT-TYPE
		SYNTAX		IpAddress
		MAX-ACCESS	read-write
		STATUS		current
		DESCRIPTION	"Start - End indicates available range of address for DHCP client.
					Both Start-IP and End-IP must in the same subnet of the network setting.
					And the Start-IP must smaller than End-IP.
					Total Max. DHCP Pool size is 1024 per system."
		::= { iswDHCPPoolEntry 13 }

	iswDHCPPoolRouter	OBJECT-TYPE
		SYNTAX		IpAddress
		MAX-ACCESS	read-write
		STATUS		current
		DESCRIPTION	"Default-router in this network."
		::= { iswDHCPPoolEntry 14 }

	iswDHCPPoolDomainName	OBJECT-TYPE
		SYNTAX		OCTET STRING ( SIZE (0 .. 64) )
		MAX-ACCESS	read-write
		STATUS		current
		DESCRIPTION	"Domain name of this network. Max. lenghth is 64 characters." 
		::= { iswDHCPPoolEntry 15 }

	iswDHCPPoolDNSServer	OBJECT-TYPE
		SYNTAX		IpAddress
		MAX-ACCESS	read-write
		STATUS		current
		DESCRIPTION	"DNS server of this network."
		::= { iswDHCPPoolEntry 16 }

	iswDHCPPoolLeaseTime	OBJECT-TYPE
		SYNTAX		Integer32 ( 60 .. 31536000 )
		UNITS		"second"
		MAX-ACCESS	read-write
		STATUS		current
		DESCRIPTION	"DHCP Pool Lease time. Default value is 86400(1 day)." 
		DEFVAL		{ 86400 }
		::= { iswDHCPPoolEntry 17 }

	iswDHCPPoolRowStatus	OBJECT-TYPE
		SYNTAX		RowStatus
		MAX-ACCESS	read-create
		STATUS		current
		DESCRIPTION	"DHCP Pool: RowStatus."
		::= { iswDHCPPoolEntry 18 }
--4
	iswDHCPBindingTable	OBJECT-TYPE
		SYNTAX		SEQUENCE OF IswDHCPBindingEntry
		MAX-ACCESS	not-accessible
		STATUS		current
		DESCRIPTION	"DHCP Binding table"
		::=	 { iswDHCPServer 4 }

	iswDHCPBindingEntry	OBJECT-TYPE
		SYNTAX		IswDHCPBindingEntry
		MAX-ACCESS	not-accessible
		STATUS		current
		DESCRIPTION	"DHCP Binding entry"
		INDEX		{ iswDHCPBindingIndex }
		::=	 { iswDHCPBindingTable 1 }

	IswDHCPBindingEntry	::=	SEQUENCE {
		iswDHCPBindingIndex			Integer32,
		iswDHCPBindingIPAddress		IpAddress,
		iswDHCPBindingMAC			PhysAddress,
		iswDHCPBindingStartTime		OCTET STRING,
		iswDHCPBindingEndTime		OCTET STRING,
		iswDHCPBindingAgentCircuitId		OCTET STRING,
		iswDHCPBindingAgentRemoteId			OCTET STRING,
		iswDHCPBindingClientHostname		OCTET STRING
		}

	iswDHCPBindingIndex	OBJECT-TYPE
		SYNTAX		Integer32 ( 1 .. 1024 )
		MAX-ACCESS	not-accessible
		STATUS		current
		DESCRIPTION	"The DHCP binding table contains the IP address, MAC address, start/end time and VLAN interface."
		::= { iswDHCPBindingEntry 1 }

	iswDHCPBindingIPAddress	OBJECT-TYPE
		SYNTAX		IpAddress
		MAX-ACCESS	read-only
		STATUS		current
		DESCRIPTION	"Lease IP address."
		::= { iswDHCPBindingEntry 2 }

	iswDHCPBindingMAC		OBJECT-TYPE
		SYNTAX		PhysAddress
		MAX-ACCESS	read-only
		STATUS		current
		DESCRIPTION	"Binding MAC address."
		::= { iswDHCPBindingEntry 3 }

	iswDHCPBindingStartTime	OBJECT-TYPE
		SYNTAX		OCTET STRING ( SIZE (20) )
		MAX-ACCESS	read-only
		STATUS		current
		DESCRIPTION	"Lease start time." 
		::= { iswDHCPBindingEntry 4 }

	iswDHCPBindingEndTime	OBJECT-TYPE
		SYNTAX		OCTET STRING ( SIZE (20) )
		MAX-ACCESS	read-only
		STATUS		current
		DESCRIPTION	"Lease end time." 
		::= { iswDHCPBindingEntry 5 }

	iswDHCPBindingAgentCircuitId	OBJECT-TYPE
		SYNTAX		OCTET STRING ( SIZE (32) )
		MAX-ACCESS	read-only
		STATUS		current
		DESCRIPTION	"Option agent circuit id string." 
		::= { iswDHCPBindingEntry 6 }
		
	iswDHCPBindingAgentRemoteId	OBJECT-TYPE
		SYNTAX		OCTET STRING ( SIZE (32) )
		MAX-ACCESS	read-only
		STATUS		current
		DESCRIPTION	"Option agent remote id string." 
		::= { iswDHCPBindingEntry 7 }

	iswDHCPBindingClientHostname	OBJECT-TYPE
		SYNTAX		OCTET STRING ( SIZE (64) )
		MAX-ACCESS	read-only
		STATUS		current
		DESCRIPTION	"Option client host name string." 
		::= { iswDHCPBindingEntry 8 }


	iswDHCPPoolClassAddress OBJECT IDENTIFIER
		::=  { iswDHCPServer 5 }

	iswDHCPPoolClassAddrPoolIndex	OBJECT-TYPE
		SYNTAX		Integer32 (1..20)
		MAX-ACCESS	read-write
		STATUS		current
		DESCRIPTION	"For indicating pool index to read/write DHCP Pool Class Address Table."
		::= { iswDHCPPoolClassAddress 1 }
		
	iswDHCPPoolClassAddressTable	OBJECT-TYPE
		SYNTAX		SEQUENCE OF IswDHCPPoolClassAddressEntry
		MAX-ACCESS	not-accessible
		STATUS		current
		DESCRIPTION	"DHCP Pool Class Address setting"
		::=	 { iswDHCPPoolClassAddress 2 }

	iswDHCPPoolClassAddressEntry	OBJECT-TYPE
		SYNTAX		IswDHCPPoolClassAddressEntry
		MAX-ACCESS	not-accessible
		STATUS		current
		DESCRIPTION	"DHCP Pool Class Address setting"
		INDEX		{ iswDHCPPoolClassAddressIndex }
		::=	 { iswDHCPPoolClassAddressTable 1 }

	IswDHCPPoolClassAddressEntry	::=	SEQUENCE {
		iswDHCPPoolClassAddressIndex			Integer32,
		iswDHCPPoolClassAddressPoolIndex		Integer32,
		iswDHCPPoolClassAddressRangeStart	IpAddress,
		iswDHCPPoolClassAddressRangeEnd		IpAddress,
		iswDHCPPoolClassAddressRowStatus		RowStatus
		}
		
	iswDHCPPoolClassAddressIndex	OBJECT-TYPE
		SYNTAX		Integer32 (1..128)
		MAX-ACCESS	not-accessible
		STATUS		current
		DESCRIPTION	"DHCP Pool Class Address Index."
		::= { iswDHCPPoolClassAddressEntry 1 }

	iswDHCPPoolClassAddressPoolIndex	OBJECT-TYPE
		SYNTAX		Integer32 (1..19)
		MAX-ACCESS	read-only
		STATUS		current
		DESCRIPTION	"One VLAN Interface can only bind with one DHCP pool.
			When a DHCP pool matches network subnet of specific VLAN interface,
			the DHCP pool would be bound to the VLAN interface automatically"
		::= { iswDHCPPoolClassAddressEntry 2 }
		
	iswDHCPPoolClassAddressRangeStart	OBJECT-TYPE
		SYNTAX		IpAddress
		MAX-ACCESS	read-write
		STATUS		current
		DESCRIPTION	"DHCP Server Pool Class address range start."
		::= { iswDHCPPoolClassAddressEntry 3 }

	iswDHCPPoolClassAddressRangeEnd	OBJECT-TYPE
		SYNTAX		IpAddress
		MAX-ACCESS	read-write
		STATUS		current
		DESCRIPTION	"DHCP Server Pool Class address range end."
		::= { iswDHCPPoolClassAddressEntry 4 }
		
	iswDHCPPoolClassAddressRowStatus	OBJECT-TYPE
		SYNTAX		RowStatus
		MAX-ACCESS	read-create
		STATUS		current
		DESCRIPTION	"DHCP Pool Class address: RowStatus."
		::= { iswDHCPPoolClassAddressEntry 5 }


-- G-Ring v2
-- G-RingV2 Group 1
	iswGRingV2Ring1Role	OBJECT-TYPE
		SYNTAX			Integer32 { ring-master (1), ring-slave (2) }
		MAX-ACCESS		read-write
		STATUS			current
		DESCRIPTION		"Role of device, accept ring-master or ring-slave."
		DEFVAL			{ 2 }
		::= { iswGRingV2Ring1 1 }

	iswGRingV2Ring1Mode	OBJECT-TYPE
		SYNTAX			Integer32 { disable (0), enable (1) }
		MAX-ACCESS		read-write
		STATUS			current
		DESCRIPTION		"Enable/Disable Ring Protect of ring group 1."
		DEFVAL			{ 0 }
		::= { iswGRingV2Ring1 2 }

	iswGRingV2Ring1Node1	OBJECT-TYPE
		SYNTAX			IswGbeIndex
		MAX-ACCESS		read-write
		STATUS			current
		DESCRIPTION		"The port in Ring Group 1 as Node1."
		DEFVAL			{ 1 }
		::= { iswGRingV2Ring1 3 }

	iswGRingV2Ring1Node2	OBJECT-TYPE
		SYNTAX			IswGbeIndex
		MAX-ACCESS		read-write
		STATUS			current
		DESCRIPTION		"The port in Ring Group 1 as Node2."
		DEFVAL			{ 2 }
		::= { iswGRingV2Ring1 4 }

	iswGRingV2Ring1State	OBJECT-TYPE
		SYNTAX		Integer32 { normal (1), fail (2) }
		MAX-ACCESS	read-only
		STATUS		current
		DESCRIPTION	"Ring state."
		::= { iswGRingV2Ring1 5 }

	iswGRingV2Ring1Node1Behavior	OBJECT-TYPE
		SYNTAX		Integer32 { blocking (1), forwarding (5) }
		MAX-ACCESS	read-only
		STATUS		current
		DESCRIPTION	"Node1 behavior: blocking or forwarding"
		::= { iswGRingV2Ring1 6 }

	iswGRingV2Ring1Node2Behavior	OBJECT-TYPE
		SYNTAX		Integer32 { blocking (1), forwarding (5) }
		MAX-ACCESS	read-only
		STATUS		current
		DESCRIPTION	"Node2 behavior: blocking or forwarding"
		::= { iswGRingV2Ring1 7 }

	iswGRingV2Ring1Node1LinkStatus	OBJECT-TYPE
		SYNTAX		Integer32 { link-down (0), link-up (1) }
		MAX-ACCESS	read-only
		STATUS		current
		DESCRIPTION	"Node1 link status."
		::= { iswGRingV2Ring1 8 }

	iswGRingV2Ring1Node2LinkStatus	OBJECT-TYPE
		SYNTAX		Integer32 { link-down (0), link-up (1) }
		MAX-ACCESS	read-only
		STATUS		current
		DESCRIPTION	"Node2 link status."
		::= { iswGRingV2Ring1 9 }

-- G-RingV2 Group 2
	iswGRingV2Ring2Role	OBJECT-TYPE
		SYNTAX			Integer32 { ring-master (1), ring-slave (2), coupling-primary (3), coupling-backup (4), dual-homing (5) }
		MAX-ACCESS		read-write
		STATUS			current
		DESCRIPTION		"Role of device, accept ring-master, ring-slave, coupling-primary, coupling-backup, dual-homing."
		DEFVAL			{ 2 }
		::= { iswGRingV2Ring2 1 }

	iswGRingV2Ring2Mode	OBJECT-TYPE
		SYNTAX			Integer32 { disable (0), enable (1) }
		MAX-ACCESS		read-write
		STATUS			current
		DESCRIPTION		"Enable/Disable rules (accept & result):
                                         Ring-Group1     Ring-Group2
                                         ===============================================
                                         enabled         enabled (all)
                                         disabled        enabled (Ring or DualHoming)
                                         disabled	 disabled (Coupling)  [Note]
                                         
                                         Note: If Ring Group 2 is coupling and enabled, if Ring Group 1 is set as disable, then Ring Group 2 will also be disabled.
					"
		DEFVAL			{ 0 }
		::= { iswGRingV2Ring2 2 }

	iswGRingV2Ring2Node1	OBJECT-TYPE
		SYNTAX			IswGbeIndex
		MAX-ACCESS		read-write
		STATUS			current
		DESCRIPTION		"The port in Ring Group 2 as Node1."
		DEFVAL			{ 3 }
		::= { iswGRingV2Ring2 3 }

	iswGRingV2Ring2Node2	OBJECT-TYPE
		SYNTAX			IswGbeIndex
		MAX-ACCESS		read-write
		STATUS			current
		DESCRIPTION		"The port in Ring Group 2 as Node2."
		DEFVAL			{ 4 }
		::= { iswGRingV2Ring2 4 }

	iswGRingV2Ring2State	OBJECT-TYPE
		SYNTAX		Integer32 { normal (1), fail (2) }
		MAX-ACCESS	read-only
		STATUS		current
		DESCRIPTION	"Ring state."
		::= { iswGRingV2Ring2 5 }

	iswGRingV2Ring2Node1Behavior	OBJECT-TYPE
		SYNTAX		Integer32 { blocking (1), forwarding (5) }
		MAX-ACCESS	read-only
		STATUS		current
		DESCRIPTION	"Node1 behavior: blocking or forwarding"
		::= { iswGRingV2Ring2 6 }

	iswGRingV2Ring2Node2Behavior	OBJECT-TYPE
		SYNTAX		Integer32 { blocking (1), forwarding (5) }
		MAX-ACCESS	read-only
		STATUS		current
		DESCRIPTION	"Node2 behavior: blocking or forwarding"
		::= { iswGRingV2Ring2 7 }

	iswGRingV2Ring2Node1LinkStatus	OBJECT-TYPE
		SYNTAX		Integer32 { link-down (0), link-up (1) }
		MAX-ACCESS	read-only
		STATUS		current
		DESCRIPTION	"Node1 link status."
		::= { iswGRingV2Ring2 8 }

	iswGRingV2Ring2Node2LinkStatus	OBJECT-TYPE
		SYNTAX		Integer32 { link-down (0), link-up (1) }
		MAX-ACCESS	read-only
		STATUS		current
		DESCRIPTION	"Node2 link status."
		::= { iswGRingV2Ring2 9 }

-- G-RingV2  Group 3
	iswGRingV2Ring3Role	OBJECT-TYPE
		SYNTAX			Integer32 { chain-head (6), chain-tail (7), chain-member (8), balancing-chain-central-block (9), balancing-chain-terminal-1 (10), balancing-chain-terminal-2 (11), balancing-chain-member (12) }
		MAX-ACCESS		read-write
		STATUS			current
		DESCRIPTION		"Role of device, accept chain-head, chain-tail, chain-member, balancing-chain-terminal-1, balancing-chain-terminal-2, balancing-chain-central-block, balancing-chain-member"
		DEFVAL			{ 8 }
		::= { iswGRingV2Ring3 1 }

	iswGRingV2Ring3Mode	OBJECT-TYPE
		SYNTAX			Integer32 { disable (0), enable (1) }
		MAX-ACCESS		read-write
		STATUS			current
		DESCRIPTION		"Enable/Disable rules: Only if Ring Group 1 and 2 both disabled, then Group 3 accept enable."
		DEFVAL			{ 0 }
		::= { iswGRingV2Ring3 2 }	
	
	iswGRingV2Ring3Node1	OBJECT-TYPE
		SYNTAX			IswGbeIndex
		MAX-ACCESS		read-write
		STATUS			current
		DESCRIPTION		"The port in Ring Group 3 as Node1."
		DEFVAL			{ 1 }
		::= { iswGRingV2Ring3 3 }

	iswGRingV2Ring3Node2	OBJECT-TYPE
		SYNTAX			IswGbeIndex
		MAX-ACCESS		read-write
		STATUS			current
		DESCRIPTION		"The port in Ring Group 3 as Node2."
		DEFVAL			{ 2 }
		::= { iswGRingV2Ring3 4 }

	iswGRingV2Ring3State	OBJECT-TYPE
		SYNTAX		Integer32 { normal (1), fail (2) }
		MAX-ACCESS	read-only
		STATUS		current
		DESCRIPTION	"Ring state."
		::= { iswGRingV2Ring3 5 }

	iswGRingV2Ring3Node1Behavior	OBJECT-TYPE
		SYNTAX		Integer32 { blocking (1), forwarding (5) }
		MAX-ACCESS	read-only
		STATUS		current
		DESCRIPTION	"Node1 behavior: blocking or forwarding"
		::= { iswGRingV2Ring3 6 }

	iswGRingV2Ring3Node2Behavior	OBJECT-TYPE
		SYNTAX		Integer32 { blocking (1), forwarding (5) }
		MAX-ACCESS	read-only
		STATUS		current
		DESCRIPTION	"Node2 behavior: blocking or forwarding"
		::= { iswGRingV2Ring3 7 }

	iswGRingV2Ring3Node1LinkStatus	OBJECT-TYPE
		SYNTAX		Integer32 { link-down (0), link-up (1) }
		MAX-ACCESS	read-only
		STATUS		current
		DESCRIPTION	"Node1 link status."
		::= { iswGRingV2Ring3 8 }

	iswGRingV2Ring3Node2LinkStatus	OBJECT-TYPE
		SYNTAX		Integer32 { link-down (0), link-up (1) }
		MAX-ACCESS	read-only
		STATUS		current
		DESCRIPTION	"Node2 link status."
		::= { iswGRingV2Ring3 9 }

--DHCP CLIENT
--1
--	iswDHCPClientTable	OBJECT-TYPE
--		SYNTAX		SEQUENCE OF IswDHCPClientEntry
--		MAX-ACCESS	not-accessible
--		STATUS		current
--		DESCRIPTION	"DHCP Client setting"
--		::=	 { iswDHCPClient 1 }
--
--	iswDHCPClientEntry	OBJECT-TYPE
--		SYNTAX		IswDHCPClientEntry
--		MAX-ACCESS	not-accessible
--		STATUS		current
--		DESCRIPTION	"DHCP Client setting"
--		INDEX		{ iswDHCPClientVlanIndex }
--		::=	 { iswDHCPClientTable 1 }
--
--	IswDHCPClientEntry	::=	SEQUENCE {
--		iswDHCPClientVlanIndex		Integer32,
--		iswDHCPClientMode			INTEGER,
--		iswDHCPClientOp60String		OCTET STRING,
--		iswDHCPClientOp61Type		INTEGER,
--		iswDHCPClientOp61String		OCTET STRING,
--		iswDHCPClientRowStatus		RowStatus
--		}
--		
--	iswDHCPClientVlanIndex	OBJECT-TYPE
--		SYNTAX		Integer32 ( 1 .. 4094 )
--		MAX-ACCESS	not-accessible
--		STATUS		current
--		DESCRIPTION	"DHCP Client VLAN index."
--		::= { iswDHCPClientEntry 1 }
--		
--	iswDHCPClientMode	OBJECT-TYPE
--		SYNTAX		INTEGER { disable (0), enable (1) }
--		MAX-ACCESS	read-write
--		STATUS		current
--		DESCRIPTION	"Enable/Disable DHCP client."   
--		DEFVAL		{ 0 }
--		::= { iswDHCPClientEntry 2 } 
--	
--	iswDHCPClientOp60String	OBJECT-TYPE
--		SYNTAX		OCTET STRING ( SIZE (64) )
--		MAX-ACCESS	read-write
--		STATUS		current
--		DESCRIPTION	"The ASCII string of DHCP class identifier(option 60)." 
--		::= { iswDHCPClientEntry 3 }
--		
--	iswDHCPClientOp61Type	OBJECT-TYPE
--		SYNTAX		INTEGER { disable (0), hostname (1), ascii (2), hex (3) }
--		MAX-ACCESS	read-write
--		STATUS		current
--		DESCRIPTION	"DHCP client option 61 type(disable, hostname, string)."   
--		DEFVAL		{ 0 }
--		::= { iswDHCPClientEntry 4 }
--		
--	iswDHCPClientOp61String	OBJECT-TYPE
--		SYNTAX		OCTET STRING ( SIZE (32) )
--		MAX-ACCESS	read-write
--		STATUS		current
--		DESCRIPTION	"The ASCII string of DHCP client identifier(option 61)." 
--		::= { iswDHCPClientEntry 5 }
--		
--	iswDHCPClientRowStatus	OBJECT-TYPE
--		SYNTAX		RowStatus
--		MAX-ACCESS	read-create
--		STATUS		current
--		DESCRIPTION	"Row Status."
--		::= { iswDHCPClientEntry 6 }
--
--2
--	iswDHCPClientStatTable	OBJECT-TYPE
--		SYNTAX		SEQUENCE OF IswDHCPClientStatEntry
--		MAX-ACCESS	not-accessible
--		STATUS		current
--		DESCRIPTION	"DHCP Client status"
--		::=	 { iswDHCPClient 2 }
--
--	iswDHCPClientStatEntry	OBJECT-TYPE
--		SYNTAX		IswDHCPClientStatEntry
--		MAX-ACCESS	not-accessible
--		STATUS		current
--		DESCRIPTION	"DHCP Client status"
--		INDEX		{ iswDHCPClientStatVlanIndex }
--		::=	 { iswDHCPClientStatTable 1 }
--
--	IswDHCPClientStatEntry	::=	SEQUENCE {
--		iswDHCPClientStatVlanIndex		Integer32,
--		iswDHCPClientServerIpaddr	IpAddress,
--		iswDHCPClientState			INTEGER,
--		iswDHCPClientIpaddr			IpAddress,
--		iswDHCPClientNetmask			IpAddress,
--		iswDHCPClientGateway			IpAddress,
--		}
--		
--	iswDHCPClientStatVlanIndex	OBJECT-TYPE
--		SYNTAX		Integer32 ( 1 .. 4094 )
--		MAX-ACCESS	not-accessible
--		STATUS		current
--		DESCRIPTION	"DHCP Client VLAN index."
--		::= { iswDHCPClientStatEntry 1 }
--		
--	iswDHCPClientServerIpaddr	OBJECT-TYPE
--		SYNTAX		IpAddress
--		MAX-ACCESS	read-only
--		STATUS		current
--		DESCRIPTION	"Server ip address."
--		::= { iswDHCPClientStatEntry 2 }
--		
--	iswDHCPClientState	OBJECT-TYPE
--		SYNTAX		INTEGER { disable (0), selecting (1), bound (2), fail (3), renewing (4), rebinding (5) }
--		MAX-ACCESS	read-only
--		STATUS		current
--		DESCRIPTION	"Current client state."   
--		DEFVAL		{ 0 }
--		::= { iswDHCPClientStatEntry 3 } 
--		
--	iswDHCPClientIpaddr	OBJECT-TYPE
--		SYNTAX		IpAddress
--		MAX-ACCESS	read-only
--		STATUS		current
--		DESCRIPTION	"Current client ip address."
--		::= { iswDHCPClientStatEntry 4 }
--		
--	iswDHCPClientNetmask	OBJECT-TYPE
--		SYNTAX		IpAddress
--		MAX-ACCESS	read-only
--		STATUS		current
--		DESCRIPTION	"Current client netmask."
--		::= { iswDHCPClientStatEntry 5 }
--		
--	iswDHCPClientGateway	OBJECT-TYPE
--		SYNTAX		IpAddress
--		MAX-ACCESS	read-only
--		STATUS		current
--		DESCRIPTION	"Client gateway address."
--		::= { iswDHCPClientStatEntry 6 }

--Private LLDP
--1
	iswLLDPPortConfigTable	OBJECT-TYPE
		SYNTAX		SEQUENCE OF IswLLDPPortConfigEntry
		MAX-ACCESS	not-accessible
		STATUS		current
		DESCRIPTION	"LLDP settings"
		::=	 { iswLLDP 1 }

	iswLLDPPortConfigEntry	OBJECT-TYPE
		SYNTAX		IswLLDPPortConfigEntry
		MAX-ACCESS	not-accessible
		STATUS		current
		DESCRIPTION	"DHCP Client setting"
		INDEX		{ iswLLDPPortConfigIndex }
		::=	 { iswLLDPPortConfigTable 1 }

	IswLLDPPortConfigEntry	::=	SEQUENCE {
		iswLLDPConfigPortIdx				Integer32,
		iswLLDPConfigManAddrPortsTxType		INTEGER
		}
		
	iswLLDPConfigPortIdx	OBJECT-TYPE
		SYNTAX		Integer32 ( 1 .. 28 )
		MAX-ACCESS	not-accessible
		STATUS		current
		DESCRIPTION	"User Port index."
		::= { iswLLDPPortConfigEntry 1 }
		
	iswLLDPConfigManAddrPortsTxType	OBJECT-TYPE
		SYNTAX		INTEGER { ipv4 (1), ipv6 (2), both (3) }
		MAX-ACCESS	read-write
		STATUS		current
		DESCRIPTION	"Port Tx Management address type (IPv4/IPv6/Both)."   
		DEFVAL		{ 1 }
		::= { iswLLDPPortConfigEntry 2 }
		
--2
	iswLLDPRemoteTable	OBJECT-TYPE
		SYNTAX		SEQUENCE OF IswLLDPRemoteEntry
		MAX-ACCESS	not-accessible
		STATUS		current
		DESCRIPTION	"LLDP Remote TTL table of neihbors"
		::=	 { iswLLDP 2 }

	iswLLDPRemoteEntry	OBJECT-TYPE
		SYNTAX		IswLLDPRemoteEntry
		MAX-ACCESS	not-accessible
		STATUS		current
		DESCRIPTION	"LLDP remote TTL entry"
		INDEX		{ lldpRemTimeMark, lldpRemLocalPortNum, lldpRemIndex }
		::=	 { iswLLDPRemoteTable 1 }

	IswLLDPRemoteEntry	::=	SEQUENCE {
		iswLLDPRemTTL		Integer32
		}
		
	iswLLDPRemTTL	OBJECT-TYPE
		SYNTAX		Integer32
		MAX-ACCESS	read-only
		STATUS		current
		DESCRIPTION	"The LLDP information valid period is set to TxHold multiplied by TxInterval seconds. (Time to Live)"
		::= { iswLLDPRemoteEntry 1 }

--3
	iswLLDPRemManAddrTable	OBJECT-TYPE
		SYNTAX		SEQUENCE OF IswLLDPRemManAddrEntry
		MAX-ACCESS	not-accessible
		STATUS		current
		DESCRIPTION	"LLDP Remote TTL table of neihbors"
		::=	 { iswLLDP 3 }

	iswLLDPRemManAddrEntry	OBJECT-TYPE
		SYNTAX		IswLLDPRemManAddrEntry
		MAX-ACCESS	not-accessible
		STATUS		current
		DESCRIPTION	"LLDP remote TTL entry"
		INDEX		{ lldpRemTimeMark, lldpRemLocalPortNum, lldpRemIndex }
		::=	 { iswLLDPRemManAddrTable 1 }

	IswLLDPRemManAddrEntry	::=	SEQUENCE {
		iswLLDPRemManAddrIPv6Subtype	Integer32,
		iswLLDPRemManAddrIPv6			OCTET STRING
		}
		
	iswLLDPRemManAddrIPv6Subtype	OBJECT-TYPE
		SYNTAX		Integer32
		MAX-ACCESS	read-only
		STATUS		current
		DESCRIPTION	"The remote manage address subtype (IPv6)"
		::= { iswLLDPRemManAddrEntry 1 }		
		
	iswLLDPRemManAddrIPv6	OBJECT-TYPE
		SYNTAX		OCTET STRING
		MAX-ACCESS	read-only
		STATUS		current
		DESCRIPTION	"The remote manage address (IPv6)"
		::= { iswLLDPRemManAddrEntry 2 }					

-- DHCPClass
	iswDhcpClassTable	OBJECT-TYPE
		SYNTAX      SEQUENCE OF IswDhcpClassEntry
		MAX-ACCESS	not-accessible
		STATUS		current
		DESCRIPTION	"DhcpClassTable"
		::= { iswDHCPClass 1 }
	---
	iswDhcpClassEntry OBJECT-TYPE
		SYNTAX		IswDhcpClassEntry
		MAX-ACCESS	not-accessible
		STATUS		current
		DESCRIPTION	"iswDhcpClassEntry"
		INDEX		{ iswDhcpClassIndex }
		::= { iswDhcpClassTable 1 }
	---
	IswDhcpClassEntry ::= SEQUENCE{
		iswDhcpClassIndex 		Integer32,
		iswDhcpClassOption 		Integer32,
		iswDhcpClassClientId		OCTET STRING,
		iswDhcpClassAgentCircuitId	OCTET STRING,
		iswDhcpClassAgentRemoteId	OCTET STRING,
		iswDhcpClassRowStatus 		RowStatus
	}
    ---
	iswDhcpClassIndex	OBJECT-TYPE
		SYNTAX		Integer32 ( 1 .. 128 ) 
		MAX-ACCESS	not-accessible
		STATUS		current
		DESCRIPTION	"DHCP class index. Maximum 128 entries."
		::= { iswDhcpClassEntry 1 }
    ---
	iswDhcpClassOption	OBJECT-TYPE
		SYNTAX		Integer32 { none (0), clientIdUser(1), clientIdHwaddr(2), agentCircuitId(3), clientIdUserHex(4), agentRemoteId(5), agentCircuitIdRemoteId(6) }
		MAX-ACCESS	read-write
		STATUS		current
		DESCRIPTION	"
                    clientIdUser(1): 
                        If this option is selected, iswDhcpClassClientId(ascii-string) must be provided.
                    clientIdHwaddr(2):
                        If this option is selected, iswDhcpClassClientId(MAC) must be provided.
                        it should be a valid MAC address xx:xx:xx:xx:xx:xx, with 17 characters. 
                        The separator could be colon (:) or dash (-).
                    agentCircuitId(3):
                        If this option is selected, iswDhcpClassAgentCircuitId(ascii-string) must be provided.
                    clientIdUserHex(4):
                        If this option is selected, iswDhcpClassClientId(hex) must be provided,
                        String length must be even since one byte hex value is presented as two octets string.
                    agentRemoteId(5):
                        If this option is selected, iswDhcpClassAgentRemoteId(ascii-string) must be provided.
                    agentCircuitIdRemoteId(6):
                        If this option is selected, both iswDhcpClassAgentRemoteId(ascii-string) and 
                        iswDhcpClassAgentCircuitId(ascii-string) must be provided in same time."
		DEFVAL { 0 }
		::= { iswDhcpClassEntry 2 }
	---
	iswDhcpClassClientId	OBJECT-TYPE
		SYNTAX		OCTET STRING ( SIZE(1..32) )
					MAX-ACCESS	read-write	
		STATUS		current
		DESCRIPTION	"If clientId option(1,2,4) is selected, , please provide this id.

                    This id format can be of the following types:
                        ascii-string:
                            Identifier string for the class entry. The maximum string length is 32.
                        hex:
                            String length must be even since one byte hex value is presented as two octets string.
                        MAX: 
                            Valid MAC address xx:xx:xx:xx:xx:xx, with 17 characters. The separator could be colon (:) or dash (-)."
		::= { iswDhcpClassEntry 3 }
	---
	iswDhcpClassAgentCircuitId	OBJECT-TYPE
		SYNTAX		OCTET STRING ( SIZE(1..32) )
					MAX-ACCESS read-write	
		STATUS		current
		DESCRIPTION	"If select agentCircuitId(3) or agentCircuitIdRemoteId(6), please provide this id.
                    ascii-string:
                            Identifier string for the class entry. The maximum string length is 32."
		::= { iswDhcpClassEntry 4 }
	---
	iswDhcpClassAgentRemoteId	OBJECT-TYPE
		SYNTAX		OCTET STRING ( SIZE(1..32) )
		MAX-ACCESS	read-write	
		STATUS		current
		DESCRIPTION	"If select agentRemoteId(5) or agentCircuitIdRemoteId(6), please provide this id.
                    ascii-string:
                            Identifier string for the class entry. The maximum string length is 32."
		::= { iswDhcpClassEntry 5 }
	---
	iswDhcpClassRowStatus	OBJECT-TYPE
		SYNTAX		RowStatus
		MAX-ACCESS	read-create	
		STATUS		current
		DESCRIPTION	"iswDhcpClassEntry Row Status."
		::= { iswDhcpClassEntry 6 }
	--- </dhcp class>
--
--

-- DHCPRelay
-- 1
	iswDHCPRelayCheck	OBJECT-TYPE
		SYNTAX		Integer32 { disable (0), enable (1) }
		MAX-ACCESS	read-write
		STATUS		current
		DESCRIPTION	"check relay information. Default value is disable (0).
					 Enabled - Always check relay information of DHCP-Reply messages.
					 Disable - Don't care relay information of DHCP-Reply messages."   
		DEFVAL		{ 0 }
		::= { iswDHCPRelay 1 } 
-- 2
	iswDHCPRelayInsert	OBJECT-TYPE
		SYNTAX		Integer32 { disable (0), enable (1) }
		MAX-ACCESS	read-write
		STATUS		current
		DESCRIPTION	"DHCP Server Lease time. Default value is (0).
					 Enabled - Always attach relay information on DHCP-Request messages. (Note:Port option82 should be enabled.)
					 Disable - Do nothing." 
		DEFVAL		{ 0 }
		::= { iswDHCPRelay 2 }
-- 3
	iswDHCPRelayRemoteIdType	OBJECT-TYPE
		SYNTAX		Integer32 {  sysMac (0), hostName (1) , ascii(2) }  -- HEX(3)
		MAX-ACCESS	read-write
		STATUS		current
		DESCRIPTION	"Specify type of remote-id. Default value is (0).
					 sys-mac - It means the remote-id is originated by system mac address.
					 hostname - It means the remote-id is originated by system host name.
					 ascii - User could configure the remote-id in format of ASCII characters." 
		DEFVAL		{ 0 }
		::= { iswDHCPRelay 3 }
		
-- 4
	iswDHCPRelayRemoteId	OBJECT-TYPE
		SYNTAX		OCTET STRING ( SIZE (1..32) )
		MAX-ACCESS	read-write
		STATUS		current
		DESCRIPTION	"sys-mac - it always is system mac address. User can not change this field.
					 hostname - it always is system host name. User can not change this field directly.
					 But it could modify system host name to originate new remote-id.
					 If the length of hostname over 32 characters, it only cut first 32 characters as remote-id.
					 ascii - user could modify this field. It supports ASCII string in range of 1 to 32 characters." 
		::= { iswDHCPRelay 4 }
		
--5
	iswDHCPRelayServerTable	OBJECT-TYPE
		SYNTAX		SEQUENCE OF IswDHCPRelayServerEntry
		MAX-ACCESS	not-accessible 
		STATUS		current
		DESCRIPTION	"DHCP relay server table."
		::= { iswDHCPRelay 5 }
		
	iswDHCPRelayServerEntry	OBJECT-TYPE
		SYNTAX		IswDHCPRelayServerEntry
		MAX-ACCESS	not-accessible
		STATUS		current
		DESCRIPTION	"DHCP relay server entry."
		INDEX		{ iswDHCPRelayServerIndex }
		::= { iswDHCPRelayServerTable 1 }
		
	IswDHCPRelayServerEntry ::= SEQUENCE{
		iswDHCPRelayServerIndex			Integer32,
		iswDHCPRelayServerIPAddr		IpAddress,
	}
	
--1	
	iswDHCPRelayServerIndex	OBJECT-TYPE
		SYNTAX		Integer32 
		MAX-ACCESS	not-accessible
		STATUS		current
		DESCRIPTION	"DHCP relay server index."
		::= { iswDHCPRelayServerEntry 1 }
--2
	iswDHCPRelayServerIPAddr	OBJECT-TYPE
		SYNTAX		IpAddress
		MAX-ACCESS	read-write
		STATUS		current
		DESCRIPTION	"DHCP relay server ip addr."
		::= { iswDHCPRelayServerEntry 2 }
		
-- DHCPRelayPort
--6
	iswDHCPRelayPortTable	OBJECT-TYPE
		SYNTAX		SEQUENCE OF IswDHCPRelayPortEntry
		MAX-ACCESS	not-accessible 
		STATUS		current
		DESCRIPTION	"DHCP relay port table. Max entry size: port number."
		::= { iswDHCPRelay 6 }
	
	iswDHCPRelayPortEntry	OBJECT-TYPE
		SYNTAX		IswDHCPRelayPortEntry
		MAX-ACCESS	not-accessible
		STATUS		current
		DESCRIPTION	"DHCP relay port entry."
		INDEX		{ iswDHCPRelayPortId }
		::= { iswDHCPRelayPortTable 1 }

	IswDHCPRelayPortEntry ::= SEQUENCE{
		iswDHCPRelayPortId		IswGbeIndex,
		iswDHCPRelayPortEnable		Integer32,
		iswDHCPRelayPortCircuitIdType	Integer32,
		iswDHCPRelayPortCircuitId	OCTET STRING,
	}

--1
	iswDHCPRelayPortId	OBJECT-TYPE
		SYNTAX		IswGbeIndex 
		MAX-ACCESS	not-accessible
		STATUS		current
		DESCRIPTION	"User Port index."
		::= { iswDHCPRelayPortEntry 1 } 

--2
	iswDHCPRelayPortEnable	OBJECT-TYPE
		SYNTAX		Integer32 { disable (0), enable (1) }
		MAX-ACCESS	read-write
		STATUS		current
		DESCRIPTION	"Enable/Disable add/strip option82 to/from DHCP packet on the port.
					 Enabled - The option82 will be attached on DHCP-Request received on the port, and strip option82 of DHCP-Reply message
					 (Note: System relay information inset/check must be enabled, too.
					 Disable - The device will not insert option82 to DHCP-Request and strip option82 of DHCP-Reply."
		::= { iswDHCPRelayPortEntry 2 } 

--3
	iswDHCPRelayPortCircuitIdType	OBJECT-TYPE
		SYNTAX		Integer32 {  portId (0), portMac (1) , ascii(2) }  -- HEX(3)
		MAX-ACCESS	read-write
		STATUS		current
		DESCRIPTION	"Specify type of circuit-id.
					 port-id - circuit-id is originated by port-id. User can not change this id.
					 port-mac - circuit-id is originated by port mac address. User can not change this id.
					 ascii - user could modify this field. It supports ASCII string in range of 1 to 32 characters." 
		DEFVAL		{ 0 }
		::= { iswDHCPRelayPortEntry 3 }

--4
	iswDHCPRelayPortCircuitId	OBJECT-TYPE
		SYNTAX		OCTET STRING ( SIZE ( 1 .. 32 ) )
		MAX-ACCESS	read-write
		STATUS		current
		DESCRIPTION	"The circuit-id." 
		::= { iswDHCPRelayPortEntry 4 }

--DHCPSnooping
--1
	iswDHCPSnoopingSystemEnable	OBJECT-TYPE
		SYNTAX		Integer32 { disable (0), enable (1) }
		MAX-ACCESS	read-write
		STATUS		current
		DESCRIPTION	"DHCP Snooping Enable/Disable . Default value is disable (0)."   
		DEFVAL		{ 0 }
		::= { iswDHCPSnooping 1 } 

--DHCPSnoopingPort
--2
	iswDHCPSnoopingPortTable	OBJECT-TYPE
		SYNTAX		SEQUENCE OF IswDHCPSnoopingPortEntry
		MAX-ACCESS	not-accessible 
		STATUS		current
		DESCRIPTION	"DHCP snooping port table. Max entry size: port number."  
		DEFVAL		{ 0 }
		::= { iswDHCPSnooping 2 }
	
	iswDHCPSnoopingPortEntry	OBJECT-TYPE
		SYNTAX		IswDHCPSnoopingPortEntry
		MAX-ACCESS	not-accessible
		STATUS		current
		DESCRIPTION	"DHCP snooping port entry."
		INDEX		{ iswDHCPSnoopingPortId }
		::= { iswDHCPSnoopingPortTable 1 }
	
	IswDHCPSnoopingPortEntry ::= SEQUENCE{
		iswDHCPSnoopingPortId		IswGbeIndex,
		iswDHCPSnoopingTrustEnable	Integer32,
	}
--1
	iswDHCPSnoopingPortId	OBJECT-TYPE
		SYNTAX		IswGbeIndex 
		MAX-ACCESS	not-accessible
		STATUS		current
		DESCRIPTION	"DHCP Snooping PortId Index."
		::= { iswDHCPSnoopingPortEntry 1 } 
--2
	iswDHCPSnoopingTrustEnable	OBJECT-TYPE
		SYNTAX		Integer32 { disable (0), enable (1) }
		MAX-ACCESS	read-write
		STATUS		current
		DESCRIPTION	"Enable/Disable Trust on the port.  Default value is disable (0).
					 Trust: Configures the port as trusted source of the DHCP messages.
					 Untrust: Configures the port as untrusted source of the DHCP messages."
		DEFVAL		{ 0 }
		::= { iswDHCPSnoopingPortEntry 2 }

--DHCPSnoopingBinding
--1
	iswDHCPSnoopingBindingTable	OBJECT-TYPE
		SYNTAX		SEQUENCE OF IswDHCPSnoopingBindingEntry
		MAX-ACCESS	not-accessible 
		STATUS		current
		DESCRIPTION	"DHCP snooping Binding table."  
		DEFVAL		{ 0 }
		::= { iswDHCPSnooping 3 }

	iswDHCPSnoopingBindingEntry	OBJECT-TYPE
		SYNTAX		IswDHCPSnoopingBindingEntry
		MAX-ACCESS	not-accessible
		STATUS		current
		DESCRIPTION	"DHCP snooping Binding entry."
		INDEX		{ iswDHCPSnoopingBindingIndex }
		::= { iswDHCPSnoopingBindingTable 1 }
	
	IswDHCPSnoopingBindingEntry ::= SEQUENCE{
		iswDHCPSnoopingBindingIndex			Integer32,
		iswDHCPSnoopingBindingPortId		IswGbeIndex,
		iswDHCPSnoopingBindingVlan			Integer32,
		iswDHCPSnoopingBindingHostIP		IpAddress,
		iswDHCPSnoopingBindingHostMac		PhysAddress,
		iswDHCPSnoopingBindingServerIP		IpAddress,
		iswDHCPSnoopingBindingNetmask		IpAddress,
		iswDHCPSnoopingBindingLease			Integer32,
	}
--1
	iswDHCPSnoopingBindingIndex		OBJECT-TYPE
		SYNTAX		Integer32 ( 1..200 )
		MAX-ACCESS	not-accessible
		STATUS		current
		DESCRIPTION	"DHCP Snooping Binding Index."
		::= { iswDHCPSnoopingBindingEntry 1 } 
--2
	iswDHCPSnoopingBindingPortId	OBJECT-TYPE
		SYNTAX		IswGbeIndex
		MAX-ACCESS	read-only
		STATUS		current
		DESCRIPTION	"Bridge Port Index. GE-1 ~ MAX Number of Port or Trunk Group."
		::= { iswDHCPSnoopingBindingEntry 2 }
--3
	iswDHCPSnoopingBindingVlan	OBJECT-TYPE
		SYNTAX		Integer32 ( 1..4094 )
		MAX-ACCESS	read-only
		STATUS		current
		DESCRIPTION	"Vlan Id. VLAN ID: 1 ~ 4094."
		::= { iswDHCPSnoopingBindingEntry 3 }
--4
	iswDHCPSnoopingBindingHostIP	OBJECT-TYPE
		SYNTAX		IpAddress
		MAX-ACCESS	read-only
		STATUS		current
		DESCRIPTION	"Ipv4 address."
		::= { iswDHCPSnoopingBindingEntry 4 }
--5
	iswDHCPSnoopingBindingHostMac	OBJECT-TYPE
		SYNTAX		PhysAddress
		MAX-ACCESS	read-only
		STATUS		current
		DESCRIPTION	"HW address."
		::= { iswDHCPSnoopingBindingEntry 5 }
--6
	iswDHCPSnoopingBindingServerIP	OBJECT-TYPE
		SYNTAX		IpAddress
		MAX-ACCESS	read-only
		STATUS		current
		DESCRIPTION	"Server Ipv4 address."
		::= { iswDHCPSnoopingBindingEntry 6 }
--7
	iswDHCPSnoopingBindingNetmask	OBJECT-TYPE
		SYNTAX		IpAddress
		MAX-ACCESS	read-only
		STATUS		current
		DESCRIPTION	"Netmask address."
		::= { iswDHCPSnoopingBindingEntry 7 }

--8
	iswDHCPSnoopingBindingLease	OBJECT-TYPE
		SYNTAX		Integer32
		UNITS		"second"
		MAX-ACCESS	read-only
		STATUS		current
		DESCRIPTION	"Lease time; unit:second."
		::= { iswDHCPSnoopingBindingEntry 8 }
--DHCPSnoopingBindingDeleteCtrl
--1
	iswDHCPSnoopingBindingDeleteCtrlVlan	OBJECT-TYPE
		SYNTAX		Integer32 ( 1 .. 4094 )
		MAX-ACCESS	read-write
		STATUS		current
		DESCRIPTION	"Delete by Vlan Id."
		::= { iswDHCPSnoopingBindingDeleteCtrl 1 }
--2
	iswDHCPSnoopingBindingDeleteCtrlPort	OBJECT-TYPE
		SYNTAX		IswGbeIndex
		MAX-ACCESS	read-write
		STATUS		current
		DESCRIPTION	"Delete by Port number."
		::= { iswDHCPSnoopingBindingDeleteCtrl 2 }
--3
	iswDHCPSnoopingBindingDeleteCtrlType	OBJECT-TYPE
		SYNTAX		Integer32 { deleteByVlan (0), deleteByPort (1), deleteByAll (2) }
		MAX-ACCESS	read-write
		STATUS		current
		DESCRIPTION	"Delete type."
		::= { iswDHCPSnoopingBindingDeleteCtrl 3 }

	iswLACPSysId					OBJECT-TYPE
		SYNTAX		PhysAddress 
		MAX-ACCESS	read-write
		STATUS		current
		DESCRIPTION	"LACP system mac address. (internal use, no config)"
		::= { iswLACPSystem 1 }
	iswLACPSysPriority				OBJECT-TYPE
		SYNTAX		Integer32 ( 1..65535 ) 
		MAX-ACCESS	read-write
		STATUS		current
		DESCRIPTION	"LACP system priority.To modify global configuration.
					 Range : 1 ~ 65535
					 Default Value : 32768."
		DEFVAL		{ 32768 }
		::= { iswLACPSystem 2 }
	iswLACPSysFilterMode			OBJECT-TYPE
		SYNTAX		Integer32 { disable (0), forward (1),softDrop (2),hardDrop (3) } 
		MAX-ACCESS	read-write
		STATUS		current
		DESCRIPTION	"LACP system filter mode. There are four modes as following:
					 Disable     (0) : Bypass incoming LACP PDUs.
					 Forward    (1): Accept LACP PDUs on LACP Port and bypass it on the non-LACP port. (default)
					 Soft-Drop  (2): Accept LACP PDUs on LACP Port and discard it on the non-LACP port.
					 Hard-Drop(3): Always drop incoming LACP PDUs."
		DEFVAL		{ 1 }
		::= { iswLACPSystem 3 }
		
--EcfmGlobal
--1
	iswEcfmGlobalStatus		OBJECT-TYPE
		SYNTAX		Integer32 { disable (0), enable (1) }
		MAX-ACCESS	read-write
		STATUS		current
		DESCRIPTION	"Ecfm status enable or disable. Control Ecfm working or not, it will stop working when the status is disable. Default value is disable (0)."   
		DEFVAL		{ 0 }
		::= { iswEcfmGlobal 1 }

--EcfmDomain
--1
	iswEcfmDomainTable		OBJECT-TYPE
		SYNTAX		SEQUENCE OF IswEcfmDomainEntry
		MAX-ACCESS	not-accessible 
		STATUS		current
		DESCRIPTION	"Ecfm Domain table."  
		::= { iswEcfmDomain 1 }

	iswEcfmDomainEntry		OBJECT-TYPE
		SYNTAX		IswEcfmDomainEntry
		MAX-ACCESS	not-accessible
		STATUS		current
		DESCRIPTION	"Ecfm Domain entry."
		INDEX		{ iswEcfmDomainIndex }
		::= { iswEcfmDomainTable 1 }
	
	IswEcfmDomainEntry ::= SEQUENCE{
		iswEcfmDomainIndex				Integer32,
		iswEcfmDomainFormat				Integer32,
		iswEcfmDomainName				OCTET STRING,
		iswEcfmDomainLevel				Integer32,
		iswEcfmDomainRowStatus			RowStatus,
	}

--1
	iswEcfmDomainIndex		OBJECT-TYPE
		SYNTAX		Integer32 ( 1..8 )
		MAX-ACCESS	not-accessible
		STATUS		current
		DESCRIPTION	"Ecfm domain index, maximum is 8."
		DEFVAL		{ 1 }
		::= { iswEcfmDomainEntry 1 } 

--2
	iswEcfmDomainFormat		OBJECT-TYPE
		SYNTAX		Integer32 { dns-like-name (1), mac-addr(2), char-string(3), none(4) }
		MAX-ACCESS	read-write
		STATUS		current
		DESCRIPTION	"1: dns-like-name, 2: mac-addr, 3: char-string, 4:none."
		DEFVAL		{ 1 }
		::= { iswEcfmDomainEntry 2 }

--3
	iswEcfmDomainName		OBJECT-TYPE
		SYNTAX		OCTET STRING ( SIZE ( 1..43 ) )
		MAX-ACCESS	read-write
		STATUS		current
		DESCRIPTION	"Ecfm Domain name, maximum length is 43.
					 The name will follow format to check.
					 The dns-like-name format example: www.sample.com
					 The mac-add format example: 00:01:02:03:04:05:65535"
		::= { iswEcfmDomainEntry 3 }

--4
	iswEcfmDomainLevel		OBJECT-TYPE
		SYNTAX		Integer32 ( 0..7 )
		MAX-ACCESS	read-write
		STATUS		current
		DESCRIPTION	"Ecfm domain level, vlaue range 0-7."
		DEFVAL		{ 0 }
		::= { iswEcfmDomainEntry 4 }
		
--5
	iswEcfmDomainRowStatus	OBJECT-TYPE
		SYNTAX		RowStatus
		MAX-ACCESS	read-create
		STATUS		current
		DESCRIPTION	"Row Status."
		::= { iswEcfmDomainEntry 5 }


--EcfmService
--1
	iswEcfmServiceTable		OBJECT-TYPE
		SYNTAX		SEQUENCE OF IswEcfmServiceEntry
		MAX-ACCESS	not-accessible 
		STATUS		current
		DESCRIPTION	"Ecfm Service table."  
		::= { iswEcfmService 1 }

	iswEcfmServiceEntry		OBJECT-TYPE
		SYNTAX		IswEcfmServiceEntry
		MAX-ACCESS	not-accessible
		STATUS		current
		DESCRIPTION	"Ecfm Service entry."
		INDEX		{ iswEcfmServiceDomainIndex }
		::= { iswEcfmServiceTable 1 }
	
	
	IswEcfmServiceEntry ::= SEQUENCE{
		iswEcfmServiceDomainIndex		Integer32,      
--		iswEcfmServiceDomainName		OCTET STRING,
		iswEcfmServiceFormat			Integer32,
		iswEcfmServiceName				OCTET STRING,
		iswEcfmServiceVlan				Integer32,
		iswEcfmServiceRowStatus			RowStatus,
	}

--1
	iswEcfmServiceDomainIndex		OBJECT-TYPE
		SYNTAX		Integer32 ( 1..8 )
		MAX-ACCESS	not-accessible
		STATUS		current
		DESCRIPTION	"Ecfm domain index, maximum is 8."
		::= { iswEcfmServiceEntry 1 } 

--2
--	iswEcfmServiceDomainName		OBJECT-TYPE
--		SYNTAX		OCTET STRING ( SIZE ( 1..43 ) )
--		MAX-ACCESS	read-write
--		STATUS		current
--		DESCRIPTION	"Ecfm Domain name, maximum length is 43."
--		::= { iswEcfmServiceEntry 2 }

--3
	iswEcfmServiceFormat		OBJECT-TYPE
		SYNTAX		Integer32 { primary-vid (1), char-string (2), unsigned-int16(3), rfc2865-vpn-id(4), icc(5) }
		MAX-ACCESS	read-write
		STATUS		current
		DESCRIPTION	"1: primary-vid, 2: char-string, 3: unsigned-int16, 4: rfc2865-vpn-id, 5: icc."
		DEFVAL		{ 2 }
		::= { iswEcfmServiceEntry 2 }

--4
	iswEcfmServiceName		OBJECT-TYPE
		SYNTAX		OCTET STRING ( SIZE ( 1..43 ) )
		MAX-ACCESS	read-write
		STATUS		current
		DESCRIPTION	"Ecfm service name, maximum length is 43.
					 The name will follow format to check.
					 The primary-vid format name is vlan number.
					 The unsigned-int16 format name is unsigned word(16 bits).
					 The rfc2865-vpn-id format name example: 313233:34353637.
					 The icc format format name example: 65536.(domain format must be none)"
		::= { iswEcfmServiceEntry 3 }

--5
	iswEcfmServiceVlan		OBJECT-TYPE
		SYNTAX		Integer32 ( 1..4094 )
		MAX-ACCESS	read-write
		STATUS		current
		DESCRIPTION	"Ecfm service vlan, vlaue range 1-4094"
		DEFVAL		{ 1 }
		::= { iswEcfmServiceEntry 4 }
	
--6
	iswEcfmServiceRowStatus	OBJECT-TYPE
		SYNTAX		RowStatus
		MAX-ACCESS	read-create
		STATUS		current
		DESCRIPTION	"Row Status."
		::= { iswEcfmServiceEntry 5 }

--EcfmMep
--1
	iswEcfmMepTable		OBJECT-TYPE
		SYNTAX		SEQUENCE OF IswEcfmMepEntry
		MAX-ACCESS	not-accessible 
		STATUS		current
		DESCRIPTION	"Ecfm Mep table."  
		::= { iswEcfmMep 1 }

	iswEcfmMepEntry		OBJECT-TYPE
		SYNTAX		IswEcfmMepEntry
		MAX-ACCESS	not-accessible
		STATUS		current
		DESCRIPTION	"Ecfm Mep entry."
		INDEX		{ iswEcfmMepIndex }  
		::= { iswEcfmMepTable 1 }
	
	
	IswEcfmMepEntry ::= SEQUENCE{
		iswEcfmMepIndex				Integer32,
		iswEcfmMepDomainIndex			Integer32,
--		iswEcfmMepDomainName			OCTET STRING,
		iswEcfmMepId				Integer32,
		iswEcfmMepVlan				Integer32,
		iswEcfmMepRowStatus			RowStatus,
	}

--1
	iswEcfmMepIndex		OBJECT-TYPE
		SYNTAX		Integer32 ( 1..16 )
		MAX-ACCESS	not-accessible
		STATUS		current
		DESCRIPTION	"Ecfm MEP index, maximum is 16."
		DEFVAL		{ 1 }
		::= { iswEcfmMepEntry 1 }

--2
	iswEcfmMepDomainIndex		OBJECT-TYPE
		SYNTAX		Integer32 ( 1..8 )
		MAX-ACCESS	read-create
		STATUS		current
		DESCRIPTION	"Ecfm domain index, maximum is 8."
		DEFVAL		{ 1 }
		::= { iswEcfmMepEntry 2 } 
		
--3
--	iswEcfmMepDomainName		OBJECT-TYPE
--		SYNTAX		OCTET STRING ( SIZE ( 1..43 ) )
--		MAX-ACCESS	read-write
--		STATUS		current
--		DESCRIPTION	"Ecfm Domain name, maximum length is 43."
--		::= { iswEcfmMepEntry 3 }

--4
	iswEcfmMepId		OBJECT-TYPE
		SYNTAX		Integer32 ( 1..8191 )
		MAX-ACCESS	read-create
		STATUS		current
		DESCRIPTION	"Maintenance end point ID, value range is 1-8191."
		DEFVAL		{ 1 }
		::= { iswEcfmMepEntry 3 }

--5
	iswEcfmMepVlan		OBJECT-TYPE
		SYNTAX		Integer32 ( 1..4094 )
		MAX-ACCESS	read-create
		STATUS		current
		DESCRIPTION	"Ecfm service vlan, vlaue range 1-4094"
		DEFVAL		{ 1 }
		::= { iswEcfmMepEntry 4 }
	
--6
	iswEcfmMepRowStatus	OBJECT-TYPE
		SYNTAX		RowStatus
		MAX-ACCESS	read-create
		STATUS		current
		DESCRIPTION	"Row Status."
		::= { iswEcfmMepEntry 5 }

--EcfmPort
--1
	iswEcfmPortTable		OBJECT-TYPE
		SYNTAX		SEQUENCE OF IswEcfmPortEntry
		MAX-ACCESS	not-accessible 
		STATUS		current
		DESCRIPTION	"Ecfm Port table."  
		::= { iswEcfmPort 1 }

	iswEcfmPortEntry		OBJECT-TYPE
		SYNTAX		IswEcfmPortEntry
		MAX-ACCESS	not-accessible
		STATUS		current
		DESCRIPTION	"Ecfm Port entry."
		INDEX		{ iswEcfmPortIfIndex }  
		::= { iswEcfmPortTable 1 }
	
	
	IswEcfmPortEntry ::= SEQUENCE{
		iswEcfmPortIfIndex			IswGbeIndex,
		iswEcfmPortDirection		Integer32,
		iswEcfmPortLevel			Integer32,
		iswEcfmPortMpid				Integer32,
		iswEcfmPortVlan				Integer32,
		iswEcfmPortActive			Integer32,
	}

--1
	iswEcfmPortIfIndex		OBJECT-TYPE
		SYNTAX		IswGbeIndex
		MAX-ACCESS	not-accessible
		STATUS		current
		DESCRIPTION	"Port number"
		DEFVAL		{ 1 }
		::= { iswEcfmPortEntry 1 } 

--2
	iswEcfmPortDirection		OBJECT-TYPE
		SYNTAX		Integer32 { down (0), up (1) }
		MAX-ACCESS	read-write
		STATUS		current
		DESCRIPTION	"MEP control message direction, default is down."
		DEFVAL		{ 0 }
		::= { iswEcfmPortEntry 2 }
	
--3
	iswEcfmPortLevel	OBJECT-TYPE
		SYNTAX		Integer32 ( 0..7 )
		MAX-ACCESS	read-write
		STATUS		current
		DESCRIPTION	"Indicates maintenance level for configuration, value range is 0-7."
		::= { iswEcfmPortEntry 3 }

--4
	iswEcfmPortMpid	OBJECT-TYPE
		SYNTAX		Integer32 ( 1..8191 )
		MAX-ACCESS	read-write
		STATUS		current
		DESCRIPTION	"MEP ID related configuration, value range is 1-8191."
		::= { iswEcfmPortEntry 4 }
		
--5
	iswEcfmPortVlan	OBJECT-TYPE
		SYNTAX		Integer32 ( 1..4094 )
		MAX-ACCESS	read-write
		STATUS		current
		DESCRIPTION	"VLAN related configuration, value range is 1-4094."
		::= { iswEcfmPortEntry 5 }
		
--6
	iswEcfmPortActive	OBJECT-TYPE
		SYNTAX		Integer32 { inactive (0), active (1) }
		MAX-ACCESS	read-write
		STATUS		current
		DESCRIPTION	"Operational status of mip, value range is inactive or active."
		::= { iswEcfmPortEntry 6 }

--EcfmCcm
--1
	iswEcfmCcmTable		OBJECT-TYPE
		SYNTAX		SEQUENCE OF IswEcfmCcmEntry
		MAX-ACCESS	not-accessible 
		STATUS		current
		DESCRIPTION	"Ecfm Ccm table."  
		::= { iswEcfmCcm 1 }

	iswEcfmCcmEntry		OBJECT-TYPE
		SYNTAX		IswEcfmCcmEntry
		MAX-ACCESS	not-accessible
		STATUS		current
		DESCRIPTION	"Ecfm Ccm entry."
		INDEX		{ iswEcfmCcmIndex }  
		::= { iswEcfmCcmTable 1 }
	
	IswEcfmCcmEntry ::= SEQUENCE{
		iswEcfmCcmIndex			Integer32,
		iswEcfmCcmInterval		Integer32,
		iswEcfmCcmLevel			Integer32,
		iswEcfmCcmVlan			Integer32,
		iswEcfmCcmActionType	Integer32,
		iswEcfmCcmDomainName	OCTET STRING,
		iswEcfmCcmServiceName	OCTET STRING,
		iswEcfmCcmRowStatus		RowStatus,
	}

--1
	iswEcfmCcmIndex		OBJECT-TYPE
		SYNTAX		Integer32 ( 1 .. 8 )
		MAX-ACCESS	not-accessible
		STATUS		current
		DESCRIPTION	"Must: MEP CCM index ID."
		::= { iswEcfmCcmEntry 1 } 

--2
	iswEcfmCcmInterval		OBJECT-TYPE
		SYNTAX		Integer32 { "100ms" (3), "1s" (4), "10s" (5), "1min" (6), "10mins" (7)}
		MAX-ACCESS	read-create
		STATUS		current
		DESCRIPTION	"Must: MEP CCM Interval, the option are 100MS, 1S, 10S, 1Min, 10Mins, default is 1S."
		DEFVAL		{ 4 }
		::= { iswEcfmCcmEntry 2 }

--3
	iswEcfmCcmLevel		OBJECT-TYPE
		SYNTAX		Integer32 ( 0 .. 7 )
		MAX-ACCESS	read-create
		STATUS		current
		DESCRIPTION	"Must: MEP level, value range is 0-7."
		::= { iswEcfmCcmEntry 3 }

--4
	iswEcfmCcmVlan		OBJECT-TYPE
		SYNTAX		Integer32 ( 1 .. 4094 )
		MAX-ACCESS	read-create
		STATUS		current
		DESCRIPTION	"Must: MEP control message vlan.
					 Value length is 1-4094."
		::= { iswEcfmCcmEntry 4 }
	
--5
	iswEcfmCcmActionType	OBJECT-TYPE
		SYNTAX		Integer32 { domain-service(2), domain-vlan(3), level-vlan(6) }
		MAX-ACCESS	read-create
		STATUS		current
		DESCRIPTION	"Must: Action type.
					 2: domain-service, 3:domain-vlan, 6:level-vlan."
		::= { iswEcfmCcmEntry 5 }

--6
	iswEcfmCcmDomainName	OBJECT-TYPE
		SYNTAX		OCTET STRING ( SIZE ( 0..43 ) )
		MAX-ACCESS	read-create
		STATUS		current
		DESCRIPTION	"Must: MEP doamin name.
					 Value length is 1-43."
		::= { iswEcfmCcmEntry 6 }
		
--7
	iswEcfmCcmServiceName	OBJECT-TYPE
		SYNTAX		OCTET STRING ( SIZE ( 0..43 ) )
		MAX-ACCESS	read-create
		STATUS		current
		DESCRIPTION	"Must: MEP service name.
					 Value length is 1-43."
		::= { iswEcfmCcmEntry 7 }
		
--8
	iswEcfmCcmRowStatus	OBJECT-TYPE
		SYNTAX		RowStatus
		MAX-ACCESS	read-create
		STATUS		current
		DESCRIPTION	"Row Status."
		::= { iswEcfmCcmEntry 8 }

--EcfmStatus
--1
	iswEcfmStatusTable		OBJECT-TYPE
		SYNTAX		SEQUENCE OF IswEcfmStatusEntry
		MAX-ACCESS	not-accessible 
		STATUS		current
		DESCRIPTION	"Ecfm Status table."  
		::= { iswEcfmStatus 1 }

	iswEcfmStatusEntry		OBJECT-TYPE
		SYNTAX		IswEcfmStatusEntry
		MAX-ACCESS	not-accessible
		STATUS		current
		DESCRIPTION	"Ecfm Status entry."
		INDEX		{ iswEcfmStatusMepIndex }  
		::= { iswEcfmStatusTable 1 }
	
	
	IswEcfmStatusEntry ::= SEQUENCE{
		iswEcfmStatusMepIndex			Integer32,
		iswEcfmStatusDomainIndex		Integer32,
		iswEcfmStatusDomainFormat		Integer32,
		iswEcfmStatusDomainName			OCTET STRING,
		iswEcfmStatusDomainLevel		Integer32,
		iswEcfmStatusServiceFormat		Integer32,
		iswEcfmStatusServiceName		OCTET STRING,
		iswEcfmStatusServiceVlan		Integer32,
		iswEcfmStatusMepId				Integer32,
		iswEcfmStatusVlan				Integer32,
		iswEcfmStatusType				Integer32,
		iswEcfmStatusMepUp				Integer32,
		iswEcfmStatusMacAddr			PhysAddress,
	}

--1
	iswEcfmStatusMepIndex		OBJECT-TYPE
		SYNTAX		Integer32
		MAX-ACCESS	not-accessible
		STATUS		current
		DESCRIPTION	"Ecfm status index, it's Ecfm Mep index."
		::= { iswEcfmStatusEntry 1 } 

--2
	iswEcfmStatusDomainIndex		OBJECT-TYPE
		SYNTAX		Integer32 ( 1 .. 8 )
		MAX-ACCESS	read-only
		STATUS		current
		DESCRIPTION	"Ecfm status index, it's Ecfm Domain index."
		::= { iswEcfmStatusEntry 2 }
		
--3
	iswEcfmStatusDomainFormat		OBJECT-TYPE
		SYNTAX		Integer32 { dns-like-name (1), mac-addr(2), char-string(3), none(4) }
		MAX-ACCESS	read-only
		STATUS		current
		DESCRIPTION	"Domain name format, 1: dns-like-name, 2: mac-addr, 3: char-string, 4:none."
		::= { iswEcfmStatusEntry 3 }

--4
	iswEcfmStatusDomainName		OBJECT-TYPE
		SYNTAX		OCTET STRING ( SIZE ( 1..43 ) )
		MAX-ACCESS	read-only
		STATUS		current
		DESCRIPTION	"Ecfm domain name, maximum length is 43."
		::= { iswEcfmStatusEntry 4 }

--5
	iswEcfmStatusDomainLevel		OBJECT-TYPE
		SYNTAX		Integer32 ( 0 .. 7 )
		MAX-ACCESS	read-only
		STATUS		current
		DESCRIPTION	"Ecfm domain level, vlaue range 0-7."
		::= { iswEcfmStatusEntry 5 }

--6
	iswEcfmStatusServiceFormat		OBJECT-TYPE
		SYNTAX		Integer32 { primary-vid (1), char-string (2), unsigned-int16(3), rfc2865-vpn-id(4), icc(5) }
		MAX-ACCESS	read-only
		STATUS		current
		DESCRIPTION	"Service name format, 1: primary-vid, 2: char-string, 3: unsigned-int16, 4: rfc2865-vpn-id, 5: icc."
		::= { iswEcfmStatusEntry 6 }

--7
	iswEcfmStatusServiceName		OBJECT-TYPE
		SYNTAX		OCTET STRING ( SIZE ( 0..43 ) )
		MAX-ACCESS	read-only
		STATUS		current
		DESCRIPTION	"Ecfm service name, maximum length is 43."
		::= { iswEcfmStatusEntry 7 }

--8
	iswEcfmStatusServiceVlan		OBJECT-TYPE
		SYNTAX		Integer32 ( 1 .. 4094 )
		MAX-ACCESS	read-only
		STATUS		current
		DESCRIPTION	"Ecfm service vlan, vlaue range 1-4094"
		::= { iswEcfmStatusEntry 8 }

--9
	iswEcfmStatusMepId		OBJECT-TYPE
		SYNTAX		Integer32 ( 1 .. 8191 )
		MAX-ACCESS	read-only
		STATUS		current
		DESCRIPTION	"Maintenance end point ID, value range is 1-8191."
		::= { iswEcfmStatusEntry 9 }

--10
	iswEcfmStatusVlan		OBJECT-TYPE
		SYNTAX		Integer32 ( 1 .. 4094 )
		MAX-ACCESS	read-only
		STATUS		current
		DESCRIPTION	"vlaue range 1-4094"
		::= { iswEcfmStatusEntry 10 }

--11
	iswEcfmStatusType		OBJECT-TYPE
		SYNTAX		Integer32 { local (0), remote (1) }
		MAX-ACCESS	read-only
		STATUS		current
		DESCRIPTION	"Local or Remote."
		::= { iswEcfmStatusEntry 11 }

--12
	iswEcfmStatusMepUp		OBJECT-TYPE
		SYNTAX		Integer32 { down (0), up (1) }
		MAX-ACCESS	read-only
		STATUS		current
		DESCRIPTION	"Direction up or down"
		::= { iswEcfmStatusEntry 12 }

--13
	iswEcfmStatusMacAddr	OBJECT-TYPE
		SYNTAX		PhysAddress
		MAX-ACCESS	read-only
		STATUS		current
		DESCRIPTION	"Mac Address format string xx:xx:xx:xx:xx:xx."
		::= { iswEcfmStatusEntry 13 }

--EcfmStatusErrors
--1
	iswEcfmStatusErrorsTable		OBJECT-TYPE
		SYNTAX		SEQUENCE OF IswEcfmStatusErrorsEntry
		MAX-ACCESS	not-accessible 
		STATUS		current
		DESCRIPTION	"Ecfm Status Errors table."  
		::= { iswEcfmStatusErrors 1 }

	iswEcfmStatusErrorsEntry		OBJECT-TYPE
		SYNTAX		IswEcfmStatusErrorsEntry
		MAX-ACCESS	not-accessible
		STATUS		current
		DESCRIPTION	"Ecfm Status Errors entry."
		INDEX		{ iswEcfmStatusErrorsLocalMepId , iswEcfmStatusErrorsRemoteMepId}  
		::= { iswEcfmStatusErrorsTable 1 }
	
	IswEcfmStatusErrorsEntry ::= SEQUENCE{
		iswEcfmStatusErrorsLocalMepId		Integer32,
		iswEcfmStatusErrorsRemoteMepId		Integer32,
		iswEcfmStatusErrorsLevel			Integer32,
		iswEcfmStatusErrorsVlan				Integer32,
		iswEcfmStatusErrorsDefect			Integer32,
	}

--1
	iswEcfmStatusErrorsLocalMepId		OBJECT-TYPE
		SYNTAX		Integer32 ( 1 .. 8191 )
		MAX-ACCESS	not-accessible
		STATUS		current
		DESCRIPTION	"Ecfm errors local mpid, value range is 1-8191."
		::= { iswEcfmStatusErrorsEntry 1 } 

--2
	iswEcfmStatusErrorsRemoteMepId		OBJECT-TYPE
		SYNTAX		Integer32 ( 1 .. 8191 )
		MAX-ACCESS	not-accessible
		STATUS		current
		DESCRIPTION	"Ecfm errors remote mpid, value range is 1-8191."
		::= { iswEcfmStatusErrorsEntry 2 } 

--3
	iswEcfmStatusErrorsLevel		OBJECT-TYPE
		SYNTAX		Integer32 ( 0 .. 7 )
		MAX-ACCESS	read-only
		STATUS		current
		DESCRIPTION	"Ecfm errors level, value range is 0-7."
		::= { iswEcfmStatusErrorsEntry 3 }

--4
	iswEcfmStatusErrorsVlan		OBJECT-TYPE
		SYNTAX		Integer32 ( 1 .. 4094)
		MAX-ACCESS	read-only
		STATUS		current
		DESCRIPTION	"Ecfm errors vlan, value range is 1-4094."
		::= { iswEcfmStatusErrorsEntry 4 }
		
--5
	iswEcfmStatusErrorsDefect		OBJECT-TYPE
		SYNTAX		Integer32 { noErrors (0), remoteDefectIndication (1), lossOfContinuity (2), unexpectedPeriod (3), unexpectedMep (4), mismerge (5), unexpectedLevel (6), locallyLinkFailure (7), internalHwFailure (8), internalSwFailure (9), aisCondition (10) , lckConditio(11) }
		MAX-ACCESS	read-only
		STATUS		current
		DESCRIPTION	"Ecfm errors defect, value range is 0-11.
					 0:noErrors, 1:remoteDefectIndication, 2:lossOfContinuity, 3:unexpectedPeriod, 4:unexpectedMep, 
					 5:mismerge, 6:unexpectedLevel, 7:locallyLinkFailure, 8:internalH/wFailure, 9:internalS/wFailure
					 10:aisCondition, 11:lckConditio "
		::= { iswEcfmStatusErrorsEntry 5 }

--ErpsGlobal
--1		
	iswErpsGlobalStatus		OBJECT-TYPE
		SYNTAX		Integer32 { disable (0), enable (1) }
		MAX-ACCESS	read-write
		STATUS		current
		DESCRIPTION	"ERPS status enable or disable. Control ERPS working or not, it will stop working when the status is disable. Default value is disable (0)."   
		DEFVAL		{ 0 }
		::= { iswErpsGlobal 1 }	

--ErpsRing
--1
	iswErpsRingTable		OBJECT-TYPE
		SYNTAX		SEQUENCE OF IswErpsRingEntry
		MAX-ACCESS	not-accessible 
		STATUS		current
		DESCRIPTION	"Erps Ring table."  
		::= { iswErpsRing 1 }

	iswErpsRingEntry		OBJECT-TYPE
		SYNTAX		IswErpsRingEntry
		MAX-ACCESS	not-accessible
		STATUS		current
		DESCRIPTION	"Erps Ring entry."
		INDEX		{ iswErpsRingInstance }  
		::= { iswErpsRingTable 1 }

	IswErpsRingEntry ::= SEQUENCE{
		iswErpsRingInstance				Integer32,
		iswErpsRingGroupId				Unsigned32,
		iswErpsRingRole					Integer32,
		iswErpsRingRplIfIndex			IswGbeIndex,
		iswErpsRingVersion				Integer32,
		iswErpsRingOpMode				Integer32,
		iswErpsRingMainRingId			Unsigned32,
		iswErpsRingPropagateTcRingId	Unsigned32,
		iswErpsRingPropagateTcStatus	Integer32,
		iswErpsRingVirtualChannel		Integer32,
		iswErpsRingIfIndex1				IswGbeIndex,
		iswErpsRingIfIndex2				IswGbeIndex,
		iswErpsRingVlan					Integer32,
		iswErpsRingPort1Mep				Integer32,
		iswErpsRingPort2Mep				Integer32,
		iswErpsRingHoldOff				Integer32,
		iswErpsRingGuard				Integer32,
		iswErpsRingWTR					Integer32,
		iswErpsRingWTB					Integer32,
		iswErpsRingActive				Integer32,
		iswErpsRingGroupRingType		Integer32,
		iswErpsRingRowStatus			RowStatus
	}

--1
	iswErpsRingInstance		OBJECT-TYPE
		SYNTAX		Integer32 ( 1 .. 4 )
		MAX-ACCESS	not-accessible
		STATUS		current
		DESCRIPTION	"ERPS ring instance, value range is 1-4."
		::= { iswErpsRingEntry 1 } 
		
--2
	iswErpsRingGroupId		OBJECT-TYPE
		SYNTAX		Unsigned32 ( 1 .. 4294967295 )
		MAX-ACCESS	read-create
		STATUS		current
		DESCRIPTION	"ERPS ring group id, value range is 1-4294967295."
		::= { iswErpsRingEntry 2 } 

--3
	iswErpsRingRole		OBJECT-TYPE
		SYNTAX		Integer32 { none (0), owner (1), neighbor (2) }
		MAX-ACCESS	read-create
		STATUS		current
		DESCRIPTION	"ERPS node role, 0: none, 1: owner, 2: neighbor, default is 0, value range is 0-2."
		DEFVAL		{ 0 }
		::= { iswErpsRingEntry 3 } 
		
--4
	iswErpsRingRplIfIndex		OBJECT-TYPE
		SYNTAX		IswGbeIndex
		MAX-ACCESS	read-create
		STATUS		current
		DESCRIPTION	"ErpsRing Role port interface.
					 It must be fill when the RPL Role is Owner.
					 It must be 0 when the role is Others."
		::= { iswErpsRingEntry 4 }

--5 
	iswErpsRingVersion		OBJECT-TYPE
		SYNTAX		Integer32 { v1 (1), v2 (2) }
		MAX-ACCESS	read-create
		STATUS		current
		DESCRIPTION	"ErpsRing version 1: v1, 2: v2, default is V2."
		DEFVAL		{ 2 }
		::= { iswErpsRingEntry 5 }

--6 
	iswErpsRingOpMode		OBJECT-TYPE
		SYNTAX		Integer32 { revert (1), non-revert (2) }
		MAX-ACCESS	read-create
		STATUS		current
		DESCRIPTION	"ErpsRing 1: Revert, 2:Non-Revert
					 Must: The role is Owner, it will recover RPL port to blocked when the ring is good.
					 Default is true."
		DEFVAL		{ 1 }
		::= { iswErpsRingEntry 6 }

--7   
	iswErpsRingMainRingId		OBJECT-TYPE
		SYNTAX		Unsigned32 ( 1 .. 4294967295 )
		MAX-ACCESS	read-create
		STATUS		current
		DESCRIPTION	"Sub-ring setting, follow main ring group id, value range is 1-4294967295."
		::= { iswErpsRingEntry 7 }
		
--8
	iswErpsRingPropagateTcRingId		OBJECT-TYPE
		SYNTAX		Unsigned32 ( 1 .. 4294967295 )
		MAX-ACCESS	read-create
		STATUS		current
		DESCRIPTION	"Ring ID configuration for TC propagation, only work on sub-ring.
					 value range is 1-4294967295."
		::= { iswErpsRingEntry 8 }

--9
	iswErpsRingPropagateTcStatus		OBJECT-TYPE
		SYNTAX		Integer32 { disable (0), enable (1) }
		MAX-ACCESS	read-create
		STATUS		current
		DESCRIPTION	"PropagateTc status, only work on sub-ring.
					 0: disable,  1: enable, default is disable."
		DEFVAL		{ 0 }
		::= { iswErpsRingEntry 9 } 

--10
	iswErpsRingVirtualChannel		OBJECT-TYPE
		SYNTAX		Integer32 { disable (0), enable (1) }
		MAX-ACCESS	read-create
		STATUS		current
		DESCRIPTION	"Assign ERPS sub-ring control message communication type.
					 0: disable,  1: enable, default is enable."
		DEFVAL		{ 1 }
		::= { iswErpsRingEntry 10 }
		
--11 
	iswErpsRingIfIndex1		OBJECT-TYPE
		SYNTAX		IswGbeIndex
		MAX-ACCESS	read-create
		STATUS		current
		DESCRIPTION	"Must: Assign ERPS ring port 0."
		::= { iswErpsRingEntry 11 }
		
--12 
	iswErpsRingIfIndex2		OBJECT-TYPE
		SYNTAX		IswGbeIndex
		MAX-ACCESS	read-create
		STATUS		current
		DESCRIPTION	"Assign ERPS ring port 1. No need to fill this field when the ERPS is sub-ring."
		::= { iswErpsRingEntry 12 }

--13
	iswErpsRingVlan		OBJECT-TYPE
		SYNTAX		Integer32 ( 1 .. 4094 )
		MAX-ACCESS	read-create
		STATUS		current
		DESCRIPTION	"Protect vlan, value range is 1-4094."
		::= { iswErpsRingEntry 13 } 

--14
	iswErpsRingPort1Mep		OBJECT-TYPE
		SYNTAX		Integer32 ( 1 .. 8191 )
		MAX-ACCESS	read-create
		STATUS		current
		DESCRIPTION	"Must: ERPS ring 0 Mep ID.
					 Maintenance entity group end point related configuration, value range is 1-8191."
		::= { iswErpsRingEntry 14 }
		
--15
	iswErpsRingPort2Mep		OBJECT-TYPE
		SYNTAX		Integer32 ( 1 .. 8191 )
		MAX-ACCESS	read-create
		STATUS		current
		DESCRIPTION	"ERPS ring 1 Mep ID. No need to fill this field when the ERPS is sub-ring.
					 Maintenance entity group end point related configuration, value range is 1-8191."
		::= { iswErpsRingEntry 15 }

--16  
	iswErpsRingHoldOff		OBJECT-TYPE
		SYNTAX		Integer32 ( 0 .. 10000 )
		MAX-ACCESS	read-create
		STATUS		current
		DESCRIPTION	"Must: Hold off timer value configuration.
					 Value range 0 - 10000, unit: ms, step 100 ms, default is 0 ms."
		DEFVAL		{ 0 }
		::= { iswErpsRingEntry 16 }

--17
	iswErpsRingGuard		OBJECT-TYPE
		SYNTAX		Integer32 ( 10 .. 2000 )
		MAX-ACCESS	read-create
		STATUS		current
		DESCRIPTION	"Must: Guard Interval to prevent reception of outdated RAPS messages.
					 Value range 10 - 2000, unit: ms, step 10 ms, default is 500 ms. 
					 Rule: WTB time >= Guard Time + 5000 (ms)"
		DEFVAL		{ 500 }
		::= { iswErpsRingEntry 17 }

--18 
	iswErpsRingWTR		OBJECT-TYPE
		SYNTAX		Integer32 ( 1 .. 12 )
		UNITS		"minute"
		MAX-ACCESS	read-create
		STATUS		current
		DESCRIPTION	"Must: The period of the WTR time can be configured by the operator in 1 minute steps between 1 and 12 minutes with a default value of 1 minute."
		DEFVAL		{ 1 }
		::= { iswErpsRingEntry 18 }

--19		
	iswErpsRingWTB		OBJECT-TYPE
		SYNTAX		Integer32 ( 5010 .. 7000 )
		UNITS		"millisecond"
		MAX-ACCESS	read-create
		STATUS		current
		DESCRIPTION	"Must: The period of the WTB time can be configured by the operator.
					 This value is not configurable explicitly as it is 5 seconds longer than the guard timer.
					 The range of the WTB timer. Value range 5010 - 7000, unit: ms, default is 5500 ms. 
					 Rule: WTB time >= Guard Time + 5000 (ms)"
		DEFVAL		{ 5500 }
		::= { iswErpsRingEntry 19 }
		
--20 
	iswErpsRingActive		OBJECT-TYPE
		SYNTAX		Integer32 { inactive (0), active (1) }
		MAX-ACCESS	read-create
		STATUS		current
		DESCRIPTION	"Activates the ERPS ring, 0: inactive,  1: active, default is inactive."
		DEFVAL		{ 0 }
		::= { iswErpsRingEntry 20 }
		
--21 
	iswErpsRingGroupRingType		OBJECT-TYPE
		SYNTAX		Integer32 { sub-ring (0), major-ring (1) }
		MAX-ACCESS	read-create
		STATUS		current
		DESCRIPTION	"ERPS group ring type, declare major ring is 1, sub-ring is 0.
					 default is Major Ring."
		DEFVAL		{ 1 }
		::= { iswErpsRingEntry 21 }

--22
	iswErpsRingRowStatus	OBJECT-TYPE
		SYNTAX		RowStatus
		MAX-ACCESS	read-create
		STATUS		current
		DESCRIPTION	"Row Status."
		::= { iswErpsRingEntry 22 }

--2	
--1 
	iswErpsInstance	OBJECT-TYPE
		SYNTAX		Integer32 ( 1 .. 4 )
		MAX-ACCESS	read-write
		STATUS		current
		DESCRIPTION	"Erps Instance."
		::= { iswErpsRingActionCtrl 1 }

--2
	iswErpsRingActionIfIndex	OBJECT-TYPE
		SYNTAX		Integer32 { ringPort0 (0), ringPort1 (1) }
		MAX-ACCESS	read-write
		STATUS		current
		DESCRIPTION	"Gigabit ethernet interface."
		::= { iswErpsRingActionCtrl 2 }
			
--3		
	iswErpsRingAction	OBJECT-TYPE
		SYNTAX		Integer32 { forceSwitch (1), manualSwitch (2) , clear (3)}
		MAX-ACCESS	read-write
		STATUS		current
		DESCRIPTION	"Applies action for ring, 1:Force Switch,  2:Manual Switch,  3:Clear."
		::= { iswErpsRingActionCtrl 3 }

--ErpsStatus
--1
	iswErpsStatusTable		OBJECT-TYPE
		SYNTAX		SEQUENCE OF IswErpsStatusEntry
		MAX-ACCESS	not-accessible 
		STATUS		current
		DESCRIPTION	"Ecfm Status Errors table."  
		::= { iswErpsStatus 1 }
		
	iswErpsStatusEntry		OBJECT-TYPE
		SYNTAX		IswErpsStatusEntry
		MAX-ACCESS	not-accessible
		STATUS		current
		DESCRIPTION	"Ecfm Status Errors entry."
		INDEX		{ iswErpsStatusRingInstance }  
		::= { iswErpsStatusTable 1 }
	
	
	IswErpsStatusEntry ::= SEQUENCE{
		iswErpsStatusRingInstance	Integer32,
		iswErpsStatusPort1			Integer32,
		iswErpsStatusPort2			Integer32,
		iswErpsStatusLink1			Integer32,
		iswErpsStatusLink2			Integer32,
		iswErpsStatusState			Integer32,
		iswErpsStatusHoldOff		Integer32,
		iswErpsStatusGuard			Integer32,
		iswErpsStatusWTR			Integer32,
		iswErpsStatusWTB			Integer32,
		iswErpsStatusRpl			Integer32,
	}

--1
	iswErpsStatusRingInstance		OBJECT-TYPE
		SYNTAX		Integer32 ( 1 .. 4 )
		MAX-ACCESS	not-accessible
		STATUS		current
		DESCRIPTION	"ERPS ring instance, value range is 1-4."
		::= { iswErpsStatusEntry 1 } 
		
--2
	iswErpsStatusPort1		OBJECT-TYPE
		SYNTAX		Integer32 { none (0), unblocked (1), blocked (2) }
		MAX-ACCESS	read-only
		STATUS		current
		DESCRIPTION	"ERPS ring port1 status, 0: None,  1: UnBlocked,  2: Blocked."
		::= { iswErpsStatusEntry 2 }

--3
	iswErpsStatusPort2		OBJECT-TYPE
		SYNTAX		Integer32 { none (0), unblocked (1), blocked (2) }
		MAX-ACCESS	read-only
		STATUS		current
		DESCRIPTION	"ERPS ring port2 status, 0: None,  1: UnBlocked,  2: Blocked."
		::= { iswErpsStatusEntry 3 }

--4
	iswErpsStatusLink1		OBJECT-TYPE
		SYNTAX		Integer32 { none (0), ok-notFailed (1), localSf (2), remoteSf (3), ms (4), fs (5) }
		MAX-ACCESS	read-only
		STATUS		current
		DESCRIPTION	"ERPS ring link1 status, 0: None,  1: OK(Not Failed),  2: Local SF,  3: Remote SF,  4: MS,  5: FS."
		::= { iswErpsStatusEntry 4 }

--5
	iswErpsStatusLink2		OBJECT-TYPE
		SYNTAX		Integer32 { none (0), ok-notFailed (1), localSf (2), remoteSf (3), ms (4), fs (5) }
		MAX-ACCESS	read-only
		STATUS		current
		DESCRIPTION	"ERPS ring link2 status, 0: None,  1: OK(Not Failed),  2: Local SF,  3: Remote SF,  4: MS,  5: FS."
		::= { iswErpsStatusEntry 5 }

--6
	iswErpsStatusState		OBJECT-TYPE
		SYNTAX		Integer32 { disable (0), idle (1), protection (2), pending (3), manualSwitch (4), forceSwitch (5) }
		MAX-ACCESS	read-only
		STATUS		current
		DESCRIPTION	"ERPS ring status, 0: disable,  1: Idle,  2: Protection,  3: Pending,  4: Manual Switch,  5: Force Switch."
		::= { iswErpsStatusEntry 6 }

--7
	iswErpsStatusHoldOff		OBJECT-TYPE
		SYNTAX		Integer32 ( 0 .. 10000 )
		UNITS		"millisecond"
		MAX-ACCESS	read-only
		STATUS		current
		DESCRIPTION	"ERPS ring hold off time, unit is ms."
		::= { iswErpsStatusEntry 7 }

--8
	iswErpsStatusGuard		OBJECT-TYPE
		SYNTAX		Integer32 ( 0 .. 2000 )
		UNITS		"millisecond"
		MAX-ACCESS	read-only
		STATUS		current
		DESCRIPTION	"ERPS ring gard time, unit is ms."
		::= { iswErpsStatusEntry 8 }
		
--9
	iswErpsStatusWTR		OBJECT-TYPE
		SYNTAX		Integer32 ( 0 .. 720000 )
		UNITS		"millisecond"
		MAX-ACCESS	read-only
		STATUS		current
		DESCRIPTION	"ERPS ring wait to restore time, unit is ms."
		::= { iswErpsStatusEntry 9 }

--10
	iswErpsStatusWTB		OBJECT-TYPE
		SYNTAX		Integer32 ( 0 .. 7000 )
		UNITS		"millisecond"
		MAX-ACCESS	read-only
		STATUS		current
		DESCRIPTION	"ERPS ring wait to block time, unit is ms."
		::= { iswErpsStatusEntry 10 }
		
--11
	iswErpsStatusRpl		OBJECT-TYPE
		SYNTAX		Integer32 { none (0), unblocked (1), blocked (2) }
		MAX-ACCESS	read-only
		STATUS		current
		DESCRIPTION	"ERPS ring RPL status, 0: None,  1: UnBlocked,  2: Blocked."
		::= { iswErpsStatusEntry 11 }
--Snmp
	iswSnmpUSMUserTable		OBJECT-TYPE
		SYNTAX		SEQUENCE OF IswSnmpUSMUserEntry
		MAX-ACCESS	not-accessible 
		STATUS		current
		DESCRIPTION	"Snmp USM User table."  
		::= { iswSnmpUSMUser 1 }

	iswSnmpUSMUserEntry		OBJECT-TYPE
		SYNTAX		IswSnmpUSMUserEntry
		MAX-ACCESS	not-accessible
		STATUS		current
		DESCRIPTION	"Snmp USM User entry."
		INDEX		{ iswSnmpUSMUserIndex }  
		::= { iswSnmpUSMUserTable 1 }
	
	
	IswSnmpUSMUserEntry ::= SEQUENCE{
		iswSnmpUSMUserIndex			Integer32,
		iswSnmpUSMUserUserName		OCTET STRING,
		iswSnmpUSMUserGroupName		OCTET STRING,
		iswSnmpUSMUserSecLevel		Integer32,
		iswSnmpUSMUserAuthMethod	Integer32,
		iswSnmpUSMUserAuthPass		OCTET STRING,
		iswSnmpUSMUserPrivMethod	Integer32,
		iswSnmpUSMUserPrivPass		OCTET STRING,
		iswSnmpUSMUserType			Integer32,
		iswSnmpUSMUserRowstatus		RowStatus,
	}

--1
	iswSnmpUSMUserIndex		OBJECT-TYPE
		SYNTAX		Integer32 ( 1 .. 32 )
		MAX-ACCESS	not-accessible
		STATUS		current
		DESCRIPTION	"Snmp USM User Index, value range is 1-32."
		::= { iswSnmpUSMUserEntry 1 } 

--2
	iswSnmpUSMUserUserName		OBJECT-TYPE
		SYNTAX		OCTET STRING ( SIZE( 1 .. 31 ) )
		MAX-ACCESS	read-create
		STATUS		current
		DESCRIPTION	"User name, length 1~31.
					 Accept any characters except space, quote mark and ?."
		::= { iswSnmpUSMUserEntry 2 } 

--3
	iswSnmpUSMUserGroupName		OBJECT-TYPE
		SYNTAX		OCTET STRING ( SIZE( 1 .. 15 ) )
		MAX-ACCESS	read-create
		STATUS		current
		DESCRIPTION	"Access Group name, length 1~15.
					 Accept any characters except space, quote mark and ?.
					 If user type is Read Only or Read Write, then this field is not needed."
		::= { iswSnmpUSMUserEntry 3 } 

--4
	iswSnmpUSMUserSecLevel		OBJECT-TYPE
		SYNTAX		Integer32 { noauth (1), auth (2), priv (3) }
		MAX-ACCESS	read-only
		STATUS		current
		DESCRIPTION	"User security level.
					 If Security Model is v1 or v2c, the field is not used, it will be show as --.
					 States as below:
						- NoAuth, NoPriv (No authentication and no Privacy)
						- Auth, NoPriv (Authentication and no Privacy)
						- Auth, Priv (Authentication and Privacy)"
		::= { iswSnmpUSMUserEntry 4 } 

--5
	iswSnmpUSMUserAuthMethod		OBJECT-TYPE
		SYNTAX		Integer32 { none (1), md5 (2), sha (3) }
		MAX-ACCESS	read-create
		STATUS		current
		DESCRIPTION	"User authentication protocol. Works only if SNMPv3 is enabled.
					 Options:
						1. None
						2. MD5
						3. SHA
					 If Auth Protocol is None, Priv Protocol always is None. If Auth Protocol is MD5 or SHA, Auth Password should be input."
		DEFVAL		{ 2 }
		::= { iswSnmpUSMUserEntry 5 } 

--6
	iswSnmpUSMUserAuthPass		OBJECT-TYPE
		SYNTAX		OCTET STRING ( SIZE( 0 .. 15 ) )
		MAX-ACCESS	read-create
		STATUS		current
		DESCRIPTION	"Authentication password, length 8~15. Works only if SNMPv3 is enabled.
					 Accept any characters except space, quote mark and ?.

					 If Authentication Protocol is None, then Privacy options are not needed."
		::= { iswSnmpUSMUserEntry 6 } 

--7
	iswSnmpUSMUserPrivMethod		OBJECT-TYPE
		SYNTAX		Integer32 { none (1), des (2) }
		MAX-ACCESS	read-create
		STATUS		current
		DESCRIPTION	"User Privacy protocol. Works only if SNMPv3 is enabled.
					 If Priv Protocol is not None, Priv Password should be input.
					 Options:
						1. None
						2. DES		"
		DEFVAL		{ 2 }
		::= { iswSnmpUSMUserEntry 7 } 

--8
	iswSnmpUSMUserPrivPass		OBJECT-TYPE
		SYNTAX		OCTET STRING ( SIZE( 0 .. 15 ) )
		MAX-ACCESS	read-create
		STATUS		current
		DESCRIPTION	"Privacy password, length 8~15. Works only if SNMPv3 is enabled.
					 Accept any characters except space, quote mark and ?.

					 If Priv Protocol is None the field not needed."
		::= { iswSnmpUSMUserEntry 8 } 

--9
	iswSnmpUSMUserType		OBJECT-TYPE
		SYNTAX		Integer32 { v3User (1), readOnly (2), readWrite (3) }
		MAX-ACCESS	read-create
		STATUS		current
		DESCRIPTION	"SNMPv3 user type.
					 Options:
						1. v3 User
						2. Read Only
						3. Read Write
					 If User type is v3 User, the Group Name should be provided.
					 No matter which User Type is selected, the authentication and Privacy options are allowed."
		DEFVAL		{ 1 }		
		::= { iswSnmpUSMUserEntry 9 } 

--10
	iswSnmpUSMUserRowstatus	OBJECT-TYPE
		SYNTAX		RowStatus
		MAX-ACCESS	read-create
		STATUS		current
		DESCRIPTION	"Row Status."
		::= { iswSnmpUSMUserEntry 10 }		








--2
	iswSnmpVACMGroupTable		OBJECT-TYPE
		SYNTAX		SEQUENCE OF IswSnmpVACMGroupEntry
		MAX-ACCESS	not-accessible 
		STATUS		current
		DESCRIPTION	"Snmp VACM Group table."  
		::= { iswSnmpVACMGroup 1 }

	iswSnmpVACMGroupEntry		OBJECT-TYPE
		SYNTAX		IswSnmpVACMGroupEntry
		MAX-ACCESS	not-accessible
		STATUS		current
		DESCRIPTION	"Snmp VACM Group entry."
		INDEX		{ iswSnmpVACMGroupIndex }  
		::= { iswSnmpVACMGroupTable 1 }
	
	
	IswSnmpVACMGroupEntry ::= SEQUENCE{
		iswSnmpVACMGroupIndex		Integer32,
		iswSnmpVACMGroupGroupName	OCTET STRING,
		iswSnmpVACMGroupSecModel	Integer32,
		iswSnmpVACMGroupSecLevel	Integer32,
		iswSnmpVACMGroupRead		OCTET STRING,
		iswSnmpVACMGroupWrite		OCTET STRING,
		iswSnmpVACMGroupRowstatus	RowStatus,
	}

--1
	iswSnmpVACMGroupIndex		OBJECT-TYPE
		SYNTAX		Integer32 ( 1 .. 32 )
		MAX-ACCESS	not-accessible
		STATUS		current
		DESCRIPTION	"Snmp VACM Group Index, value range is 1-32."
		::= { iswSnmpVACMGroupEntry 1 } 

--2
	iswSnmpVACMGroupGroupName		OBJECT-TYPE
		SYNTAX		OCTET STRING ( SIZE( 1 .. 15 ) )
		MAX-ACCESS	read-create
		STATUS		current
		DESCRIPTION	"Group name, length 1~15.
					 Accept any characters except space, quote mark and ?."
		::= { iswSnmpVACMGroupEntry 2 } 

--3
	iswSnmpVACMGroupSecModel		OBJECT-TYPE
		SYNTAX		Integer32 { v1 (1), v2c (2), v3usm (3) }
		MAX-ACCESS	read-create
		STATUS		current
		DESCRIPTION	"SNMP security model.
					 Options:
						- v1
						  supports read/write view.
						- v2c
						  supports read/write view.
						- v3usm
						  supports read/write view & security level."
		DEFVAL		{ 3 }
		::= { iswSnmpVACMGroupEntry 3 } 

--4
	iswSnmpVACMGroupSecLevel		OBJECT-TYPE
		SYNTAX		Integer32 { noauth (1), auth (2), priv (3) }
		MAX-ACCESS	read-create
		STATUS		current
		DESCRIPTION	"User security level.
					 If Security Model is v1 or v2c, the field is not used, it will be show as --.
					 States as below:
						- NoAuth, NoPriv (No authentication and no Privacy)
						- Auth, NoPriv (Authentication and no Privacy)
						- Auth, Priv (Authentication and Privacy)"
		DEFVAL		{ 1 }
		::= { iswSnmpVACMGroupEntry 4 } 

--5
	iswSnmpVACMGroupRead		OBJECT-TYPE
		SYNTAX		OCTET STRING ( SIZE( 1 .. 15 ) )
		MAX-ACCESS	read-create
		STATUS		current
		DESCRIPTION	"Access View for Read (snmp-get)
					 Select from the view list. If list is empty, create access view with page SNMP View first.
					 It will display unknown(xxxx) when the name of xxxx doesn't exist in view name."
		::= { iswSnmpVACMGroupEntry 5 } 

--6
	iswSnmpVACMGroupWrite		OBJECT-TYPE
		SYNTAX		OCTET STRING ( SIZE( 1 .. 15 ) )
		MAX-ACCESS	read-create
		STATUS		current
		DESCRIPTION	"Access View for Write (snmp-set)
					 Select from the view list. If list is empty, create access view with page SNMP View first.
					 It will display unknown(xxxx) when the name of xxxx doesn't exist in view name."
		::= { iswSnmpVACMGroupEntry 6 } 

--7		
	iswSnmpVACMGroupRowstatus	OBJECT-TYPE
		SYNTAX		RowStatus
		MAX-ACCESS	read-create
		STATUS		current
		DESCRIPTION	"Row Status."
		::= { iswSnmpVACMGroupEntry 7 }		



--3
	iswSnmpCommunityTable		OBJECT-TYPE
		SYNTAX		SEQUENCE OF IswSnmpCommunityEntry
		MAX-ACCESS	not-accessible 
		STATUS		current
		DESCRIPTION	"Snmp Community table."  
		::= { iswSnmpCommunity 1 }

	iswSnmpCommunityEntry		OBJECT-TYPE
		SYNTAX		IswSnmpCommunityEntry
		MAX-ACCESS	not-accessible
		STATUS		current
		DESCRIPTION	"Snmp Community entry."
		INDEX		{ iswSnmpCommunityIndex }  
		::= { iswSnmpCommunityTable 1 }
	
	
	IswSnmpCommunityEntry ::= SEQUENCE{
		iswSnmpCommunityIndex		Integer32,
		iswSnmpCommunityName		OCTET STRING,
		iswSnmpCommunityViewName	OCTET STRING,
		iswSnmpCommunityGroupName	OCTET STRING,
		iswSnmpCommunityAccessMode	Integer32,
		iswSnmpCommunityStatus		RowStatus,
	}

--1
	iswSnmpCommunityIndex		OBJECT-TYPE
		SYNTAX		Integer32 ( 1 .. 32 )
		MAX-ACCESS	not-accessible
		STATUS		current
		DESCRIPTION	"SNMP Community index, The system supports up to 32 Community data."
		::= { iswSnmpCommunityEntry 1 } 

--2
	iswSnmpCommunityName		OBJECT-TYPE
		SYNTAX		OCTET STRING ( SIZE( 1 .. 31 ) )
		MAX-ACCESS	read-create
		STATUS		current
		DESCRIPTION	"SNMP Community name, for SNMP v1/v2c. 
					 Only if community name match, the SNMP request would be received. 
					 Community Name max size is 31 characters."
		::= { iswSnmpCommunityEntry 2 } 

--3
	iswSnmpCommunityViewName		OBJECT-TYPE
		SYNTAX		OCTET STRING ( SIZE( 0 .. 15 ) )
		MAX-ACCESS	read-create
		STATUS		current
		DESCRIPTION	"View and Group are used for SNMP v3 only. 
					 A community is allowed to bind one of the view or group name. If it does not take any group or view, it will be a v1/v2c community. If it takes a view or a group name, the community will be treated as a v3 community. The v2c and v3 communities could exit in the community table concurrently. 
					 It will display unknown(name) when view/group name doesn't exist in view/group table."
		::= { iswSnmpCommunityEntry 3 } 

--4
	iswSnmpCommunityGroupName		OBJECT-TYPE
		SYNTAX		OCTET STRING ( SIZE( 0 .. 15 ) )
		MAX-ACCESS	read-create
		STATUS		current
		DESCRIPTION	"View and Group are used for SNMP v3 only. 
					 A community is allowed to bind one of the view or group name. If it does not take any group or view, it will be a v1/v2c community. If it takes a view or a group name, the community will be treated as a v3 community. The v2c and v3 communities could exit in the community table concurrently. 
					 It will display unknown(name) when view/group name doesn't exist in view/group table."
		::= { iswSnmpCommunityEntry 4 } 

--5
	iswSnmpCommunityAccessMode		OBJECT-TYPE
		SYNTAX		Integer32  { ro (1), rw (2) }
		MAX-ACCESS	read-create
		STATUS		current
		DESCRIPTION	"Choice access right. Allow Get operation only, or allow both Get and Set."
		DEFVAL		{ 2 }
		::= { iswSnmpCommunityEntry 5 } 

--6
	iswSnmpCommunityStatus		OBJECT-TYPE
		SYNTAX		RowStatus
		MAX-ACCESS	read-create
		STATUS		current
		DESCRIPTION	"Row Status."
		::= { iswSnmpCommunityEntry 6 } 




--4
	iswSnmpVACMViewTable		OBJECT-TYPE
		SYNTAX		SEQUENCE OF IswSnmpVACMViewEntry
		MAX-ACCESS	not-accessible 
		STATUS		current
		DESCRIPTION	"Snmp VACM View table."  
		::= { iswSnmpVACMView 1 }

	iswSnmpVACMViewEntry		OBJECT-TYPE
		SYNTAX		IswSnmpVACMViewEntry
		MAX-ACCESS	not-accessible
		STATUS		current
		DESCRIPTION	"Snmp VACM View entry."
		INDEX		{ iswSnmpVACMViewIndex }  
		::= { iswSnmpVACMViewTable 1 }
	
	
	IswSnmpVACMViewEntry ::= SEQUENCE{
		iswSnmpVACMViewIndex		Integer32,
		iswSnmpVACMViewName			OCTET STRING,
		iswSnmpVACMViewType			Integer32,
		iswSnmpVACMViewSubtree		OCTET STRING,
		iswSnmpVACMViewRowstatus	RowStatus,
	}

--1
	iswSnmpVACMViewIndex		OBJECT-TYPE
		SYNTAX		Integer32 ( 1 .. 32 )
		MAX-ACCESS	not-accessible
		STATUS		current
		DESCRIPTION	"Snmp VACM View Index, value range is 1-32."
		::= { iswSnmpVACMViewEntry 1 } 

--2
	iswSnmpVACMViewName		OBJECT-TYPE
		SYNTAX		OCTET STRING ( SIZE( 1 .. 15 ) )
		MAX-ACCESS	read-create
		STATUS		current
		DESCRIPTION	"View name, length 1~15.
					 Accept any characters except space, quote mark and ?."
		::= { iswSnmpVACMViewEntry 2 } 

--3
	iswSnmpVACMViewType		OBJECT-TYPE
		SYNTAX		Integer32  { included (1), excluded (2) }
		MAX-ACCESS	read-create
		STATUS		current
		DESCRIPTION	"Accessible/Not accessible of object (SNMP OID).
					 Select down list box:
						1. Include, allow access the subtree/oid;
						2. Exclude, doesn't allow access the subtree/oid."
		DEFVAL		{ 1 }
		::= { iswSnmpVACMViewEntry 3 } 		
		
--4
	iswSnmpVACMViewSubtree		OBJECT-TYPE
		SYNTAX		OCTET STRING ( SIZE( 1 .. 31 ) )
		MAX-ACCESS	read-create
		STATUS		current
		DESCRIPTION	"SNMP OID or Object Name of MIB
					 Input format is OID, char length 1~31.
					 Accept MIB object name iswitch or wildcard (*)."
		::= { iswSnmpVACMViewEntry 4 } 		

--5		
	iswSnmpVACMViewRowstatus	OBJECT-TYPE
		SYNTAX		RowStatus
		MAX-ACCESS	read-create
		STATUS		current
		DESCRIPTION	"Row Status."
		::= { iswSnmpVACMViewEntry 5 }		
	
	
--SnmpVACMViewDeleteCtrl
--4

--1
	iswSnmpVACMViewDeleteCtrlIndex	OBJECT-TYPE
		SYNTAX		Integer32 ( 1 .. 32 )
		MAX-ACCESS	read-write
		STATUS		current
		DESCRIPTION	"Delete by index."
		::= { iswSnmpVACMViewDeleteCtrl 1 }

--2
	iswSnmpVACMViewDeleteCtrlName	OBJECT-TYPE
		SYNTAX		OCTET STRING ( SIZE( 1 .. 15 ) )
		MAX-ACCESS	read-write
		STATUS		current
		DESCRIPTION	"Delete by name."
		::= { iswSnmpVACMViewDeleteCtrl 2 }
		
--3
	iswSnmpVACMViewDeleteCtrlype	OBJECT-TYPE
		SYNTAX		Integer32 { deleteByIndex (0), deleteByName (1) }
		MAX-ACCESS	read-write
		STATUS		current
		DESCRIPTION	"Delete type."
		::= { iswSnmpVACMViewDeleteCtrl 3 }
	


--5
--snmpV3	

	iswSnmpV3Enabled		OBJECT-TYPE
		SYNTAX		Integer32 { disable (0), enable (1) }
		MAX-ACCESS	read-write
		STATUS		current
		DESCRIPTION	"This button is used to set whether snmp v3 is enable or not. 
					 If snmpV3 switch is set to disable, the system would use snmp v2c only. 
					 If snmpV3 switch is set to enable, the system would use snmp v3 setting. 
					 Changing this will restart SNMP automatically.
					 The snmp v3 parameters would be valid only if snmp v3 is enabled."   
		DEFVAL		{ 0 }
		::= { iswSnmpVersion 1 }	

--LACPport
	iswLACPPortTable				OBJECT-TYPE
		SYNTAX		SEQUENCE OF IswLACPPortEntry
		MAX-ACCESS	not-accessible 
		STATUS		current
		DESCRIPTION	"Lacp port table. Max entry size: port number."
		::= { iswLACPPort 1 }
	iswLACPPortEntry		OBJECT-TYPE
		SYNTAX		IswLACPPortEntry
		MAX-ACCESS	not-accessible
		STATUS		current
		DESCRIPTION	"LACP port entry."
		INDEX		{ iswLACPPortId }
		::= { iswLACPPortTable 1 }
	
	IswLACPPortEntry ::= SEQUENCE{
		iswLACPPortId				IswGbeIndex,
		iswLACPPortEnable			Integer32,
		iswLACPPortPrio				Integer32,
		iswLACPPortKey				Integer32,
		iswLACPPortAccessMode		Integer32,
		iswLACPPortPeriodicMode		Integer32,
	}
	
	iswLACPPortId		OBJECT-TYPE
		SYNTAX		IswGbeIndex
		MAX-ACCESS	not-accessible
		STATUS		current
		DESCRIPTION	"Bridge Port Index."
		::= { iswLACPPortEntry 1 }
	iswLACPPortEnable		OBJECT-TYPE
		SYNTAX		Integer32  { disable (0), enable (1) }
		MAX-ACCESS	read-write
		STATUS		current
		DESCRIPTION	"Enable/Disable Lacp on the interface port index."
		DEFVAL		{ 0 }
		::= { iswLACPPortEntry 2 }
	iswLACPPortPrio			OBJECT-TYPE
		SYNTAX		Integer32 (1 .. 65535)
		MAX-ACCESS	read-write
		STATUS		current
		DESCRIPTION	"The Priority of LACP port.
					 Range : 1 ~ 65535.
					 Default : 32768."
		DEFVAL		{ 32768 }
		::= { iswLACPPortEntry 3 }
	iswLACPPortKey			OBJECT-TYPE
		SYNTAX		Integer32 (1 .. 65535)
		MAX-ACCESS	read-write
		STATUS		current
		DESCRIPTION	"The Key of LACP port. It supports Auto and Specific mode.
					 When auto is setting, the key will be auto-generated according to link speed of physical port.
					 When specific is setting, user can configure the key value in the range of 1 to 65535."
		DEFVAL		{ 0 }
		::= { iswLACPPortEntry 4 }
	iswLACPPortAccessMode	OBJECT-TYPE
		SYNTAX		Integer32 { passive (1) , active (2) }
		MAX-ACCESS	read-write
		STATUS		current
		DESCRIPTION	"Access mode of the LACP port. It supports Active and Passive mode.
					 When Active is setting, this LACP port always generates LACP packet to do negotiation with partner .
					 When Passive is setting, this LACP port will do nothing until it receives LACP packet from the partner ."
		DEFVAL		{ 2 }
		::= { iswLACPPortEntry 5 }
	iswLACPPortPeriodicMode	OBJECT-TYPE
		SYNTAX		Integer32 { fast (1) , slow (2) }
		MAX-ACCESS	read-write
		STATUS		current
		DESCRIPTION	"Periodic mode of the LACP port. It supports fast and slow mode.
					 When fast is setting, the number of seconds between periodic transmissions is using Short Timeouts.
					 When slow is setting, the number of seconds between periodic transmissions is using Long Timeouts.
					 These two timeout values are specified in IEEE-Std 802.1AX??2008, as follows:
					 The Short Timeouts is 1 second.
					 The Long Timeouts is 30 seconds."
		DEFVAL		{ 1 }
		::= { iswLACPPortEntry 6 }
  
--LACPAggr

	iswLACPAggrTable				OBJECT-TYPE
		SYNTAX		SEQUENCE OF IswLACPAggrEntry
		MAX-ACCESS	not-accessible 
		STATUS		current
		DESCRIPTION	"Lacp aggregator table. Max entry size: port number."
		::= { iswLACPAggr 1 }
	iswLACPAggrEntry		OBJECT-TYPE
		SYNTAX		IswLACPAggrEntry
		MAX-ACCESS	not-accessible
		STATUS		current
		DESCRIPTION	"LACP aggregator entry."
		INDEX		{ iswLACPAggrId, iswLACPAggrActorPortId }
		::= { iswLACPAggrTable 1 }
	
	IswLACPAggrEntry ::= SEQUENCE{
		iswLACPAggrId					Integer32,
		iswLACPAggrActorPortId			IswGbeIndex,
		iswLACPAggrActorPortPrio		Integer32,
		iswLACPAggrActorPortAdminKey	Integer32,
		iswLACPAggrActorPortOperKey		Integer32,
		iswLACPAggrActorPortState		Integer32,
		iswLACPAggrPartnerSysId			OCTET STRING,
		iswLACPAggrPartnerSysPrio		Integer32,
		iswLACPAggrPartnerPortId		Integer32,
		iswLACPAggrPartnerPortPrio		Integer32,
		iswLACPAggrPartnerPortOperKey	Integer32,
		iswLACPAggrPartnerPortState		Integer32
	}
	
	iswLACPAggrId			OBJECT-TYPE
		SYNTAX		Integer32 ( 1 .. 28 )
		MAX-ACCESS	not-accessible
		STATUS		current
		DESCRIPTION	"LACP aggregator id."
		::= { iswLACPAggrEntry 1 }	
	
	iswLACPAggrActorPortId			OBJECT-TYPE
		SYNTAX		IswGbeIndex 
		MAX-ACCESS	not-accessible
		STATUS		current
		DESCRIPTION	"LACP aggregator port count which joined the aggregator."
		::= { iswLACPAggrEntry 2 }

	iswLACPAggrActorPortPrio			OBJECT-TYPE
		SYNTAX		Integer32 
		MAX-ACCESS	read-only
		STATUS		current
		DESCRIPTION	"The priority value assigned to the port, used to converge dynamic Key changes."
		::= { iswLACPAggrEntry 3 }

	iswLACPAggrActorPortAdminKey			OBJECT-TYPE
		SYNTAX		Integer32 ( 1..65535 )
		MAX-ACCESS	read-only
		STATUS		current
		DESCRIPTION	"The administrative value of Key assigned to this port by administrator or System policy.
					 When auto is setting on the port, the key will be generated depended on link speed of physical port.
					 When specific is setting on the port, user can configure the key value in the range of 1 to 65535."
		::= { iswLACPAggrEntry 4 }

	iswLACPAggrActorPortOperKey			OBJECT-TYPE
		SYNTAX		Integer32 
		MAX-ACCESS	read-only
		STATUS		current
		DESCRIPTION	"The operational value of Key assigned to this port by the Actor."
		::= { iswLACPAggrEntry 5 }

	iswLACPAggrActorPortState			OBJECT-TYPE
		SYNTAX		Integer32
		MAX-ACCESS	read-only
		STATUS		current
		DESCRIPTION	"The operational values of the Actor's state parameters. This consists of the following set of variables,
					 encoded as individual bits within a single octet, as follows:
					  1) LACP_Activity is encoded in bit 0.
						  Active LACP is encoded as a 1; Passive LACP is encoded as a 0.
					  2) LACP_Timeout is encoded in bit 1.
						 Short Timeout is encoded as a 1; Long Timeout is encoded as a 0.
					  3) Aggregation is encoded in bit 2.
						  If TRUE (encoded as a 1), this flag indicates that the System considers this link to be Aggregateable.
						 If FALSE(encoded as a 0), the link is considered to be Individual.
					  4) Synchronization is encoded in bit 3.
						  If TRUE (encoded as a 1), the System considers this link to be IN_SYNC.
						  If FALSE(encoded as a 0), then this link is currently OUT_OF_SYNC.
					  5) Collecting is encoded in bit 4.
						  TRUE (encoded as a 1) means collection of incoming frames on this link is definitely enabled.
						  Its value is otherwise FALSE (encoded as a 0).
					  6) Distributing is encoded in bit 5.
						  FALSE (encoded as a 0) means distribution of outgoing frames on this link is definitely disabled.
						  Its value is otherwise TRUE (encoded as a 1).
					  7) Defaulted is encoded in bit 6.
						  If TRUE (encoded as a 1), it is using Defaulted operational Partner information,
						  administratively configured for the Partner.
						  If FALSE (encoded as a 0), the operational Partner information in use has been received in a LACPDU.
					  8) Expired is encoded in bit 7.
						  If TRUE (encoded as a 1), it indicates that the Actor's Receive machine is in the EXPIRED state;
						  if FALSE (encoded as a 0), it indicates that the Actor's Receive machine is not in the EXPIRED state."
		::= { iswLACPAggrEntry 6 }

	iswLACPAggrPartnerSysId		OBJECT-TYPE
		SYNTAX		OCTET STRING ( SIZE (6) ) 
		MAX-ACCESS	read-only
		STATUS		current
		DESCRIPTION	"The operational value of the MAC address component of the System Identifier of the Partner."
		::= { iswLACPAggrEntry 7 }

	iswLACPAggrPartnerSysPrio		OBJECT-TYPE
		SYNTAX		Integer32 
		MAX-ACCESS	read-only
		STATUS		current
		DESCRIPTION	"The operational value of the System Priority of the Partner."
		::= { iswLACPAggrEntry 8 }

	iswLACPAggrPartnerPortId		OBJECT-TYPE
		SYNTAX		Integer32 
		MAX-ACCESS	read-only
		STATUS		current
		DESCRIPTION	"The operational value of the port number assigned to this link by the Partner."
		::= { iswLACPAggrEntry 9 }

	iswLACPAggrPartnerPortPrio		OBJECT-TYPE
		SYNTAX		Integer32 
		MAX-ACCESS	read-only
		STATUS		current
		DESCRIPTION	"The operational value of the priority value assigned to this link by the Partner,
					 used to converge dynamic Key changes."
		::= { iswLACPAggrEntry 10 }

	iswLACPAggrPartnerPortOperKey		OBJECT-TYPE
		SYNTAX		Integer32 
		MAX-ACCESS	read-only
		STATUS		current
		DESCRIPTION	"The operational value of the Key value assigned to this link by the Partner."
		::= { iswLACPAggrEntry 11 }

	iswLACPAggrPartnerPortState		OBJECT-TYPE
		SYNTAX		Integer32 
		MAX-ACCESS	read-only
		STATUS		current
		DESCRIPTION	"The operational value of the Actor's view of the current values of the Partner's state parameters.
					 The value consists of the following set of variables, as described in Actor Oper Key."
		::= { iswLACPAggrEntry 12 }


 
--
	iswPRGSysMode					OBJECT-TYPE
		SYNTAX		Integer32 { disable (0), enable (1) }
		MAX-ACCESS	read-write
		STATUS		current
		DESCRIPTION	"Enable / Disable System Port Redundant Mode.Default value is disable (0)."
		DEFVAL		{ 0 }
		::= { iswPRGSystem 1 }
--PRG Port
	iswPRGPortTable				OBJECT-TYPE
		SYNTAX		SEQUENCE OF IswPRGPortEntry
		MAX-ACCESS	not-accessible 
		STATUS		current
		DESCRIPTION	"PRG port table. Max entry size: port number."
		::= { iswPRGPort 1 }
	iswPRGPortEntry				OBJECT-TYPE
		SYNTAX		IswPRGPortEntry
		MAX-ACCESS	not-accessible
		STATUS		current
		DESCRIPTION	"PRG port entry."
		INDEX		{ iswPRGPortId }
		::= { iswPRGPortTable 1 }
	
	IswPRGPortEntry ::= SEQUENCE{
		iswPRGPortId				IswGbeIndex,
		iswPRGPortGroupId			Integer32,
	}
	iswPRGPortId				OBJECT-TYPE
		SYNTAX		IswGbeIndex
		MAX-ACCESS	not-accessible
		STATUS		current
		DESCRIPTION	"Bridge Port Index."
		::= { iswPRGPortEntry 1 }
	iswPRGPortGroupId			OBJECT-TYPE
		SYNTAX		Integer32 ( 1 .. 12) 
		MAX-ACCESS	read-write
		STATUS		current
		DESCRIPTION	"Join group index by port.Range :  0 , Group 1 ~ 12.
					 Default value is 0 , means not belong to any group.
					 At least 2 ports within a Redundant-Group, max 24 ports in a group."
		DEFVAL		{ 0 }
		::= { iswPRGPortEntry 2 }
--PRGGroup
	iswPRGGroupTable			OBJECT-TYPE
		SYNTAX		SEQUENCE OF IswPRGGroupEntry
		MAX-ACCESS	not-accessible 
		STATUS		current
		DESCRIPTION	"PRG Group table. Max entry size: port group index."
		::= { iswPRGGroup 1 }
	iswPRGGroupEntry			OBJECT-TYPE
		SYNTAX		IswPRGGroupEntry
		MAX-ACCESS	not-accessible
		STATUS		current
		DESCRIPTION	"PRG group entry."
		INDEX		{ iswPRGGroupId }
		::= { iswPRGGroupTable 1 }
	IswPRGGroupEntry ::= SEQUENCE{
		iswPRGGroupId				Integer32,
		iswPRGGroupMembers			OCTET STRING,
		iswPRGGroupFwdMembers		OCTET STRING,
		iswPRGGroupBlkMembers		OCTET STRING,
	}
	iswPRGGroupId				OBJECT-TYPE
		SYNTAX		Integer32 ( 1 .. 12)
		MAX-ACCESS	not-accessible
		STATUS		current
		DESCRIPTION	"Redundant group index. Range : Group1~12."
		::= { iswPRGGroupEntry 1 }
	iswPRGGroupMembers			OBJECT-TYPE
		SYNTAX		OCTET STRING  ( SIZE ( 4 ) )
		MAX-ACCESS	read-only
		STATUS		current
		DESCRIPTION	"The member of ports to join group index.
				     bit0 is not used.
					 bit1 is meaning GEPort-1,
					 bit2 is meaning GEPort-2,
					 bit3 is meaning GEPort-3,  
					 ...
					 bit27 is meaning GEPort-27,
					 bit28 is meaning GEPort-28
					 other bits are not used.."
		::= { iswPRGGroupEntry 2 }
	iswPRGGroupFwdMembers		OBJECT-TYPE
		SYNTAX		OCTET STRING  ( SIZE ( 4 ) )
		MAX-ACCESS	read-only
		STATUS		current
		DESCRIPTION	"When system port redundant mode disable,group members belong to forwarding member.
					 The forwarding port in join group index.
					 bit0 is not used.
					 bit1 is meaning GEPort-1,
					 bit2 is meaning GEPort-2,
					 bit3 is meaning GEPort-3,  
					 ...
					 bit27 is meaning GEPort-27,
					 bit28 is meaning GEPort-28
					 other bits are not used."
		::= { iswPRGGroupEntry 3 }
	iswPRGGroupBlkMembers		OBJECT-TYPE
		SYNTAX		OCTET STRING  ( SIZE ( 4 ) )
		MAX-ACCESS	read-only
		STATUS		current
		DESCRIPTION	"When system port redundant mode enable,group members belong to blocked member.
					 The blocking ports in join group index.
					 bit0 is not used.
					 bit1 is meaning GEPort-1,
					 bit2 is meaning GEPort-2,
					 bit3 is meaning GEPort-3,  
					 ...
					 bit27 is meaning GEPort-27,
					 bit28 is meaning GEPort-28
					 other bits are not used."
		::= { iswPRGGroupEntry 4 }
--
	iswGVRPEnable					OBJECT-TYPE
		SYNTAX		Integer32 { disable (0), enable (1) }
		MAX-ACCESS	read-write
		STATUS		current
		DESCRIPTION	"Enable/Disable GVRP on the system."
		DEFVAL		{ 0 }
		::= { iswGVRPConf 1 }
	iswGVRPLeaveAllTime				OBJECT-TYPE
		SYNTAX		Integer32 (10 .. 10000)
		UNITS		"cent-second"
		MAX-ACCESS	read-write
		STATUS		current
		DESCRIPTION	"Set GVRP leave-all-time in range of 10 to 10000(unit:cent-second).Default value : 1000."
		DEFVAL		{ 1000 }
		::= { iswGVRPConf 2 }
--
--GVRP Port
	iswGVRPPortTable			OBJECT-TYPE
		SYNTAX		SEQUENCE OF IswGVRPPortEntry
		MAX-ACCESS	not-accessible 
		STATUS		current
		DESCRIPTION	"GVRP port table. Max entry size: port number."
		::= { iswGVRPPortConf 1 }
	iswGVRPPortEntry			OBJECT-TYPE
		SYNTAX		IswGVRPPortEntry
		MAX-ACCESS	not-accessible
		STATUS		current
		DESCRIPTION	"GVRP port entry."
		INDEX		{ iswGVRPPortId }
		::= { iswGVRPPortTable 1 }
	IswGVRPPortEntry  ::= SEQUENCE{
		iswGVRPPortId				IswGbeIndex,
		iswGVRPPortEnable			Integer32,
		iswGVRPPortJoinTime			Integer32,
		iswGVRPPortLeaveTime		Integer32,
	}
	iswGVRPPortId				OBJECT-TYPE
		SYNTAX		IswGbeIndex
		MAX-ACCESS	not-accessible
		STATUS		current
		DESCRIPTION	"GVRP port id."
		::= { iswGVRPPortEntry 1 }
	iswGVRPPortEnable			OBJECT-TYPE
		SYNTAX		Integer32  { disable (0), enable (1) }
		MAX-ACCESS	read-write
		STATUS		current
		DESCRIPTION	"Enable/Disable GVRP on the port."
		DEFVAL		{ 0 }
		::= { iswGVRPPortEntry 2 }
	iswGVRPPortJoinTime			OBJECT-TYPE
		SYNTAX		Integer32 (10 .. 10000)
		UNITS		"cent-second"
		MAX-ACCESS	read-write
		STATUS		current
		DESCRIPTION	"The time which apply to per interface's join timer.
					 Range : 10 ~ 10000 (cent-second); default is 20."
		DEFVAL		{20}
		::= { iswGVRPPortEntry 3 }
	iswGVRPPortLeaveTime		OBJECT-TYPE
		SYNTAX		Integer32 (10 .. 10000)
		UNITS		"cent-second"
		MAX-ACCESS	read-write
		STATUS		current
		DESCRIPTION	"The time which apply to per interface's leave timer.
					 Range : 10 ~ 10000 (cent-second); default is 60."
		DEFVAL		{ 60 }
		::= { iswGVRPPortEntry 4 }
--
	iswIPSGPortTable			OBJECT-TYPE
		SYNTAX		SEQUENCE OF IswIPSGPortEntry
		MAX-ACCESS	not-accessible 
		STATUS		current
		DESCRIPTION	"IPSG port table. Max entry size: port number."
		::= { iswIPSGPort 1 }
	iswIPSGPortEntry			OBJECT-TYPE
		SYNTAX		IswIPSGPortEntry
		MAX-ACCESS	not-accessible
		STATUS		current
		DESCRIPTION	"IPSG port entry."
		INDEX		{ iswIPSGPortId }
		::= { iswIPSGPortTable 1 }
	IswIPSGPortEntry  ::= SEQUENCE{
		iswIPSGPortId				IswGbeIndex,
		iswIPSGPortEnable			Integer32,
		iswIPSGPortLimit			Integer32,
	}
	iswIPSGPortId				OBJECT-TYPE
		SYNTAX		IswGbeIndex
		MAX-ACCESS	not-accessible
		STATUS		current
		DESCRIPTION	"Bridge Port Index."
		::= { iswIPSGPortEntry 1 }
	iswIPSGPortEnable			OBJECT-TYPE
		SYNTAX		Integer32  { disable (0), enable (1) }
		MAX-ACCESS	read-write
		STATUS		current
		DESCRIPTION	"Enable/Disable IP Source Guard of port. Default value : disable (0)."
		DEFVAL		{ 0 }
		::= { iswIPSGPortEntry 2 }
	iswIPSGPortLimit			OBJECT-TYPE
		SYNTAX		Integer32  (0 .. 5 | 150)
		MAX-ACCESS	read-write
		STATUS		current
		DESCRIPTION	"Maximum dynamic binding source on the port. The value is 0 ~ 5 or 150 (unlimited) ."
		DEFVAL		{ 150 }
		::= { iswIPSGPortEntry 3 }
	iswIPSGStaticBindingTable			OBJECT-TYPE
		SYNTAX		SEQUENCE OF IswIPSGStaticBindingEntry
		MAX-ACCESS	not-accessible 
		STATUS		current
		DESCRIPTION	"IPSG StaticBinding table. Max entry size: Port number."
		::= { iswIPSGStaticBinding 1 }
	iswIPSGStaticBindingEntry			OBJECT-TYPE
		SYNTAX		IswIPSGStaticBindingEntry
		MAX-ACCESS	not-accessible
		STATUS		current
		DESCRIPTION	"IPSG StaticBinding entry."
		INDEX		{ iswIPSGStaticBindingIdx }
		::= { iswIPSGStaticBindingTable 1 }
	IswIPSGStaticBindingEntry  ::= SEQUENCE{
		iswIPSGStaticBindingIdx			IswGbeIndex,
		iswIPSGStaticBindingPortId		IswGbeIndex,
		iswIPSGStaticBindingVlan		Integer32,
		iswIPSGStaticBindingSourceIp		IpAddress,
		iswIPSGStaticBindingSourceMac		PhysAddress,
		iswIPSGStaticBindingRowStatus		RowStatus,
	}
	iswIPSGStaticBindingIdx				OBJECT-TYPE
		SYNTAX		IswGbeIndex
		MAX-ACCESS	not-accessible
		STATUS		current
		DESCRIPTION	"Bridge Port Index."
		::= { iswIPSGStaticBindingEntry 1 }
	iswIPSGStaticBindingPortId			OBJECT-TYPE
		SYNTAX		IswGbeIndex
		MAX-ACCESS	read-create
		STATUS		current
		DESCRIPTION	"The identity for the Port.
					 Range 1 ~ max port."
		::= { iswIPSGStaticBindingEntry 2 }
	iswIPSGStaticBindingVlan			OBJECT-TYPE
		SYNTAX		Integer32 ( 1 .. 4094 )
		MAX-ACCESS	read-create
		STATUS		current
		DESCRIPTION	"The identity for the VLAN Interface.
					 Range 1~4094."
		::= { iswIPSGStaticBindingEntry 3 }
	iswIPSGStaticBindingSourceIp		OBJECT-TYPE
		SYNTAX		IpAddress 
		MAX-ACCESS	read-create
		STATUS		current
		DESCRIPTION	"IP address for the VLAN interface.
					 Range 0~255.
					 Default value is 0."
		::= { iswIPSGStaticBindingEntry 4 }
	iswIPSGStaticBindingSourceMac		OBJECT-TYPE
		SYNTAX		PhysAddress
		MAX-ACCESS	read-create
		STATUS		current
		DESCRIPTION	"MAC address for the VLAN interface."
		::= { iswIPSGStaticBindingEntry 5 }
	iswIPSGStaticBindingRowStatus		OBJECT-TYPE
		SYNTAX		RowStatus	
		MAX-ACCESS	read-create
		STATUS		current
		DESCRIPTION	"Row Status."
		::= { iswIPSGStaticBindingEntry 6 }
--
	iswIPSGBindingTable			OBJECT-TYPE
		SYNTAX		SEQUENCE OF IswIPSGBindingEntry
		MAX-ACCESS	not-accessible 
		STATUS		current
		DESCRIPTION	"IPSG Binding table. Max entry size: Port number."
		::= { iswIPSGBinding 1 }
	iswIPSGBindingEntry			OBJECT-TYPE
		SYNTAX		IswIPSGBindingEntry
		MAX-ACCESS	not-accessible
		STATUS		current
		DESCRIPTION	"IPSG Binding entry."
		INDEX		{ iswIPSGBindingIdx }
		::= { iswIPSGBindingTable 1 }
	IswIPSGBindingEntry  ::= SEQUENCE{
		iswIPSGBindingIdx			Integer32,
		iswIPSGBindingPortId			IswGbeIndex,
		iswIPSGBindingVlan			Integer32,
		iswIPSGBindingSourceIp			IpAddress,
		iswIPSGBindingSourceMac			PhysAddress,
		iswIPSGBindingStateMode			Integer32,
	}
	iswIPSGBindingIdx				OBJECT-TYPE
		SYNTAX		Integer32 ( 1 .. 150 )
		MAX-ACCESS	not-accessible
		STATUS		current
		DESCRIPTION	"Index."
		::= { iswIPSGBindingEntry 1 }
	iswIPSGBindingPortId			OBJECT-TYPE
		SYNTAX		IswGbeIndex
		MAX-ACCESS	read-only
		STATUS		current
		DESCRIPTION	"Bridge Port Index."
		::= { iswIPSGBindingEntry 2 }
	iswIPSGBindingVlan			OBJECT-TYPE
		SYNTAX		Integer32 ( 1 .. 4094 )
		MAX-ACCESS	read-only
		STATUS		current
		DESCRIPTION	"Vlan Id."
		::= { iswIPSGBindingEntry 3 }
	iswIPSGBindingSourceIp		OBJECT-TYPE
		SYNTAX		IpAddress 
		MAX-ACCESS	read-only
		STATUS		current
		DESCRIPTION	"Ipv4 address."
		::= { iswIPSGBindingEntry 4 }
	iswIPSGBindingSourceMac		OBJECT-TYPE
		SYNTAX		PhysAddress
		MAX-ACCESS	read-only
		STATUS		current
		DESCRIPTION	"HW address."
		::= { iswIPSGBindingEntry 5 }
	iswIPSGBindingStateMode				OBJECT-TYPE
		SYNTAX		Integer32	{ dhcpSnooping ( 0 ) , static ( 1 ) }
		MAX-ACCESS	read-only
		STATUS		current
		DESCRIPTION	"binding source state."
		::= { iswIPSGBindingEntry 6 }

--IPSG Delete Control
	iswIPSGBindingDeleteCtrlVlan			OBJECT-TYPE
		SYNTAX		Integer32 (1 .. 4094)
		MAX-ACCESS	read-write
		STATUS		current
		DESCRIPTION	"Delete by Vlan Id."
		::= { iswIPSGBindingDeleteCtrl 1 }
	iswIPSGBindingDeleteCtrlPort			OBJECT-TYPE
		SYNTAX		IswGbeIndex
		MAX-ACCESS	read-write
		STATUS		current
		DESCRIPTION	"Delete by Port number."
		::= { iswIPSGBindingDeleteCtrl 2 }
	iswIPSGBindingDeleteCtrlType		OBJECT-TYPE
		SYNTAX		Integer32 { deleteByVlan(0) , deleteByPort (1) , deleteByAll(2) }
		MAX-ACCESS	read-write
		STATUS		current
		DESCRIPTION	"Delete type. "
		::= { iswIPSGBindingDeleteCtrl 3 }
--McConf
	iswMcConfMode			OBJECT-TYPE
		SYNTAX		Integer32  { disable (0), enable (1) }
		MAX-ACCESS	read-write
		STATUS		current
		DESCRIPTION	"Enable/Disable IP multicast routing. Default value : disable (0)."
		DEFVAL		{ 0 }
		::= { iswMcConf 1 }
--McIfConf
	iswMcIfConfTable			OBJECT-TYPE
		SYNTAX		SEQUENCE OF IswMcIfConfEntry
		MAX-ACCESS	not-accessible 
		STATUS		current
		DESCRIPTION	"Multicast Interface Configuration table. Max entry size: Vlan ID."
		::= { iswMcIfConf 1 }
	iswMcIfConfEntry			OBJECT-TYPE
		SYNTAX		IswMcIfConfEntry
		MAX-ACCESS	not-accessible
		STATUS		current
		DESCRIPTION	"IPSG Binding entry."
		INDEX		{ iswMcIfVlanID }
		::= { iswMcIfConfTable 1 }
	IswMcIfConfEntry	  ::= SEQUENCE{
		iswMcIfVlanID					Integer32,
		iswMcIfMode					Integer32,
		iswMcIfRowStatus				RowStatus,
	}	
	iswMcIfVlanID				OBJECT-TYPE
		SYNTAX		Integer32 ( 1 .. 4094 )
		MAX-ACCESS	not-accessible
		STATUS		current
		DESCRIPTION	"mcIfVlanId is the identity for the McIfConf."
		::= { iswMcIfConfEntry 1 }
	iswMcIfMode					OBJECT-TYPE
		SYNTAX		Integer32  { enable (1) }
		MAX-ACCESS	read-create
		STATUS		current
		DESCRIPTION	"Enable interface multicast mode."
		DEFVAL		{ 1 }
		::= { iswMcIfConfEntry 2 }
	iswMcIfRowStatus			OBJECT-TYPE
		SYNTAX		RowStatus	
		MAX-ACCESS	read-create
		STATUS		current
		DESCRIPTION	"Row Status."
		::= { iswMcIfConfEntry 3 }
--McRoute
	iswMcRouteTable			OBJECT-TYPE
		SYNTAX		SEQUENCE OF IswMcRouteEntry
		MAX-ACCESS	not-accessible 
		STATUS		current
		DESCRIPTION	"IP Multicast Route table. Max entry size: Index number."
		::= { iswMcRoute 1 }
	iswMcRouteEntry			OBJECT-TYPE
		SYNTAX		IswMcRouteEntry
		MAX-ACCESS	not-accessible
		STATUS		current
		DESCRIPTION	"IPSG Binding entry."
		INDEX		{ iswMcRouteIndex }
		::= { iswMcRouteTable 1 }
	IswMcRouteEntry  ::= SEQUENCE{
		iswMcRouteIndex					Integer32,
		iswMcRouteSourceIP				IpAddress,
		iswMcRouteNetmask				IpAddress,
		iswMcRouteRpfIP					IpAddress,
--		iswMcRouteMetric				Integer32,
		iswMcRouteRowStatus				RowStatus,
	}	
	iswMcRouteIndex			OBJECT-TYPE
		SYNTAX		Integer32 ( 1 .. 32 )
		MAX-ACCESS	not-accessible
		STATUS		current
		DESCRIPTION	"IP multicast route index."
		::= { iswMcRouteEntry 1 }
	iswMcRouteSourceIP		OBJECT-TYPE
		SYNTAX		IpAddress 
		MAX-ACCESS	read-create
		STATUS		current
		DESCRIPTION	"Multicast route source address."
		::= { iswMcRouteEntry 2 }
	iswMcRouteNetmask		OBJECT-TYPE
		SYNTAX		IpAddress 
		MAX-ACCESS	read-create
		STATUS		current
		DESCRIPTION	"Multicast route source netmask."
		::= { iswMcRouteEntry 3 }
	iswMcRouteRpfIP			OBJECT-TYPE
		SYNTAX		IpAddress 
		MAX-ACCESS	read-create
		STATUS		current
		DESCRIPTION	"Multicast route RPF address."
		::= { iswMcRouteEntry 4 }
--	iswMcRouteMetric		OBJECT-TYPE
	--	SYNTAX		Integer32 ( 1 .. 32 )
	--	MAX-ACCESS	read-create
	--	STATUS		current
	--	DESCRIPTION	"Multicast route metric."
	--	DEFVAL		{ 1 }
	--	::= { iswMcRouteEntry 5 }
	iswMcRouteRowStatus		OBJECT-TYPE
		SYNTAX		RowStatus	
		MAX-ACCESS	read-create
		STATUS		current
		DESCRIPTION	"Row Status."
		::= { iswMcRouteEntry 5 }
	
--NRoute
	iswMRouteTable	OBJECT-TYPE
		SYNTAX		SEQUENCE OF IswMRouteEntry
		MAX-ACCESS	not-accessible
		STATUS		current
		DESCRIPTION	"User stats table. Max entry size: 10."
		::= { iswMRoute 1 }

	iswMRouteEntry	OBJECT-TYPE
		SYNTAX		IswMRouteEntry
		MAX-ACCESS	not-accessible
		STATUS		current
		DESCRIPTION	"User stats entry."
		INDEX		{ iswMRouteIndex }
		::= { iswMRouteTable 1 }
		
	IswMRouteEntry ::= SEQUENCE{
		iswMRouteIndex			Integer32,
		iswMRouteSourceIp		IpAddress,
		iswMRouteGroupIp		IpAddress,
		iswMRouteUptime			TimeTicks,
		iswMRouteDelExpire		TimeTicks,
		iswMRouteFlag			OCTET STRING,
		iswMRoutePort			IswGbeIndex,
		iswMRouteVlan			Integer32,
		iswMRouteRpfNeighbor	IpAddress,
		iswMRouteRecvUptime		TimeTicks,
		iswMRouteRecvExpire		TimeTicks,
		iswMRouteOutgoing		OCTET STRING
	}
	iswMRouteIndex				OBJECT-TYPE
		SYNTAX		Integer32 
		MAX-ACCESS	not-accessible
		STATUS		current
		DESCRIPTION	"MRoute Table Index."
		::= { iswMRouteEntry 1 }
	iswMRouteSourceIp			OBJECT-TYPE
		SYNTAX		IpAddress 
		MAX-ACCESS	read-only
		STATUS		current
		DESCRIPTION	"Source IP address of the stream."
		::= { iswMRouteEntry 2 }
	iswMRouteGroupIp			OBJECT-TYPE
		SYNTAX		IpAddress 
		MAX-ACCESS	read-only
		STATUS		current
		DESCRIPTION	"Group IP address of the stream."
		::= { iswMRouteEntry 3 }
	iswMRouteUptime				OBJECT-TYPE
		SYNTAX		TimeTicks 
		MAX-ACCESS	read-only
		STATUS		current
		DESCRIPTION	"Uptime timer for this multicast routing rule."
		::= { iswMRouteEntry 4 }
	iswMRouteDelExpire			OBJECT-TYPE
		SYNTAX		TimeTicks
		MAX-ACCESS	read-only
		STATUS		current
		DESCRIPTION	"Expire timer for this multicast routing rule."
		::= { iswMRouteEntry 5 }
	iswMRouteFlag				OBJECT-TYPE
		SYNTAX		OCTET STRING  ( SIZE ( 1 ) )
		MAX-ACCESS	read-only
		STATUS		current
		DESCRIPTION	"Multicast route state flags:
					 bit 0 : D , bit 1 : S,
					 bit 2 : P,  bit 3 : V.
					 D - Dense, S - Static, P - Pruned, V - Dvmrp"
		::= { iswMRouteEntry 6 }
	iswMRoutePort				OBJECT-TYPE
		SYNTAX		IswGbeIndex 
		MAX-ACCESS	read-only
		STATUS		current
		DESCRIPTION	"Including Interface Port number."
		::= { iswMRouteEntry 7 }
	iswMRouteVlan				OBJECT-TYPE
		SYNTAX		Integer32 
		MAX-ACCESS	read-only
		STATUS		current
		DESCRIPTION	"Including Interface Id."
		::= { iswMRouteEntry 8 }
	iswMRouteRpfNeighbor		OBJECT-TYPE
		SYNTAX		IpAddress 
		MAX-ACCESS	read-only
		STATUS		current
		DESCRIPTION	"RPF neighbor IP."
		::= { iswMRouteEntry 9 }
	iswMRouteRecvUptime			OBJECT-TYPE
		SYNTAX		TimeTicks 
		MAX-ACCESS	read-only
		STATUS		current
		DESCRIPTION	"Uptime for received stream."
		::= { iswMRouteEntry 10 }
	iswMRouteRecvExpire			OBJECT-TYPE
		SYNTAX		TimeTicks 
		MAX-ACCESS	read-only
		STATUS		current
		DESCRIPTION	"Expire for received stream."
		::= { iswMRouteEntry 11 }
	iswMRouteOutgoing			OBJECT-TYPE
		SYNTAX		OCTET STRING 
		MAX-ACCESS	read-only
		STATUS		current
		DESCRIPTION	"Outgoing Interface List description.
					 Including Interface Id, State/Mode."
		::= { iswMRouteEntry 12 }

--
	iswUserStatsTable	OBJECT-TYPE
		SYNTAX		SEQUENCE OF IswUserStatsEntry
		MAX-ACCESS	not-accessible
		STATUS		current
		DESCRIPTION	"User stats table. Max entry size: 10."
		::= { iswSysMgt 3 }

	iswUserStatsEntry	OBJECT-TYPE
		SYNTAX		IswUserStatsEntry
		MAX-ACCESS	not-accessible
		STATUS		current
		DESCRIPTION	"User stats entry."
		INDEX		{ iswUserStatsIndex }
		::= { iswUserStatsTable 1 }
		
	IswUserStatsEntry ::= SEQUENCE{
		iswUserStatsIndex			Integer32,
		iswUserStatsLoginType		Integer32,
		--iswUserStatsCookieID		Integer32,
		--iswUserStatsIdleSeconds	Integer32,
		iswUserStatsIp				IpAddress,
		iswUserStatsUserName		OCTET STRING
		--iswUserStatsMethod		Integer32,
		--iswUserStatsInfo			OCTET STRING,
		--iswUserStatsExtraInfo		OCTET STRING,
	}

--1 
	iswUserStatsIndex	OBJECT-TYPE
		SYNTAX		Integer32 ( 1 .. 10 )
		MAX-ACCESS	not-accessible
		STATUS		current
		DESCRIPTION	"User stats index."
		::= { iswUserStatsEntry 1 }
--2     
	iswUserStatsLoginType	OBJECT-TYPE
		SYNTAX		Integer32 { cli (0), web (1), console (2) }
		MAX-ACCESS	read-only
		STATUS		current
		DESCRIPTION	"User stats login type."
		::= { iswUserStatsEntry 2 }
--3       
	--iswUserStatsCookieID	OBJECT-TYPE
	--	SYNTAX		Integer32
	--	MAX-ACCESS	read-only
	--	STATUS		current
	--	DESCRIPTION	"User stats cookie ID."
	--	::= { iswUserStatsEntry 3 }
--4        
	--iswUserStatsIdleSeconds	OBJECT-TYPE
	--	SYNTAX		Integer32
	--	MAX-ACCESS	read-only
	--	STATUS		current
	--	DESCRIPTION	"User stats idle seconds."
	--	::= { iswUserStatsEntry 4 }
--5      
	iswUserStatsIp	OBJECT-TYPE
		SYNTAX		IpAddress
		MAX-ACCESS	read-only
		STATUS		current
		DESCRIPTION	"User stats IP."
		::= { iswUserStatsEntry 3 }
--6    
	iswUserStatsUserName	OBJECT-TYPE
		SYNTAX		OCTET STRING 
		MAX-ACCESS	read-only
		STATUS		current
		DESCRIPTION	"User stats user name."
		::= { iswUserStatsEntry 4 }
--7
	--iswUserStatsMethod	OBJECT-TYPE
	--	SYNTAX		Integer32
	--	MAX-ACCESS	read-only
	--	STATUS		current
	--	DESCRIPTION	"User stats method."
	--	::= { iswUserStatsEntry 5 }
--8   
	--iswUserStatsInfo	OBJECT-TYPE
	--	SYNTAX		OCTET STRING
	--	MAX-ACCESS	read-only
	--	STATUS		current
	--	DESCRIPTION	"User stats info."
	--	::= { iswUserStatsEntry 5 }
--9
	--iswUserStatsExtraInfo	OBJECT-TYPE
	--	SYNTAX		OCTET STRING
	--	MAX-ACCESS	read-only
	--	STATUS		current
	--	DESCRIPTION	"User stats extra info."
	--	::= { iswUserStatsEntry 6 }
--User
	iswUserTable	OBJECT-TYPE
		SYNTAX		SEQUENCE OF IswUserEntry
		MAX-ACCESS	not-accessible
		STATUS		current
		DESCRIPTION	"User table. Max entry size: 3."
		::= { iswUser 1 }

	iswUserEntry	OBJECT-TYPE
		SYNTAX		IswUserEntry
		MAX-ACCESS	not-accessible
		STATUS		current
		DESCRIPTION	"User entry."
		INDEX		{ iswUserIndex }
		::= { iswUserTable 1 }
		
	IswUserEntry ::= SEQUENCE{
		iswUserIndex			Integer32,
		iswUserName				OCTET STRING,
		iswUserPassword			OCTET STRING,
		iswUserAccessLevel		Integer32,
		iswUserComment			OCTET STRING,
		iswUserRowstatus		RowStatus,
	}
	iswUserIndex				OBJECT-TYPE
		SYNTAX		Integer32 ( 1 .. 32 )
		MAX-ACCESS	not-accessible
		STATUS		current
		DESCRIPTION	"User index."
		::= { iswUserEntry 1 }
	iswUserName					OBJECT-TYPE
		SYNTAX		OCTET STRING 
		MAX-ACCESS	read-create
		STATUS		current
		DESCRIPTION	"User name (Range : 1 to 31 characters).
					 Only for create,can't not set."
		::= { iswUserEntry 2 }
	iswUserPassword				OBJECT-TYPE
		SYNTAX		OCTET STRING 
		MAX-ACCESS	read-write
		STATUS		current
		DESCRIPTION	"User Password (Range : 0 to 31 characters)."
		::= { iswUserEntry 3 }
	iswUserAccessLevel			OBJECT-TYPE
		SYNTAX		Integer32 { superUser(1),engineer(2),guest(3) }
		MAX-ACCESS	read-write
		STATUS		current
		DESCRIPTION	"access level of the user :
					 Super User - The user can access to all functions.
					 Engineer - The user can access to all functions except user account management.
					 Guest - The user can access to basic display functions."
		::= { iswUserEntry 4 }
	iswUserComment				OBJECT-TYPE
		SYNTAX		OCTET STRING 
		MAX-ACCESS	read-write
		STATUS		current
		DESCRIPTION	"Description of the user account (Range : 0 to 31 characters)."
		::= { iswUserEntry 5 }
	iswUserRowstatus			OBJECT-TYPE
		SYNTAX		RowStatus	
		MAX-ACCESS	read-create
		STATUS		current
		DESCRIPTION	"Row Status."
		::= { iswUserEntry 6 }
--LedStatus
	iswLedStateP1				OBJECT-TYPE
		SYNTAX		Integer32 { off(0) , on(1)}
		MAX-ACCESS	read-only
		STATUS		current
		DESCRIPTION	"The power1 indicator LED state."
		::= { iswLedState 1 }
	iswLedStateP2				OBJECT-TYPE
		SYNTAX		Integer32 { off(0) , on(1)}
		MAX-ACCESS	read-only
		STATUS		current
		DESCRIPTION	"The power2 indicator LED state."
		::= { iswLedState 2 }
	iswLedStateRR				OBJECT-TYPE
		SYNTAX		Integer32 { off(0) , on(1)}
		MAX-ACCESS	read-only
		STATUS		current
		DESCRIPTION	"The RR indicator LED state."
		::= { iswLedState 3 }
	iswLedStateRS				OBJECT-TYPE
		SYNTAX		Integer32 { off(0) , on(1)}
		MAX-ACCESS	read-only
		STATUS		current
		DESCRIPTION	"The RS indicator LED state."
		::= { iswLedState 4 }
	iswLedStateAlarm			OBJECT-TYPE
		SYNTAX		Integer32 { off(0) , on(1)}
		MAX-ACCESS	read-only
		STATUS		current
		DESCRIPTION	"The Alarm indicator LED state."
		::= { iswLedState 5 }
	iswLedStatePortTable	OBJECT-TYPE
		SYNTAX		SEQUENCE OF IswLedStatePortEntry
		MAX-ACCESS	not-accessible
		STATUS		current
		DESCRIPTION	"LedStatePort table. Max entry size: Port Index."
		::= { iswLedState 6 }
	iswLedStatePortEntry	OBJECT-TYPE
		SYNTAX		IswLedStatePortEntry
		MAX-ACCESS	not-accessible
		STATUS		current
		DESCRIPTION	"LedStatePort entry."
		INDEX		{ iswLedStatePortIndex }
		::= { iswLedStatePortTable 1 }
		
	IswLedStatePortEntry ::= SEQUENCE{
		iswLedStatePortIndex	IswGbeIndex,
		iswLedStatePortEnable	Integer32,
	}
	iswLedStatePortIndex	OBJECT-TYPE
		SYNTAX		IswGbeIndex
		MAX-ACCESS	not-accessible
		STATUS		current
		DESCRIPTION	"LedStatePort index."
		::= { iswLedStatePortEntry 1 }
	iswLedStatePortEnable	OBJECT-TYPE
		SYNTAX		Integer32	{ off(0) , on(1)}
		MAX-ACCESS	read-only
		STATUS		current
		DESCRIPTION	"The port indicator LED state."
		::= { iswLedStatePortEntry 2 }
--

--NtpServer
	iswNtpServerMode		OBJECT-TYPE
		SYNTAX		Integer32 { disable (0), enable (1) }
		MAX-ACCESS	read-write
		STATUS		current
		DESCRIPTION	"Enable/Disable NTP Server.
					 Value range is Disabled/Enabled, default value is Disabled."
		DEFVAL		{ 0 }
		::= { iswNtpServer 1 }
		
--NtpClient
	iswNtpClientPollingInterval		OBJECT-TYPE
		SYNTAX		Unsigned32 ( 0 | 60.. 65535 )
		UNITS		"second"
		MAX-ACCESS	read-write
		STATUS		current
		DESCRIPTION	"Sets polling interval (seconds) that NTP client will sync with designated NTP server.
					 Range is 60 ~ 65535, 0 is disable."
		DEFVAL		{ 0 }
		::= { iswNtpClient 1 }

	iswNtpClientServerIp1		OBJECT-TYPE
		SYNTAX		IpAddress
		MAX-ACCESS	read-write
		STATUS		current
		DESCRIPTION	"Sets NTP server IP address #1 for your system."
		::= { iswNtpClient 2 }

	iswNtpClientServerIp2		OBJECT-TYPE
		SYNTAX		IpAddress
		MAX-ACCESS	read-write
		STATUS		current
		DESCRIPTION	"Sets NTP server IP address #2 for your system."
		::= { iswNtpClient 3 }

	iswNtpClientServerIp3		OBJECT-TYPE
		SYNTAX		IpAddress
		MAX-ACCESS	read-write
		STATUS		current
		DESCRIPTION	"Sets NTP server IP address #3 for your system."
		::= { iswNtpClient 4 }

	iswNtpClientServerIp4		OBJECT-TYPE
		SYNTAX		IpAddress
		MAX-ACCESS	read-write
		STATUS		current
		DESCRIPTION	"Sets NTP server IP address #4 for your system."
		::= { iswNtpClient 5 }

	iswNtpClientServerIp5		OBJECT-TYPE
		SYNTAX		IpAddress
		MAX-ACCESS	read-write
		STATUS		current
		DESCRIPTION	"Sets NTP server IP address #5 for your system."
		::= { iswNtpClient 6 }

	iswNtpClientSync		OBJECT-TYPE
		SYNTAX		Integer32  { idle (0), sync (1) }
		MAX-ACCESS	read-write
		STATUS		current
		DESCRIPTION	"Get always return idle (0), set sync (1) to trigger NTP client time synchronization."
		::= { iswNtpClient 7 }
--AlmSystemUsage
	iswCPULoading		OBJECT-TYPE
		SYNTAX		Integer32( 0 .. 100 )
		MAX-ACCESS	read-only
		STATUS		current
		DESCRIPTION	"Show current CPU loading in unit of one percentage."
		-- DEFVAL		{ 0 }
		::= { iswAlmSystemUsage 1 }

	iswCPULoadingThreshold 		OBJECT-TYPE
		SYNTAX		Integer32( 50 .. 90 )
		MAX-ACCESS	read-write
		STATUS		current
		DESCRIPTION	"One threshold percenatage to trigger high CPU loading alert."
		DEFVAL		{ 75 }		
		::= { iswAlmSystemUsage 2 }
	iswMemoryLoading		OBJECT-TYPE
		SYNTAX		Integer32( 0 .. 100 )
		MAX-ACCESS	read-only
		STATUS		current
		DESCRIPTION	"Show current memory loading in unit of one percentage."
		-- DEFVAL		{ 0 }
		::= { iswAlmSystemUsage 3 }

	iswMemoryLoadingThreshold 		OBJECT-TYPE
		SYNTAX		Integer32( 50 .. 90 )
		MAX-ACCESS	read-write
		STATUS		current
		DESCRIPTION	"One threshold percenatage to trigger high memory loading alert."
		DEFVAL		{ 50 }
		::= { iswAlmSystemUsage 4 }		
--
--Bandwidth
	iswBandwidthHighestInRate		OBJECT-TYPE
		SYNTAX		Integer32( 0 .. 100 )
		MAX-ACCESS	read-only
		STATUS		current
		DESCRIPTION	"Show the port that has higest Rx traffic loading now."
		::= { iswBandwidth 1 }
		
	iswBandwidthHighestERate		OBJECT-TYPE
		SYNTAX		Integer32( 0 .. 100 )
		MAX-ACCESS	read-only
		STATUS		current
		DESCRIPTION	"Show the port that has higest Tx traffic loading now."
		::= { iswBandwidth 2 }
		
	iswBandwidthInThreshold		OBJECT-TYPE
		SYNTAX		Integer32( 50 .. 90 )
		MAX-ACCESS	read-write
		STATUS		current
		DESCRIPTION	"One threshold percentage to trigger high RX traffic loading alert.
					 The range is 50~90 percentage. Default value is 50."
		DEFVAL		{ 50 }
		::= { iswBandwidth 3 }
		
	iswBandwidthInShfTime		OBJECT-TYPE
		SYNTAX		Integer32( 10 .. 255 )
		MAX-ACCESS	read-write
		STATUS		current
		DESCRIPTION	"A time gap between starting of detecting high RX traffic loading to continuous duration time.
					 It support the range of 10 to 255, in unit of one second. The default is 10."
		DEFVAL		{ 10 }
		::= { iswBandwidth 4 }
		
	iswBandwidthEThreshold		OBJECT-TYPE
		SYNTAX		Integer32( 50 .. 90 )
		MAX-ACCESS	read-write
		STATUS		current
		DESCRIPTION	"One threshold percentage to trigger high TX traffic loading alert.
					 The range is 50~90 percentage. Default value is 50."
		DEFVAL		{ 50 }
		::= { iswBandwidth 5 }

	iswBandwidthEShfTime		OBJECT-TYPE
		SYNTAX		Integer32( 10 .. 255 )
		MAX-ACCESS	read-write
		STATUS		current
		DESCRIPTION	"A time gap between starting of detecting high TX traffic loading to continuous duration time.
					 It support the range of 10 to 255, in unit of one second. The default is 10."
		DEFVAL		{ 10 }
		::= { iswBandwidth 6 }
--
	iswBandwidthUsageTable		OBJECT-TYPE
		SYNTAX			SEQUENCE OF IswBandwidthUsageEntry
		MAX-ACCESS		not-accessible
		STATUS			current
		DESCRIPTION		"Bandwidth Usage table."
		::= { iswBandwidth 7 }
	
	iswBandwidthUsageEntry OBJECT-TYPE
		SYNTAX		IswBandwidthUsageEntry
		MAX-ACCESS  not-accessible
		STATUS      current
		DESCRIPTION "Bandwidth Usage entry."
		INDEX       { iswBandwidthRateIndex }
		::= { iswBandwidthUsageTable 1 }

	IswBandwidthUsageEntry ::= SEQUENCE {
		iswBandwidthRateIndex		IswGbeIndex,
		iswBandwidthInRate			Integer32,
		iswBandwidthERate			Integer32
	}
	
	iswBandwidthRateIndex OBJECT-TYPE
		SYNTAX		IswGbeIndex
		MAX-ACCESS  not-accessible
		STATUS      current
		DESCRIPTION "The value will return to 1 when the index over record size."
		::= { iswBandwidthUsageEntry 1 }
	
	iswBandwidthInRate OBJECT-TYPE
		SYNTAX      Integer32 ( 0 .. 100)
		MAX-ACCESS  read-only
		STATUS      current
		DESCRIPTION	"Ingress rate for Bandwidth.
					 The rate is 0~100 percentage. Default is 0."
		-- DEFVAL		{ 0 }
		::= { iswBandwidthUsageEntry 2 }
		
	iswBandwidthERate OBJECT-TYPE
		SYNTAX      Integer32 ( 0 .. 100)
		MAX-ACCESS  read-only
		STATUS      current
		DESCRIPTION	"Egress rate for Bandwidth.
					 The rate is 0~100 percentage. Default is 0."
		-- DEFVAL		{ 0 }
		::= { iswBandwidthUsageEntry 3 }
		
	iswFlashUtil OBJECT-TYPE
		SYNTAX      Integer32
		MAX-ACCESS  read-only
		STATUS      current
		DESCRIPTION
		"Flash Utilization, 0-100 %"
		::= { iswFlashInfo 1 }

	iswFlashSize OBJECT-TYPE
		SYNTAX      Integer32
		MAX-ACCESS  read-only
		STATUS      current
		DESCRIPTION
		"Flash Size"
		::= { iswFlashInfo 2 }

	iswFlashType OBJECT-TYPE
		SYNTAX      Integer32 {  n25Q256(1), w25Q01(2) }
		MAX-ACCESS  read-only
		STATUS      current
		DESCRIPTION
		"Flash Type"
		::= { iswFlashInfo 3 }

--1
	iswCLITimeout		OBJECT-TYPE
		SYNTAX		Integer32 ( 0 | 60.. 65535 )
		UNITS		"second"
		MAX-ACCESS	read-write
		STATUS		current
		DESCRIPTION	"CLI settings timeout. Range is 60 ~ 65535, 0 is no timeout."
		DEFVAL		{ 600 }
		::= { iswCLISettings 1 }

--2		
	iswCLIMaxSessions	OBJECT-TYPE
		SYNTAX		Integer32 ( 1 .. 10 )
		MAX-ACCESS	read-write
		STATUS		current
		DESCRIPTION	"CLI settings max sessions."
		::= { iswCLISettings 2 }
--
--1
	iswSntpPollingInterval 	OBJECT-TYPE
		SYNTAX		Integer32 ( 0 | 60.. 65535 )
		UNITS		"second"
		MAX-ACCESS	read-write
		STATUS		current
		DESCRIPTION	"Sntp polling interval. Default value is 0 which meaning sntp polling is disabled. 
					If sntp polling enabled, the range should between 60 to 65535."  
		DEFVAL		{ 0 }
		::= { iswSntp 1 }
--2
	iswSntpTimeZone 			OBJECT-TYPE
		SYNTAX		Integer32 { idl (0), idlw (1), nt (2), ahst (3), bdt (4), cat (5), yst (6), hdt (7), pst (8), ydt (9), mst (10), pdt(11),
						cst (12), mdt (13), est (14), cdt (15), ast( 16), edt (17), nft (18), adt (19), bra (20), gwst (21), at (22),
						wat (23), gmt (24), wet (25), ut (26), utc (27), cet (28), bst (29), met (30), mewt (31), swt (32), fwt (33),
						eet (34), mest (35), fst (36), egst (37), egdt (38), bt (39), it (40), zp4 (41), zp5 (42), ist (43), zp6 (44),
						nst (45), sst (46), wast (47), jt (48), cct (49), hst (50), wadt (51), wst (52), jst (53), kst (54), cast (55),
						sast (56), jdt (57), gst (58), east (59), cadt (60), sadt (61), eadt (62), nzt (63), nzst (64), idle (65),
						nzdt (66) }
		MAX-ACCESS	read-write
		STATUS		current
		DESCRIPTION	"sntp timezone.
					List:
					0   IDL  -12:00  International Date Line
					1  IDLW  -12:00  International Date Line West
					2    NT  -11:00  Nome Time
					3  AHST  -10:00  Alaska-Hawaii Standard Time
					4   BDT  -10:00  BDT
					5   CAT  -10:00  Central Alaska Time
					6   YST  -09:00  Yukon Standard Time
					7   HDT  -09:00  HDT
					8   PST  -08:00  Pacific Standard Time
					9   YDT  -08:00  YDT
					10  MST  -07:00  Mountain Standard Time
					11  PDT  -07:00  Pacific Daylight Time
					12  CST  -06:00  Central Standard Time
					13  MDT  -06:00  Mountain Daylight Time
					14  EST  -05:00  Eastern Standard Time
					15  CDT  -05:00  Central Daylight Time
					16  AST  -04:00  Atlantic Standard Time
					17  EDT  -04:00  Eastern Daylight Time
					18  NFT  -03:30  Newfoundland Standard Time
					19  ADT  -03:00  Atlantic Daylight Time
					20  BRA  -03:00  Brazil Standard Time
					21 GWST  -03:00  Greenland Western Standard Time
					22   AT  -02:00  Azores Time
					23  WAT  -01:00  West Africa Time
					24  GMT  +00:00  Greenwich Mean Time
					25  WET  +00:00  Western European Time
					26   UT  +00:00  Universal Time
					27  UTC  +00:00  Universal Time
					28  CET  +01:00  Central European Time
					29  BST  +01:00  British Summer Time
					30  MET  +01:00  Middle European Time
					31 MEWT  +01:00  Middle European Winter Time
					32  SWT  +01:00  Swedish Winter Time
					33  FWT  +01:00  French Winter Time
					34  EET  +02:00  Eastern European Time
					35 MEST  +02:00  Middle European Summer Time
					36  FST  +02:00  French Summer Time
					37 EGST  +02:00  Egypt Standard Time
					38 EGDT  +03:00  Egypt Daylight Time
					39   BT  +03:00  Baghdad Time
					40   IT  +03:30  Iran Time
					41  ZP4  +04:00  GMT Plus 4 Hours
					42  ZP5  +05:00  GMT Plus 5 Hours
					43  IST  +05:30  Indian Standard Time
					44  ZP6  +06:00  GMT Plus 6 Hours
					45  NST  +06:30  North Sumatra Time
					46  SST  +07:00  South Sumatra Time
					47 WAST  +07:00  West Australian Standard Time
					48   JT  +07:30  Java Time
					49  CCT  +08:00  China Coast Time
					50  HST  +08:00  Hong Kong Standard Time
					51 WADT  +08:00  West Australian Daylight Time
					52  WST  +08:00  WST
					53  JST  +09:00  Japan Standard Time
					54  KST  +09:00  Korean Standard Time
					55 CAST  +09:30  Central Australian Standard Time
					56 SAST  +09:30  South Australian Standard Time
					57  JDT  +10:00  JDT
					58  GST  +10:00  Guam Standard Time
					59 EAST  +10:00  East Australian Standard Time
					60 CADT  +10:30  Central Australian Daylight Time
					61 SADT  +10:30  South Australian Daylight Time
					62 EADT  +11:00  East Australian Daylight Time
					63  NZT  +12:00  New Zealand Time
					64 NZST  +12:00  New Zealand Standard Time
					65 IDLE  +12:00  International Date Line East
					66 NZDT  +13:00  New Zealand Daylight Time
					"
		::= { iswSntp 2 }
--3
	iswSntpServerIp 	OBJECT-TYPE
		SYNTAX		IpAddress
		MAX-ACCESS	read-write
		STATUS		current
		DESCRIPTION	"Sntp server IP."
		::= { iswSntp 3 }
--4
	iswSntpSync 		OBJECT-TYPE
		SYNTAX		Integer32 {  idle(0), sync(1) }
		MAX-ACCESS	read-write
		STATUS		current
		DESCRIPTION	"Sync Date Time with SNTP. Return 0 when get this object. Set sync(1) to trigger SNTP Sync."
		::= { iswSntp 4 }
--
--1
	iswSysDate 		OBJECT-TYPE
		SYNTAX		OCTET STRING ( SIZE ( 10 ) )
		MAX-ACCESS	read-write
		STATUS		current
		DESCRIPTION	"System date. Format: MM/DD/YYYY. Fix length. The YYYY range is 2000~2036."
		::= { iswSysDateTime 1 }
--2
	iswSysTime 		OBJECT-TYPE
		SYNTAX		OCTET STRING ( SIZE ( 8 ) )
		MAX-ACCESS	read-write
		STATUS		current
		DESCRIPTION	"System time. Format: HH:MM:SS. Fix length."
		::= { iswSysDateTime 2 }
--
--1
	iswSyslogIpAddr 	OBJECT-TYPE
		SYNTAX		IpAddress
		MAX-ACCESS	read-write
		STATUS		current
		DESCRIPTION	"Syslog IP address."
		::= { iswSyslog 1 }
--
--1
	iswSyslogdAction	OBJECT-TYPE
		SYNTAX		Integer32 { disable (0), enable (1) }
		MAX-ACCESS	read-write
		STATUS		current
		DESCRIPTION	"Service syslogd action. Default value is disable (0).
					If set enable when syslog already enabled, syslog will be restart." 
		DEFVAL		{ 0 }
		::= { iswSyslog 2 }
		--
	iswSyslogAdditionalServerTable OBJECT-TYPE
		SYNTAX      SEQUENCE OF IswSyslogAdditionalServerEntry
		MAX-ACCESS  not-accessible
		STATUS      current
		DESCRIPTION "Table of additional syslog servers."
		::= { iswSyslog 3 }

	iswSyslogAdditionalServerEntry OBJECT-TYPE
		SYNTAX      IswSyslogAdditionalServerEntry
		MAX-ACCESS  not-accessible
		STATUS      current
		DESCRIPTION "Entry in the additional syslog server table."
		INDEX       { iswSyslogAdditionalServeIdx }
		::= { iswSyslogAdditionalServerTable 1 }

	IswSyslogAdditionalServerEntry ::= SEQUENCE {
		iswSyslogAdditionalServeIdx             Integer32,
		iswSyslogAdditionalServerIpAddr         IpAddress,
		iswSyslogAdditionalServerStatusBitmap   Integer32
	}

	iswSyslogAdditionalServeIdx OBJECT-TYPE
		SYNTAX      Integer32 (2..8)
		MAX-ACCESS  not-accessible
		STATUS      current
		DESCRIPTION "Index for the additional syslog server entry. (start index is 2.)"
		::= { iswSyslogAdditionalServerEntry 1 }

	iswSyslogAdditionalServerIpAddr OBJECT-TYPE
		SYNTAX      IpAddress
		MAX-ACCESS  read-write
		STATUS      current
		DESCRIPTION "IP address of the additional syslog server."
		::= { iswSyslogAdditionalServerEntry 2 }

	iswSyslogAdditionalServerStatusBitmap OBJECT-TYPE
		SYNTAX      Integer32
		MAX-ACCESS  read-write
		STATUS      current
		DESCRIPTION	"Status bitmap of the additional syslog server. Starting from the least significant bit (rightmost), 
					(This mask is shared no matter which index is set.)
					e.g. 
						4  (Dec) = 0x04(Hex)  =  b'0000 0100' indicates that additional server  2 is off. 
						12 (Dec) = 0x0C(Hex)  =  b'0000 1100' indicates that additional server  2, 3 are off.
						60 (Dec) = 0x3C(Hex)  =  b'0011 1100' indicates that additional server  2, 3, 4 and 5  are off.
						508(Dec) = 0x1FC(Hex) =  b'0001 1111 1100' indicates that additional server 2 ~ 8 are off. (same as 0xFFFFFFFF)"
		::= { iswSyslogAdditionalServerEntry 3 }
--1  
	iswSystemUnitLedStatus	OBJECT-TYPE
		SYNTAX		Integer32 { off (0), green (2)}
		MAX-ACCESS	read-only
		STATUS		current
		DESCRIPTION	"System unit led status."
		::= { iswSysLedStatus 1 }
--2	 
	iswSystemAlmLedStatus	OBJECT-TYPE
		SYNTAX		Integer32 { off (0), red (1)}
		MAX-ACCESS	read-only
		STATUS		current
		DESCRIPTION	"System alarm led status."
		::= { iswSysLedStatus 2 }
--
--1
	iswInvSnmpAgentVer	OBJECT-TYPE
		SYNTAX		OCTET STRING (SIZE(1..16))
		MAX-ACCESS	read-only
		STATUS		current
		DESCRIPTION	"This object value presents that current NE by implementation
					is compliant to which version the SNMP	Agent belongs to."
		::= {iswInventory 1}

	iswInvSwVersion	OBJECT-TYPE
		SYNTAX		OCTET STRING ( SIZE ( 0 .. 47 ) )
		MAX-ACCESS	read-only
		STATUS		current
		DESCRIPTION	"Inventory SW version."
		::= { iswInventory 2 }
 
	--iswInvInbandDbVersion	OBJECT-TYPE
	--	SYNTAX		OCTET STRING ( SIZE ( 0 .. 31 ) )
	--	MAX-ACCESS	read-only
	--	STATUS		current
	--	DESCRIPTION	"Inventory inband database version."
	--	::= { iswInventory 3 }
  
	--iswInvGenenalDbVersion	OBJECT-TYPE
	--	SYNTAX		OCTET STRING ( SIZE ( 0 .. 31 ) )
	--	MAX-ACCESS	read-only
	--	STATUS		current
	--	DESCRIPTION	"Inventory general database version."
	--	::= { iswInventory 4 }

	iswBootLoaderInfoVersion	OBJECT-TYPE
		SYNTAX		OCTET STRING 
		MAX-ACCESS	read-only
		STATUS		current
		DESCRIPTION	"Inventory boot loader information version."
		::= { iswInventory 5 } 

	iswSysMacAddr				OBJECT-TYPE
		SYNTAX		PhysAddress 
		MAX-ACCESS	read-only
		STATUS		current
		DESCRIPTION	"System mac address."
		::= { iswInventory 6 }

--
	iswHttpPort		OBJECT-TYPE
		SYNTAX		Integer32 (1..65535)
		MAX-ACCESS	read-write
		STATUS		current
		DESCRIPTION	"Http Port.
					http port number and https port number can't be the same.
					"
		DEFVAL		{80}
		::= {iswHttp 1}

	iswHttpsPort		OBJECT-TYPE
		SYNTAX		Integer32 (1..65535)
		MAX-ACCESS	read-write
		STATUS		current
		DESCRIPTION	"Https Port.
					http port number and https port number can't be the same.
					"
		DEFVAL          {443}
		::= { iswHttp 2 }

	iswHttpServiceOption	OBJECT-TYPE
		SYNTAX		Integer32 { http(0), https(1) }
		MAX-ACCESS	read-write
		STATUS		current
		DESCRIPTION	"Http Service Option.
					Default is http"
		DEFVAL 		{0}
		::= { iswHttp 3 }
--
	iswSdpProductModel OBJECT-TYPE
		SYNTAX      OCTET STRING ( SIZE ( 0 .. 25 ) )
		MAX-ACCESS  read-only
		STATUS      current
		DESCRIPTION
		"Product Model name."
		::= { iswSdp 1 }

	iswSdpSwVersion OBJECT-TYPE
		SYNTAX      OCTET STRING ( SIZE ( 0 .. 20 ) )
		MAX-ACCESS  read-only
		STATUS      current
		DESCRIPTION
		"System SW version"
		::= { iswSdp 2 }

	iswSdpSwBuild OBJECT-TYPE
		SYNTAX      OCTET STRING ( SIZE ( 0 .. 30 ) )
		MAX-ACCESS  read-only
		STATUS      current
		DESCRIPTION
		"System SW version built date"
		::= { iswSdp 3 }

	iswSdpPhyMac OBJECT-TYPE
		SYNTAX      PhysAddress
		MAX-ACCESS  read-only
		STATUS      current
		DESCRIPTION
		"Phy Mac address"
		::= { iswSdp 4 }

	iswSdpPortCount OBJECT-TYPE
		SYNTAX      Integer32
		MAX-ACCESS  read-only
		STATUS      current
		DESCRIPTION
		"Port Count"
		::= { iswSdp 5 }

	iswSdpManagedFlag OBJECT-TYPE
		SYNTAX      INTEGER  { un-managed(0), managed(1)  } 
		MAX-ACCESS  read-write
		STATUS      current
		DESCRIPTION
		"If it is (1)managed, then alarm LED should be in blink status.
		If it is (0)un-managed, then alarm LED is normal. Default is (0)un-managed."
		DEFVAL { 0 }
		::= { iswSdp 6 }

--
--1
	iswSysRestart	OBJECT-TYPE
		SYNTAX		Integer32 { restart (1) }
		MAX-ACCESS	read-write
		STATUS		current
		DESCRIPTION	"System restart. Always return 0 when read."
		::= { iswMtnMgt 1 }

--2
	iswSysSaveConfig	OBJECT-TYPE
		SYNTAX		Integer32 {
						idle(0),
						config-save(1),
						config-restore-by-index(2),
						config-restore-by-index-restart(3),
						config-clear-all(4),
						config-clear-all-restart(5),
						config-clear-general(6),
						config-clear-general-restart(7),
						export-cliconfig(8),
--						export-cliconfig-binary(9),
						import-cliconfig(10),
						import-cliconfig-restart(11),
--						import-cliconfig-binary(12),
--						import-cliconfig-binary-restart(13),
						config-save-replace-index(14),     
						export-cliconfig-tftp(15),
						import-cliconfig-tftp(16),
						import-cliconfig-restart-tftp(17),
						
						ftpPutSuccess(101),
						ftpPutFail(102),
						ftpPutInProgress(103),
						ftpGetSuccess(104),
						ftpGetFail(105),
						ftpGetInProgress(106),
						memoryWriteSuccess(107),
						memoryWriteFail(108),
						memoryWriteInprogress(109),
						memoryReadSuccess(110),
						memoryReadFail(111),
						memoryReadInprogress(112),
						tftpPutSuccess(113),
						tftpPutFail(114),
						tftpPutInProgress(115),
						tftpGetSuccess(116),
						tftpGetFail(117),
						tftpGetInProgress(118)
						}
		MAX-ACCESS	read-write
		STATUS		current
		DESCRIPTION	"This object used to show and trigger DB save and restore action.
					Save inband configuration and runtime configuration as active database (configuration for next boot.)
					If status is inprogress, then cannot allow set/write.
					
					Notes:
						(1) config-restore-by-index(2),config-restore-by-index-restart(3),config-save-replace-index(14)
								Above 3 options need to set iswSysSaveConfigInbandIdx and iswSysSaveConfigGenIdx first.
						(2) config-save(1),config-save-replace-index(14)
								Above 2 options need to set iswSysSaveConfigInbandName and iswSysSaveConfigGenName first.
								If do not set iswSysSaveConfigInbandName and iswSysSaveConfigGenName first (these two names are empty), 
								system will set these two name automatically snd format is 01/05/2013 05:45:57.
						(3) If the option ends with restart, then system will be restart immediately.
						(4) The Import or Export options need to set FTP configuration.
								iswFTPServerIp
								iswFTPUserName
								iswFTPUserPassword
								iswFTPFileName
							"
		::= { iswMtnMgt 2 }

	iswSysSaveConfigInbandIdx	OBJECT-TYPE
		SYNTAX		Integer32 ( 1 .. 16 )
		MAX-ACCESS	read-write
		STATUS		current
		DESCRIPTION	"Inband DB index for CLI config action.
					Set iswSysSaveConfig as config-restore-by-index(2), system load the specific inband cfg as runningcfg.
					Set iswSysSaveConfig as config-restore-by-index-restart(3), system will restart with specific inband DB.
					Set iswSysSaveConfig as config-save-replace-index(14), system save current runningcfg to specific inband DB.
					"
		::= { iswMtnMgt 3 }

	iswSysSaveConfigGenIdx	OBJECT-TYPE
		SYNTAX		Integer32 ( 1 .. 16 )
		MAX-ACCESS	read-write
		STATUS		current
		DESCRIPTION	"Genral DB index for CLI config action.
					Set iswSysSaveConfig as config-restore-by-index(2), system load the specific general cfg as running cfg.
					Set iswSysSaveConfig as config-restore-by-index-restart(3), system will restart with specific general DB.
					Set iswSysSaveConfig as config-save-replace-index(14), system save current runningcfg to specific general DB.
					"
		::= { iswMtnMgt 4 }
		
	iswSysSaveConfigInbandName	OBJECT-TYPE
		SYNTAX			OCTET STRING (SIZE ( 0 ..31 ))
		MAX-ACCESS		read-write
		STATUS			current
		DESCRIPTION		"
		Specify naming of database that stores the inband IP configuration.
		Set this object before further action you will choose on iswSysSaveConfig.
		iswSysSaveConfig: config-save(1)/config-save-replace-index(14).
		"
		::= { iswMtnMgt 9 }

	iswSysSaveConfigGenName	OBJECT-TYPE    
		SYNTAX			OCTET STRING (SIZE ( 0 ..31 ))
		MAX-ACCESS		read-write
		STATUS			current
		DESCRIPTION		"
		Specify naming of database that stores the runtime configuration.
		Set this object before further action you will choose on iswSysSaveConfig.
		iswSysSaveConfig: config-save(1)/config-save-replace-index(14).
		"
		::= { iswMtnMgt 10 }


	iswCurrentCpuTemperature	OBJECT-TYPE
		SYNTAX			Integer32
		MAX-ACCESS		read-only
		STATUS			current
		DESCRIPTION		"Current cpu temperature."
		::= { iswSysTemperature 1 }

	iswUpShiftThreshold		OBJECT-TYPE
		SYNTAX			Integer32 ( -55 .. 85 )
		MAX-ACCESS		read-write
		STATUS			current
		DESCRIPTION		"Temperature threshold of system high temperature alarm."
		::= { iswSysTemperature 2 }

	iswUpShiftTime			OBJECT-TYPE
		SYNTAX			Integer32 ( 1 .. 255 )
		MAX-ACCESS		read-write
		STATUS			current
		DESCRIPTION		"This threshold is a time interval used to judge alarm is on/set.
					If system current temperature exceeds the 'Up Shift Threshold' and remain for time of 'Up Shift Time', alarm is consider as set and system will generate a system high temperature alarm. "
		::= { iswSysTemperature 3 }

	iswDownShiftThreshold		OBJECT-TYPE
		SYNTAX			Integer32 ( -55 .. 85 )
		MAX-ACCESS		read-write
		STATUS			current
		DESCRIPTION		"Temperature threshold of system low temperature alarm."
		::= { iswSysTemperature 4 }

	iswDownShiftTime		OBJECT-TYPE
		SYNTAX			Integer32 ( 1 .. 255 )
		MAX-ACCESS		read-write
		STATUS			current
		DESCRIPTION		"This threshold is a time interval used to judge alarm is off/cleared.
					If system current temperature lower than the 'Down Shift Threshold' and remain for time of 'Down Shift Time', alarm is consider as cleared and system will clear low temperature alarm."
		::= { iswSysTemperature 5 }

--
-- DDM

	iswDDMconfig		OBJECT-TYPE
		SYNTAX			INTEGER { disable(0), enable(1) }
		MAX-ACCESS		read-write
		STATUS			current
		DESCRIPTION		"To set DDM enable or disable, get DDM status. "
		::= { iswDDM 1 }
 
	iswDDMITable		OBJECT-TYPE
		SYNTAX			SEQUENCE OF IswDDMIEntry
		MAX-ACCESS		not-accessible
		STATUS			current
		DESCRIPTION		"To get DDM Information of SFP modules."
		::= { iswDDM 2 }
	
	iswDDMIEntry OBJECT-TYPE
		SYNTAX		IswDDMIEntry
		MAX-ACCESS  not-accessible
		STATUS      current
		DESCRIPTION 
			"Each entry has a set of DDMI status."
		INDEX       { iswDDMIPortIndex }
		::= { iswDDMITable 1 }

	IswDDMIEntry ::= SEQUENCE {
		iswDDMIPortIndex						IswGbeIndex,
		iswDDMISfpDetected						TruthValue,
		iswDDMIA0Vendor							OCTET STRING,
		iswDDMIA0PartNumber						OCTET STRING,
		iswDDMIA0SerialNumber					OCTET STRING,
		iswDDMIA0Revision						OCTET STRING,
		iswDDMIA0DateCode						OCTET STRING,
		iswDDMIA0Transceiver					OCTET STRING,
		iswDDMIA2CurrentTemperature				OCTET STRING,
		iswDDMIA2TemperatureHighAlarmThreshold	OCTET STRING,
		iswDDMIA2TemperatureLowAlarmThreshold   OCTET STRING,
		iswDDMIA2TemperatureHighWarnThreshold   OCTET STRING,
		iswDDMIA2TemperatureLowWarnThreshold    OCTET STRING,
		iswDDMIA2CurrentVoltage					OCTET STRING,
		iswDDMIA2VoltageHighAlarmThreshold      OCTET STRING,
		iswDDMIA2VoltageLowAlarmThreshold		OCTET STRING,
		iswDDMIA2VoltageHighWarnThreshold		OCTET STRING,
		iswDDMIA2VoltageLowWarnThreshold		OCTET STRING,
		iswDDMIA2CurrentTxBias					OCTET STRING,
		iswDDMIA2TxBiasHighAlarmThreshold		OCTET STRING,
		iswDDMIA2TxBiasLowAlarmThreshold		OCTET STRING,
		iswDDMIA2TxBiasHighWarnThreshold		OCTET STRING,
		iswDDMIA2TxBiasLowWarnThreshold			OCTET STRING,
		iswDDMIA2CurrentTxPower					OCTET STRING,
		iswDDMIA2TxPowerHighAlarmThreshold		OCTET STRING,
		iswDDMIA2TxPowerLowAlarmThreshold		OCTET STRING,
		iswDDMIA2TxPowerHighWarnThreshold		OCTET STRING,
		iswDDMIA2TxPowerLowWarnThreshold		OCTET STRING,
		iswDDMIA2CurrentRxPower					OCTET STRING,
		iswDDMIA2RxPowerHighAlarmThreshold      OCTET STRING,
		iswDDMIA2RxPowerLowAlarmThreshold		OCTET STRING,
		iswDDMIA2RxPowerHighWarnThreshold		OCTET STRING,
		iswDDMIA2RxPowerLowWarnThreshold		OCTET STRING
	}
	
	iswDDMIPortIndex OBJECT-TYPE
		SYNTAX		IswGbeIndex
		MAX-ACCESS  not-accessible
		STATUS      current
		DESCRIPTION 
			"DDMI port index."
		::= { iswDDMIEntry 1 }
	
	iswDDMISfpDetected OBJECT-TYPE
		SYNTAX      TruthValue
		MAX-ACCESS  read-only
		STATUS      current
		DESCRIPTION 
			"SFP module is detected or not. true is to detected and false is not
			 detected."
		::= { iswDDMIEntry 2 }

	iswDDMIA0Vendor OBJECT-TYPE
		SYNTAX      OCTET STRING
		MAX-ACCESS  read-only
		STATUS      current
		DESCRIPTION 
			"Vendor name."
		::= { iswDDMIEntry 3 }

	iswDDMIA0PartNumber OBJECT-TYPE
		SYNTAX      OCTET STRING
		MAX-ACCESS  read-only
		STATUS      current
		DESCRIPTION 
			"Part number."
		::= { iswDDMIEntry 4 }

	iswDDMIA0SerialNumber OBJECT-TYPE
		SYNTAX      OCTET STRING
		MAX-ACCESS  read-only
		STATUS      current
		DESCRIPTION 
			"Serial number."
		::= { iswDDMIEntry 5 }

	iswDDMIA0Revision OBJECT-TYPE
		SYNTAX      OCTET STRING
		MAX-ACCESS  read-only
		STATUS      current
		DESCRIPTION 
			"Revision."
		::= { iswDDMIEntry 6 }

	iswDDMIA0DateCode OBJECT-TYPE
		SYNTAX      OCTET STRING
		MAX-ACCESS  read-only
		STATUS      current
		DESCRIPTION 
			"Date Code."
		::= { iswDDMIEntry 7 }

	iswDDMIA0Transceiver OBJECT-TYPE
		SYNTAX      OCTET STRING
		MAX-ACCESS  read-only
		STATUS      current
		DESCRIPTION 
			"SFP type."
		::= { iswDDMIEntry 8 }

	iswDDMIA2CurrentTemperature OBJECT-TYPE
		SYNTAX      OCTET STRING
		MAX-ACCESS  read-only
		STATUS      current
		DESCRIPTION 
			"Current temperature in Celcius."
		::= { iswDDMIEntry 9 }

	iswDDMIA2TemperatureHighAlarmThreshold OBJECT-TYPE
		SYNTAX      OCTET STRING
		MAX-ACCESS  read-only
		STATUS      current
		DESCRIPTION 
			"Temperature high alarm threshold in Celcius."
		::= { iswDDMIEntry 10 }

	iswDDMIA2TemperatureLowAlarmThreshold OBJECT-TYPE
		SYNTAX      OCTET STRING
		MAX-ACCESS  read-only
		STATUS      current
		DESCRIPTION 
			"Temperature low alarm threshold in Celcius."
		::= { iswDDMIEntry 11 }

	iswDDMIA2TemperatureHighWarnThreshold OBJECT-TYPE
		SYNTAX      OCTET STRING
		MAX-ACCESS  read-only
		STATUS      current
		DESCRIPTION 
			"Temperature high warning threshold in Celcius."
		::= { iswDDMIEntry 12 }

	iswDDMIA2TemperatureLowWarnThreshold OBJECT-TYPE
		SYNTAX      OCTET STRING
		MAX-ACCESS  read-only
		STATUS      current
		DESCRIPTION 
			"Temperature low warning threshold in Celcius."
		::= { iswDDMIEntry 13 }

	iswDDMIA2CurrentVoltage OBJECT-TYPE
		SYNTAX      OCTET STRING
		MAX-ACCESS  read-only
		STATUS      current
		DESCRIPTION 
			"Current voltage in Volt."
		::= { iswDDMIEntry 14 }

	iswDDMIA2VoltageHighAlarmThreshold OBJECT-TYPE
		SYNTAX      OCTET STRING
		MAX-ACCESS  read-only
		STATUS      current
		DESCRIPTION 
			"Voltage high alarm threshold in Volt."
		::= { iswDDMIEntry 15 }

	iswDDMIA2VoltageLowAlarmThreshold OBJECT-TYPE
		SYNTAX      OCTET STRING
		MAX-ACCESS  read-only
		STATUS      current
		DESCRIPTION 
			"Voltage low alarm threshold in Volt."
		::= { iswDDMIEntry 16 }

	iswDDMIA2VoltageHighWarnThreshold OBJECT-TYPE
		SYNTAX      OCTET STRING
		MAX-ACCESS  read-only
		STATUS      current
		DESCRIPTION 
			"Voltage high warning threshold in Volt."
		::= { iswDDMIEntry 17 }

	iswDDMIA2VoltageLowWarnThreshold OBJECT-TYPE
		SYNTAX      OCTET STRING
		MAX-ACCESS  read-only
		STATUS      current
		DESCRIPTION 
			"Voltage low warning threshold in Volt."
		::= { iswDDMIEntry 18 }

	iswDDMIA2CurrentTxBias OBJECT-TYPE
		SYNTAX      OCTET STRING
		MAX-ACCESS  read-only
		STATUS      current
		DESCRIPTION 
			"Current Tx bias in mA."
		::= { iswDDMIEntry 19 }

	iswDDMIA2TxBiasHighAlarmThreshold OBJECT-TYPE
		SYNTAX      OCTET STRING
		MAX-ACCESS  read-only
		STATUS      current
		DESCRIPTION 
			"Tx bias high alarm threshold in mA."
		::= { iswDDMIEntry 20 }

	iswDDMIA2TxBiasLowAlarmThreshold OBJECT-TYPE
		SYNTAX      OCTET STRING
		MAX-ACCESS  read-only
		STATUS      current
		DESCRIPTION 
			"Tx bias low alarm threshold in mA."
		::= { iswDDMIEntry 21 }

	iswDDMIA2TxBiasHighWarnThreshold OBJECT-TYPE
		SYNTAX      OCTET STRING
		MAX-ACCESS  read-only
		STATUS      current
		DESCRIPTION 
			"Tx bias high warning threshold in mA."
		::= { iswDDMIEntry 22 }

	iswDDMIA2TxBiasLowWarnThreshold OBJECT-TYPE
		SYNTAX      OCTET STRING
		MAX-ACCESS  read-only
		STATUS      current
		DESCRIPTION 
			"Tx bias low warning threshold in mA."
		::= { iswDDMIEntry 23 }

	iswDDMIA2CurrentTxPower OBJECT-TYPE
		SYNTAX      OCTET STRING
		MAX-ACCESS  read-only
		STATUS      current
		DESCRIPTION 
			"Current Tx power in dBm."
		::= { iswDDMIEntry 24 }

	iswDDMIA2TxPowerHighAlarmThreshold OBJECT-TYPE
		SYNTAX      OCTET STRING
		MAX-ACCESS  read-only
		STATUS      current
		DESCRIPTION 
			"Tx power high alarm threshold in dBm."
		::= { iswDDMIEntry 25 }

	iswDDMIA2TxPowerLowAlarmThreshold OBJECT-TYPE
		SYNTAX      OCTET STRING
		MAX-ACCESS  read-only
		STATUS      current
		DESCRIPTION 
			"Tx power low alarm threshold in dBm."
		::= { iswDDMIEntry 26 }

	iswDDMIA2TxPowerHighWarnThreshold OBJECT-TYPE
		SYNTAX      OCTET STRING
		MAX-ACCESS  read-only
		STATUS      current
		DESCRIPTION 
			"Tx power high warning threshold in dBm."
		::= { iswDDMIEntry 27 }

	iswDDMIA2TxPowerLowWarnThreshold OBJECT-TYPE
		SYNTAX      OCTET STRING
		MAX-ACCESS  read-only
		STATUS      current
		DESCRIPTION 
			"Tx power low warning threshold in dBm."
		::= { iswDDMIEntry 28 }

	iswDDMIA2CurrentRxPower OBJECT-TYPE
		SYNTAX      OCTET STRING
		MAX-ACCESS  read-only
		STATUS      current
		DESCRIPTION 
			"Current Rx power in dBm."
		::= { iswDDMIEntry 29 }

	iswDDMIA2RxPowerHighAlarmThreshold OBJECT-TYPE
		SYNTAX      OCTET STRING
		MAX-ACCESS  read-only
		STATUS      current
		DESCRIPTION 
			"Rx power high alarm threshold in dBm."
		::= { iswDDMIEntry 30 }

	iswDDMIA2RxPowerLowAlarmThreshold OBJECT-TYPE
		SYNTAX      OCTET STRING
		MAX-ACCESS  read-only
		STATUS      current
		DESCRIPTION 
			"Rx power low alarm threshold in dBm."
		::= { iswDDMIEntry 31 }

	iswDDMIA2RxPowerHighWarnThreshold OBJECT-TYPE
		SYNTAX      OCTET STRING
		MAX-ACCESS  read-only
		STATUS      current
		DESCRIPTION 
			"Rx power high warning threshold in dBm."
		::= { iswDDMIEntry 32 }

	iswDDMIA2RxPowerLowWarnThreshold OBJECT-TYPE
		SYNTAX      OCTET STRING
		MAX-ACCESS  read-only
		STATUS      current
		DESCRIPTION 
			"Rx power low warning threshold in dBm."
		::= { iswDDMIEntry 33 }

-- 
	iswRestartSNMPAgent OBJECT-TYPE
		SYNTAX          INTEGER { ready(0), active(1) }
		MAX-ACCESS      read-write
		STATUS          current
		DESCRIPTION     "SNMP Agent Restart. Set active(1) to Restart SNMP Agent
						After SNMP Agent is restarted, the configuration of following 4 tables will take effect.
									snmpCommunityTable
									snmpTargetAddrTable
									snmpTargetParamsTable
									snmpNotifyTable
						It will take 2-3 seconds for SNMP agent restart, so it is recommended to restart SNMP agent after all the SNMP configuration is modified completely.
						"
		::= { iswMtnMgt 7 }   

--1
	iswFTPServerIp		OBJECT-TYPE
		SYNTAX		IpAddress
		MAX-ACCESS	read-write
		STATUS		current
		DESCRIPTION	"FTP or TFTP serve IP address."
		::= { iswFTPServer 1 }
--2
	iswFTPUserName		OBJECT-TYPE
		SYNTAX		OCTET STRING ( SIZE ( 0 .. 32 ) )
		MAX-ACCESS	read-write
		STATUS		current
		DESCRIPTION	"FTP user name."
		::= { iswFTPServer 2 }
--3
	iswFTPUserPassword	OBJECT-TYPE
		SYNTAX		OCTET STRING ( SIZE ( 0 .. 32 ) )
		MAX-ACCESS	read-write
		STATUS		current
		DESCRIPTION	"FTP user password."
		::= { iswFTPServer 3 }
--4
	iswFTPFileName		OBJECT-TYPE
		SYNTAX		OCTET STRING ( SIZE ( 0 .. 64 ) )
		MAX-ACCESS	read-write
		STATUS		current
		DESCRIPTION	"FTP or TFTP file name used by iswSysSaveConfig or iswRemoteDlAction."
		::= { iswFTPServer 4 }
--
--
	iswDBSaveRestoreInbandTable		OBJECT-TYPE
		SYNTAX		SEQUENCE OF IswDBSaveRestoreInbandEntry
		MAX-ACCESS	not-accessible
		STATUS		current
		DESCRIPTION	"DB save restore inband table. Max entry size: 16."
		::= { iswDBSaveRestore 1 }
		
	iswDBSaveRestoreInbandEntry	OBJECT-TYPE
		SYNTAX		IswDBSaveRestoreInbandEntry
		MAX-ACCESS	not-accessible
		STATUS		current
		DESCRIPTION	"DB save restore inband entry."
		INDEX		{ iswDBSaveRestoreInbandIndex }
		::= { iswDBSaveRestoreInbandTable 1 }
		
	IswDBSaveRestoreInbandEntry ::= SEQUENCE{
		iswDBSaveRestoreInbandIndex			Integer32,
		iswDBSaveRestoreInbandName			OCTET STRING,
		iswDBSaveRestoreInbandSize			Gauge32,
		iswDBSaveRestoreInbandUncpSize		Gauge32
	}
--1
	iswDBSaveRestoreInbandIndex	OBJECT-TYPE
		SYNTAX		Integer32 ( 1 .. 16 )
		MAX-ACCESS	not-accessible
		STATUS		current
		DESCRIPTION	"DB save restore inband index."
		::= { iswDBSaveRestoreInbandEntry 1 }
--2
	iswDBSaveRestoreInbandName	OBJECT-TYPE
		SYNTAX		OCTET STRING
		MAX-ACCESS	read-only
		STATUS		current
		DESCRIPTION	"DB save restore inband name."
		::= { iswDBSaveRestoreInbandEntry 2 }
--3
	iswDBSaveRestoreInbandSize	OBJECT-TYPE
		SYNTAX		Gauge32
		MAX-ACCESS	read-only
		STATUS		current
		DESCRIPTION	"DB save restore inband size."
		::= { iswDBSaveRestoreInbandEntry 3 }
--4
	iswDBSaveRestoreInbandUncpSize	OBJECT-TYPE
		SYNTAX		Gauge32
		MAX-ACCESS	read-only
		STATUS		current
		DESCRIPTION	"DB save restore inband uncompressed size."
		::= { iswDBSaveRestoreInbandEntry 4 }
--
	iswDBSaveRestoreGeneralTable		OBJECT-TYPE
		SYNTAX		SEQUENCE OF IswDBSaveRestoreGeneralEntry
		MAX-ACCESS	not-accessible
		STATUS		current
		DESCRIPTION	"DB save restore general table. Max entry size: 16."
		::= { iswDBSaveRestore 2 }
		
	iswDBSaveRestoreGeneralEntry	OBJECT-TYPE
		SYNTAX		IswDBSaveRestoreGeneralEntry
		MAX-ACCESS	not-accessible
		STATUS		current
		DESCRIPTION	"DB save restore general entry."
		INDEX		{ iswDBSaveRestoreGeneralIndex }
		::= { iswDBSaveRestoreGeneralTable 1 }
		
	IswDBSaveRestoreGeneralEntry ::= SEQUENCE{
		iswDBSaveRestoreGeneralIndex		Integer32,
		iswDBSaveRestoreGeneralName			OCTET STRING,
		iswDBSaveRestoreGeneralSize			Gauge32,
		iswDBSaveRestoreGeneralUncpSize		Gauge32
	}
--1
	iswDBSaveRestoreGeneralIndex	OBJECT-TYPE
		SYNTAX		Integer32  ( 1 .. 16 )
		MAX-ACCESS	not-accessible
		STATUS		current
		DESCRIPTION	"DB save restore general index."
		::= { iswDBSaveRestoreGeneralEntry 1 }
--2
	iswDBSaveRestoreGeneralName	OBJECT-TYPE
		SYNTAX		OCTET STRING
		MAX-ACCESS	read-only
		STATUS		current
		DESCRIPTION	"DB save restore general name."
		::= { iswDBSaveRestoreGeneralEntry 2 }
--3
	iswDBSaveRestoreGeneralSize	OBJECT-TYPE
		SYNTAX		Gauge32
		MAX-ACCESS	read-only
		STATUS		current
		DESCRIPTION	"DB save restore general size."
		::= { iswDBSaveRestoreGeneralEntry 3 }
--4
	iswDBSaveRestoreGeneralUncpSize	OBJECT-TYPE
		SYNTAX		Gauge32
		MAX-ACCESS	read-only
		STATUS		current
		DESCRIPTION	"DB save restore general uncompressed size."
		::= { iswDBSaveRestoreGeneralEntry 4 }
--
--1
	iswDBSaveRestoreActiveIndex	OBJECT-TYPE
		SYNTAX		Integer32
		MAX-ACCESS	read-only
		STATUS		current
		DESCRIPTION	"DB save restore active index."
		::= { iswDBSaveRestore 3 }
--2
	iswDBSaveRestoreBootIndex	OBJECT-TYPE
		SYNTAX		Integer32
		MAX-ACCESS	read-only
		STATUS		current
		DESCRIPTION	"DB save restore boot index."
		::= { iswDBSaveRestore 4 }
--3
	iswDBSaveRestoreEntryCount	OBJECT-TYPE
		SYNTAX		Integer32
		MAX-ACCESS	read-only
		STATUS		current
		DESCRIPTION	"DB save restore entry count."
		::= { iswDBSaveRestore 5 }
--4
	iswDBSaveRestoreGenActiveIndex	OBJECT-TYPE
		SYNTAX		Integer32
		MAX-ACCESS	read-only
		STATUS		current
		DESCRIPTION	"DB save restore active index."
		::= { iswDBSaveRestore 6 }
--5
	iswDBSaveRestoreGenBootIndex	OBJECT-TYPE
		SYNTAX		Integer32
		MAX-ACCESS	read-only
		STATUS		current
		DESCRIPTION	"DB save restore boot index."
		::= { iswDBSaveRestore 7 }
--6
	iswDBSaveRestoreGenEntryCount	OBJECT-TYPE
		SYNTAX		Integer32
		MAX-ACCESS	read-only
		STATUS		current
		DESCRIPTION	"DB save restore entry count."
		::= { iswDBSaveRestore 8 }
--4
	--iswDBSaveRestoreType	OBJECT-TYPE
	--	SYNTAX		Integer32
	--	MAX-ACCESS	read-only
	--	STATUS		current
	--	DESCRIPTION	"DB save restore restore type."
	--	::= { iswDBSaveRestore 6 }
--
--1
	iswRemoteDlAction	OBJECT-TYPE
		SYNTAX		Integer32  { image-noreboot(0), image-reboot(1), bootloader-noreboot(2), bootloader-reboot(3),
                                 image-noreboot-tftp(4), image-reboot-tftp(5) 		}
		MAX-ACCESS	read-write
		STATUS		current
		DESCRIPTION	"Active image/bootloader remote download with Reboot or no reboot after remote download.
					Before this action, please set iswFTPServer parameters properly for FTP or TFTP;
                    image-noreboot(0) and image-reboot(1) use FTP for file transferring;
                    image-noreboot-tftp(4) and image-reboot-tftp(5) use TFTP for file transferring."
		::= { iswFWDownload 1 }
--2
	iswRemoteDlImageStatus	OBJECT-TYPE
		SYNTAX		Integer32 { idle (0), ftpSuccess (1), ftpFail (2), ftpInprogress (3), flashWriteSuccess (4), flashWriteFail (5), flashWriteInprogress (6),
                                          tftpSuccess (7), tftpFail (8), tftpInprogress (9)		}
		MAX-ACCESS	read-only
		STATUS		current
		DESCRIPTION	"Image remote download status."
		::= { iswFWDownload 2 }

	iswRemoteDlBootloaderStatus	OBJECT-TYPE
		SYNTAX		Integer32 { idle (0), ftpSuccess (1), ftpFail (2), ftpInprogress (3), flashWriteSuccess (4), flashWriteFail (5), flashWriteInprogress (6) }
		MAX-ACCESS	read-only
		STATUS		current
		DESCRIPTION	"Bootloader remote download status."
		::= { iswFWDownload 3 }
--
	iswFWInfoTable	OBJECT-TYPE
		SYNTAX		SEQUENCE OF IswFWInfoEntry
		MAX-ACCESS	not-accessible
		STATUS		current
		DESCRIPTION	"FW information table. Max entry size: 2."
		::= { iswMtnFirmware 2 }
		
	iswFWInfoEntry	OBJECT-TYPE
		SYNTAX		IswFWInfoEntry
		MAX-ACCESS	not-accessible
		STATUS		current
		DESCRIPTION	"FW information entry."
		INDEX		{ iswFWInfoIndex }
		::= { iswFWInfoTable 1 }
		
	IswFWInfoEntry ::= SEQUENCE{
		iswFWInfoIndex		Integer32,
		iswFWInfoVersion	OCTET STRING,
		iswFWInfoDate		OCTET STRING,
		iswFWInfoName		OCTET STRING,
		iswFWInfoActive		Integer32,
		iswFWInfoNextBoot	Integer32
	}
--1
	iswFWInfoIndex		OBJECT-TYPE
		SYNTAX		Integer32  { partition0 (0), partition1 (1) }
		MAX-ACCESS	not-accessible
		STATUS		current
		DESCRIPTION	"FW information."
		::= { iswFWInfoEntry 1 }
--2
	iswFWInfoVersion	OBJECT-TYPE
		SYNTAX		OCTET STRING ( SIZE ( 0 .. 11 ) )
		MAX-ACCESS	read-only
		STATUS		current
		DESCRIPTION	"FW information version."
		::= { iswFWInfoEntry 2 }
--3
	iswFWInfoDate		OBJECT-TYPE
		SYNTAX		OCTET STRING ( SIZE ( 0 .. 11 ) )
		MAX-ACCESS	read-only
		STATUS		current
		DESCRIPTION	"FW information date."
		::= { iswFWInfoEntry 3 }
--4
	iswFWInfoName		OBJECT-TYPE
		SYNTAX		OCTET STRING ( SIZE ( 0 .. 31 ) )
		MAX-ACCESS	read-only
		STATUS		current
		DESCRIPTION	"FW information name."
		::= { iswFWInfoEntry 4 }
--5
	iswFWInfoActive	OBJECT-TYPE
		SYNTAX		Integer32 { deactive(0), active(1)  }
		MAX-ACCESS	read-only
		STATUS		current
		DESCRIPTION	"Show the partition is active or not."
		::= { iswFWInfoEntry 5 }
--6
	iswFWInfoNextBoot	OBJECT-TYPE
		SYNTAX		Integer32 { deactive(0), active(1)  }
		MAX-ACCESS	read-write
		STATUS		current
		DESCRIPTION	"In write case, set partition as active to switch next boot partition."
		::= { iswFWInfoEntry 6 }
--

	iswFWUpgradeScheduleTable	OBJECT-TYPE
		SYNTAX		SEQUENCE OF IswFWUpgradeScheduleEntry
		MAX-ACCESS	not-accessible
		STATUS		current
		DESCRIPTION	"FW schedule upgrade Table. Max entry size: 1."
		::=	 { iswMtnFirmware 3 }

	iswFWUpgradeScheduleEntry	OBJECT-TYPE
		SYNTAX		IswFWUpgradeScheduleEntry
		MAX-ACCESS	not-accessible
		STATUS		current
		DESCRIPTION	"FW schedule upgrade entry."
		INDEX		{ iswFWUpgradeScheduleIndex }
		::=	 { iswFWUpgradeScheduleTable 1 }

	IswFWUpgradeScheduleEntry	::=	 SEQUENCE	{
		iswFWUpgradeScheduleIndex			Integer32,
		iswFWUpgradeScheduleTime			OCTET STRING,
		iswFWUpgradeScheduleServerIp		IpAddress,
		iswFWUpgradeScheduleUserName		OCTET STRING,
		iswFWUpgradeScheduleUserPassword	OCTET STRING,
		iswFWUpgradeScheduleFileName		OCTET STRING,
		iswFWUpgradeScheduleOption			Integer32,
		iswFWUpgradeScheduleRowStatus		RowStatus
		}

	iswFWUpgradeScheduleIndex	OBJECT-TYPE
		SYNTAX		Integer32   ( 1 .. 1 )
		MAX-ACCESS	not-accessible
		STATUS		current
		DESCRIPTION	"FW schedule upgrade index."
		::= { iswFWUpgradeScheduleEntry 1 }

--1
	iswFWUpgradeScheduleTime	OBJECT-TYPE
		SYNTAX		OCTET STRING ( SIZE ( 19 ) )
		MAX-ACCESS	read-create
		STATUS		current
		DESCRIPTION	"Time for FW scheduled upgrade (must be within follow 30 days)
					Format must be MM/DD/YYYY HH:MM:SS
					Example: 03/20/2013 18:30:20
					"
		::= { iswFWUpgradeScheduleEntry 2 }
--2
	iswFWUpgradeScheduleServerIp	OBJECT-TYPE
		SYNTAX		IpAddress
		MAX-ACCESS	read-create
		STATUS		current
		DESCRIPTION	"FW upgrade schedule server IP."
		::= { iswFWUpgradeScheduleEntry 3 }
--3
	iswFWUpgradeScheduleUserName	OBJECT-TYPE
		SYNTAX		OCTET STRING ( SIZE ( 1 .. 32 ) )
		MAX-ACCESS	read-create
		STATUS		current
		DESCRIPTION	"FW upgrade schedule user name."
		::= { iswFWUpgradeScheduleEntry 4 }
--4
	iswFWUpgradeScheduleUserPassword	OBJECT-TYPE
		SYNTAX		OCTET STRING ( SIZE ( 0 .. 32 ) )
		MAX-ACCESS	read-create
		STATUS		current
		DESCRIPTION	"FW upgrade schedule user password."
		::= { iswFWUpgradeScheduleEntry 5 }
--5
	iswFWUpgradeScheduleFileName	OBJECT-TYPE
		SYNTAX		OCTET STRING ( SIZE ( 1 .. 64 ) )
		MAX-ACCESS	read-create
		STATUS		current
		DESCRIPTION	"FW upgrade schedule file name."
		::= { iswFWUpgradeScheduleEntry 6 }
--6
	iswFWUpgradeScheduleOption	OBJECT-TYPE
		SYNTAX		Integer32   { bootloader-noreboot(0), bootloader-reboot(1), image-noreboot(2), image-reboot(3) }
		MAX-ACCESS	read-create
		STATUS		current
		DESCRIPTION	"FW upgrade schedule option."
		::= { iswFWUpgradeScheduleEntry 7 }  

--7
	iswFWUpgradeScheduleRowStatus	OBJECT-TYPE
		SYNTAX		RowStatus
		MAX-ACCESS	read-create
		STATUS		current
		DESCRIPTION	"RowStatus"
		::= { iswFWUpgradeScheduleEntry 8 }
--		
--	
	iswEthernetPortTable	OBJECT-TYPE
		SYNTAX		SEQUENCE OF IswEthernetPortEntry
		MAX-ACCESS	not-accessible
		STATUS		current
		DESCRIPTION	"Ethernet port table. Max entry size: port number."
		::= { iswEnetPort 1 }
		
	iswEthernetPortEntry	OBJECT-TYPE
		SYNTAX		IswEthernetPortEntry
		MAX-ACCESS	not-accessible
		STATUS		current
		DESCRIPTION	"Ethernet port entry."
		INDEX		{ iswPortEnetPortIndex }
		::= { iswEthernetPortTable 1 }
		
	IswEthernetPortEntry ::= SEQUENCE{
		iswPortEnetPortIndex			IswGbeIndex,
		iswPortEnetAdminStatus			Integer32,
		iswPortEnetMode					Integer32,
		iswPortEnetLinkStatus			Integer32,
		iswPortEnetCopperSFPPriority	Integer32,
		iswPortEnetSFPStatus			Integer32,
		iswPortEnetFlowCtrl				Integer32,
		iswPortEnetSFPSpeed				Integer32
	}
--1	
	iswPortEnetPortIndex	OBJECT-TYPE
		SYNTAX		IswGbeIndex
		MAX-ACCESS	not-accessible
		STATUS		current
		DESCRIPTION	"Port ethernet port index."
		::= { iswEthernetPortEntry 1 }  
--2	
	iswPortEnetAdminStatus	OBJECT-TYPE
		SYNTAX		Integer32	{ disable(0), enable(1) }
		MAX-ACCESS	read-write
		STATUS		current
		DESCRIPTION	"Port ethernet admin status. Default value is enable (1)." 
		DEFVAL		{ 1 }
		::= { iswEthernetPortEntry 2 } 
--3
	iswPortEnetMode	OBJECT-TYPE
		SYNTAX		Integer32	{ auto(1), half10m(2), full10m(3), half100m(4), full100m(5), full1g(6) }
		MAX-ACCESS	read-write
		STATUS		current
		DESCRIPTION	"Port ethernet mode(Not support CuSFP). Default value is auto (1).
					Fiber port are SFP, can't change the mode."
		DEFVAL		{ 1 }
		::= { iswEthernetPortEntry 3 }  
--4	
	iswPortEnetLinkStatus	OBJECT-TYPE
		SYNTAX		Integer32	{ full1000m(1), full100m(2), half100m(3), full10m(4), half10m(5), linkDown(6), full2500m(7), full10gbps(8) }
		MAX-ACCESS	read-only
		STATUS		current
		DESCRIPTION	"Port ethernet link status." 
		::= { iswEthernetPortEntry 4 }  
--5	
	iswPortEnetCopperSFPPriority	OBJECT-TYPE
		SYNTAX		Integer32	{ sfp(1), copper(2) }
		MAX-ACCESS	read-write
		STATUS		current
		DESCRIPTION	"Port ethernet copper SFP priority. 
					Copper port only accept copper(2), can't be changed.
					Filber port only accept sfp(1), can't be changed.
					Only some models support Copper/SFP combo port, default is SFP first.
					Combo port (copper and fiber) default is sfp(1), allow change to copper(2)."
		DEFVAL		{ 1 }
		::= { iswEthernetPortEntry 5 }  
--6	
	iswPortEnetSFPStatus	OBJECT-TYPE
		SYNTAX		Integer32	{ linkup(1), linkdown(2)  }
		MAX-ACCESS	read-only
		STATUS		current
		DESCRIPTION	"Port ethernet SFP status.
					Copper port always linkdown(2).
					Combo port (copper and fiber) is linkup(1) or linkdown(2).
					Filber port, if value is linkup(1), can refer to iswPortEnetLinkStatus. [full1000m(1), full100m(2), full2500m(7), full10gbps(8)]."
		::= { iswEthernetPortEntry 6 }  
--7	
	iswPortEnetFlowCtrl	OBJECT-TYPE
		SYNTAX		Integer32	{ disable(0), enable(1) }
		MAX-ACCESS	read-write
		STATUS		current
		DESCRIPTION	"Port ethernet flow control. Default value is disable (0)."     
		DEFVAL		{ 0 }
		::= { iswEthernetPortEntry 7 }
--8
	iswPortEnetSFPSpeed	OBJECT-TYPE
		SYNTAX		Integer32	{ auto(1), full100m(2), full1000m(3), full2500m(4),  full10g(5) }
		MAX-ACCESS	read-write
		STATUS		current
		DESCRIPTION	"Filber Port speed. Default value is auto (1)."
		DEFVAL		{ 1 }
		::= { iswEthernetPortEntry 8 }		
--

	iswIfStatsTable	OBJECT-TYPE
		SYNTAX		SEQUENCE OF IswIfStatsEntry
		MAX-ACCESS	not-accessible
		STATUS		current
		DESCRIPTION	"Interface statistic table. Max entry size: 10."
		::= { iswPortStats 1 }
		
	iswIfStatsEntry	OBJECT-TYPE
		SYNTAX		IswIfStatsEntry
		MAX-ACCESS	not-accessible
		STATUS		current
		DESCRIPTION	"If entry."
		INDEX		{ iswIfIndex }
		::= { iswIfStatsTable 1 }
		
	IswIfStatsEntry ::= SEQUENCE{
		iswIfIndex					IswGbeIndex,
		--iswIfDescr				OCTET STRING,
		iswIfInDiscards				Counter32,
		iswIfInErrors				Counter32,
		iswIfOutDiscards			Counter32,
		iswIfOutErrors				Counter32,
		iswIfxHCInOctets			Counter64,
		iswIfxHCInUcastPkts			Counter64,
		iswIfxHCInMulticastPkts		Counter64,
		iswIfxHCInBroadcastPkts		Counter64,
		iswIfxHCOutOctets			Counter64,
		iswIfxHCOutUcastPkts		Counter64,
		iswIfxHCOutMulticastPkts	Counter64,
		iswIfxHCOutBroadcastPkts	Counter64,
		--iswIfxHCInOctetsH			Counter32,
		--iswIfxHCInUcastPktsH		Counter32,
		--iswIfxHCInMulticastPktsH	Counter32,
		--iswIfxHCInBroadcastPktsH	Counter32,
		--iswIfxHCOutOctetsH		Counter32,
		--iswIfxHCOutUcastPktsH		Counter32,
		--iswIfxHCOutMulticastPktsH	Counter32,
		--iswIfxHCOutBroadcastPktsH	Counter32,
		iswIfTableClearStats		Integer32
	} 
--1
	iswIfIndex	OBJECT-TYPE
		SYNTAX		IswGbeIndex
		MAX-ACCESS	not-accessible
		STATUS		current
		DESCRIPTION	"If index."
		::= { iswIfStatsEntry 1 }   

	iswIfInDiscards	OBJECT-TYPE
		SYNTAX		Counter32
		MAX-ACCESS	read-only
		STATUS		current
		DESCRIPTION	"If income discards."
		::= { iswIfStatsEntry 2 } 

	iswIfInErrors	OBJECT-TYPE
		SYNTAX		Counter32
		MAX-ACCESS	read-only
		STATUS		current
		DESCRIPTION	"If income errors."
		::= { iswIfStatsEntry 3 } 

	iswIfOutDiscards	OBJECT-TYPE
		SYNTAX		Counter32
		MAX-ACCESS	read-only
		STATUS		current
		DESCRIPTION	"If out discards."
		::= { iswIfStatsEntry 4 } 

	iswIfOutErrors	OBJECT-TYPE
		SYNTAX		Counter32
		MAX-ACCESS	read-only
		STATUS		current
		DESCRIPTION	"If out errors."
		::= { iswIfStatsEntry 5 } 

	iswIfxHCInOctets	OBJECT-TYPE
		SYNTAX		Counter64
		MAX-ACCESS	read-only
		STATUS		current
		DESCRIPTION	"Ifx HC In octets."
		::= { iswIfStatsEntry 6 } 

	iswIfxHCInUcastPkts	OBJECT-TYPE
		SYNTAX		Counter64
		MAX-ACCESS	read-only
		STATUS		current
		DESCRIPTION	"Ifx HC In ucast packets."
		::= { iswIfStatsEntry 7 } 

	iswIfxHCInMulticastPkts	OBJECT-TYPE
		SYNTAX		Counter64
		MAX-ACCESS	read-only
		STATUS		current
		DESCRIPTION	"Ifx HC In multicast packets."
		::= { iswIfStatsEntry 8 } 

	iswIfxHCInBroadcastPkts	OBJECT-TYPE
		SYNTAX		Counter64
		MAX-ACCESS	read-only
		STATUS		current
		DESCRIPTION	"Ifx HC In broadcast packets."
		::= { iswIfStatsEntry 9 } 

	iswIfxHCOutOctets	OBJECT-TYPE
		SYNTAX		Counter64
		MAX-ACCESS	read-only
		STATUS		current
		DESCRIPTION	"Ifx HC Out octets."
		::= { iswIfStatsEntry 10 } 

	iswIfxHCOutUcastPkts	OBJECT-TYPE
		SYNTAX		Counter64
		MAX-ACCESS	read-only
		STATUS		current
		DESCRIPTION	"Ifx HC Out ucast packets."
		::= { iswIfStatsEntry 11 } 

	iswIfxHCOutMulticastPkts	OBJECT-TYPE
		SYNTAX		Counter64
		MAX-ACCESS	read-only
		STATUS		current
		DESCRIPTION	"Ifx HC Out multicast packets."
		::= { iswIfStatsEntry 12 }

	iswIfxHCOutBroadcastPkts	OBJECT-TYPE
		SYNTAX		Counter64
		MAX-ACCESS	read-only
		STATUS		current
		DESCRIPTION	"Ifx HC Out broadcast packets."
		::= { iswIfStatsEntry 13 }

--	iswIfxHCInOctetsH	OBJECT-TYPE
--		SYNTAX		Counter32
--		MAX-ACCESS	read-only
--		STATUS		current
--		DESCRIPTION	"Ifx HC In octets. High Counter32."
--		::= { iswIfStatsEntry 14 } 

--	iswIfxHCInUcastPktsH	OBJECT-TYPE
--		SYNTAX		Counter32
--		MAX-ACCESS	read-only
--		STATUS		current
--		DESCRIPTION	"Ifx HC In ucast packets. High Counter32."
--		::= { iswIfStatsEntry 15 } 

--	iswIfxHCInMulticastPktsH	OBJECT-TYPE
--		SYNTAX		Counter32
--		MAX-ACCESS	read-only
--		STATUS		current
--		DESCRIPTION	"Ifx HC In multicast packets. High Counter32."
--		::= { iswIfStatsEntry 16 } 

--	iswIfxHCInBroadcastPktsH	OBJECT-TYPE
--		SYNTAX		Counter32
--		MAX-ACCESS	read-only
--		STATUS		current
--		DESCRIPTION	"Ifx HC In broadcast packets. High Counter32."
--		::= { iswIfStatsEntry 17 } 

--	iswIfxHCOutOctetsH	OBJECT-TYPE
--		SYNTAX		Counter32
--		MAX-ACCESS	read-only
--		STATUS		current
--		DESCRIPTION	"Ifx HC Out octets. High Counter32."
--		::= { iswIfStatsEntry 18 } 

--	iswIfxHCOutUcastPktsH	OBJECT-TYPE
--		SYNTAX		Counter32
--		MAX-ACCESS	read-only
--		STATUS		current
--		DESCRIPTION	"Ifx HC Out ucast packets. High Counter32."
--		::= { iswIfStatsEntry 19 } 

--	iswIfxHCOutMulticastPktsH	OBJECT-TYPE
--		SYNTAX		Counter32
--		MAX-ACCESS	read-only
--		STATUS		current
--		DESCRIPTION	"Ifx HC Out multicast packets. High Counter32."
--		::= { iswIfStatsEntry 20 } 

--	iswIfxHCOutBroadcastPktsH	OBJECT-TYPE
--		SYNTAX		Counter32
--		MAX-ACCESS	read-only
--		STATUS		current
--		DESCRIPTION	"Ifx HC Out broadcast packets. High Counter32."
--		::= { iswIfStatsEntry 21 }

	iswIfTableClearStats	OBJECT-TYPE
		SYNTAX		Integer32 { clearStats (1) }
		MAX-ACCESS	read-write
		STATUS		current
		DESCRIPTION	"Set statistics as zero."
		::= { iswIfStatsEntry 14 }
--
--
--  iswEtherStatsTable counters are same as RMON counters ( etherStatsTable )
--

	iswEtherStatsTable	OBJECT-TYPE
		SYNTAX		SEQUENCE OF IswEtherStatsEntry
		MAX-ACCESS	not-accessible
		STATUS		current
		DESCRIPTION	"Ethernet stats table. Max entry size: port number."
		::= { iswPortStats 2 }
		
	iswEtherStatsEntry	OBJECT-TYPE
		SYNTAX		IswEtherStatsEntry
		MAX-ACCESS	not-accessible
		STATUS		current
		DESCRIPTION	"Ethernet stats entry."
		INDEX		{ iswEtherStatsIfindex }
		::= { iswEtherStatsTable 1 }
		
	IswEtherStatsEntry ::= SEQUENCE{
		iswEtherStatsIfindex				IswGbeIndex,
		iswEtherStatsDropEvents				Counter32,
		iswEtherStatsOctets					Counter32,
		iswEtherStatsPkts					Counter32,
		iswEtherStatsBroadcastPkts			Counter32,
		iswEtherStatsMulticastPkts			Counter32,
		iswEtherStatsCRCAlignErrors			Counter32,
		iswEtherStatsUndersizePkts			Counter32,
		iswEtherStatsOversizePkts			Counter32,
		iswEtherStatsFragments				Counter32,
		iswEtherStatsJabbers				Counter32,
		iswEtherStatsCollisions				Counter32,
		iswEtherStatsPkts64Octets			Counter32,
		iswEtherStatsPks65to127Octets		Counter32,
		iswEtherStatsPkts128to255Octets		Counter32,
		iswEtherStatsPkts256to511Octets		Counter32,
		iswEtherStatsPkts512to1023Octets	Counter32,
		iswEtherStatsPkts1024to1518Octets	Counter32,
		iswEtherStatsClear					Integer32
	}
--1
	iswEtherStatsIfindex	OBJECT-TYPE
		SYNTAX		IswGbeIndex
		MAX-ACCESS	not-accessible
		STATUS		current
		DESCRIPTION	"Ethernet stats index."
		::= { iswEtherStatsEntry 1 }
--2
	iswEtherStatsDropEvents	OBJECT-TYPE
		SYNTAX		Counter32
		MAX-ACCESS	read-only
		STATUS		current
		DESCRIPTION	"Ethernet stats drop events."
		::= { iswEtherStatsEntry 2 } 
--3
	iswEtherStatsOctets	OBJECT-TYPE
		SYNTAX		Counter32
		MAX-ACCESS	read-only
		STATUS		current
		DESCRIPTION	"Ethernet stats octets."
		::= { iswEtherStatsEntry 3 } 
--4
	iswEtherStatsPkts	OBJECT-TYPE
		SYNTAX		Counter32
		MAX-ACCESS	read-only
		STATUS		current
		DESCRIPTION	"Ethernet stats packets."
		::= { iswEtherStatsEntry 4 } 
--5
	iswEtherStatsBroadcastPkts	OBJECT-TYPE
		SYNTAX		Counter32
		MAX-ACCESS	read-only
		STATUS		current
		DESCRIPTION	"Ethernet stats broadcast packets."
		::= { iswEtherStatsEntry 5 } 
--6
	iswEtherStatsMulticastPkts	OBJECT-TYPE
		SYNTAX		Counter32
		MAX-ACCESS	read-only
		STATUS		current
		DESCRIPTION	"Ethernet stats multicast packets."
		::= { iswEtherStatsEntry 6 } 
--7
	iswEtherStatsCRCAlignErrors	OBJECT-TYPE
		SYNTAX		Counter32
		MAX-ACCESS	read-only
		STATUS		current
		DESCRIPTION	"Ethernet stats CRC align errors."
		::= { iswEtherStatsEntry 7 } 
--8
	iswEtherStatsUndersizePkts	OBJECT-TYPE
		SYNTAX		Counter32
		MAX-ACCESS	read-only
		STATUS		current
		DESCRIPTION	"Ethernet stats under size packets."
		::= { iswEtherStatsEntry 8 } 
--9
	iswEtherStatsOversizePkts	OBJECT-TYPE
		SYNTAX		Counter32
		MAX-ACCESS	read-only
		STATUS		current
		DESCRIPTION	"Ethernet stats oversize packets."
		::= { iswEtherStatsEntry 9 } 
--10
	iswEtherStatsFragments	OBJECT-TYPE
		SYNTAX		Counter32
		MAX-ACCESS	read-only
		STATUS		current
		DESCRIPTION	"Ethernet stats fragments."
		::= { iswEtherStatsEntry 10 } 
--11
	iswEtherStatsJabbers	OBJECT-TYPE
		SYNTAX		Counter32
		MAX-ACCESS	read-only
		STATUS		current
		DESCRIPTION	"Ethernet stats jabbers."
		::= { iswEtherStatsEntry 11 } 
--12
	iswEtherStatsCollisions	OBJECT-TYPE
		SYNTAX		Counter32
		MAX-ACCESS	read-only
		STATUS		current
		DESCRIPTION	"Ethernet stats collisions."
		::= { iswEtherStatsEntry 12 } 
--13
	iswEtherStatsPkts64Octets	OBJECT-TYPE
		SYNTAX		Counter32
		MAX-ACCESS	read-only
		STATUS		current
		DESCRIPTION	"Ethernet stats packets 64 octets."
		::= { iswEtherStatsEntry 13 } 
--14
	iswEtherStatsPks65to127Octets	OBJECT-TYPE
		SYNTAX		Counter32
		MAX-ACCESS	read-only
		STATUS		current
		DESCRIPTION	"Ethernet stats packets 65 to 127 octets."
		::= { iswEtherStatsEntry 14 } 
--15
	iswEtherStatsPkts128to255Octets	OBJECT-TYPE
		SYNTAX		Counter32
		MAX-ACCESS	read-only
		STATUS		current
		DESCRIPTION	"Ethernet stats packets 128 to 255 octets."
		::= { iswEtherStatsEntry 15 } 
--16
	iswEtherStatsPkts256to511Octets	OBJECT-TYPE
		SYNTAX		Counter32
		MAX-ACCESS	read-only
		STATUS		current
		DESCRIPTION	"Ethernet stats packets 256 to 511 octets."
		::= { iswEtherStatsEntry 16 } 
--17
	iswEtherStatsPkts512to1023Octets	OBJECT-TYPE
		SYNTAX		Counter32
		MAX-ACCESS	read-only
		STATUS		current
		DESCRIPTION	"Ethernet stats packets 512 to 1023 octets."
		::= { iswEtherStatsEntry 17 } 
--18
	iswEtherStatsPkts1024to1518Octets	OBJECT-TYPE
		SYNTAX		Counter32
		MAX-ACCESS	read-only
		STATUS		current
		DESCRIPTION	"Ethernet stats packets 1024 to 1518 octets."
		::= { iswEtherStatsEntry 18 } 
--19
	iswEtherStatsClear	OBJECT-TYPE
		SYNTAX		Integer32 { clearStats(1) }
		MAX-ACCESS	read-write
		STATUS		current
		DESCRIPTION	"Set Ethernet stats as zero."
		::= { iswEtherStatsEntry 19 }
		
	iswDot1xStatistics		OBJECT IDENTIFIER
		::=  { iswPerform 2 }

	iswDot1xAuthEapolStatsTable	OBJECT-TYPE
		SYNTAX		SEQUENCE OF IswDot1xAuthEapolStatsEntry
		MAX-ACCESS	not-accessible
		STATUS		current
		DESCRIPTION	"Table of Authenticator statistics counters.
					A table that contains the statistics objects for the Authenticator PAE associated with each Ethernet Port.
					An entry appears in this table for each port that may authenticate access to itself.
					Max entry size: port number."
		::= { iswDot1xStatistics 1 }
		
	iswDot1xAuthEapolStatsEntry	OBJECT-TYPE
		SYNTAX		IswDot1xAuthEapolStatsEntry
		MAX-ACCESS	not-accessible
		STATUS		current
		DESCRIPTION	"AuthEapol Stats entry."
		INDEX		{ iswDot1xAuthEapolStatsPortId }
		::= { iswDot1xAuthEapolStatsTable 1 } 
		
	IswDot1xAuthEapolStatsEntry ::= SEQUENCE{
		iswDot1xAuthEapolStatsPortId			IswGbeIndex,
		iswDot1xAuthEapolFramesRx				Unsigned32,
		iswDot1xAuthEapolFramesTx				Unsigned32,
		iswDot1xAuthEapolStartFramesRx			Unsigned32,
		iswDot1xAuthEapolLogoffFramesRx			Unsigned32,
		iswDot1xAuthEapolRespIdFramesRx			Unsigned32,
		iswDot1xAuthEapolRespFramesRx			Unsigned32,
		iswDot1xAuthEapolReqIdFramesTx			Unsigned32,
		iswDot1xAuthEapolReqFramesTx			Unsigned32,
		iswDot1xAuthInvalidEapolFramesRx		Unsigned32,
		iswDot1xAuthEapLengthErrorFramesRx		Unsigned32,
		iswDot1xAuthLastEapolFrameVersion		Unsigned32
    } 
--1 
	iswDot1xAuthEapolStatsPortId	OBJECT-TYPE
		SYNTAX		IswGbeIndex
		MAX-ACCESS	not-accessible
		STATUS		current
		DESCRIPTION	"The index of port."
		::= { iswDot1xAuthEapolStatsEntry 1 }  
--2    
	iswDot1xAuthEapolFramesRx	OBJECT-TYPE
		SYNTAX		Unsigned32
		MAX-ACCESS	read-only
		STATUS		current
		DESCRIPTION	"The number of valid EAPOL frames of any type that have been received."
		::= { iswDot1xAuthEapolStatsEntry 2 } 
--3    
	iswDot1xAuthEapolFramesTx	OBJECT-TYPE
		SYNTAX		Unsigned32
		MAX-ACCESS	read-only
		STATUS		current
		DESCRIPTION	"The number of EAPOL frames of any type that have been transmitted."
		::= { iswDot1xAuthEapolStatsEntry 3 }
--4    
	iswDot1xAuthEapolStartFramesRx	OBJECT-TYPE
		SYNTAX		Unsigned32 	
		MAX-ACCESS	read-only
		STATUS		current
		DESCRIPTION	"The number of EAPOL Start frames that have been received."
		::= { iswDot1xAuthEapolStatsEntry 4 }
--5    
	iswDot1xAuthEapolLogoffFramesRx	OBJECT-TYPE
		SYNTAX		Unsigned32 	
		MAX-ACCESS	read-only
		STATUS		current
		DESCRIPTION	"The number of EAPOL Logoff frames that have been received."
		::= { iswDot1xAuthEapolStatsEntry 5 }
--6    
	iswDot1xAuthEapolRespIdFramesRx	OBJECT-TYPE
		SYNTAX		Unsigned32
		MAX-ACCESS	read-only
		STATUS		current
		DESCRIPTION	"The number of EAP Resp/Id frames that have been received."
		::= { iswDot1xAuthEapolStatsEntry 6 }
--7    
	iswDot1xAuthEapolRespFramesRx	OBJECT-TYPE
		SYNTAX		Unsigned32
		MAX-ACCESS	read-only
		STATUS		current
		DESCRIPTION	"The number of valid EAP Response frames(other than Resp/Id frames) that have been received."
		::= { iswDot1xAuthEapolStatsEntry 7 }
--8    
	iswDot1xAuthEapolReqIdFramesTx	OBJECT-TYPE
		SYNTAX		Unsigned32 	
		MAX-ACCESS	read-only
		STATUS		current
		DESCRIPTION	"The number of EAP Req/Id frames that have been transmitted."
		::= { iswDot1xAuthEapolStatsEntry 8 }
--9    
	iswDot1xAuthEapolReqFramesTx	OBJECT-TYPE
		SYNTAX		Unsigned32
		MAX-ACCESS	read-only
		STATUS		current
		DESCRIPTION	"The number of EAP Request frames(other than Req/Id frames) that have been transmitted."
		::= { iswDot1xAuthEapolStatsEntry 9 }
--10    
	iswDot1xAuthInvalidEapolFramesRx	OBJECT-TYPE
		SYNTAX		Unsigned32
		MAX-ACCESS	read-only
		STATUS		current
		DESCRIPTION	"The number of EAPOL frames that have been received by this Authenticator in which the frame type is not recognized."
		::= { iswDot1xAuthEapolStatsEntry 10 }
--11    
	iswDot1xAuthEapLengthErrorFramesRx	OBJECT-TYPE
		SYNTAX		Unsigned32
		MAX-ACCESS	read-only
		STATUS		current
		DESCRIPTION	"The number of EAPOL frames that have been received by this Authenticator in which the Packet Body Length field is invalid."
		::= { iswDot1xAuthEapolStatsEntry 11 }
--12    
	iswDot1xAuthLastEapolFrameVersion	OBJECT-TYPE
		SYNTAX		Unsigned32
		MAX-ACCESS	read-only
		STATUS		current
		DESCRIPTION	"The protocol version number carried in the most recently received EAPOL frame."
		::= { iswDot1xAuthEapolStatsEntry 12 }
		
	iswDot1xAuthEapolStatsClearCtrl		OBJECT IDENTIFIER
		::=  { iswDot1xStatistics 2 }

	iswDot1xAuthEapolStatsClearPortId	OBJECT-TYPE
		SYNTAX		IswGbeIndex
		MAX-ACCESS	read-write
		STATUS		current
		DESCRIPTION	"Port id for Dot1x Auth Eapol Stats clear. (clearByPort)"
		::= { iswDot1xAuthEapolStatsClearCtrl 1 }

	iswDot1xAuthEapolStatsClearType	OBJECT-TYPE
		SYNTAX		Integer32 { clearAll(0), clearByPort(1)  }
		MAX-ACCESS	read-write
		STATUS		current
		DESCRIPTION	"Type of Dot1x Auth Eapol Stats clear."
		::= { iswDot1xAuthEapolStatsClearCtrl 2 }
		
	iswDot1xRadiusStatsTable	OBJECT-TYPE
		SYNTAX		SEQUENCE OF IswDot1xRadiusStatsEntry
		MAX-ACCESS	not-accessible
		STATUS		current
		DESCRIPTION	"Table of RADIUS statistics counters. 
					It contains the statistics objects for the Authenticator associated with RADIUS Server.
					Max entry size: 1."
		::= { iswDot1xStatistics 3 }
		
	iswDot1xRadiusStatsEntry	OBJECT-TYPE
		SYNTAX		IswDot1xRadiusStatsEntry
		MAX-ACCESS	not-accessible
		STATUS		current
		DESCRIPTION	"Radius Stats entry."
		INDEX		{ iswDot1xRadiusServerId }
		::= { iswDot1xRadiusStatsTable 1 } 
		
	IswDot1xRadiusStatsEntry ::= SEQUENCE{
		iswDot1xRadiusServerId						Integer32,
		iswDot1xRadiusAuthClientAccessRequests		Unsigned32,
		iswDot1xRadiusAuthClientAccessAccepts		Unsigned32,
		iswDot1xRadiusAuthClientAccessRejects		Unsigned32,
		iswDot1xRadiusAuthClientAccessChallenges	Unsigned32,
		iswDot1xRadiusAuthClientBadAuthenticators	Unsigned32,
		iswDot1xRadiusAuthClientTimeouts			Unsigned32,
		iswDot1xRadiusAuthClientPacketsDropped		Unsigned32
	} 
--1 
	iswDot1xRadiusServerId	OBJECT-TYPE
		SYNTAX		Integer32 (1)
		MAX-ACCESS	not-accessible
		STATUS		current
		DESCRIPTION	"The index of Radius Server."
		::= { iswDot1xRadiusStatsEntry 1 }  
--2    
	iswDot1xRadiusAuthClientAccessRequests	OBJECT-TYPE
		SYNTAX		Unsigned32
		MAX-ACCESS	read-only
		STATUS		current
		DESCRIPTION	"The number of RADIUS Access-Request sent to RADIUS server."
		::= { iswDot1xRadiusStatsEntry 2 } 
--3    
	iswDot1xRadiusAuthClientAccessAccepts	OBJECT-TYPE
		SYNTAX		Unsigned32
		MAX-ACCESS	read-only
		STATUS		current
		DESCRIPTION	"The number of RADIUS Access-Accept received from RADIUS server."
		::= { iswDot1xRadiusStatsEntry 3 }
--4    
	iswDot1xRadiusAuthClientAccessRejects	OBJECT-TYPE
		SYNTAX		Unsigned32
		MAX-ACCESS	read-only
		STATUS		current
		DESCRIPTION	"The number of RADIUS Access-Reject received from RADIUS server."
		::= { iswDot1xRadiusStatsEntry 4 }
--5 
	iswDot1xRadiusAuthClientAccessChallenges	OBJECT-TYPE
		SYNTAX		Unsigned32
		MAX-ACCESS	read-only
		STATUS		current
		DESCRIPTION	"The number of RADIUS Access-Challenge received from RADIUS server."
		::= { iswDot1xRadiusStatsEntry 5 }
--6    
	iswDot1xRadiusAuthClientBadAuthenticators	OBJECT-TYPE
		SYNTAX		Unsigned32
		MAX-ACCESS	read-only
		STATUS		current
		DESCRIPTION	"The number of invalid RADIUS response packet received from RADIUS server."
		::= { iswDot1xRadiusStatsEntry 6 }
--7    
	iswDot1xRadiusAuthClientTimeouts	OBJECT-TYPE
		SYNTAX		Unsigned32
		MAX-ACCESS	read-only
		STATUS		current
		DESCRIPTION	"The number server timeout happened on Backend Authentication state machine."
		::= { iswDot1xRadiusStatsEntry 7 }
--8    
	iswDot1xRadiusAuthClientPacketsDropped	OBJECT-TYPE
		SYNTAX		Unsigned32
		MAX-ACCESS	read-only
		STATUS		current
		DESCRIPTION	"The number of packet from RADIUS server to be silent drop by Authenticator."
		::= { iswDot1xRadiusStatsEntry 8 }
		
	iswDot1xRadiusStatsClear	OBJECT-TYPE
		SYNTAX		Integer32 { clearAll(1) }
		MAX-ACCESS	read-write
		STATUS		current
		DESCRIPTION	"Clear Authenticator Backend statistics counters."
		::=  { iswDot1xStatistics 4 }
--
--  Event / Alarm Table
--
	iswEventTable	OBJECT-TYPE
		SYNTAX		SEQUENCE OF IswEventEntry
		MAX-ACCESS	not-accessible
		STATUS		current
		DESCRIPTION	"The Event Log table."
		::=	 { iswEvtMgt 1 }

	iswEventEntry	OBJECT-TYPE
		SYNTAX		IswEventEntry
		MAX-ACCESS	not-accessible
		STATUS		current
		DESCRIPTION	"An Entry in the Event table."
		INDEX		{ iswEventRowId }
		::=	 { iswEventTable 1 }

	IswEventEntry	 ::=	SEQUENCE {
		iswEventRowId			Integer32,
		iswEventSeqId			Unsigned32,
		iswEventEntPhyIndex		IswEntIndex,
		iswEventIfIndex			IswEventIfIndex,
		iswEventTypeId			IswEventType,
		iswEventTime			OCTET STRING,
		iswEventUserLoginIp		IpAddress,
		iswEventUserLoginMethod	INTEGER, 
		iswEventUserLoginName	OCTET STRING
		}

	iswEventRowId	OBJECT-TYPE
		SYNTAX		Integer32  ( 1 .. 256  )
		MAX-ACCESS	not-accessible
		STATUS		current
		DESCRIPTION	"This object indicates the row index in table."
		::=	 { iswEventEntry 1 }

	iswEventSeqId	OBJECT-TYPE
		SYNTAX		Unsigned32
		MAX-ACCESS	read-only
		STATUS		current
		DESCRIPTION	"This object indicates the sequnce index in table, when new event generated, index increases."
		::=	 { iswEventEntry 2 }

	iswEventEntPhyIndex	OBJECT-TYPE
		SYNTAX		IswEntIndex
		MAX-ACCESS	read-only
		STATUS		current
		DESCRIPTION	"This attribute indicates the occurrence entity.
					system(1),
					main-card(2),
					gbe-card(3)"
		::=	 { iswEventEntry 3 }

	iswEventIfIndex	OBJECT-TYPE
		SYNTAX		IswEventIfIndex
		MAX-ACCESS	read-only
		STATUS		current
		DESCRIPTION	"This attribute indicates the occurrence interface or type of alarm profile changed."
		::=	 { iswEventEntry 4 }

	iswEventTypeId	OBJECT-TYPE
		SYNTAX		IswEventType
		MAX-ACCESS	read-only
		STATUS		current
		DESCRIPTION	"This attribute indicates the number of event type."
		::=	 { iswEventEntry 5 }

	iswEventTime	OBJECT-TYPE
		SYNTAX		OCTET STRING ( SIZE ( 32 ) )
		MAX-ACCESS	read-only
		STATUS		current
		DESCRIPTION	"This attribute indicates the event occurence time."
		::=	 { iswEventEntry 6 }

	iswEventUserLoginIp	OBJECT-TYPE
		SYNTAX		IpAddress
		MAX-ACCESS	read-only
		STATUS		current
		DESCRIPTION	"Information for user login event
					iswSystemUserLoginSuccess(26), 
					iswSystemUserLoginFailure(27), 
					iswSystemLoginSessionLogout(28), 
					iswSystemLoginSessionTimeout(29), 
		"
		::=	 { iswEventEntry 7 }

	iswEventUserLoginMethod	OBJECT-TYPE
		SYNTAX	INTEGER
			{
					console(1),
					telnet(2),
					ssh(3),
					cluster(4),
					web(5)
			}
		MAX-ACCESS	read-only
		STATUS		current
		DESCRIPTION	"Information for user login event
					iswSystemUserLoginSuccess(26), 
					iswSystemUserLoginFailure(27), 
					iswSystemLoginSessionLogout(28), 
					iswSystemLoginSessionTimeout(29), 
		"
		::=	 { iswEventEntry 8 }
		
	iswEventUserLoginName	OBJECT-TYPE
		SYNTAX		OCTET STRING (SIZE (1..64))
		MAX-ACCESS	read-only
		STATUS		current
		DESCRIPTION	"Information for user login event
                iswSystemUserLoginSuccess(26), 
                iswSystemUserLoginFailure(27), 
                iswSystemLoginSessionLogout(28), 
                iswSystemLoginSessionTimeout(29), 
		"
		::=	 { iswEventEntry 9 }

	iswEventClear	OBJECT-TYPE
		SYNTAX		INTEGER	 {active(1),ready(2)}
		MAX-ACCESS	read-write
		STATUS		current
		DESCRIPTION	"Set this object active to clear system	event log."
		::=	 { iswEvtMgt 2 }

--	
--
	iswEventProfileTable	OBJECT-TYPE
		SYNTAX		SEQUENCE OF IswEventProfileEntry
		MAX-ACCESS	not-accessible
		STATUS		current
		DESCRIPTION	"Define all Alarm Event Profile ID, Mask, Level and Severity."
		::=	 { iswEvtMgt 3 }

	iswEventProfileEntry	OBJECT-TYPE
		SYNTAX		IswEventProfileEntry
		MAX-ACCESS	not-accessible
		STATUS		current
		DESCRIPTION	"Define all Alarm Event Profile ID, Mask, Level and Severity."
		INDEX		{ iswEventProfileTypeId }
		::=	 { iswEventProfileTable 1 }

	IswEventProfileEntry	::=	SEQUENCE {
		iswEventProfileTypeId			IswEventType,
		iswEventProfileMask				Integer32,
		iswEventProfileLevel			Integer32,
		iswEventProfileSyslogSeverity	Integer32
	}
	iswEventProfileTypeId	OBJECT-TYPE
		SYNTAX		IswEventType
		MAX-ACCESS	read-only
		STATUS		current
		DESCRIPTION	"Alarm Event Profile Id."
		::= { iswEventProfileEntry 1 }

	iswEventProfileMask	OBJECT-TYPE
		SYNTAX		Integer32 { mask (0), unmask (1) }
		MAX-ACCESS	read-write
		STATUS		current
		DESCRIPTION	"Alarm Event Profile Mask/UnMask, default is unMask."
		DEFVAL		{ 1 }
		::= { iswEventProfileEntry 2 }

	iswEventProfileLevel	OBJECT-TYPE
		SYNTAX		Integer32 { minor (1), major (2) }
		MAX-ACCESS	read-write
		STATUS		current
		DESCRIPTION	"Alarm Event Profile Major/Minor, default is Minor."
		DEFVAL		{ 1 }
		::= { iswEventProfileEntry 3 }

	iswEventProfileSyslogSeverity	OBJECT-TYPE
		SYNTAX		Integer32 { emergency (0), alert (1), critical (2), error (3), warning (4), notice (5), info (6) }
		MAX-ACCESS	read-write
		STATUS		current
		DESCRIPTION	"Alarm Event Profile Emergency/Alert/Critical/Error/Warning/Notice/Info, default is Info."
		DEFVAL		{ 6 }
		::= { iswEventProfileEntry 4 }

--
--
	iswCurrentAlarmTable	OBJECT-TYPE
		SYNTAX		SEQUENCE OF IswCurrentAlarmEntry
		MAX-ACCESS	not-accessible
		STATUS		current
		DESCRIPTION	"The Current Alarm table."
		::=	 { iswAlmMgt 1 }

	iswCurrentAlarmEntry	OBJECT-TYPE
		SYNTAX		IswCurrentAlarmEntry
		MAX-ACCESS	not-accessible
		STATUS		current
		DESCRIPTION	"An Entry in the event table."
		INDEX		{ iswCurrentAlarmRowId }
		::=	 { iswCurrentAlarmTable 1 }

	IswCurrentAlarmEntry	::=	SEQUENCE {
		iswCurrentAlarmRowId		Unsigned32,
		iswCurrentAlarmSeqId		Unsigned32,
		iswCurrentAlarmTypeId		IswAlarmType,
		iswCurrentAlarmIfIndex		IswAlarmIfIndex,
		iswCurrentAlarmLevel		IswAlarmLevel,
		iswCurrentAlarmState		IswAlarmState,
		iswCurrentAlarmTime			OCTET STRING
		}

	iswCurrentAlarmRowId	OBJECT-TYPE
		SYNTAX		Unsigned32	 ( 1 .. 65535 )
		MAX-ACCESS	read-only
		STATUS		current
		DESCRIPTION	"This object indicates the row index in table."
		::=	 { iswCurrentAlarmEntry 1 }

	iswCurrentAlarmSeqId	OBJECT-TYPE
		SYNTAX		Unsigned32	 ( 1 .. 65535 )
		MAX-ACCESS	read-only
		STATUS		current
		DESCRIPTION	"This object indicates the sequence index in table, when new alarm generated, index increases."
		::=	 { iswCurrentAlarmEntry 2 }

	iswCurrentAlarmTypeId	OBJECT-TYPE
		SYNTAX		IswAlarmType
		MAX-ACCESS	read-only
		STATUS		current
		DESCRIPTION	"This attribute indicates the number of alarm type."
		::=	 { iswCurrentAlarmEntry 3 }

	iswCurrentAlarmIfIndex	OBJECT-TYPE
		SYNTAX		IswAlarmIfIndex
		MAX-ACCESS	read-only
		STATUS		current
		DESCRIPTION	"This attribute indicates the occurrence interface."
		::=	 { iswCurrentAlarmEntry 4 }

	iswCurrentAlarmLevel	OBJECT-TYPE
		SYNTAX		IswAlarmLevel
		MAX-ACCESS	read-only
		STATUS		current
		DESCRIPTION	"This attribute indicates the alarm level."
		::=	 { iswCurrentAlarmEntry 5 }

	iswCurrentAlarmState	OBJECT-TYPE
		SYNTAX		IswAlarmState
		MAX-ACCESS	read-only
		STATUS		current
		DESCRIPTION	"This attribute indicates the alarm state."
		::=	 { iswCurrentAlarmEntry 6 }

	iswCurrentAlarmTime	OBJECT-TYPE
		SYNTAX		OCTET STRING (SIZE ( 32 ) )
		MAX-ACCESS	read-only
		STATUS		current
		DESCRIPTION	"This attribute indicates the alarm occurence time."
		::=	 { iswCurrentAlarmEntry 7 }
--
--
	iswHistoryAlarmTable	OBJECT-TYPE
		SYNTAX		SEQUENCE OF IswHistoryAlarmEntry
		MAX-ACCESS	not-accessible
		STATUS		current
		DESCRIPTION	"The History(Log) Alarm table."
		::=	 { iswAlmMgt 2 }

	iswHistoryAlarmEntry	OBJECT-TYPE
		SYNTAX		IswHistoryAlarmEntry
		MAX-ACCESS	not-accessible
		STATUS		current
		DESCRIPTION	"An Entry in the event hisotry table."
		INDEX		{ iswHistoryAlarmRowId }
		::=	 { iswHistoryAlarmTable 1 }

	IswHistoryAlarmEntry	::=	SEQUENCE {
		iswHistoryAlarmRowId		Unsigned32,
		iswHistoryAlarmSeqId		Unsigned32,
		iswHistoryAlarmTypeId		IswAlarmType,
		iswHistoryAlarmIfIndex		IswAlarmIfIndex,
		iswHistoryAlarmLevel		IswAlarmLevel,
		iswHistoryAlarmState		IswAlarmState,
		iswHistoryAlarmTime			OCTET STRING
		}

	iswHistoryAlarmRowId	OBJECT-TYPE
		SYNTAX		Unsigned32	 ( 1 .. 65535 )
		MAX-ACCESS	read-only
		STATUS		current
		DESCRIPTION	"This object indicates the row index in table."
		::=	 { iswHistoryAlarmEntry 1 }

	iswHistoryAlarmSeqId	OBJECT-TYPE
		SYNTAX		Unsigned32	 ( 1 .. 65535 )
		MAX-ACCESS	read-only
		STATUS		current
		DESCRIPTION	"This object indicates the sequence index in table, when new alarm generated/cleard, index increases."
		::=	 { iswHistoryAlarmEntry 2 }

	iswHistoryAlarmTypeId	OBJECT-TYPE
		SYNTAX		IswAlarmType
		MAX-ACCESS	read-only
		STATUS		current
		DESCRIPTION	"This attribute indicates the number of alarm type."
		::=	 { iswHistoryAlarmEntry 3 }

	iswHistoryAlarmIfIndex	OBJECT-TYPE
		SYNTAX		IswAlarmIfIndex
		MAX-ACCESS	read-only
		STATUS		current
		DESCRIPTION	"This attribute indicates the occurrence interface."
		::=	 { iswHistoryAlarmEntry 4 }

	iswHistoryAlarmLevel	OBJECT-TYPE
		SYNTAX		IswAlarmLevel
		MAX-ACCESS	read-only
		STATUS		current
		DESCRIPTION	"This attribute indicates the alarm level."
		::=	 { iswHistoryAlarmEntry 5 }

	iswHistoryAlarmState	OBJECT-TYPE
		SYNTAX		IswAlarmState
		MAX-ACCESS	read-only
		STATUS		current
		DESCRIPTION	"This attribute indicates the alarm state."
		::=	 { iswHistoryAlarmEntry 6 }

	iswHistoryAlarmTime	OBJECT-TYPE
		SYNTAX		OCTET STRING (SIZE ( 32 ) )
		MAX-ACCESS	read-only
		STATUS		current
		DESCRIPTION	"This attribute indicates the alarm occurence time."
		::=	 { iswHistoryAlarmEntry 7 }

--
--
	iswAlarmClear	OBJECT-TYPE
		SYNTAX		INTEGER	 {active(1),ready(2)}
		MAX-ACCESS	read-write
		STATUS		current
		DESCRIPTION	"Set this object active to clear system	alarm log."
		::=	 { iswAlmMgt 3 }
--	
--
	iswAlarmProfileTable	OBJECT-TYPE
		SYNTAX		SEQUENCE OF IswAlarmProfileEntry
		MAX-ACCESS	not-accessible
		STATUS		current
		DESCRIPTION	"Define all Alarm Profile ID, Mask, and Level."
		::=	 { iswAlmMgt 4 }

	iswAlarmProfileEntry	OBJECT-TYPE
		SYNTAX		IswAlarmProfileEntry
		MAX-ACCESS	not-accessible
		STATUS		current
		DESCRIPTION	"Define all Alarm Profile ID, Mask, and Level."
		INDEX		{ iswAlarmTypeId }
		::=	 { iswAlarmProfileTable 1 }

	IswAlarmProfileEntry	::=	SEQUENCE {
		iswAlarmTypeId		IswAlarmType,
		iswAlarmMask		IswAlarmMask,
		iswAlarmLevel		IswAlarmLevel,
		}

	iswAlarmTypeId	OBJECT-TYPE
		SYNTAX		IswAlarmType
		MAX-ACCESS	read-only
		STATUS		current
		DESCRIPTION	"Alarm Profile Id"
		::= { iswAlarmProfileEntry 1 } 

	iswAlarmMask	OBJECT-TYPE
		SYNTAX		IswAlarmMask
		MAX-ACCESS	read-write
		STATUS		current
		DESCRIPTION	"Alarm Profile Mask/UnMask, default is Mask"
		DEFVAL		{ 0 }
		::= { iswAlarmProfileEntry 2 }

	iswAlarmLevel	OBJECT-TYPE
		SYNTAX		IswAlarmLevel
		MAX-ACCESS	read-write
		STATUS		current
		DESCRIPTION	"Alarm Profile Major/Minor, default is Minor"
		DEFVAL		{ 1 }
		::= { iswAlarmProfileEntry 3 }
--
-- Traps
--
	iswEventTraps	OBJECT IDENTIFIER
		::=  { iswTraps 1 }

	iswAlarmTraps	OBJECT IDENTIFIER
		::=  { iswTraps 2 }
--
--
	iswEventSystemTraps	OBJECT IDENTIFIER
		::=  { iswEventTraps 1 }
		
	iswEventGbeTraps	OBJECT IDENTIFIER
		::=  { iswEventTraps 2 }
		
	iswEventDdmiTraps	OBJECT IDENTIFIER
		::=  { iswEventTraps 3 }
--
--
	iswTrapEvtSysRestart	NOTIFICATION-TYPE
		OBJECTS			{ iswEventSeqId, iswEventEntPhyIndex, iswEventTypeId, iswEventTime }
		STATUS			current
		DESCRIPTION		"System receives Restart command from CLI/SNMP/Web."
		::=  {  iswEventSystemTraps  1  }

	iswTrapEvtSysDownloadBegin	NOTIFICATION-TYPE
		OBJECTS			{ iswEventSeqId, iswEventEntPhyIndex, iswEventTime }
		STATUS			current
		DESCRIPTION		"Firmware download begin."
		::=  {  iswEventSystemTraps  2  }

	iswTrapEvtSysDownloadSuccess	NOTIFICATION-TYPE
		OBJECTS			{ iswEventSeqId, iswEventEntPhyIndex, iswEventTime }
		STATUS			current
		DESCRIPTION		"Firmware download Success."
		::=  {  iswEventSystemTraps  3  }
		
	iswTrapEvtSysDownloadFail	NOTIFICATION-TYPE
		OBJECTS			{ iswEventSeqId, iswEventEntPhyIndex, iswEventTime }
		STATUS			current
		DESCRIPTION		"Firmware download Fail."
		::=  {  iswEventSystemTraps  4  }
		
	iswTrapEvtSysProvisiondataExport	NOTIFICATION-TYPE
		OBJECTS			{ iswEventSeqId, iswEventEntPhyIndex, iswEventTime }
		STATUS			current
		DESCRIPTION		"System CLI configuration export."
		::=  {  iswEventSystemTraps  5  }
                        
	iswTrapEvtSysProvisiondataImport	NOTIFICATION-TYPE
		OBJECTS			{ iswEventSeqId, iswEventEntPhyIndex, iswEventTime }
		STATUS			current
		DESCRIPTION		"System CLI configuration import."
		::=  {  iswEventSystemTraps  6  }
                        
	iswTrapEvtSysProvisiondataSetdefault	NOTIFICATION-TYPE
		OBJECTS			{ iswEventSeqId, iswEventEntPhyIndex, iswEventTime }
		STATUS			current
		DESCRIPTION		"System configuration set to default."
		::=  {  iswEventSystemTraps  7  }
                        
	iswTrapEvtSysAlarmLogClear	NOTIFICATION-TYPE
		OBJECTS			{ iswEventSeqId, iswEventEntPhyIndex, iswEventTime }
		STATUS			current
		DESCRIPTION		"System alarm log table clear."
		::=  {  iswEventSystemTraps  8  }
                        
	iswTrapEvtSysEventLogClear	NOTIFICATION-TYPE
		OBJECTS			{ iswEventSeqId, iswEventEntPhyIndex, iswEventTime }
		STATUS			current
		DESCRIPTION		"System event log table clear."
		::=  {  iswEventSystemTraps  9  }

	iswTrapEvtSysRTCDateTimeChange	NOTIFICATION-TYPE
		OBJECTS			{ iswEventSeqId, iswEventEntPhyIndex, iswEventTime }
		STATUS			current
		DESCRIPTION		"System Real Time Clock time change."
		::=  {  iswEventSystemTraps  10  }

	iswTrapEvtSysAlarmProfileChange	NOTIFICATION-TYPE
		OBJECTS			{ iswEventSeqId, iswEventIfIndex, iswEventTime }
		STATUS			current
		DESCRIPTION		"System Alarm Profile change."
		::=  {  iswEventSystemTraps  11  }
                        
	iswTrapEvtSysFTPReceptionStart	NOTIFICATION-TYPE
		OBJECTS			{ iswEventSeqId, iswEventEntPhyIndex, iswEventTime }
		STATUS			current
		DESCRIPTION		"FTP Reception Start"
		::=  {  iswEventSystemTraps  12  }

	iswTrapEvtSysFTPReceptionComplete	NOTIFICATION-TYPE
		OBJECTS			{ iswEventSeqId, iswEventEntPhyIndex, iswEventTime }
		STATUS			current
		DESCRIPTION		"FTP Reception Complete."
		::=  {  iswEventSystemTraps  13  }
                        
	iswTrapEvtSysFTPReceptionIncomplete	NOTIFICATION-TYPE
		OBJECTS			{ iswEventSeqId, iswEventEntPhyIndex, iswEventTime }
		STATUS			current
		DESCRIPTION		"FTP Reception Incomplete."
		::=  {  iswEventSystemTraps  14  }
                        
	iswTrapEvtSysSNTPTimeZoneChange	NOTIFICATION-TYPE
		OBJECTS			{ iswEventSeqId, iswEventEntPhyIndex, iswEventTime }
		STATUS			current
		DESCRIPTION		"SNTP Time Zone Change."
		::=  {  iswEventSystemTraps  15  }
                        
	iswTrapEvtSysSNTPProvisionChanged	NOTIFICATION-TYPE
		OBJECTS			{ iswEventSeqId, iswEventEntPhyIndex, iswEventTime }
		STATUS			current
		DESCRIPTION		"SNTP Provision Changed."
		::=  {  iswEventSystemTraps  16  }
                        
	iswTrapEvtSysDatabaseSavingFailed	NOTIFICATION-TYPE
		OBJECTS			{ iswEventSeqId, iswEventEntPhyIndex, iswEventTime }
		STATUS			current
		DESCRIPTION		"Database Saving Failed."
		::=  {  iswEventSystemTraps  17  }
                        
	iswTrapEvtSysUserLoginSuccess	NOTIFICATION-TYPE
		OBJECTS			{ iswEventSeqId, iswEventEntPhyIndex, iswEventTime, iswEventUserLoginIp, iswEventUserLoginMethod, iswEventUserLoginName }
		STATUS			current
		DESCRIPTION		"User Login Success."
		::=  {  iswEventSystemTraps  18  }

	iswTrapEvtSysUserLoginFailure	NOTIFICATION-TYPE
		OBJECTS			{ iswEventSeqId, iswEventEntPhyIndex, iswEventTime, iswEventUserLoginIp, iswEventUserLoginMethod, iswEventUserLoginName }
		STATUS			current
		DESCRIPTION		"User Login Failure."
		::=  {  iswEventSystemTraps  19  }
                        
	iswTrapEvtSysLoginSessionLogout	NOTIFICATION-TYPE
		OBJECTS			{ iswEventSeqId, iswEventEntPhyIndex, iswEventTime, iswEventUserLoginIp, iswEventUserLoginMethod, iswEventUserLoginName }
		STATUS			current
		DESCRIPTION		"User Logout."
		::=  {  iswEventSystemTraps  20  }

	iswTrapEvtSysLoginSessionTimeout	NOTIFICATION-TYPE
		OBJECTS			{ iswEventSeqId, iswEventEntPhyIndex, iswEventTime, iswEventUserLoginIp, iswEventUserLoginMethod, iswEventUserLoginName }
		STATUS			current
		DESCRIPTION		"User kick-out due to timeout."
		::=  {  iswEventSystemTraps  21  }

	iswTrapEvtSysAlarmLEDOn	NOTIFICATION-TYPE
		OBJECTS			{ iswEventSeqId, iswEventEntPhyIndex, iswEventTime }
		STATUS			current
		DESCRIPTION		"System Alarm LED On."
		::=  {  iswEventSystemTraps  22  }

	iswTrapEvtSysAlarmLEDOff	NOTIFICATION-TYPE
		OBJECTS			{ iswEventSeqId, iswEventEntPhyIndex, iswEventTime }
		STATUS			current
		DESCRIPTION		"System Alarm LED Off."
		::=  {  iswEventSystemTraps  23  }

	iswTrapEvtSysAlarmOutPutOn	NOTIFICATION-TYPE
		OBJECTS			{ iswEventSeqId, iswEventEntPhyIndex, iswEventTime }
		STATUS			current
		DESCRIPTION		"System Alarm Output On."
		::=  {  iswEventSystemTraps  24  }

	iswTrapEvtSysAlarmOutPutOff	NOTIFICATION-TYPE
		OBJECTS			{ iswEventSeqId, iswEventEntPhyIndex, iswEventTime }
		STATUS			current
		DESCRIPTION		"System Alarm Output Off."
		::=  {  iswEventSystemTraps  25  }
                        
	iswTrapEvtSysDDMIEnabled	NOTIFICATION-TYPE
		OBJECTS			{ iswEventSeqId, iswEventEntPhyIndex, iswEventTime }
		STATUS			current
		DESCRIPTION		"System DDMI is enabled."
		::=  {  iswEventSystemTraps  26  }

	iswTrapEvtSysDDMIDisabled	NOTIFICATION-TYPE
		OBJECTS			{ iswEventSeqId, iswEventEntPhyIndex, iswEventTime }
		STATUS			current
		DESCRIPTION		"System DDMI is disabled."
		::=  {  iswEventSystemTraps  27  }

--	iswTrapEvtSysClusterInformationchanged	NOTIFICATION-TYPE
--		OBJECTS			{ iswEventSeqId, iswEventEntPhyIndex, iswEventTime }
--		STATUS			current
--		DESCRIPTION		"System Cluster Information changed."
--		::=  {  iswEventSystemTraps  28  }
                        
	iswTrapEvtGEPortLinkup	NOTIFICATION-TYPE
		OBJECTS			{ iswEventSeqId, iswEventIfIndex, iswEventTime }
		STATUS			current
		DESCRIPTION		"Specific GE port link is up."
		::=  {  iswEventGbeTraps  1  }
                        
	iswTrapEvtGEPortLinkdown	NOTIFICATION-TYPE
		OBJECTS			{ iswEventSeqId, iswEventIfIndex, iswEventTime }
		STATUS			current
		DESCRIPTION		"Specific GE port link is down."
		::=  {  iswEventGbeTraps  2  }
		
	iswTrapEvtSfpTemperatureHighAlarm	NOTIFICATION-TYPE
		OBJECTS			{ iswEventSeqId, iswEventIfIndex, iswEventTime }
		STATUS			current
		DESCRIPTION		"SFP temperature reaches high alarm."
		::=  {  iswEventDdmiTraps  1  }
		
	iswTrapEvtSfpTemperatureLowAlarm	NOTIFICATION-TYPE
		OBJECTS			{ iswEventSeqId, iswEventIfIndex, iswEventTime }
		STATUS			current
		DESCRIPTION		"SFP temperature reaches low alarm."
		::=  {  iswEventDdmiTraps  2  }
		
	iswTrapEvtSfpTemperatureHighWarn	NOTIFICATION-TYPE
		OBJECTS			{ iswEventSeqId, iswEventIfIndex, iswEventTime }
		STATUS			current
		DESCRIPTION		"SFP temperature reaches high warning."
		::=  {  iswEventDdmiTraps  3  }
	
	iswTrapEvtSfpTemperatureLowWarn		NOTIFICATION-TYPE
		OBJECTS			{ iswEventSeqId, iswEventIfIndex, iswEventTime }
		STATUS			current
		DESCRIPTION		"SFP temperature reaches low warning."
		::=  {  iswEventDdmiTraps  4  }
		
	iswTrapEvtSfpTemperatureNormal		NOTIFICATION-TYPE
		OBJECTS			{ iswEventSeqId, iswEventIfIndex, iswEventTime }
		STATUS			current
		DESCRIPTION		"SFP temperature returns to normal."
		::=  {  iswEventDdmiTraps  5  }
--
--
	iswAlarmSystemTraps	OBJECT IDENTIFIER
		::=  { iswAlarmTraps 1 }

		
	iswAlarmGbeTraps	OBJECT IDENTIFIER
		::=  { iswAlarmTraps 2 }
--
--
	iswTrapAlmGE1PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-1 port link is down."
		::=  {  iswAlarmGbeTraps  1  }

	iswTrapAlmGE2PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-2 port link is down."
		::=  {  iswAlarmGbeTraps  2  }

	iswTrapAlmGE3PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-3 port link is down."
		::=  {  iswAlarmGbeTraps  3  }

	iswTrapAlmGE4PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-4 port link is down."
		::=  {  iswAlarmGbeTraps  4  }

	iswTrapAlmGE5PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-5 port link is down."
		::=  {  iswAlarmGbeTraps  5  }

	iswTrapAlmGE6PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-6 port link is down."
		::=  {  iswAlarmGbeTraps  6  }

	iswTrapAlmGE7PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-7 port link is down."
		::=  {  iswAlarmGbeTraps  7  }

	iswTrapAlmGE8PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-8 port link is down."
		::=  {  iswAlarmGbeTraps  8  }

	iswTrapAlmGE9PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-9 port link is down."
		::=  {  iswAlarmGbeTraps  9  }

	iswTrapAlmGE10PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-10 port link is down."
		::=  {  iswAlarmGbeTraps  10  }

	iswTrapAlmGE11PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-11 port link is down."
		::=  {  iswAlarmGbeTraps  11  }

	iswTrapAlmGE12PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-12 port link is down."
		::=  {  iswAlarmGbeTraps  12  }

	iswTrapAlmGE13PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-13 port link is down."
		::=  {  iswAlarmGbeTraps  13  }

	iswTrapAlmGE14PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-14 port link is down."
		::=  {  iswAlarmGbeTraps  14  }

	iswTrapAlmGE15PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-15 port link is down."
		::=  {  iswAlarmGbeTraps  15  }

	iswTrapAlmGE16PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-16 port link is down."
		::=  {  iswAlarmGbeTraps  16  }

	iswTrapAlmGE17PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-17 port link is down."
		::=  {  iswAlarmGbeTraps  17  }

	iswTrapAlmGE18PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-18 port link is down."
		::=  {  iswAlarmGbeTraps  18  }

	iswTrapAlmGE19PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-19 port link is down."
		::=  {  iswAlarmGbeTraps  19  }

	iswTrapAlmGE20PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-20 port link is down."
		::=  {  iswAlarmGbeTraps  20  }

	iswTrapAlmGE21PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-21 port link is down."
		::=  {  iswAlarmGbeTraps  21  }

	iswTrapAlmGE22PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-22 port link is down."
		::=  {  iswAlarmGbeTraps  22  }

	iswTrapAlmGE23PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-23 port link is down."
		::=  {  iswAlarmGbeTraps  23  }

	iswTrapAlmGE24PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-24 port link is down."
		::=  {  iswAlarmGbeTraps  24  }

	iswTrapAlmGE25PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-25 port link is down."
		::=  {  iswAlarmGbeTraps  25  }

	iswTrapAlmGE26PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-26 port link is down."
		::=  {  iswAlarmGbeTraps  26  }

	iswTrapAlmGE27PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-27 port link is down."
		::=  {  iswAlarmGbeTraps  27  }

	iswTrapAlmGE28PortLinkDown	NOTIFICATION-TYPE
		OBJECTS			{ iswCurrentAlarmSeqId, iswCurrentAlarmIfIndex, iswCurrentAlarmLevel, iswCurrentAlarmState, iswCurrentAlarmTime}
		STATUS			current
		DESCRIPTION		"Specific GE-28 port link is down."
		::=  {  iswAlarmGbeTraps  28  }

	iswTrapAlmPowerAlarm	NOTIFICATION-TYPE
		OBJECTS			{ iswCurrentAlarmSeqId, iswCurrentAlarmIfIndex, iswCurrentAlarmLevel, iswCurrentAlarmState, iswCurrentAlarmTime}
		STATUS			current
		DESCRIPTION		"Specific power alarm."
		::=  {  iswAlarmGbeTraps  29  }
		
	iswTrapAlmAboveTemperature	NOTIFICATION-TYPE
		OBJECTS			{ iswCurrentAlarmSeqId, iswCurrentAlarmIfIndex, iswCurrentAlarmLevel, iswCurrentAlarmState, iswCurrentAlarmTime}
		STATUS			current
		DESCRIPTION		"Specific above temperature."
		::=  {  iswAlarmGbeTraps  30  }
		
	iswTrapAlmBelowTemperature	NOTIFICATION-TYPE
		OBJECTS			{ iswCurrentAlarmSeqId, iswCurrentAlarmIfIndex, iswCurrentAlarmLevel, iswCurrentAlarmState, iswCurrentAlarmTime}
		STATUS			current
		DESCRIPTION		"Specific below temperature."
		::=  {  iswAlarmGbeTraps  31  }
    ---
	iswDRouteTblTable	OBJECT-TYPE
        SYNTAX      SEQUENCE OF IswDRouteTblEntry
		MAX-ACCESS	not-accessible
		STATUS		current
		DESCRIPTION	"iswDRouteTblTable"
		::= { iswDvmrpConf 4 }
	---
	iswDRouteTblEntry OBJECT-TYPE
		SYNTAX		IswDRouteTblEntry
		MAX-ACCESS	not-accessible
		STATUS		current
		DESCRIPTION	"iswDRouteTblTable entry"
		INDEX		{ iswDRouteTblTableId }
		::= { iswDRouteTblTable 1 }
	---
	IswDRouteTblEntry ::= SEQUENCE{
		iswDrtId			Integer32,
		iswDrtSourceNetwork		IpAddress,
		iswDrtSourceMask		IpAddress,
		iswDrtSourcePrefixLen		Integer32,
		iswDrtRouteType			Integer32,
		iswDrtMetric			Integer32,
		iswDrtUptime			TimeTicks,
		iswDrtExpire			TimeTicks,
		iswDrtIfVlan			Integer32,
		iswDrtNeighborIp		IpAddress
	}
    ---
	iswDrtId 	OBJECT-TYPE
		SYNTAX		Integer32
		MAX-ACCESS	not-accessible
		STATUS		current
		DESCRIPTION	"iswDrtId."
		::= { iswDRouteTblEntry 1 }
	---
	iswDrtSourceNetwork	OBJECT-TYPE
		SYNTAX		IpAddress
		MAX-ACCESS	read-only
		STATUS		current
		DESCRIPTION	"Source network."
		::= { iswDRouteTblEntry 2 }
	---
	iswDrtSourceMask	OBJECT-TYPE
		SYNTAX		IpAddress
		MAX-ACCESS	read-only
		STATUS		current
		DESCRIPTION	"Source mask."
		::= { iswDRouteTblEntry 3 }
	---
	iswDrtSourcePrefixLen	OBJECT-TYPE
		SYNTAX		Integer32
		MAX-ACCESS	read-only
		STATUS		current
		DESCRIPTION	"Source prefix length."
		::= { iswDRouteTblEntry 4 }
	---
	iswDrtRouteType	OBJECT-TYPE
		SYNTAX		Integer32 { local (1), dvmrp (2) }
		MAX-ACCESS	read-only
		STATUS		current
		DESCRIPTION	"Metric of route."
		::= { iswDRouteTblEntry 5 }
	---
	iswDrtMetric	OBJECT-TYPE
		SYNTAX		Integer32
		MAX-ACCESS	read-only
		STATUS		current
		DESCRIPTION	"The route metric for the IP interface.
                    Range 1 to 32. 32 indicates infinity."
		::= { iswDRouteTblEntry 6 }
	---
	iswDrtUptime	OBJECT-TYPE
		SYNTAX		TimeTicks
		MAX-ACCESS	read-only
		STATUS		current
		DESCRIPTION	"The total of time from creating this route entry to now."
		::= { iswDRouteTblEntry 7 }
	---
	iswDrtExpire	OBJECT-TYPE
		SYNTAX		TimeTicks  
		MAX-ACCESS	read-only
		STATUS		current
		DESCRIPTION	"The minimum amount of time remaining before this entry will be aged out."
		::= { iswDRouteTblEntry 8 }
	---
	iswDrtIfVlan	OBJECT-TYPE
		SYNTAX		Integer32 ( 1 .. 4094 ) 
		MAX-ACCESS	read-only
		STATUS		current
		DESCRIPTION	"The VLAN ID of the IP interface."
		::= { iswDRouteTblEntry 9 }
	---
	---
	iswDrtNeighborIp	OBJECT-TYPE
		SYNTAX		IpAddress
		MAX-ACCESS	read-only
		STATUS		current
		DESCRIPTION	"The outgoing network address for this next hop."
		::= { iswDRouteTblEntry 10 }
	--
	--------------------------------------
	iswMcJoinTable	OBJECT-TYPE
		SYNTAX      SEQUENCE OF IswMcJoinEntry
		MAX-ACCESS	not-accessible
		STATUS		current
		DESCRIPTION	"iswMcJoinTable"
		::= { iswMc 4 }
	--
	iswMcJoinEntry OBJECT-TYPE
		SYNTAX		IswMcJoinEntry
		MAX-ACCESS	not-accessible
		STATUS		current
		DESCRIPTION	"iswMcJoinEntry"
		INDEX		{ iswMcJoinIdx }
		::= { iswMcJoinTable 1 }
	--
	IswMcJoinEntry ::= SEQUENCE{
		iswMcJoinIdx 			Integer32,
		iswMcJoinGrpIp			OCTET STRING,
		iswMcJoinNetmask		OCTET STRING,
		iswMcJoinSrcIp 			OCTET STRING,
		iswMcJoinNextHopVlanId		Integer32,
		iswMcJoinProtocol 		Integer32,
		iswMcJoinRowStatus 		RowStatus
	}
	--
	iswMcJoinIdx	OBJECT-TYPE
		SYNTAX		Integer32
		MAX-ACCESS	not-accessible
		STATUS		current
		DESCRIPTION	"Multicast join index."
		::= { iswMcJoinEntry 1 }
	--
	iswMcJoinGrpIp	OBJECT-TYPE
		SYNTAX		OCTET STRING  ( SIZE ( 1..16 ) ) 
		MAX-ACCESS	read-write	
		STATUS		current
		DESCRIPTION	"Multicast join group address."
		::= { iswMcJoinEntry 2 }
	--
	iswMcJoinNetmask	OBJECT-TYPE
		SYNTAX		OCTET STRING ( SIZE ( 1..16 ) )
		MAX-ACCESS	read-write	
		STATUS		current
		DESCRIPTION	"Multicast join group netmask."
		::= { iswMcJoinEntry 3 }
	--
	iswMcJoinSrcIp	OBJECT-TYPE
		SYNTAX		OCTET STRING ( SIZE ( 1..16 ) )
		MAX-ACCESS	read-write	
		STATUS		current
		DESCRIPTION	"Multicast join source address."
		::= { iswMcJoinEntry 4 }
	--
	iswMcJoinNextHopVlanId	OBJECT-TYPE
		SYNTAX		Integer32 ( 1 .. 4094 ) 
		MAX-ACCESS	read-write	
		STATUS		current
		DESCRIPTION	"Multicast join next hop VLAN ID."
		::= { iswMcJoinEntry 5 }
	--
	iswMcJoinProtocol	OBJECT-TYPE
		SYNTAX		Integer32 { static (1), pimDm (2), dvmrp (3) }
		MAX-ACCESS	read-write	
		STATUS		current
		DESCRIPTION	"Join to which protocol."
		::= { iswMcJoinEntry 6 }
	--
	iswMcJoinRowStatus	OBJECT-TYPE
		SYNTAX		RowStatus
		MAX-ACCESS	read-create
		STATUS		current
		DESCRIPTION	"Row Status."
		::= { iswMcJoinEntry 7 }
	--
--1
	iswLoopProtectGlobalEnable		OBJECT-TYPE
		SYNTAX		Integer32 { disable (0), enable (1) }
		MAX-ACCESS	read-write
		STATUS		current
		DESCRIPTION	"Enable/Disable system loop protection. Default is disable."
		DEFVAL		{0}
		::= { iswLoopProtectSystemConfig 1 }
		
	iswLoopProtectGlobalTransmitTime		OBJECT-TYPE
		SYNTAX		Integer32 ( 1 .. 10 ) 
		UNITS		"second"
		MAX-ACCESS	read-write
		STATUS		current
		DESCRIPTION	"The interval between each loop protection PDU sent on each port. Valid values are 1 to 10 seconds. Default value is 5 seconds."
		DEFVAL		{ 5 }
		::= { iswLoopProtectSystemConfig 2 }

	iswLoopProtectGlobalShutdownTime		OBJECT-TYPE
		SYNTAX		Integer32 ( 0 .. 604800 ) 
		UNITS		"second"
		MAX-ACCESS	read-write
		STATUS		current
		DESCRIPTION	"The period (in seconds) for which a port will be kept disabled in the event of a loop is detected (and the port action shuts down the port). 
					Valid values are 0 to 604800 seconds (7 days). A value of zero will keep a port disabled (until next device restart or loop protection disable). 
					Default value is 180 seconds."
		DEFVAL		{ 180 }
		::= { iswLoopProtectSystemConfig 3 }
	
--1
	iswLoopProtectPortConfigTable		OBJECT-TYPE
		SYNTAX		SEQUENCE OF IswLoopProtectPortConfigEntry
		MAX-ACCESS	not-accessible 
		STATUS		current
		DESCRIPTION	"Loop Protection Port Configuration Table."  
		::= { iswLoopProtectPortConfig 1 }

	iswLoopProtectPortConfigEntry		OBJECT-TYPE
		SYNTAX		IswLoopProtectPortConfigEntry
		MAX-ACCESS	not-accessible
		STATUS		current
		DESCRIPTION	"Loop Protection Port Configuration entry."
		INDEX		{ iswLoopProtectPortConfigPortIdx }
		::= { iswLoopProtectPortConfigTable 1 }
	
	IswLoopProtectPortConfigEntry ::= SEQUENCE{
		iswLoopProtectPortConfigPortIdx			IswGbeIndex,
		iswLoopProtectPortConfigPortEnable		Integer32
	}
--1
	iswLoopProtectPortConfigPortIdx		OBJECT-TYPE
		SYNTAX		IswGbeIndex
		MAX-ACCESS	not-accessible
		STATUS		current
		DESCRIPTION	"Port index."
		::= { iswLoopProtectPortConfigEntry 1 } 
--2
	iswLoopProtectPortConfigPortEnable		OBJECT-TYPE
		SYNTAX		Integer32 { disable (0), enable (1) }
		MAX-ACCESS	read-write
		STATUS		current
		DESCRIPTION	"Enable/Disable port loop protection. Default is enable."
		DEFVAL		{1}
		::= { iswLoopProtectPortConfigEntry 2 }
--1
	iswLoopProtectPortStatusTable		OBJECT-TYPE
		SYNTAX		SEQUENCE OF IswLoopProtectPortStatusEntry
		MAX-ACCESS	not-accessible 
		STATUS		current
		DESCRIPTION	"Loop Protection Port Status Table."  
		::= { iswLoopProtectPortStatus 1 }

	iswLoopProtectPortStatusEntry		OBJECT-TYPE
		SYNTAX		IswLoopProtectPortStatusEntry
		MAX-ACCESS	not-accessible
		STATUS		current
		DESCRIPTION	"Loop Protection Port Status entry."
		INDEX		{ iswLoopProtectPortStatusPortIdx }
		::= { iswLoopProtectPortStatusTable 1 }
	
	IswLoopProtectPortStatusEntry ::= SEQUENCE{
		iswLoopProtectPortStatusPortIdx			IswGbeIndex,
		iswLoopProtectPortStatusPortMode		Integer32,
		iswLoopProtectPortStatusLoops			Integer32,
		iswLoopProtectPortStatusPortStatus		Integer32,
		iswLoopProtectPortStatusLoop			Integer32,
		iswLoopProtectPortStatusLastLoopTime	OCTET STRING
	}
--1
	iswLoopProtectPortStatusPortIdx		OBJECT-TYPE
		SYNTAX		IswGbeIndex
		MAX-ACCESS	not-accessible
		STATUS		current
		DESCRIPTION	"Port index."
		::= { iswLoopProtectPortStatusEntry 1 } 
--2
	iswLoopProtectPortStatusPortMode		OBJECT-TYPE
		SYNTAX		Integer32 { disable (0), enable (1) }
		MAX-ACCESS	read-only
		STATUS		current
		DESCRIPTION	"Current port config mode."
		::= { iswLoopProtectPortStatusEntry 2 }
--3
	iswLoopProtectPortStatusLoops		OBJECT-TYPE
		SYNTAX		Integer32 
		MAX-ACCESS	read-only
		STATUS		current
		DESCRIPTION	"The number of loops detected on this port."
		::= { iswLoopProtectPortStatusEntry 3 }
--4
	iswLoopProtectPortStatusPortStatus		OBJECT-TYPE
		SYNTAX		Integer32 { down (0), up (1), disable (2)  }
		MAX-ACCESS	read-only
		STATUS		current
		DESCRIPTION	"The current link status of the port.
					down:port link status is down 
					up:port link status is up
					disable:port is disabled by loop protection."
		::= { iswLoopProtectPortStatusEntry 4 }
--5
	iswLoopProtectPortStatusLoop		OBJECT-TYPE
		SYNTAX		Integer32 { noloop (0), loop (1)  }
		MAX-ACCESS	read-only
		STATUS		current
		DESCRIPTION	"It indicates that looop detected on this port."
		::= { iswLoopProtectPortStatusEntry 5 }
--6
	iswLoopProtectPortStatusLastLoopTime		OBJECT-TYPE
		SYNTAX		OCTET STRING ( SIZE ( 19 ) )
		MAX-ACCESS	read-only
		STATUS		current
		DESCRIPTION	"The time of the last loop event detected. Format: MM/DD/YYYY HH:MM:SS. Fix length. The YYYY range is 2000~2036."
		::= { iswLoopProtectPortStatusEntry 6 }
END
