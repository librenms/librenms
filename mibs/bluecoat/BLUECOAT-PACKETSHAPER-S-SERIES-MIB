--  BLUECOAT-PACKETSHAPER-S-SERIES-MIB.my Blue Coat PacketShaper S-SERIES MIB
--  Copyright 2015 Blue Coat Systems, Inc.

    BLUECOAT-PACKETSHAPER-S-SERIES-MIB DEFINITIONS ::= BEGIN
 

        IMPORTS
            OBJECT-GROUP, MODULE-COMPLIANCE, NOTIFICATION-GROUP            
                FROM SNMPv2-CONF            
            Integer32, Gauge32, Counter32, 
            OBJECT-TYPE, MODULE-IDENTITY, OBJECT-IDENTITY, NOTIFICATION-TYPE            
                FROM SNMPv2-SMI            
            DisplayString, DateAndTime            
                FROM SNMPv2-TC
            bcsi
            	FROM BCSI-MIB;

		packetShaperS-Series MODULE-IDENTITY
			LAST-UPDATED "201404040000Z"
			ORGANIZATION "Blue Coat Systems, Inc."
			CONTACT-INFO "Internet: www.bluecoat.com
                 		  USA(Corporate) Phone: +1 866 30BCOAT or +1 408 220 2200"
			DESCRIPTION "Blue Coat PacketShaper S Series MIB"
			REVISION     "201802090000Z"
			DESCRIPTION "PacketShaper S Series MIB"

			::= { bcsi 11 }

        products       	OBJECT IDENTIFIER ::= { packetShaperS-Series 1 }
		packetShaper   	OBJECT IDENTIFIER ::= { products 1 }
		s500     		OBJECT IDENTIFIER ::= { packetShaper 1 }

        bluecoatMibs   	OBJECT IDENTIFIER ::= { packetShaperS-Series 2 }
        psCommonMibS    OBJECT IDENTIFIER ::= { bluecoatMibs 1 }
	-- specific MIB sections
		-- psTraps defined below 		  ::= { psCommonMibS 0 }
        psLinks        	OBJECT IDENTIFIER ::= { psCommonMibS 1 }
        psPartitions   	OBJECT IDENTIFIER ::= { psCommonMibS 2 }
        psClasses      	OBJECT IDENTIFIER ::= { psCommonMibS 3 }
        psAlarms       	OBJECT IDENTIFIER ::= { psCommonMibS 4 }
        psAdmin        	OBJECT IDENTIFIER ::= { psCommonMibS 5 }
        psAlarmVars     OBJECT IDENTIFIER ::= { psCommonMibS 6 }
        psAgentEvents   OBJECT IDENTIFIER ::= { psCommonMibS 8 }
        psUserEvents    OBJECT IDENTIFIER ::= { psCommonMibS 9 }
        psHighAv        OBJECT IDENTIFIER ::= { psCommonMibS 10 }

	-- psTraps group

   		-- 1.3.6.1.4.1.14501.11.2.1.0
        psTraps OBJECT-IDENTITY
            STATUS current
            DESCRIPTION 
                "Root node for PacketShaper S-Series trap types."
            ::= { psCommonMibS 0 }

		-- 1.3.6.1.4.1.14501.11.2.1.0.1
        psAlarmLicenseExpired NOTIFICATION-TYPE
            STATUS current
            DESCRIPTION
				"The license for the PacketShaper S-series has expired."
            ::= { psTraps 1 }

   		-- 1.3.6.1.4.1.14501.11.2.1.0.2
        psAlarmBCAAAPrimary NOTIFICATION-TYPE
			OBJECTS	{ psAlarmBCAAAPrimaryStatus }	
            STATUS current
            DESCRIPTION
				"The PacketShaper S-series has lost contact with the
				primary BCAAA server. The psAlarmBCAAAPrimaryStatus provides
				additonal information about the failure."
            ::= { psTraps 2 }


   		-- 1.3.6.1.4.1.14501.11.2.1.0.3
        psAlarmBCAAASecondary NOTIFICATION-TYPE
			OBJECTS	{ psAlarmBCAAASecondaryStatus }	
            STATUS current
            DESCRIPTION
				"The PacketShaper S-series has lost contact with the
				secondary BCAAA server. The psAlarmBCAAASecondaryStatus
				provides additional information about the failure."
            ::= { psTraps 3 }

   		-- 1.3.6.1.4.1.14501.11.2.1.0.4
        psAlarmPowerSystemOne NOTIFICATION-TYPE
            STATUS current
            DESCRIPTION
                "A psAlarmPowerSystemOne trap signifies that the first power
                supply of the device has failed."
            ::= { psTraps 4 }


   		-- 1.3.6.1.4.1.14501.11.2.1.0.5
        psAlarmPowerSystemTwo NOTIFICATION-TYPE
            STATUS current
            DESCRIPTION
                "A psAlarmPowerSystemTwo trap signifies that
                the second power supply of the device has failed."
            ::= { psTraps 5 }

   		-- 1.3.6.1.4.1.14501.11.2.1.0.6
        psAlarmFan NOTIFICATION-TYPE
			OBJECTS {psAlarmFanModuleID}
            STATUS current
            DESCRIPTION
                "A psAlarmFan trap signifies that one of the system fans
                of the device has failed. The psAlarmFanModuleID specifies
				which fan has failed."
            ::= { psTraps 6 }

        psAlarmVoltageSensor NOTIFICATION-TYPE
            OBJECTS { psAlarmVoltageSensorID }
            STATUS current
            DESCRIPTION
                "A psAlarmVoltageSensor trap signifies that a voltage sensor 
                has detected a voltage outside its allowed range.
                The psAlarmVoltageSensorID identifies the sensor"
            ::= { psTraps 7 }

   		-- 1.3.6.1.4.1.14501.11.2.1.0.8
        psAlarmTemperatureSensor NOTIFICATION-TYPE
            OBJECTS { psAlarmTemperatureSensorID }
            STATUS current
            DESCRIPTION
                "A psAlarmTemperatureSensor trap signifies that a temperature sensor 
                has detected a temperature outside its allowed range.
                The psAlarmTemperatureSensorID identifies the sensor"
            ::= { psTraps 8 }

   		-- 1.3.6.1.4.1.14501.11.2.1.0.9
        psAlarmMeasurementEngine NOTIFICATION-TYPE
            OBJECTS { psAlarmMeasurementEngineStatus }
            STATUS current
            DESCRIPTION
                "A psAlarmMeasurementEngine trap signifies that the Measurement
                Engine has changed to a state of less readiness, or failed on
                startup. "
            ::= { psTraps 9 }

   	    -- 1.3.6.1.4.1.14501.11.2.1.0.10
        psAlarmUserEvent NOTIFICATION-TYPE
            OBJECTS { userEventTrapName,        userEventTrapExpression, userEventTrapVariable,
                      userEventTrapElementType, userEventTrapRegid,      userEventTrapDate,
                      userEventTrapValue,       userEventTrapTarget,     userEventTrapThreshold,
                      userEventTrapRearm,       userEventTrapDayCount,   userEventTrapDayLimit }
            STATUS current
            DESCRIPTION 
                "A psAlarmUserEvent trap signifies that a user event, which has
                been registered by the user, has occurred.  The associated variables
                give more information on the event."
            ::= { psTraps 10 }

   	    -- 1.3.6.1.4.1.14501.11.2.1.0.11
        psAlarmAgentEvent NOTIFICATION-TYPE
            OBJECTS { agentEventTrapName, agentEventTrapDate, agentEventTrapType, agentEventTrapDescription }
            STATUS current
            DESCRIPTION 
                "A psAlarmAgentEvent trap signifies that an agent event, which has
                been triggered by the user, has occurred.  The associated variables
                give more information on the event."
            ::= { psTraps 11 }

   	    -- 1.3.6.1.4.1.14501.11.2.1.0.12
        psFeatureHighAvDeviceDown NOTIFICATION-TYPE
            OBJECTS { psFeatureHighAvDeviceDownStatus, psFeatureHighAvDeviceDownRouter,
                      psFeatureHighAvDeviceDownInterface }
            STATUS current
            DESCRIPTION
                "A psFeatureHighAvDeviceDown trap signifies that an interface
                or router we are tracking has gone down. If it is an interface that
                went down, the bindings will show the corresponding router and the
                name of the interface which went down. The name will be specified
                as 'unknown' if we could not resolve the interface name. But if it
                is the router that went down, the interface name will not be specified."
            ::= { psTraps 12 }

	-- the psLinks group

        linkTableSize OBJECT-TYPE
            SYNTAX Integer32 (2..2147483647)
            MAX-ACCESS read-only
            STATUS current
            DESCRIPTION
                "Number of entries in the linkTable"
            ::= { psLinks 1 }

        linkTable OBJECT-TYPE
            SYNTAX SEQUENCE OF LinkEntry
            MAX-ACCESS not-accessible
            STATUS current
            DESCRIPTION
                "A list of link entries."
            ::= { psLinks 2 }

        linkEntry OBJECT-TYPE
            SYNTAX LinkEntry
            MAX-ACCESS not-accessible
            STATUS current
            DESCRIPTION
                "A link entry containing containing statistical objects for
                a link."
            INDEX { linkIndex }
            ::= { linkTable 1 }

        LinkEntry ::=
            SEQUENCE { 
                linkIndex
                    Integer32,
                linkName
                    DisplayString,
                linkByteCount
                    Counter32,
                linkByteCountHi
                    Counter32,
                linkPkts
                    Counter32,
				linkPktsHi
		    		Counter32,
                linkDataPkts
                    Counter32,
                linkDataPktsHi
                    Counter32,
                linkReTxs
                    Counter32,
                linkReTxsHi
                    Counter32,
                linkReTxTosses
                    Counter32,
                linkReTxTossesHi
                    Counter32,
                linkCirFails
                    Counter32,
                linkCirFailsHi
                    Counter32,
                linkCirAllocs
                    Counter32,
                linkCirAllocsHi
                    Counter32,
                linkPeakTcpConns
                    Gauge32,
                linkTcpConnInits
                    Counter32,
                linkTcpConnInitsHi
                    Counter32,
                linkTcpConnExits
                    Counter32,
                linkTcpConnExitsHi
                    Counter32,
                linkTcpConnRefuses
                    Counter32,
                linkTcpConnRefusesHi
                    Counter32,
                linkTcpConnIgnores
                    Counter32,
                linkTcpConnIgnoresHi
                    Counter32,
                linkTcpConnAborts
                    Counter32,
                linkTcpConnAbortsHi
                    Counter32,
                linkTcpConnDenies
                    Counter32,
                linkTcpConnDeniesHi
                    Counter32,
                linkSize
                    Gauge32,
                linkSizeHi
                    Gauge32,
                linkRate
                    Gauge32,
                linkRateHi
                    Gauge32,
                linkPeakGuaranteedRateFlows
                    Gauge32,
                linkReTxByteCount
                    Counter32,
                linkReTxByteCountHi
                    Counter32,
                linkTotalRxPkts
                    Counter32,
                linkTotalRxPktsHi
                    Counter32,
                linkTotalTxPkts
                    Counter32,
                linkTotalTxPktsHi
                    Counter32,
                linkRxNoBufs
                    Counter32,
                linkRxNoBufsHi
                    Counter32,
                linkRxPktDrops
                    Counter32,
                linkRxPktDropsHi
                    Counter32,
                linkTxPktDrops
                    Counter32,
                linkTxPktDropsHi
                    Counter32,
                linkRxErrors
                    Counter32,
                linkRxErrorsHi
                    Counter32,
                linkTxErrors
                    Counter32,
                linkTxErrorsHi
                    Counter32,
                linkTcpAllocFails
                    Counter32,
                linkTcpAllocFailsHi
                    Counter32,
                linkIpdgAllocFails
                    Counter32,
                linkIpdgAllocFailsHi
                    Counter32,
                linkHostdbAllocFails
                    Counter32,
                linkHostdbAllocFailsHi
                    Counter32,
                linkShapingMode
                    INTEGER,
                linkAutoclassifyMode
                    INTEGER,
                linkMacSameSidePkts
                    Counter32,
                linkMacSameSidePktsHi
                    Counter32,
                linkPassthruPkts
                    Counter32,
                linkPassthruPktsHi
                    Counter32,
                linkTotalRxBytes
                    Counter32,
                linkTotalRxBytesHi
                    Counter32,
                linkTotalTxBytes
                    Counter32,
                linkTotalTxBytesHi
                    Counter32,
                linkClassChecks
                    Counter32,
                linkClassChecksHi
                    Counter32,
                linkPassthruBytes
                    Counter32,
                linkPassthruBytesHi
                    Counter32
             }

        linkIndex OBJECT-TYPE
            SYNTAX Integer32 (0..2147483647)
            MAX-ACCESS not-accessible
            STATUS current
            DESCRIPTION
                "A unique ID for a link."
            ::= { linkEntry 1 }

        linkName OBJECT-TYPE
            SYNTAX DisplayString
            MAX-ACCESS read-only
            STATUS current
            DESCRIPTION
                "A unique name for a link."
            ::= { linkEntry 2 }

        linkByteCount OBJECT-TYPE
            SYNTAX Counter32
            MAX-ACCESS read-only
            STATUS current
            DESCRIPTION
                "The byte count in the link"
            ::= { linkEntry 3 }

        linkByteCountHi OBJECT-TYPE
            SYNTAX Counter32
            MAX-ACCESS read-only
            STATUS current
            DESCRIPTION
                "The High 32 bits of byte count in the link."
            ::= { linkEntry 4 }

        linkPkts OBJECT-TYPE
            SYNTAX Counter32
            MAX-ACCESS read-only
            STATUS current
            DESCRIPTION
                "The packet count in the link"
            ::= { linkEntry 5 }

        linkPktsHi OBJECT-TYPE
            SYNTAX Counter32
            MAX-ACCESS read-only
            STATUS current
            DESCRIPTION
                "The high 32 bits of the packet count in the link"
            ::= { linkEntry 6 }

        linkDataPkts OBJECT-TYPE
            SYNTAX Counter32
            MAX-ACCESS read-only
            STATUS current
            DESCRIPTION
                "The TCP data packet count in the link"
            ::= { linkEntry 7 }

        linkDataPktsHi OBJECT-TYPE
            SYNTAX Counter32
            MAX-ACCESS read-only
            STATUS current
            DESCRIPTION
                "The high 32 bits of the TCP data packet count in the link"
            ::= { linkEntry 8 }

        linkReTxs OBJECT-TYPE
            SYNTAX Counter32
            MAX-ACCESS read-only
            STATUS current
            DESCRIPTION
                "The TCP retransmit packet count in the link"
            ::= { linkEntry 9 }

        linkReTxsHi OBJECT-TYPE
            SYNTAX Counter32
            MAX-ACCESS read-only
            STATUS current
            DESCRIPTION
                "The high 32 bits of the TCP retransmit packet count in the link"
            ::= { linkEntry 10 }

        linkReTxTosses OBJECT-TYPE
            SYNTAX Counter32
            MAX-ACCESS read-only
            STATUS current
            DESCRIPTION
                "The TCP tossed retransmit packet count in the link"
            ::= { linkEntry 11 }

        linkReTxTossesHi OBJECT-TYPE
            SYNTAX Counter32
            MAX-ACCESS read-only
            STATUS current
            DESCRIPTION
                "The high 32 bits of the TCP tossed retransmit packet count in the link"
            ::= { linkEntry 12 }

        linkCirFails OBJECT-TYPE
            SYNTAX Counter32
            MAX-ACCESS read-only
            STATUS current
            DESCRIPTION
                "The count of CIR fails events in the link"
            ::= { linkEntry 13 }

        linkCirFailsHi OBJECT-TYPE
            SYNTAX Counter32
            MAX-ACCESS read-only
            STATUS current
            DESCRIPTION
                "The high 32 bits of the count of CIR fails events in the link"
            ::= { linkEntry 14 }

        linkCirAllocs OBJECT-TYPE
            SYNTAX Counter32
            MAX-ACCESS read-only
            STATUS current
            DESCRIPTION
                "The count of CIR alloc events in the link"
            ::= { linkEntry 15 }

        linkCirAllocsHi OBJECT-TYPE
            SYNTAX Counter32
            MAX-ACCESS read-only
            STATUS current
            DESCRIPTION
                "The high 32 bits of the count of CIR alloc events in the link"
            ::= { linkEntry 16 }

        linkPeakTcpConns OBJECT-TYPE
            SYNTAX Gauge32
            MAX-ACCESS read-only
            STATUS current
            DESCRIPTION
                "The peak number of active TCP flows in the link."
            ::= { linkEntry 17 }

        linkTcpConnInits OBJECT-TYPE
            SYNTAX Counter32
            MAX-ACCESS read-only
            STATUS current
            DESCRIPTION
                "The count of TCP flows started in the link"
            ::= { linkEntry 18 }

        linkTcpConnInitsHi OBJECT-TYPE
            SYNTAX Counter32
            MAX-ACCESS read-only
            STATUS current
            DESCRIPTION
                "The high 32 bits of the count of TCP flows started in the link"
            ::= { linkEntry 19 }

        linkTcpConnExits OBJECT-TYPE
            SYNTAX Counter32
            MAX-ACCESS read-only
            STATUS current
            DESCRIPTION
                "The count of TCP flows exited in the link"
            ::= { linkEntry 20 }

        linkTcpConnExitsHi OBJECT-TYPE
            SYNTAX Counter32
            MAX-ACCESS read-only
            STATUS current
            DESCRIPTION
                "The high 32 bits of the count of TCP flows exited in the link"
            ::= { linkEntry 21 }

       linkTcpConnRefuses OBJECT-TYPE
            SYNTAX Counter32
            MAX-ACCESS read-only
            STATUS current
            DESCRIPTION
                "The count of TCP flows exited by TCP refuse in the link"
            ::= { linkEntry 22 }

       linkTcpConnRefusesHi OBJECT-TYPE
            SYNTAX Counter32
            MAX-ACCESS read-only
            STATUS current
            DESCRIPTION
                "The high 32 bits of the count of TCP flows exited by TCP refuse in the link"
            ::= { linkEntry 23 }

        linkTcpConnIgnores OBJECT-TYPE
            SYNTAX Counter32
            MAX-ACCESS read-only
            STATUS current
            DESCRIPTION
                "The count of TCP flows exited by being ignored in the link."
            ::= { linkEntry 24 }

        linkTcpConnIgnoresHi OBJECT-TYPE
            SYNTAX Counter32
            MAX-ACCESS read-only
            STATUS current
            DESCRIPTION
                "The high 32 bits of the count of TCP flows exited by being ignored in the link."
            ::= { linkEntry 25 }

        linkTcpConnAborts OBJECT-TYPE
            SYNTAX Counter32
            MAX-ACCESS read-only
            STATUS current
            DESCRIPTION
                "The count of TCP flows aborted in the link."
            ::= { linkEntry 26 }

        linkTcpConnAbortsHi OBJECT-TYPE
            SYNTAX Counter32
            MAX-ACCESS read-only
            STATUS current
            DESCRIPTION
                "The high 32 bits of the count of TCP flows aborted in the link."
            ::= { linkEntry 27 }

        linkTcpConnDenies OBJECT-TYPE
            SYNTAX Counter32
            MAX-ACCESS read-only
            STATUS current
            DESCRIPTION
                "The count of TCP flows denied by CIR fail in the link."
            ::= { linkEntry 28 }

        linkTcpConnDeniesHi OBJECT-TYPE
            SYNTAX Counter32
            MAX-ACCESS read-only
            STATUS current
            DESCRIPTION
                "The high 32 bits of the count of TCP flows denied by CIR fail in the link."
            ::= { linkEntry 29 }

		linkSize OBJECT-TYPE
            SYNTAX Gauge32
            MAX-ACCESS read-only
            STATUS current
            DESCRIPTION
                "The size of the link in bps."
            ::= { linkEntry 30 }

        linkSizeHi OBJECT-TYPE
            SYNTAX Gauge32
            MAX-ACCESS read-only
            STATUS current
            DESCRIPTION
                "The high 32 bits of the size of the link in bps."
            ::= { linkEntry 31 }

        linkRate OBJECT-TYPE
            SYNTAX Gauge32
            MAX-ACCESS read-only
            STATUS current
            DESCRIPTION
                "The peak bps of the link."
            ::= { linkEntry 32 }

        linkRateHi OBJECT-TYPE
            SYNTAX Gauge32
            MAX-ACCESS read-only
            STATUS current
            DESCRIPTION
                "The  high 32 bits of the peak bps of the link."
            ::= { linkEntry 33 }

       linkPeakGuaranteedRateFlows OBJECT-TYPE
            SYNTAX Gauge32
            MAX-ACCESS read-only
            STATUS current
            DESCRIPTION
                "The peak number of guaranteed rate flows active on the link."
            ::= { linkEntry 34 }

       linkReTxByteCount OBJECT-TYPE
            SYNTAX Counter32
            MAX-ACCESS read-only
            STATUS current
            DESCRIPTION
                "The count of retransmitted bytes on the link."
            ::= { linkEntry 35 }

        linkReTxByteCountHi OBJECT-TYPE
            SYNTAX Counter32
            MAX-ACCESS read-only
            STATUS current
            DESCRIPTION
                "The high 32 bits of the count of retransmitted bytes on the link"
            ::= { linkEntry 36 }

        linkTotalRxPkts OBJECT-TYPE
            SYNTAX Counter32
            MAX-ACCESS read-only
            STATUS current
            DESCRIPTION
                "The total packets received on the link."
            ::= { linkEntry 37 }

        linkTotalRxPktsHi OBJECT-TYPE
            SYNTAX Counter32
            MAX-ACCESS read-only
            STATUS current
            DESCRIPTION
                "The high 32 bits of the total packets received on the link."
            ::= { linkEntry 38 }

        linkTotalTxPkts OBJECT-TYPE
            SYNTAX Counter32
            MAX-ACCESS read-only
            STATUS current
            DESCRIPTION
                "The total packets transmitted on the link."
            ::= { linkEntry 39 }

        linkTotalTxPktsHi OBJECT-TYPE
            SYNTAX Counter32
            MAX-ACCESS read-only
            STATUS current
            DESCRIPTION
                "The high 32 bits of the total packets transmitted on the link."
            ::= { linkEntry 40 }

       linkRxNoBufs OBJECT-TYPE
            SYNTAX Counter32
            MAX-ACCESS read-only
            STATUS current
            DESCRIPTION
                "The count of packets that were dropped due to unavailable buffers."
            ::= { linkEntry 41 }

        linkRxNoBufsHi OBJECT-TYPE
            SYNTAX Counter32
            MAX-ACCESS read-only
            STATUS current
            DESCRIPTION
                "The high 32 bits of the count of packets that were dropped 
		due to unavailable buffers."
            ::= { linkEntry 42 }

        linkRxPktDrops OBJECT-TYPE
            SYNTAX Counter32
            MAX-ACCESS read-only
            STATUS current
            DESCRIPTION
                "The count of packets dropped due to no buffers, no connection blocks or random dropping."
            ::= { linkEntry 43 }

        linkRxPktDropsHi OBJECT-TYPE
            SYNTAX Counter32
            MAX-ACCESS read-only
            STATUS current
            DESCRIPTION
                "The high 32 bits of the count of packets dropped due to no buffers, 
		no connection blocks or random dropping."
            ::= { linkEntry 44 }

        linkTxPktDrops OBJECT-TYPE
            SYNTAX Counter32
            MAX-ACCESS read-only
            STATUS current
            DESCRIPTION
                "The count of transmitted packets that were dropped due to no route available, 
		an i/o error or no buffers."
            ::= { linkEntry 45 }

        linkTxPktDropsHi OBJECT-TYPE
            SYNTAX Counter32
            MAX-ACCESS read-only
            STATUS current
            DESCRIPTION
                "The high 32 bits of the count of transmitted packets that were dropped due to 
		no route available, an i/o error or no buffers."
            ::= { linkEntry 46 }

      	linkRxErrors OBJECT-TYPE
            SYNTAX Counter32
            MAX-ACCESS read-only
            STATUS current
            DESCRIPTION
                "The count of received packets that were dropped due to hardware errors."
            ::= { linkEntry 47 }

        linkRxErrorsHi OBJECT-TYPE
            SYNTAX Counter32
            MAX-ACCESS read-only
            STATUS current
            DESCRIPTION
                "The high 32 bits of the count of received packets that were dropped due to hardware errors."
            ::= { linkEntry 48 }

        linkTxErrors OBJECT-TYPE
            SYNTAX Counter32
            MAX-ACCESS read-only
            STATUS current
            DESCRIPTION
                "The count of transmitted packets that were dropped due to hardware errors."
            ::= { linkEntry 49 }

        linkTxErrorsHi OBJECT-TYPE
            SYNTAX Counter32
            MAX-ACCESS read-only
            STATUS current
            DESCRIPTION
                "The high 32 bits of the count of transmitted packets that were dropped due to hardware errors."
            ::= { linkEntry 50 }

        linkTcpAllocFails OBJECT-TYPE
            SYNTAX Counter32
            MAX-ACCESS read-only
            STATUS current
            DESCRIPTION
                "The count of TCP alloc fails on a link."
            ::= { linkEntry 51 }

        linkTcpAllocFailsHi OBJECT-TYPE
            SYNTAX Counter32
            MAX-ACCESS read-only
            STATUS current
            DESCRIPTION
                "The high 32 bits of the count of TCP alloc fails on a link."
            ::= { linkEntry 52 }

        linkIpdgAllocFails OBJECT-TYPE
            SYNTAX Counter32
            MAX-ACCESS read-only
            STATUS current
            DESCRIPTION
                "The count of IPDG alloc fails on a link."
            ::= { linkEntry 53 }

        linkIpdgAllocFailsHi OBJECT-TYPE
            SYNTAX Counter32
            MAX-ACCESS read-only
            STATUS current
            DESCRIPTION
                "The high 32 bits of the count of IPDG alloc fails on a link."
            ::= { linkEntry 54 }

      	linkHostdbAllocFails OBJECT-TYPE
            SYNTAX Counter32
            MAX-ACCESS read-only
            STATUS current
            DESCRIPTION
                "The count of Host DB alloc fails on a link."
            ::= { linkEntry 55 }

      	linkHostdbAllocFailsHi OBJECT-TYPE
            SYNTAX Counter32
            MAX-ACCESS read-only
            STATUS current
            DESCRIPTION
                "The high 32 bits of the count of Host DB alloc fails on a link."
            ::= { linkEntry 56 }

        linkShapingMode OBJECT-TYPE
            SYNTAX INTEGER
                {
                off(1),
                on(2),
                watch(4)
                }
            MAX-ACCESS read-only
            STATUS current
            DESCRIPTION
                "The current shaping mode."
            ::= { linkEntry 57 }

        linkAutoclassifyMode OBJECT-TYPE
            SYNTAX INTEGER
                {
                off(1),
                on(2)
                }
            MAX-ACCESS read-only
            STATUS current
            DESCRIPTION
                "The current autoclassification mode."
            ::= { linkEntry 58 }

        linkMacSameSidePkts OBJECT-TYPE
            SYNTAX Counter32
            MAX-ACCESS read-only
            STATUS current
            DESCRIPTION
                "The total number of same-side packets on the link."
            ::= { linkEntry 59 }

        linkMacSameSidePktsHi OBJECT-TYPE
            SYNTAX Counter32
            MAX-ACCESS read-only
            STATUS current
            DESCRIPTION
                "The high 32 bits of the total number of same-side packets on the link."
            ::= { linkEntry 60 }

      	linkPassthruPkts OBJECT-TYPE
            SYNTAX Counter32
            MAX-ACCESS read-only
            STATUS current
            DESCRIPTION
                "The total packets passed through on the link."
            ::= { linkEntry 61 }

        linkPassthruPktsHi OBJECT-TYPE
            SYNTAX Counter32
            MAX-ACCESS read-only
            STATUS current
            DESCRIPTION
                "The high 32 bits of the total packets passed through on the link."
            ::= { linkEntry 62 }

        linkTotalRxBytes OBJECT-TYPE
            SYNTAX Counter32
            MAX-ACCESS read-only
            STATUS current
            DESCRIPTION
                "The total number of bytes received on the link."
            ::= { linkEntry 63 }

        linkTotalRxBytesHi OBJECT-TYPE
            SYNTAX Counter32
            MAX-ACCESS read-only
            STATUS current
            DESCRIPTION
                "The high 32 bits of the total number of bytes received on the link."
            ::= { linkEntry 64 }

        linkTotalTxBytes OBJECT-TYPE
            SYNTAX Counter32
            MAX-ACCESS read-only
            STATUS current
            DESCRIPTION
                "The total number of bytes transmitted on the link."
            ::= { linkEntry 65 }

        linkTotalTxBytesHi OBJECT-TYPE
            SYNTAX Counter32
            MAX-ACCESS read-only
            STATUS current
            DESCRIPTION
                "The high 32 bits of the total number of bytes transmitted on the link."
            ::= { linkEntry 66 }

        linkClassChecks OBJECT-TYPE
            SYNTAX Counter32
            MAX-ACCESS read-only
            STATUS current
            DESCRIPTION
                "The number of traversals of the class tree."
            ::= { linkEntry 67 }

        linkClassChecksHi OBJECT-TYPE
            SYNTAX Counter32
            MAX-ACCESS read-only
            STATUS current
            DESCRIPTION
                "The high 32 bits of the number of traversals of the class tree."
            ::= { linkEntry 68 }

        linkPassthruBytes OBJECT-TYPE
            SYNTAX Counter32
            MAX-ACCESS read-only
            STATUS current
            DESCRIPTION
                "The total number of bytes passed through on the link."
            ::= { linkEntry 69 }

        linkPassthruBytesHi OBJECT-TYPE
            SYNTAX Counter32
            MAX-ACCESS read-only
            STATUS current
            DESCRIPTION
                "The high 32 bits of the total number of bytes passed through on the link."
            ::= { linkEntry 70 }


	-- the psPartitions group

      	partitionTableSize OBJECT-TYPE
            SYNTAX Integer32 (2..2147483647)
            MAX-ACCESS read-only
            STATUS current
            DESCRIPTION
                "Number of entries in the partitionTable"
            ::= { psPartitions 1 }

        partitionTable OBJECT-TYPE
            SYNTAX SEQUENCE OF PartitionEntry
            MAX-ACCESS not-accessible
            STATUS current
            DESCRIPTION
                "A list of partition entries."
            ::= { psPartitions 2 }

        partitionEntry OBJECT-TYPE
            SYNTAX PartitionEntry
            MAX-ACCESS not-accessible
            STATUS current
            DESCRIPTION
                "A partition entry containing statistical objects for a
                traffic partition."
            INDEX { partitionIndex }
            ::= { partitionTable 1 }

        PartitionEntry ::=
            SEQUENCE { 
                partitionIndex
                    Integer32,
                partitionName
                    DisplayString,
                partitionLinkDirection
                    INTEGER,
                partitionByteCount
                    Counter32,
                partitionByteCountHi
                    Counter32,
                partitionPkts
                    Counter32,
                partitionPktsHi
                    Counter32,
                partitionDataPkts
                    Counter32,
                partitionDataPktsHi
                    Counter32,
                partitionReTxs
                    Counter32,
                partitionReTxsHi
                    Counter32,
                partitionReTxTosses
                    Counter32,
                partitionReTxTossesHi
                    Counter32,
                partitionCirFails
                    Counter32,
                partitionCirFailsHi
                    Counter32,
                partitionCirAllocs
                    Counter32,
                partitionCirAllocsHi
                    Counter32,
                partitionPeakTcpConns
                    Gauge32,
                partitionTcpConnInits
                    Counter32,
                partitionTcpConnInitsHi
                    Counter32,
                partitionTcpConnExits
                    Counter32,
                partitionTcpConnExitsHi
                    Counter32,
                partitionTcpConnRefuses
                    Counter32,
                partitionTcpConnRefusesHi
                    Counter32,
                partitionTcpConnIgnores
                    Counter32,
                partitionTcpConnIgnoresHi
                    Counter32,
                partitionTcpConnAborts
                    Counter32,
                partitionTcpConnAbortsHi
                    Counter32,
                partitionTcpConnDenies
                    Counter32,
                partitionTcpConnDeniesHi
                    Counter32,
                partitionMinimumBps
                   	Gauge32,
                partitionMinimumBpsHi
                    Gauge32,
                partitionBurstLimit
                    Gauge32,
                partitionBurstLimitHi
                    Gauge32,
                partitionRate
                    Gauge32,
                partitionRateHi
                    Gauge32,
                partitionFirstSatisfiedPriority
                    Gauge32,
                partitionTimeOverLimit
                    Counter32,
                partitionPeakGuaranteedRateFlows
                    Gauge32,
                partitionReTxByteCount
                    Counter32,
                partitionReTxByteCountHi
                    Counter32,
                partitionDynamicCapCount
                    Counter32,
                partitionDynamicNoCount
                    Counter32,
                partitionDynamicLiveUserCount
                    Gauge32,
                partitionCommittmentFailures
                    Counter32,
                partitionLateDropPktCount
                    Gauge32,
                partitionLateDropPktCountHi
                    Gauge32,
                partitionLateDropByteCount
                    Gauge32,
                partitionLateDropByteCountHi
                    Gauge32,
                partitionSchedDropPktCount
                    Gauge32,
                partitionSchedDropPktCountHi
                    Gauge32,
                partitionSchedDropByteCount
                    Gauge32,
                partitionSchedDropByteCountHi
                    Gauge32,
                partitionFrameBytes
                    Counter32,
                partitionFrameBytesHi
                    Counter32,
                partitionFrameTargetRate
                    Gauge32,
                partitionFrameTargetRateHi
                    Gauge32,
                partitionFrameCount
                    Counter32,
                partitionFrameCountHi
                    Counter32,
                partitionEcnCount
                    Counter32,
                partitionEcnCountHi
                    Counter32
             }

        partitionIndex OBJECT-TYPE
            SYNTAX Integer32 (0..2147483647)
            MAX-ACCESS not-accessible 
            STATUS current
            DESCRIPTION
                "A unique ID for a  partition."
            ::= { partitionEntry 1 }

        partitionName OBJECT-TYPE
            SYNTAX DisplayString
            MAX-ACCESS read-only
            STATUS current
            DESCRIPTION
                "A unique name for a partition."
            ::= { partitionEntry 2 }

        partitionLinkDirection OBJECT-TYPE
            SYNTAX INTEGER
                {
                inBound(1),
                outBound(2)
                }
            MAX-ACCESS read-only
            STATUS current
            DESCRIPTION
                "The orientation of a partition."
            ::= { partitionEntry 3 }

        partitionByteCount OBJECT-TYPE
            SYNTAX Counter32
            MAX-ACCESS read-only
            STATUS current
            DESCRIPTION
                "The byte count in the partition"
            ::= { partitionEntry 4 }

        partitionByteCountHi OBJECT-TYPE
            SYNTAX Counter32
            MAX-ACCESS read-only
            STATUS current
            DESCRIPTION
                "The high 32 bits of byte count in the partition."
            ::= { partitionEntry 5 }

        partitionPkts OBJECT-TYPE
            SYNTAX Counter32
            MAX-ACCESS read-only
            STATUS current
            DESCRIPTION
                "The packet count in the partition."
            ::= { partitionEntry 6 }

        partitionPktsHi OBJECT-TYPE
            SYNTAX Counter32
            MAX-ACCESS read-only
            STATUS current
            DESCRIPTION
                "The high 32 bits of the packet count in the partition."
            ::= { partitionEntry 7 }

        partitionDataPkts OBJECT-TYPE
            SYNTAX Counter32
            MAX-ACCESS read-only
            STATUS current
            DESCRIPTION
                "The TCP data packet count in the partition."
            ::= { partitionEntry 8 }

        partitionDataPktsHi OBJECT-TYPE
            SYNTAX Counter32
            MAX-ACCESS read-only
            STATUS current
            DESCRIPTION
                "The high 32 bits of the TCP data packet count in the partition."
            ::= { partitionEntry 9 }

        partitionReTxs OBJECT-TYPE
            SYNTAX Counter32
            MAX-ACCESS read-only
            STATUS current
            DESCRIPTION
                "The TCP retransmit packet count in the partition."
            ::= { partitionEntry 10 }

        partitionReTxsHi OBJECT-TYPE
            SYNTAX Counter32
            MAX-ACCESS read-only
            STATUS current
            DESCRIPTION
                "The high 32 bits of the TCP retransmit packet count in the partition."
            ::= { partitionEntry 11 }

        partitionReTxTosses OBJECT-TYPE
            SYNTAX Counter32
            MAX-ACCESS read-only
            STATUS current
            DESCRIPTION
                "The TCP tossed retransmit packet count in the partition"
            ::= { partitionEntry 12 }

        partitionReTxTossesHi OBJECT-TYPE
            SYNTAX Counter32
            MAX-ACCESS read-only
            STATUS current
            DESCRIPTION
                "The high 32 bits of the TCP tossed retransmit packet count in the partition"
            ::= { partitionEntry 13 }

        partitionCirFails OBJECT-TYPE
            SYNTAX Counter32
            MAX-ACCESS read-only
            STATUS current
            DESCRIPTION
                "The count of CIR fail events in the partition."
            ::= { partitionEntry 14 }

        partitionCirFailsHi OBJECT-TYPE
            SYNTAX Counter32
            MAX-ACCESS read-only
            STATUS current
            DESCRIPTION
                "The high 32 bits of the count of CIR fail events in the partition."
            ::= { partitionEntry 15 }

        partitionCirAllocs OBJECT-TYPE
            SYNTAX Counter32
            MAX-ACCESS read-only
            STATUS current
            DESCRIPTION
                "The count of CIR alloc events in the partition."
            ::= { partitionEntry 16 }

        partitionCirAllocsHi OBJECT-TYPE
            SYNTAX Counter32
            MAX-ACCESS read-only
            STATUS current
            DESCRIPTION
                "The high 32 bits of the count of CIR alloc events in the partition."
            ::= { partitionEntry 17 }

        partitionPeakTcpConns OBJECT-TYPE
            SYNTAX Gauge32
            MAX-ACCESS read-only
            STATUS current
            DESCRIPTION
                "The peak no. of active TCP flows in the partition."
            ::= { partitionEntry 18 }

        partitionTcpConnInits OBJECT-TYPE
            SYNTAX Counter32
            MAX-ACCESS read-only
            STATUS current
            DESCRIPTION
                "The count of TCP flows started in the partition."
            ::= { partitionEntry 19 }

        partitionTcpConnInitsHi OBJECT-TYPE
            SYNTAX Counter32
            MAX-ACCESS read-only
            STATUS current
            DESCRIPTION
                "The high 32 bits of the count of TCP flows started in the partition."
            ::= { partitionEntry 20 }

      	partitionTcpConnExits OBJECT-TYPE
            SYNTAX Counter32
            MAX-ACCESS read-only
            STATUS current
            DESCRIPTION
                "The count of TCP flows exited in the partition."
            ::= { partitionEntry 21 }

      	partitionTcpConnExitsHi OBJECT-TYPE
            SYNTAX Counter32
            MAX-ACCESS read-only
            STATUS current
            DESCRIPTION
                "The high 32 bits of the count of TCP flows exited in the partition."
            ::= { partitionEntry 22 }

        partitionTcpConnRefuses OBJECT-TYPE
            SYNTAX Counter32
            MAX-ACCESS read-only
            STATUS current
            DESCRIPTION
                "The count of TCP flows exited by TCP refuse in the partition."
            ::= { partitionEntry 23 }

        partitionTcpConnRefusesHi OBJECT-TYPE
            SYNTAX Counter32
            MAX-ACCESS read-only
            STATUS current
            DESCRIPTION
                "The high 32 bits of the count of TCP flows exited by TCP refuse in the partition."
            ::= { partitionEntry 24 }

        partitionTcpConnIgnores OBJECT-TYPE
            SYNTAX Counter32
            MAX-ACCESS read-only
            STATUS current
            DESCRIPTION
                "The count of TCP flows exited by being ignored in the partition."
            ::= { partitionEntry 25 }

        partitionTcpConnIgnoresHi OBJECT-TYPE
            SYNTAX Counter32
            MAX-ACCESS read-only
            STATUS current
            DESCRIPTION
                "The high 32 bits of the count of TCP flows exited by being ignored in the partition."
            ::= { partitionEntry 26 }

        partitionTcpConnAborts OBJECT-TYPE
            SYNTAX Counter32
            MAX-ACCESS read-only
            STATUS current
            DESCRIPTION
                "The count of TCP flows aborted in the partition."
            ::= { partitionEntry 27 }

        partitionTcpConnAbortsHi OBJECT-TYPE
            SYNTAX Counter32
            MAX-ACCESS read-only
            STATUS current
            DESCRIPTION
                "The high 32 bits of the count of TCP flows aborted in the partition."
            ::= { partitionEntry 28 }

        partitionTcpConnDenies OBJECT-TYPE
            SYNTAX Counter32
            MAX-ACCESS read-only
            STATUS current
            DESCRIPTION
                "The count of TCP flows denied by CIR fail in the partition."
            ::= { partitionEntry 29 }

        partitionTcpConnDeniesHi OBJECT-TYPE
            SYNTAX Counter32
            MAX-ACCESS read-only
            STATUS current
            DESCRIPTION
                "The high 32 bits of the count of TCP flows denied by CIR fail in the partition."
            ::= { partitionEntry 30 }

       	partitionMinimumBps OBJECT-TYPE
            SYNTAX Gauge32
            MAX-ACCESS read-only
            STATUS current
            DESCRIPTION
                "The minimum size in bps of the partition."
            ::= { partitionEntry 31 }

        partitionMinimumBpsHi OBJECT-TYPE
            SYNTAX Gauge32
            MAX-ACCESS read-only
            STATUS current
            DESCRIPTION
                "The minimum size in bps of the partition."
            ::= { partitionEntry 32 }

        partitionBurstLimit OBJECT-TYPE
            SYNTAX Gauge32
            MAX-ACCESS read-only
            STATUS current
            DESCRIPTION
                "The partition burst limit in bps."
            ::= { partitionEntry 33 }

        partitionBurstLimitHi OBJECT-TYPE
            SYNTAX Gauge32
            MAX-ACCESS read-only
            STATUS current
            DESCRIPTION
                "The partition burst limit in bps."
            ::= { partitionEntry 34 }

        partitionRate OBJECT-TYPE
            SYNTAX Gauge32
            MAX-ACCESS read-only
            STATUS current
            DESCRIPTION
                "The peak total rate in bps of the partition."
            ::= { partitionEntry 35 }

        partitionRateHi OBJECT-TYPE
            SYNTAX Gauge32
            MAX-ACCESS read-only
            STATUS current
            DESCRIPTION
                "The peak total rate in bps of the partition."
            ::= { partitionEntry 36 }

     	partitionFirstSatisfiedPriority OBJECT-TYPE
            SYNTAX Gauge32
            MAX-ACCESS read-only
            STATUS current
            DESCRIPTION
                "The peak first priority level at which demand was satisfied (0-8)."
            ::= { partitionEntry 37 }

        partitionTimeOverLimit OBJECT-TYPE
            SYNTAX Counter32
            MAX-ACCESS read-only
            STATUS current
            DESCRIPTION
                "The total time in seconds spent over partition
                size for the partition"
            ::= { partitionEntry 38 }

      	partitionPeakGuaranteedRateFlows OBJECT-TYPE
            SYNTAX Gauge32
            MAX-ACCESS read-only
            STATUS current
            DESCRIPTION
                "The peak number of guaranteed rate flows active on the partition."
            ::= { partitionEntry 39 }

        partitionReTxByteCount OBJECT-TYPE
            SYNTAX Counter32
            MAX-ACCESS read-only
            STATUS current
            DESCRIPTION
                "The count of retransmitted bytes on the partition.  This is the
                low-order 32 bits."
            ::= { partitionEntry 40 }

        partitionReTxByteCountHi OBJECT-TYPE
            SYNTAX Counter32
            MAX-ACCESS read-only
            STATUS current
            DESCRIPTION
                "The high 32 bits of the count of retransmitted bytes on the partition."
            ::= { partitionEntry 41 }

        partitionDynamicCapCount OBJECT-TYPE
            SYNTAX Counter32
            MAX-ACCESS read-only
            STATUS current
            DESCRIPTION
                "The count of dynamic partition reaching caps."
            ::= { partitionEntry 42 }

        partitionDynamicNoCount OBJECT-TYPE
            SYNTAX Counter32
            MAX-ACCESS read-only
            STATUS current
            DESCRIPTION
                "The count of unavailable dynamic partition ."
            ::= { partitionEntry 43 }

        partitionDynamicLiveUserCount OBJECT-TYPE
            SYNTAX Gauge32
            MAX-ACCESS read-only
            STATUS current
            DESCRIPTION
                "The count of total live dynamic partition user."
            ::= { partitionEntry 44 }

        partitionCommittmentFailures OBJECT-TYPE
            SYNTAX Counter32
            MAX-ACCESS read-only
            STATUS current
            DESCRIPTION
                "The number of minute intervals that were not given the minimum programmed bandwidth."
            ::= { partitionEntry 45 }

        partitionLateDropPktCount OBJECT-TYPE
            SYNTAX Gauge32
            MAX-ACCESS read-only
            STATUS current
            DESCRIPTION
                "The count of number of late drops in the partition."
            ::= { partitionEntry 46 }

        partitionLateDropPktCountHi OBJECT-TYPE
            SYNTAX Gauge32
            MAX-ACCESS read-only
            STATUS current
            DESCRIPTION
                "The high 32 bits of the count of number of late drops in the partition."
            ::= { partitionEntry 47 }

        partitionLateDropByteCount OBJECT-TYPE
            SYNTAX Gauge32
            MAX-ACCESS read-only
            STATUS current
            DESCRIPTION
                "The count of late drop bytes in the partition."
            ::= { partitionEntry 48 }

        partitionLateDropByteCountHi OBJECT-TYPE
            SYNTAX Gauge32
            MAX-ACCESS read-only
            STATUS current
            DESCRIPTION
                "The high 32 bits of the count of late drop bytes in the partition"
            ::= { partitionEntry 49 }

        partitionSchedDropPktCount OBJECT-TYPE
            SYNTAX Gauge32
            MAX-ACCESS read-only
            STATUS current
            DESCRIPTION
                "The count of number of scheduler drops in the partition."
            ::= { partitionEntry 50 }

        partitionSchedDropPktCountHi OBJECT-TYPE
            SYNTAX Gauge32
            MAX-ACCESS read-only
            STATUS current
            DESCRIPTION
                "The high 32 bits of the count of number of scheduler drops in the partition."
            ::= { partitionEntry 51 }

        partitionSchedDropByteCount OBJECT-TYPE
            SYNTAX Gauge32
            MAX-ACCESS read-only
            STATUS current
            DESCRIPTION
                "The count of scheduler drop bytes in the partition."
            ::= { partitionEntry 52 }

        partitionSchedDropByteCountHi OBJECT-TYPE
            SYNTAX Gauge32
            MAX-ACCESS read-only
            STATUS current
            DESCRIPTION
                "The high 32 bits of the count of scheduler drop bytes in the partition."
            ::= { partitionEntry 53 }

       	partitionFrameBytes OBJECT-TYPE
            SYNTAX Counter32
            MAX-ACCESS read-only
            STATUS current
            DESCRIPTION
                "The number of PVC bytes in the partition."
            ::= { partitionEntry 54 }

        partitionFrameBytesHi OBJECT-TYPE
            SYNTAX Counter32
            MAX-ACCESS read-only
            STATUS current
            DESCRIPTION
                "The high 32 bits of the number of PVC bytes in the partition."
            ::= { partitionEntry 55 }

        partitionFrameTargetRate OBJECT-TYPE
            SYNTAX Gauge32
            MAX-ACCESS read-only
            STATUS current
            DESCRIPTION
                "The target frame rate in the partition."
            ::= { partitionEntry 56 }

        partitionFrameTargetRateHi OBJECT-TYPE
            SYNTAX Gauge32
            MAX-ACCESS read-only
            STATUS current
            DESCRIPTION
                "The high 32 bits of the target frame rate in the partition."
            ::= { partitionEntry 57 }

        partitionFrameCount OBJECT-TYPE
            SYNTAX Counter32
            MAX-ACCESS read-only
            STATUS current
            DESCRIPTION
                "The number of frames in the partition."
            ::= { partitionEntry 58 }

        partitionFrameCountHi OBJECT-TYPE
            SYNTAX Counter32
            MAX-ACCESS read-only
            STATUS current
            DESCRIPTION
                "The high 32 bits of the number of frames in the partition."
            ::= { partitionEntry 59 }

        partitionEcnCount OBJECT-TYPE
            SYNTAX Counter32
            MAX-ACCESS read-only
            STATUS current
            DESCRIPTION
                "The number of ECNs in the partition."
            ::= { partitionEntry 60 }

        partitionEcnCountHi OBJECT-TYPE
            SYNTAX Counter32
            MAX-ACCESS read-only
            STATUS current
            DESCRIPTION
                "The high 32 bits of the number of ECNs in the partition."
            ::= { partitionEntry 61 }


	-- the psClasses group

        classTableSize OBJECT-TYPE
            SYNTAX Integer32 (2..2147483647)
            MAX-ACCESS read-only
            STATUS current
            DESCRIPTION
                "Number of entries in the classTable"
            ::= { psClasses 1 }

        classTable OBJECT-TYPE
            SYNTAX SEQUENCE OF ClassEntry
            MAX-ACCESS not-accessible
            STATUS current
            DESCRIPTION
                "A list of traffic class entries."
            ::= { psClasses 2 }

        classEntry OBJECT-TYPE
            SYNTAX ClassEntry
            MAX-ACCESS not-accessible
            STATUS current
            DESCRIPTION
                "A traffic class entry containing statistical objects
                for a traffic class."
            INDEX { classIndex }
            ::= { classTable 1 }

        ClassEntry ::=
            SEQUENCE { 
                classIndex
                    Integer32,
                className
                    DisplayString,
                classOwningPartName
                    DisplayString,
                classLinkDirection
                    INTEGER,
                classByteCount
                    Counter32,
                classByteCountHi
                    Counter32,
                classPkts
                    Counter32,
                classPktsHi
                    Counter32,
                classDataPkts
                    Counter32,
                classDataPktsHi
                    Counter32,
                classReTxs
                    Counter32,
                classReTxsHi
                    Counter32,
                classReTxTosses
                    Counter32,
                classReTxTossesHi
                    Counter32,
                classCirFails
                    Counter32,
                classCirFailsHi
                    Counter32,
                classCirAllocs
                    Counter32,
                classCirAllocsHi
                    Counter32,
                classPeakTcpConns
                    Gauge32,
                classTcpConnInits
                    Counter32,
                classTcpConnInitsHi
                    Counter32,
                classTcpConnExits
                    Counter32,
                classTcpConnExitsHi
                    Counter32,
                classTcpConnRefuses
                    Counter32,
                classTcpConnRefusesHi
                    Counter32,
                classTcpConnIgnores
                    Counter32,
                classTcpConnIgnoresHi
                    Counter32,
                classTcpConnAborts
                    Counter32,
                classTcpConnAbortsHi
                    Counter32,
                classTcpConnDenies
                    Counter32,
                classTcpConnDeniesHi
                    Counter32,
                classHits
                    Counter32,
                classHitsHi
                    Counter32,
                classPolicyHits
                    Counter32,
                classPolicyHitsHi
                    Counter32,
                classRate
                    Gauge32,
                classRateHi
                    Gauge32,
                classPeakGuaranteedRateFlows
                    Gauge32,
                classReTxByteCount
                    Counter32,
                classReTxByteCountHi
                    Counter32,
                classFullName
                    DisplayString,
                classCurrentRate
                    Gauge32,
                classCurrentRateHi
                    Gauge32,
                classPktExchangeTime
                    Counter32,
                classPktExchangeTimeHi
                    Counter32,
                classPktExchangeTimeSamples
                    Counter32,
                classClientFloodBlock
                    Counter32,
                classServerFloodBlock
                    Counter32,
                classPeakIpdgConns
                    Gauge32,
                classWebResponse2XX
                    Counter32,
                classWebResponse2XXHi
                    Counter32,
                classWebResponse3XX
                    Counter32,
                classWebResponse3XXHi
                    Counter32,
                classWebResponse4XX
                    Counter32,
                classWebResponse4XXHi
                    Counter32,
                classWebResponse5XX
                    Counter32,
                classWebResponse5XXHi
                    Counter32,
            	classRtpExpectedPackets
                    Gauge32,
            	classRtpExpectedPacketsHi
                    Gauge32,
            	classRtpLostPackets
                	Gauge32,
            	classRtpLostPacketsHi
                	Gauge32,
            	classRtpJitterCount
                	Counter32,
            	classRtpJitterSum
                	Gauge32,
            	classRtpLatencyCount
                	Counter32,
            	classRtpLatencySum
                	Gauge32,
            	classIcmpRttMsecsSum
                	Gauge32,
            	classIcmpRttCount
                	Counter32,
            	classIcmpAttemptCount
                	Counter32,	        
            	classNoBwDropBytesCount
                	Counter32,
            	classNoBwDropBytesCountHi
                	Counter32,
            	classTotalBytesCount
                	Counter32,
            	classTotalBytesCountHi
                	Counter32
        }

       	classIndex OBJECT-TYPE
            SYNTAX Integer32 (0..2147483647)
            MAX-ACCESS not-accessible 
            STATUS current
            DESCRIPTION
                "A unique ID for a traffic class."
            ::= { classEntry 1 }

        className OBJECT-TYPE
            SYNTAX DisplayString
            MAX-ACCESS read-only
            STATUS current
            DESCRIPTION
                "A unique name for a traffic class."
            ::= { classEntry 2 }

        classOwningPartName OBJECT-TYPE
            SYNTAX DisplayString
            MAX-ACCESS read-only
            STATUS current
            DESCRIPTION
                "A unique name for the partition which owns the class."
            ::= { classEntry 3 }

        classLinkDirection OBJECT-TYPE
            SYNTAX INTEGER
                {
                inBound(1),
                outBound(2)
                }
            MAX-ACCESS read-only
            STATUS current
            DESCRIPTION
                "The orientation of the class."
            ::= { classEntry 4 }

        classByteCount OBJECT-TYPE
            SYNTAX Counter32
            MAX-ACCESS read-only
            STATUS current
            DESCRIPTION
                "The byte count in the class."
            ::= { classEntry 5 }

        classByteCountHi OBJECT-TYPE
            SYNTAX Counter32
            MAX-ACCESS read-only
            STATUS current
            DESCRIPTION
                "The High 32 bits of byte count in the class."
            ::= { classEntry 6 }

     	classPkts OBJECT-TYPE
            SYNTAX Counter32
            MAX-ACCESS read-only
            STATUS current
            DESCRIPTION
                "The packet count in the class."
            ::= { classEntry 7 }

     	classPktsHi OBJECT-TYPE
            SYNTAX Counter32
            MAX-ACCESS read-only
            STATUS current
            DESCRIPTION
                "The high 32 bits of the packet count in the class."
            ::= { classEntry 8 }

        classDataPkts OBJECT-TYPE
            SYNTAX Counter32
            MAX-ACCESS read-only
            STATUS current
            DESCRIPTION
                "The TCP data packet count in the class."
            ::= { classEntry 9 }

        classDataPktsHi OBJECT-TYPE
            SYNTAX Counter32
            MAX-ACCESS read-only
            STATUS current
            DESCRIPTION
                "The high 32 bits of the TCP data packet count in the class."
            ::= { classEntry 10 }

        classReTxs OBJECT-TYPE
            SYNTAX Counter32
            MAX-ACCESS read-only
            STATUS current
            DESCRIPTION
                "The TCP retransmit packet count in the class."
            ::= { classEntry 11 }

        classReTxsHi OBJECT-TYPE
            SYNTAX Counter32
            MAX-ACCESS read-only
            STATUS current
            DESCRIPTION
                "The high 32 bits of the TCP retransmit packet count in the class."
            ::= { classEntry 12 }

        classReTxTosses OBJECT-TYPE
            SYNTAX Counter32
            MAX-ACCESS read-only
            STATUS current
            DESCRIPTION
                "The TCP tossed retransmit packet count in the class."
            ::= { classEntry 13 }

        classReTxTossesHi OBJECT-TYPE
            SYNTAX Counter32
            MAX-ACCESS read-only
            STATUS current
            DESCRIPTION
                "The high 32 bits of the TCP tossed retransmit packet count in the class."
            ::= { classEntry 14 }

        classCirFails OBJECT-TYPE
            SYNTAX Counter32
            MAX-ACCESS read-only
            STATUS current
            DESCRIPTION
                "The count of CIR fails events in the class."
            ::= { classEntry 15 }

        classCirFailsHi OBJECT-TYPE
            SYNTAX Counter32
            MAX-ACCESS read-only
            STATUS current
            DESCRIPTION
                "The high 32 bits of the count of CIR fails events in the class."
            ::= { classEntry 16 }

        classCirAllocs OBJECT-TYPE
            SYNTAX Counter32
            MAX-ACCESS read-only
            STATUS current
            DESCRIPTION
                "The count of CIR alloc events in the class."
            ::= { classEntry 17 }

        classCirAllocsHi OBJECT-TYPE
            SYNTAX Counter32
            MAX-ACCESS read-only
            STATUS current
            DESCRIPTION
                "The high 32 bits of the count of CIR alloc events in the class."
            ::= { classEntry 18 }

        classPeakTcpConns OBJECT-TYPE
            SYNTAX Gauge32
            MAX-ACCESS read-only
            STATUS current
            DESCRIPTION
                "The peak number of active TCP flows in the class."
            ::= { classEntry 19 }

       classTcpConnInits OBJECT-TYPE
            SYNTAX Counter32
            MAX-ACCESS read-only
            STATUS current
            DESCRIPTION
                "The count of TCP flows started in the class."
            ::= { classEntry 20 }

       classTcpConnInitsHi OBJECT-TYPE
            SYNTAX Counter32
            MAX-ACCESS read-only
            STATUS current
            DESCRIPTION
                "The high 32 bits of the count of TCP flows started in the class."
            ::= { classEntry 21 }

        classTcpConnExits OBJECT-TYPE
            SYNTAX Counter32
            MAX-ACCESS read-only
            STATUS current
            DESCRIPTION
                "The count of TCP flows exited in the class."
            ::= { classEntry 22 }

        classTcpConnExitsHi OBJECT-TYPE
            SYNTAX Counter32
            MAX-ACCESS read-only
            STATUS current
            DESCRIPTION
                "The high 32 bits of the count of TCP flows exited in the class."
            ::= { classEntry 23 }

        classTcpConnRefuses OBJECT-TYPE
            SYNTAX Counter32
            MAX-ACCESS read-only
            STATUS current
            DESCRIPTION
                "The count of TCP flows exited by TCP refuse in the class."
            ::= { classEntry 24 }

        classTcpConnRefusesHi OBJECT-TYPE
            SYNTAX Counter32
            MAX-ACCESS read-only
            STATUS current
            DESCRIPTION
                "The high 32 bits of the count of TCP flows exited by TCP refuse in the class."
            ::= { classEntry 25 }

        classTcpConnIgnores OBJECT-TYPE
            SYNTAX Counter32
            MAX-ACCESS read-only
            STATUS current
            DESCRIPTION
                "The count of TCP flows exited by being ignored in the class."
            ::= { classEntry 26 }

        classTcpConnIgnoresHi OBJECT-TYPE
            SYNTAX Counter32
            MAX-ACCESS read-only
            STATUS current
            DESCRIPTION
                "The high 32 bits of the count of TCP flows exited by being ignored in the class."
            ::= { classEntry 27 }

        classTcpConnAborts OBJECT-TYPE
            SYNTAX Counter32
            MAX-ACCESS read-only
            STATUS current
            DESCRIPTION
                "The count of TCP flows aborted in the class."
            ::= { classEntry 28 }

        classTcpConnAbortsHi OBJECT-TYPE
            SYNTAX Counter32
            MAX-ACCESS read-only
            STATUS current
            DESCRIPTION
                "The high 32 bits of the count of TCP flows aborted in the class."
            ::= { classEntry 29 }

        classTcpConnDenies OBJECT-TYPE
            SYNTAX Counter32
            MAX-ACCESS read-only
            STATUS current
            DESCRIPTION
                "The count of TCP flows denied by CIR fail in the class."
            ::= { classEntry 30 }

        classTcpConnDeniesHi OBJECT-TYPE
            SYNTAX Counter32
            MAX-ACCESS read-only
            STATUS current
            DESCRIPTION
                "The high 32 bits of the count of TCP flows denied by CIR fail in the class."
            ::= { classEntry 31 }

        classHits OBJECT-TYPE
            SYNTAX Counter32
            MAX-ACCESS read-only
            STATUS current
            DESCRIPTION
                "Count of hits in the class"
            ::= { classEntry 32 }

        classHitsHi OBJECT-TYPE
            SYNTAX Counter32
            MAX-ACCESS read-only
            STATUS current
            DESCRIPTION
                "The high 32 bits of the count of hits in the class"
            ::= { classEntry 33 }

        classPolicyHits OBJECT-TYPE
            SYNTAX Counter32
            MAX-ACCESS read-only
            STATUS current
            DESCRIPTION
                "Count of policy hits in the class"
            ::= { classEntry 34 }

        classPolicyHitsHi OBJECT-TYPE
            SYNTAX Counter32
            MAX-ACCESS read-only
            STATUS current
            DESCRIPTION
                "The high 32 bits of the count of policy hits in the class"
            ::= { classEntry 35 }

        classRate OBJECT-TYPE
            SYNTAX Gauge32
            MAX-ACCESS read-only
            STATUS current
            DESCRIPTION
                "The peak total rate in bps of the class"
            ::= { classEntry 36 }

        classRateHi OBJECT-TYPE
            SYNTAX Gauge32
            MAX-ACCESS read-only
            STATUS current
            DESCRIPTION
                "The high 32 bits of the peak total rate in bps of the class"
            ::= { classEntry 37 }

        classPeakGuaranteedRateFlows OBJECT-TYPE
            SYNTAX Gauge32
            MAX-ACCESS read-only
            STATUS current
            DESCRIPTION
                "The peak number of guaranteed rate flows active on the class."
            ::= { classEntry 38 }

       	classReTxByteCount OBJECT-TYPE
            SYNTAX Counter32
            MAX-ACCESS read-only
            STATUS current
            DESCRIPTION
                "The count of retransmitted bytes on the class.  This is the low-order
                32 bits."
            ::= { classEntry 39 }

        classReTxByteCountHi OBJECT-TYPE
            SYNTAX Counter32
            MAX-ACCESS read-only
            STATUS current
            DESCRIPTION
                "The count of retransmitted bytes on the class.  This is the high-order
                32 bits."
            ::= { classEntry 40 }

        classFullName OBJECT-TYPE
            SYNTAX DisplayString
            MAX-ACCESS read-only
            STATUS current
            DESCRIPTION
                "The complete name of the class, e.g. /Inbound/Inside/HTTP.
                Note that the className variable gives only the last part,
                in this example HTTP."
            ::= { classEntry 41 }

        classCurrentRate OBJECT-TYPE
            SYNTAX Gauge32
            MAX-ACCESS read-only
            STATUS current
            DESCRIPTION
                "The current rate in bits per second."
            ::= { classEntry 42 }

        classCurrentRateHi OBJECT-TYPE
            SYNTAX Gauge32
            MAX-ACCESS read-only
            STATUS current
            DESCRIPTION
                "The current rate in bits per second."
            ::= { classEntry 43 }

       classPktExchangeTime OBJECT-TYPE
            SYNTAX Counter32
            MAX-ACCESS read-only
            STATUS current
            DESCRIPTION
                "The packet exchange time for TCP
                data packets, between PacketShaper and the server side.
                This is the low-order 32 bits."
            ::= { classEntry 44 }

        classPktExchangeTimeHi OBJECT-TYPE
            SYNTAX Counter32
            MAX-ACCESS read-only
            STATUS current
            DESCRIPTION
                "The packet exchange time for TCP
                data packets, between PacketShaper and the server side.
                This is the high-order 32 bits."
            ::= { classEntry 45 }

        classPktExchangeTimeSamples OBJECT-TYPE
            SYNTAX Counter32
            MAX-ACCESS read-only
            STATUS current
            DESCRIPTION
                "The total number of packet exchanges
                counted for the classPktExchangeTime /
                classPktExchangeTimeHi number."
            ::= { classEntry 46 }

        classClientFloodBlock OBJECT-TYPE
            SYNTAX Counter32
            MAX-ACCESS read-only
            STATUS current
            DESCRIPTION
                "The total number of client side SYN flood attacks blocked."
            ::= { classEntry 47 }

        classServerFloodBlock OBJECT-TYPE
            SYNTAX Counter32
            MAX-ACCESS read-only
            STATUS current
            DESCRIPTION
                "The total number of server side SYN flood attacks blocked."
            ::= { classEntry 48 }

        classPeakIpdgConns OBJECT-TYPE
            SYNTAX Gauge32
            MAX-ACCESS read-only
            STATUS current
            DESCRIPTION
                "The peak number of active IPDG flows in the class."
            ::= { classEntry 49 }

        classWebResponse2XX OBJECT-TYPE
            SYNTAX Counter32
            MAX-ACCESS read-only
            STATUS current
            DESCRIPTION
                "The count of HTTP response messages having 2XX status codes (successful)."
            ::= { classEntry 50 }

        classWebResponse2XXHi OBJECT-TYPE
            SYNTAX Counter32
            MAX-ACCESS read-only
            STATUS current
            DESCRIPTION
                "The high 32 bits of the count of HTTP response messages having 2XX status codes (successful)."
            ::= { classEntry 51 }

     	classWebResponse3XX OBJECT-TYPE
            SYNTAX Counter32
            MAX-ACCESS read-only
            STATUS current
            DESCRIPTION
                "The count of HTTP response messages having 3XX status codes (redirection)."
            ::= { classEntry 52 }

     	classWebResponse3XXHi OBJECT-TYPE
            SYNTAX Counter32
            MAX-ACCESS read-only
            STATUS current
            DESCRIPTION
                "The high 32 bits of the count of HTTP response messages having 3XX status codes (redirection)."
            ::= { classEntry 53 }

        classWebResponse4XX OBJECT-TYPE
            SYNTAX Counter32
            MAX-ACCESS read-only
            STATUS current
            DESCRIPTION
                "The count of HTTP response messages having 4XX status codes (client error)."
            ::= { classEntry 54 }

        classWebResponse4XXHi OBJECT-TYPE
            SYNTAX Counter32
            MAX-ACCESS read-only
            STATUS current
            DESCRIPTION
                "The high 32 bits of the count of HTTP response messages having 4XX status codes (client error)."
            ::= { classEntry 55 }

        classWebResponse5XX OBJECT-TYPE
            SYNTAX Counter32
            MAX-ACCESS read-only
            STATUS current
            DESCRIPTION
                "The count of HTTP response messages having 5XX status codes (server error)."
            ::= { classEntry 56 }

        classWebResponse5XXHi OBJECT-TYPE
            SYNTAX Counter32
            MAX-ACCESS read-only
            STATUS current
            DESCRIPTION
                "The high 32 bits of the count of HTTP response messages having 5XX status codes (server error)."
            ::= { classEntry 57 }

      	classRtpExpectedPackets OBJECT-TYPE
            SYNTAX  Gauge32
            MAX-ACCESS  read-only
            STATUS current
            DESCRIPTION
                "The total number of RTP packets that were expected for the class."
            ::= { classEntry 58 }
      
      	classRtpExpectedPacketsHi OBJECT-TYPE
            SYNTAX  Gauge32
            MAX-ACCESS  read-only
            STATUS current
            DESCRIPTION
                "The high 32 bits of the total number of RTP packets that were expected for the class."
            ::= { classEntry 59 }

        classRtpLostPackets OBJECT-TYPE
            SYNTAX  Gauge32
            MAX-ACCESS  read-only
            STATUS current
            DESCRIPTION
            "The total number of RTP packets lost for the class."
            ::= { classEntry 60 }

        classRtpLostPacketsHi OBJECT-TYPE
            SYNTAX  Gauge32
            MAX-ACCESS  read-only
            STATUS current
            DESCRIPTION
            "The high 32 bits of the total number of RTP packets lost for the class."
            ::= { classEntry 61 }
           
        classRtpJitterCount OBJECT-TYPE
            SYNTAX  Counter32
            MAX-ACCESS  read-only
            STATUS current
            DESCRIPTION
                "The total number of RTP packets used to compute jitter. 
                 Jitter average is classRtpJitterSum/classRtpJitterCount."
            ::= { classEntry 62 }				
		
        classRtpJitterSum OBJECT-TYPE
            SYNTAX  Gauge32
            MAX-ACCESS  read-only
            STATUS current
            DESCRIPTION
                "The sum or RTP jitter for all packets on which jitter is measured for the class. 
                 Jitter average is classRtpJitterSum/classRtpJitterCount."
            ::= { classEntry 63 }		

        classRtpLatencyCount OBJECT-TYPE
            SYNTAX  Counter32
            MAX-ACCESS  read-only
            STATUS current
            DESCRIPTION
                "The total number of latency samples used to compute average latency. 
                 Latency average is classRtpLatencySum/classRtpLatencyCount."
            ::= { classEntry 64 }				
		
        classRtpLatencySum OBJECT-TYPE
            SYNTAX  Gauge32
            MAX-ACCESS  read-only
            STATUS current
            DESCRIPTION
                "Cumulative sum of latency value of the latency samples. 
                 Latency average is classRtpLatencySum/classRtpLatencyCount."
            ::= { classEntry 65 }
		
        classIcmpRttMsecsSum OBJECT-TYPE
            SYNTAX  Gauge32
            MAX-ACCESS  read-only
            STATUS current
            DESCRIPTION
                "The sum of ICMP RTTs in msecs. 
                 ICMP RTT average is classICMPRttMsecsSumSum/classIcmpRttCount."
            ::= { classEntry 66 }		

        classIcmpRttCount OBJECT-TYPE
            SYNTAX  Counter32
            MAX-ACCESS  read-only
            STATUS current
            DESCRIPTION
                "The total number of ICMP RTT samples. 
                 ICMP RTT average is classICMPRttMsecsSumSum/classIcmpRttCount."
            ::= { classEntry 67 }				
		
        classIcmpAttemptCount OBJECT-TYPE
            SYNTAX  Counter32
            MAX-ACCESS read-only
            STATUS current
            DESCRIPTION
                "The total number of ICMP RTT sample attempts. 
                 ICMP RTT success rate is classIcmpRttCount/classIcmpAttemptCount."
            ::= { classEntry 68 }		
        classNoBwDropBytesCount OBJECT-TYPE
            SYNTAX  Counter32
            MAX-ACCESS  read-only
            STATUS  current
            DESCRIPTION
                "The low 32 bits of byte count that was dropped in the class because of bandwidth congestion."
            ::= { classEntry 69 }

        classNoBwDropBytesCountHi OBJECT-TYPE
            SYNTAX  Counter32
            MAX-ACCESS  read-only
            STATUS  current
            DESCRIPTION
                "The High 32 bits of byte count that was dropped in the class because of bandwidth congestion."
            ::= { classEntry 70 }

        classTotalBytesCount OBJECT-TYPE
            SYNTAX  Counter32
            MAX-ACCESS  read-only
            STATUS  current
            DESCRIPTION
                "The low 32 bits of the total byte count of packets that were transmitted successfully plus 
                 the number of bytes that was dropped in classNoBwDropBytesCount variable."
            ::= { classEntry 71 }

        classTotalBytesCountHi OBJECT-TYPE
            SYNTAX  Counter32
            MAX-ACCESS  read-only
            STATUS  current
            DESCRIPTION
                "The High 32 bits of the total byte count of packets that were transmitted successfully plus 
                 the number of bytes that was dropped in classNoBwDropBytesCount variable."
            ::= { classEntry 72 }


	-- the psAlarms group.  In each case, a trap is paired with a variable
  	-- Since traps are unreliable, managers should also poll the relevant
  	-- variable.
   	-- traps for InsideLink and OutsideLink do not exist here, since the MIB-II
   	-- LinkDown traps are used instead.
       	psAlarmInsideLinkCount OBJECT-TYPE
            SYNTAX Counter32
            MAX-ACCESS read-only
            STATUS current
            DESCRIPTION
                "The number of MIB-II LinkDown traps sent by
                the agent since the last reset, where ifIndex
                was for an Inside link."
            ::= { psAlarms 1 }

        psAlarmOutsideLinkCount OBJECT-TYPE
            SYNTAX Counter32
            MAX-ACCESS read-only
            STATUS current
            DESCRIPTION
                "The number of MIB-II LinkDown traps sent by
                the agent since the last reset, where ifIndex
                was for an Outside link. "
           	::= { psAlarms 2 }

        psAlarmAuthFailCount OBJECT-TYPE
            SYNTAX Counter32
            MAX-ACCESS read-only
            STATUS current
            DESCRIPTION
                "The number of MIB-II authenticationFailure traps
				 sent by the agent since the last reset. "
           	::= { psAlarms 3 }

        psAlarmBCAAAPrimaryCount OBJECT-TYPE
            SYNTAX Counter32
            MAX-ACCESS read-only
            STATUS current
            DESCRIPTION
                "The number of times that we detected that the primary
				 BCAAA server was unavailable. "
           	::= { psAlarms 4 }

        psAlarmBCAAASecondaryCount OBJECT-TYPE
            SYNTAX Counter32
            MAX-ACCESS read-only
            STATUS current
            DESCRIPTION
                "The number of times that we detected that the secondary
				 BCAAA server was unavailable. "
           	::= { psAlarms 5 }

        psAlarmBCAAAPrimaryStatus OBJECT-TYPE
            SYNTAX INTEGER
                {
                unknown(0),
                ok(1),
                fail(2),
                unconfig(3),
                off(4)
                }
            MAX-ACCESS read-only
            STATUS current
            DESCRIPTION
                "Status of the primary BCAAA server.  A status of fail(2) means that PacketShaper
                cannot log in to the primary BCAAA server. unconfig(3) means that no primary
                BCAAA server is configured.  off(4) means that the BCAAA Client service is disabled."
            ::= { psAlarms 6 }

        psAlarmBCAAASecondaryStatus OBJECT-TYPE
            SYNTAX INTEGER
                {
                unknown(0),
                ok(1),
                fail(2),
                unconfig(3),
                off(4)
                }
            MAX-ACCESS read-only
            STATUS current
            DESCRIPTION
                "Status of the secondary BCAAA server.  A status of fail(2) means that PacketShaper
                cannot log in to the secondary BCAAA server. unconfig(3) means that no secondary
                BCAAA server is configured. off(4) means that the BCAAA Client service is disabled."
            ::= { psAlarms 7 }

        psAlarmCpuUtilizationPct    OBJECT-TYPE
            SYNTAX  Gauge32 (0..100)
            UNITS "percent"
            MAX-ACCESS   read-only
            STATUS   current
            DESCRIPTION
                "The average CPU utilization in percentage as seen by agent."
        ::= { psAlarms 8 }

        psAlarmPowerSystemOneCount OBJECT-TYPE
            SYNTAX Counter32
            MAX-ACCESS read-only
            STATUS current
            DESCRIPTION
                "The number of psAlarmPowerSystemOne traps sent by
                the agent since the last reset."
            ::= { psAlarms 9 }

        
        psAlarmPowerSystemOneStatus OBJECT-TYPE
            SYNTAX INTEGER
                {
                ok(0),
                notOk(1),
                noStatus(2)
                }
            MAX-ACCESS read-only
            STATUS current
            DESCRIPTION
                "The operational status of the first power system
                of the device.noStatus(2) indicates that power supply
                                status is not available.
                (0) UP
                (1) DOWN
				(2) No Status"
            ::= { psAlarms 10 }

        
        psAlarmPowerSystemTwoCount OBJECT-TYPE
            SYNTAX Counter32
            MAX-ACCESS read-only
            STATUS current
            DESCRIPTION
                "The number of psAlarmPowerSystemTwo traps sent by
                the agent since the last reset."
            ::= { psAlarms 11 }

        
        psAlarmPowerSystemTwoStatus OBJECT-TYPE
            SYNTAX INTEGER
                {
                ok(0),
                notOk(1),
                noStatus(2)
                }
            MAX-ACCESS read-only
            STATUS current
            DESCRIPTION
                "The operational status of the second power supply
                of the device.noStatus(2) indicates that power supply
                                status is not available.
                (0) UP
                (1) DOWN
                (2) No Status"
            ::= { psAlarms 12 }

        psAlarmFanOneCount OBJECT-TYPE
            SYNTAX Counter32
            MAX-ACCESS read-only
            STATUS current
            DESCRIPTION
                "The number of psAlarmFan traps sent by
                the agent since the last reset for system
				fan one."
            ::= { psAlarms 13 }


        psAlarmFanOneStatus OBJECT-TYPE
            SYNTAX INTEGER
                {
                ok(0),
                notOk(1),
                noStatus(2)
                }
            MAX-ACCESS read-only
            STATUS current
            DESCRIPTION
                "The operational status of the first fan of the device.
              	noStatus(2) indicates that fan status is not available.
                (0) UP
                (1) DOWN
                (2) No status available"
            ::= { psAlarms 14 }

        psAlarmFanTwoCount OBJECT-TYPE
            SYNTAX Counter32
            MAX-ACCESS read-only
            STATUS current
            DESCRIPTION
                "The number of psAlarmFan traps sent by
                the agent since the last reset for system
				fan two."
            ::= { psAlarms 15 }


        psAlarmFanTwoStatus OBJECT-TYPE
            SYNTAX INTEGER
                {
                ok(0),
                notOk(1),
                noStatus(2)
                }
            MAX-ACCESS read-only
            STATUS current
            DESCRIPTION
                "The operational status of the second fan of the device.
              	noStatus(2) indicates that fan status is not available.
                (0) UP
                (1) DOWN
                (2) No status available"
            ::= { psAlarms 16 }

        psAlarmFanThreeCount OBJECT-TYPE
            SYNTAX Counter32
            MAX-ACCESS read-only
            STATUS current
            DESCRIPTION
                "The number of psAlarmFan traps sent by
                the agent since the last reset for system
				fan three."
            ::= { psAlarms 17 }


        psAlarmFanThreeStatus OBJECT-TYPE
            SYNTAX INTEGER
                {
                ok(0),
                notOk(1),
                noStatus(2)
                }
            MAX-ACCESS read-only
            STATUS current
            DESCRIPTION
                "The operational status of the third fan of the device.
              	noStatus(2) indicates that fan status is not available.
                (0) UP
                (1) DOWN
                (2) No status available"
            ::= { psAlarms 18 }

        psAlarmFanFourCount OBJECT-TYPE
            SYNTAX Counter32
            MAX-ACCESS read-only
            STATUS current
            DESCRIPTION
                "The number of psAlarmFan traps sent by
                the agent since the last reset for system
				fan four."
            ::= { psAlarms 19 }


        psAlarmFanFourStatus OBJECT-TYPE
            SYNTAX INTEGER
                {
                ok(0),
                notOk(1),
                noStatus(2)
                }
            MAX-ACCESS read-only
            STATUS current
            DESCRIPTION
                "The operational status of the fourth fan of the device.
              	noStatus(2) indicates that fan status is not available.
                (0) UP
                (1) DOWN
                (2) No status available"
            ::= { psAlarms 20 }

        psAlarmFanFiveCount OBJECT-TYPE
            SYNTAX Counter32
            MAX-ACCESS read-only
            STATUS current
            DESCRIPTION
                "The number of psAlarmFan traps sent by
                the agent since the last reset for system
				fan five."
            ::= { psAlarms 21 }


        psAlarmFanFiveStatus OBJECT-TYPE
            SYNTAX INTEGER
                {
                ok(0),
                notOk(1),
                noStatus(2)
                }
            MAX-ACCESS read-only
            STATUS current
            DESCRIPTION
                "The operational status of the fifth fan of the device.
              	noStatus(2) indicates that fan status is not available.
                (0) UP
                (1) DOWN
                (2) No status available"
            ::= { psAlarms 22 }

        psAlarmFanSixCount OBJECT-TYPE
            SYNTAX Counter32
            MAX-ACCESS read-only
            STATUS current
            DESCRIPTION
                "The number of psAlarmFan traps sent by
                the agent since the last reset for system
				fan six."
            ::= { psAlarms 23 }


        psAlarmFanSixStatus OBJECT-TYPE
            SYNTAX INTEGER
                {
                ok(0),
                notOk(1),
                noStatus(2)
                }
            MAX-ACCESS read-only
            STATUS current
            DESCRIPTION
                "The operational status of the sixth fan of the device.
              	noStatus(2) indicates that fan status is not available.
                (0) UP
                (1) DOWN
                (2) No status available"
            ::= { psAlarms 24 }

        psAlarmVoltageSensorCount OBJECT-TYPE
            SYNTAX Counter32
            MAX-ACCESS read-only
            STATUS   current
            DESCRIPTION
                "The number of psAlarmVoltageSensor traps sent by
                the agent since the last reset."
            ::= { psAlarms 25 }

        psAlarmVoltageSensorStatus OBJECT-TYPE
            SYNTAX INTEGER
                {
                voltageOk(0),
				badvoltageCpu(1),
				badVoltage1v(2),
				badVoltageCpuAnd1v(3),
				badVoltage12v(4),
				badVoltage12vAndCpu(5),
				badVoltage12vAnd1v(6),
				badVoltage12vAnd1vAndCpu(7),
				badVoltage3v(8),
				badVoltage3vAndCpu(9),
				badVoltage3vAnd1v(10),
				badVoltage3vAnd1vAndCpu(11),
				badVoltage3vAnd12v(12),
				badVoltage3vAnd12vAndCpu(13),
				badVoltage3vAnd12vAnd1v(14),
				badVoltage3vAnd12vAnd1vAndCpu(15),
				badVoltage5v(16),
				badVoltage5vAndCpu(17),
				badVoltage5vAnd1v(18),
				badVoltage5vAnd1vAndCpu(19),
				badVoltage5vAnd12v(20),
				badVoltage5vAnd12vAndCpu(21),
				badVoltage5vAnd12vAnd1v(22),
				badVoltage5vAnd12vAnd1vAndCpu(23),
				badVoltage5vAnd3v(24),
				badVoltage5vAnd3vAndCpu(25),
				badVoltage5vAnd3vAnd1v(26),
				badVoltage5vAnd5vAnd1vAndCpu(27),
				badVoltage5vAnd3vAnd12v(28),
				badVoltage5vAnd3vAnd12vAndCpu(29),
				badVoltage5vAnd3vAnd12vAnd1v(30),
				badVoltage5vAnd3vAnd12vAnd1vAndCpu(31)
                }
            MAX-ACCESS read-only
            STATUS current
            DESCRIPTION
                "The status of the voltage analog inputs.
                voltageOk(0) All voltage readings are normal,
				badvoltageCpu(1) A CPU sensor has detected an abnormal voltage,
				badVoltage1v(2) The 1.1v input is abnormal ,
				badVoltageCpuAnd1v(3),
				badVoltage12v(4) The 12v input is abnormal,
				badVoltage12vAndCpu(5),
				badVoltage12vAnd1v(6),
				badVoltage12vAnd1vAndCpu(7),
				badVoltage3v(8) The 3V input is abnormal,
				badVoltage3vAndCpu(9),
				badVoltage3vAnd1v(10),
				badVoltage3vAnd1vAndCpu(11),
				badVoltage3vAnd12v(12),
				badVoltage3vAnd12vAndCpu(13),
				badVoltage3vAnd12vAnd1v(14),
				badVoltage3vAnd12vAnd1vAndCpu(15),
				badVoltage5V(16) The 5V input is abnormal
				badVoltage5vAndCpu(17),
				badVoltage5vAnd1v(18),
				badVoltage5vAnd1vAndCpu(19),
				badVoltage5vAnd12v(20),
				badVoltage5vAnd12vAndCpu(21),
				badVoltage5vAnd12vAnd1v(22),
				badVoltage5vAnd12vAnd1vAndCpu(23),
				badVoltage5vAnd3v(24),
				badVoltage5vAnd3vAndCpu(25),
				badVoltage5vAnd3vAnd1v(26),
				badVoltage5vAnd5vAnd1vAndCpu(27),
				badVoltage5vAnd3vAnd12v(28),
				badVoltage5vAnd3vAnd12vAndCpu(29),
				badVoltage5vAnd3vAnd12vAnd1v(30),
				badVoltage5vAnd3vAnd12vAnd1vAndCpu(31)"
            ::= { psAlarms 26 }

        psAlarmTemperatureSensorCount OBJECT-TYPE
            SYNTAX Counter32
            MAX-ACCESS read-only
            STATUS   current
            DESCRIPTION
                "The number of psAlarmTemperatureSensor traps sent by
                the agent since the last reset."
            ::= { psAlarms 27 }

        psAlarmTemperatureSensorStatus OBJECT-TYPE
            SYNTAX INTEGER
                {
                tempOk(0),
				badTempCpu(1),
				badTempRam(2),
				badTempRamAndCpu(3),
				badTempMb(4),
				badTempMbAndCpu(5),
				badTempMbAndRam(6),
				badTempMbAndRamAndCpu(7),
				badTempPsu(8),
				badTempPsuAndCpu(9),
				badTempPsuAndRam(10),
				badTempPsuAndRamAndCpu(11),
				badTempPsuAndMb(12),
				badTempPsuAndMbAndCpu(13),
				badTempPsuAndMbAndRam(14),
				badTempPsuAndMbAndRamAndCpu(15)
				}
            MAX-ACCESS read-only
            STATUS current
            DESCRIPTION
                "The status of the temperature sensor inputs.
                TempOK(0) All voltage readings are normal,
				badTempCpu(1) A CPU sensor has detected an abnormal temp,
				badTempRam(2) A DIMM sensor has detected an abnormal temp,
				badTempRamAndCpu(3),
				badTempMb(4) A motherboard sensor has detected and abnormal temp,
				badTempMbAndCpu(5),
				badTempMbAndRam(6),
				badTempMbAndRamAndCpu(7),
				badTempPsu(8) A power supply sensor has detected an abnormal temp,
				badTempPsuAndCpu(9),
				badTempPsuAndRam(10),
				badTempPsuAndRamAndCpu(11),
				badTempPsuAndMb(12),
				badTempPsuAndMbAndCpu(13),
				badTempPsuAndMbAndRam(14),
				badTempPsuAndMbAndRamAndCpu(15)"
            ::= { psAlarms 28 }

        psAlarmMeasurementEngineCount OBJECT-TYPE
            SYNTAX Counter32
            MAX-ACCESS read-only
            STATUS current
            DESCRIPTION
                "The number of psAlarmMeasurementEngine traps sent by
                the agent since the last reset."
            ::= { psAlarms 29 }

        psAlarmMeasurementEngineStatus OBJECT-TYPE
            SYNTAX INTEGER
                {
                startupError(1),
                notStarted(2),
                disabled(3),
                suspended(4),
                stopping(5),
                backup(6),
                restore(7),
                starting(8),
                syncing(9),
				running(10)
                }
            MAX-ACCESS read-only
            STATUS current
            DESCRIPTION
                "The current status of the Measurement Engine.  The values
                enumerated above correspond to those shown in the command
                line 'me show' command.
                (1) error on startup
                (2) not started
                (3) disabled
                (4) suspended
                (5) stopping
                (6) backing up data
                (7) restoring data
                (8) starting
                (9) syncing data
				(10) running"
            ::= { psAlarms 30 }

	-- the psAdmin group

       	psSerialNumber OBJECT-TYPE
            SYNTAX DisplayString
            MAX-ACCESS read-only
            STATUS current
            DESCRIPTION
                "This object reflects the serial number of the PacketShaper."
            ::= { psAdmin 1 }

       	psUpTime OBJECT-TYPE
            SYNTAX Counter32
            MAX-ACCESS read-only
            STATUS current
            DESCRIPTION
                "The number of seconds the PacketShaper has been up and running."
            ::= { psAdmin 2 }

        psShapingStatusAdmin OBJECT-TYPE
            SYNTAX INTEGER
                {
                on(1),
                off(2),
                bypass(3),
                other(4),
                watch(5),
				passthru(6)
                }
            MAX-ACCESS read-write
            STATUS current
            DESCRIPTION
                "This object reflects the current configured traffic shaping status
                of the PacketShaper.  The value of other(4) may occur in certain
                cases which can only be caused through the PacketShaper's user
                interface, and cannot be set through this variable   "
            ::= { psAdmin 3 }


	-- the Alarm Variables group
	-- These objects are added to psTraps to provide additional information

        psAlarmFanModuleID OBJECT-TYPE
            SYNTAX INTEGER
                {
                fan1(1),
                fan2(2),
                fan3(3),
                fan4(4),
                fan5(5),
                fan6(6)
                }
            MAX-ACCESS accessible-for-notify
            STATUS current
            DESCRIPTION
                "The system fan module number."
            ::= { psAlarmVars 1 }
		

        psAlarmVoltageSensorID OBJECT-TYPE
            SYNTAX INTEGER
                {
                ps5VMain(8),
                ps5VStby(9),
                ps12V1(10),
                ps12V2(11),
                ps1p1V(18),
                psCpu(19),
                ps3p3V1(34),
                ps3p3v2(35)
                }
            MAX-ACCESS accessible-for-notify
            STATUS current
            DESCRIPTION
                "The voltage sensor number.

                 ps5VMain(8) 		= 5.5V power supply,
                 ps5VStby(9)     	= 5.5v standby power supply,
                 ps12V1(10)        	= 12V power supply one,
                 ps12V2(11)      	= 12V power supply two,
                 ps1p1V(18)       	= 1.1V power supply,
                 psCpu(19)          = CPU core voltage , 
                 ps3p3V1(34)  		= 3.3V power supply one,
                 ps3p3V2(35)       	= 3.3V power supply two"
            ::= { psAlarmVars 2 }

        psAlarmTemperatureSensorID OBJECT-TYPE
            SYNTAX INTEGER
                {
                mbTemp(1),
				psuInTemp1(6),
				psuInTemp2(7),
                ramA1Temp(51),
                ramA2Temp(52),
                ramB1Temp(54),
				ramB2Temp(55),
				ramC1Temp(57),
				ramC2Temp(58),
				ramD1Temp(60),
				ramD2Temp(61),
				mbTempC(62),
				mbTempR(63),
				psuCore1(82),
				psuCore2(83),
				cpuTemp(99)
                }
            MAX-ACCESS accessible-for-notify
            STATUS current
            DESCRIPTION
                "The temperature sensor number.
                 for the PS12K the IPMI sensor numbers are used.
               	mbTemp(1)		= Motherboard,
				psuInTemp1(6)	= Power Supply 1 inlet,
				psuInTemp2(7)	= Power Supply 2 inlet,
                ramA1Temp(51)	= RAM DIMM A1,
                ramA2Temp(52)	= RAM DIMM A2,
                ramB1Temp(54)	= RAM DIMM B1,
				ramB2Temp(55)	= RAM DIMM B2,
				ramC1Temp(57)	= RAM DIMM C1,
				ramC2Temp(58)	= RAM DIMM C2,
				ramD1Temp(60)	= RAM DIMM D1,
				ramD2Temp(61)	= RAM DIMM D2,
				mbTempC(62)		= Center Motherboard,
				mbTempR(63)		= Right Motherboard,
				psuCore1(82)	= Power Supply 1 core,
				psuCore2(83)	= Power Supply 2 core,
				cpuTemp(99)		= CPU"
            ::= { psAlarmVars 3 }

-- User Events
	psUserEventTrapVars OBJECT IDENTIFIER ::= { psUserEvents 1 }

-- VarBinds for User Events

        userEventTrapName OBJECT-TYPE
            SYNTAX DisplayString
            MAX-ACCESS accessible-for-notify
            STATUS current
            DESCRIPTION
                "The name of the user event which has occurred."
            ::= { psUserEventTrapVars 1 }

        
        userEventTrapExpression OBJECT-TYPE
            SYNTAX DisplayString
            MAX-ACCESS accessible-for-notify
            STATUS current
            DESCRIPTION
                "The expression defining this user event."
            ::= { psUserEventTrapVars 2 }

        
        userEventTrapVariable OBJECT-TYPE
            SYNTAX DisplayString
            MAX-ACCESS accessible-for-notify
            STATUS current
            DESCRIPTION
                "The name of the Measurement Engine variable which is
                tested in this user event."
            ::= { psUserEventTrapVars 3 }

        
        userEventTrapElementType OBJECT-TYPE
            SYNTAX INTEGER
                {
                link(1),
                class(2),
                partition(3)
                }
            MAX-ACCESS accessible-for-notify
            STATUS current
            DESCRIPTION
                "The type of element which is tested in this user event."
            ::= { psUserEventTrapVars 4 }

        
        userEventTrapRegid OBJECT-TYPE
            SYNTAX Integer32 (1..2147483647)
            MAX-ACCESS accessible-for-notify
            STATUS current
            DESCRIPTION
                "The registration of this user event."
            ::= { psUserEventTrapVars 5 }

        
        userEventTrapDate OBJECT-TYPE
            SYNTAX DateAndTime
            MAX-ACCESS accessible-for-notify
            STATUS current
            DESCRIPTION
                "The time the event occurred."
            ::= { psUserEventTrapVars 6 }

        
        userEventTrapValue OBJECT-TYPE
            SYNTAX Integer32 (0..2147483647)
            MAX-ACCESS accessible-for-notify
            STATUS current
            DESCRIPTION
                "The value of userEventTrapVariable which triggered the event."
            ::= { psUserEventTrapVars 7 }

        
        userEventTrapTarget OBJECT-TYPE
            SYNTAX DisplayString
            MAX-ACCESS accessible-for-notify
            STATUS current
            DESCRIPTION
                "The name of the link, class, or partition,
                as given in userEventTrapElementType, which is
                the target of this event regiatration."
            ::= { psUserEventTrapVars 8 }

        
        userEventTrapThreshold OBJECT-TYPE
            SYNTAX Integer32 (0..2147483647)
            MAX-ACCESS accessible-for-notify
            STATUS current
            DESCRIPTION
                "The threshold value which triggers this event.
                See the value of userEventTrapExpression
                for the signedness with respect to the threshold (<, >, etc.)"
            ::= { psUserEventTrapVars 9 }

        
        userEventTrapRearm OBJECT-TYPE
            SYNTAX Integer32 (0..2147483647)
            MAX-ACCESS accessible-for-notify
            STATUS current
            DESCRIPTION
                "The rearm value which must be hit after an occurrence
                of this event in order to rearm it.
                See the value of userEventTrapExpression
                for the signedness with respect to the threshold (<, >, etc.)"
            ::= { psUserEventTrapVars 10 }

        
        userEventTrapDayCount OBJECT-TYPE
            SYNTAX Integer32 (0..2147483647)
            MAX-ACCESS accessible-for-notify
            STATUS current
            DESCRIPTION
                "The number of times this event has occurred on this
                day (as counted from midnight to midnight, local time).
                If this value is greater than or equal to userEventTrapDayLimit,
                and that value is non-zero, then no more instances of this
                event will be reported until the next day."
            ::= { psUserEventTrapVars 11 }

        
        userEventTrapDayLimit OBJECT-TYPE
            SYNTAX Integer32 (0..2147483647)
            MAX-ACCESS accessible-for-notify
            STATUS current
            DESCRIPTION
                "The maximum number of times this event is allowed to occur per
                day (as counted from midnight to midnight, local time),
                as configured by the user.  A value of zero denotes no limit."
            ::= { psUserEventTrapVars 12 }


        userEventTrapStatus OBJECT-TYPE
            SYNTAX INTEGER { violated(1), rearmed(2) }
            MAX-ACCESS accessible-for-notify
            STATUS current
            DESCRIPTION
                "The user event trap status.  Indicats if the trap is for a 
                threshold violation or if the event is rearmed."
        ::= { psUserEventTrapVars 13 }

      
        psFeatureHighAvDeviceDownCount OBJECT-TYPE
            SYNTAX Counter32
            MAX-ACCESS read-only
            STATUS current
            DESCRIPTION
                "The number of psFeatureHighAvDevice traps sent by
                the agent since the last reset."
            ::= { psHighAv 1 }


-- Agent Events
	psAgentEventTrapVars OBJECT IDENTIFIER ::= { psAgentEvents 1 }

-- VarBinds for Agent Events
        agentEventTrapName OBJECT-TYPE
            SYNTAX DisplayString
            MAX-ACCESS accessible-for-notify
            STATUS current
            DESCRIPTION
                "The name of the agent instance which has fired the event."
            ::= { psAgentEventTrapVars 1 }

        
        agentEventTrapDate OBJECT-TYPE
            SYNTAX DateAndTime
            MAX-ACCESS accessible-for-notify
            STATUS current
            DESCRIPTION
                "The time the event occurred."
            ::= { psAgentEventTrapVars 2 }

        
        agentEventTrapType OBJECT-TYPE
            SYNTAX INTEGER
                {
                red(1),
                yellow(2),
                blue(3),
                grey(4),
                green(5)
                }
            MAX-ACCESS accessible-for-notify
            STATUS current
            DESCRIPTION
                "The type of event that occurred, 5 = GREEN, 1 = RED, 2 = YELLOW, 3 = BLUE, 4 = GREY."
            ::= { psAgentEventTrapVars 3 }

        
        agentEventTrapDescription OBJECT-TYPE
            SYNTAX DisplayString
            MAX-ACCESS accessible-for-notify
            STATUS current
            DESCRIPTION
                "A description of the event that has occurred."
            ::= { psAgentEventTrapVars 4 }

        psFeatureHighAvDeviceDownStatus OBJECT-TYPE
            SYNTAX INTEGER { up(1), down(2) }
            MAX-ACCESS read-only
            STATUS current
            DESCRIPTION
                "The operational status of the interface of the router
                we are polling.
                (1) UP
                (2) DOWN."
            ::= { psHighAv 2 }

      
        psFeatureHighAvDeviceDownRouter OBJECT-TYPE
            SYNTAX DisplayString
            MAX-ACCESS read-only
            STATUS current
            DESCRIPTION
                "The name of a router that has gone down
                or the name of the router whose one of the
                interfaces has gone down."
            ::= { psHighAv 3 }


        psFeatureHighAvDeviceDownInterface OBJECT-TYPE
            SYNTAX DisplayString
            MAX-ACCESS read-only
            STATUS current
            DESCRIPTION
                "The name of the interface that has gone down. The name
                will be specified as 'unknown' in the cases where we
                could not resolve the interface name. The interface
                name will have a value of NULL or zero-length value
                if the router goes down."
            ::= { psHighAv 4 } 

	-- conformance section
	
	bluecoatConformance OBJECT IDENTIFIER ::= {  packetShaperS-Series 3 }
	bluecoatGroups OBJECT IDENTIFIER ::= { bluecoatConformance 1 }


 	psLinkObjectsGroup1 OBJECT-GROUP
            OBJECTS { linkTableSize, linkName, linkByteCount, linkByteCountHi, linkPkts, linkPktsHi,
                linkDataPkts, linkDataPktsHi, linkReTxs, linkReTxsHi, linkReTxTosses, linkReTxTossesHi, linkCirFails,
                linkCirFailsHi, linkCirAllocs, linkCirAllocsHi, linkPeakTcpConns, linkTcpConnInits, linkTcpConnInitsHi,
                linkTcpConnExits, linkTcpConnExitsHi, linkTcpConnRefuses, linkTcpConnRefusesHi, linkTcpConnIgnores,
                linkTcpConnIgnoresHi, linkTcpConnAborts, linkTcpConnAbortsHi, linkTcpConnDenies, linkTcpConnDeniesHi,
                linkSize, linkSizeHi, linkRate, linkRateHi, linkPeakGuaranteedRateFlows, linkReTxByteCount,
                linkReTxByteCountHi, linkTotalRxPkts, linkTotalRxPktsHi, linkTotalTxPkts, linkTotalTxPktsHi,
				linkRxNoBufs, linkRxNoBufsHi, linkRxPktDrops, linkRxPktDropsHi, linkTxPktDrops, linkTxPktDropsHi,
                linkRxErrors, linkRxErrorsHi, linkTxErrors, linkTxErrorsHi, linkTcpAllocFails, linkTcpAllocFailsHi,
                linkIpdgAllocFails, linkIpdgAllocFailsHi, linkHostdbAllocFails, linkHostdbAllocFailsHi, linkShapingMode,
                linkAutoclassifyMode, linkMacSameSidePkts, linkMacSameSidePktsHi, linkPassthruPkts, linkPassthruPktsHi,
                linkTotalRxBytes, linkTotalRxBytesHi, linkTotalTxBytes, linkTotalTxBytesHi, linkClassChecks, 
				linkClassChecksHi, linkPassthruBytes, linkPassthruBytesHi } 
            STATUS current
            DESCRIPTION 
                "A collection of objects that provides information regarding the PacketShaper S-Series
				 links."
            ::= { bluecoatGroups 1 }

 	psPartitionObjectsGroup1 OBJECT-GROUP
            OBJECTS {partitionTableSize, partitionName, partitionLinkDirection, partitionByteCount,
                partitionByteCountHi, partitionPkts, partitionPktsHi, partitionDataPkts, partitionDataPktsHi, partitionReTxs,
                partitionReTxsHi, partitionReTxTosses,partitionReTxTossesHi, partitionCirFails, partitionCirFailsHi,
                partitionCirAllocs, partitionCirAllocsHi, partitionPeakTcpConns, partitionTcpConnInits, partitionTcpConnInitsHi,
                partitionTcpConnExits, partitionTcpConnExitsHi, partitionTcpConnRefuses, partitionTcpConnRefusesHi, 
				partitionTcpConnIgnores, partitionTcpConnIgnoresHi, partitionTcpConnAborts, partitionTcpConnAbortsHi, partitionTcpConnDenies,
                partitionTcpConnDeniesHi, partitionMinimumBps, partitionMinimumBpsHi, partitionBurstLimit, partitionBurstLimitHi,
                partitionRate, partitionRateHi, partitionFirstSatisfiedPriority, partitionTimeOverLimit, partitionPeakGuaranteedRateFlows,
                partitionReTxByteCount, partitionReTxByteCountHi, partitionDynamicCapCount, partitionDynamicNoCount, partitionDynamicLiveUserCount,
                partitionCommittmentFailures, partitionLateDropPktCount, partitionLateDropPktCountHi, partitionLateDropByteCount,
                partitionLateDropByteCountHi, partitionSchedDropPktCount, partitionSchedDropPktCountHi, partitionSchedDropByteCount,
                partitionSchedDropByteCountHi, partitionFrameBytes, partitionFrameBytesHi, partitionFrameTargetRate, partitionFrameTargetRateHi,
                partitionFrameCount, partitionFrameCountHi, partitionEcnCount, partitionEcnCountHi } 
            STATUS current
            DESCRIPTION 
                "A collection of objects that provides information regarding the partitions configured on 
				the PacketShaper S-Series."
            ::= { bluecoatGroups 2 }

 	psClassObjectsGroup1 OBJECT-GROUP
            OBJECTS { classTableSize, className, classOwningPartName, classLinkDirection, classByteCount,
                	classByteCountHi, classPkts, classPktsHi, classDataPkts, classDataPktsHi, classReTxs, classReTxsHi, classReTxTosses,
                	classReTxTossesHi, classCirFails, classCirFailsHi, classCirAllocs, classCirAllocsHi, classPeakTcpConns, classTcpConnInits,
                	classTcpConnInitsHi, classTcpConnExits, classTcpConnExitsHi, classTcpConnRefuses, classTcpConnRefusesHi, classTcpConnIgnores,
                	classTcpConnIgnoresHi, classTcpConnAborts, classTcpConnAbortsHi, classTcpConnDenies, classTcpConnDeniesHi, classHits,
 	              	classHitsHi, classPolicyHits, classPolicyHitsHi, classRate, classRateHi, classPeakGuaranteedRateFlows, classReTxByteCount,
                	classReTxByteCountHi, classFullName, classCurrentRate, classCurrentRateHi, classPktExchangeTime, classPktExchangeTimeHi,
                	classPktExchangeTimeSamples, classClientFloodBlock, classServerFloodBlock, classPeakIpdgConns, classWebResponse2XX,
                	classWebResponse2XXHi, classWebResponse3XX, classWebResponse3XXHi, classWebResponse4XX, classWebResponse4XXHi, classWebResponse5XX,
                	classWebResponse5XXHi, classRtpExpectedPackets, classRtpExpectedPacketsHi, classRtpLostPackets, classRtpLostPacketsHi,
            		classRtpJitterCount, classRtpJitterSum, classRtpLatencyCount, classRtpLatencySum, classIcmpRttMsecsSum, classIcmpRttCount,
            		classIcmpAttemptCount, classNoBwDropBytesCount, classNoBwDropBytesCountHi, classTotalBytesCount, classTotalBytesCountHi } 
            STATUS current
            DESCRIPTION 
                "A collection of objects that provides information regarding the traffic classes configured on
				the PacketShaper S-Series."
            ::= { bluecoatGroups 3 }

	psAlarmObjectGroup1 OBJECT-GROUP
            OBJECTS { psAlarmInsideLinkCount, psAlarmOutsideLinkCount, psAlarmAuthFailCount,psAlarmBCAAAPrimaryCount, psAlarmBCAAASecondaryCount,
						psAlarmBCAAAPrimaryStatus, psAlarmBCAAASecondaryStatus, psAlarmCpuUtilizationPct, psAlarmPowerSystemOneCount, psAlarmPowerSystemOneStatus,
						psAlarmPowerSystemTwoCount, psAlarmPowerSystemTwoStatus, psAlarmFanOneCount, psAlarmFanOneStatus,  psAlarmFanTwoCount, psAlarmFanTwoStatus, 
						psAlarmFanThreeCount, psAlarmFanThreeStatus,  psAlarmFanFourCount, psAlarmFanFourStatus,  psAlarmFanFiveCount, psAlarmFanFiveStatus,
						psAlarmFanSixCount, psAlarmFanSixStatus, psAlarmVoltageSensorCount, psAlarmVoltageSensorStatus, psAlarmTemperatureSensorCount,
						psAlarmTemperatureSensorStatus, psAlarmMeasurementEngineCount, psAlarmMeasurementEngineStatus, psFeatureHighAvDeviceDownCount,
                        psFeatureHighAvDeviceDownStatus, psFeatureHighAvDeviceDownRouter, psFeatureHighAvDeviceDownInterface }
            STATUS current
            DESCRIPTION
                "A collection of objects that provides more information regarding various 
                 notification types that are sent by the PacketShaper S-series."
            ::= { bluecoatGroups 4 }

	psAdminObjectGroup1 OBJECT-GROUP
            OBJECTS { psSerialNumber, psUpTime, psShapingStatusAdmin }
            STATUS current
            DESCRIPTION
                "A collection of objects that provides more information regarding various 
                 admin related functions on the PacketShaper S-Series."
            ::= { bluecoatGroups 5 }

  	psNotificationGroup1 NOTIFICATION-GROUP
            NOTIFICATIONS { psAlarmLicenseExpired, psAlarmBCAAAPrimary, psAlarmBCAAASecondary, psAlarmPowerSystemOne, psAlarmPowerSystemTwo, psAlarmFan,
							psAlarmVoltageSensor, psAlarmTemperatureSensor, psAlarmMeasurementEngine, psAlarmUserEvent, psAlarmAgentEvent, psFeatureHighAvDeviceDown }
            STATUS current
            DESCRIPTION 
                "A collection of objects that provides information regarding various notification types
                 that can be sent by the PacketShaper S-Series."
            ::= { bluecoatGroups 6 }
	
  	psAlarmVarsGroup1 OBJECT-GROUP
            OBJECTS { psAlarmFanModuleID, psAlarmVoltageSensorID, psAlarmTemperatureSensorID }
            STATUS current
            DESCRIPTION 
                "A collection of objects that provides information regarding various notification types
                 that can be sent by the PacketShaper S-Series."
            ::= { bluecoatGroups 7 }

    psUserEventObjectGroup1 OBJECT-GROUP
           OBJECTS { userEventTrapName, userEventTrapExpression, userEventTrapVariable, userEventTrapElementType,
                userEventTrapRegid, userEventTrapDate, userEventTrapValue, userEventTrapTarget,
                userEventTrapRearm, userEventTrapDayCount, userEventTrapDayLimit, userEventTrapStatus,
                userEventTrapThreshold }
            STATUS current
            DESCRIPTION 
                "A collection of objects that provides information regarding user event trap sent by PacketShaper."
            ::= { bluecoatGroups 8 }
	
 	psAgentEventObjectGroup1 OBJECT-GROUP
            OBJECTS { agentEventTrapName, agentEventTrapDate, agentEventTrapType, agentEventTrapDescription }
            STATUS current
            DESCRIPTION 
                "A collection of objects that provides information regarding agent event trap sent by PacketShaper."
            ::= { bluecoatGroups 9 }


  	bluecoatCompliances OBJECT IDENTIFIER ::= { bluecoatConformance 2 }
    psCompliance1 MODULE-COMPLIANCE
            STATUS current
            DESCRIPTION
                "A collection of groups providing for Blue Coat Compliance module psCompliance1."
            MODULE BLUECOAT-PACKETSHAPER-S-SERIES-MIB    -- this module
                MANDATORY-GROUPS { psLinkObjectsGroup1, psPartitionObjectsGroup1, psClassObjectsGroup1, psAlarmObjectGroup1, 
				psAdminObjectGroup1, psNotificationGroup1, psAlarmVarsGroup1, psUserEventObjectGroup1, psAgentEventObjectGroup1 }
            ::= { bluecoatCompliances 1 }

    END

-- BLUECOAT-PACKETSHAPER-S-SERIES-MIB.my
