--=============================================================================
--
-- Proxim Corporation - Enterprise LAN Division 
-- 3950 Shackleford Rd. Suite 500
-- Duluth, GA 30096
-- USA
--
--=============================================================================
--
-- ORiNOCO Management Information Base (MIB)
--
--=============================================================================
--
-- FILENAME:	orinoco.mib
--
-- DESIGNER:	Daniel R. Borges (DRB)
--
-- TITLE:		ORiNOCO Management Information Base
--
-- USED IN:		ORiNOCO Product Line for SNMP Management.  This MIB is 
--				intended for the following products:
--								Access Point
--								Broadband Gateway
--								Outdoor Router
--
--=============================================================================
--
-- Document History Information
--
--=============================================================================
--
-- Version  Date	  Authors			Decription
--
--=============================================================================
-- v1.00    Aug 29    DRB, Lucent		Intitial Document Creation
--          2000
--=============================================================================
-- v1.10    Sept 01   DRB, Lucent		Removal of unecessary objects.
--          2000
--=============================================================================
-- v1.20    Sept 04   DRB, Lucent		Correction on Ranges for IAPP 
--          2000                        Parameters.
--=============================================================================
-- v1.30    Sept 07   DRB, Lucent		Appropriate values set fro the IAPP
--          2000                        Parameters.
--=============================================================================
-- v1.40    Sept 08   NRP, Lucent		Updated all objects.
--          2000
--=============================================================================
-- v1.50    Sept 12   DRB, Lucent		Added objects to enable/disable the
--          2000                        trap Groups and also added new traps.
--                                      Added Session Idle Timeout object to
--                                      PPP Group.
--=============================================================================
-- v1.60    Sept 26   DRB, Lucent		Change name of group from web to HTTP.
--          2000                        Added RG-2000 to ORiNOCO product tree.
--=============================================================================
-- v1.70    Oct 30    DRB, Lucent		Added trap and trap variable to inform
--          2000                        when a software task has suspended.
--=============================================================================
-- v1.80    Nov 15    DRB, Lucent		Changed underscore characters to dashes
--          2000                        and removed conflict between two trap
--                                      variables:
--                                           oriConfigurationTrapsStatus
--                                           oriTrapVarTaskSuspended
--=============================================================================
-- v1.90    Feb 05    DRB, Lucent		Sync up between ORiNOCO MIB and AS-2000
--          2001                        MIB objects.  The following changes
--                                      were made:
--                                      1. Changed the following indeces from
--                                         non-accessible to read-only:
--                                         - oriSNMPAccessTableIndex
--                                         - oriSNMPTrapHostTableIndex
--                                         - oriProtocolFilterTableIndex
--                                         - oriAccessControlTableIndex
--                                         - oriStaticMACAddressFilterTableIndex
--                                         - oriLinkIntTableIndex
--                                         - oriPPPMACtoIPTableIndex
--                                         - oriPPPIPPoolTableIndex
--                                         - oriDHCPServerIPPoolTableIndex
--                                         - oriProxyAgentAPTableIndex
--                                         - oriStormThresholdIfIndex
--                                      2. Added the following objects:
--                                         - oriSystemInvMgmtBSPBootloaderVersion
--                                         - AS Client IPX Table
--                                      3. Change to range value of 
--                                         oriTFTPFileType, included all file
--                                         type available on the AS-2000 
--                                         device.  This should be reviewed 
--                                         and decided if going to be supported
--                                         in other ORiNOCO devices.
--                                      4. Added the following objects the 
--                                         the Link Test Table:
--                                             - oriLinkTestInterface
--                                             - oriLinkTestRadioType
--                                      5. Added Access Server IAPP station 
--                                         table to IAPP group.
--                                      6. Added Traps for RADIUS Auth and 
--                                         Acct not configured.
--                                      7. Changed range on 
--                                         oriPPPSessionIdleTimeout object.
--=============================================================================
-- v2.00    Feb 13	  DRB, Lucent		Added the following objects to sync up
--          2001                        AS-2000 MIB:
--										    - oriIfProfileCode
--											- oriSystemReboot
--											- oriSystemContactEmail
--											- oriIfMACAddress
--										Made Inventory Management a sub-group
--										of System Group.
--										Removed oriPPPNumIPPoolTableEntry from
--										PPP group - duplicate object.
--=============================================================================
-- v2.01    Feb 13    DRB, Lucent		Added default value to appropriate
--          2001                        objects.
--=============================================================================
-- v2.02    Mar 05    DRB, Agere		Following Changes have been made to the
--          2001                        ORiNOCO MIB:
--                                      1. Created Interface group and placed
--                                         wireless and ethernet interfaces as
--                                         sub-group.
--                                      2. Created two tables under the
--                                         wireless interface group for
--                                         properties and security objects.
--                                      3. Create IP and IPX sub-group under
--                                         Network group.
--                                      4. Moved DHCP Client Type into the 
--                                         Network IP sub-group.
--                                      5. Created Authentication and
--                                         Accounting sub-groups under the
--                                         RADIUS group.
--                                      6. Created Hardware, Software,
--                                         Firmware, and BSP/BL sub-groups
--                                         under System Inventory Mgmt Group.
--                                      7. Removed 
--                                         oriIfInvMgmtRadioFirmwareDate for it
--                                         does not exist.
--                                      8. Renamed oriWirelessIfDeliveryTraffi-
--                                         cIndicationMap to 
--                                         oriWirelessIfDTIMPeriod and made
--                                         corrections to description.
--                                      9. Created Miscellaneous Trap group.
--=============================================================================
-- v2.03    Mar 14    DRB, Agere		Following Changes have been made to the
--          2001                        ORiNOCO MIB:
--                                      1. Add delete as an integer value to
--                                         the following tables:
--                                             - oriProtocolFilterTable
--                                             - oriAccessControlTable
--                                             - oriStaticMACAddressFilterTable
--                                      2. Added the following object required
--                                         for AP-2000 software:
--                                             -  oriSystemContactPhoneNumber
--                                             -  oriProtocolFilterProtocol-
--                                                Comment to Protocol Table.
--                                             -  oriHTTPUserName
--                                      3. Fixed range for Storm Threshold
--                                         Broadcast and Multicast Objects.
--                                      4. Removed the 
--                                         oriStormThresholdIfIndex from
--                                         Storm Threshold table.  The IfIndex
--                                         from MIB-II interface table shall
--                                         be used.
--                                      5. Moved Gateway IP Address, default
--                                         lease time, maximum lease time from
--                                         DHCP group to the DHCP IP Pool 
--                                         Table.
--=============================================================================
-- v2.04    Mar 26    DRB, Agere		Removed Proxy Agent Group.
--          2001                        Specified values for 
--                                      oriSNMPAccessTableInterface.
--                                      Added SNMPSetupStatus in order to
--                                      enable/disable SNMP based Management.
--                                      Added oriIAPPSendAnnounceRequestOnStart
--                                      to the IAPP Group.
--                                      Added the following objects to the 
--                                      Systems Group:
--                                       - oriSystemFlashUpdate
--                                       - oriSystemFlashBackupInterval
--                                       - oriSystemEmergencyResetToDefault
--                                      Added the following Groups:
--                                       - Proxy ARP (orinocoProxyARP)
--                                       - Spanning Tree (orinocoSpanningTree)
--                                       - PTP (orinocoPTP)
--=============================================================================
-- v2.05    Mar 30    DRB, Agere		Added Import of ifIndex from RFC-1213
--          2001                        and correct object name ot ifIndex.
--=============================================================================
-- v2.06    Apr 03    DRB, Agere		Removed the
--          2001                        oriSNMPTestReadWritepassword from the
--                                      MIB.
--=============================================================================
-- v2.07    Apr 10    DRB, Agere		Renamed Inventory Management Objects
--          2001                        from ComputerID to ComponentID.
--										Defined Inventory Management Parameters
--										for BSP/BL, ORiNOCO MIB, and Wireless
--										Interface Cards.
--=============================================================================
-- v2.08    Apr 18    DRB, Agere		Added Wireless Card primary firmware
--          2001                        inventory management objects, compID,
--										variant, major, and minor versions.
--=============================================================================
-- v2.09    Apr 26    DRB, Agere		Changed PTP group name to WDS.
--          2001                        Modified the Spanning Tree Status
--                                      object modifying enable/disable
--                                      enumeration.
--=============================================================================
-- v2.10    May 09    DRB, Agere		Added the following Traps:
--          2001                         oriTrapZeroSizeImage
--                                       oriTrapInvalidImage
--                                       oriTrapImageTooLarge
--                                       oriTrapBootPFailed
--                                       oriTrapDHCPFailed
--                                       oriTrapDuplicateIPAddressEncountered
--                                       oriTrapWLCVoltageDiscrepancy
--                                       oriTrapWLCIncompatibleVendor
--                                       oriTrapWLCFirmwareDonwloadFailure
--                                       oriTrapWLCIncompatibleFirmware
--                                      Added the following Trap Variables:
--                                       oriTrapVarUnauthorizedClientMACAddress
--                                       oriTrapVarWirelessCard
--                                      Added object in order to enable/disable
--                                      the image trap group.
--=============================================================================
-- v2.11    May 16    DRB, Agere		Added necessary objects to support
--          2001                        AP-2000 features/modules:
--                                       oriWirelessIfLoadBalancing
--                                       oriWirelessIfMediumDensityDistribution
--                                       oriStaticMACAddressFilterComment
--                                       oriDHCPServerIPPoolTableDNSIPAddress
--                                      Added 802.1x group with one object to
--                                      enable/disable this feature.
--                                      Added the following traps:
--                                       oriTrapIncompatibleImage
--=============================================================================
-- v3.00    May 18    DRB, Agere		Converted MIB Definition from SMIv1 to
--          2001                        SMIv2.  Modified 802.1x group to
--                                      security group and added security
--                                      configuration object and encryption key
--                                      length table per wireless interface.
--=============================================================================
-- v3.01    May 21    DRB, Agere		Added RG-1100 in the product branch as
--          2001                        orinocoproduct number 8.  Updated
--                                      comments to the link integrity objects.
--                                      Corrected RADIUS shared secret from
--                                      read-only to read-write.  Added index
--                                      to interface table.  Created a generic
--                                      inventory management table for
--                                      components and component interfaces.
--=============================================================================
-- v3.02    May 23/24    DRB, Agere		Added Protocol Packet Filter sub-group
--          2001                        under Filtering Group.  Added interface
--                                      bit mask to Protocol Filtering table.
--                                      Added PPPoE Group.  Removed Gateway IP
--                                      Address, Subnetmask, and DNS IP Address
--                                      from DHCP Server Table and made them
--                                      scalar objects.  Added Secondary DNS IP 
--                                      Address in DHCP group.
--                                      Added System mode to be supported by
--                                      RG-2.  Added Configuration File group
--                                      for RG-2.  Added HTTP file name 
--                                      table, refresh delay, and HTTP mgmt per
--                                      interface in the HTTP group.  Added
--                                      DNS Redirect Group.  Added Event Log
--                                      to system group.  Added an AOL group.
--                                      Changed EthernetIf Settings into a
--                                      table since RG-2 has two ethernet ifs.
--                                      Added network IP configuration table
--                                      since RG-2 has two ethernet interfaces.
--=============================================================================
-- v3.03    May 30       DRB, Agere		Corrected oriPPPoEMACtoSessionTableISP-
--          2001                        Name object type to DisplayString.
--=============================================================================
-- v3.04    June 11     DRB, Agere		Updated trap description with severity
--          2001                        level.  Changed trap variables from
--                                      read-only to not-accessible.
--=============================================================================
-- v3.05    June 20     DRB, Agere		Added two new sub-groups to the DHCP
--          2001                        group, namely server and client.
--                                      Added Create State to all tables.
--                                      Modified oriConfigFileName to read-only
--                                      Added index to the oriPPPoESessionTable
--                                      and oriPPPoEMACtoSessionTable.
--                                      Changed HTTP Status and SNMP Status
--                                      interface bit mask.  Modified
--                                      description on multicast rate.
--=============================================================================
-- v3.06    June 21     DRB, Agere		Removed IP Address Type object, since
--          2001                        object added to DHCP client group.
--                                      Added index to EventLog Table and
--                                      added create to HTTP table status
--                                      object.  Changed data-type of WEP keys
--                                      to OCTET STRING.  Added statement
--                                      to description of objects that ought to
--                                      be treated as write-only (masked):
--                                        - Encryption Keys (WEP)
--                                        - Passwords
--                                        - RADIUS Shared Secret
--=============================================================================
-- v3.07    Oct 15     	DRB, Agere		Added ADSL Interface Group as a
--          2001                        subgroup to ORiNOCO Interface.
--=============================================================================
-- v3.08    Oct 16, 17 	DRB, Agere		Changed data-type of WEP keys to 
--          2001                        DisplayString.  Added object to SNMP
--                                      group disable/enable the IP Access
--                                      Table.  Added object for Protocol
--                                      Filter interface bit mask.  Added the
--                                      port filter sub-group to filtering 
--                                      group.  Removed Primary and Secondary
--                                      DNS IP address objects from DHCP Server
--                                      group and added it to DNS group.
--                                      Changed DNSRedirect group to DNS group.
--                                      Changed OID of DHCP Client ID object to
--                                      1 (instead of 2).  Removed DHCP Client
--                                      address type since it is already in the
--                                      network group.  Added NAT group.  Added
--                                      system user name and password for HTTP
--                                      and telnet access.  Removed default
--                                      values for network IP address, subnet 
--                                      mask and gateway IP address objects 
--                                      since it is product specific.  Added
--                                      manual value to PPPoE WAN Connect mode
--                                      object.  Added a PPPoE WAN connect mode
--                                      status object.  Added a Ping Test
--                                      group.  Added a mask for filtering the
--                                      severity of the event log table.
--                                      Changed the following object names:
--                                        oriProtocolFilterIfMask to
--                                           oriProtocolFilterInterfaceBitMask
--                                        oriProtocolFilterFlag to
--                                           oriProtocolFilterOperationType
--                                      Added Counter64 to data type import
--                                      list.  Changed MAX-ACCESS of trap
--                                      variables from not-accessible to
--                                      read-only.  Updated contact info for
--                                      MIB module identity.  Removed Event Log
--                                      index from Event Log Table.
--=============================================================================
-- v3.09    Oct 22 	DRB, Agere			Removed the following traps:
--          2001                            oriTrapsADSLIfProfile0Status
--                                          oriTrapsADSLIfProfile1Status
--                                      Added a single trap control object for
--                                      ADSL interface related traps and added
--                                      and ADSL trap group.
--=============================================================================
-- v3.10    Oct 23 	DRB, Agere			Changed the ADSL Interface Profile
--          2001                        configuration to index 1 and 2.
--=============================================================================
-- v3.11    Oct 30 	DRB, Agere			Added ADSL Advanced Statistics Group
--          2001                        and respective objects.
--=============================================================================
-- v3.12    Oct 31 	DRB, Agere			Added the following objects to the
--          2001                        System group for Telnet and HTTP
--                                      interface access:
--                                          - oriSystemAccessUserName
--                                          - oriSystemAccessPassword 
--                                          - oriSystemAccessLoginTimeout 
--                                          - oriSystemAccessIdleTimeout    
--=============================================================================
-- v3.13    Dec 03 	DRB, Agere			Added objects for the following 
--          2001                        feature groups:
--										    - HereUare
--										    - SpectraLink VoIP
--										    - Advanced Bridging Filter
--                                      Modified Proxy ARP group to IP/ARP
--                                      group and added required objects for
--                                      IP/ARP filtering.
--                                      Changed the following table object 
--                                      names for consistency:
--                                          - oriAccessControlMACAddress ->
--											  oriAccessControlTableMACAddress
--                                          - oriAccessControlComment ->
--                                            oriAccessControlTableComment
--                                          - oriAccessControlEntryStatus ->
--                                            oriAccessControlTableEntryStatus
--                                          - oriLinkIntTableStatus ->
--                                            oriLinkIntTableEntryStatus
--                                          - oriWDSSetupTableStatus ->
--                                            oriWDSSetupTableEntryStatus
--                                      Changed default value of 
--                                      oriTelnetLoginTimeout to 30 seconds.
--                                      Changed description of 
--                                      oriLinkIntPollInterval.
--                                      Added oriHTTPHelpInformationLink to 
--                                      HTTP group.
--                                      Added oriTrapWLCFirmwareFailure trap.
--                                      Changed the values of the Wireless Card
--                                      Distance between APs object to support
--                                      UHD firmware enhancement.
--                                      Added oriWirelessIfAutoChannelSelect
--                                      object to Wireless If Properties table.
--=============================================================================
-- v3.14    Dec 18 	DRB, Agere			Added VLAN group and required objects.
--          2001                        Added Primary and Secondary DNS Server
--                                      IP Addresses to DHCP Server group.
--                                      Updated description of Link Integrity
--                                      Interval and default value definition.
--                                      Default value defined for Link Test
--                                      table timeout.  Changed location of
--                                      MODULE-IDENTITY macro to comply with
--                                      SNMP v2c.  Modififed IAPP 
--                                      Retransmission default value to 4.
--                                      Modified the following object names for
--                                      consistency:
--                                        - oriNetworkIPXClientStatus ->
--                                          oriNetworkIPXClientTableEntryStatus
--                                        - oriRADIUSAuthServerStatus ->
--                                          oriRADIUSAuthServerTableEntryStatus
--                                        - oriRADIUSAcctServerStatus ->
--                                          oriRADIUSAcctServerTableEntryStatus
--                                        - oriWirelessIfEncryptionStatus ->
--                                          oriWirelessIfEncryptionTableEntryStatus
--                                        - oriStaticMACAddressFilterStatus ->
--                                          oriStaticMACAddressFilterTableEntryStatus
--                                        - oriBroadcastFilteringStatus ->
--                                          oriBroadcastFilteringTableEntryStatus 
--                                      Added trap variable to specify the
--                                      client failed authentication type.
--                                      Modified enterprise OID to Agere 
--                                      Systems assigned OID number 11898.
--=============================================================================
-- v3.15    Jan 08 	DRB, Agere			Updated description for 
--          2002                        oriWirelessIfAllowedSupportedDataRates.
--                                      Modified the VLAN group to include
--                                      the following objects:
--                                          - Status
--                                          - Frame Types
--                                          - Table of VLAN IDs
--                                      Added the following groups, subgroups,
--                                      and objects for the OR-2000 Product.
--                                          - orinocoWORP
--                                          - orinocoWORPConfiguration
--                                          - orinocoWORPAuthentication
--                                          - orinocoDHCPRelay
--                                      Added 5 Traps for the OR-2000 Product. 
--                                      Changed default value for Auto Channel
--                                      Select object.  Modified status of
--                                      oriTelnetSessions to obsolete since no
--                                      longer used.
--                                      Modified the following object names for 
--                                      consistency:
--                                       - oriProtocolFilterStatus ->
--                                         oriProtocolFilterTableEntryStatus
--                                       - oriWirelessIfAutoChannelSelect ->
--                                         oriWirelessIfAutoChannelSelectStatus 
--                                       - oriWirelessIfEncryptionTableEntryStatus
--                                         oriWirelessIfEncryptionStatus
--=============================================================================
-- v3.16    Jan 28 	DRB, Agere			Added Textual Convention for VLAN Tag 
--          2002                        ID Type.  Added VLAN Mgmt Tag ID to
--                                      VLAN group.  Changed the VLAN ID object
--                                      type to the defined textual convention.
--                                      Added the following groups, subgroups,
--                                      tables, and objects for mgmt of the
--                                      COR/ROR-2000 product, which could be
--                                      used by other products in the future:
--                                       - WORP Interface Config Subgroup and
--                                         table to orinocoIf group.
--                                       - WORP Statistics table to WORP
--                                         Interface subgroup.
--                                       - Feature based Licensing subgroup to
--                                         orinocoSys and added Feature table.
--                                       - Added group for monitoring station 
--                                         statistics, orinocoStationStats  
--                                      Modified the trap OIDs for conformance
--                                      with SMIv2 and SNMPv2c.
--                                      Removed the orinocoWORP group and
--                                      subgroups since this group was moved to
--                                      a subgroup for orinocoIf.  Added RIP
--                                      subgroup to orinocoNETRIP.
--=============================================================================
-- v3.17    Feb 04 	DRB, Agere			Added Textual convention for Interface
--          2002                        Bitmask object.
--                                      Updated the description for the
--                                      following objects:
--                                       - oriSystemMode
--                                       - oriHTTPWebsiteNameTable
--                                       - oriHTTPWebSitenameTableIndex  
--                                       - oriHTTPWebSiteFilename 
--                                       - oriHTTPWebSiteLanguage
--                                       - oriHTTPWebSiteDescription
--                                       - oriHTTPWebSitenameTableStatus
--                                       - oriNetworkIPConfigTable
--                                       - oriSNMPAccessTableInterfaceBitmask
--                                       - oriSNMPInterfaceBitmask
--                                       - oriProtocolFilterInterfaceBitmask
--                                       - oriPortFilterTableEntryInterfaceBitmask
--                                       - oriTelnetInterfaceBitmask
--                                       - oriHTTPInterfaceBitmask
--                                       - oriSystemFeatureTable
--                                       - oriSystemFeatureTableEnry
--                                       - oriWORPIfConfigTableRegistrationTimeout
--                                       - oriWORPIfConfigTableRetries
--                                      Corrected the Notification Type OID.
--                                      Removed VLAN Frame Type Object and
--                                      reassigned OIDs to VLAN groups.
--=============================================================================
-- v3.18    Feb 05 	DRB, Agere			Added Tx Rate control to Wireless
--          2002                        interface table.
--=============================================================================
-- v3.19    Feb 21 	DRB, Agere			Corrected enumerated values for station
--          2002                        statistics table station type.  Added
--                                      object for enabling/disabling
--                                      monitoring station statistics.
--=============================================================================
-- v3.20    Mar 25 	DRB, Agere			Merge between previous MIB version and
--          2002                        BG MIB.
--                                      Added TEXTUAL-CONVENTION, 
--                                      MODULE-COMPLIANCE, and OBJECT-GROUP.
--                                      Modified INTEGER to Integer32 for the
--                                      VlanId textual convention.
--                                      Changed module identity and the
--                                      MIB tree structure.
--                                      Added oriSystemAccessMaxSessions to the
--                                      orinocoSys group.
--                                      Modified the enumerated values for the
--                                      oriTFTPFileType object.
--                                      Added the following object for 
--                                      Bandwidth Throttling feature:
--                                       - oriWirelessIfBandwidthLimitIn
--                                       - oriWirelessIfBandwidthLimitOut
--                                       - oriEthernetIfBandwidthLimitIn
--                                       - oriEthernetIfBandwidthLimitOut
--                                      Added oriDHCPClientInterfaceBitmask to 
--                                      DHCP Client subgroup.
--                                      Removed the following WORP Traps:
--                                       - oriWORPLinkDown
--                                       - oriWORPRegistrationIndication
--                                       - oriWORPSystemAuthenticationFailure
--                                      Added the following WORP Traps:
--                                       - oriWORPStationRegister
--                                       - oriWORPStationDeRegister
--                                      Added the following traps for System
--                                      Feature based License:
--                                       - oriTrapIncompatibleLicenseFile
--                                       - oriTrapFeatureNotSupported
--                                       - oriTrapZeroLicenseFiles
--                                       - oriTrapInvalidLicenseFile
--                                       - oriTrapUselessLicense
--                                      Added oriTrapVarInterface to the trap
--                                      variable group.
--                                      Changed type from Gauge32 to Integer32
--                                      and configured ranges for the following
--                                      objects:
--                                       - oriWORPIfStatTableAverageLocalSignal
--                                       - oriWORPIfStatTableAverageLocalNoise
--                                       - oriWORPIfStatTableAverageRemoteSignal
--                                       - oriWORPIfStatTableAverageRemoteNoise
--                                       - oriStationStatTableInSignal
--                                       - oriStationStatTableInNoise
--                                       - oriStationStatTableRemoteSignal
--                                       - oriStationStatTableRemoteNoise
--                                      Configured ranges for the following
--                                      objects:
--                                       - oriStationStatTableIndex
--                                      Updated description for the following
--                                      objects:
--                                       - oriStationStatTableAdminStatus
--                                       - oriStationStatTableOperStatus
--                                       - oriTrapAuthenticationFailure
--                                       - oriSystemFeatureTable
--                                      Removed the following objects from the
--                                      oriWORPIfStatTable:
--                                       - oriWORPIfStatTableRegistrationAborts
--                                       - oriWORPIfStatTableRequestIgnored
--                                       - oriWORPIfStatTableQueueLength
--                                      Added oriWORPIfConfigTableNetworkSecret
--                                      to oriWORPIfTable.
--                                      Removed orinocoNetRIP subgroup.
--=============================================================================
-- v3.21    Apr 01 	DRB, Agere			Updated the ADSL Interface Group with
--          2002                        requirements provided by BG team.
--                                      Changed object descriptions to be 
--                                      generic and providing more information.
--                                      oriWirelessIfMACAddress status has been
--                                      changed to deprecated.
--                                      oriTelnetSessions status has been
--                                      changed to deprecated.
--                                      Added Trap for invalid VLAN ID
--                                      configuration.
--                                      Changed the data type and range for
--                                      oriWirelessIfEncryptionTxKey to
--                                      integer32 and size of 0-3.
--                                      Removed wep enumerated value from the
--                                      oriSecurityConfiguration object.
--=============================================================================
-- v3.22    Apr 24 	DRB, Agere			Added rekeying interval object to the
--          2002                        Security Group.
--=============================================================================   
-- v3.23    June 25 DRB, Agere			Added the following groups/subgroups/
--          2002                        objects to support AP-2000 2.1 release:
--                                       - Packet Forwarding
--                                       - IBSS Traffic Control
--                                       - Syslog
--                                       - DNS Client
--                                       - Syslog
--                                      Added RADIUS MAC Address format object
--                                      to RADIUS group.  Added RADIUS Server
--                                      name and addressing type to both 
--                                      Authentication and Accounting RADIUS 
--                                      Server tables.
--=============================================================================
-- v3.24    June 28 DRB, Agere			Changed RADIUS IP Address object status
--          2002                        to obsolete.  Added two enumerated
--                                      values to PPPoE Session Connect Mode.
--                                      Added object to configure the interface
--                                      where the PPPoE client should try to
--                                      establish a PPPoE connection.
--=============================================================================
-- v3.25    July 2 DRB, Agere			Added default value for RADIUS Server
--          2002                        Addressing Format.  Added object to HTTP
--                                      group for enabling/disabling SSL.
--=============================================================================
-- v3.26    July 17 DRB, Agere			Added certificate to TFTP File Type
--          2002                        Object.  Added SSL password to HTTP
--                                      group.  Added AlphaOne to the orinoco
--                                      product tree.
--=============================================================================
-- v3.27    July 23 DRB, Agere			Added two additional values to RADIUS
--          2002                        MAC address delimiters.  Changed DNS 
--										Client status default value to disable.
--										Removed PPPoE Connection Interface obj.
--										Removed value from PPPoE connect mode.
--										Added Trap for when the DNS client can
--										not resolve a specified host name.
--										Added Turbo Mode obj in Wireless If
--										properties table.  Updated description
--										on the data rates obj to address Turbo
--										mode speeds.  Added value to key length
--										table for wide-key support.  Added trap
--										for Radar Interference detected.
--										Corrected values in the encryption key
--										lenght table.  Added object to enable
--										or disable the HTTP setup wizard.
--=============================================================================
-- v3.28    Aug 20 DRB, Agere			Added orinocoSNTP group and respective
--          2002                        mgmt objs.  Removed SSL and HereUare
--                                      objs since not supported.
--=============================================================================
-- v3.29    Sept 04 DRB, Proxim			Added trap for SNTP failure.  Changed
--          2002                        MIB header and Module Identity to
--                                      Proxim Corporation.
--=============================================================================
-- v3.30    Sept 18 DRB, Proxim			Removed certificate from the TFTP File
--          2002                        type values.  Removed AlwaysOnForRADIUS
--                                      from the PPPoE WAN connect mode values.
--=============================================================================
-- v3.31    Nov  23  AP, Proxim			Removed onehundredandfiftytwo option (for 11a cards) from oriSecurityEncryptionKeyLength
-- 		2002						object 
--=============================================================================
--
-- COMPILERS:	NuDesign, MG-Soft, VxWorks, and HP-OpenView MIB Compilers
--
--=============================================================================

--=============================================================================
--				     Copyright (C) 2002 Proxim Corporation
--						Proxim Corporation - PROPRIETARY
--		Disclosure to third parties or reproduction in any from
--		whatsoever, without prior written consent, is strictly forbiden.
--=============================================================================

--=============================================================================
-- Includes
--=============================================================================

--#condInclude "rfc1155.smi"
--#condInclude "rfc1212.smi"
--#condInclude "rfc1213.inc"
--#condInclude "rfc1215.smi"

--=============================================================================
-- ORiNOCO MIB Begin
--=============================================================================
				
ORiNOCO-MIB DEFINITIONS ::= BEGIN

--=============================================================================
-- ORiNOCO MIB Imports
--=============================================================================

IMPORTS

	MODULE-IDENTITY, OBJECT-TYPE, NOTIFICATION-TYPE, OBJECT-IDENTITY, 
	enterprises, IpAddress, Counter32, Gauge32, TimeTicks, Integer32, 
	Counter64
        FROM SNMPv2-SMI
	
	DisplayString, PhysAddress, MacAddress, TruthValue, TimeStamp, 
	TimeInterval, DateAndTime, RowStatus, TEXTUAL-CONVENTION
	    FROM SNMPv2-TC

	MODULE-COMPLIANCE, OBJECT-GROUP
	    FROM SNMPv2-CONF

    ifIndex
        FROM RFC1213-MIB;

--=============================================================================
-- ORiNOCO MIB Module Identity: orinoco
--=============================================================================

orinoco MODULE-IDENTITY
    LAST-UPDATED "200211230000Z"
    ORGANIZATION "Proxim Corporation"
        CONTACT-INFO 
           "Daniel R. Borges
        Proxim Corporation
        Enterprise LAN Division
            3950 Shackleford Rd. Suite 500
            Duluth, GA 30096
            USA
            Tel:   +1.678.924.6533
            Fax:   +1.678.924.6512
        Email: drborges@proxim.com"
        DESCRIPTION
            "MIB Definition used in the ORiNOCO Wireless Product Line:
             iso(1).org(3).dod(6).internet(1).private(4).enterprises(1).
         agere(11898).orinoco(2)"
    ::= { agere 2 }
       
--=============================================================================
-- Definition of Textual Conventions
--=============================================================================

    VlanId ::= TEXTUAL-CONVENTION
        STATUS current
        DESCRIPTION
            "A 12-bit VLAN ID used in the VLAN Tag header."
    SYNTAX Integer32 (0..4094)
        
    InterfaceBitmask ::= TEXTUAL-CONVENTION
        STATUS current
        DESCRIPTION
            "An Interface Bitmask used to enable or disable access or
            functionality of an interface in the system.  Each bit in this 
            object represents a network interface in the system consistent 
            with the ifIndex object in MIB-II.  The value for this object is
            interpreted as a bitfield, where the value of 1 means enabled.
            Examples of Usage:            
        1. For a system with the following interfaces:
             - Ethernet If = 1
             - Loopback If = 2
             - Wireless If A = 3
             - Wireless If B = 4
            Interface Bitmask usage:
             - 00000000 (0x00): all Interfaces disabled
             - 00000001 (0x01): Ethernet If enabled
             - 00000100 (0x04): Wireless If A enabled
             - 00001000 (0x08): Wireless If B enabled
             - 00001101 (0x0D): All Interfaces enabled
             - 00001111 (0x0F): All Interfaces enabled (see Note)
             - 00000101 (0x05): Ethernet and Wireless If A enabled
             - 00000111 (0x07): Ethernet and Wireless If A enabled (see Note)
            Note: The internal loopback interface bit (00000010, 0x02) is
            ignored in the usage of the interface bitmask object.

        2. For a system with the following interfaces:
             - Ethernet WAN If = 1
             - Ethernet LAN If = 2
             - Wireless If A = 3
            Inteface Bitmask usage:
             - 00000000 (0x00): all Interfaces disabled
             - 00000001 (0x01): Ethernet WAN If enabled
             - 00000010 (0x02): Ethernet LAN If enabled
             - 00000011 (0x03): Ethernet WAN and LAN If enabled
             - 00000100 (0x04): Wireless If A enabled
             - 00000101 (0x05): Ethernet WAN and Wireless If A enabled
             - 00000110 (0x06): Ethernet LAN and Wireless If A enabled
             - 00000111 (0x07): All Interfaces enabled
             
            3. For a system with the following interfaces:
             - Ethernet If = 1
             - Loopback If = 2
             - Wireless If A = 3
            Interface Bitmask usage:
             - 00000000 (0x00): all Interfaces disabled
             - 00000001 (0x01): Ethernet If enabled
             - 00000100 (0x04): Wireless If A enabled
             - 00000101 (0x05): Ethernet and Wireless If A enabled
             - 00000111 (0x07): Ethernet and Wireless If A enabled (see Note)
            Note: The internal loopback interface bit (00000010, 0x02) is
            ignored in the usage of the interface bitmask object."
        SYNTAX Integer32 (0..255)

--=============================================================================
-- Definition of Agere MIB OID Tree
--=============================================================================

agere						OBJECT IDENTIFIER ::= { enterprises 11898 }

--=============================================================================
-- Definition of the ORiNOCO MIB Objects: orincoObjects
--=============================================================================

orinocoObjects				OBJECT IDENTIFIER ::= { orinoco 1 }

--=============================================================================
-- Definition of the ORiNOCO Notifications: orinocoNotifications
--=============================================================================

orinocoNotifications		OBJECT IDENTIFIER ::= { orinoco 2 }

--=============================================================================
-- Definition of the ORiNOCO Conformance: orinocoConformance
--=============================================================================

orinocoConformance    		OBJECT IDENTIFIER ::= { orinoco 3 }
orinocoGroups				OBJECT IDENTIFIER ::= { orinocoConformance 1 }
orinocoCompliances			OBJECT IDENTIFIER ::= { orinocoConformance 2 }

--=============================================================================
-- Definition of the ORiNOCO Products: orinocoProducts
--=============================================================================

orinocoProducts        		OBJECT IDENTIFIER ::= { orinoco 4 }

ap1000          			OBJECT IDENTIFIER ::= { orinocoProducts 1 }
rg1000          			OBJECT IDENTIFIER ::= { orinocoProducts 2 } 
as1000          			OBJECT IDENTIFIER ::= { orinocoProducts 3 }
as2000          			OBJECT IDENTIFIER ::= { orinocoProducts 4 }
ap500           			OBJECT IDENTIFIER ::= { orinocoProducts 5 }
ap2000          			OBJECT IDENTIFIER ::= { orinocoProducts 6 }
bg2000          			OBJECT IDENTIFIER ::= { orinocoProducts 7 }
rg1100          			OBJECT IDENTIFIER ::= { orinocoProducts 8 }
or2000          			OBJECT IDENTIFIER ::= { orinocoProducts 9 }
alphaOne					OBJECT IDENTIFIER ::= { orinocoProducts 10 }

--=============================================================================
-- Definition of the ORiNOCO MIB Object Groups and Subgroups
--=============================================================================

-- System Group and System Inventory Management Group
orinocoSys                  OBJECT IDENTIFIER ::= { orinocoObjects 1 }

    -- Interface Group
orinocoIf		            OBJECT IDENTIFIER ::= { orinocoObjects 2 }
	
	-- Network Group
orinocoNet		            OBJECT IDENTIFIER ::= { orinocoObjects 3 }
	
	-- SNMP Group
orinocoSNMP                 OBJECT IDENTIFIER ::= { orinocoObjects 4 }
	
	-- Filtering Group
orinocoFiltering			OBJECT IDENTIFIER ::= { orinocoObjects 5 }

    -- Remote Authentication Dial In User Service Group
orinocoRADIUS				OBJECT IDENTIFIER ::= { orinocoObjects 6 }

    -- Telnet Group
orinocoTelnet				OBJECT IDENTIFIER ::= { orinocoObjects 7 }

    -- TFTP Group
orinocoTFTP				 	OBJECT IDENTIFIER ::= { orinocoObjects 8 }

    -- Serial Group
orinocoSerial				OBJECT IDENTIFIER ::= { orinocoObjects 9 }

    -- Inter-Access Point Protocol Group
orinocoIAPP					OBJECT IDENTIFIER ::= { orinocoObjects 10 }

    -- Link Test Group
orinocoLinkTest				OBJECT IDENTIFIER ::= { orinocoObjects 11 }

    -- Link Integrity Group
orinocoLinkInt	            OBJECT IDENTIFIER ::= { orinocoObjects 12 }

    -- Encryption Control Protocol Group
orinocoECP					OBJECT IDENTIFIER ::= { orinocoObjects 13 }

    -- Point to Point Group
orinocoPPP					OBJECT IDENTIFIER ::= { orinocoObjects 14 }

    -- Dynamic Host Configuration Protocol Group
orinocoDHCP					OBJECT IDENTIFIER ::= { orinocoObjects 15 }

    -- HTTP (web) Group
orinocoHTTP					OBJECT IDENTIFIER ::= { orinocoObjects 16 }

	-- WDS Group
orinocoWDS					OBJECT IDENTIFIER ::= { orinocoObjects 17 }

    -- Traps Group
orinocoTrap					OBJECT IDENTIFIER ::= { orinocoObjects 18 }

	-- IP/ARP Group
orinocoIPARP				OBJECT IDENTIFIER ::= { orinocoObjects 19 }
	
	-- Spanning Tree Group
orinocoSpanningTree			OBJECT IDENTIFIER ::= { orinocoObjects 20 }
	
	-- Security Group
orinocoSecurity				OBJECT IDENTIFIER ::= { orinocoObjects 21 }

	-- PPPoE Group
orinocoPPPoE				OBJECT IDENTIFIER ::= { orinocoObjects 22 }
	
-- Configuration Group
orinocoConfig				OBJECT IDENTIFIER ::= { orinocoObjects 23 }

	-- DNS Group
orinocoDNS					OBJECT IDENTIFIER ::= { orinocoObjects 24 }

	-- AOL Group
orinocoAOL					OBJECT IDENTIFIER ::= { orinocoObjects 25 }
				
	-- NAT Group
orinocoNAT					OBJECT IDENTIFIER ::= { orinocoObjects 26 }

	-- Ping Group
orinocoPing					OBJECT IDENTIFIER ::= { orinocoObjects 27 }

	-- SpectraLink VoIP Group
orinocoSpectraLink			OBJECT IDENTIFIER ::= { orinocoObjects 29 }				
	
	-- VLAN Group
orinocoVLAN					OBJECT IDENTIFIER ::= { orinocoObjects 30 }

-- DMZ Group
orinocoDMZ					OBJECT IDENTIFIER ::= { orinocoObjects 31 }	

-- OEM Group
orinocoOEM					OBJECT IDENTIFIER ::= { orinocoObjects 32 }	

    -- Station Statistics Group
orinocoStationStatistics	OBJECT IDENTIFIER ::= { orinocoObjects 33 }
	
-- Simple Network Time Protocol Group
orinocoSNTP					OBJECT IDENTIFIER ::= { orinocoObjects 34 }

--=============================================================================
-- Definition of the System Subgroups
--=============================================================================

    -- System Inventory Management Subgroup
	orinocoSysInvMgmt		OBJECT IDENTIFIER ::= { orinocoSys 1 }
	
    -- System Feature based License Subgroup
orinocoSysFeature			OBJECT IDENTIFIER ::= { orinocoSys 19 }

    -- System Log (Syslog) Subgroup
orinocoSyslog				OBJECT IDENTIFIER ::= { orinocoSys 21 }

--=============================================================================
-- Definition of the Interface Subgroups
--=============================================================================

    -- Wireless Interface Subgroup
	orinocoWirelessIf		OBJECT IDENTIFIER ::= { orinocoIf 1 }

    -- Ethernet Interface Subgroup
	orinocoEthernetIf       OBJECT IDENTIFIER ::= { orinocoIf 2 }

    -- ADSL Interface Subgroup
	orinocoADSLIf       	OBJECT IDENTIFIER ::= { orinocoIf 3 }

    -- WORP Interface Subgroup
orinocoWORPIf       		OBJECT IDENTIFIER ::= { orinocoIf 5 }
	
--=============================================================================
-- Definition of the Network Subgroups
--=============================================================================

    -- IP Network Subgroup
	orinocoNetIP			OBJECT IDENTIFIER ::= { orinocoNet 1 }

    -- IPX Network Subgroup
	orinocoNetIPX       	OBJECT IDENTIFIER ::= { orinocoNet 2 }

--=============================================================================
-- Definition of the RADIUS Subgroups
--=============================================================================

    -- Authentication RADIUS Subgroup
	orinocoRADIUSAuth		OBJECT IDENTIFIER ::= { orinocoRADIUS 1 }

    -- Accounting RADIUS Subgroup
	orinocoRADIUSAcct       OBJECT IDENTIFIER ::= { orinocoRADIUS 2 }

--=============================================================================
-- Definition of the Filtering Subgroups
--=============================================================================

    -- Protocol Filtering Subgroup
	orinocoProtocolFilter   	OBJECT IDENTIFIER ::= { orinocoFiltering 1 }

    -- Access Control Filter Subgroup
	orinocoAccessControl    	OBJECT IDENTIFIER ::= { orinocoFiltering 2 }
									 
    -- Static MAC Address Filter Subgroup
	orinocoStaticMACAddressFilter 
								OBJECT IDENTIFIER ::= { orinocoFiltering 3 }

    -- Storm Threshold Filter Subgroup
    orinocoStormThreshold   	OBJECT IDENTIFIER ::= { orinocoFiltering 4 }

    -- IP Packet and Port Filtering Subgroup
    orinocoPortFilter       OBJECT IDENTIFIER ::= { orinocoFiltering 5 }

    -- Advanced Bridging Filter Subgroup
    orinocoAdvancedFiltering	OBJECT IDENTIFIER ::= { orinocoFiltering 6 } 
    
    --Packet Forwarding Subgroup
	orinocoPacketForwarding		OBJECT IDENTIFIER ::= { orinocoFiltering 7 }    
	
	-- IBSS Traffic Control Subgroup
	orinocoIBSSTraffic			OBJECT IDENTIFIER ::= { orinocoFiltering 8 }	

--=============================================================================
-- Definition of the DHCP Subgroups
--=============================================================================

    -- DHCP Server Subgroup
	orinocoDHCPServer		OBJECT IDENTIFIER ::= { orinocoDHCP 1 }

    -- DHCP Client Subgroup
	orinocoDHCPClient		OBJECT IDENTIFIER ::= { orinocoDHCP 2 }

    -- DHCP Relay Agent Subgroup
    orinocoDHCPRelay		OBJECT IDENTIFIER ::= { orinocoDHCP 3 }

--=============================================================================
-- Definition of the ADSL Interface Subgroups
--=============================================================================

    -- ADSL Interface Configuration Subgroup
    orinocoADSLIfConfig	OBJECT IDENTIFIER ::= { orinocoADSLIf 1 }

  -- ADSL Interface Profile 0 Basic Configuration Subgroup
orinocoADSLIfConfigBasic	OBJECT IDENTIFIER ::= { orinocoADSLIfConfig 1 }

    -- ADSL Interface Profile 0 Advanced Configuration Subgroup	                        
orinocoADSLIfConfigAdvanced	OBJECT IDENTIFIER ::= { orinocoADSLIfConfig 2 }
    
    -- ADSL Interface Statistics Subgroup
orinocoADSLIfStatistics		OBJECT IDENTIFIER ::= { orinocoADSLIf 2 }

    -- ADSL Interface Basic Statistics Subgroup
orinocoADSLIfStatBasic		OBJECT IDENTIFIER ::= { orinocoADSLIfStatistics 1 }

    -- ADSL Interface Advanced Statistics Subgroup
orinocoADSLIfStatAdvanced	OBJECT IDENTIFIER ::= { orinocoADSLIfStatistics 2 }

    -- ADSL Interface Basic ATM Statistics Subgroup
orinocoADSLIfStatATMBasic	OBJECT IDENTIFIER ::= { orinocoADSLIfStatistics 3 }

    -- ADSL Interface Advanced ATM Statistics Subgroup
orinocoADSLIfStatATMAdvanced OBJECT IDENTIFIER ::= { orinocoADSLIfStatistics 4 }

 -- ADSL Interface Diagnosis Subgroup
orinocoADSLIfDiagnosis		OBJECT IDENTIFIER ::= { orinocoADSLIf 3 }

-- ADSL Interface Diagnosis Loop Back Subgroup
orinocoADSLIfDiagLoopBack	OBJECT IDENTIFIER ::= { orinocoADSLIfDiagnosis 4 }
                                                                                 
--=============================================================================
-- Definition of the DNS Subgroups
--=============================================================================

-- DNS Client Subgroup
orinocoDNSClient			OBJECT IDENTIFIER ::= { orinocoDNS 5 }
                                                                                 
--=============================================================================
-- The System Group: orinocoSys
--=============================================================================

	oriSystemAdminState    OBJECT-TYPE
    	SYNTAX INTEGER
			{
	    		normal(1),
			    maintenance(2)
			}
	    MAX-ACCESS read-write
	    STATUS current
	    DESCRIPTION
		"This object identifies the device's state.  When the device is 
			in normal mode it will accept new connections and pass traffic 
			through normally.  When the device is in maintenance mode, it will
		not pass traffic and will not accept new connections, but it can be
		fully managed.  The default value for this object should be 
		normal."
		DEFVAL { normal }
	    ::= { orinocoSys 2 }

	oriSystemAdminStateTimer    OBJECT-TYPE
    	SYNTAX Integer32 (0..3600)
	    MAX-ACCESS read-write
	    STATUS current
	    DESCRIPTION
		"This object is a timer used when changing the device's state 
			from Normal to Maintenance mode.  When the device's state is 
			changed from Normal to Maintenance mode or vice-versa this timer 
			shall count down for the state to be changed.  This timer is in
			seconds and can be set from 0 - 3600 seconds (0 - 60 minutes).  
		The default value for this timer should be 900 seconds 
		(15 minutes)."
		DEFVAL { 900 }
	    ::= { orinocoSys 3 }

	oriSystemReboot	OBJECT-TYPE
	    SYNTAX Integer32
	    MAX-ACCESS read-write
	    STATUS current
	    DESCRIPTION
        "This object is used to reboot the device.  The value assigned
        to this object is the number of seconds until the next reboot."
        ::= { orinocoSys 4 }

    oriSystemContactEmail OBJECT-TYPE
        SYNTAX DisplayString
        MAX-ACCESS read-write
        STATUS current
        DESCRIPTION
        "This object is used to identify the email address of the 
        contact person for this managed device."
        ::= { orinocoSys 5 }

    oriSystemContactPhoneNumber OBJECT-TYPE
        SYNTAX DisplayString
        MAX-ACCESS read-write
        STATUS current
        DESCRIPTION
        "This object is used to identify the phone number of the
        contact person for this managed device."
        ::= { orinocoSys 6 }

	oriSystemFlashUpdate OBJECT-TYPE
 		SYNTAX Integer32
   	    MAX-ACCESS read-write
        STATUS current
        DESCRIPTION
	  	"When this variable is set, all the objects that are
			to be comitted to flash will be written to flash. This
		will be done immediately after the value is set, regardless
		of the value set."
   		::= { orinocoSys 7 } 

	oriSystemFlashBackupInterval OBJECT-TYPE
        SYNTAX Integer32
        MAX-ACCESS read-write
        STATUS current
        DESCRIPTION
        "This object is used for the backup time interval for flash 
        memory to be udpated."
	    ::= { orinocoSys 8 } 

	oriSystemEmergencyResetToDefault OBJECT-TYPE
    SYNTAX Integer32
   	    MAX-ACCESS read-write
        STATUS current
        DESCRIPTION
        "This object is used to reset the device to factory default
        values.  When this variable is set to 1, all the objects shall be
        set to factory default values.  The default value for this object
        should be 0."
	    DEFVAL { 0 }
        ::= { orinocoSys 9 }
        
	oriSystemMode OBJECT-TYPE
	    SYNTAX INTEGER
	        {
	            bridge(1),
	            gateway(2)
	        }
   	    MAX-ACCESS read-write
        STATUS current
        DESCRIPTION
            "This object represents the mode the system is configured to 
        operate in, either bridge or gateway/router mode."
	    DEFVAL { bridge }
        ::= { orinocoSys 10 }

    oriSystemEventLogTable	OBJECT-TYPE
    	SYNTAX SEQUENCE OF OriSystemEventLogTableEntry
    	MAX-ACCESS not-accessible
    	STATUS current
    	DESCRIPTION
    		"This table contains system event log information that can include
		events, errors, and informational messages.  This is a circular
		buffer with a limit 100 entries."
    	::= { orinocoSys 11 }
    	
    oriSystemEventLogTableEntry		OBJECT-TYPE
    	SYNTAX OriSystemEventLogTableEntry
    	MAX-ACCESS not-accessible
    	STATUS current
    	DESCRIPTION
		"This object represents an entry in the system event log 
    		table."
    	INDEX { oriSystemEventLogMessage }
    	::= { oriSystemEventLogTable 1 }
    
    OriSystemEventLogTableEntry ::=
    	SEQUENCE
    		{
    			oriSystemEventLogMessage		DisplayString
            }                                
                	        	    
	oriSystemEventLogMessage OBJECT-TYPE
	    SYNTAX DisplayString
   	    MAX-ACCESS read-only
        STATUS current
        DESCRIPTION
            "This object is used to store system event log information.
            This is also used as the index to the table."
        ::= { oriSystemEventLogTableEntry 1 }

	oriSystemEventLogTableReset OBJECT-TYPE
	    SYNTAX Integer32 (1..1)
	    MAX-ACCESS read-write
        STATUS current
        DESCRIPTION
            "This object is used to reset/clear the event log table.  When
            this object is the set all entries in the event log table are
        deleted/cleared."
        ::= { orinocoSys 12 }

	oriSystemEventLogMask OBJECT-TYPE
	    SYNTAX Integer32
	    MAX-ACCESS read-write
        STATUS current
        DESCRIPTION
        "This object is used to control what events will be logged by
		the event log facility. It is a mask, each bit is used to 
		enable/disable a corresponding set of log messages.
		Each nibble (4 bits == 1 hex digit == a nibble) represents a
		category of log messages. There are 4 levels of messages per
		category (1 bit per level per category). The least significant
		bit is a higher priority message.
		As follows:
		    security - nibble 1, bits 1-4
			errors - nibble 2, bits 5-8
			system startup - nibble 3, bits 9-12
			warnings - nibble 4, bits 13-16
			information - nibble 5, bits 17-20
		
		    0x00000 - No events will be logged.
		    0x000F0 - Only errors will be logged.
		    0x0F0F0 - Warnings and errors will be logged.
		    0xFFFFF - All events will be logged."
        ::= { orinocoSys 13 }
        
    oriSystemAccessUserName OBJECT-TYPE
    	SYNTAX DisplayString
	    MAX-ACCESS read-write
        STATUS current
        DESCRIPTION
        "This object represents the system access user name for the
        supported management interfaces (Telnet and HTTP)."
        ::= { orinocoSys 14 }    

	oriSystemAccessPassword OBJECT-TYPE
	    SYNTAX DisplayString
	    MAX-ACCESS read-write
        STATUS current
        DESCRIPTION
        "This object represents the system access password for the
        supported management interfaces (Telnet and HTTP).  This object 
        should be treated as write-only and returned as asterisks."
        ::= { orinocoSys 15 }

    oriSystemAccessLoginTimeout OBJECT-TYPE
        SYNTAX Integer32 (0..300)
        MAX-ACCESS read-write
        STATUS current
        DESCRIPTION 
        "This object represents the login timeout in seconds.  The
        default value should be 60 seconds (1 minute)."
        DEFVAL { 60 }
        ::= { orinocoSys 16 }

    oriSystemAccessIdleTimeout OBJECT-TYPE
        SYNTAX Integer32 (0..36000)
        MAX-ACCESS read-write
        STATUS current
        DESCRIPTION
        "This object represents the inactivity or idle timeout in
        seconds.  The default value should be 900 seconds (15 minutes)."
        DEFVAL { 900 }
        ::= { orinocoSys 17 }
        
oriSystemEventLogNumberOfMessages OBJECT-TYPE
    SYNTAX Integer32
    MAX-ACCESS read-only
    STATUS current
    DESCRIPTION
        "This object represnets the number of messages currently stored 
        in the event log table."
    ::= { orinocoSys 18 }

oriSystemAccessMaxSessions OBJECT-TYPE
    SYNTAX Integer32 (0..5)
    MAX-ACCESS read-only
    STATUS current
    DESCRIPTION
        "This object controls the maximum number of simultaneous telnet, 
        http, and serial managmenent sessions."
    ::= { orinocoSys 20 }
    
--=============================================================================
-- The System Inventory Management Subgroup: orinocoSysInvMgmt
--=============================================================================

    oriSystemInvMgmtComponentTable	OBJECT-TYPE
    	SYNTAX SEQUENCE OF OriSystemInvMgmtComponentTableEntry
    	MAX-ACCESS not-accessible
    	STATUS current
    	DESCRIPTION
		"This table contains the inventory management objects for the 
		system components."
    	::= { orinocoSysInvMgmt 1 }
    	
    oriSystemInvMgmtComponentTableEntry		OBJECT-TYPE
    	SYNTAX OriSystemInvMgmtComponentTableEntry
    	MAX-ACCESS not-accessible
    	STATUS current
    	DESCRIPTION
    		"This object represents an entry in the system inventory 
    		management component table."
    	INDEX { oriSystemInvMgmtTableComponentIndex }
    	::= { oriSystemInvMgmtComponentTable 1 }
    
    OriSystemInvMgmtComponentTableEntry ::=
    	SEQUENCE
    		{
    		    oriSystemInvMgmtTableComponentIndex			Integer32,
    			oriSystemInvMgmtTableComponentSerialNumber	DisplayString,
    			oriSystemInvMgmtTableComponentName			DisplayString,
    			oriSystemInvMgmtTableComponentId			Integer32,
    			oriSystemInvMgmtTableComponentVariant		Integer32,		
                oriSystemInvMgmtTableComponentReleaseVersion	Integer32,
                oriSystemInvMgmtTableComponentMajorVersion  Integer32,
                oriSystemInvMgmtTableComponentMinorVersion  Integer32
            }                                
                	        
	oriSystemInvMgmtTableComponentIndex    OBJECT-TYPE
    	SYNTAX Integer32
    	MAX-ACCESS read-only
    	STATUS current
    	DESCRIPTION
		"This object represents the table index."
    	::= { oriSystemInvMgmtComponentTableEntry 1 }
    	
	oriSystemInvMgmtTableComponentSerialNumber    OBJECT-TYPE
    	SYNTAX DisplayString
    	MAX-ACCESS read-only
    	STATUS current
    	DESCRIPTION
		"This object identifies the system component serial number."
    	::= { oriSystemInvMgmtComponentTableEntry 2 }
    	
	oriSystemInvMgmtTableComponentName    OBJECT-TYPE
    	SYNTAX DisplayString
    	MAX-ACCESS read-only
    	STATUS current
    	DESCRIPTION
		"This object identifies the system component name."
    	::= { oriSystemInvMgmtComponentTableEntry 3 }

	oriSystemInvMgmtTableComponentId    OBJECT-TYPE
    	SYNTAX Integer32
    	MAX-ACCESS read-only
    	STATUS current
    	DESCRIPTION
		"This object identifies the system component identification."
    	::= { oriSystemInvMgmtComponentTableEntry 4 }

	oriSystemInvMgmtTableComponentVariant    OBJECT-TYPE
    	SYNTAX Integer32
    	MAX-ACCESS read-only
    	STATUS current
    	DESCRIPTION
		"This object identifies the system component variant number."
    	::= { oriSystemInvMgmtComponentTableEntry 5 }

	oriSystemInvMgmtTableComponentReleaseVersion    OBJECT-TYPE
    	SYNTAX Integer32
    	MAX-ACCESS read-only
    	STATUS current
    	DESCRIPTION
		"This object identifies the system component release version 
		number."
    	::= { oriSystemInvMgmtComponentTableEntry 6 }
    	
	oriSystemInvMgmtTableComponentMajorVersion    OBJECT-TYPE
    	SYNTAX Integer32
    	MAX-ACCESS read-only
    	STATUS current
    	DESCRIPTION
		"This object identifies the system component major version 
			number."
    	::= { oriSystemInvMgmtComponentTableEntry 7 }

	oriSystemInvMgmtTableComponentMinorVersion    OBJECT-TYPE
    	SYNTAX Integer32
    	MAX-ACCESS read-only
    	STATUS current
    	DESCRIPTION
		"This object identifies the system component minor version 
			number."
    	::= { oriSystemInvMgmtComponentTableEntry 8 }
    	
    oriSystemInvMgmtTableComponentIfTable    OBJECT-TYPE
    	SYNTAX SEQUENCE OF OriSystemInvMgmtTableComponentIfTableEntry
    	MAX-ACCESS not-accessible
    	STATUS current
    	DESCRIPTION
		"This table contains the inventory management objects for the
		system components."
        ::= { orinocoSysInvMgmt 2 }
    	    	
    oriSystemInvMgmtTableComponentIfTableEntry		OBJECT-TYPE
    	SYNTAX OriSystemInvMgmtTableComponentIfTableEntry
    	MAX-ACCESS not-accessible
    	STATUS current
    	DESCRIPTION
		"This object represents an entry in the system component 
		interface table."
    	INDEX { oriSystemInvMgmtTableComponentIndex,
    	        oriSystemInvMgmtInterfaceTableIndex }
    	::= { oriSystemInvMgmtTableComponentIfTable 1 }
    	
    OriSystemInvMgmtTableComponentIfTableEntry ::=
        SEQUENCE
            {
                oriSystemInvMgmtInterfaceTableIndex			Integer32,
                oriSystemInvMgmtInterfaceId					Integer32,
                oriSystemInvMgmtInterfaceRole				INTEGER,
                oriSystemInvMgmtInterfaceVariant			Integer32,
                oriSystemInvMgmtInterfaceBottomNumber		Integer32,
                oriSystemInvMgmtInterfaceTopNumber			Integer32
			}

	oriSystemInvMgmtInterfaceTableIndex    OBJECT-TYPE
    	SYNTAX Integer32
    	MAX-ACCESS read-only
    	STATUS current
    	DESCRIPTION
		"This object identifies the interface table index."
    	::= { oriSystemInvMgmtTableComponentIfTableEntry 1 }
    					    
	oriSystemInvMgmtInterfaceId    OBJECT-TYPE
    	SYNTAX Integer32
    	MAX-ACCESS read-only
    	STATUS current
    	DESCRIPTION
		"This object identifies the system component interface 
			identification."
    	::= { oriSystemInvMgmtTableComponentIfTableEntry 2 }

	oriSystemInvMgmtInterfaceRole    OBJECT-TYPE
    	SYNTAX INTEGER
    	    {
    	        actor(1),
    	        supplier(2)
    	    }
    	MAX-ACCESS read-only
    	STATUS current
    	DESCRIPTION
		"This object identifies the system component interface role."
    	::= { oriSystemInvMgmtTableComponentIfTableEntry 3 }
    	
	oriSystemInvMgmtInterfaceVariant    OBJECT-TYPE
    	SYNTAX Integer32
    	MAX-ACCESS read-only
    	STATUS current
    	DESCRIPTION
		"This object identifies the system component's interface
			variant number."
    	::= { oriSystemInvMgmtTableComponentIfTableEntry 4 }

	oriSystemInvMgmtInterfaceBottomNumber    OBJECT-TYPE
    	SYNTAX Integer32
    	MAX-ACCESS read-only
    	STATUS current
    	DESCRIPTION
		"This object identifies the system component's interface
			bottom number."
    	::= { oriSystemInvMgmtTableComponentIfTableEntry 5 }

	oriSystemInvMgmtInterfaceTopNumber    OBJECT-TYPE
    	SYNTAX Integer32
    	MAX-ACCESS read-only
    	STATUS current
    	DESCRIPTION
		"This object identifies the system component's interface
			top number."
    	::= { oriSystemInvMgmtTableComponentIfTableEntry 6 }
    	    	
--=============================================================================
-- The System Feature based License Subgroup: orinocoSysFeature
--=============================================================================

    oriSystemFeatureTable	OBJECT-TYPE
    	SYNTAX SEQUENCE OF OriSystemFeatureTableEntry
    	MAX-ACCESS not-accessible
    	STATUS current
    	DESCRIPTION
    		"This table contains a list of features that the current image 
    		supports and indicates if this features is licensed (enabled) or 
    		not (disabled).  Each row represents a supported and/or licensed 
    		feature.  Supported indicates if the current image supports the 
    		image while Licensed indicates that a license is available to use 
		this feature.  Based on the license information in this table, 
		some MIB groups/subgroups/tables will be enabled or disabled."
    	::= { orinocoSysFeature 1 }
    	
    oriSystemFeatureTableEntry		OBJECT-TYPE
    	SYNTAX OriSystemFeatureTableEntry
    	MAX-ACCESS not-accessible
    	STATUS current
    	DESCRIPTION
		"This object represents an entry in the system feature license 
		table."
    	INDEX { oriSystemFeatureTableCode }
    	::= { oriSystemFeatureTable 1 }
    
    OriSystemFeatureTableEntry ::=
    	SEQUENCE
    		{
    		    oriSystemFeatureTableCode			INTEGER,
    		    oriSystemFeatureTableSupported		Integer32,
    		    oriSystemFeatureTableLicensed		Integer32,
    		    oriSystemFeatureTableDescription    DisplayString
    		}
                	        
	oriSystemFeatureTableCode    OBJECT-TYPE
    	SYNTAX INTEGER
    	    {
    	        bandwidthWiFi(1),
    	        bandwidthWDS(2),
    	        bandwidthWORP(3),
    	        bandwidthTurboCell(4),
    	        bandwidthADSL(5),
    	        bandwidthCable(6),
    	        bandwidthPhone(7),
    	        maxStationsWiFi(8),
    	        maxLinksWDS(9),
    	        maxStationsWORP(10),
    	        maxStationsTurboCell(11),
    	        maxPPPoESessions(12),
    	        managementHTTP(13),
    	        remoteLinkTest(14),
    	        routingStatic(15),
    	        routingRIP(16),
    	        routingOSPF(17),
    	        spanningTreeProtocol(18),
    	        linkIntegrity(19),
    	        dHCPServer(20),
    	        dHCPRelayAgent(21),
    	        proxyARP(22),
    	        filteringStatic(23),
    	        authRADIUS(24),
    	        acctRADIUS(25),
    	        throttlingRADIUS(26),
    	        filterIP(27),
    	        ieee802dot1x(28),
    	        nse(29),
    	        iAPP(30),
    	        dNSRedirect(31),
    	        aOLNATGateway(32),
    	        hereUare(33),
    	        spectralink(34),
    	        vLANTagging(35)
    	    }    
    	MAX-ACCESS read-only
    	STATUS current
    	DESCRIPTION
		"This object identifies the code for the licensed feature and 
		is used as index for this table."
    	::= { oriSystemFeatureTableEntry 1 }
    	
	oriSystemFeatureTableSupported    OBJECT-TYPE
    	SYNTAX Integer32
    	MAX-ACCESS read-only
    	STATUS current
    	DESCRIPTION
		"This object represents the maximum value for the feature as 
			supported by the current image. For boolean features zero means 
			not supported, non-zero value means supported."
    	::= { oriSystemFeatureTableEntry 2 }
    	
	oriSystemFeatureTableLicensed    OBJECT-TYPE
    	SYNTAX Integer32
    	MAX-ACCESS read-only
    	STATUS current
    	DESCRIPTION
		"This object represents the maximum value for the feature as 
			enforced by the license(s). For boolean features zero means 
			not licensed, non-zero value means licensed."
    	::= { oriSystemFeatureTableEntry 3 }

	oriSystemFeatureTableDescription    OBJECT-TYPE
    	SYNTAX DisplayString
    	MAX-ACCESS read-only
    	STATUS current
    	DESCRIPTION
		"This object represents a textual description for the licensed 
			feature."
    	::= { oriSystemFeatureTableEntry 4 }

--=============================================================================
-- The System Log (Syslog) Subgroup: orinocoSyslog
--=============================================================================

oriSyslogStatus OBJECT-TYPE
	SYNTAX INTEGER
	    {
	        enable(1),
	        disable(2)
	    }
	MAX-ACCESS read-write
	STATUS current
	DESCRIPTION
	    "This object is used to enable or disable the syslog feature."
	::= { orinocoSyslog 1 }

oriSyslogPort OBJECT-TYPE
	SYNTAX Integer32
	MAX-ACCESS read-only
	STATUS current
	DESCRIPTION
	    "This object represents the UDP destination port number for syslog 
	    services.  The standard syslog port is 514."
	::= { orinocoSyslog 2 }

oriSyslogPriority OBJECT-TYPE
	SYNTAX Integer32 (1..7)
	MAX-ACCESS read-write
	STATUS current
	DESCRIPTION
	    "This object represents the lowest message priority to be logged by
	    the syslog service."
	::= { orinocoSyslog 3 }

oriSyslogHeartbeat OBJECT-TYPE
	SYNTAX INTEGER
	    {
	        enable(1),
	        disable(2)
	    }
	MAX-ACCESS read-write
	STATUS current
	DESCRIPTION
	    "This object is used to enable or disable logging of heartbeat messages
	    by the syslog service."
	DEFVAL { disable }
	::= { orinocoSyslog 4 }

oriSyslogHeartbeatInterval OBJECT-TYPE
	SYNTAX Integer32 (1..604800)
	MAX-ACCESS read-write
	STATUS current
	DESCRIPTION
	    "This object is used to configure interval (in seconds) for which
	    heartbeat messages will be logged."
	DEFVAL { 900 }
	::= { orinocoSyslog 5 }

oriSyslogHostTable OBJECT-TYPE
    SYNTAX SEQUENCE OF OriSyslogHostTableEntry
    MAX-ACCESS not-accessible
    STATUS current
    DESCRIPTION
       "This table is used to configure syslog hosts."
    ::= { orinocoSyslog 6 }

oriSyslogHostTableEntry OBJECT-TYPE
    SYNTAX OriSyslogHostTableEntry
    MAX-ACCESS not-accessible
    STATUS current
    DESCRIPTION
       "This object represents an entry for the syslog host table."
    INDEX { oriSyslogHostTableIndex }
    ::= { oriSyslogHostTable 1 }

OriSyslogHostTableEntry ::=
    SEQUENCE
        {
            oriSyslogHostTableIndex   Integer32,
            oriSyslogHostIPAddress   IpAddress,
            oriSyslogHostComment   DisplayString,
            oriSyslogHostTableEntryStatus INTEGER
        }

oriSyslogHostTableIndex OBJECT-TYPE
    SYNTAX Integer32
    MAX-ACCESS read-only
    STATUS current
    DESCRIPTION
  "This object represents an index in the syslog host table."
    ::= { oriSyslogHostTableEntry 1 }

oriSyslogHostIPAddress OBJECT-TYPE
    SYNTAX IpAddress
    MAX-ACCESS read-write
    STATUS current
    DESCRIPTION
  "This object represents the IP address of the host running the
  syslog daemon."
    ::= { oriSyslogHostTableEntry 2 }

oriSyslogHostComment OBJECT-TYPE
    SYNTAX DisplayString
    MAX-ACCESS read-write
    STATUS current
    DESCRIPTION
  "This object represents an optional comment for the syslog host, for
  example the host name or a reference."
    ::= { oriSyslogHostTableEntry 3 }

oriSyslogHostTableEntryStatus OBJECT-TYPE
    SYNTAX INTEGER
  {
      enable(1),
      disable(2),
      delete(3),
      create(4)
  }
    MAX-ACCESS read-write
    STATUS current
    DESCRIPTION
  "This object is used to enable, disable, delete, or create an
  entry in the syslog host table."
    ::= { oriSyslogHostTableEntry 4 }
	    
--=============================================================================
-- The Interface Group: orinocoIf
--=============================================================================

--=============================================================================
-- The Wireless Interface Subgroup: orinocoWirelessIf
--=============================================================================     

--=============================================================================
-- The Wireless Interface Properties Table: oriWirelessIfPropertiesTable
--=============================================================================

	oriWirelessIfPropertiesTable    OBJECT-TYPE
    	SYNTAX SEQUENCE OF OriWirelessIfPropertiesEntry
    	MAX-ACCESS not-accessible
    	STATUS current
	    DESCRIPTION
		"This table contains information on the properties and 
		capabilities of the wireless interface(s) present in the device."
	    ::= { orinocoWirelessIf 1 }

	oriWirelessIfPropertiesEntry    OBJECT-TYPE
    	SYNTAX OriWirelessIfPropertiesEntry
	    MAX-ACCESS not-accessible
	    STATUS current
	    DESCRIPTION
		"This object represents the entry in the wireless interface 
		properties table."
	    INDEX { oriWirelessIfPropertiesIndex }
    	::= { oriWirelessIfPropertiesTable 1 }

	OriWirelessIfPropertiesEntry ::=
	    SEQUENCE
	    	{
				oriWirelessIfPropertiesIndex				Integer32,
				oriWirelessIfNetworkName					DisplayString,
				oriWirelessIfMediumReservation				Integer32,
				oriWirelessIfInterferenceRobustness			INTEGER,
				oriWirelessIfDTIMPeriod						Integer32,
				oriWirelessIfChannel						Integer32,
				oriWirelessIfDistancebetweenAPs				INTEGER,
				oriWirelessIfMulticastRate					INTEGER,
				oriWirelessIfClosedSystem					INTEGER,
				oriWirelessIfAllowedSupportedDataRates		OCTET STRING,
				oriWirelessIfRegulatoryDomainList			OCTET STRING,
				oriWirelessIfAllowedChannels				OCTET STRING,
				oriWirelessIfMACAddress						PhysAddress,
				oriWirelessIfLoadBalancing					INTEGER,
				oriWirelessIfMediumDensityDistribution		INTEGER,
			oriWirelessIfTxRate							Integer32,
				oriWirelessIfAutoChannelSelectStatus			INTEGER,
			oriWirelessIfBandwidthLimitIn				Gauge32,
			oriWirelessIfBandwidthLimitOut				Gauge32,
			oriWirelessIfTurboModeStatus				INTEGER
				}

	oriWirelessIfPropertiesIndex    OBJECT-TYPE
    	SYNTAX Integer32
	    MAX-ACCESS read-only
	    STATUS current
	    DESCRIPTION
		"This object represents a unique value for each interface in the
		system and is used as index to this table."
	    ::= { oriWirelessIfPropertiesEntry 1 }

	oriWirelessIfNetworkName    OBJECT-TYPE
	    SYNTAX DisplayString
	    MAX-ACCESS read-write
	    STATUS current
	    DESCRIPTION
		"This object represents the network name (SSID) for this wireless 
			interface."
		DEFVAL { "My Wireless Network" }
	    ::= { oriWirelessIfPropertiesEntry 2 }

	oriWirelessIfMediumReservation    OBJECT-TYPE
	    SYNTAX Integer32 (0..2347)
	    MAX-ACCESS read-write
	    STATUS current
	    DESCRIPTION                                                     
		"This object represents the medium reservation value.  The range
			for this parameter is 0 - 2347.  The medium reservation specifies 
			the number of octects in a frame above which a RTS/CTS handshake is
		performed.  The default value should be 2347, which disables 
		RTS/CTS mode."
		DEFVAL { 2347 }
	    ::= { oriWirelessIfPropertiesEntry 3 }

	oriWirelessIfInterferenceRobustness    OBJECT-TYPE
    	SYNTAX INTEGER
			{
			    enable(1),
			    disable(2)
			}
	    MAX-ACCESS read-write
	    STATUS current
	    DESCRIPTION
		"This object enables or disables the interference robustness 
		feature.  The default value for this object should be disable."
		DEFVAL { disable }
	    ::= { oriWirelessIfPropertiesEntry 4 }

	oriWirelessIfDTIMPeriod    OBJECT-TYPE
    	SYNTAX Integer32 (1..65535)
	    MAX-ACCESS read-write
	    STATUS current
	    DESCRIPTION
		"This object represents the delivery traffic indication map 
			period.  This is the interval between the transmission of multicast
			frames on the wireless inteface.  It is expressed in the Beacon
		messages.  The recommended default value for this object is 1."
		DEFVAL { 1 }
        ::= { oriWirelessIfPropertiesEntry 5 }

	oriWirelessIfChannel    OBJECT-TYPE
	    SYNTAX Integer32 (1..14)
	    MAX-ACCESS read-write
	    STATUS current
	    DESCRIPTION
		"This object represents the radio frequency channel for this 
		wireless interface.  The default value for this object should 
		be is 3."
		DEFVAL { 3 }
	    ::= { oriWirelessIfPropertiesEntry 6 }

	oriWirelessIfDistancebetweenAPs    OBJECT-TYPE
	    SYNTAX INTEGER
			{
			    large(1),
			    medium(2),
		    small(3),
		    minicell(4),
		    microcell(5)
			}
	    MAX-ACCESS read-write
	    STATUS current
	    DESCRIPTION
		"This object identifies the distance between access points.
			The default value for this parameter should be large."
		DEFVAL { large }	    
	    ::= { oriWirelessIfPropertiesEntry 7 }

	oriWirelessIfMulticastRate	OBJECT-TYPE
	    SYNTAX INTEGER
			{
			    oneMegabitPerSecond(1),
			    twoMegabitsPerSecond(2),
			    fivedotfiveMegabitsPerSecond(3),
			    elevenMegabitsPerSecond(4)
			}
	    MAX-ACCESS read-write
	    STATUS current
	    DESCRIPTION
		"This object identifies multicast rate of the wireless interface. 
		This is dependent on the distance between APs.  When the distance
		between APs object is set to small, minicell, or microcell the 
		multicast rates can be set to 11 Mbit/s, 5.5 Mbit/s, 2 Mbit/s, 
		and 1 Mbit/s.  When this object is set to medium, the allowed 
		rates are 5.5 Mbit/s, 2 Mbit/s, 1 Mbit/s.  When this object is set
		to large, then the multicast rates can be set to 2 Mbits/s or 
		1 Mbits/s.  The default value for this object should be 
		2 Mbits/sec."
		DEFVAL { twoMegabitsPerSecond }
		::= { oriWirelessIfPropertiesEntry 8 }

	oriWirelessIfClosedSystem	OBJECT-TYPE
    	SYNTAX INTEGER
			{
			    enable(1),
			    disable(2)
			}
	    MAX-ACCESS read-write
	    STATUS current
	    DESCRIPTION
		"This object is used as a flag which identifies whether the 
			device will accept association requests to this interface, for 
			client stations configured with a network name of 'ANY'.  When 
		this object is disabled, it will accept association requests 
			from client stations with a network name of 'ANY'.  If this 
		object is set to enable then the interface will only accept 
		association requests that match the interface's network name 
		(SSID).  The default value for this object should be disable."
		DEFVAL { disable }
	    ::= { oriWirelessIfPropertiesEntry 9 }

	oriWirelessIfAllowedSupportedDataRates	OBJECT-TYPE
	    SYNTAX OCTET STRING
	    MAX-ACCESS read-only
	    STATUS current
	    DESCRIPTION
		"This object reflects the transmit rates supported by the 
		wireless interface.  The values of this object are given in 
		units of 500 kbps. 
		Examples for supported data rates:
		 - 802.11b PHY (DSSS - 2.4 GHz)
		    - 0 = Auto Fallback
		    - 2 = 1 Mbps
		    - 4 = 2 Mbps
		    - 11 = 5.5 Mbps
		    - 22 = 11 Mbps
			
		 - 802.11a PHY (OFDM - 5 GHz)
		    - 0 = Auto Fallback
		    - 12 = 6 Mbps
		    - 18 = 9 Mbps
		    - 24 = 12 Mbps
		    - 36 = 18 Mbps
		    - 48 = 24 Mbps
		    - 72 = 36 Mbps
		    - 96 = 48 Mbps
		    - 108 = 54 Mbps
			
		 - 802.11a PHY (OFDM - 5 GHz) with Turbo Mode Enabled
		    - 0 = Auto Fallback
		    - 24 = 12 Mbps
		    - 36 = 18 Mbps
		    - 48 = 24 Mbps
		    - 72 = 36 Mbps
		    - 96 = 48 Mbps
		    - 144 = 72 Mbps
		    - 192 = 96 Mbps
		    - 216 = 108 Mbps"
	    ::= { oriWirelessIfPropertiesEntry 10 }

	oriWirelessIfRegulatoryDomainList	OBJECT-TYPE
	    SYNTAX OCTET STRING
	    MAX-ACCESS read-only
	    STATUS current
	    DESCRIPTION
		"This object specifies to which regulatory domain the wireless
		interface belongs to."
	    ::= { oriWirelessIfPropertiesEntry 11 }

	oriWirelessIfAllowedChannels	OBJECT-TYPE 
	    SYNTAX OCTET STRING
	    MAX-ACCESS read-only
	    STATUS current	
	    DESCRIPTION
		"This object reflects the radio frequency channels that the 
			interface supports."    
	    ::= { oriWirelessIfPropertiesEntry 12 }

	oriWirelessIfMACAddress	OBJECT-TYPE
	    SYNTAX PhysAddress
	    MAX-ACCESS read-only
    STATUS deprecated
	    DESCRIPTION
	    "This object represents the MAC address of the wireless interface
	    present in the device.  This object has been deprecated."
	    ::= { oriWirelessIfPropertiesEntry 13 }

	oriWirelessIfLoadBalancing	OBJECT-TYPE
	    SYNTAX INTEGER
	        {
	            enable(1),
	            disable(2)
	        }
	    MAX-ACCESS read-write
	    STATUS current
	    DESCRIPTION
	    "This object is used to configure the load balancing feature
	    for the wireless interface."
		DEFVAL { enable }
	    ::= { oriWirelessIfPropertiesEntry 14 }

    oriWirelessIfMediumDensityDistribution    OBJECT-TYPE
        SYNTAX INTEGER
            {
                enable(1),
                disable(2)
            }
	    MAX-ACCESS read-write
	    STATUS current
	    DESCRIPTION
		    "This object is used to configure the medium density distribution
	    feature for the wireless interface."
		DEFVAL { enable }
	    ::= { oriWirelessIfPropertiesEntry 15 }

oriWirelessIfTxRate	OBJECT-TYPE
    SYNTAX Integer32 (0..255)
    MAX-ACCESS read-write
    STATUS current
    DESCRIPTION
		"This object is used to configure the transmit rate for unicast 
		traffic for the wireless interface.  This object is dependent on 
		the transmit rates supported by the wireless interface (refer 
		to MIB object - oriWirelessIfAllowedSupportedDataRates and 
		dot11PHYType).  The values of this object are given in units of 
		500 kbps.  A value of zero (0) is interpreted as auto fallback. 
		
		Examples for configuring this object:
		 - 802.11b PHY (DSSS - 2.4 GHz)
		    - 0 = Auto Fallback
		    - 2 = 1 Mbps
		    - 4 = 2 Mbps
		    - 11 = 5.5 Mbps
		    - 22 = 11 Mbps
		
		 - 802.11a PHY (OFDM - 5 GHz)
		    - 0 = Auto Fallback
		    - 12 = 6 Mbps
		    - 18 = 9 Mbps
		    - 24 = 12 Mbps
		    - 36 = 18 Mbps
		    - 48 = 24 Mbps
		    - 72 = 36 Mbps
		    - 96 = 48 Mbps
		    - 108 = 54 Mbps
		
		 - 802.11a PHY (OFDM - 5 GHz) with Turbo Mode Enabled
		    - 0 = Auto Fallback
		    - 24 = 12 Mbps
		    - 36 = 18 Mbps
		    - 48 = 24 Mbps
		    - 72 = 36 Mbps
		    - 96 = 48 Mbps
		    - 144 = 72 Mbps
		    - 192 = 96 Mbps
		    - 216 = 108 Mbps
		The default value for this object should be zero 
		(0) auto fallback."
	DEFVAL { 0 }
    ::= { oriWirelessIfPropertiesEntry 16 }

	 oriWirelessIfAutoChannelSelectStatus    OBJECT-TYPE
        SYNTAX INTEGER
            {
                enable(1),
                disable(2)
            }
	    MAX-ACCESS read-write
	    STATUS current
	   DESCRIPTION
	    "This object is used to configure the automatic frequency channel
	    feature for the wireless interface.  If this object is enabled, the
		    frequency channel object can not be set, but the frequency channel 
		    selected will be given in that object.  The default value for
	    this object should be enable."
		DEFVAL { enable }
    ::= { oriWirelessIfPropertiesEntry 17 }

oriWirelessIfBandwidthLimitIn OBJECT-TYPE
    SYNTAX Gauge32
    MAX-ACCESS read-write
    STATUS current
    DESCRIPTION
	    "This object represents the input bandwidth limit of the interface 
	    in increments of 64 kbps. The value can be limited by a previous 
	    written value, the negotiation process during registration or by a 
	    license. A written value will only take effect after reboot."		
    ::= { oriWirelessIfPropertiesEntry 18 }

oriWirelessIfBandwidthLimitOut OBJECT-TYPE
    SYNTAX Gauge32
    MAX-ACCESS read-write
    STATUS current
    DESCRIPTION
        "This object represents the output bandwidth limit of the interface 
        in increments of 64 kbps. The value can be limited by a previous 
        written value, the negotiation process during registration or by a 
        license. A written value will only take effect after reboot."		
    ::= { oriWirelessIfPropertiesEntry 19 }
	    
oriWirelessIfTurboModeStatus OBJECT-TYPE
    SYNTAX INTEGER
        {
            enable(1),
            disable(2)
        }
    MAX-ACCESS read-write
    STATUS current
    DESCRIPTION
        "This object is used to enable or disable turbo mode support.  Turbo
        mode is only supported for 802.11a PHY (OFDM - 5 GHz) wireless NICs.
        When Turbo mode is enabled the data rates will be doubled (refer to
        oriWirelessIfAllowedSupportedDataRates object description)."
    ::= { oriWirelessIfPropertiesEntry 20 }

--=============================================================================
-- The Wireless Interface Security Table: oriWirelessIfSecurityTable
--=============================================================================

	oriWirelessIfSecurityTable    OBJECT-TYPE
    	SYNTAX SEQUENCE OF OriWirelessIfSecurityEntry
    	MAX-ACCESS not-accessible
    	STATUS current
	    DESCRIPTION
		"This table contains information on the security management objects 
		for the wireless interface(s) present in the device."
	    ::= { orinocoWirelessIf 2 }

	oriWirelessIfSecurityEntry    OBJECT-TYPE
    	SYNTAX OriWirelessIfSecurityEntry
	    MAX-ACCESS not-accessible
	    STATUS current
	    DESCRIPTION
		"This object represents an entry in the wireless interface 
		security table."
	    INDEX { oriWirelessIfSecurityIndex }
    	::= { oriWirelessIfSecurityTable 1 }

	OriWirelessIfSecurityEntry ::=
	    SEQUENCE
		    {
				oriWirelessIfSecurityIndex				Integer32,
				oriWirelessIfEncryptionOptions			INTEGER,
				oriWirelessIfEncryptionStatus			INTEGER,
				oriWirelessIfEncryptionKey1				DisplayString,
				oriWirelessIfEncryptionKey2				DisplayString,
				oriWirelessIfEncryptionKey3				DisplayString,
				oriWirelessIfEncryptionKey4				DisplayString,
			oriWirelessIfEncryptionTxKey	   		Integer32,	
				oriWirelessIfDenyNonEncryptedData		INTEGER,
				oriWirelessIfProfileCode				Integer32
		    }
	
	oriWirelessIfSecurityIndex    OBJECT-TYPE
    	SYNTAX Integer32
	    MAX-ACCESS read-only
	    STATUS current
	    DESCRIPTION
		"This object represents a unique value for each interface in the
		system and is used as index to this table."
	    ::= { oriWirelessIfSecurityEntry 1 }

	oriWirelessIfEncryptionOptions    OBJECT-TYPE
	    SYNTAX INTEGER
	    	{
	       	    none(1),
	       	    wep(2),
	       	    rcFour128(3)
	      	}
	    MAX-ACCESS read-only
	    STATUS current
	    DESCRIPTION
		"This object reflects the wireless interface's security 
		capabilities (such as WEP and other standard and proprietary
		security features)."
	    ::= { oriWirelessIfSecurityEntry 2 }

	oriWirelessIfEncryptionStatus    OBJECT-TYPE
	    SYNTAX INTEGER
	    	{
	       	    enable(1),
	       	    disable(2)
	      	}
	    MAX-ACCESS read-write
	    STATUS current
	    DESCRIPTION	
		"This object is used to enable or disable WEP encryption for the 
		wireless interface."
		DEFVAL { disable }
	    ::= { oriWirelessIfSecurityEntry 3 }

	oriWirelessIfEncryptionKey1    OBJECT-TYPE
		SYNTAX DisplayString
	   	MAX-ACCESS read-write
 	   	STATUS current
	    DESCRIPTION
		"This object represents Encryption Key 1.  This object should be
			treated as write-only and returned as asterisks."
	    ::= { oriWirelessIfSecurityEntry 4 }

	oriWirelessIfEncryptionKey2    OBJECT-TYPE
	    SYNTAX DisplayString
	    MAX-ACCESS read-write
	    STATUS current
	    DESCRIPTION
		"This object represents Encryption Key 2.  This object should be
			treated as write-only and returned as asterisks."
	    ::= { oriWirelessIfSecurityEntry 5 }

	oriWirelessIfEncryptionKey3    OBJECT-TYPE
	    SYNTAX DisplayString
	    MAX-ACCESS read-write
	    STATUS current	
	    DESCRIPTION
		"This object represents Encryption Key 3.  This object should be
			treated as write-only and returned as asterisks."
	    ::= { oriWirelessIfSecurityEntry 6 }

	oriWirelessIfEncryptionKey4    OBJECT-TYPE
	    SYNTAX DisplayString
	    MAX-ACCESS read-write
	    STATUS current	
	    DESCRIPTION
		"This object represents Encryption Key 4.  This object should be
			treated as write-only and returned as asterisks."
	    ::= { oriWirelessIfSecurityEntry 7 }

	oriWirelessIfEncryptionTxKey    OBJECT-TYPE
    SYNTAX Integer32 (0..3)
	    MAX-ACCESS read-write
	    STATUS current
	    DESCRIPTION
		"This object indicates which encryption key is used to encrypt
		data that is sent via the wireless interfaces.  When this object is
		configured to 0, then Encryption Key 1 will be used.  When this object
		is configured to 1, then Encryption Key 2 will be used.  When
		this object is configured to 2, then Encryption Key 3 will be used.
		When this object is configured to 3, then Encryption Key 4 will be
		used.  The default value for this object should be key 0."
	DEFVAL { 0 }
	    ::= { oriWirelessIfSecurityEntry 8 }

	oriWirelessIfDenyNonEncryptedData    OBJECT-TYPE
	    SYNTAX INTEGER
	    	{
	       	    enable(1),
	       	    disable(2)
	      	}
	    MAX-ACCESS read-write
	    STATUS current
	    DESCRIPTION
			"This parameter indicates if this interface will accept or deny 
			non-encrypted data.  The default value for this parameters is
			disabled."
		DEFVAL { disable }
	    ::= { oriWirelessIfSecurityEntry 9 }

	oriWirelessIfProfileCode    OBJECT-TYPE
	    SYNTAX Integer32
        MAX-ACCESS read-only
        STATUS current
	    DESCRIPTION
        "The object represents the profile code of the wirelesss interface.
        This information is comprised of a vendor indication and a 
        capability indication (example: bronze or gold card)."
        ::= { oriWirelessIfSecurityEntry 10 } 

--=============================================================================
-- The Ethernet Interface Subgroup: orinocoEthernetIf
--=============================================================================

    oriEthernetIfConfigTable    OBJECT-TYPE
        SYNTAX SEQUENCE OF OriEthernetIfConfigTableEntry
        MAX-ACCESS not-accessible
        STATUS current
        DESCRIPTION
       "This table is used to configure the ethernet interface(s) for the 
       device."
        ::= { orinocoEthernetIf 1 }

    oriEthernetIfConfigTableEntry    OBJECT-TYPE
        SYNTAX OriEthernetIfConfigTableEntry
        MAX-ACCESS not-accessible
        STATUS current
        DESCRIPTION
       "This object represents an entry in the ethernet interface 
       configuration table."
        INDEX { oriEthernetIfConfigTableIndex }
        ::= { oriEthernetIfConfigTable 1 }

    OriEthernetIfConfigTableEntry ::=
        SEQUENCE 
            {
                oriEthernetIfConfigTableIndex		Integer32,
            oriEthernetIfConfigSettings				INTEGER,
            oriEthernetIfConfigBandwidthLimitIn		Gauge32,
			oriEthernetIfConfigBandwidthLimitOut	Gauge32
            }

    oriEthernetIfConfigTableIndex	OBJECT-TYPE
        SYNTAX Integer32
        MAX-ACCESS read-only
        STATUS current
        DESCRIPTION
        "This object represents the index of the ethernet configuraiton
        table."
        ::= { oriEthernetIfConfigTableEntry 1 }
                   
	oriEthernetIfConfigSettings    OBJECT-TYPE
	    SYNTAX INTEGER
			{
			    tenMegabitPerSecHalfDuplex(1),
			    tenMegabitPerSecFullDuplex(2),
			    tenMegabitPerSecAutoDuplex(3),
			    onehundredMegabitPerSecHalfDuplex(4),
			    onehundredMegabitPerSecFullDuplex(5),
			    autoSpeedHalfDuplex(6),
			    autoSpeedAutoDuplex(7)
			}
	    MAX-ACCESS read-write
	    STATUS current
	    DESCRIPTION
		"This object is used to configure the Ethernet interface's speed.
		Some devices support all the configuration options
		listed above, while others support only a subset of the
		configuration options."
		DEFVAL { tenMegabitPerSecHalfDuplex }
    	::= { oriEthernetIfConfigTableEntry 2 }

oriEthernetIfConfigBandwidthLimitIn OBJECT-TYPE
    SYNTAX Gauge32
    MAX-ACCESS read-write
    STATUS current
    DESCRIPTION
        "This object represents the input bandwidth limit of the interface 
        in increments of 64 kbps.  The value can be limited by a previous 
        written value, the negotiation process during registration, or by 
        a license.  A written value will only take effect after reboot."		
    ::= { oriEthernetIfConfigTableEntry 3 }

oriEthernetIfConfigBandwidthLimitOut OBJECT-TYPE
    SYNTAX Gauge32
    MAX-ACCESS read-write
    STATUS current
    DESCRIPTION
        "This object represents the output bandwidth limit of the interface
        in increments of 64 kbps.  The value can be limited by a previous 
        written value, the negotiation process during registration, or by
        a license.  A written value will only take effect after reboot."            		
    ::= { oriEthernetIfConfigTableEntry 4 }
    
--=============================================================================
-- The Interface Subgroup: orinocoIf
--=============================================================================

oriIfWANInterfaceMACAddress OBJECT-TYPE
    SYNTAX PhysAddress
    MAX-ACCESS read-write
    STATUS current
    DESCRIPTION
		"This object represents the MAC address of the WAN interface."
    ::= { orinocoIf 4 }

--=============================================================================
-- The ADSL Interface Subgroup: orinocoADSLIf
--=============================================================================

--=============================================================================
-- The ADSL Interface Configuration Subgroup: orinocoADSLIfConfig
--=============================================================================

--=============================================================================
-- The ADSL Interface Basic Configuration Subgroup: orinocoADSLIfConfigBasic
--=============================================================================

oriADSLIfConfigBasicTable OBJECT-TYPE
    SYNTAX SEQUENCE OF OriADSLIfConfigBasicTableEntry
	    MAX-ACCESS not-accessible
	    STATUS current
	    DESCRIPTION 
	    "This table is used to configure the ADSL interface of the device."
    ::= { orinocoADSLIfConfigBasic 1 }

oriADSLIfConfigBasicTableEntry OBJECT-TYPE
    SYNTAX OriADSLIfConfigBasicTableEntry
	    MAX-ACCESS not-accessible
	    STATUS current
	    DESCRIPTION 
	    "This object represents an entry in the ADSL interface 
	    configuration table.  Each entry in this table represents a PVC
	    configuration."
	    INDEX { ifIndex }
    ::= { oriADSLIfConfigBasicTable 1 }

OriADSLIfConfigBasicTableEntry ::= 
        SEQUENCE 
            {
            oriADSLIfConfigBasicVCI				Integer32,
            oriADSLIfConfigBasicVPI				Integer32,
            oriADSLIfConfigBasicEncapsulation	INTEGER	
            }

oriADSLIfConfigBasicVCI OBJECT-TYPE
	    SYNTAX Integer32 (0..65535)
	    MAX-ACCESS read-write
	    STATUS current
	    DESCRIPTION 
	    "This object is the identifier of a virtual connection with a 
	    range of 0-65535."
	    DEFVAL { 35 }
    ::= { oriADSLIfConfigBasicTableEntry 1 }

oriADSLIfConfigBasicVPI OBJECT-TYPE
	    SYNTAX Integer32 (0..255)
	    MAX-ACCESS read-write
	    STATUS current
	    DESCRIPTION 
	    "This object is the identifier of a virtual path with a 
	    range of 0-255."
	    DEFVAL { 0 }
    ::= { oriADSLIfConfigBasicTableEntry 2 }

oriADSLIfConfigBasicEncapsulation OBJECT-TYPE
    SYNTAX INTEGER 
        {
	        rfc2684LlcSnapBridged(1),
	        rfc2684LlcSnapRouted(2),
	        rfc2684VcmuxBridged(3),
	        rfc2684VcmuxRouted(4),		    
	        rfc2364PPPoAVcmux(5),
	        rfc2364PPPoALlc(6)
        }
	    MAX-ACCESS read-write
	    STATUS current
	    DESCRIPTION 
	    "This object is used to configure the ADSL encapsulation type:
	        rfc2684LlcSnapBridged(1),
	 	    rfc2684LlcSnapRouted(2),
		    rfc2684VcmuxBridged(3),
		    rfc2684VcmuxRouted(4),				
		    rfc2364PPPoAVcmux(5),
		    rfc2364PPPoALlc(6)"
	DEFVAL { rfc2684LlcSnapBridged }
    ::= { oriADSLIfConfigBasicTableEntry 3 }

oriADSLIfConfigBasicPPPoAUserName OBJECT-TYPE
    SYNTAX DisplayString 
	    MAX-ACCESS read-write
	    STATUS current
	    DESCRIPTION 
        "This object represents the PPPoA user name."
    ::= { orinocoADSLIfConfigBasic 2 }

oriADSLIfConfigBasicPPPoAPassword OBJECT-TYPE
    SYNTAX DisplayString 
    MAX-ACCESS read-write
    STATUS current
    DESCRIPTION
        "This object represents the PPPoA password.  This object 
        should be treated as write-only and returned as asterisks."
    ::= { orinocoADSLIfConfigBasic 3 }

--=============================================================================
-- The ADSL Interface Profile 0 Advanced Configuration Subgroup: 
--     orinocoADSLIfConfigAdvanced
--=============================================================================

oriADSLIfConfigAdvTrellisCoding OBJECT-TYPE
	    SYNTAX INTEGER 
	        {
            on(1),
			off(2)			
	        }
	    MAX-ACCESS read-write
	    STATUS current
	    DESCRIPTION 
	    "This object is used to turn Trellis Coding on or off."
	    DEFVAL { on }
    ::= { orinocoADSLIfConfigAdvanced 1 }

oriADSLIfConfigAdvADSLProtocol OBJECT-TYPE
	    SYNTAX INTEGER 
	        {
            auto(1),
            ansi(2),
            gdmt(3),
            glite(4)
	        }
	    MAX-ACCESS read-write
	    STATUS current
	    DESCRIPTION 
	    "This object is used to configure the ADSL Protocol,
	         auto(1),
	         ansi(2),
	         gdmt(3),
	         glite(4)"
	    DEFVAL { auto }
    ::= { orinocoADSLIfConfigAdvanced 2 }

--=============================================================================
-- The ADSL Interface Basic Statistics Subgroup: orinocoADSLIfStatBasic
--=============================================================================

    oriADSLIfStatADSLLinkStatus  OBJECT-TYPE
	    SYNTAX INTEGER 
	        {
            idle(1),
            handshake(2),
            initializing(3),
            active(4)
	        }
	    MAX-ACCESS read-only
	    STATUS current
	    DESCRIPTION 
	    "This object represents the modem status byte:
	        idle(1)
	        handshake(2)
	        initializing(3)
	        active(4)"
	    ::= { orinocoADSLIfStatBasic 1 }

    oriADSLIfStatADSLOperationalMode  OBJECT-TYPE
	    SYNTAX INTEGER 
	        {
	            ansi(1), 
	            gdmt(2), 
	            glite(3)
	        }
	    MAX-ACCESS read-only
	    STATUS current
	    DESCRIPTION 
	    "This object represents the current operating mode:
	        ansi(1)		
	        gdmt(2)		
	        glite(3)"
	    ::= { orinocoADSLIfStatBasic 2 }

	oriADSLIfStatADSLFarEndVendorID  OBJECT-TYPE
    SYNTAX DisplayString 
		MAX-ACCESS read-only
	    STATUS current
	    DESCRIPTION 
	    "This object represents the ADSL Far end Vendor ID, which is 
	    translated from either ANSI or ITU Vendor ID into Venodr name."
	    ::= { orinocoADSLIfStatBasic 3 }

	oriADSLIfStatADSLChannelMode  OBJECT-TYPE
	    SYNTAX INTEGER 
			{ 
				fast(1), 
				interleaved(2) 
			} 
		MAX-ACCESS read-only
	    STATUS current
	    DESCRIPTION 
	    "This object represents the current ADSL Channel mode:
			fast(1),
			interleaved(2)"
	    ::= { orinocoADSLIfStatBasic 4 }

	oriADSLIfStatADSLDnStrRate  OBJECT-TYPE
	    SYNTAX Integer32
		MAX-ACCESS read-only
	    STATUS current
	    DESCRIPTION 
	    "This object represents the current downstream rate in kbps."
	    ::= { orinocoADSLIfStatBasic 5 }

	oriADSLIfStatADSLUpStrRate  OBJECT-TYPE
	    SYNTAX Integer32
		MAX-ACCESS read-only
	    STATUS current
	    DESCRIPTION 
	    "This object represents the current upstream rate in kbps."
	    ::= { orinocoADSLIfStatBasic 6 }

    oriADSLIfStatADSLLoopLength  OBJECT-TYPE
	    SYNTAX Integer32
	    MAX-ACCESS read-only
	    STATUS current
	    DESCRIPTION 
	    "This object represents the estimated looplength to CO/DSLAM."
	    ::= { orinocoADSLIfStatBasic 7 }

--=============================================================================
-- The ADSL Interface Advanced Statistics Subgroup: orinocoADSLIfStatAdvanced
--=============================================================================

    oriADSLIfStatADSLLinkRetrainSinceReset  OBJECT-TYPE
	    SYNTAX Counter32
		MAX-ACCESS read-only
	    STATUS current
	    DESCRIPTION 
	    "This counter indicates the number of links retrain since reset."
	    ::= { orinocoADSLIfStatAdvanced 1 }

    oriADSLIfStatADSLLinkRetrainCurrDay  OBJECT-TYPE
	    SYNTAX Counter32
		MAX-ACCESS read-only
	    STATUS current
	    DESCRIPTION 
		    "This counter indicates the number of link retrain during 
		    current day."
	    ::= { orinocoADSLIfStatAdvanced 2 }

    oriADSLIfStatADSLLinkRetrainCurrInterval  OBJECT-TYPE
	    SYNTAX Counter32
		MAX-ACCESS read-only
	    STATUS current
	    DESCRIPTION 
		    "This counter indicates the number of link retrain during 
		    current 15 minute interval."
	    ::= { orinocoADSLIfStatAdvanced 3 }

    oriADSLIfStatADSLInitErrorSinceReset  OBJECT-TYPE
	    SYNTAX Counter32
		MAX-ACCESS read-only
	    STATUS current
	    DESCRIPTION 
		    "This counter indicates the number of initialization errors 
		    since reset."
	    ::= { orinocoADSLIfStatAdvanced 4 }

    oriADSLIfStatADSLInitErrorCurrDay  OBJECT-TYPE
	    SYNTAX Counter32
		MAX-ACCESS read-only
	    STATUS current
	    DESCRIPTION 
		    "This counter indicates the number of initialization errors during 
		    current day."
	    ::= { orinocoADSLIfStatAdvanced 5 }

    oriADSLIfStatADSLInitErrorCurrInterval  OBJECT-TYPE
	    SYNTAX Counter32
		MAX-ACCESS read-only
	    STATUS current
	    DESCRIPTION 
		    "This counter indicates the number of initialization errors during 
		    current 15 min interval."
	    ::= { orinocoADSLIfStatAdvanced 6 }

    oriADSLIfStatADSLInitTimeoutSinceReset  OBJECT-TYPE
	    SYNTAX Counter32
		MAX-ACCESS read-only
	    STATUS current
	    DESCRIPTION 
		    "This counter indicates the number of initialization timeout 
		    since reset."
	    ::= { orinocoADSLIfStatAdvanced 7 }

    oriADSLIfStatADSLInitTimeoutCurrDay  OBJECT-TYPE
	    SYNTAX Counter32
		MAX-ACCESS read-only
	    STATUS current
	    DESCRIPTION 
		    "This counter indicates the number of initialization timeout during 
		    current day."
	    ::= { orinocoADSLIfStatAdvanced 8 }

    oriADSLIfStatADSLInitTimeoutCurrInterval  OBJECT-TYPE
	    SYNTAX Counter32
		MAX-ACCESS read-only
	    STATUS current
	    DESCRIPTION 
		    "This counter indicates the number of initialization timeout during 
		    current 15 min interval."
	    ::= { orinocoADSLIfStatAdvanced 9 }

    oriADSLIfStatADSLLomsSinceReset  OBJECT-TYPE
	    SYNTAX Counter32
		MAX-ACCESS read-only
	    STATUS current
	    DESCRIPTION 
		    "This counter indicates the number of loss margin since reset."
	    ::= { orinocoADSLIfStatAdvanced 10 }

    oriADSLIfStatADSLLomsCurrDay  OBJECT-TYPE
	    SYNTAX Counter32
		MAX-ACCESS read-only
	    STATUS current
	    DESCRIPTION 
	    "This counter indicates the number of loss margin during 
	    current day."
	    ::= { orinocoADSLIfStatAdvanced 11 }

    oriADSLIfStatADSLLomsCurrInterval  OBJECT-TYPE  
	    SYNTAX Counter32
		MAX-ACCESS read-only
	    STATUS current
	    DESCRIPTION 
		    "This counter indicates the number of loss margin during current 
		    15 min interval."
	    ::= { orinocoADSLIfStatAdvanced 12 }

    oriADSLIfStatADSLUnavailableSecondsSinceReset  OBJECT-TYPE  
	    SYNTAX Counter32
		MAX-ACCESS read-only
	    STATUS current
	    DESCRIPTION 
        "This counter indicates the number of seconds the ADSL line has 
        not been connected since reset."
	    ::= { orinocoADSLIfStatAdvanced 13 }

    oriADSLIfStatADSLUnavailableSecondsCurrDay  OBJECT-TYPE  
	    SYNTAX Counter32
		MAX-ACCESS read-only
	    STATUS current
	    DESCRIPTION 
	    "This counter indicates the number of seconds the ADSL line has 
	    not been connected during current day."
	    ::= { orinocoADSLIfStatAdvanced 14 }

    oriADSLIfStatADSLUnavailableSecondsCurrInterval  OBJECT-TYPE  
	    SYNTAX Counter32
		MAX-ACCESS read-only
	    STATUS current
	    DESCRIPTION 
	    "This counter indicates the number of seconds the ADSL line has not
	    been connected during current 15 min interval."
	    ::= { orinocoADSLIfStatAdvanced 15 }

    oriADSLIfStatADSLUpStrNoiseMargin  OBJECT-TYPE  
	    SYNTAX Integer32
		MAX-ACCESS read-only
	    STATUS current
	    DESCRIPTION 
	    "This object represents the current upstream noise margin."
	    ::= { orinocoADSLIfStatAdvanced 16 }

    oriADSLIfStatADSLDnStrNoiseMargin  OBJECT-TYPE  
	    SYNTAX Integer32
		MAX-ACCESS read-only
	    STATUS current
	    DESCRIPTION 
	    "This object represents the current downstream noise margin."
	    ::= { orinocoADSLIfStatAdvanced 17 }

    oriADSLIfStatADSLUpStrHECCount  OBJECT-TYPE
	    SYNTAX Counter32
	    MAX-ACCESS read-only
	    STATUS current
	    DESCRIPTION 
		    "This counter indicates the number of upstream received 
		    superframes with at least one cell with an errored HEC."		
	    ::= { orinocoADSLIfStatAdvanced 18 }

    oriADSLIfStatADSLDnStrHECCount  OBJECT-TYPE
	    SYNTAX Counter32
	    MAX-ACCESS read-only
	    STATUS current
	    DESCRIPTION 
		    "This counter indicates the number of downstream received 
		    superframes with at least one cell with an errored HEC."
	    ::= { orinocoADSLIfStatAdvanced 19 }

--=============================================================================
-- The ADSL Interface Basic ATM Statistics Subgroup: orinocoADSLIfStatATMBasic
--=============================================================================

    oriADSLIfStatATMProtocolStatus  OBJECT-TYPE
	    SYNTAX INTEGER 
	        {
	            active(1),
	            inactive(2),
	            error(3)
	        }
	    MAX-ACCESS read-only
	    STATUS current
	    DESCRIPTION 
	    "This object indicates the status of encapsulation protocol:
	    	active(1),
	    	inactive(2)
	    	error(3)."
	    ::= { orinocoADSLIfStatATMBasic 1 }

    oriADSLIfStatATMATMLayer  OBJECT-TYPE
	    SYNTAX INTEGER
	        {
	            sync(1),
	            unsync(2)
	        }
	    MAX-ACCESS read-only
	    STATUS current
	    DESCRIPTION 
	    "This object indicates whether ATM Layer is in sync or not:
	    	sync(1), 
	    	unsync(2)."
	    ::= { orinocoADSLIfStatATMBasic 2 }

    oriADSLIfStatATMThroughputUp  OBJECT-TYPE
	    SYNTAX Integer32
	    MAX-ACCESS read-only
	    STATUS current
	    DESCRIPTION 
        "This object indicates the upstream data throughput in Kbytes/s."
	    ::= { orinocoADSLIfStatATMBasic 3 }

    oriADSLIfStatATMThroughputDown  OBJECT-TYPE
	    SYNTAX Integer32
	    MAX-ACCESS read-only
	    STATUS current
	    DESCRIPTION 
        "This object indicates the downstream data throughput in Kbytes/s."
	    ::= { orinocoADSLIfStatATMBasic 4 }

   oriADSLIfStatATMPeakCellRate  OBJECT-TYPE
	    SYNTAX Integer32
	    MAX-ACCESS read-only
	    STATUS current
	    DESCRIPTION 
        "This object indicates the number of cells per second."
	    ::= { orinocoADSLIfStatATMBasic 5 }

--=============================================================================
-- The ADSL Interface Advanced ATM Statistics Subgroup: 
--     orinocoADSLIfStatATMAdvanced
--=============================================================================

    oriADSLIfStatATMModemUpTime  OBJECT-TYPE
    SYNTAX DisplayString
	    MAX-ACCESS read-only
	    STATUS current
	    DESCRIPTION 
        "This counter indicates the elapsed time (day:hr:min:secs format) 
        since last ADSL link up."
	    ::= { orinocoADSLIfStatATMAdvanced 1 }

    oriADSLIfStatATMUnknownVCIVPICount  OBJECT-TYPE
	    SYNTAX Counter32
	    MAX-ACCESS read-only
	    STATUS current
	    DESCRIPTION 
		    "This counter indicates the number of cells received with unknow
	    VCI or VPI number."
	    ::= { orinocoADSLIfStatATMAdvanced 2 }

    oriADSLIfStatATMRxCellCount  OBJECT-TYPE
	    SYNTAX Counter64
	    MAX-ACCESS read-only
	    STATUS current
	    DESCRIPTION 
	    "This counter indicates the number of cells received since 
		    last link up."
	    ::= { orinocoADSLIfStatATMAdvanced 3 }

    oriADSLIfStatATMTxCellCount  OBJECT-TYPE
	    SYNTAX Counter64
	    MAX-ACCESS read-only
	    STATUS current
	    DESCRIPTION 
	    "This object indicates the number of cells transmitted since 
		    last link up."
	    ::= { orinocoADSLIfStatATMAdvanced 4 }

    oriADSLIfStatATMRxByteCount  OBJECT-TYPE
	    SYNTAX Counter64
	    MAX-ACCESS read-only
	    STATUS current
	    DESCRIPTION 
	    "This object indicates the number of bytes received since 
		    last link up."		
	    ::= { orinocoADSLIfStatATMAdvanced 5 }

    oriADSLIfStatATMTxByteCount  OBJECT-TYPE
	    SYNTAX Counter64
	    MAX-ACCESS read-only
	    STATUS current
	    DESCRIPTION 
	    "This object indicates the number of bytes transmitted since 
		    last link up."		
	    ::= { orinocoADSLIfStatATMAdvanced 6 }

    oriADSLIfStatATMTxFrameCount  OBJECT-TYPE
	    SYNTAX Counter32
	    MAX-ACCESS read-only
	    STATUS current
	    DESCRIPTION 
	    "This object indicates the number of frames transmitted since 
		    last link up."	
	    ::= { orinocoADSLIfStatATMAdvanced 7 }

    oriADSLIfStatATMRxFrameCount  OBJECT-TYPE
	    SYNTAX Counter32
	    MAX-ACCESS read-only
	    STATUS current
	    DESCRIPTION 
	    "This object indicates the number of frames received since 
		    last link up."	
	    ::= { orinocoADSLIfStatATMAdvanced 8 }

    oriADSLIfStatATMRxBufOverruns  OBJECT-TYPE
	    SYNTAX Counter32
	    MAX-ACCESS read-only
	    STATUS current
	    DESCRIPTION 
	    "This object indicates the number of buffer overruns since 
		    last link up."
	    ::= { orinocoADSLIfStatATMAdvanced 9 }

    oriADSLIfStatATMRxAlignErrors  OBJECT-TYPE
	    SYNTAX Counter32
  	    MAX-ACCESS read-only
	    STATUS current
	    DESCRIPTION 
	    "This object indicates the number of alignment errors since
		    last link up."
	    ::= { orinocoADSLIfStatATMAdvanced 10 }

    oriADSLIfStatATMHECErrors  OBJECT-TYPE
	    SYNTAX Counter32
	    MAX-ACCESS read-only
	    STATUS current
	    DESCRIPTION 
	    "This object indicates the number of downstream HEC errors 
		    since last link up."
	    ::= { orinocoADSLIfStatATMAdvanced 11 }

    oriADSLIfStatATMCRCErrors  OBJECT-TYPE
	    SYNTAX Counter32
	    MAX-ACCESS read-only
	    STATUS current
	    DESCRIPTION 
	    "This object indicates the number of downstream CRC errors since
		    last link up."
	    ::= { orinocoADSLIfStatATMAdvanced 12 }

    oriADSLIfStatATMHECErrorsRate  OBJECT-TYPE
	    SYNTAX Integer32
	    MAX-ACCESS read-only
	    STATUS current
	    DESCRIPTION 
	    "This object indicates the rate of downstream HEC errors."
	    ::= { orinocoADSLIfStatATMAdvanced 13 }
                  
    oriADSLIfStatATMCRCErrorsRate  OBJECT-TYPE
	    SYNTAX Integer32
	    MAX-ACCESS read-only
	    STATUS current
	    DESCRIPTION 
	    "This object indicates the rate of downstream CRC errors."
	    ::= { orinocoADSLIfStatATMAdvanced 14 }
 
	oriADSLIfStatATMLossCellDelination  OBJECT-TYPE
	    SYNTAX Counter32
	    MAX-ACCESS read-only
	    STATUS current
	    DESCRIPTION 
	    "This object indicates the count of cell delination."
	    ::= { orinocoADSLIfStatATMAdvanced 15 }

--=============================================================================
-- The ADSL Interface Diagnosis Subgroup: orinocoADSLIfDiagnosis
--=============================================================================

oriADSLIfDiagTestCommand OBJECT-TYPE
    SYNTAX INTEGER
        {	
			hardware(1),
			togglelink(2),
			resetlink(3),		
			oamloopback(4),
			snr(5)						
        }
    MAX-ACCESS read-write
    STATUS current
    DESCRIPTION 
	    "This object indicates the test command to execute:
	    	hardware(1)
	    	togglelink(2)
	    	resetlink(3)
	    	oamloopback(4)
	    	snr(5)."
    ::= { orinocoADSLIfDiagnosis 1 }

oriADSLIfDiagHardwareTestResult OBJECT-TYPE
    SYNTAX INTEGER
        {				            
			success(1),
			failure(2),
			testing(3)		
        }
    MAX-ACCESS read-only
    STATUS current
    DESCRIPTION 
	    "This object indicates the hardware test status:
	    	success(1)
	    	failure(2)
	    	testing(3)."
    ::= { orinocoADSLIfDiagnosis 2 }

oriADSLIfDiagLinkStatus OBJECT-TYPE
    SYNTAX INTEGER
        {
            idle(1),
			handshake(2),
			training(3),
			active(4)
        }
    MAX-ACCESS read-only
    STATUS current
    DESCRIPTION 
	    "This object indicates the current link status:
	    	idle(1)
	    	handshake(2)
	    	training(3)
	    	active(4)."
    ::= { orinocoADSLIfDiagnosis 3 }

oriADSLIfDiagActivePVCTable OBJECT-TYPE
    SYNTAX SEQUENCE OF OriADSLIfDiagActivePVCTableEntry
    MAX-ACCESS not-accessible
    STATUS current
    DESCRIPTION
        "This table is used to configure/diagnose the ADSL interface
        active PVC."
    ::= { orinocoADSLIfDiagnosis 5 }

oriADSLIfDiagActivePVCTableEntry OBJECT-TYPE
    SYNTAX OriADSLIfDiagActivePVCTableEntry
    MAX-ACCESS not-accessible
    STATUS current
    DESCRIPTION 
	    "This object represents an entry in the ADSL interface active
	    PVC table.  Each entry in this table represents a PVC."
    INDEX { ifIndex }
    ::= { oriADSLIfDiagActivePVCTable 1 }

OriADSLIfDiagActivePVCTableEntry ::= 
    SEQUENCE 
        {   
        	oriADSLIfDiagActivePVCTableIndex  	Integer32,
            oriADSLIfDiagVPIActivePVC			Integer32,
            oriADSLIfDiagVCIActivePVC			Integer32,
            oriADSLIfDiagEchoActivePVC			INTEGER,
            oriADSLIfDiagEncapActivePVC			INTEGER	
        }

oriADSLIfDiagActivePVCTableIndex OBJECT-TYPE
    SYNTAX Integer32
    MAX-ACCESS read-only
    STATUS current
    DESCRIPTION 
        "This object represents the index of the ADSL active PVC Table."
    ::= { oriADSLIfDiagActivePVCTableEntry 1 }

oriADSLIfDiagVPIActivePVC OBJECT-TYPE
    SYNTAX Integer32 (0..65535)
    MAX-ACCESS read-only
    STATUS current
    DESCRIPTION 
	    "This object represents an identifier of a virtual connection
	    with a range of 0-65535."
    DEFVAL { 35 }
    ::= { oriADSLIfDiagActivePVCTableEntry  2 }

oriADSLIfDiagVCIActivePVC OBJECT-TYPE
    SYNTAX Integer32 (0..255)
    MAX-ACCESS read-only
    STATUS current
    DESCRIPTION 
	    "This object represents an identifier of a virtual path with a 
	    range of 0-255."
    DEFVAL { 0 }
    ::= { oriADSLIfDiagActivePVCTableEntry 3 }

oriADSLIfDiagEchoActivePVC OBJECT-TYPE
    SYNTAX INTEGER 
	    {			
		    on(1), 
		    off(2)
	    }
    MAX-ACCESS read-write
    STATUS current
    DESCRIPTION 
	    "This object is used to configure echo mode on or off."
    ::= { oriADSLIfDiagActivePVCTableEntry 4 }

oriADSLIfDiagEncapActivePVC OBJECT-TYPE
    SYNTAX INTEGER 
        {
	        rfc2684LlcSnapBridged(1),
	        rfc2684LlcSnapRouted(2),
	        rfc2684VcmuxBridged(3),
	        rfc2684VcmuxRouted(4),		    
	        rfc2364PPPoAVcmux(5),
	        rfc2364PPPoALlc(6)
        }
    MAX-ACCESS read-only
    STATUS current
    DESCRIPTION 
	    "This object represents the active PVC encapsulation format, which
	    can be:
		    rfc2684LlcSnapBridged(1),
		    rfc2684LlcSnapRouted(2),
		    rfc2684VcmuxBridged(3),
		    rfc2684VcmuxRouted(4),				
		    rfc2364PPPoAVcmux(5),
		    rfc2364PPPoALlc(6)."	   	
    ::= { oriADSLIfDiagActivePVCTableEntry 5 }

oriADSLIfDiagLastUnknownPVC OBJECT-TYPE
    SYNTAX DisplayString
    MAX-ACCESS read-only
    STATUS current
    DESCRIPTION 
	    "This object represents the last ATM cell with unknown PVC."
    ::= { orinocoADSLIfDiagnosis 6 }
    
--=============================================================================
-- The ADSL Interface Diagnosis Loop Back Test Subgroup: 
--     orinocoADSLIfDiagLoopBack
--=============================================================================

oriADSLIfDiagLoopBackVPI OBJECT-TYPE
    SYNTAX Integer32
    MAX-ACCESS read-write
    STATUS current
    DESCRIPTION 
	    "This object specifies the VPI number to perform the loopback 
	    test."
    ::= { orinocoADSLIfDiagLoopBack 1 }

oriADSLIfDiagLoopBackVCI OBJECT-TYPE
    SYNTAX Integer32
    MAX-ACCESS read-write
    STATUS current
    DESCRIPTION 
	    "This object specifies the VCI number to perform the loopback
	    test."
    ::= { orinocoADSLIfDiagLoopBack 2 }

oriADSLIfDiagLoopBackType OBJECT-TYPE
    SYNTAX INTEGER 
        {
		    f5end(1),
		    f4end(2),
		    f5seg(3),
		    f4seg(4)
	    }
    MAX-ACCESS read-write
    STATUS current
    DESCRIPTION 
	    "The object specifies the type of loopback test to be performed."
    ::= { orinocoADSLIfDiagLoopBack 3 }

oriADSLIfDiagLoopBackTest OBJECT-TYPE
    SYNTAX Integer32 (1..65535)
    MAX-ACCESS read-only
    STATUS current
    DESCRIPTION 
	    "This object indicates the elapsed time (in mili-seconds) before 
	    receiving a reply.  A value of 65535 indicates no reply received."
    ::= { orinocoADSLIfDiagLoopBack 4 }

oriADSLIfDiagSignalNoiseRatio OBJECT-TYPE
    SYNTAX OCTET STRING (SIZE (257))
    MAX-ACCESS read-only
    STATUS current
    DESCRIPTION
       "This object represents a 257 signed bytes for SNR value.  The last 
       byte indicates availability; A value of 0 indicates not ready and 
       a value of 1 indicates ready."
  ::= { orinocoADSLIfDiagnosis 7 } 

oriADSLIfDiagResetStatistics OBJECT-TYPE
    SYNTAX INTEGER
    MAX-ACCESS read-write
    STATUS current
    DESCRIPTION 
	    "This object is used to reset the statistics.  Setting this object
	    resets the statistics."
    ::= { orinocoADSLIfDiagnosis 8 }

oriADSLIfDiagLastErrorMsg OBJECT-TYPE
    SYNTAX DisplayString
    MAX-ACCESS read-only
    STATUS current
    DESCRIPTION 
	    "This object represents the last error message of test failure."
    ::= { orinocoADSLIfDiagnosis 9 }

oriADSLIfDiagNumActivePVC OBJECT-TYPE
    SYNTAX Integer32
    MAX-ACCESS read-only
    STATUS current
    DESCRIPTION 
	    "This object represents the number of active PVC."
    ::= { orinocoADSLIfDiagnosis 10 }      

--=============================================================================
-- The WORP Interface Subgroup: orinocoWORPIf
--=============================================================================

	oriWORPIfConfigTable		OBJECT-TYPE
		SYNTAX  SEQUENCE OF OriWORPIfConfigTableEntry
    	MAX-ACCESS not-accessible
    	STATUS current
    	DESCRIPTION
	    "This table is used to configure the mode, time-outs, and protocol 
	    objects for wireless interface(s) that are configured to run WORP."
    	::= { orinocoWORPIf 1 }

	oriWORPIfConfigTableEntry	OBJECT-TYPE
	    SYNTAX  OriWORPIfConfigTableEntry
    	MAX-ACCESS not-accessible
    	STATUS current
    	DESCRIPTION
    	    "This object represents an entry in the WORP Interface
    	    Configuration Table."
	    INDEX { ifIndex }
    	::= { oriWORPIfConfigTable 1 }
	
    OriWORPIfConfigTableEntry ::=
    	SEQUENCE
    		{
		    	oriWORPIfConfigTableMode					INTEGER,
		    	oriWORPIfConfigTableBaseStationName			DisplayString,
		    	oriWORPIfConfigTableMaxSatellites			Integer32,
		    	oriWORPIfConfigTableRegistrationTimeout		Integer32,
	    	oriWORPIfConfigTableRetries					Integer32,
	    	oriWORPIfConfigTableNetworkSecret           DisplayString
    		 }                                

  	oriWORPIfConfigTableMode    OBJECT-TYPE
	    SYNTAX INTEGER
	        {
	            disabled(1),
	            ap(2),
	            base(3),
	            satellite(4)
	        }
	    MAX-ACCESS read-write
	    STATUS current
	    DESCRIPTION
        "The running mode of this interface: 
            - If set to disabled, the interface is disabled.
            - If set to AP, the interface will run in standard IEEE802.11 
              mode.
            - If set to Base, the interface will be a WORP master 
              interface and be able to connect to multiple WORP satellites.
            - If set to Satellite, the interface will be a WORP slave 
              interface."
        DEFVAL { disabled }
	    ::= { oriWORPIfConfigTableEntry 1 } 

	oriWORPIfConfigTableBaseStationName    OBJECT-TYPE
	    SYNTAX DisplayString
	    MAX-ACCESS read-write
	    STATUS current
	    DESCRIPTION
            "The name of the base station.  For a base this name will default 
        to the MIB-II sysName; for a satellite to empty (if not registered 
            to any base) or the name it is registered to.  When a name is set 
            for a satellite, the satellite will only register on a base 
            with this name."
	    ::= { oriWORPIfConfigTableEntry 2 }

    oriWORPIfConfigTableMaxSatellites    OBJECT-TYPE
	    SYNTAX Integer32
	    MAX-ACCESS read-write
	    STATUS current
	    DESCRIPTION
            "The maximum of remotes allowed on this interface.  Please note 
            that this value will also be limited by the image and the 
            license."
	    ::= { oriWORPIfConfigTableEntry 3 }

    oriWORPIfConfigTableRegistrationTimeout    OBJECT-TYPE
	    SYNTAX Integer32 (1..10)
	    MAX-ACCESS read-write
	    STATUS current
	    DESCRIPTION
        "This object represents the Timeout of regristration and 
        authentication, configurable between 1sec and 10sec."
	    ::= { oriWORPIfConfigTableEntry 4 }

    oriWORPIfConfigTableRetries    OBJECT-TYPE
	    SYNTAX Integer32 (1..10)
	    MAX-ACCESS read-write
	    STATUS current
	    DESCRIPTION
        "The number of times a data message will be retransmitted,
        configurable between 0 and 10.  The value 0 allows unreliable 
            operation for streaming applications."
	    ::= { oriWORPIfConfigTableEntry 5 }

oriWORPIfConfigTableNetworkSecret OBJECT-TYPE
    SYNTAX DisplayString
    MAX-ACCESS read-write
    STATUS current
    DESCRIPTION
        "The NetworkSecret is a string that must be the same for all 
        stations in a certain network.  If a station has another secret 
        configured as the base, the base will not allow the station to 
        register.  This object should be treated as write-only and 
        returned as asterisks."	    
    ::= { oriWORPIfConfigTableEntry 6 }
    
	oriWORPIfStatTable		OBJECT-TYPE
		SYNTAX  SEQUENCE OF OriWORPIfStatTableEntry
    	MAX-ACCESS not-accessible
    	STATUS current
    	DESCRIPTION
	    "This table is used to monitor the statistics of interfaces that 
	    run WORP."
    	::= { orinocoWORPIf 2 }

	oriWORPIfStatTableEntry	OBJECT-TYPE
	    SYNTAX  OriWORPIfStatTableEntry
    	MAX-ACCESS not-accessible
    	STATUS current
    	DESCRIPTION
    	    "This object represents an entry in the WORP Interface
    	    Statistics Table."
	    INDEX { ifIndex }
    	::= { oriWORPIfStatTable 1 }
	
    OriWORPIfStatTableEntry ::=
    	SEQUENCE
    		{
		    	oriWORPIfStatTableRemotePartners			Counter32,
	    	oriWORPIfStatTableAverageLocalSignal		Integer32,
	    	oriWORPIfStatTableAverageLocalNoise			Integer32,
	    	oriWORPIfStatTableAverageRemoteSignal		Integer32,
	    	oriWORPIfStatTableAverageRemoteNoise		Integer32,
		    	oriWORPIfStatTableBaseStationAnnounces		Counter32,
		    	oriWORPIfStatTableRegistrationRequests		Counter32,
		    	oriWORPIfStatTableRegistrationRejects		Counter32,
		    	oriWORPIfStatTableAuthenticationRequests	Counter32,
		    	oriWORPIfStatTableAuthenticationConfirms	Counter32,
		    	oriWORPIfStatTableRegistrationAttempts		Counter32,
		    	oriWORPIfStatTableRegistrationIncompletes	Counter32,
		    	oriWORPIfStatTableRegistrationTimeouts		Counter32,
		    	oriWORPIfStatTableRegistrationLastReason	INTEGER,
		    	oriWORPIfStatTablePollData					Counter32,
		    	oriWORPIfStatTablePollNoData				Counter32,
		    	oriWORPIfStatTableReplyData					Counter32,
		    	oriWORPIfStatTableReplyMoreData				Counter32,
		    	oriWORPIfStatTableReplyNoData				Counter32,
		    	oriWORPIfStatTableRequestForService			Counter32,
		    	oriWORPIfStatTableSendSuccess				Counter32,
		    	oriWORPIfStatTableSendRetries				Counter32,
		    	oriWORPIfStatTableSendFailures				Counter32,
		    	oriWORPIfStatTableReceiveSuccess			Counter32,
		    	oriWORPIfStatTableReceiveRetries			Counter32,
		    	oriWORPIfStatTableReceiveFailures			Counter32,
		    	oriWORPIfStatTablePollNoReplies				Counter32
		    }                                

  	oriWORPIfStatTableRemotePartners    OBJECT-TYPE
	    SYNTAX Counter32
	    MAX-ACCESS read-only
	    STATUS current
	    DESCRIPTION
            "The number of remote partners.  For a satellite, this parameter
            will always be zero or one."
	    ::= { oriWORPIfStatTableEntry 1 } 

	oriWORPIfStatTableAverageLocalSignal    OBJECT-TYPE
    SYNTAX Integer32 (-102..-10)
	    MAX-ACCESS read-only
	    STATUS current
	    DESCRIPTION
            "The current signal level calculated over all inbound packets.
            This variable indicates the running average of the local signal 
            level using the algorithm (3/4*oldvalue + 1/4*newvalue)."
	    ::= { oriWORPIfStatTableEntry 2 }

	oriWORPIfStatTableAverageLocalNoise    OBJECT-TYPE
    SYNTAX Integer32 (-102..-10)
	    MAX-ACCESS read-only
	    STATUS current
	    DESCRIPTION
            "The current noise level calculated over all inbound packets.
            This variable indicates the running average of the local noise 
            level using the algorithm (3/4*oldvalue + 1/4*newvalue)."
	    ::= { oriWORPIfStatTableEntry 3 }

    oriWORPIfStatTableAverageRemoteSignal    OBJECT-TYPE
    SYNTAX Integer32 (-102..-10)
	    MAX-ACCESS read-only
	    STATUS current
	    DESCRIPTION
            "The current remote signal level calculated over the inbound 
            packets send by this station. This variable indicates the 
            running average over all registered stations of the remote 
            signal level using the algorithm (3/4*oldvalue + 1/4*newvalue)."
	    ::= { oriWORPIfStatTableEntry 4 }

    oriWORPIfStatTableAverageRemoteNoise    OBJECT-TYPE
    SYNTAX Integer32 (-102..-10)
	    MAX-ACCESS read-only
	    STATUS current
	    DESCRIPTION
            "The current average remote noise level calculated over the 
            inbound packets send by this station. This variable indicates 
            the running average over all registered stations of the remote 
            noise level using the algorithm (3/4*oldvalue + 1/4*newvalue)."
	    ::= { oriWORPIfStatTableEntry 5 }

    oriWORPIfStatTableBaseStationAnnounces    OBJECT-TYPE
	    SYNTAX Counter32
	    MAX-ACCESS read-only
	    STATUS current
	    DESCRIPTION
            "The number of Base Station Announces Broadcasts (BSAB) sent 
            (base) or received (satellite) on this interface."
	    ::= { oriWORPIfStatTableEntry 6 }

    oriWORPIfStatTableRegistrationRequests    OBJECT-TYPE
	    SYNTAX Counter32
	    MAX-ACCESS read-only
	    STATUS current
	    DESCRIPTION
            "The number of Registration Requests (RREQ) sent (satellite) or 
            received (base) on this interface."
	    ::= { oriWORPIfStatTableEntry 7 }

    oriWORPIfStatTableRegistrationRejects    OBJECT-TYPE
	    SYNTAX Counter32
	    MAX-ACCESS read-only
	    STATUS current
	    DESCRIPTION
            "The number of Registration Rejects (RREJ) sent (base) or 
            received (satellite) on this interface."
	    ::= { oriWORPIfStatTableEntry 8 }

    oriWORPIfStatTableAuthenticationRequests    OBJECT-TYPE
	    SYNTAX Counter32
	    MAX-ACCESS read-only
	    STATUS current
	    DESCRIPTION
            "The number of Authentication Requests (AREQ) sent (satellite) or 
            received (base) on this interface."
	    ::= { oriWORPIfStatTableEntry 9 }

    oriWORPIfStatTableAuthenticationConfirms    OBJECT-TYPE
	    SYNTAX Counter32
	    MAX-ACCESS read-only
	    STATUS current
	    DESCRIPTION
            "The number of Authentication Confirms (ACFM) sent (base) or 
            received (satellite) on this interface."
	    ::= { oriWORPIfStatTableEntry 10 }

    oriWORPIfStatTableRegistrationAttempts    OBJECT-TYPE
	    SYNTAX Counter32
	    MAX-ACCESS read-only
	    STATUS current
	    DESCRIPTION
            "The number of times a Registration Attempt has been initiated."
	    ::= { oriWORPIfStatTableEntry 11 }

    oriWORPIfStatTableRegistrationIncompletes    OBJECT-TYPE
	    SYNTAX Counter32
	    MAX-ACCESS read-only
	    STATUS current
	    DESCRIPTION
            "The number of registration attempts that is not completed yet. 
            For a satellite this parameters will always be zero or one."
	    ::= { oriWORPIfStatTableEntry 12 }

    oriWORPIfStatTableRegistrationTimeouts    OBJECT-TYPE
	    SYNTAX Counter32
	    MAX-ACCESS read-only
	    STATUS current
	    DESCRIPTION
        "The number of times the registration procedure timed out."
	    ::= { oriWORPIfStatTableEntry 13 }

   oriWORPIfStatTableRegistrationLastReason    OBJECT-TYPE
	    SYNTAX INTEGER
	        {
	            none(1),
	            noMoreAllowed(2),
	            incorrectParameter(3),
	            roaming(4),
	            timeout(5),
	            lowQuality(6)
	        }
	    MAX-ACCESS read-only
	    STATUS current
	    DESCRIPTION
        "The reason for why the last registration was aborted or failed."
    ::= { oriWORPIfStatTableEntry 14 }

    oriWORPIfStatTablePollData    OBJECT-TYPE
	    SYNTAX Counter32
	    MAX-ACCESS read-only
	    STATUS current
	    DESCRIPTION
            "The number of polls with data sent (base) or received 
            (satellite)."
    ::= { oriWORPIfStatTableEntry 15 }

    oriWORPIfStatTablePollNoData    OBJECT-TYPE
	    SYNTAX Counter32
	    MAX-ACCESS read-only
	    STATUS current
	    DESCRIPTION
            "The number of polls with no data sent (base) or received 
            (satellite)."
    ::= { oriWORPIfStatTableEntry 16 }

    oriWORPIfStatTableReplyData    OBJECT-TYPE
	    SYNTAX Counter32
	    MAX-ACCESS read-only
	    STATUS current
	    DESCRIPTION
            "The number of poll replies with data sent (satellite) or 
            received (base). This counter does not include replies with the 
            MoreData flag set (see ReplyMoreData)."
    ::= { oriWORPIfStatTableEntry 17 }

    oriWORPIfStatTableReplyMoreData    OBJECT-TYPE
	    SYNTAX Counter32
	    MAX-ACCESS read-only
	    STATUS current
	    DESCRIPTION
            "The number of poll replies with data sent (satellite) or 
            received (base) with the MoreData flag set (see also ReplyData)."
    ::= { oriWORPIfStatTableEntry 18 }

    oriWORPIfStatTableReplyNoData    OBJECT-TYPE
	    SYNTAX Counter32
	    MAX-ACCESS read-only
	    STATUS current
	    DESCRIPTION
            "The number of poll replies with no data sent (satellite) or 
            received (base)."
    ::= { oriWORPIfStatTableEntry 19 }

    oriWORPIfStatTableRequestForService    OBJECT-TYPE
	    SYNTAX Counter32
	    MAX-ACCESS read-only
	    STATUS current
	    DESCRIPTION
            "The number of requests for service sent (satellite) or 
            received (base)."
    ::= { oriWORPIfStatTableEntry 20 }

    oriWORPIfStatTableSendSuccess    OBJECT-TYPE
	    SYNTAX Counter32
	    MAX-ACCESS read-only
	    STATUS current
	    DESCRIPTION
            "The number of data packets sent that were acknowledged and did 
            not need a retransmit."
    ::= { oriWORPIfStatTableEntry 21 }

    oriWORPIfStatTableSendRetries    OBJECT-TYPE
	    SYNTAX Counter32
	    MAX-ACCESS read-only
	    STATUS current
	    DESCRIPTION
            "The number of data packets sent that needed retransmition but 
            were finally received succesfully by the remote partner."
    ::= { oriWORPIfStatTableEntry 22 }

    oriWORPIfStatTableSendFailures    OBJECT-TYPE
	    SYNTAX Counter32
	    MAX-ACCESS read-only
	    STATUS current
	    DESCRIPTION
            "The number of data packets sent that were (finally) not received 
            succesfully by the remote partner."
    ::= { oriWORPIfStatTableEntry 23 }

    oriWORPIfStatTableReceiveSuccess    OBJECT-TYPE
	    SYNTAX Counter32
	    MAX-ACCESS read-only
	    STATUS current
	    DESCRIPTION
            "The number of data packets received that were acknowledged and 
            did not need a retransmit of the remote partner."
    ::= { oriWORPIfStatTableEntry 24 }

    oriWORPIfStatTableReceiveRetries    OBJECT-TYPE
	    SYNTAX Counter32
	    MAX-ACCESS read-only
	    STATUS current
	    DESCRIPTION
            "The number of data packets received that needed retransmition by 
            the remote partner but were finally received succesfully."
    ::= { oriWORPIfStatTableEntry 25 }

    oriWORPIfStatTableReceiveFailures    OBJECT-TYPE
	    SYNTAX Counter32
	    MAX-ACCESS read-only
	    STATUS current
	    DESCRIPTION
            "The number of data packets that were (finally) not received 
            succesfully."
    ::= { oriWORPIfStatTableEntry 26 }

    oriWORPIfStatTablePollNoReplies    OBJECT-TYPE
	    SYNTAX Counter32
	    MAX-ACCESS read-only
	    STATUS current
	    DESCRIPTION
            "The number of times a poll was sent but no reply was received. 
        This object only applies to the base."
    ::= { oriWORPIfStatTableEntry 27 }
	    
--=============================================================================
-- The Network Group: orinocoNet
--=============================================================================

--=============================================================================
-- The Network IP Subgroup: orinocoNetIP
--=============================================================================

    oriNetworkIPConfigTable    OBJECT-TYPE
        SYNTAX SEQUENCE OF OriNetworkIPConfigTableEntry
        MAX-ACCESS not-accessible
        STATUS current
        DESCRIPTION
           "This table contains the Network IP configuration for the network 
       interface(s) of the device.  For bridge mode, only the address 
       assigned to the Ethernet interface (index 1) will be used."
        ::= { orinocoNetIP 1 }

    oriNetworkIPConfigTableEntry    OBJECT-TYPE
        SYNTAX OriNetworkIPConfigTableEntry
        MAX-ACCESS not-accessible
        STATUS current
        DESCRIPTION
       "This object represents an entry for the network IP configuration 
       for each interface in the system."
        INDEX { oriNetworkIPConfigTableIndex }
        ::= { oriNetworkIPConfigTable 1 }

    OriNetworkIPConfigTableEntry ::=
        SEQUENCE 
            {
                oriNetworkIPConfigTableIndex		Integer32,
                oriNetworkIPConfigIPAddress			IpAddress,
                oriNetworkIPConfigSubnetMask		IpAddress
            }

	oriNetworkIPConfigTableIndex	OBJECT-TYPE
	    SYNTAX Integer32
	    MAX-ACCESS read-only
	    STATUS current
	    DESCRIPTION
		"This object represents an index or interface number in the 
			network IP configuration table."
	    ::= { oriNetworkIPConfigTableEntry 1 }

	oriNetworkIPConfigIPAddress	OBJECT-TYPE
	    SYNTAX IpAddress
	    MAX-ACCESS read-write
	    STATUS current
	    DESCRIPTION
		"This object represents the IP Address of the network interface."
	    ::= { oriNetworkIPConfigTableEntry 2 }

	oriNetworkIPConfigSubnetMask OBJECT-TYPE
	    SYNTAX IpAddress
	    MAX-ACCESS read-write
	    STATUS current
	    DESCRIPTION
		"This object represents the subnet mask of the network interface."
	    ::= { oriNetworkIPConfigTableEntry 3 }

	oriNetworkIPDefaultRouterIPAddress    OBJECT-TYPE
	    SYNTAX IpAddress
	    MAX-ACCESS read-write
	    STATUS current
	    DESCRIPTION
		"This object represents the IP address of the gateway or router
		of the device."
	    ::= { orinocoNetIP 3 }

	oriNetworkIPDefaultTTL    OBJECT-TYPE
	    SYNTAX Integer32
	    MAX-ACCESS read-write
	    STATUS current
	    DESCRIPTION
			"The default value inserted into the Time-To-Live (TTL) field of 
			the IP header of datagrams originated at this entity, whenever a 
		TTL value is not supplied by the transport layer protocol."
		DEFVAL { 64 }
    	::= { orinocoNetIP 4 }

	oriNetworkIPAddressType    OBJECT-TYPE
	    SYNTAX INTEGER
			{         
			    static(1),
			    dynamic(2)
			}
	    MAX-ACCESS read-write
	    STATUS current
	    DESCRIPTION
		"This object identifies if the device is configured to be 
			assigned a static or dynamic IP address using a DHCP client."
		DEFVAL { dynamic }
	    ::= { orinocoNetIP 5 }

--=============================================================================
-- The Network IPX Subgroup: orinocoNetIPX
--=============================================================================

	oriNetworkIPXProtocolSupport    OBJECT-TYPE
	    SYNTAX INTEGER
			{
			    ip(1),
			    ipx(2),
			    both(3)
			}
	    MAX-ACCESS read-write
	    STATUS current
	    DESCRIPTION
		"This object represents what protocol will be active or supported
			by the device. For the AS-2000 device, it can be on IP mode, IPX 
		mode, or both IP and IPX mode."
		DEFVAL { ip }
	    ::= { orinocoNetIPX 1 }

	oriNetworkIPXDefaultRouterNodeNumber    OBJECT-TYPE
    	SYNTAX PhysAddress
	    MAX-ACCESS read-write
	    STATUS current
	    DESCRIPTION
			"If the source IPX network number is not equal to the destination 
			IPX Network number in the packet from wireless side to the wired 
			side, then replace the destination Ethernet MAC address with the 
			value of this object (Default IPX router node number)."
	    ::= { orinocoNetIPX 2 }

	oriNetworkIPXEthernetEncapsulationFormat    OBJECT-TYPE
	    SYNTAX INTEGER
			{
			    ethII802dot3encapsulation(1),
			    eth802dot3withSNAPHdr(2),
			    eth802dot3withoutSNAPHdr(3)
			}
	    MAX-ACCESS read-write
	    STATUS current
	    DESCRIPTION
			"This object represents the encapsulation type to be used for the 
		IPX packets sent on the wired interface."
		DEFVAL { ethII802dot3encapsulation }
	    ::= { orinocoNetIPX 3 }

	oriNetworkIPXWiredtoWirelessBridgedPacketCount    OBJECT-TYPE
	    SYNTAX Counter32
	    MAX-ACCESS read-only
	    STATUS current
	    DESCRIPTION
			"This object represents the number of packets bridged from the 
		wired to wireless interface."
	    ::= { orinocoNetIPX 4 }

	oriNetworkIPXWirelesstoWiredBridgedPacketCount    OBJECT-TYPE
	    SYNTAX Counter32
	    MAX-ACCESS read-only
	    STATUS current
	    DESCRIPTION
			"This object represents the number of packets bridged from the 
		wireless to wired interface."
	    ::= { orinocoNetIPX 5 }

    oriNetworkIPXClientTable    OBJECT-TYPE
        SYNTAX SEQUENCE OF OriNetworkIPXClientEntry
        MAX-ACCESS not-accessible
        STATUS current
        DESCRIPTION
       "This table provides statistics for the IPX clients (AS Clients
       using the IPX protocol) connected to the AS-2000 device."
        ::= { orinocoNetIPX 6 }

    oriNetworkIPXClientEntry    OBJECT-TYPE
        SYNTAX OriNetworkIPXClientEntry
        MAX-ACCESS not-accessible
        STATUS current
        DESCRIPTION
       "This object represents an entry in the IPX client table."
        INDEX { oriNetworkIPXPPPSessionId }
        ::= { oriNetworkIPXClientTable 1 }

    OriNetworkIPXClientEntry ::=
        SEQUENCE 
            {
                oriNetworkIPXPPPSessionId			Integer32,
                oriNetworkIPXClientNetworkNumber	OCTET STRING,
                oriNetworkIPXClientMAC         		PhysAddress,
                oriNetworkIPXClientTableEntryStatus		INTEGER
            }

    oriNetworkIPXPPPSessionId   OBJECT-TYPE
        SYNTAX Integer32 
        MAX-ACCESS read-only
        STATUS current
        DESCRIPTION
        "This object represents the PPP Session ID assigned by the 
        AS-2000 to the IPX client (AS Client)."
        ::= { oriNetworkIPXClientEntry 1 }

    oriNetworkIPXClientNetworkNumber    OBJECT-TYPE
        SYNTAX OCTET STRING
        MAX-ACCESS read-only
        STATUS current
        DESCRIPTION
        "This object represents the IPX Node Number assigned by a Novell 
        Server to the IPX client (AS Client)."
        ::= { oriNetworkIPXClientEntry 2 }

    oriNetworkIPXClientMAC OBJECT-TYPE
        SYNTAX PhysAddress
        MAX-ACCESS read-only
        STATUS current
        DESCRIPTION
        "This object represents the wireless interface MAC of the 
        IPX client (AS Client)."
        ::= { oriNetworkIPXClientEntry 3 }

    oriNetworkIPXClientTableEntryStatus    OBJECT-TYPE
        SYNTAX INTEGER
            {
                enable(1),
                disable(2),
                delete(3)
            }
        MAX-ACCESS read-write
        STATUS current
        DESCRIPTION
       "This object is used to indicate whether an IPX client (AS Client)
       is active or inactive.  This object is also used to terminate an
       IPX client session/connection."
        ::= { oriNetworkIPXClientEntry 4 }

--=============================================================================
-- The SNMP Group: orinocoSNMP
--=============================================================================

	oriSNMPReadPassword    OBJECT-TYPE
	    SYNTAX DisplayString
	    MAX-ACCESS read-write
	    STATUS current
	    DESCRIPTION
		"This object represents the read-only community name used in the
		SNMP protocol.  This object is used for reading objects from the
		SNMP agent.  This object should be treated as write-only and 
		returned as asterisks."
		DEFVAL { "public" }
	    ::= { orinocoSNMP 1 }

	oriSNMPReadWritePassword    OBJECT-TYPE
	    SYNTAX DisplayString
	    MAX-ACCESS read-write
	    STATUS current
	    DESCRIPTION
		"This objecgt represents the read-write community name used in 
		the SNMP protocol.  This object is used for reading and writing
		objects to and from the SNMP Agent.  This object should be treated 
		as write-only and returned as asterisks."
		DEFVAL { "public" }
	    ::= { orinocoSNMP 2 }

	oriSNMPAuthorizedManagerCount    OBJECT-TYPE
	    SYNTAX Counter32
	    MAX-ACCESS read-only
	    STATUS current
	    DESCRIPTION
		"This object reflects the number of entries in the Management IP 
			Access Table."
	    ::= { orinocoSNMP 3 }

	oriSNMPAccessTable    OBJECT-TYPE
	    SYNTAX SEQUENCE OF OriSNMPAccessTableEntry
	    MAX-ACCESS not-accessible
	    STATUS current
	    DESCRIPTION
		"This table is used configure management stations that are
		authorized to manage the device.  This table applies to the 
		supported management services/interfaces (SNMP, HTTP, and Telnet).
		This table is limited to 20 entries."
	    ::= { orinocoSNMP 4 }

	oriSNMPAccessTableEntry    OBJECT-TYPE
    	SYNTAX OriSNMPAccessTableEntry
	    MAX-ACCESS not-accessible
	    STATUS current
	    DESCRIPTION
		"This object identifies an entry in the Management IP Access 
		Table."
	    INDEX { oriSNMPAccessTableIndex }
    	::= { oriSNMPAccessTable 1 }

	OriSNMPAccessTableEntry ::=
		SEQUENCE
			{
				oriSNMPAccessTableIndex			Integer32,
				oriSNMPAccessTableIPAddress		IpAddress,
				oriSNMPAccessTableIPMask		IpAddress,
			oriSNMPAccessTableInterfaceBitmask	InterfaceBitmask,
				oriSNMPAccessTableComment		DisplayString,
				oriSNMPAccessTableEntryStatus	INTEGER
		    }

	oriSNMPAccessTableIndex    OBJECT-TYPE
	    SYNTAX Integer32
	    MAX-ACCESS read-only
	    STATUS current
	    DESCRIPTION
		"This object represents the index for the Management IP Access
		Table."
	    ::= { oriSNMPAccessTableEntry 1 }

	oriSNMPAccessTableIPAddress    OBJECT-TYPE
	    SYNTAX IpAddress
	    MAX-ACCESS read-write
	    STATUS current
	    DESCRIPTION
		"This object represents the IP address of the management station
			authorized to manage the device."
	    ::= { oriSNMPAccessTableEntry 2 }

	oriSNMPAccessTableIPMask    OBJECT-TYPE
	    SYNTAX IpAddress
	    MAX-ACCESS read-write
	    STATUS current
	    DESCRIPTION
		"This object represents the IP subnet mask.  This object can
			be used to grant access to a complete subnet."
	    ::= { oriSNMPAccessTableEntry 3 }

oriSNMPAccessTableInterfaceBitmask OBJECT-TYPE
    SYNTAX InterfaceBitmask
	    MAX-ACCESS read-write
	    STATUS current
	    DESCRIPTION
			"This object is used to control the interface access for each 
		table entry in the Management IP Access Table."
	    ::= { oriSNMPAccessTableEntry 4 }

	oriSNMPAccessTableComment    OBJECT-TYPE
	    SYNTAX DisplayString
	    MAX-ACCESS read-write
	    STATUS current
	    DESCRIPTION
		"This object is used for an optional comment associated to the 
		Management IP Access Table entry."
	    ::= { oriSNMPAccessTableEntry 5 }

	oriSNMPAccessTableEntryStatus    OBJECT-TYPE
	    SYNTAX INTEGER
			{
			    enable(1),
			    disable(2),
		    delete(3),
		    create(4)
			}
	    MAX-ACCESS read-write
	    STATUS current
	    DESCRIPTION
		"This object is used to enable, disable, delete, or create an 
		entry in the Management IP Access Table."
	    ::= { oriSNMPAccessTableEntry 6 }

	oriSNMPTrapHostTable    OBJECT-TYPE
	    SYNTAX SEQUENCE OF OriSNMPTrapHostTableEntry
	    MAX-ACCESS not-accessible
    	STATUS current
	    DESCRIPTION
			"This table contains the information regarding the trap host that 
			will receive SNMP traps sent by the device.  This table is limited
			10 entries."
	    ::= { orinocoSNMP 5 }

	oriSNMPTrapHostTableEntry    OBJECT-TYPE
	    SYNTAX OriSNMPTrapHostTableEntry
	    MAX-ACCESS not-accessible
	    STATUS current
	    DESCRIPTION
		"This object identifies an entry in the SNMP Trap Host Table."
	    INDEX { oriSNMPTrapHostTableIndex }
	    ::= { oriSNMPTrapHostTable 1 }

	OriSNMPTrapHostTableEntry ::=
		SEQUENCE
			{
				oriSNMPTrapHostTableIndex			Integer32,
				oriSNMPTrapHostTableIPAddress		IpAddress,
				oriSNMPTrapHostTablePassword		DisplayString,
				oriSNMPTrapHostTableComment			DisplayString,
				oriSNMPTrapHostTableEntryStatus		INTEGER
		    }                      

	oriSNMPTrapHostTableIndex    OBJECT-TYPE
	    SYNTAX Integer32
	    MAX-ACCESS read-only 
	    STATUS current
	    DESCRIPTION
		"This object is used as an index for the SNMP Trap Host Table."
	    ::= { oriSNMPTrapHostTableEntry 1 }

	oriSNMPTrapHostTableIPAddress    OBJECT-TYPE
	    SYNTAX IpAddress
	    MAX-ACCESS read-write
	    STATUS current
	    DESCRIPTION
		"This object represents the IP address of the management station
		that will receive SNMP Traps from the device."
	    ::= { oriSNMPTrapHostTableEntry 2 }

	oriSNMPTrapHostTablePassword    OBJECT-TYPE
	    SYNTAX DisplayString
	    MAX-ACCESS read-write
	    STATUS current
	    DESCRIPTION
		"This object represents the password that is sent with the SNMP
		trap messages to allow the host to accept or reject the traps.  
			The trap host will only accept SNMP traps if this password matches 
			the host's password.  This object should be treated as write-only 
			and returned as asterisks."
	    ::= { oriSNMPTrapHostTableEntry 3 }

	oriSNMPTrapHostTableComment    OBJECT-TYPE
	    SYNTAX DisplayString
	    MAX-ACCESS read-write
	    STATUS current
	    DESCRIPTION
		"This object is used for an optional comment associated to the 
			SNMP Trap Host Table entry."
	    ::= { oriSNMPTrapHostTableEntry 4 }

	oriSNMPTrapHostTableEntryStatus    OBJECT-TYPE
	    SYNTAX INTEGER
			{
			    enable(1),
			    disable(2),
		    delete(3),
		    create(4)
			}
	    MAX-ACCESS read-write
	    STATUS current
	    DESCRIPTION
		"This object is used to enable, disable, delete, create an 
			entry in the SNMP Trap Host Table."
	    ::= { oriSNMPTrapHostTableEntry 5 }

oriSNMPInterfaceBitmask OBJECT-TYPE
    SYNTAX InterfaceBitmask
    MAX-ACCESS read-write
    STATUS current
    DESCRIPTION
        "This object is used to control the interface access for SNMP 
        based management (not HTTP and Telnet)."
    ::= { orinocoSNMP 7 }

      oriSNMPErrorMessage OBJECT-TYPE
      SYNTAX DisplayString
      MAX-ACCESS read-only
      STATUS current
      DESCRIPTION
        "This object is used to provide additional information in case of
        an SNMP error."
     ::= { orinocoSNMP 8 }        

	oriSNMPAccessTableStatus    OBJECT-TYPE
	    SYNTAX INTEGER
	        {
	            enable(1),
	            disable(2)
	        }
	    MAX-ACCESS read-write
	    STATUS current
	    DESCRIPTION
		"This object is used to enable or disable the Management IP Access
		Table.  If this object is disabled, the check based on source IP
		address for the enteries in the Management IP Access Table will not
		be performed."
    ::= { orinocoSNMP 9 }
        
--=============================================================================
-- The Protocol Filtering Subgroup: orinocoProtocolFilter
--=============================================================================

	oriProtocolFilterOperationType  OBJECT-TYPE
	    SYNTAX INTEGER
		    {
			     passthru(1),
	    		 block(2) 
		    } 
    	MAX-ACCESS read-write
	    STATUS current
	    DESCRIPTION 
		"This object is used to passthru (allow) or block (deny) packets
		with protocols in the protocol filter table."
		DEFVAL { block } 
	    ::= { orinocoProtocolFilter 1 }

	oriProtocolFilterTable OBJECT-TYPE
	    SYNTAX SEQUENCE OF OriProtocolFilterTableEntry
	    MAX-ACCESS not-accessible
	    STATUS current
	    DESCRIPTION
			"This table contains the two byte hexadecimal values of the 
			protocols. The packets whose protocol field matches with any of 
			the entries in this table will be forwarded or dropped based on 
			value of oriProtocolFilterFlag.  This table is limited to 256
		ethernet protocols (enteries)."
	    ::= { orinocoProtocolFilter 2 }

	oriProtocolFilterTableEntry  OBJECT-TYPE
	    SYNTAX OriProtocolFilterTableEntry
	    MAX-ACCESS not-accessible
	    STATUS current
	    DESCRIPTION
		"This object represents an entry in the protocol filter table."
	    INDEX { oriProtocolFilterTableIndex }
	    ::= { oriProtocolFilterTable 1 }

	OriProtocolFilterTableEntry  ::=
		SEQUENCE
		    {
				oriProtocolFilterTableIndex			Integer32,
				oriProtocolFilterProtocol			OCTET STRING,
				oriProtocolFilterProtocolComment 	DisplayString,
				oriProtocolFilterTableEntryStatus			INTEGER,
			oriProtocolFilterTableInterfaceBitmask	InterfaceBitmask,
			oriProtocolFilterProtocolString			DisplayString
		    }

	oriProtocolFilterTableIndex OBJECT-TYPE
	    SYNTAX Integer32
	    MAX-ACCESS read-only
	    STATUS current
	    DESCRIPTION
		"This object is used to index the protocol filter table."
	    ::= { oriProtocolFilterTableEntry 1 }

	oriProtocolFilterProtocol  OBJECT-TYPE
	    SYNTAX OCTET STRING (SIZE(2))
	    MAX-ACCESS read-write
	    STATUS current
	    DESCRIPTION
		"This object represents a two byte hexadecimal value for the 
		Ethernet protocol to be filtered (the protocol field of the 
		Ethernet packet)."
	    ::= { oriProtocolFilterTableEntry 2 }

	oriProtocolFilterProtocolComment  OBJECT-TYPE
	    SYNTAX DisplayString
	    MAX-ACCESS read-write
	    STATUS current
	    DESCRIPTION
		"This object is used as an optional comment for the ethernet 
		protocol to be filtered."
	    ::= { oriProtocolFilterTableEntry 3 }

	oriProtocolFilterTableEntryStatus   OBJECT-TYPE 
	    SYNTAX INTEGER
		   {
		      enable(1),
		      disable(2),
	      delete(3),
	      create(4)
		   }
	    MAX-ACCESS read-write
	    STATUS current
	    DESCRIPTION
		"This object is used to enable, disable, delete, create the 
		Ethernet protocols in this table."
	    ::= { oriProtocolFilterTableEntry 4 }

oriProtocolFilterTableInterfaceBitmask OBJECT-TYPE 
    SYNTAX InterfaceBitmask
    MAX-ACCESS read-write
    STATUS current
    DESCRIPTION
		"This object is isued to control protocol filtering per interface
		for each entry in this table."
    ::= { oriProtocolFilterTableEntry 5 }

oriProtocolFilterProtocolString OBJECT-TYPE
    SYNTAX DisplayString
    MAX-ACCESS read-write
    STATUS current
    DESCRIPTION
		"This object represents the value in the protocol field of the 
		Ethernet packet. The value is of 4-digit Hex format. 
		Example:	The value of IP protocol is 0800. 
		       		The value of ARP protocol is 0806."
    ::= { oriProtocolFilterTableEntry 6}

oriProtocolFilterInterfaceBitmask OBJECT-TYPE
    SYNTAX InterfaceBitmask
    MAX-ACCESS read-write
    STATUS current
    DESCRIPTION
		"This object is isued to control protocol filtering per interface
		for the table."
    ::= { orinocoProtocolFilter 3 }
    
--=============================================================================
-- The Access Control Subgroup: orinocoAccessControl
--=============================================================================

	oriAccessControlStatus  OBJECT-TYPE
	    SYNTAX INTEGER
		   {
		        enable(1),
		        disable(2)
		   } 
	    MAX-ACCESS read-write
	    STATUS current
	    DESCRIPTION
		"This object is used to enable or disable MAC Access Control 
		feature/filter in the device."
		DEFVAL { disable }
	    ::= { orinocoAccessControl 1 } 

	oriAccessControlOperationType OBJECT-TYPE
	    SYNTAX INTEGER
		    {
		        passthru(1),       
		        block(2)
		    } 
    	MAX-ACCESS read-write
	    STATUS current
	    DESCRIPTION
			"This flag determines whether the stations with MAC addresses 
		listed in the access control table will be allowed or denied 
		access.  This flag is used only if oriAccessControlStatus is 
		enabled.  This table is limited to 1000 MAC Address entries."
		DEFVAL { passthru }
	    ::= { orinocoAccessControl 2 }      

	oriAccessControlTable OBJECT-TYPE
	    SYNTAX SEQUENCE OF OriAccessControlEntry
	    MAX-ACCESS not-accessible
	    STATUS current
	    DESCRIPTION
			"This table contains the information about MAC addresses of the 
			wireless stations that are either allowed or disallowed access 
		(based on oriAccessControlOperation) through this device. 
			This table is used only if oriAccessControlStatus is enabled."
	    ::= { orinocoAccessControl 3 }

	oriAccessControlEntry OBJECT-TYPE
	    SYNTAX OriAccessControlEntry	
	    MAX-ACCESS not-accessible
	    STATUS current
	    DESCRIPTION
		"This object represents the entry in the access control table."
	    INDEX { oriAccessControlTableIndex }
	    ::= { oriAccessControlTable 1 }

	OriAccessControlEntry ::=
		SEQUENCE
	    	{
				oriAccessControlTableIndex			Integer32, 
				oriAccessControlTableMACAddress		PhysAddress, 
		        oriAccessControlTableComment		DisplayString, 
		        oriAccessControlTableEntryStatus	INTEGER 
			}

	oriAccessControlTableIndex OBJECT-TYPE
	    SYNTAX Integer32
	    MAX-ACCESS read-only
	    STATUS current
	    DESCRIPTION
		"This object is used as an index for the access control table."
	    ::= { oriAccessControlEntry 1 }

	oriAccessControlTableMACAddress OBJECT-TYPE
	    SYNTAX PhysAddress
	    MAX-ACCESS read-write
	    STATUS current
	    DESCRIPTION
		"This object represents the MAC address of the wireless station 
		that can access the device."
	    ::= { oriAccessControlEntry 2 }

	oriAccessControlTableComment OBJECT-TYPE
	    SYNTAX DisplayString
	    MAX-ACCESS read-write
	    STATUS current
	    DESCRIPTION
		"This object is used as an optional comment associated to the 
			access control table entry."
	    ::= { oriAccessControlEntry 3 }

	oriAccessControlTableEntryStatus OBJECT-TYPE 
	    SYNTAX INTEGER
			{
				enable(1),
				disable(2),
	        delete(3),
	        create(4)
			}
	    MAX-ACCESS read-write
	    STATUS current
	    DESCRIPTION
		"This object is used to enable, disable, delete, create the entries
		in the Access Control Table."
	    ::= { oriAccessControlEntry 4 }

--=============================================================================
-- The Static MAC Address Filter Subgroup: orinocoStaticMACAddressFilter
--=============================================================================

	oriStaticMACAddressFilterTable OBJECT-TYPE 
	    SYNTAX SEQUENCE OF OriStaticMACAddressFilterEntry 
	    MAX-ACCESS not-accessible
	    STATUS current
	    DESCRIPTION
		"This table provides the MAC address of the stations on the wired 
		and the wireless interface; the MAC addresses will be given in 
		pairs.  Stations listed in the Static MAC Address filter will 
		have no traffic forwarded by the device.  This way Multicast 
			traffic exchanged between stations or servers can be prevented, 
			from being transmitted over the wireless medium when both stations 
			are actually located on the wired backbone.  This table is limited
			to 200 entries."
	    ::= { orinocoStaticMACAddressFilter 1 }

	oriStaticMACAddressFilterEntry  OBJECT-TYPE
	    SYNTAX OriStaticMACAddressFilterEntry 
	    MAX-ACCESS not-accessible
	    STATUS current
	    DESCRIPTION
		"This object identifies the entry in the Static MAC address 
		filter table."
	    INDEX { oriStaticMACAddressFilterTableIndex }
	    ::= { oriStaticMACAddressFilterTable 1 }

	OriStaticMACAddressFilterEntry ::=
		SEQUENCE
			{
				oriStaticMACAddressFilterTableIndex			Integer32,
		        oriStaticMACAddressFilterWiredAddress		PhysAddress,
		        oriStaticMACAddressFilterWiredMask			PhysAddress,
		        oriStaticMACAddressFilterWirelessAddress	PhysAddress,
		        oriStaticMACAddressFilterWirelessMask		PhysAddress,
		        oriStaticMACAddressFilterTableEntryStatus 	INTEGER,
		        oriStaticMACAddressFilterComment			DisplayString 
	    	}

	oriStaticMACAddressFilterTableIndex OBJECT-TYPE
	    SYNTAX Integer32
	    MAX-ACCESS read-only
	    STATUS current
	    DESCRIPTION
		"This object is used as an index for the Static MAC address 
		filter table."
	    ::= { oriStaticMACAddressFilterEntry 1 }       

	oriStaticMACAddressFilterWiredAddress OBJECT-TYPE
	    SYNTAX PhysAddress
	    MAX-ACCESS read-write
	    STATUS current
	    DESCRIPTION
		"This object represents the MAC address of the station on the 
		wired interface of the device."
	    ::= { oriStaticMACAddressFilterEntry 2 }       

	oriStaticMACAddressFilterWiredMask OBJECT-TYPE
	    SYNTAX PhysAddress
	    MAX-ACCESS read-write
	    STATUS current 
	    DESCRIPTION
			"This mask determines the presence of wildcard characters in the 
		MAC address of the station on the wired interface.  The value F 
		(hex digit) in the mask indicates the presence of a wildcard 
		character and the value 0 indicates its absence."
	    ::= { oriStaticMACAddressFilterEntry 3 }           

	oriStaticMACAddressFilterWirelessAddress OBJECT-TYPE
	    SYNTAX PhysAddress
	    MAX-ACCESS read-write
	    STATUS current
	    DESCRIPTION
		"This object represents the MAC address of the station on the 
		wireless interface."
	    ::= { oriStaticMACAddressFilterEntry 4 }

	oriStaticMACAddressFilterWirelessMask OBJECT-TYPE
    	SYNTAX PhysAddress
		MAX-ACCESS read-write
	    STATUS current 
	    DESCRIPTION
			"The mask that determines the presence of wildcard characters in 
			the MAC address of the station on the wireless side. The value F 
			(hex digit) indicates the presence of a wildcard character and the 
			hex digit 0 indicates its absense."
	    ::= { oriStaticMACAddressFilterEntry 5 }       

	oriStaticMACAddressFilterTableEntryStatus   OBJECT-TYPE 
	    SYNTAX INTEGER
			{
				enable(1),
			    disable(2),
		    delete(3),
		    create(4)
			}
	    MAX-ACCESS read-write
    	STATUS current
	    DESCRIPTION
		"This object is used to enable, disable, delete, create an entry
		in the Static MAC Address Table."
	    ::= { oriStaticMACAddressFilterEntry 6 }

	oriStaticMACAddressFilterComment    OBJECT-TYPE
	    SYNTAX DisplayString
	    MAX-ACCESS read-write
	    STATUS current
	    DESCRIPTION
		"This object is used for an optional comment associated to the 
			access control table entry."
	    ::= { oriStaticMACAddressFilterEntry 7 }
	    
--=============================================================================
-- The Storm Threshold Subgroup: orinocoStormThreshold
--=============================================================================

	oriBroadcastAddressThreshold OBJECT-TYPE
	    SYNTAX Integer32 (0..255)
	    MAX-ACCESS read-write
	    STATUS current
	    DESCRIPTION 
			"If broadcast rate from any device (identified by its MAC address) 
		exceeds the limit specified by this value, the device will 
			ignore all subsequent messages issued by the particular network 
			device, or ignore all messages of that type. Valid values for 
			address threshold is between 0 - 255 frames per second. Initial 
			Value is 0 (Disable Storm Threshold Protection)."
		DEFVAL { 0 }
    	::= { orinocoStormThreshold 1 }

	oriMulticastAddressThreshold OBJECT-TYPE
	    SYNTAX Integer32 (0..255)
	    MAX-ACCESS read-write
	    STATUS current
	    DESCRIPTION 
			"If multicast rate from any device (identified by its MAC address) 
		exceeds the limit specified by this value, the device will 
			ignore all subsequent messages issued by the particular network 
			device, or ignore all messages of that type. Valid values for 
			address threshold is between 0 - 255 frames per second. Initial 
			Value is 0 (Disable Storm Threshold Protection)."
		DEFVAL { 0 }
	    ::= { orinocoStormThreshold 2 }

	oriStormThresholdTable OBJECT-TYPE
	    SYNTAX SEQUENCE OF OriStormThresholdTableEntry
	    MAX-ACCESS not-accessible
	    STATUS current
	    DESCRIPTION
			"The table containing broadcast and multicast threshold values for 
			each interface."
	    ::= { orinocoStormThreshold 3 }

	oriStormThresholdTableEntry  OBJECT-TYPE
	    SYNTAX OriStormThresholdTableEntry
	    MAX-ACCESS not-accessible
	    STATUS current
	    DESCRIPTION
		"This object represents an entry in the storm threshold filter 
		table."
	    INDEX { ifIndex }
	   ::= { oriStormThresholdTable 1 }

	OriStormThresholdTableEntry ::=
		SEQUENCE
	    	{
				oriStormThresholdIfBroadcast	Integer32,
	    	    oriStormThresholdIfMulticast	Integer32
		    }

	oriStormThresholdIfBroadcast  OBJECT-TYPE
	    SYNTAX Integer32 (0..9999)
	    MAX-ACCESS read-write
	    STATUS current
	    DESCRIPTION
			"This parameter specifies a set of Broadcast Storm thresholds for 
		each interface/port of the device, identifying separate 
			values for the number of Broadcast messages/second.  Default value
			is zero, which means disabled."
		DEFVAL { 0 } 
	    ::= { oriStormThresholdTableEntry 1 }

	oriStormThresholdIfMulticast  OBJECT-TYPE        
	    SYNTAX Integer32 (0..9999)
	    MAX-ACCESS read-write
	    STATUS current
	    DESCRIPTION
			"This parameter specifies a set of Multicast Storm thresholds for 
		each interface/port of the device, identifying separate 
			values for the number of Multicast messages/second.  Default value
			is zero, which means disabled."
		DEFVAL { 0 } 
	    ::= { oriStormThresholdTableEntry 2 }

--=============================================================================
-- The Port Filtering Subgroup: orinocoPortFilter
-- Filtering per Interface based on IP Address and Port Number.
--=============================================================================

	oriPortFilterStatus  OBJECT-TYPE
	    SYNTAX INTEGER
		   {
		        enable(1),
		        disable(2)
		   } 
	    MAX-ACCESS read-write
	    STATUS current
	    DESCRIPTION
		"This object is used to enable or disable port filtering."
		DEFVAL { disable }
	    ::= { orinocoPortFilter 1 } 

	oriPortFilterOperationType OBJECT-TYPE
	    SYNTAX INTEGER
		    {
		        passthru(1),       
		        block(2)
		    } 
    	MAX-ACCESS read-write
	    STATUS current
	    DESCRIPTION
		"This object determines whether the stations with ports 
		listed in the port filter table must be allowed (passthru) or 
		denied (block) to access the device.  This object is used only if 
		oriPacketFilterStatus is enabled."
		DEFVAL { passthru }
	    ::= { orinocoPortFilter 2 }      

	oriPortFilterTable OBJECT-TYPE
	    SYNTAX SEQUENCE OF OriPortFilterTableEntry
	    MAX-ACCESS not-accessible
	    STATUS current
	    DESCRIPTION
		"This table contains the Port number of packets to be filtered. 
		The packets whose port field matches with any of the enabled entries in 
		this table will be blocked (dropped).  This table is limited to 
		256 entries."
	    ::= { orinocoPortFilter 3 }

	oriPortFilterTableEntry OBJECT-TYPE
	    SYNTAX OriPortFilterTableEntry	
	    MAX-ACCESS not-accessible
	    STATUS current
	    DESCRIPTION
		"This parameter represents the entry in the port filter table."
	    INDEX { oriPortFilterTableEntryIndex }
	    ::= { oriPortFilterTable 1 }

	OriPortFilterTableEntry ::=
		SEQUENCE
	    	{
				oriPortFilterTableEntryIndex				Integer32, 
				oriPortFilterTableEntryPort					Integer32, 
				oriPortFilterTableEntryPortType				INTEGER, 
				oriPortFilterTableEntryInterfaceBitmask		InterfaceBitmask,
		        oriPortFilterTableEntryComment				DisplayString, 
		        oriPortFilterTableEntryStatus				INTEGER 
			}

	oriPortFilterTableEntryIndex OBJECT-TYPE
	    SYNTAX Integer32 (0..256)
	    MAX-ACCESS read-only
	    STATUS current
	    DESCRIPTION
		"This object is used as the index for the port filter table.  This
		table supports up to 256 entries."
	    ::= { oriPortFilterTableEntry 1 }

	oriPortFilterTableEntryPort OBJECT-TYPE
	    SYNTAX Integer32
	    MAX-ACCESS read-write
	    STATUS current
	    DESCRIPTION
		"This object represents the port number of the packets to be 
		filtered."
	    ::= { oriPortFilterTableEntry 2 }

	oriPortFilterTableEntryPortType OBJECT-TYPE 
	    SYNTAX INTEGER
			{
				tcp(1),
				udp(2),
		        both(3)
			}
	    MAX-ACCESS read-write
	    STATUS current
	    DESCRIPTION
	    "This object specifies the port type."
	    ::= { oriPortFilterTableEntry 3 }

	oriPortFilterTableEntryInterfaceBitmask    OBJECT-TYPE
	    SYNTAX InterfaceBitmask
	    MAX-ACCESS read-write
	    STATUS current
	    DESCRIPTION
		"This object is used to control port filtering per interface for 
		each entry in the table."
		::= { oriPortFilterTableEntry 4 }

	oriPortFilterTableEntryComment OBJECT-TYPE
	    SYNTAX DisplayString
	    MAX-ACCESS read-write
	    STATUS current
	    DESCRIPTION
		"This object is used for an optional comment associated to the 
			port filter table entry."
	    ::= { oriPortFilterTableEntry 5 }

	oriPortFilterTableEntryStatus OBJECT-TYPE 
	    SYNTAX INTEGER
			{
				enable(1),
				disable(2),
		        delete(3),
		        create(4)
			}
	    MAX-ACCESS read-write
	    STATUS current
	    DESCRIPTION
		"This object is used to enable, disable, delete, create an entry
		in the Port Filter Table."
	    ::= { oriPortFilterTableEntry 6 }

--=============================================================================
-- The Advanced Bridge Filtering Subgroup: orinocoAdvancedFiltering
--=============================================================================

	oriBroadcastFilteringTable OBJECT-TYPE
	    SYNTAX SEQUENCE OF OriBroadcastFilteringTableEntry
	    MAX-ACCESS not-accessible
	    STATUS current
	    DESCRIPTION
			"The table entries for broadcast filters.  This table shall contain
			5 entries."
	    ::= { orinocoAdvancedFiltering 1 }

	oriBroadcastFilteringTableEntry  OBJECT-TYPE
	    SYNTAX OriBroadcastFilteringTableEntry
	    MAX-ACCESS not-accessible
	    STATUS current
	    DESCRIPTION
			"This object represents an entry in the broadcast filtering 
			table."
	    INDEX { oriBroadcastFilteringTableIndex }
	    ::= { oriBroadcastFilteringTable 1 }

	OriBroadcastFilteringTableEntry ::=
		SEQUENCE
	    	{
				oriBroadcastFilteringTableIndex		Integer32,
				oriBroadcastFilteringProtocolName	DisplayString,
				oriBroadcastFilteringDirection		INTEGER,
				oriBroadcastFilteringTableEntryStatus 	INTEGER
		    }

    oriBroadcastFilteringTableIndex    OBJECT-TYPE
        SYNTAX Integer32
        MAX-ACCESS read-only
        STATUS current
        DESCRIPTION
            "This object represents the index of the Broadcast Filtering
            table."
        ::= { oriBroadcastFilteringTableEntry 1 }

    oriBroadcastFilteringProtocolName    OBJECT-TYPE
        SYNTAX DisplayString
        MAX-ACCESS read-only
        STATUS current
        DESCRIPTION
            "This object represents the broadcast protocol name to
            be filtered."
        ::= { oriBroadcastFilteringTableEntry 2 }

    oriBroadcastFilteringDirection    OBJECT-TYPE
        SYNTAX INTEGER
            {
                ethernetToWireless(1),
                wirelessToEthernet(2),
                both(3)
            }
        MAX-ACCESS read-write
        STATUS current
        DESCRIPTION
        "This object represents the direction of the broadcast filter.
            The filter can be enabled for Ethernet to Wireless, Wireless
        to Ethernet, or both directions."
        ::= { oriBroadcastFilteringTableEntry 3 }

    oriBroadcastFilteringTableEntryStatus    OBJECT-TYPE
        SYNTAX INTEGER
            {
                enable(1),
                disable(2)
            }
        MAX-ACCESS read-write
        STATUS current
        DESCRIPTION
        "This object is used to enable or disable the broadcast filter
        table enteries."
        ::= { oriBroadcastFilteringTableEntry 4 }

--=============================================================================
-- The Packet Forwarding Subgroup: orinocoPacketForwarding
--=============================================================================

	oriPacketForwardingStatus OBJECT-TYPE
    	SYNTAX INTEGER
	        {
        	enable(1),
        	disable(2)
		    }
    	MAX-ACCESS read-write
	    STATUS current
	    DESCRIPTION
        "This object is used to enable or disable the Packet Forwarding 
		feature."
	    DEFVAL { disable }
	    ::= { orinocoPacketForwarding 1 }

	oriPacketForwardingMACAddress OBJECT-TYPE
	    SYNTAX MacAddress
	    MAX-ACCESS read-write
	    STATUS current
	    DESCRIPTION
		"This object represents the MAC Address to which all frames will be
		forwarded by the device."
	    ::= { orinocoPacketForwarding 2 }   
                                         
	oriPacketForwardingInterface OBJECT-TYPE
	    SYNTAX Integer32 (0..15)
	    MAX-ACCESS read-write
	    STATUS current
	    DESCRIPTION
	    "This object is used to configure the interface or port that frames
        will be forwarded to.  If this object is not configured, value set
	    to zero, then the bridge will forward the packets on the interface
        or port the MAC address was learned on.  If this object is not
        configured, value set to zero, and the bridge has not yet learned the
        MAC address then the frames will be forwarded on all interfaces and 
        ports."
    ::= { orinocoPacketForwarding 3 }  
    
--=============================================================================
-- The IntraBSS Traffic Control Subgroup
--=============================================================================

	oriIBSSTrafficOperation OBJECT-TYPE
    	SYNTAX INTEGER
	        {
	            passthru(1),
	            block(2)
		    }
	    MAX-ACCESS read-write
	    STATUS current
	    DESCRIPTION
	        "This object is used to control IntraBSS Traffic.  If this object
	        is set to the passthru, then IBSS traffic will be allowed; if this
	        object is set to block, then IBSS traffic will be denied."
	    DEFVAL { passthru }
	    ::= { orinocoIBSSTraffic 1 }

--=============================================================================
-- The RADIUS Group: orinocoRADIUS
--=============================================================================

	oriRADIUSClientInvalidServerAddress	OBJECT-TYPE
	    SYNTAX Counter32
	    MAX-ACCESS read-only
	    STATUS current
	    DESCRIPTION
			"This counter represents the total number of RADIUS access-response
		messages received from an unknown address since system startup."
		::= { orinocoRADIUS 3 }

	oriRADIUSMACAccessControl	OBJECT-TYPE
	    SYNTAX INTEGER
			{
			    enable(1),
			    disable(2)
			}
	    MAX-ACCESS read-write
	    STATUS current
	    DESCRIPTION
		"This object is used to enables RADIUS Access Control based on 
		wireless stations MAC Address."
		DEFVAL { disable }
		::= { orinocoRADIUS 4 }

	oriRADIUSAuthorizationLifeTime	OBJECT-TYPE
	    SYNTAX Integer32 (900..43200)
	    MAX-ACCESS read-write
	    STATUS current
	    DESCRIPTION
		"This object represents the authorization lifetime for a certain 
		MAC based RADIUS authenticated client.  The units for this object 
		is seconds."
		DEFVAL { 900 }
		::= { orinocoRADIUS 5 }  
		
	oriRADIUSMACAddressFormat OBJECT-TYPE
	    SYNTAX INTEGER
	        {
	            dashDelimited(1),
	            colonDelimited(2),
	            singleDashDelimited(3),
                noDelimiter(4)
            
		    }
	    MAX-ACCESS read-write
	    STATUS current
	    DESCRIPTION
	        "This object is used to configure the MAC Address format that is to be 
        used for communication with the RADIUS Server.
        Examples of MAC Address Format are:
            - Dash Delimited:        00-11-22-AA-BB-CC
            - Colon Delimited:       00:11:22:AA:BB:CC
            - Single Dash Delimited: 001122-AABBCC
            - No Delimiter:          001122AABBCC"
	    DEFVAL { dashDelimited }
	    ::= { orinocoRADIUS 6 }
		
--=============================================================================
-- The RADIUS Authentication Group: orinocoRADIUSAuth
--=============================================================================

	oriRADIUSAuthServerTable	OBJECT-TYPE
	    SYNTAX SEQUENCE OF OriRADIUSAuthServerTableEntry
	    MAX-ACCESS not-accessible
	    STATUS current
	    DESCRIPTION
			"This table represents the RADIUS servers that the device will 
		communicated with for client authentication.  Usually this table 
		should have two members representing the primary and secondary 
		(backup) RADIUS Authentication Servers."
	    ::= { orinocoRADIUSAuth 1 }

	oriRADIUSAuthServerTableEntry    OBJECT-TYPE
	    SYNTAX OriRADIUSAuthServerTableEntry
	    MAX-ACCESS not-accessible
	    STATUS current
	    DESCRIPTION
		"This object represents an entry in the RADIUS Authentication
			Server Table."
	    INDEX { oriRADIUSAuthServerTableIndex }
	    ::= { oriRADIUSAuthServerTable 1 }

	OriRADIUSAuthServerTableEntry ::=
		SEQUENCE
		    {
				oriRADIUSAuthServerTableIndex					Integer32,
				oriRADIUSAuthServerType							INTEGER,
				oriRADIUSAuthServerTableEntryStatus				INTEGER,
				oriRADIUSAuthServerIPAddress					IpAddress,
				oriRADIUSAuthServerDestPort						Integer32,
				oriRADIUSAuthServerSharedSecret					DisplayString,
				oriRADIUSAuthServerResponseTime					Integer32,
				oriRADIUSAuthServerMaximumRetransmission		Integer32,
				oriRADIUSAuthClientAccessRequests				Counter32,
				oriRADIUSAuthClientAccessRetransmissions		Counter32,
				oriRADIUSAuthClientAccessAccepts				Counter32,
				oriRADIUSAuthClientAccessChallenges				Counter32,
				oriRADIUSAuthClientAccessRejects				Counter32,
				oriRADIUSAuthClientMalformedAccessResponses		Counter32,
				oriRADIUSAuthClientAuthInvalidAuthenticators	Counter32,
				oriRADIUSAuthClientTimeouts						Counter32,      
				oriRADIUSAuthServerNameOrIPAddress				DisplayString,
				oriRADIUSAuthServerAddressingFormat				INTEGER
			}

	oriRADIUSAuthServerTableIndex    OBJECT-TYPE
	    SYNTAX Integer32
	    MAX-ACCESS read-only
	    STATUS current
	    DESCRIPTION
		"This object is used as an index to the RADIUS Authentication
		Server Table."
	    ::= { oriRADIUSAuthServerTableEntry 1 }

	oriRADIUSAuthServerType    OBJECT-TYPE
	    SYNTAX INTEGER
			{
			    authentication(1),
			    accounting(2),
			    authAndAcct(3)
			}
	    MAX-ACCESS read-only
	    STATUS current
	    DESCRIPTION
		"This object indicates if the RADIUS server will provide 
			Authentication service, Accounting service, or both."
	    ::= { oriRADIUSAuthServerTableEntry 2 }

	oriRADIUSAuthServerTableEntryStatus    OBJECT-TYPE
	    SYNTAX INTEGER
			{
			    enable(1),
			    disable(2)
			}
	    MAX-ACCESS read-write
	    STATUS current
	    DESCRIPTION
		"This object identifies if the RADIUS server entry is enabled or
			disabled."
	    ::= { oriRADIUSAuthServerTableEntry 3 }

	oriRADIUSAuthServerIPAddress    OBJECT-TYPE
	    SYNTAX IpAddress
	    MAX-ACCESS read-write
	    STATUS deprecated
	    DESCRIPTION
		"This object represents the IP address of the RADIUS server."
	    ::= { oriRADIUSAuthServerTableEntry 4 }

	oriRADIUSAuthServerDestPort    OBJECT-TYPE
	    SYNTAX Integer32
	    MAX-ACCESS read-write
	    STATUS current
	    DESCRIPTION
		"This object represents the RADIUS server authentication port - 
			the default value is 1812."
		DEFVAL { 1812 }
	    ::= { oriRADIUSAuthServerTableEntry 5 }

	oriRADIUSAuthServerSharedSecret    OBJECT-TYPE
	    SYNTAX DisplayString
	    MAX-ACCESS read-write
	    STATUS current
	    DESCRIPTION
		"This object represents the shared secret between the RADIUS 
			server and client.  This object should be treated as write-only 
			and returned as asterisks."
	    ::= { oriRADIUSAuthServerTableEntry 6 }

	oriRADIUSAuthServerResponseTime    OBJECT-TYPE
	    SYNTAX Integer32 (1..10)
	    MAX-ACCESS read-write
	    STATUS current
	    DESCRIPTION
		"This object represents the time (in seconds) for which the 
			RADIUS client will wait, until another authentication request is
		sent to the server."
		DEFVAL { 3 }
	    ::= { oriRADIUSAuthServerTableEntry 7 }

	oriRADIUSAuthServerMaximumRetransmission    OBJECT-TYPE
	    SYNTAX Integer32 (1..4)
	    MAX-ACCESS read-write
    	STATUS current
	    DESCRIPTION
		"This object represents the number of retransmissions of 
		authentication requests by the RADIUS Client to the Server."
		DEFVAL { 3 }
	    ::= { oriRADIUSAuthServerTableEntry 8 }

	oriRADIUSAuthClientAccessRequests    OBJECT-TYPE
    	SYNTAX Counter32
	    MAX-ACCESS read-only
    	STATUS current
	    DESCRIPTION
		"This object represents the number of RADIUS Access Requests 
			messages transmitted from the client to the server since client 
			startup."
	    ::= { oriRADIUSAuthServerTableEntry 9 }

	oriRADIUSAuthClientAccessRetransmissions    OBJECT-TYPE
	    SYNTAX Counter32
	    MAX-ACCESS read-only
	    STATUS current
	    DESCRIPTION	
		"This object represents the number of RADIUS Access Requests 
		retransmitted by the client to the server since system startup."
	    ::= { oriRADIUSAuthServerTableEntry 10 }

	oriRADIUSAuthClientAccessAccepts    OBJECT-TYPE
	    SYNTAX Counter32
	    MAX-ACCESS read-only
	    STATUS current
	    DESCRIPTION
		"This object indicates the number of RADIUS Access Accept messages 
		received since system startup."
	    ::= { oriRADIUSAuthServerTableEntry 11 }

	oriRADIUSAuthClientAccessChallenges    OBJECT-TYPE
	    SYNTAX Counter32
	    MAX-ACCESS read-only
	    STATUS current
	    DESCRIPTION	
		"This object represents the number of RADIUS Access Challenges 
		messages received since system startup."
	    ::= { oriRADIUSAuthServerTableEntry 12 }

	oriRADIUSAuthClientAccessRejects    OBJECT-TYPE
	    SYNTAX Counter32
	    MAX-ACCESS read-only
	    STATUS current
	    DESCRIPTION
		"This object represents the number of RADIUS Access Rejects 
		messages received since system startup."
	    ::= { oriRADIUSAuthServerTableEntry 13 }

	oriRADIUSAuthClientMalformedAccessResponses    OBJECT-TYPE
	    SYNTAX Counter32
	    MAX-ACCESS read-only
	    STATUS current
	    DESCRIPTION
		"This object represents the number of malformed RADIUS Access 
		Response messages received since system startup."
	    ::= { oriRADIUSAuthServerTableEntry 14 }

	oriRADIUSAuthClientAuthInvalidAuthenticators    OBJECT-TYPE
	    SYNTAX Counter32
	    MAX-ACCESS read-only
	    STATUS current
	    DESCRIPTION	
		"This object represents the number of malformed RADIUS Access 
			Response messages containing invalid authenticators received since 
		system startup."
	    ::= { oriRADIUSAuthServerTableEntry 15 }

	oriRADIUSAuthClientTimeouts    OBJECT-TYPE
	    SYNTAX Counter32
	    MAX-ACCESS read-only	
	    STATUS current
	    DESCRIPTION
		"This object represents the total number of timeouts for RADIUS 
		Access Request messages since system startup."
	    ::= { oriRADIUSAuthServerTableEntry 16 }          

	oriRADIUSAuthServerNameOrIPAddress OBJECT-TYPE
	    SYNTAX DisplayString
	    MAX-ACCESS read-write
	    STATUS current
	    DESCRIPTION
	        "This object is used to specify the RADIUS Server host name or
	        IP Address."            
	    ::= { oriRADIUSAuthServerTableEntry 17 }
	
	oriRADIUSAuthServerAddressingFormat OBJECT-TYPE
	    SYNTAX INTEGER
	        {
	            ipAddress(1),
	            name(2)
	        }
	    MAX-ACCESS read-write
	    STATUS current
	    DESCRIPTION
	        "This object is used to specify the addressing format for configuring
	        the RADIUS Server.  If this object is configured to IP Address, then
	        IP address should be used to specify the server.  If this object is
	        configured to name, then the host name should be specified."      
		DEFVAL { ipAddress }		        
	    ::= { oriRADIUSAuthServerTableEntry 18 }
	    
--=============================================================================
-- The RADIUS Accounting Group: orinocoRADIUSAcct
--=============================================================================

	oriRADIUSAcctStatus OBJECT-TYPE
	    SYNTAX INTEGER
	        {
	            enable(1),
	            disable(2)
		    }
	    MAX-ACCESS read-write
	    STATUS current
	    DESCRIPTION
	        "This object is used to enable or disable the RADIUS Accounting 
	        service."
	    DEFVAL { disable }
	    ::= { orinocoRADIUSAcct 1 }
	
	oriRADIUSAcctInactivityTimer OBJECT-TYPE
	    SYNTAX Integer32 (1..60)
	    MAX-ACCESS read-write
	    STATUS current
	    DESCRIPTION
			"This parameter represents the inactivity or idle timeout in 
			minutes after which an Accounting Stop request is sent to the
			RADIUS Accounting server - the default value is 5 minutes."
		DEFVAL { 5 }
	    ::= { orinocoRADIUSAcct 2 }

	oriRADIUSAcctServerTable	OBJECT-TYPE
	    SYNTAX SEQUENCE OF OriRADIUSAcctServerTableEntry
	    MAX-ACCESS not-accessible
	    STATUS current
	    DESCRIPTION
			"This table represents the RADIUS servers that the device will 
			communicated with for accounting.  Usually this table should 
		have two members representing the primary and secondary (backup) 
			RADIUS Accounting Servers."
	    ::= { orinocoRADIUSAcct 3 }

	oriRADIUSAcctServerTableEntry    OBJECT-TYPE
	    SYNTAX OriRADIUSAcctServerTableEntry
	    MAX-ACCESS not-accessible
	    STATUS current
	    DESCRIPTION
		"This object represents an entry into the RADIUS Accouting
			Server Table."
	    INDEX { oriRADIUSAcctServerTableIndex }
	    ::= { oriRADIUSAcctServerTable 1 }

	OriRADIUSAcctServerTableEntry ::=
		SEQUENCE
		    {
				oriRADIUSAcctServerTableIndex					Integer32,
				oriRADIUSAcctServerType							INTEGER,
				oriRADIUSAcctServerTableEntryStatus				INTEGER,
				oriRADIUSAcctServerIPAddress					IpAddress,
				oriRADIUSAcctServerDestPort						Integer32,
				oriRADIUSAcctServerSharedSecret					DisplayString,
				oriRADIUSAcctServerResponseTime					Integer32,
				oriRADIUSAcctServerMaximumRetransmission		Integer32,
				oriRADIUSAcctClientAccountingRequests			Counter32,
				oriRADIUSAcctClientAccountingRetransmissions	Counter32,
				oriRADIUSAcctClientAccountingResponses			Counter32,
				oriRADIUSAcctClientAcctInvalidAuthenticators	Counter32, 
				oriRADIUSAcctServerNameOrIPAddress				DisplayString,
				oriRADIUSAcctServerAddressingFormat				INTEGER
			}
  
	oriRADIUSAcctServerTableIndex    OBJECT-TYPE
	    SYNTAX Integer32
	    MAX-ACCESS read-only
	    STATUS current
	    DESCRIPTION
		"This object is used as the index to the RADIUS Server Accounting
		table."
	    ::= { oriRADIUSAcctServerTableEntry 1 }

	oriRADIUSAcctServerType    OBJECT-TYPE
	    SYNTAX INTEGER
			{
			    authentication(1),
			    accounting(2),
			    authAndAcct(3)
			}
	    MAX-ACCESS read-only
	    STATUS current
	    DESCRIPTION
		"This object indicates if the RADIUS server will provide 
			Authentication service, Accounting service, or both."
	    ::= { oriRADIUSAcctServerTableEntry 2 }
  
	oriRADIUSAcctServerTableEntryStatus    OBJECT-TYPE
	    SYNTAX INTEGER
			{
			    enable(1),
			    disable(2)
			}
	    MAX-ACCESS read-write
	    STATUS current
	    DESCRIPTION
		"This object identifies if the RADIUS server entry is enabled or
			disabled."
	    ::= { oriRADIUSAcctServerTableEntry 3 }

	oriRADIUSAcctServerIPAddress    OBJECT-TYPE
	    SYNTAX IpAddress
	    MAX-ACCESS read-write
	    STATUS deprecated
	    DESCRIPTION
		"This object represents the IP address of the RADIUS server."
	    ::= { oriRADIUSAcctServerTableEntry 4 }
  
	oriRADIUSAcctServerDestPort    OBJECT-TYPE
	    SYNTAX Integer32
	    MAX-ACCESS read-write
	    STATUS current
	    DESCRIPTION
		"This object represents the RADIUS server accounting port - 
			the default value is 1813."
		DEFVAL { 1813 }
	    ::= { oriRADIUSAcctServerTableEntry 5 }

	oriRADIUSAcctServerSharedSecret    OBJECT-TYPE
	    SYNTAX DisplayString
	    MAX-ACCESS read-write
	    STATUS current
	    DESCRIPTION
		"This object represents the shared secret between the RADIUS 
			server and client.  This object should be treated as write-only 
			and returned as asterisks."
	    ::= { oriRADIUSAcctServerTableEntry 6 }

	oriRADIUSAcctServerResponseTime    OBJECT-TYPE
	    SYNTAX Integer32 (1..10)
	    MAX-ACCESS read-write
	    STATUS current
	    DESCRIPTION
		"This object represents the time (in seconds) for which the 
			RADIUS client will wait, until another authentication request is
		sent to the server."
		DEFVAL { 3 }
	    ::= { oriRADIUSAcctServerTableEntry 7 }

	oriRADIUSAcctServerMaximumRetransmission    OBJECT-TYPE
	    SYNTAX Integer32 (1..4)
	    MAX-ACCESS read-write
    	STATUS current
	    DESCRIPTION
		"This object represents the number of retransmissions of 
		authentication requests by the RADIUS Client to the Server."
		DEFVAL { 3 }
	    ::= { oriRADIUSAcctServerTableEntry 8 }

	oriRADIUSAcctClientAccountingRequests    OBJECT-TYPE
	    SYNTAX Counter32
	    MAX-ACCESS read-only
	    STATUS current
	    DESCRIPTION		
		"This object represents the number of Accounting Requests messages 
		sent since system startup."
	    ::= { oriRADIUSAcctServerTableEntry 9 }

	oriRADIUSAcctClientAccountingRetransmissions    OBJECT-TYPE
	    SYNTAX Counter32
	    MAX-ACCESS read-only
	    STATUS current
	    DESCRIPTION
		"This object represents the number of Accounting Requests 
		messages retransmitted sent since system startup."
	    ::= { oriRADIUSAcctServerTableEntry 10 }

	oriRADIUSAcctClientAccountingResponses    OBJECT-TYPE
	    SYNTAX Counter32
	    MAX-ACCESS read-only
	    STATUS current
	    DESCRIPTION
		"This object represents the number of Accounting Response messages 
		received since system startup."
	    ::= { oriRADIUSAcctServerTableEntry 11 }

	oriRADIUSAcctClientAcctInvalidAuthenticators    OBJECT-TYPE
	    SYNTAX Counter32
	    MAX-ACCESS read-only
	    STATUS current
	    DESCRIPTION
		"This object represents the number of Accounting Response 
		messages which contain invalid authenticators received since system
			startup."
	    ::= { oriRADIUSAcctServerTableEntry 12 }   

	oriRADIUSAcctServerNameOrIPAddress OBJECT-TYPE
	    SYNTAX DisplayString
	    MAX-ACCESS read-write
	    STATUS current
	    DESCRIPTION
	        "This object is used to specify the RADIUS Server host name or the
	        IP Address."
	    ::= { oriRADIUSAcctServerTableEntry 13 }

	oriRADIUSAcctServerAddressingFormat OBJECT-TYPE
	    SYNTAX INTEGER
	        {
	            ipAddress(1),
	            name(2)
	        }
	    MAX-ACCESS read-write
	    STATUS current
	    DESCRIPTION
	        "This object is used to specify the addressing format for configuring
	        the RADIUS Server.  If this object is configured to IP Address, then
	        IP address should be used to specify the server.  If this object is
	        configured to name, then the host name should be specified."  
 		DEFVAL { ipAddress }	        
	    ::= { oriRADIUSAcctServerTableEntry 14 }

--=============================================================================
-- The Telnet Group: orinocoTelnet
--=============================================================================

oriTelnetSessions OBJECT-TYPE
	SYNTAX Integer32 (0..5)
    MAX-ACCESS read-write
    STATUS deprecated
    DESCRIPTION
		"This object is used to enable or disable telnet access and
	    to specify the maximum number of active telnet sessions.  When this
	    object is set to 0, telnet access is disabled.  When this object
	    is set to something greater than 0, then it specifies the maximum
	    number of active telnet sessions.  This object has been deprecated."
	DEFVAL { 1 }
    ::= { orinocoTelnet 1 }

	oriTelnetPassword    OBJECT-TYPE
	    SYNTAX DisplayString
	    MAX-ACCESS read-write
	    STATUS current
	    DESCRIPTION
		"This object is the password to access the device via the telnet
		interface.  This object should be treated as write-only and 
		returned as asterisks."
		DEFVAL { "public" }
	    ::= { orinocoTelnet 2 }

	oriTelnetPort    OBJECT-TYPE
	    SYNTAX Integer32
	    MAX-ACCESS read-write
	    STATUS current
	    DESCRIPTION
		"This object represents the TCP/IP port for which the telnet 
		daemon/server will be accessible."
		DEFVAL { 23 }
	    ::= { orinocoTelnet 3 }

	oriTelnetLoginTimeout    OBJECT-TYPE
	    SYNTAX Integer32 (0..300)
	    MAX-ACCESS read-write
	    STATUS current
	    DESCRIPTION
		"This object represents the telnet login timeout in seconds."
		DEFVAL { 30 }
	    ::= { orinocoTelnet 4 }

	oriTelnetIdleTimeout    OBJECT-TYPE
	    SYNTAX Integer32 (0..36000)
	    MAX-ACCESS read-write
	    STATUS current
	    DESCRIPTION
		"This object represents the telnet inactivity/idle timeout in 
		seconds."
		DEFVAL { 900 }
	    ::= { orinocoTelnet 5 }

	oriTelnetInterfaceBitmask    OBJECT-TYPE
	    SYNTAX InterfaceBitmask
	    MAX-ACCESS read-write
	    STATUS current
	    DESCRIPTION
			"This object is used to control interface access for telnet based 
			management."
		::= { orinocoTelnet 6 }
	    
--=============================================================================
-- The TFTP Group: orinocoTFTP
--=============================================================================

	oriTFTPServerIPAddress    OBJECT-TYPE
	    SYNTAX IpAddress
	    MAX-ACCESS read-write
	    STATUS current
	    DESCRIPTION
		"This object represents the IP address of the TFTP server."
        DEFVAL { '0a000002'H }
	    ::= { orinocoTFTP 1 }

	oriTFTPFileName    OBJECT-TYPE
	    SYNTAX DisplayString
	    MAX-ACCESS read-write
	    STATUS current
	    DESCRIPTION
		"This object represents the filename to upload or download to the 
		TFTP server."
		DEFVAL { "Filename" }
	    ::= { orinocoTFTP 2 }

	oriTFTPFileType    OBJECT-TYPE
	    SYNTAX INTEGER
		    {
	        config(1),
		        image(2),
	        bootloader(3),
	        license(4)
		    }
	    MAX-ACCESS read-write
	    STATUS current
	    DESCRIPTION	
		"This object is used for the device to know what type of file is
			being uploaded or downloaded."
	    ::= { orinocoTFTP 3 }

	oriTFTPOperation    OBJECT-TYPE 
	    SYNTAX INTEGER
			{
			    upload(1),
			    download(2),
				downloadAndReboot(3)
			}
	    MAX-ACCESS read-write
	    STATUS current
	    DESCRIPTION
		"This object represents the TFTP operation to be executed.  The
		upload function shall transfer the specified file from the
			device to the TFTP server.  The download function shall transfer
		the specified file from the TFTP server to the device.  The 
		download and reboot option, will perform the download and then 
		reboot the device."
	    ::= { orinocoTFTP 4 }

	oriTFTPFileMode    OBJECT-TYPE 
	    SYNTAX INTEGER
			{
			    ascii(1),
			    bin(2)
			}
	    MAX-ACCESS read-write
	    STATUS current
	    DESCRIPTION
	        "This objects represents the file transfer mode for the TFTP
	        protocol."
	    ::= { orinocoTFTP 5 }

	oriTFTPOperationStatus    OBJECT-TYPE 
	    SYNTAX INTEGER
			{
			    idle(1),
			    inProgress(2),
			    successful(3),
				failure(4)
			}
	    MAX-ACCESS read-only
	    STATUS current
	    DESCRIPTION
		"This object represents the TFTP operation status.  When a TFTP
			operation is idle (not in progress) this object will be set to 1.
			When a TFTP operation is in progress this object will be set to 2.  
			When a TFTP operation has been successful this object will be set 
			to 3.  When a TFTP operation has failed this object will be set 
			to 4."
	    ::= { orinocoTFTP 6 }
	    
--=============================================================================
-- The Serial Group: orinocoSerial
--=============================================================================

	oriSerialBaudRate    OBJECT-TYPE
	    SYNTAX INTEGER
			{
			    baud2400(1),
			    baud4800(2),
			    baud9600(3),
			    baud19200(4),
			    baud38400(5),
			    baud57600(6)
			}
	    MAX-ACCESS read-write
	    STATUS current
	    DESCRIPTION
		"This object represents the baud rate for the serial interface -
			the default value is 9600."
		DEFVAL { baud9600 }
	    ::= { orinocoSerial 1 }

	oriSerialDataBits    OBJECT-TYPE
	    SYNTAX Integer32 (4..8)
	    MAX-ACCESS read-only
	    STATUS current
	    DESCRIPTION
		"This object represents the serial interface data bits - the 
			default value is 8."
		DEFVAL { 8 }
	    ::= { orinocoSerial 2 }

	oriSerialParity    OBJECT-TYPE
	    SYNTAX INTEGER
			{
			    even(1),
			    odd(2),
			    none(3),
			    mark(4),
			    space(5)
			}
	    MAX-ACCESS read-only
	    STATUS current
	    DESCRIPTION
		"This object is used for the serial interface parity check - the
			default value is none."
		DEFVAL { none }
	    ::= { orinocoSerial 3 }

	oriSerialStopBits    OBJECT-TYPE
	    SYNTAX INTEGER
			{
			    bit1(1),
			    bit1dot5(2),
			    bit2(3)
			}
	    MAX-ACCESS read-only
	    STATUS current
	    DESCRIPTION
		"This object indicates the serial interface stop bits - the 
			default value is 1."
		DEFVAL { bit1 }
	    ::= { orinocoSerial 4 }

	oriSerialFlowControl    OBJECT-TYPE
	    SYNTAX INTEGER
			{
			    xonxoff(1),
			    none(2)
			}
	    MAX-ACCESS read-write
	    STATUS current
	    DESCRIPTION
		"This object is used for the serial interface flow control - the
			default value is none."
		DEFVAL { none }
	    ::= { orinocoSerial 5 }

--=============================================================================
-- The IAPP Group: orinocoIAPP
--=============================================================================

	oriIAPPStatus    OBJECT-TYPE
	    SYNTAX INTEGER
			{
			    enable(1),
			    disable(2)
			}
	    MAX-ACCESS read-write
	    STATUS current
	    DESCRIPTION
		"This object is used to enable or disable the IAPP feature."
		DEFVAL { enable }
	    ::= { orinocoIAPP 1 }

	oriIAPPPeriodicAnnounceInterval    OBJECT-TYPE
	    SYNTAX INTEGER
			{
				eighty(80),
				oneHundredTwenty(120),
				oneHundredSixty(160),
				twoHundred(200)
			}
	    MAX-ACCESS read-write
	    STATUS current
	    DESCRIPTION
		"This object represents interval in seconds for performing an 
		IAPP announce operation by the device."
		DEFVAL { oneHundredTwenty }
	    ::= { orinocoIAPP 2 }

	oriIAPPAnnounceResponseTime    OBJECT-TYPE
	    SYNTAX Integer32
	    MAX-ACCESS read-only
	    STATUS current
	    DESCRIPTION
		"This object indicates the amount of time in seconds the 
			device waits to send an IAPP announce response after an announce 
		request message is sent."
	    ::= { orinocoIAPP 3 }

	oriIAPPHandoverTimeout    OBJECT-TYPE
	    SYNTAX INTEGER
			{
			    fourHundredTen(410),
				fiveHundredTwelve(512),
				sixHundredFourteen(614),
				sevenHundredSeventeen(717),
				eightHundredNineteen(819)
			}
	    MAX-ACCESS read-write
	    STATUS current
	    DESCRIPTION
		"This object represents the time in milliseconds the device 
		waits before it resends a handover response message.  This
		object is originally given in kuseconds, but has been converted
			to milliseconds."
		DEFVAL { fiveHundredTwelve }
	    ::= { orinocoIAPP 4 }

	oriIAPPMaximumHandoverRetransmissions    OBJECT-TYPE
	    SYNTAX Integer32 (1..4)
	    MAX-ACCESS read-write
	    STATUS current	
	    DESCRIPTION
		"This object indicates the maximum amount of retransmission sent
		by the device for a handover request message."
		DEFVAL { 4 }
	    ::= { orinocoIAPP 5 }

	oriIAPPAnnounceRequestSent    OBJECT-TYPE
	    SYNTAX Counter32
	    MAX-ACCESS read-only
	    STATUS current
	    DESCRIPTION
		"This object represents the total number of IAPP Announce 
		Request Messages sent since system startup."
	    ::= { orinocoIAPP 6 }

	oriIAPPAnnounceRequestReceived    OBJECT-TYPE
	    SYNTAX Counter32
	    MAX-ACCESS read-only
	    STATUS current
	    DESCRIPTION
		"This object represents the total number of IAPP Announce 
		Request Messages received since system startup."		
	    ::= { orinocoIAPP 7 }

	oriIAPPAnnounceResponseSent    OBJECT-TYPE
	    SYNTAX Counter32
	    MAX-ACCESS read-only
	    STATUS current
	    DESCRIPTION	
		"This object represents the total number of IAPP Announce 
		Response Messages sent since system startup."
	    ::= { orinocoIAPP 8 }

	oriIAPPAnnounceResponseReceived    OBJECT-TYPE
	    SYNTAX Counter32
	    MAX-ACCESS read-only
	    STATUS current
	    DESCRIPTION
		"This object represents the total number of IAPP Announce 
		Response Messages received since system startup."
	    ::= { orinocoIAPP 9 }

	oriIAPPHandoverRequestSent    OBJECT-TYPE
	    SYNTAX Counter32
	    MAX-ACCESS read-only
	    STATUS current
	    DESCRIPTION
		"This object represents the total number of IAPP Handover 
		Request messages sent since system startup."
	    ::= { orinocoIAPP 10}

	oriIAPPHandoverRequestReceived    OBJECT-TYPE
	    SYNTAX Counter32
	    MAX-ACCESS read-only
	    STATUS current
	    DESCRIPTION
		"This object represents the total number of IAPP Handover 
		Request messages received since system startup."
	    ::= { orinocoIAPP 11 }

	oriIAPPHandoverRequestRetransmissions    OBJECT-TYPE
	    SYNTAX Counter32
	    MAX-ACCESS read-only
	    STATUS current
	    DESCRIPTION
		"This object represents the total number of IAPP Handover 
		Request retransmissions since system startup."
	    ::= { orinocoIAPP 12 }

	oriIAPPHandoverResponseSent    OBJECT-TYPE
	    SYNTAX Counter32
	    MAX-ACCESS read-only
	    STATUS current
	    DESCRIPTION
		"This object represents the total number of IAPP Handover 
		Response messages sent since system startup."
	    ::= { orinocoIAPP 13 }

	oriIAPPHandoverResponseReceived    OBJECT-TYPE
	    SYNTAX Counter32
	    MAX-ACCESS read-only
	    STATUS current
	    DESCRIPTION
		"This object represents the total number of IAPP Handover 
		Response messages received since system startup."
	    ::= { orinocoIAPP 14 }

	oriIAPPPDUsDropped    OBJECT-TYPE
	    SYNTAX Counter32
	    MAX-ACCESS read-only
	    STATUS current
	    DESCRIPTION
		"This object represents the total number of IAPP packets dropped
		due to erroneous information within the packet since system
		startup."
	    ::= { orinocoIAPP 15 }

	oriIAPPRoamingClients    OBJECT-TYPE 
	    SYNTAX Counter32
	    MAX-ACCESS read-only
	    STATUS current
	    DESCRIPTION
		"This object represents the total number of client that have 
		roamed from one device to another.  This parameter is per device 
		and not a total counter of all the roaming clients for all devices 
		on the network."
	    ::= { orinocoIAPP 16 }

	oriIAPPTerminatePPPSessionPDUsSent    OBJECT-TYPE
	    SYNTAX Counter32
	    MAX-ACCESS read-only
	    STATUS current
	    DESCRIPTION
		"This object represents a count of the terminate PPP Session PDUs
			sent."
	    ::= { orinocoIAPP 17 }

	oriIAPPTerminatePPPSessionPDUsReceived    OBJECT-TYPE
	    SYNTAX Counter32
	    MAX-ACCESS read-only
	    STATUS current
	    DESCRIPTION	
		"This object represents a count of the terminate PPP Session PDUs
			received."
	    ::= { orinocoIAPP 18 }

	oriIAPPTerminatePPPSessionACKsSent    OBJECT-TYPE
	    SYNTAX Counter32
	    MAX-ACCESS read-only
	    STATUS current
	    DESCRIPTION
			"This object represents the number of terminate PPP Session 
			acknowledgement PDUs sent."
	    ::= { orinocoIAPP 19 }

	oriIAPPTerminatePPPSessionACKsReceived    OBJECT-TYPE
	    SYNTAX Counter32
	    MAX-ACCESS read-only	
	    STATUS current
	    DESCRIPTION
			"This object represents the number of terminate PPP Session 
			acknowledgement PDUs received."
	    ::= { orinocoIAPP 20 }

    oriIAPPMACIPTable    OBJECT-TYPE
        SYNTAX SEQUENCE OF OriIAPPMACIPTableEntry
        MAX-ACCESS not-accessible
        STATUS current
        DESCRIPTION
       "This table contains a list of devices on the network that support
       IAPP and have the feature enabled."
        ::= { orinocoIAPP 21 }

    oriIAPPMACIPTableEntry    OBJECT-TYPE
        SYNTAX OriIAPPMACIPTableEntry
        MAX-ACCESS not-accessible
        STATUS current
        DESCRIPTION
       "This object represents an entry in the IAPP table, which 
       essentially is a device that supports IAPP and has the feature
       enabled."
        INDEX { oriIAPPMACIPTableIndex }
        ::= { oriIAPPMACIPTable 1 }

    OriIAPPMACIPTableEntry ::=
        SEQUENCE 
            {
                oriIAPPMACIPTableIndex        			Integer32,
                oriIAPPMACIPTableSystemName 		 	DisplayString,
                oriIAPPMACIPTableIPAddress 			 	IpAddress,
                oriIAPPMACIPTableBSSID				 	PhysAddress,
                oriIAPPMACIPTableESSID  				DisplayString
			}
                
    oriIAPPMACIPTableIndex    OBJECT-TYPE
        SYNTAX Integer32 
        MAX-ACCESS read-only
        STATUS current
        DESCRIPTION
        "This object is used as the index for the IAPP MAC-IP table."
        ::= { oriIAPPMACIPTableEntry 1 }

    oriIAPPMACIPTableSystemName    OBJECT-TYPE
	    SYNTAX DisplayString
	    MAX-ACCESS read-only
	    STATUS current
	    DESCRIPTION
	    "This object represents the System Name of the IAPP enabled 
		    device."
	    ::= { oriIAPPMACIPTableEntry 2 }

    oriIAPPMACIPTableIPAddress    OBJECT-TYPE
        SYNTAX IpAddress
        MAX-ACCESS read-only
        STATUS current
        DESCRIPTION
        "This object represents the IP Address of the IAPP enabled device."
        ::= { oriIAPPMACIPTableEntry 3 }

    oriIAPPMACIPTableBSSID OBJECT-TYPE
        SYNTAX PhysAddress
        MAX-ACCESS read-only
        STATUS current
        DESCRIPTION
        "This object represents the BSSID (MAC address of wireless 
        interface) of the IAPP enabled device."
        ::= { oriIAPPMACIPTableEntry 4 }

    oriIAPPMACIPTableESSID OBJECT-TYPE
        SYNTAX DisplayString
        MAX-ACCESS read-only
        STATUS current
        DESCRIPTION
        "This object represents the ESSID (network name) of the IAPP 
        enabled device."
        ::= { oriIAPPMACIPTableEntry 5 }

	oriIAPPSendAnnounceRequestOnStart OBJECT-TYPE
	    SYNTAX INTEGER
	        {
	            enable(1),
	            disable(2)
	        } 
	    MAX-ACCESS read-write
	    STATUS current
	    DESCRIPTION
        "This object is used to determine whether to send announce request
	    on start."
		DEFVAL { enable }
	    ::=  { orinocoIAPP 22 }
	    
--=============================================================================
-- The Link Test Group: orinocoLinkTest
--=============================================================================

	oriLinkTestTimeOut	OBJECT-TYPE
	    SYNTAX Integer32
	    MAX-ACCESS read-write
	    STATUS current
	    DESCRIPTION
		"The value of this object determines the time (in seconds) that a 
			link test will continue without any SNMP requests for a Link Test 
		Table entry.  When the time expires the Link Test Table is 
		cleared."
		DEFVAL { 900 }
	    ::= { orinocoLinkTest 1 }

	oriLinkTestInterval    OBJECT-TYPE
	    SYNTAX Integer32
	    MAX-ACCESS read-write
	    STATUS current
	    DESCRIPTION
		"This object indicates the interval (in milliseconds) between 
		sending link test frames to a station."
		DEFVAL { 200 }
	    ::= { orinocoLinkTest 3 }

	oriLinkTestExplore    OBJECT-TYPE
	    SYNTAX INTEGER
			{
			    tableTimedOut(1),
			    exploring(2),
			    exploreResultsAvailable(3)
			}
	    MAX-ACCESS read-write
	    STATUS current
	    DESCRIPTION
		"When this object is set to 2, the device will send out an explore 
		request on all 802.11 interfaces and from the results build the 
		Link Test table. This table is valid only while this object is 
		set to 3."
	    ::= { orinocoLinkTest 4 }

	oriLinkTestTable    OBJECT-TYPE
	    SYNTAX SEQUENCE OF OriLinkTestTableEntry
	    MAX-ACCESS not-accessible
	    STATUS current
	    DESCRIPTION
			"This table contains the information for the stations currently 
		associated with the access point."
	    ::= { orinocoLinkTest 5 }

	oriLinkTestTableEntry    OBJECT-TYPE
	    SYNTAX OriLinkTestTableEntry
    	MAX-ACCESS not-accessible
	    STATUS current
	    DESCRIPTION
		"This object represents the entry in the Remote Link Test table."
	    INDEX { oriLinkTestTableIndex }
	    ::= { oriLinkTestTable 1 }

	OriLinkTestTableEntry ::=
		SEQUENCE
		    {
			    oriLinkTestTableIndex 				Integer32,
			    oriLinkTestInProgress				INTEGER,
			    oriLinkTestStationName				DisplayString,
			    oriLinkTestMACAddress				PhysAddress,
			    oriLinkTestStationProfile			Integer32,
			    oriLinkTestOurCurSignalLevel		Integer32,
			    oriLinkTestOurCurNoiseLevel			Integer32,
			    oriLinkTestOurCurSNR				Integer32,
			    oriLinkTestOurMinSignalLevel		Integer32,
			    oriLinkTestOurMinNoiseLevel			Integer32,
			    oriLinkTestOurMinSNR				Integer32,
			    oriLinkTestOurMaxSignalLevel		Integer32,
			    oriLinkTestOurMaxNoiseLevel			Integer32,
			    oriLinkTestOurMaxSNR				Integer32,
			    oriLinkTestOurLowFrameCount			Integer32,
			    oriLinkTestOurStandardFrameCount	Integer32,
			    oriLinkTestOurMediumFrameCount		Integer32,
			    oriLinkTestOurHighFrameCount		Integer32,
			    oriLinkTestHisCurSignalLevel		Integer32,
			    oriLinkTestHisCurNoiseLevel			Integer32,
			    oriLinkTestHisCurSNR				Integer32,
			    oriLinkTestHisMinSignalLevel		Integer32,
			    oriLinkTestHisMinNoiseLevel			Integer32,
			    oriLinkTestHisMinSNR				Integer32,
			    oriLinkTestHisMaxSignalLevel		Integer32,
			    oriLinkTestHisMaxNoiseLevel			Integer32,
			    oriLinkTestHisMaxSNR				Integer32,
		    	oriLinkTestHisLowFrameCount			Integer32,
			    oriLinkTestHisStandardFrameCount	Integer32,
			    oriLinkTestHisMediumFrameCount		Integer32,
			    oriLinkTestHisHighFrameCount		Integer32,
			    oriLinkTestInterface                DisplayString,
			    oriLinkTestRadioType                DisplayString
			}

	oriLinkTestTableIndex    OBJECT-TYPE
	    SYNTAX Integer32
	    MAX-ACCESS read-only
	    STATUS current
	    DESCRIPTION
		"This object represents a unique value for each station.  The 
			value for each station must remain constant at least from one 
			explore to the next."
	    ::= { oriLinkTestTableEntry 1 }

	oriLinkTestInProgress    OBJECT-TYPE
	    SYNTAX INTEGER
		    {
				noLinkTestInProgress(1),
				linkTestIinProgress(2)
		    }
	    MAX-ACCESS read-write
	    STATUS current
	    DESCRIPTION
		"When this object is set to 2 the device will initiate a link test 
		sequence with this station."
	    ::= { oriLinkTestTableEntry 2 }

	oriLinkTestStationName    OBJECT-TYPE
	    SYNTAX DisplayString
	    MAX-ACCESS read-only
	    STATUS current
	    DESCRIPTION
		"This object identifies the name of the station whom which the 
			link test is being performed."
	    ::= { oriLinkTestTableEntry 3 }

	oriLinkTestMACAddress    OBJECT-TYPE
	    SYNTAX PhysAddress
	    MAX-ACCESS read-only
	    STATUS current
	    DESCRIPTION
		"This object represents the MAC address that will be mapped to 
			the IP Address of the station."
	    ::= { oriLinkTestTableEntry 4 }

	oriLinkTestStationProfile    OBJECT-TYPE
	    SYNTAX Integer32
	    MAX-ACCESS read-only
	    STATUS current
	    DESCRIPTION
		"This object represents the profile/capabilities for this station."
	    ::= { oriLinkTestTableEntry 5 }

	oriLinkTestOurCurSignalLevel    OBJECT-TYPE
	    SYNTAX Integer32
	    MAX-ACCESS read-only
	    STATUS current
	    DESCRIPTION
			"The current signal level (in dB) for the link test from this 
		station.  This object indicates the running average of the local 
			signal level using the algorithm (3/4*oldvalue + 1/4*newvalue)."	
	    ::= { oriLinkTestTableEntry 6 }

	oriLinkTestOurCurNoiseLevel    OBJECT-TYPE
	    SYNTAX Integer32
	    MAX-ACCESS read-only
	    STATUS current
	    DESCRIPTION
			"The current noise level (in dB) for the link test to this station. 
		This object indicates the running average of the local noise 
			level."
	    ::= { oriLinkTestTableEntry 7}

	oriLinkTestOurCurSNR    OBJECT-TYPE
	    SYNTAX Integer32
	    MAX-ACCESS read-only
	    STATUS current
	    DESCRIPTION
			"The current signal to noise ratio for the link test to this 
			station."
	    ::= { oriLinkTestTableEntry 8 }

	oriLinkTestOurMinSignalLevel    OBJECT-TYPE
	    SYNTAX Integer32
	    MAX-ACCESS read-only
	    STATUS current
	    DESCRIPTION
			"The minimum signal level during the link test to this station."
	    ::= { oriLinkTestTableEntry 9 }

	oriLinkTestOurMinNoiseLevel    OBJECT-TYPE
	    SYNTAX Integer32
	    MAX-ACCESS read-only
	    STATUS current
	    DESCRIPTION	
			"The minimum noise level during the link test to this station."
	    ::= { oriLinkTestTableEntry 10 }

	oriLinkTestOurMinSNR    OBJECT-TYPE
	    SYNTAX Integer32
	    MAX-ACCESS read-only
	    STATUS current
	    DESCRIPTION	
			"The minimum signal to noise ratio during the link test to this 
			station."
	    ::= { oriLinkTestTableEntry 11 }

	oriLinkTestOurMaxSignalLevel    OBJECT-TYPE
	    SYNTAX Integer32
	    MAX-ACCESS read-only
	    STATUS current
	    DESCRIPTION
			"The maximum signal level during the link test to this station."
	    ::= { oriLinkTestTableEntry 12 }

	oriLinkTestOurMaxNoiseLevel    OBJECT-TYPE
	    SYNTAX Integer32
	    MAX-ACCESS read-only
	    STATUS current
	    DESCRIPTION
			"The maximum noise level during the link test to this station."
	    ::= { oriLinkTestTableEntry 13 }

	oriLinkTestOurMaxSNR    OBJECT-TYPE
	    SYNTAX Integer32
	    MAX-ACCESS read-only
	    STATUS current
	    DESCRIPTION
			"The maximum signal to noise ratio during the link test to this 
			station."
	    ::= { oriLinkTestTableEntry 14 }

	oriLinkTestOurLowFrameCount    OBJECT-TYPE
	    SYNTAX Integer32
	    MAX-ACCESS read-only
	    STATUS current
	    DESCRIPTION
			"The total number of frames sent at 1 Mbit/s speed during the link 
			test to this station."
	    ::= { oriLinkTestTableEntry 15 }

	oriLinkTestOurStandardFrameCount    OBJECT-TYPE
	    SYNTAX Integer32
	    MAX-ACCESS read-only
	    STATUS current
	    DESCRIPTION
			"The total number of frames sent at 2 Mbit/s speed during the link 
			test to this station."
	    ::= { oriLinkTestTableEntry 16 }

	oriLinkTestOurMediumFrameCount    OBJECT-TYPE
	    SYNTAX Integer32
	    MAX-ACCESS read-only
	    STATUS current
	    DESCRIPTION
			"The total number of frames sent at 5.5 Mbit/s (for Turbo-8, it is 
			5 Mbit/s) speed during the link test to this station."
	    ::= { oriLinkTestTableEntry 17 }

	oriLinkTestOurHighFrameCount    OBJECT-TYPE
	    SYNTAX Integer32
	    MAX-ACCESS read-only
	    STATUS current
	    DESCRIPTION
			"The total number of frames sent at 11 Mbit/s (for Turbo-8, it is 
			8 Mbit/s) speed during the link test to this station."
	    ::= { oriLinkTestTableEntry 18 }

	oriLinkTestHisCurSignalLevel    OBJECT-TYPE
	    SYNTAX Integer32
	    MAX-ACCESS read-only
	    STATUS current
	    DESCRIPTION
			"The current signal level for the link test to the remote station 
			or access point."
	    ::= { oriLinkTestTableEntry 19 }

	oriLinkTestHisCurNoiseLevel    OBJECT-TYPE
	    SYNTAX Integer32
	    MAX-ACCESS read-only
	    STATUS current
	    DESCRIPTION
		"The current noise level for the link test to the remote station
		or access point device."
	    ::= { oriLinkTestTableEntry 20 }

	oriLinkTestHisCurSNR    OBJECT-TYPE
	    SYNTAX Integer32
	    MAX-ACCESS read-only
	    STATUS current
	    DESCRIPTION
			"The current signal to noise ratio for the link test to the remote 
		station or access point device."
	    ::= { oriLinkTestTableEntry 21 }	

	oriLinkTestHisMinSignalLevel    OBJECT-TYPE
	    SYNTAX Integer32
	    MAX-ACCESS read-only
	    STATUS current
	    DESCRIPTION
		"The minimum signal level during the link test to the remote station
		or access point device."
	    ::= { oriLinkTestTableEntry 22 }

	oriLinkTestHisMinNoiseLevel    OBJECT-TYPE
	    SYNTAX Integer32
	    MAX-ACCESS read-only
	    STATUS current
	    DESCRIPTION
			"The minimum noise level during the link test to the remote station 
		or access point device."
	    ::= { oriLinkTestTableEntry 23 }

	oriLinkTestHisMinSNR    OBJECT-TYPE
	    SYNTAX Integer32
	    MAX-ACCESS read-only
	    STATUS current
	    DESCRIPTION
			"The minimum signal to noise ratio during the link test to the 
		remote station or access point device."
	    ::= { oriLinkTestTableEntry 24 }	

	oriLinkTestHisMaxSignalLevel    OBJECT-TYPE
	    SYNTAX Integer32
	    MAX-ACCESS read-only
	    STATUS current
	    DESCRIPTION
			"The maximum signal level during the link test to the remote 
		station or access point device."
	    ::= { oriLinkTestTableEntry 25 }

	oriLinkTestHisMaxNoiseLevel    OBJECT-TYPE
	    SYNTAX Integer32
	    MAX-ACCESS read-only
	    STATUS current
	    DESCRIPTION
			"The maximum noise level during the link test to the remote station 
		or access point device."
	    ::= { oriLinkTestTableEntry 26 }

	oriLinkTestHisMaxSNR    OBJECT-TYPE
    	SYNTAX Integer32
	    MAX-ACCESS read-only
	    STATUS current
	    DESCRIPTION
			"The maximum signal to noise ratio during the link test to the 
		remote station or access point device."
	    ::= { oriLinkTestTableEntry 27 }

	oriLinkTestHisLowFrameCount    OBJECT-TYPE
	    SYNTAX Integer32
	    MAX-ACCESS read-only
	    STATUS current
	    DESCRIPTION
			"The total number of frames sent at 1 Mbit/s speed during the link 
		test to the remote station or access point device."
	    ::= { oriLinkTestTableEntry 28 }

	oriLinkTestHisStandardFrameCount    OBJECT-TYPE
	    SYNTAX Integer32
	    MAX-ACCESS read-only
	    STATUS current
	    DESCRIPTION
			"The total number of frames sent at 2 Mbit/s speed during the link 
		test to the remote station or access point device."
	    ::= { oriLinkTestTableEntry 29 }

	oriLinkTestHisMediumFrameCount    OBJECT-TYPE
	    SYNTAX Integer32
	    MAX-ACCESS read-only
	    STATUS current
	    DESCRIPTION
			"The total number of frames sent at 5.5 Mbit/s (for Turbo-8, it is 
			5 Mbit/s) speed during the link test to the remote station or 
		access point device."
	    ::= { oriLinkTestTableEntry 30 }

	oriLinkTestHisHighFrameCount    OBJECT-TYPE
	    SYNTAX Integer32
	    MAX-ACCESS read-only
	    STATUS current
	    DESCRIPTION
			"The total number of frames sent at 11 Mbit/s (for Turbo-8, it is 
			5 Mbit/s) speed during the link test to the remote station or 
		access point device."
	    ::= { oriLinkTestTableEntry 31 }

	oriLinkTestInterface   OBJECT-TYPE
	    SYNTAX DisplayString
	    MAX-ACCESS read-only
	    STATUS current
	    DESCRIPTION
        "This object represents the wireless interface number to which the 
        Client has sent the Explore Response Message."
	    ::= { oriLinkTestTableEntry 32 }

	oriLinkTestRadioType    OBJECT-TYPE
	    SYNTAX DisplayString
	    MAX-ACCESS read-only
	    STATUS current
	    DESCRIPTION
		"The Wireless Standard eg. IEEE 802.11 or IEEE 802.11b being used
		by the remote station."
	    ::= { oriLinkTestTableEntry 33 }

--=============================================================================
-- The Link Integrity Group: orinocoLinkInt
--=============================================================================

	oriLinkIntStatus    OBJECT-TYPE
	    SYNTAX INTEGER
			{
			    enable(1),
			    disable(2)
			}
	    MAX-ACCESS read-write
	    STATUS current
	    DESCRIPTION
		"This object is used to enable or disable the link integrity 
			functionality."
	    ::= { orinocoLinkInt 1 }

	oriLinkIntPollInterval    OBJECT-TYPE	
	    SYNTAX Integer32
	    MAX-ACCESS read-write
	    STATUS current
	    DESCRIPTION
		"This object is used to set the poll interval (in milliseconds) 
			for the link integrity check.  The valid values for this objects
			are multiples of 500 milliseconds, a value of zero is not 
			supported."
		DEFVAL { 500 }
	    ::= { orinocoLinkInt 2 }

	oriLinkIntPollRetransmissions    OBJECT-TYPE
	    SYNTAX Integer32
	    MAX-ACCESS read-write
	    STATUS current
	    DESCRIPTION
		"This object is used to set the number of retransmissions for 
			the link integrity check."
	    ::= { orinocoLinkInt 3 }

	oriLinkIntTable    OBJECT-TYPE
	    SYNTAX SEQUENCE OF OriLinkIntTableEntry
	    MAX-ACCESS not-accessible
	    STATUS current
	    DESCRIPTION
			"This table contains the target IP addresses in order to perform 
			the link integrity check.  This table is limited to 5 entries."
	    ::= { orinocoLinkInt 4 }

	oriLinkIntTableEntry    OBJECT-TYPE
	    SYNTAX OriLinkIntTableEntry
	    MAX-ACCESS not-accessible
	    STATUS current
	    DESCRIPTION
		"This object identifies the entry in the link integrity target 
		table."
	    INDEX { oriLinkIntTableIndex }
    	::= { oriLinkIntTable 1 }

	OriLinkIntTableEntry ::=
		SEQUENCE
		    {
		    	oriLinkIntTableIndex			Integer32,
			    oriLinkIntTableTargetIPAddress	IpAddress,
			    oriLinkIntTableComment			DisplayString,
			    oriLinkIntTableEntryStatus			INTEGER
		    }

	oriLinkIntTableIndex    OBJECT-TYPE
	    SYNTAX Integer32
	    MAX-ACCESS read-only
	    STATUS current
	    DESCRIPTION
		"This object is used as an index for the link integrity target 
			table."
	    ::= { oriLinkIntTableEntry 1 }

	oriLinkIntTableTargetIPAddress    OBJECT-TYPE
	    SYNTAX IpAddress
	    MAX-ACCESS read-write
	    STATUS current
	    DESCRIPTION
		"This object represents the IP address of the target machine for
			the link integrity check."
    	::= { oriLinkIntTableEntry 2 }

	oriLinkIntTableComment    OBJECT-TYPE
	    SYNTAX DisplayString
	    MAX-ACCESS read-write
	    STATUS current
	    DESCRIPTION
		"This object is used as an optional comment associated to the 
			link integrity table entry."
	    ::= { oriLinkIntTableEntry 3 }

	oriLinkIntTableEntryStatus    OBJECT-TYPE
	    SYNTAX INTEGER
			{
			    enable(1),
			    disable(2),
		    delete(3),
		    create(4)
			}
	    MAX-ACCESS read-write
	    STATUS current
	    DESCRIPTION
		"This object is used to enable, disable, delete, or create an 
			entry in the link integrity table."
    	::= { oriLinkIntTableEntry 4 }

--=============================================================================
-- The ECP Group: orinocoECP
--=============================================================================

	oriECPRetransmissionCount    OBJECT-TYPE
	    SYNTAX Integer32
	    MAX-ACCESS read-write
	    STATUS current
	    DESCRIPTION
			"This object represents the number of retransmissions when 
			responses are not received within the timeout period."
	    ::= { orinocoECP 1 }

	oriECPResponseRetransmissions    OBJECT-TYPE
	    SYNTAX Integer32
	    MAX-ACCESS read-write
	    STATUS current
	    DESCRIPTION
		"This object represents the number of times the transmitted 
			response can be retransmitted."
	    ::= { orinocoECP 2 }

	oriECPResponseRetransmissionTimeout    OBJECT-TYPE
	    SYNTAX Integer32
	    MAX-ACCESS read-write
	    STATUS current
	    DESCRIPTION
		"This object represents the timeout interval for a response to be
			received."
	    ::= { orinocoECP 3 }

--=============================================================================
-- The PPP Group: orinocoPPP
--=============================================================================

	oriPPPIPAddressAssignmentType    OBJECT-TYPE 
	    SYNTAX INTEGER
			{
			    local(1),
			    dhcpRelay(2),
			    radius(3)
			}
	    MAX-ACCESS read-write
	    STATUS current
	    DESCRIPTION
		"This object identifies whether the IP addresses assigned to the 
		AS Clients are obtained from the local address pool, from DHCP 
		Server via DHCP Relay, or from the RADIUS server."
		DEFVAL { local }
	    ::= { orinocoPPP 1 }

	oriPPPMACtoIPMappingCount    OBJECT-TYPE
	    SYNTAX Integer32
	    MAX-ACCESS read-only
	    STATUS current
	    DESCRIPTION
		"This object represents the number of MAC address to IP address 
			static mappings are present in the MAC to IP Mapping Table."
	    ::= { orinocoPPP 2 }

	oriPPPMACtoIPMappingTable    OBJECT-TYPE
	    SYNTAX SEQUENCE OF OriPPPMACtoIPMappingTableEntry
	    MAX-ACCESS not-accessible
	    STATUS current
	    DESCRIPTION
			"This table contains the static mapping of MAC addresses to IP 
			addresses."	
	    ::= { orinocoPPP 3 }
        	
	oriPPPMACtoIPMappingTableEntry    OBJECT-TYPE
	    SYNTAX OriPPPMACtoIPMappingTableEntry
	    MAX-ACCESS not-accessible
	    STATUS current
	    DESCRIPTION
			"This object represents the entry of the MAC to IP Address mapping 
		table."
	    INDEX { oriPPPMACtoIPTableIndex }
	    ::= { oriPPPMACtoIPMappingTable 1 }

	OriPPPMACtoIPMappingTableEntry  ::=
	    SEQUENCE
			{
			    oriPPPMACtoIPTableIndex			Integer32,
			    oriPPPMACtoIPTableMACAddress	PhysAddress,
			    oriPPPMACtoIPTableIPAddress		IpAddress,
			    oriPPPMACtoIPTableComment		DisplayString,
			    oriPPPMACtoIPTableEntryStatus	INTEGER
			}

	oriPPPMACtoIPTableIndex    OBJECT-TYPE
	    SYNTAX Integer32
	    MAX-ACCESS read-only
	    STATUS current
	    DESCRIPTION
		"This object represents the index to the IP to MAC address 
		mapping table."
	    ::= { oriPPPMACtoIPMappingTableEntry 1 }
	
	oriPPPMACtoIPTableMACAddress    OBJECT-TYPE
	    SYNTAX PhysAddress
	    MAX-ACCESS read-write
	    STATUS current
	    DESCRIPTION
		"This object represents the MAC address that will be mapped to 
			the IP Address."
	    ::= { oriPPPMACtoIPMappingTableEntry 2 }

	oriPPPMACtoIPTableIPAddress    OBJECT-TYPE
	    SYNTAX IpAddress
	    MAX-ACCESS read-write
    	STATUS current
	    DESCRIPTION
			"This objects identifies IP address corresponding to the MAC 
			address."
	    ::= { oriPPPMACtoIPMappingTableEntry 3 }

	oriPPPMACtoIPTableComment    OBJECT-TYPE
	    SYNTAX DisplayString
	    MAX-ACCESS read-write
	    STATUS current
	    DESCRIPTION
		"The object represents the comment for this entry."
	    ::= { oriPPPMACtoIPMappingTableEntry 4 }

	oriPPPMACtoIPTableEntryStatus	OBJECT-TYPE
	    SYNTAX INTEGER
			{
			    enable(1),
			    disable(2),
		    delete(3),
		    create(4)
			}
	    MAX-ACCESS read-write
	    STATUS current
	    DESCRIPTION
		"This object is used to enable, disable, delete, create the 
			table entry."
	    ::= { oriPPPMACtoIPMappingTableEntry 5 }

	oriPPPKeepAliveInterval    OBJECT-TYPE
	    SYNTAX Integer32
	    MAX-ACCESS read-write									 
	    STATUS current
	    DESCRIPTION
		"This object represents the keep alive interval to be notified to
			the PPP layer."
	    ::= { orinocoPPP 4 }

	oriPPPNumKeepAliveTimeouts  OBJECT-TYPE
	    SYNTAX Integer32
	    MAX-ACCESS read-write
	    STATUS current
	    DESCRIPTION
			"This object represents the maximum number of timeouts before the 
			PPP session is brought down."
	    ::= { orinocoPPP 5 }

	oriPPPSessionIdleTimeout OBJECT-TYPE
        SYNTAX Integer32 (0..36000)
	    MAX-ACCESS read-only
	    STATUS current
	    DESCRIPTION
		"This object indicates the idle timeout (in seconds) in order to 
		disconnect an idle PPP client."
	    ::= { orinocoPPP 6 }

	oriPPPPrimaryDNSIPAddress  OBJECT-TYPE
	    SYNTAX IpAddress
	    MAX-ACCESS read-write
	    STATUS current
	    DESCRIPTION
		"This object represents the IP address of the primary DNS server 
			in the network."
	    ::= { orinocoPPP 7 }

	oriPPPSecondaryDNSIPAddress  OBJECT-TYPE
	    SYNTAX IpAddress
	    MAX-ACCESS read-write
	    STATUS current
	    DESCRIPTION
		"This object represents the IP address of the secondary DNS server 
		in the network."
	    ::= { orinocoPPP 8 }

	oriPPPMaxNumberOfUsers  OBJECT-TYPE
	    SYNTAX Integer32
	    MAX-ACCESS read-write
	    STATUS current
	    DESCRIPTION
		"This object represents the number of user allowed to connect to 
			the device."
	    ::= { orinocoPPP 9 }

	oriPPPIPPoolTableEntries    OBJECT-TYPE
	    SYNTAX Integer32
	    MAX-ACCESS read-only
	    STATUS current
	    DESCRIPTION
		"This object represents the number of entries in the PPP IP 
			Address Pool Table."
	    ::= { orinocoPPP 10 }

	oriPPPCHAPStatus    OBJECT-TYPE
	    SYNTAX INTEGER
			{
			    enable(1),
			    disable(2)
			}
	    MAX-ACCESS read-write
	    STATUS current
	    DESCRIPTION
        "This object indicates the status of CHAP in the device."
	    ::= { orinocoPPP 11 }

	oriPPPCHAPPriority    OBJECT-TYPE
	    SYNTAX Integer32
	    MAX-ACCESS read-write
	    STATUS current
	    DESCRIPTION
		"This object indicates the priority of CHAP among all 
		authentictaion protocols enabled."
	    ::= { orinocoPPP 12 }

	oriPPPPAPStatus    OBJECT-TYPE
	    SYNTAX INTEGER
			{
			    enable(1),
			    disable(2)
			}
	    MAX-ACCESS read-write
	    STATUS current
	    DESCRIPTION
        "This object indicates the status of PAP in the device."
	    ::= { orinocoPPP 13 }

	oriPPPPAPPriority    OBJECT-TYPE
	    SYNTAX Integer32
	    MAX-ACCESS read-write
	    STATUS current
	    DESCRIPTION
		"This object indicates the priority of PAP among all 
		authentictaion protocols enabled on the device."
	    ::= { orinocoPPP 14 }

	oriPPPPrimaryWINSIPAddress  OBJECT-TYPE
	    SYNTAX IpAddress
	    MAX-ACCESS read-write
	    STATUS current
	    DESCRIPTION
		"This object represents the IP address of the Primary WINS/NBNS 
		server in the network."
	    ::= { orinocoPPP 15 }
	
	oriPPPSecondaryWINSIPAddress  OBJECT-TYPE
	    SYNTAX IpAddress
	    MAX-ACCESS read-write
	    STATUS current
    	DESCRIPTION
		"This object represents the IP address of the Secondary WINS/NBNS 
		server in the network."
	    ::= { orinocoPPP 16 }

	oriPPPIPPoolTable  OBJECT-TYPE
	    SYNTAX SEQUENCE OF OriPPPIPPoolTableEntry
	    MAX-ACCESS not-accessible
	    STATUS current
	    DESCRIPTION
		"This table is used for configuring IP address pools to be assinged
		to PPP clients (AS Clients) by the device."
	    ::= { orinocoPPP 17 }
        
	oriPPPIPPoolTableEntry  OBJECT-TYPE
		SYNTAX OriPPPIPPoolTableEntry
	    MAX-ACCESS not-accessible
	    STATUS current
		DESCRIPTION
		"This object represents an in entry the oriPPPIPPoolTable."
	    INDEX { oriPPPIPPoolTableIndex }
	    ::= { oriPPPIPPoolTable 1 }

	OriPPPIPPoolTableEntry  ::=
	    SEQUENCE
			{
			    oriPPPIPPoolTableIndex 			Integer32,
			    oriPPPIPPoolTableStartIPAddress	IpAddress,
			    oriPPPIPPoolTableEndIPAddress	IpAddress,
			    oriPPPIPPoolTableWidth 			Integer32,
			    oriPPPIPPoolTableComment		DisplayString,
			    oriPPPIPPoolTableEntryStatus 	INTEGER
			}

	oriPPPIPPoolTableIndex    OBJECT-TYPE
	    SYNTAX Integer32
	    MAX-ACCESS read-only
	    STATUS current
	    DESCRIPTION
		"This object is used as an index for the PPP IP Pool table."
	    ::= { oriPPPIPPoolTableEntry 1 }

	oriPPPIPPoolTableStartIPAddress    OBJECT-TYPE
	    SYNTAX IpAddress
	    MAX-ACCESS read-write
	    STATUS current
	    DESCRIPTION
	    "This object represents the start IP address for the IP Pool."
	    ::= { oriPPPIPPoolTableEntry 2 }
	
	oriPPPIPPoolTableEndIPAddress    OBJECT-TYPE
		SYNTAX IpAddress
	    MAX-ACCESS read-write
	    STATUS current
	    DESCRIPTION
	    "This object represents the end IP address for the IP Pool."
	    ::= { oriPPPIPPoolTableEntry 3 }

	oriPPPIPPoolTableWidth    OBJECT-TYPE
	    SYNTAX Integer32
	    MAX-ACCESS read-write
	    STATUS current
	    DESCRIPTION
	    "This object represents the width of the IP Pool."
	    ::= { oriPPPIPPoolTableEntry 4 }

	oriPPPIPPoolTableComment    OBJECT-TYPE	
	    SYNTAX DisplayString
	    MAX-ACCESS read-write
	    STATUS current
	    DESCRIPTION
		"The object represents an optional comment for the IP Pool."
	    ::= { oriPPPIPPoolTableEntry 5 }

	oriPPPIPPoolTableEntryStatus    OBJECT-TYPE
	    SYNTAX INTEGER
			{
			    enable(1),
			    disable(2),
		    delete(3),
		    create(4)
			}
	    MAX-ACCESS read-write
	    STATUS current
	    DESCRIPTION
		"This object represents the status of the entry, whether to be 
		used or not used.  Setting this object to delete will remove 
		this entry."
	    ::= { oriPPPIPPoolTableEntry 6 }

--=============================================================================
-- The DHCP Group: orinocoDHCP
--=============================================================================

--=============================================================================
-- The DHCP Server Subgroup: orinocoDHCPServer
--=============================================================================

	oriDHCPServerStatus	OBJECT-TYPE
	    SYNTAX INTEGER
			{
			    enable(1),
			    disable(2)
			}
	    MAX-ACCESS read-write
	    STATUS current
	    DESCRIPTION
		"This object indicates if the DHCP server is enabled or disabled
		in the device."
	    ::= { orinocoDHCPServer 1 }

	oriDHCPServerIPPoolTable    OBJECT-TYPE
	    SYNTAX SEQUENCE OF OriDHCPServerIPPoolTableEntry
	    MAX-ACCESS not-accessible
	    STATUS current
	    DESCRIPTION
		"This table contains the pools of IP Addresses that the DHCP server 
			will assign to the DHCP clients.  This table is limited to
			20."
	    ::= { orinocoDHCPServer 2 }
        
	oriDHCPServerIPPoolTableEntry  OBJECT-TYPE
		SYNTAX OriDHCPServerIPPoolTableEntry
	    MAX-ACCESS not-accessible
		STATUS current
		DESCRIPTION
		"This object represents entries in the DHCP IP Address Pool Table."
	    INDEX { oriDHCPServerIPPoolTableIndex }
	    ::= { oriDHCPServerIPPoolTable 1 }

	OriDHCPServerIPPoolTableEntry  ::=
   		SEQUENCE
			{
			    oriDHCPServerIPPoolTableIndex 					Integer32,
			    oriDHCPServerIPPoolTableStartIPAddress			IpAddress,
			    oriDHCPServerIPPoolTableEndIPAddress			IpAddress,
			    oriDHCPServerIPPoolTableWidth 					Integer32,
			    oriDHCPServerIPPoolTableDefaultLeaseTime        Integer32,
			    oriDHCPServerIPPoolTableMaximumLeaseTime		Integer32,
			    oriDHCPServerIPPoolTableComment					DisplayString,
			    oriDHCPServerIPPoolTableEntryStatus 			INTEGER
			}
			
	oriDHCPServerIPPoolTableIndex    OBJECT-TYPE
	    SYNTAX Integer32
	    MAX-ACCESS read-only
	    STATUS current
	    DESCRIPTION
		"This object is used as the index for the IP Address Pool table."
	    ::= { oriDHCPServerIPPoolTableEntry 1 }

	oriDHCPServerIPPoolTableStartIPAddress    OBJECT-TYPE
	    SYNTAX IpAddress
	    MAX-ACCESS read-write
	    STATUS current
	    DESCRIPTION
        "This object represents the start IP address for this DHCP IP 
	        Address IP Pool Table entry."
	    ::= { oriDHCPServerIPPoolTableEntry 2 }
	
	oriDHCPServerIPPoolTableEndIPAddress    OBJECT-TYPE
	    SYNTAX IpAddress
	    MAX-ACCESS read-write
	    STATUS current
	    DESCRIPTION
	    "This object represents the end IP address for this DHCP IP 
    	    Address IP Pool Table entry."
	    ::= { oriDHCPServerIPPoolTableEntry 3 }

	oriDHCPServerIPPoolTableWidth    OBJECT-TYPE
	    SYNTAX Integer32
	    MAX-ACCESS read-write
	    STATUS current
	    DESCRIPTION
        "This object represents the width or number of IP Address in the 
	        DHCP IP Address Pool table entry."
	    ::= { oriDHCPServerIPPoolTableEntry 4 }

	oriDHCPServerIPPoolTableDefaultLeaseTime    OBJECT-TYPE
	    SYNTAX Integer32
	    MAX-ACCESS read-write
	    STATUS current
	    DESCRIPTION
		"This object represents the default lease time, in seconds, for 
			the IP address assigned by the DHCP server to the DHCP client."
	    ::= { oriDHCPServerIPPoolTableEntry 5 }

	oriDHCPServerIPPoolTableMaximumLeaseTime    OBJECT-TYPE
	    SYNTAX Integer32
	    MAX-ACCESS read-write
	    STATUS current
	    DESCRIPTION
		"This object represents the maximum lease time in seconds for 
			the IP address assigned by the DHCP server to the DHCP client."
	    ::= { oriDHCPServerIPPoolTableEntry 6 }

	oriDHCPServerIPPoolTableComment    OBJECT-TYPE
	    SYNTAX DisplayString
	    MAX-ACCESS read-write
	    STATUS current
	    DESCRIPTION
		"This object represents an optional comment for this table entry."
	    ::= { oriDHCPServerIPPoolTableEntry 7 }

	oriDHCPServerIPPoolTableEntryStatus    OBJECT-TYPE
	    SYNTAX INTEGER
			{
			    enable(1),
			    disable(2),
		    delete(3),
		    create(4)
			}
	    MAX-ACCESS read-write
	    STATUS current
	    DESCRIPTION
		"The object indicates the status of the DHCP IP Address Pool 
			Table entry."
	    ::= { oriDHCPServerIPPoolTableEntry 8 }

	oriDHCPServerDefaultGatewayIPAddress    OBJECT-TYPE
	    SYNTAX IpAddress
	    MAX-ACCESS read-write
	    STATUS current
	    DESCRIPTION
		"This object represents the IP Address of the gateway or router 
			that the DHCP Server will assign to the DHCP client."
	    ::= { orinocoDHCPServer 3 }
	    
	oriDHCPServerSubnetMask    OBJECT-TYPE
	    SYNTAX IpAddress
	    MAX-ACCESS read-only
	    STATUS current
	    DESCRIPTION
        "This object represents the subnet mask to be provided to 
        DHCP clients.  This object is the same as the subnet mask for
        the device."
	    ::= { orinocoDHCPServer 4 }

	oriDHCPServerNumIPPoolTableEntries    OBJECT-TYPE
	    SYNTAX Integer32
	    MAX-ACCESS read-only
	    STATUS current
	    DESCRIPTION
		"This object represents the number of entries in the DHCP IP 
			Address Pool Table."
	    ::= { orinocoDHCPServer 5 }

	oriDHCPServerPrimaryDNSIPAddress    OBJECT-TYPE
	    SYNTAX IpAddress
	    MAX-ACCESS read-write
	    STATUS current
	    DESCRIPTION
		"This object represents the primary DNS Server IP Address to be
			assinged to a DHCP Client."
	    ::= { orinocoDHCPServer 6 }

	oriDHCPServerSecondaryDNSIPAddress    OBJECT-TYPE
	    SYNTAX IpAddress
	    MAX-ACCESS read-write
	    STATUS current
	    DESCRIPTION
		"This object represents the secondary DNS Server IP Address to be
			assinged to a DHCP Client."
	    ::= { orinocoDHCPServer 7 }
	    
--=============================================================================
-- The DHCP Client Subgroup: orinocoDHCPClient
--=============================================================================

    oriDHCPClientID    OBJECT-TYPE
	    SYNTAX DisplayString
	    MAX-ACCESS read-write
	    STATUS current
	    DESCRIPTION
        "This object represents the DHCP client ID."
        ::= { orinocoDHCPClient 1 }

oriDHCPClientInterfaceBitmask OBJECT-TYPE
    SYNTAX InterfaceBitmask
    MAX-ACCESS read-write
    STATUS current
    DESCRIPTION
        "This object indicates to which interface a DHCP Request 
        in sent when the unit is in routing mode"
    ::= { orinocoDHCPClient 2 }

--=============================================================================
-- The DHCP Relay Agent Subgroup: orinocoDHCPRelay
--=============================================================================

	oriDHCPRelayStatus    OBJECT-TYPE
	    SYNTAX INTEGER
		   {
		        enable(1),
		        disable(2)
		   } 
	    MAX-ACCESS read-write
	    STATUS current
	    DESCRIPTION
			"This object is used to enable and disable the DHCP Relay 
			functionality."
		DEFVAL { disable }
	    ::= { orinocoDHCPRelay 1 } 
			
	oriDHCPRelayDHCPServerTable    OBJECT-TYPE
	    SYNTAX  SEQUENCE OF OriDHCPRelayDHCPServerTableEntry
   	    MAX-ACCESS not-accessible
    	STATUS current
    	DESCRIPTION
		"This table contains a list of DHCP servers to which the
		DHCP Agent will communicate with."
    	::= { orinocoDHCPRelay 2 }

	oriDHCPRelayDHCPServerTableEntry    OBJECT-TYPE
	    SYNTAX  OriDHCPRelayDHCPServerTableEntry
    	MAX-ACCESS not-accessible
    	STATUS current
    	DESCRIPTION
	    "This object represents and entry in the DHCP Server table."
	    INDEX {oriDHCPRelayDHCPServerTableIndex }
    	::= { oriDHCPRelayDHCPServerTable 1 }

	OriDHCPRelayDHCPServerTableEntry ::=
    	SEQUENCE
    		{
		    	oriDHCPRelayDHCPServerTableIndex       		Integer32,
		    	oriDHCPRelayDHCPServerTableIpAddress		IpAddress,
		    	oriDHCPRelayDHCPServerTableComment			DisplayString,
    		    oriDHCPRelayDHCPServerTableEntryStatus  	INTEGER
    		}                                
                 	
	oriDHCPRelayDHCPServerTableIndex 	OBJECT-TYPE
	    SYNTAX Integer32 (1..10)
	    MAX-ACCESS read-only
	    STATUS current
	    DESCRIPTION
		"This object is used as the index to this table.  This table is 
		limited to 10 entries."  
	    ::= { oriDHCPRelayDHCPServerTableEntry 1 }  

	oriDHCPRelayDHCPServerTableIpAddress	OBJECT-TYPE
	    SYNTAX IpAddress
	    MAX-ACCESS read-write
	    STATUS current
	    DESCRIPTION
		"This object represents the IP address of the DHCP server
			 that shall receive DHCP requests from the device."  
	    ::= { oriDHCPRelayDHCPServerTableEntry 2 }

	oriDHCPRelayDHCPServerTableComment    OBJECT-TYPE
	    SYNTAX DisplayString
	    MAX-ACCESS read-write
	    STATUS current
	    DESCRIPTION
		"This object represents an optional comment in order to provide
			additional information or a unique identifier for the DHCP server
			(for example the server system name)."  
	    ::= { oriDHCPRelayDHCPServerTableEntry 3 }

  	oriDHCPRelayDHCPServerTableEntryStatus    OBJECT-TYPE
	    SYNTAX INTEGER
	        {
		        enable(1),
		        disable(2),
	        delete(3),
	        create(4)
	        }
    MAX-ACCESS read-write
	    STATUS current
	    DESCRIPTION
		"This object is used to enable, disable, delete or create an 
		entry in the DHCP Server Table."  
	    DEFVAL {disable}
	    ::= { oriDHCPRelayDHCPServerTableEntry 4 } 

--=============================================================================
-- The HTTP Server Group: orinocoHTTP
--=============================================================================

oriHTTPInterfaceBitmask OBJECT-TYPE
    SYNTAX InterfaceBitmask
	    MAX-ACCESS read-write
	    STATUS current
	    DESCRIPTION
			"This object is used to control interface access for HTTP based 
			management."
	    ::= { orinocoHTTP 1 }

	oriHTTPPassword    OBJECT-TYPE
	    SYNTAX DisplayString
	    MAX-ACCESS read-write
	    STATUS current
	    DESCRIPTION
		"This object represents the login password in order to manage 
			the device via a standard web browser.  This object should be
			treated as write-only and returned as asterisks."
	    ::= { orinocoHTTP 2 }

	oriHTTPPort    OBJECT-TYPE
	    SYNTAX Integer32
	    MAX-ACCESS read-write
	    STATUS current
	    DESCRIPTION
		"This object represents the TCP/IP port by which the HTTP server 
			will be accessible."
	    ::= { orinocoHTTP 3 }

oriHTTPWebSitenameTable OBJECT-TYPE
    SYNTAX SEQUENCE OF OriHTTPWebSitenameTableEntry
    MAX-ACCESS not-accessible
    STATUS current
    DESCRIPTION
     	"This table is used to store the different website interfaces 
     	stored in the device.  Different interfaces can be used to 
     	support multiple languages, user levels (novice, expert), etc."
    ::= { orinocoHTTP 4 }

oriHTTPWebSitenameTableEntry OBJECT-TYPE
    SYNTAX OriHTTPWebSitenameTableEntry
    MAX-ACCESS not-accessible
    STATUS current
    DESCRIPTION
        "This object represents an entry is the HTTP website name table."
    INDEX { oriHTTPWebSitenameTableIndex  }
    ::= { oriHTTPWebSitenameTable 1 }

OriHTTPWebSitenameTableEntry  ::=
    SEQUENCE
        {
	   	        oriHTTPWebSitenameTableIndex  		Integer32,
            oriHTTPWebSiteFilename 				DisplayString,
            oriHTTPWebSiteLanguage				DisplayString,
            oriHTTPWebSiteDescription			DisplayString,
            oriHTTPWebSitenameTableStatus		INTEGER
        }

oriHTTPWebSitenameTableIndex OBJECT-TYPE
    SYNTAX Integer32
    MAX-ACCESS read-only
    STATUS current
    DESCRIPTION
        "This objects represents the index to the website interface
        table."
    ::= { oriHTTPWebSitenameTableEntry  1 }

oriHTTPWebSiteFilename OBJECT-TYPE
    SYNTAX DisplayString
    MAX-ACCESS read-only
    STATUS current
    DESCRIPTION
        "This object represents the filename under which the website
        interface is stored in the device."
    ::= { oriHTTPWebSitenameTableEntry  2 }

oriHTTPWebSiteLanguage OBJECT-TYPE
    SYNTAX DisplayString
    MAX-ACCESS read-only
    STATUS current
    DESCRIPTION
        "This object represents the language of the website interface."
    ::= { oriHTTPWebSitenameTableEntry  3 }

oriHTTPWebSiteDescription OBJECT-TYPE
    SYNTAX DisplayString
    MAX-ACCESS read-only
    STATUS current
    DESCRIPTION
        "This object provides a description for the website interface."
    ::= { oriHTTPWebSitenameTableEntry  4 }
                
oriHTTPWebSitenameTableStatus  OBJECT-TYPE
    SYNTAX INTEGER
        {
            enable(1),
            disable(2),
            delete(3)
        } 
    MAX-ACCESS read-write
    STATUS current
    DESCRIPTION
		"This object is used to enable, disable, or delete a website 
		interface file."
    ::= { oriHTTPWebSitenameTableEntry 5 }

oriHTTPRefreshDelay OBJECT-TYPE
    SYNTAX Integer32
    MAX-ACCESS read-write
    STATUS current
    DESCRIPTION
		"This object is used for the automatic refresh delay for the 
		website pages."
    ::= { orinocoHTTP 5 }

	oriHTTPHelpInformationLink    OBJECT-TYPE
	    SYNTAX DisplayString
	    MAX-ACCESS read-write
	    STATUS current
	    DESCRIPTION
		"This object is used to configure the link in the web
			interface for where help information can be retrieved."
    ::= { orinocoHTTP 6 }
	    
oriHTTPSetupWizardStatus OBJECT-TYPE
    SYNTAX INTEGER
        {
            enable(1),
            disable(2)
        }
    MAX-ACCESS read-write
    STATUS current
    DESCRIPTION
        "This object is used to enable or disable the HTT setup wizard.  The
        user can manually disable this functionality or when the setup wizard
        completes it process successfully it sets this object to disable."
	DEFVAL { enable }
    ::= { orinocoHTTP 9 }

--=============================================================================
-- The WDS Group: orinocoWDS
--=============================================================================

	oriWDSSetupTable OBJECT-TYPE
	    SYNTAX SEQUENCE OF OriWDSSetupTableEntry
	    MAX-ACCESS not-accessible
	    STATUS current
	    DESCRIPTION
     	"This table is used in to configure the WDS feature in the device."
        ::= { orinocoWDS 1 }
	
    oriWDSSetupTableEntry  OBJECT-TYPE
	    SYNTAX OriWDSSetupTableEntry
	    MAX-ACCESS not-accessible
	    STATUS current
	    DESCRIPTION
        "This object represents an entry in the WDS table.  Note this
        table is index by ifIndex and WDS table index."
        INDEX { ifIndex, oriWDSSetupTablePortIndex  }
        ::= { oriWDSSetupTable 1 }

	OriWDSSetupTableEntry  ::=
	    SEQUENCE
	        {
  	   	        oriWDSSetupTablePortIndex  			Integer32,
	            oriWDSSetupTableEntryStatus 				INTEGER,
               	oriWDSSetupTablePartnerMACAddress  	PhysAddress
	        }

	oriWDSSetupTablePortIndex OBJECT-TYPE
	    SYNTAX Integer32 (1..6)
	    MAX-ACCESS read-only
	    STATUS current
	    DESCRIPTION
    	"This object represents the WDS port number."
	    ::= { oriWDSSetupTableEntry  1 }
            
	oriWDSSetupTableEntryStatus  OBJECT-TYPE
	    SYNTAX INTEGER
	        {
	            enable(1),
	            disable(2)
	        } 
	    MAX-ACCESS read-write
	    STATUS current
	    DESCRIPTION
		"This object is used to enable or disable a WDS table entry (link)."
	    ::= { oriWDSSetupTableEntry 2 }

	oriWDSSetupTablePartnerMACAddress OBJECT-TYPE
	    SYNTAX PhysAddress
	    MAX-ACCESS read-write
	    STATUS current
	    DESCRIPTION
	    "This object represents the partner MAC address for a WDS table
	    entry (link)."
	    ::= { oriWDSSetupTableEntry 3 }

--=============================================================================
-- The Trap Group: orinocoTrap
--=============================================================================

--=============================================================================
-- The Trap Variables: oriTrapVariable
--=============================================================================

	oriTrapVariable    OBJECT IDENTIFIER
    	::= { orinocoTrap 1 }

	oriGenericTrapVariable    OBJECT-TYPE
	    SYNTAX DisplayString
	    MAX-ACCESS read-only
	    STATUS current
	    DESCRIPTION
			"This object is used to provide additional information on traps."
	    ::= { oriTrapVariable 1 }

	oriTrapVarMACAddress    OBJECT-TYPE
	    SYNTAX PhysAddress
	    MAX-ACCESS read-only
	    STATUS current
	    DESCRIPTION
		"This object is used to store the MAC address of the device
			that has sent a trap."
	    ::= { oriTrapVariable 2 }

	oriTrapVarTFTPIPAddress    OBJECT-TYPE
	    SYNTAX IpAddress
	    MAX-ACCESS read-only
	    STATUS current
	    DESCRIPTION
			"This object is used to store the IP Address of the TFTP server."
	    ::= { oriTrapVariable 3 }

	oriTrapVarTFTPFilename    OBJECT-TYPE
    	SYNTAX DisplayString
	    MAX-ACCESS read-only
	    STATUS current
	    DESCRIPTION
			"This object is used to store the name of the file on which the 
			TFTP operation has occurred."
	    ::= { oriTrapVariable 4 }

	oriTrapVarTFTPOperation    OBJECT-TYPE
	    SYNTAX INTEGER
			{
			    upload(1),
			    download(2)
			}
	    MAX-ACCESS read-only
	    STATUS current
	    DESCRIPTION
			"This object is used to store the TFTP operation that failed, 
		either download or upload."
	    ::= { oriTrapVariable 5 }

	oriTrapVarUnauthorizedManagerIPaddress    OBJECT-TYPE
	    SYNTAX IpAddress
	    MAX-ACCESS read-only
	    STATUS current
	    DESCRIPTION
		"This object is used to store the IP address of the unauthorized 
			manager that has attempted to manage the device."
	    ::= { oriTrapVariable 6 }

     oriTrapVarFailedAuthenticationType    OBJECT-TYPE
        SYNTAX DisplayString
        MAX-ACCESS read-only
        STATUS current
        DESCRIPTION
            "This trap variable is used to specify the client authentication
            method/type that failed.  The authentication methods/types are
        dependant on the device and can range from the following:
                - MAC Access Control List
                - RADIUS MAC Authentication
                - 802.1x Authentication specifying the EAP Type."
		::= { oriTrapVariable 7 }
		
	oriTrapVarUnAuthorizedManagerCount    OBJECT-TYPE
	    SYNTAX Counter32
	    MAX-ACCESS read-only
	    STATUS current
	    DESCRIPTION
		"This object represents a counter for the number of unauthorized 
			SNMP managers that have attempted to modify and/or view the devices 
			setup.  When this number is incremented a trap should be sent out 
			notifying the trap host(s) that an unauthorized station has 
			attempted to configure or monitor the device the count should also 
			be sent out in the trap message."
	    ::= { oriTrapVariable 8 }

    oriTrapVarTaskSuspended    OBJECT-TYPE
	    SYNTAX DisplayString
		MAX-ACCESS read-only
		STATUS current
		DESCRIPTION
	    "This object is used to inform what task has been suspended
		on the device."
		::= { oriTrapVariable 9 }

    oriTrapVarUnauthorizedClientMACAddress    OBJECT-TYPE
        SYNTAX PhysAddress
        MAX-ACCESS read-only
        STATUS current
        DESCRIPTION
        "This object is used to store the MAC Address of an
            unauthorized client station."
        ::= { oriTrapVariable 17 }
        
    oriTrapVarWirelessCard    OBJECT-TYPE
        SYNTAX INTEGER
            {
                pcCardA(1),
                pcCardB(2)
            }
        MAX-ACCESS read-only
        STATUS current
        DESCRIPTION
        "This object is used to determine on which Wireless Card,
		    PC Card A or PC Card B, a wireless TRAP has occured on."
		::= { oriTrapVariable 18 }
 
oriTrapVarInterface OBJECT-TYPE
    SYNTAX Integer32
    MAX-ACCESS read-only
    STATUS current
    DESCRIPTION
        "This object is used to store the interface number."
    ::= { oriTrapVariable 21 }
     		
--=============================================================================
-- The Enable/Disable Trap Group Variables
--=============================================================================

    oriConfigurationTrapsStatus    OBJECT-TYPE
	    SYNTAX INTEGER
		    {
			    enable(1),
				disable(2)
			}
		MAX-ACCESS read-write
		STATUS current
		DESCRIPTION
	    "This object is used to enable or disable the configuration
			related traps."
		::= { oriTrapVariable 10 }

    oriSecurityTrapsStatus    OBJECT-TYPE
	    SYNTAX INTEGER
		    {
			    enable(1),
				disable(2)
			}
		MAX-ACCESS read-write
		STATUS current
		DESCRIPTION
	    "This object is used to enable or disable the security
			related traps."
		::= { oriTrapVariable 11 }

    oriWirelessIfTrapsStatus    OBJECT-TYPE
	    SYNTAX INTEGER
		    {
			    enable(1),
				disable(2)
			}
		MAX-ACCESS read-write
		STATUS current
		DESCRIPTION
	    "This object is used to enable or disable the wireless 
		interface/card related traps."
		::= { oriTrapVariable 12 }

    oriOperationalTrapsStatus    OBJECT-TYPE
	    SYNTAX INTEGER
		    {
			    enable(1),
				disable(2)
			}
		MAX-ACCESS read-write
		STATUS current
		DESCRIPTION
	    "This object is used to enable or disable the operational
			related traps."
		::= { oriTrapVariable 13 }

    oriFlashMemoryTrapsStatus    OBJECT-TYPE
	    SYNTAX INTEGER
		    {
			    enable(1),
				disable(2)
			}
		MAX-ACCESS read-write
		STATUS current
		DESCRIPTION
	    "This object is used to enable or disable the flash memory
		related traps."
		::= { oriTrapVariable 14 }

    oriTFTPTrapsStatus    OBJECT-TYPE
	    SYNTAX INTEGER
		    {
			    enable(1),
				disable(2)
			}
		MAX-ACCESS read-write
		STATUS current
		DESCRIPTION
	    "This object is used to enable or disable the TFTP
			related traps."
		::= { oriTrapVariable 15 }

    oriTrapsImageStatus    OBJECT-TYPE
	    SYNTAX INTEGER
		    {
			    enable(1),
				disable(2)
			}
		MAX-ACCESS read-write
		STATUS current
		DESCRIPTION
	    "This object is used to enable or disable the Image
		    related traps."
		::= { oriTrapVariable 16 }
		
	oriADSLIfTrapsStatus    OBJECT-TYPE
	    SYNTAX INTEGER
		    {
			  enable(1),
			  disable(2)
		    }
		MAX-ACCESS read-write
		STATUS current
		DESCRIPTION
	    "This object is used to enable or disable the ADSL
		interface related traps."
		::= { oriTrapVariable 19 }     		

	oriWORPTrapsStatus    OBJECT-TYPE
	    SYNTAX INTEGER
		    {
			  enable(1),
			  disable(2)
		    }
		MAX-ACCESS read-write
		STATUS current
		DESCRIPTION
	    "This object is used to enable or disable the WORP related traps."
		::= { oriTrapVariable 20 }
		
--=============================================================================
-- The IP/ARP Group: orinocoIPARP
--=============================================================================

    oriProxyARPStatus OBJECT-TYPE
 	    SYNTAX INTEGER
		    {
		        enable(1),
		        disable(2)
		    }
        MAX-ACCESS read-write
	    STATUS current
	    DESCRIPTION
	        "This object is used to enable/disable the Proxy ARP functionality
        in the device."
	    DEFVAL { enable }
        ::= {  orinocoIPARP 1 }

    oriIPARPFilteringStatus OBJECT-TYPE
 	    SYNTAX INTEGER
		    {
		        enable(1),
		        disable(2)
		    }
        MAX-ACCESS read-write
	    STATUS current
	    DESCRIPTION
	        "This object is used to enable/disable the IP/ARP functionality
        in the device."
	    DEFVAL { disable }
            ::= {  orinocoIPARP 2 }

    oriIPARPFilteringIPAddress OBJECT-TYPE
 	    SYNTAX IpAddress
        MAX-ACCESS read-write
	    STATUS current
	    DESCRIPTION
	        "This object is used to specify the IP/ARP Filtering address 
        in the device."
        ::= {  orinocoIPARP 3 }

    oriIPARPFilteringSubnetMask OBJECT-TYPE
 	    SYNTAX IpAddress
        MAX-ACCESS read-write
	    STATUS current
	    DESCRIPTION
	        "This object is used to specify the IP/ARP Subnet Mask 
        in the device."
        ::= {  orinocoIPARP 4 }
                    
--=============================================================================
-- The Spanning Tree Group: orinocoSpanningTree
--=============================================================================

    oriSpanningTreeStatus OBJECT-TYPE
	    SYNTAX INTEGER
	        {
			    enable(1),
			    disable(2)
  	        }
	    MAX-ACCESS read-write
	    STATUS current
	    DESCRIPTION
	        "This object is used to enable/disable the spanning tree protocol
        in the device."
	    DEFVAL { enable }
	    ::= { orinocoSpanningTree 1 }

--=============================================================================
-- The Security Group: orinocoSecurity
--=============================================================================

    oriSecurityConfiguration    OBJECT-TYPE
	    SYNTAX INTEGER
	        {
			    none(1),
		    dot1x(2),
		    mixedWepAnddot1x(3)
  	        }
	    MAX-ACCESS read-write
	    STATUS current
	    DESCRIPTION
        "This object represents the supported security configuration options."
	    DEFVAL { none }
	    ::= { orinocoSecurity 1 }

	oriSecurityEncryptionKeyLengthTable OBJECT-TYPE
	    SYNTAX SEQUENCE OF OriSecurityEncryptionKeyLengthTableEntry
	    MAX-ACCESS not-accessible
	    STATUS current
	    DESCRIPTION
     	"This table is used to specify the encryption key length for
     	the wireless interface(s)."
        ::= { orinocoSecurity 2 }
	
    oriSecurityEncryptionKeyLengthTableEntry  OBJECT-TYPE
	    SYNTAX OriSecurityEncryptionKeyLengthTableEntry
	    MAX-ACCESS not-accessible
	    STATUS current
	    DESCRIPTION
        "This object represents an entry in the encryption key 
        length table."
        INDEX { ifIndex }
        ::= { oriSecurityEncryptionKeyLengthTable 1 }

	OriSecurityEncryptionKeyLengthTableEntry ::=
	    SEQUENCE
	        {
	            oriSecurityEncryptionKeyLength			INTEGER
	        }

    oriSecurityEncryptionKeyLength    OBJECT-TYPE
	    SYNTAX INTEGER
	        {
            sixtyFourBits(1),
            oneHundredTwentyEightBits(2)
	        }
	    MAX-ACCESS read-write
	    STATUS current
	    DESCRIPTION
	        "This object represents the encryption key length, the supported
        key lengths are 64 bits (40 + 24 for IV), 128 bits (104 + 24 for IV), 
        and 152 bits (128 + 24 for IV)."
    DEFVAL { sixtyFourBits }
	    ::= { oriSecurityEncryptionKeyLengthTableEntry 1 }

oriSecurityRekeyingInterval OBJECT-TYPE
    SYNTAX Integer32 (60..65535)
    MAX-ACCESS read-write
    STATUS current
    DESCRIPTION
        "This object represents the encryption rekeying interval in seconds."
    ::= { orinocoSecurity 3 }
    
--=============================================================================
-- The PPPoE Group: orinocoPPPoE
--=============================================================================

	oriPPPoEStatus OBJECT-TYPE
	    SYNTAX INTEGER
	        {
	            enable(1),
	            disable(2)
	        } 
	    MAX-ACCESS read-write
	    STATUS current
	    DESCRIPTION
	        "This object allows to enable or disable the PPPoE service in the 
        device."
	    DEFVAL { disable }
	    ::= { orinocoPPPoE 1 }
	    
	oriPPPoEMaximumNumberOfSessions OBJECT-TYPE
	    SYNTAX Integer32 
	    MAX-ACCESS read-write
	    STATUS current
	    DESCRIPTION
	        "This object represents the maximum number of PPPoE sessions."
	    DEFVAL { 10 }
	    ::= { orinocoPPPoE 2 }

	oriPPPoENumberOfActiveSessions OBJECT-TYPE
	    SYNTAX Counter32 
	    MAX-ACCESS read-only
	    STATUS current
	    DESCRIPTION
        "This object represents the number of active PPPoE sessions."
	    ::= { orinocoPPPoE 3 }
	    
	oriPPPoESessionTable OBJECT-TYPE
	    SYNTAX SEQUENCE OF OriPPPoESessionTableEntry
	    MAX-ACCESS not-accessible
	    STATUS current
	    DESCRIPTION
     	"This table is used to configure the PPPoE session information."
        ::= { orinocoPPPoE 4 }
	
    oriPPPoESessionTableEntry  OBJECT-TYPE
	    SYNTAX OriPPPoESessionTableEntry
	    MAX-ACCESS not-accessible
	    STATUS current
	    DESCRIPTION
        "This object represents an entry in the PPPoE session table."
        INDEX { oriPPPoESessionISPName }
        ::= { oriPPPoESessionTable 1 }

	OriPPPoESessionTableEntry ::=
	    SEQUENCE
	        {
	            oriPPPoESessionTableIndex						Integer32,
	            oriPPPoESessionWANConnectMode					INTEGER,
	            oriPPPoESessionIdleTimeOut						Integer32,
	            oriPPPoESessionConnectTime						Counter32,
	            oriPPPoESessionConnectTimeLimitation			Integer32,
	            oriPPPoESessionConfigPADITxInterval				Integer32,
	            oriPPPoESessionConfigPADIMaxNumberOfRetries		Integer32,
	            oriPPPoESessionBindingsNumberPADITx			    Counter32,
	            oriPPPoESessionBindingsNumberPADTTx				Counter32,
	            oriPPPoESessionBindingsNumberServiceNameErrors 	Counter32,
	            oriPPPoESessionBindingsNumberACSystemErrors		Counter32,
	            oriPPPoESessionBindingsNumberGenericErrorsRx	Counter32,
	            oriPPPoESessionBindingsNumberGenericErrorsTx	Counter32,
	            oriPPPoESessionBindingsNumberMalformedPackets	Counter32,
	            oriPPPoESessionBindingsNumberMultiplePADORx		Counter32,
	            oriPPPoESessionUserName							DisplayString,
	            oriPPPoESessionUserNamePassword					DisplayString,
	            oriPPPoESessionServiceName						DisplayString,
	            oriPPPoESessionISPName							DisplayString,
	            oriPPPoESessionTableStatus						INTEGER,
	            oriPPPoESessionWANManualConnect					INTEGER,
	            oriPPPoESessionWANConnectionStatus				INTEGER
	        }

	oriPPPoESessionTableIndex OBJECT-TYPE
	    SYNTAX Integer32
	    MAX-ACCESS read-only
	    STATUS current
	    DESCRIPTION
        "This object is used as the index to the PPPoE Session Table."
        ::= { oriPPPoESessionTableEntry 1 }
        
	oriPPPoESessionWANConnectMode OBJECT-TYPE
	    SYNTAX INTEGER
          {
               alwaysOn(1),
               onDemand(2),
               manual(3)
          }
	    MAX-ACCESS read-write
	    STATUS current
	    DESCRIPTION
	        "This object represents the WAN connect mode."
        DEFVAL { alwaysOn }
        ::= { oriPPPoESessionTableEntry 2 }

	oriPPPoESessionIdleTimeOut OBJECT-TYPE
	    SYNTAX Integer32 
	    MAX-ACCESS read-write
	    STATUS current
	    DESCRIPTION
        "This object is used as a timeout for the PPPoE session to be
        disconnected from public side if idle for specified amount of 
        time."
	    ::= { oriPPPoESessionTableEntry 3 }

    oriPPPoESessionConnectTime OBJECT-TYPE
        SYNTAX Counter32
        MAX-ACCESS read-only
        STATUS current
        DESCRIPTION
        "This object identifies the PPPoE session connect time."
        ::= { oriPPPoESessionTableEntry 4 }

	oriPPPoESessionConnectTimeLimitation OBJECT-TYPE
	    SYNTAX Integer32 
	    MAX-ACCESS read-write
	    STATUS current
	    DESCRIPTION
        "This object represents the maximum connection time per session."
	    DEFVAL { 0 }
	    ::= { oriPPPoESessionTableEntry 5 }
	
	oriPPPoESessionConfigPADITxInterval OBJECT-TYPE
	    SYNTAX Integer32 
	    MAX-ACCESS read-write
	    STATUS current
	    DESCRIPTION
        "This object represents the time in seconds between PADI retries 
        from the Host."
	    ::= { oriPPPoESessionTableEntry 6 }

	oriPPPoESessionConfigPADIMaxNumberOfRetries OBJECT-TYPE
	    SYNTAX Integer32 
	    MAX-ACCESS read-write
	    STATUS current
	    DESCRIPTION
        "This object represents the number of times the Host sends 
        a PADI."
	    ::= { oriPPPoESessionTableEntry 7 }

	oriPPPoESessionBindingsNumberPADITx OBJECT-TYPE
	    SYNTAX Counter32 
	    MAX-ACCESS read-only                                  
	    STATUS current
	    DESCRIPTION
        "This object represents the number of PPPoE PADI transmitted."
	    ::= { oriPPPoESessionTableEntry 8 }

	oriPPPoESessionBindingsNumberPADTTx OBJECT-TYPE
	    SYNTAX Counter32 
	    MAX-ACCESS read-only                                  
	    STATUS current
	    DESCRIPTION
        "This object represents the number of PPPoE PADT transmitted."
	    ::= { oriPPPoESessionTableEntry 9 }
	    
	oriPPPoESessionBindingsNumberServiceNameErrors  OBJECT-TYPE
	    SYNTAX Counter32 
	    MAX-ACCESS read-only
	    STATUS current
	    DESCRIPTION
        "This object represents the number of PPPoE Service-Name-Error 
        tags received/transmitted."
	    ::= { oriPPPoESessionTableEntry 10 }

	oriPPPoESessionBindingsNumberACSystemErrors OBJECT-TYPE
	    SYNTAX Counter32 
	    MAX-ACCESS read-only
	    STATUS current
	    DESCRIPTION
        "This object represents the number of PPPoE AC-System-Error 
        tags received/transmitted."
	    ::= { oriPPPoESessionTableEntry 11 }

	oriPPPoESessionBindingsNumberGenericErrorsRx OBJECT-TYPE
	    SYNTAX Counter32
	    MAX-ACCESS read-only
	    STATUS current
	    DESCRIPTION
        "This object represents the number of PPPoE Generic-Error 
        tags received."
	    ::= { oriPPPoESessionTableEntry 12 }

	oriPPPoESessionBindingsNumberGenericErrorsTx OBJECT-TYPE
	    SYNTAX Counter32 
	    MAX-ACCESS read-only
	    STATUS current
	    DESCRIPTION
        "This object represents the number of PPPoE Generic Error 
        tags transmitted."
	    ::= { oriPPPoESessionTableEntry 13 }

	oriPPPoESessionBindingsNumberMalformedPackets OBJECT-TYPE
	    SYNTAX Counter32 
	    MAX-ACCESS read-only
	    STATUS current
	    DESCRIPTION
        "This object represents teh number of malformed PPPoE 
        packets received."
	    ::= { oriPPPoESessionTableEntry 14 }

	oriPPPoESessionBindingsNumberMultiplePADORx OBJECT-TYPE
	    SYNTAX Counter32 
	    MAX-ACCESS read-only
	    STATUS current
	    DESCRIPTION
        "This object represents the number of PPPoE multiple PADO's 
        received after a PADI request."
	    ::= { oriPPPoESessionTableEntry 15 }

	oriPPPoESessionUserName OBJECT-TYPE
	    SYNTAX DisplayString 
	    MAX-ACCESS read-write
	    STATUS current
	    DESCRIPTION
	        "This object represents the PPPoE user name."
	    ::= { oriPPPoESessionTableEntry 16 }

	oriPPPoESessionUserNamePassword OBJECT-TYPE
	    SYNTAX DisplayString 
	    MAX-ACCESS read-write
	    STATUS current
	    DESCRIPTION
	        "This object represents the PPPoE user name password.  This object 
	        should be treated as write-only and returned as asterisks."
	    ::= { oriPPPoESessionTableEntry 17 }

	oriPPPoESessionServiceName OBJECT-TYPE
	    SYNTAX DisplayString 
	    MAX-ACCESS read-write
	    STATUS current
	    DESCRIPTION
	        "This object represents the PPPoE service name."
	    ::= { oriPPPoESessionTableEntry 18 }

	oriPPPoESessionISPName OBJECT-TYPE
	    SYNTAX DisplayString 
	    MAX-ACCESS read-write
	    STATUS current
	    DESCRIPTION
	        "This object represents the PPPoE ISP name."
	    ::= { oriPPPoESessionTableEntry 19 }

	oriPPPoESessionTableStatus OBJECT-TYPE
	    SYNTAX INTEGER
	        {
	            enable(1),
	            disable(2),
	            delete(3),
	            create(4)
	        } 
	    MAX-ACCESS read-write
	    STATUS current
	    DESCRIPTION
	        "This object represents the PPPoE ISP table entry status."
	    ::= { oriPPPoESessionTableEntry 20 }

	oriPPPoESessionWANManualConnect OBJECT-TYPE
	    SYNTAX INTEGER
	        {
	            enable(1),
	            disable(2)
	        } 
	    MAX-ACCESS read-write
	    STATUS current
	    DESCRIPTION
	        "This object is used to connect of disconnect the PPPoE session
	        when the connect mode is set to manual."
	    ::= { oriPPPoESessionTableEntry 21 }

	oriPPPoESessionWANConnectionStatus OBJECT-TYPE
	    SYNTAX INTEGER
	        {
	            null(1),
	            start(2),
	            addingStack(3),
	            stackAdded(4),
	            stackAddError(5),
	            connectFailed(6),
	            authFailed(7),
	            up(8),
	            down(9),
	            suspended(10),
	            unknown(11)
	        } 
	    MAX-ACCESS read-only
	    STATUS current
	    DESCRIPTION
	        "This object represents the state of the PPPoE WAN connection
	        interface."
	    ::= { oriPPPoESessionTableEntry 22 }
	    	    
	oriPPPoEMACtoSessionTable OBJECT-TYPE
	    SYNTAX SEQUENCE OF OriPPPoEMACtoSessionTableEntry
	    MAX-ACCESS not-accessible
	    STATUS current
	    DESCRIPTION
         	"This table is used to map client MAC address to PPPoE Session
         	information for an ISP."
        ::= { orinocoPPPoE 5 }
	
    oriPPPoEMACtoSessionTableEntry  OBJECT-TYPE
	    SYNTAX OriPPPoEMACtoSessionTableEntry
	    MAX-ACCESS not-accessible
	    STATUS current
	    DESCRIPTION
        "This object represents an entry in the PPPoE MAC to 
        Session table."
        INDEX { oriPPPoEMACtoSessionTableIndex }
        ::= { oriPPPoEMACtoSessionTable 1 }

	OriPPPoEMACtoSessionTableEntry ::=
	    SEQUENCE
	        {
	            oriPPPoEMACtoSessionTableIndex				Integer32,
	            oriPPPoEMACtoSessionTableMACAddress			PhysAddress,
	            oriPPPoEMACtoSessionTableISPName			DisplayString,
	            oriPPPoEMACtoSessionTableStatus				INTEGER
	        }

    oriPPPoEMACtoSessionTableIndex    OBJECT-TYPE
        SYNTAX Integer32
        MAX-ACCESS read-only
        STATUS current
        DESCRIPTION
        "This object is used as the index to the PPPoE Session Table."
        ::= { oriPPPoEMACtoSessionTableEntry 1 }
        
    oriPPPoEMACtoSessionTableMACAddress		OBJECT-TYPE
        SYNTAX PhysAddress
        MAX-ACCESS read-write
        STATUS current
        DESCRIPTION
            "This object represents the client MAC address."
        ::= { oriPPPoEMACtoSessionTableEntry 2 }

    oriPPPoEMACtoSessionTableISPName		OBJECT-TYPE
        SYNTAX DisplayString
        MAX-ACCESS read-write
        STATUS current
        DESCRIPTION
            "This object represents the ISP name."
        ::= { oriPPPoEMACtoSessionTableEntry 3 }

	oriPPPoEMACtoSessionTableStatus OBJECT-TYPE
	    SYNTAX INTEGER
	        {
	            enable(1),
	            disable(2),
	            delete(3),
	            create(4)
	        } 
	    MAX-ACCESS read-write
	    STATUS current
	    DESCRIPTION
	        "This object represents the PPPoE MAC to Session table 
	        entry status."
	    ::= { oriPPPoEMACtoSessionTableEntry 4 }

--=============================================================================
-- The Configuration Group: orinocoConfig
--=============================================================================

    oriConfigResetToDefaults    OBJECT-TYPE
	    SYNTAX INTEGER
	        {
			    bridgeMode(1),
			    gatewayMode(2),
			    gatewayModeDHCPClient(3),
			    gatewayModePPPoE(4)
  	        }
	    MAX-ACCESS read-write
	    STATUS current
	    DESCRIPTION
        "This object represents the quickstart modes that the
	        device can be configured in."
	    DEFVAL { gatewayMode }
	    ::= { orinocoConfig 1 }

	oriConfigFileTable OBJECT-TYPE
	    SYNTAX SEQUENCE OF OriConfigFileTableEntry
	    MAX-ACCESS not-accessible
	    STATUS current
	    DESCRIPTION
         	"This table contains the current configuration files stored in the
     	device.  This table is used to manage the different configuration
     	files."
        ::= { orinocoConfig 2 }
	
    oriConfigFileTableEntry  OBJECT-TYPE
	    SYNTAX OriConfigFileTableEntry
	    MAX-ACCESS not-accessible
	    STATUS current
	    DESCRIPTION
        "This object represents an entry in the configuration file table."
        INDEX { oriConfigFileTableIndex }
        ::= { oriConfigFileTable 1 }

	OriConfigFileTableEntry ::=
	    SEQUENCE
	        {
	            oriConfigFileTableIndex				Integer32,
	            oriConfigFileName					DisplayString,
	            oriConfigFileStatus					INTEGER
	        }

    oriConfigFileTableIndex    OBJECT-TYPE
	    SYNTAX Integer32
	    MAX-ACCESS read-only
	    STATUS current
	    DESCRIPTION
	        "This object represents the index to the configuration file
	        table."
	    ::= { oriConfigFileTableEntry 1 }

    oriConfigFileName    OBJECT-TYPE
	    SYNTAX DisplayString
    MAX-ACCESS read-write
	    STATUS current
	    DESCRIPTION
	        "This object represents the configuration file name."
	    ::= { oriConfigFileTableEntry 2 }

    oriConfigFileStatus    OBJECT-TYPE
	    SYNTAX INTEGER
	        {
	            enable(1),
	            disable(2),
            delete(3)
	        }   
	    MAX-ACCESS read-write
	    STATUS current
	    DESCRIPTION
	        "This object represents the status of the configuration file.
	        The possible options are:
	            - Enable: active configuration file
	            - Disable: inactive configuration file
            - Delete: in order to delete the configuration file"
	    ::= { oriConfigFileTableEntry 3 }

    oriConfigSaveFile    OBJECT-TYPE
	    SYNTAX DisplayString
	    MAX-ACCESS read-write
	    STATUS current
	    DESCRIPTION
	        "This object saves the configuration to the specified name."
	    ::= { orinocoConfig 3 }

oriConfigSaveKnownGood OBJECT-TYPE
    SYNTAX INTEGER
        {
		    saveKnownGood(1)
	        }
    MAX-ACCESS read-write
    STATUS current
    DESCRIPTION
        "This object is used to identify the last know good configuration
        file used.  Setting a value of 1 to this objecgt saves the current 
        configuration as the known good configuration."
    ::= { orinocoConfig 4 }

--=============================================================================
-- The DNS Group: orinocoDNS
--=============================================================================   

--=============================================================================
-- The DNS Redirect Group: orinocoDNS
--=============================================================================

    oriDNSRedirectStatus    OBJECT-TYPE
	    SYNTAX INTEGER
	        {
			    enable(1),
			    disable(2)
			}
	    MAX-ACCESS read-write
	    STATUS current
	    DESCRIPTION
	        "This object is used to enable or disable the DNS Redirect
	        functionality."
	    DEFVAL { enable }
	    ::= { orinocoDNS 1 }

    oriDNSRedirectMaxResponseWaitTime    OBJECT-TYPE
	    SYNTAX Integer32
	    MAX-ACCESS read-write
	    STATUS current
	    DESCRIPTION
	        "This object represents the maximum response wait time for
	        DNS redirect.  The units for this object is seconds."
	    DEFVAL { 10 }
	    ::= { orinocoDNS 2 }

	oriDNSPrimaryDNSIPAddress    OBJECT-TYPE
	    SYNTAX IpAddress
	    MAX-ACCESS read-write
	    STATUS current
	    DESCRIPTION
        "This object represents the Primary DNS IP Address."
	  ::= { orinocoDNS 3 }

	oriDNSSecondaryDNSIPAddress    OBJECT-TYPE
	    SYNTAX IpAddress
	    MAX-ACCESS read-write
	    STATUS current
	    DESCRIPTION
        "This object represents the Secondary DNS IP Address."
	    ::= { orinocoDNS 4 }

--=============================================================================
-- The DNS Client Subgroup: orinocoDNSClient
--=============================================================================

	oriDNSClientStatus OBJECT-TYPE
	    SYNTAX INTEGER
	        {
			    enable(1),
			    disable(2)
			}
	    MAX-ACCESS read-write
	    STATUS current
	    DESCRIPTION
	        "This object is used to enable or disable the DNS Client feature."
	    DEFVAL { disable }
	    ::= { orinocoDNSClient 1 }
	
	oriDNSClientPrimaryServerIPAddress OBJECT-TYPE
	    SYNTAX IpAddress
	    MAX-ACCESS read-write
	    STATUS current
	    DESCRIPTION
	        "This object represents the Primary Server DNS IP Address."
	  ::= { orinocoDNSClient 2 }
	
	oriDNSClientSecondaryServerIPAddress OBJECT-TYPE
	    SYNTAX IpAddress
	    MAX-ACCESS read-write
	    STATUS current
	    DESCRIPTION
	        "This object represents the Secondary Server DNS IP Address."
	    ::= { orinocoDNSClient 3 }

	oriDNSClientDefaultDomainName OBJECT-TYPE
	    SYNTAX DisplayString
	    MAX-ACCESS read-write
	    STATUS current
	    DESCRIPTION
	        "This object represents the default domain name for the DNS Client."
	    ::= { orinocoDNSClient 4 }

--=============================================================================
-- The AOL Group: orinocoAOL
--=============================================================================

    oriAOLNATALGStatus OBJECT-TYPE
	    SYNTAX INTEGER
	        {
			    enable(1),
			    disable(2)
  	        }
	    MAX-ACCESS read-write
	    STATUS current
	    DESCRIPTION
	        "This object is used to enable/disable the AOL NAT Application
	        Level Gateway (ALG) support."
	    DEFVAL { disable }
	    ::= { orinocoAOL 1 }

--=============================================================================
-- The NAT Group: orinocoNAT
--=============================================================================

	oriNatType OBJECT-TYPE
	    SYNTAX Integer32
	    MAX-ACCESS read-write
	    STATUS current
	    DESCRIPTION
	        "A Bit Mask documenting the NAT device's actual 
	         configuration according to natTypeMask above.   

	         Its value may be one and only one of the options below: 
          - Basic-NAT			(Bit 0) 
          - NAPT				(Bit 1) 
          - Bi-directional-NAT  (Bit 2) 
          - Twice-NAT			(Bit 3) 
          - RSA-IP-Server		(Bit 4) 
          - RSAP-IP-Server	    (Bit 5) 
 
          - Bit 0, if set, indicates that Basic-NAT is configured. 
          - Bit 1, if set, indicates that NAPT is configured. 
          - Bit 2, if set, indicates that Bi-directional-NAT  
	         is configured. 
          - Bit 3, if set, indicates that Twice-NAT is configured. 
          - Bit 4, if set, indicates that RSA-IP-Server is  
	         configured. 
          - Bit 5, if set, indicates that RSAP-IP-Server  
	         is configured."
		::= { orinocoNAT 1 }
	    
	oriNatStaticBindStatus OBJECT-TYPE
	    SYNTAX INTEGER
			{
			    enable(1),
			    disable(2)
			} 
	    MAX-ACCESS read-write
	    STATUS current
	    DESCRIPTION
        "This object is used to enable or disable static bind entries 
        on the NAT device."
	    ::= { orinocoNAT 2 }

	oriNatStaticIPBindTable    OBJECT-TYPE
	    SYNTAX SEQUENCE OF OriNatStaticIPBindTableEntry
	    MAX-ACCESS not-accessible
	    STATUS current
	    DESCRIPTION
		"This table contains NAT IP bind specific information."
	    ::= { orinocoNAT 3 }
        
	oriNatStaticIPBindTableEntry  OBJECT-TYPE
		SYNTAX OriNatStaticIPBindTableEntry
	    MAX-ACCESS not-accessible
		STATUS current
		DESCRIPTION
		"This object is an entry in the NAT Static IP Bind Table."
	    INDEX { oriNatStaticIPBindTableIndex }
	    ::= { oriNatStaticIPBindTable 1 }

	OriNatStaticIPBindTableEntry  ::=
   		SEQUENCE
			{
			    oriNatStaticIPBindTableIndex		Integer32,
			    oriNatStaticIPBindLocalAddress		IpAddress,
			    oriNatStaticIPBindRemoteAddress		IpAddress,
			    oriNatStaticIPBindTableEntryStatus 	INTEGER
			}
			
	oriNatStaticIPBindTableIndex    OBJECT-TYPE
	    SYNTAX Integer32
	    MAX-ACCESS read-only
	    STATUS current
	    DESCRIPTION
		"This object is used as the index for the NAT static IP 
		bind table."
	    ::= { oriNatStaticIPBindTableEntry 1 }

	oriNatStaticIPBindLocalAddress    OBJECT-TYPE
	    SYNTAX IpAddress
	    MAX-ACCESS read-write
	    STATUS current
	    DESCRIPTION
        "This object represents the local IP address for this NAT
	        Static IP bind Table entry."
	    ::= { oriNatStaticIPBindTableEntry 2 }
	
	oriNatStaticIPBindRemoteAddress    OBJECT-TYPE
	    SYNTAX IpAddress
	    MAX-ACCESS read-write
	    STATUS current
	    DESCRIPTION
	    "This object represents the remote IP address for this NAT
    	    Static IP bind Table entry."
	    ::= { oriNatStaticIPBindTableEntry 3 }


	oriNatStaticIPBindTableEntryStatus    OBJECT-TYPE
	    SYNTAX INTEGER
			{
			    enable(1),
			    disable(2),
			    delete(3),
			    create(4)
			}
	    MAX-ACCESS read-write
	    STATUS current
	    DESCRIPTION
		"The object indicates the status of the NAT Static IP Bind 
			Table entry."
	    ::= { oriNatStaticIPBindTableEntry 4 }

	oriNatStaticPortBindTable    OBJECT-TYPE
	    SYNTAX SEQUENCE OF OriNatStaticPortBindTableEntry
	    MAX-ACCESS not-accessible
	    STATUS current
	    DESCRIPTION
		"This table is used to configure NAT Port bind specific 
		information."
	    ::= { orinocoNAT 4 }
        
	oriNatStaticPortBindTableEntry  OBJECT-TYPE
		SYNTAX OriNatStaticPortBindTableEntry
	    MAX-ACCESS not-accessible
		STATUS current
		DESCRIPTION
		"This object represents an entry in the NAT Static Port Bind 
		Table."
	    INDEX { oriNatStaticPortBindTableIndex }
	    ::= { oriNatStaticPortBindTable 1 }

	OriNatStaticPortBindTableEntry  ::=
   		SEQUENCE
			{
			    oriNatStaticPortBindTableIndex			Integer32,
			    oriNatStaticPortBindLocalAddress		IpAddress,
			    oriNatStaticPortBindLocalPort			Integer32,
			    oriNatStaticPortBindRemotePort			Integer32,
				oriNatStaticPortBindPortType			INTEGER,
			    oriNatStaticPortBindTableEntryStatus 	INTEGER
			}
			
	oriNatStaticPortBindTableIndex    OBJECT-TYPE
	    SYNTAX Integer32
	    MAX-ACCESS read-only
	    STATUS current
	    DESCRIPTION
		"This object is used as  the index for the NAT static Port 
		bind table."
	    ::= { oriNatStaticPortBindTableEntry 1 }

	oriNatStaticPortBindLocalAddress    OBJECT-TYPE
	    SYNTAX IpAddress
	    MAX-ACCESS read-write
	    STATUS current
	    DESCRIPTION
        "This object represents the local IP address for this NAT Static
	        Port bind Table entry."
	    ::= { oriNatStaticPortBindTableEntry 2 }
	
	oriNatStaticPortBindLocalPort    OBJECT-TYPE
	    SYNTAX Integer32
	    MAX-ACCESS read-write
	    STATUS current
	    DESCRIPTION
	    "This object represents the local port number for this NAT Static
    	    Port bind Table entry."
	    ::= { oriNatStaticPortBindTableEntry 3 }

	oriNatStaticPortBindRemotePort    OBJECT-TYPE
	    SYNTAX Integer32
	    MAX-ACCESS read-write
	    STATUS current
	    DESCRIPTION
	    "This object represents the remote port number for this NAT Static
    	    Port bind Table entry."
	    ::= { oriNatStaticPortBindTableEntry 4 }

	oriNatStaticPortBindPortType OBJECT-TYPE 
	    SYNTAX INTEGER
			{
				tcp(1),
				udp(2),
		        both(3)
			}
	    MAX-ACCESS read-write
	    STATUS current
	    DESCRIPTION
		"This object represents the port type for this NAT Static
	    Port bind Table entry."
	    ::= { oriNatStaticPortBindTableEntry 5 }

	oriNatStaticPortBindTableEntryStatus    OBJECT-TYPE
	    SYNTAX INTEGER
			{
			    enable(1),
			    disable(2),
			    delete(3),
			    create(4)
			}
	    MAX-ACCESS read-write
	    STATUS current
	    DESCRIPTION
		"The object indicates the status of the NAT Static Port Bind 
			Table entry."
	    ::= { oriNatStaticPortBindTableEntry 6 }

--=============================================================================
-- The Ping Group: orinocoPing
--=============================================================================

	oriPingTestStatus    OBJECT-TYPE
	    SYNTAX INTEGER
			{
			    disable(1),
			    pinging(2),
			    pingResultsAvailable(3)
			}
	    MAX-ACCESS read-write
	    STATUS current
	    DESCRIPTION
		"This object is used to control the ping test.  
		When this parameter is set to 2, the device will start a ping test 
		on the configured target IP Address for the configured number of 
		ping requests.  When this parameter is set to 3, the results of the 
		ping test are available."
	    ::= { orinocoPing 1 }

	oriPingTestTargetIPAdddress    OBJECT-TYPE
	    SYNTAX IpAddress
	    MAX-ACCESS read-write
	    STATUS current
	    DESCRIPTION
			"This object represents the target IP Address for the ping test."
	    ::= { orinocoPing 2 }

	oriPingTestNumberOfPingRequests    OBJECT-TYPE
	    SYNTAX Integer32 (0..100)
	    MAX-ACCESS read-write
	    STATUS current
	    DESCRIPTION
			"This object represents the number of ping requests that will be
			transmitted to the target IP address.  This object is limited to
			100 ping requests."
	    ::= { orinocoPing 3 }

	oriPingTestPacketSize    OBJECT-TYPE
	    SYNTAX Integer32 (0..65535)
	    MAX-ACCESS read-write
	    STATUS current
	    DESCRIPTION
			"This object represents the packet size for the ping requests/
			messages transmitted to the target IP address."
	    ::= { orinocoPing 4 }
	    	    
	oriPingTestRequestsTx    OBJECT-TYPE
	    SYNTAX Counter32
	    MAX-ACCESS read-only
	    STATUS current
	    DESCRIPTION
			"This counter represents the total number of ping requests/messages
			transmitted to the target IP address."
	    ::= { orinocoPing 5 }
	    
	oriPingTestRepliesRx    OBJECT-TYPE
	    SYNTAX Counter32
	    MAX-ACCESS read-only
	    STATUS current
	    DESCRIPTION
			"This counter represents the number of ping replies received from
			the target IP address."
	    ::= { orinocoPing 6 }	    

	oriPingTestTimeoutCount    OBJECT-TYPE
	    SYNTAX Counter32
	    MAX-ACCESS read-only
	    STATUS current
	    DESCRIPTION
			"This counter represents the number of timeouts or ping failures to
			the target IP address."
	    ::= { orinocoPing 7 }

--=============================================================================
-- The SpectraLink VoIP Group: orinocoSpectraLink
--=============================================================================

    oriSpectraLinkStatus    OBJECT-TYPE
	    SYNTAX INTEGER
	        {
	            enable(1),
	            disable(2)
  	        }
	    MAX-ACCESS read-write
	    STATUS current
	    DESCRIPTION
	        "This object is used to enable or disable the SpectraLink VoIP 
	        feature."
	    DEFVAL { disable }
	    ::= { orinocoSpectraLink 1 }

--=============================================================================
-- The VLAN Group: orinocoVLAN
--=============================================================================

    oriVLANStatus    OBJECT-TYPE
	    SYNTAX INTEGER
	        {
	            enable(1),
	            disable(2)
  	        }
	    MAX-ACCESS read-write
	    STATUS current
	    DESCRIPTION
	        "This object is used to enable or disable the VLAN feature."
	    DEFVAL { disable }
	    ::= { orinocoVLAN 1 }

    oriVLANMgmtIdentifier    OBJECT-TYPE
	    SYNTAX VlanId
	    MAX-ACCESS read-write
	    STATUS current
	    DESCRIPTION
	        "This object represents the VLAN management Identifier (ID)."
	    DEFVAL { 0 }
	    ::= { orinocoVLAN 2 }
	    
	oriVLANIDTable OBJECT-TYPE
	    SYNTAX SEQUENCE OF OriVLANIDTableEntry
	    MAX-ACCESS not-accessible
	    STATUS current
	    DESCRIPTION
         	"This table is used to configure the VLAN IDs for the device."
        ::= { orinocoVLAN 3 }
	
    oriVLANIDTableEntry  OBJECT-TYPE
	    SYNTAX OriVLANIDTableEntry
	    MAX-ACCESS not-accessible
	    STATUS current
	    DESCRIPTION
	        "This object represents an entry in the respective table.  In this
	        case each table entry represents a VLAN ID."
        INDEX { oriVLANIDTableIndex }
        ::= { oriVLANIDTable 1 }

	OriVLANIDTableEntry ::=
	    SEQUENCE
	        {
	            oriVLANIDTableIndex			Integer32,
	            oriVLANIDTableIdentifier	VlanId
	        }

    oriVLANIDTableIndex    OBJECT-TYPE
	    SYNTAX Integer32
	    MAX-ACCESS read-only
	    STATUS current
	    DESCRIPTION
	        "This object represents the index to the VLAN ID Table."
	    ::= { oriVLANIDTableEntry 1 }
	    
    oriVLANIDTableIdentifier    OBJECT-TYPE
	    SYNTAX VlanId
	    MAX-ACCESS read-write
	    STATUS current
	    DESCRIPTION
	        "This object represents the VLAN Identifier (ID)."
	    DEFVAL { 0 }
	    ::= { oriVLANIDTableEntry 2 }
                	    	                
--=============================================================================
-- The DMZ Group: orinocoDMZ
--=============================================================================

oriDMZHostTable OBJECT-TYPE
    SYNTAX SEQUENCE OF OriDMZHostTableEntry
    MAX-ACCESS not-accessible
    STATUS current
    DESCRIPTION
		"A table containing DMZ host IP information. 
		Only if the system is in Gateway mode, and the NAT is enabled, 
		and this table has valid 'enabled' entry, the DMZ takes effect."
    ::= { orinocoDMZ 1 }
    
oriDMZHostTableEntry OBJECT-TYPE
	SYNTAX OriDMZHostTableEntry
    MAX-ACCESS not-accessible
	STATUS current
	DESCRIPTION
		"This object represents an entry in the DMZ host IP Table."
    INDEX { oriDMZHostTableIndex }
    ::= { oriDMZHostTable 1 }

OriDMZHostTableEntry ::=
	SEQUENCE
		{
		    oriDMZHostTableIndex		Integer32,
		    oriDMZHostTableHostIP		IpAddress,
			oriDMZHostTableComment		DisplayString,
		    oriDMZHostTableEntryStatus 	INTEGER
		}
		
oriDMZHostTableIndex OBJECT-TYPE
    SYNTAX Integer32
    MAX-ACCESS read-only
    STATUS current
    DESCRIPTION
		"This object is used as the index for the DMZ host IP Table."
    ::= { oriDMZHostTableEntry 1 }

oriDMZHostTableHostIP OBJECT-TYPE
    SYNTAX IpAddress
    MAX-ACCESS read-write
    STATUS current
    DESCRIPTION
        "This object represents the DMZ host IP address."
    ::= { oriDMZHostTableEntry 2 }

oriDMZHostTableComment OBJECT-TYPE
    SYNTAX DisplayString
    MAX-ACCESS read-write
    STATUS current
    DESCRIPTION
        "This objecgt is used for an optional comment associated to the 
		DMZ host IP Table entry."
    ::= { oriDMZHostTableEntry 3 }

oriDMZHostTableEntryStatus OBJECT-TYPE
    SYNTAX INTEGER
		{
		    enable(1),
		    disable(2),
		    delete(3),
		    create(4)
		}
    MAX-ACCESS read-write
    STATUS current
    DESCRIPTION
		"The object indicates the status of the DMZ host IP Table entry."
    ::= { oriDMZHostTableEntry 4 }

--=============================================================================
-- The OEM Group: orinocoOEM
--=============================================================================

oriOEMName OBJECT-TYPE
    SYNTAX DisplayString
    MAX-ACCESS read-only
    STATUS current
    DESCRIPTION
        "This object is used to specify the OEM name."
    ::= { orinocoOEM 1 }

oriOEMHomeUrl OBJECT-TYPE
    SYNTAX DisplayString
    MAX-ACCESS read-write
    STATUS current
    DESCRIPTION
        "This object is used to specify the OEM home URL."
    ::= { orinocoOEM 2 }

oriOEMProductName OBJECT-TYPE
    SYNTAX DisplayString
    MAX-ACCESS read-only
    STATUS current
    DESCRIPTION
        "This object represents the product name.  It is the same name as 
        shown in all management Web pages."
    ::= { orinocoOEM 3 }

oriOEMProductModel OBJECT-TYPE
    SYNTAX DisplayString
    MAX-ACCESS read-only
    STATUS current
    DESCRIPTION
        "This object represents the product model."
    ::= { orinocoOEM 4 }

oriOEMLogoImageFile OBJECT-TYPE
    SYNTAX DisplayString
    MAX-ACCESS read-only
    STATUS current
    DESCRIPTION
        "This object represents the name of logo image file."
    ::= { orinocoOEM 5 }

oriOEMNoNavLogoImageFile OBJECT-TYPE
    SYNTAX DisplayString
    MAX-ACCESS read-only
    STATUS current
    DESCRIPTION
        "This object represents the name of no nav. logo image file."
    ::= { orinocoOEM 6 }

--=============================================================================
-- The Station Statistics Group: orinocoStationsStatistics
--=============================================================================

	oriStationStatTable OBJECT-TYPE
	    SYNTAX SEQUENCE OF OriStationStatTableEntry
	    MAX-ACCESS not-accessible
	    STATUS current
	    DESCRIPTION
     	"This table contains wireless stations statistics."
        ::= { orinocoStationStatistics 1 }
	
    oriStationStatTableEntry  OBJECT-TYPE
	    SYNTAX OriStationStatTableEntry
	    MAX-ACCESS not-accessible
	    STATUS current
	    DESCRIPTION
	        "This object represents an entry in the respective table.  In this
	        case each table entry represents a wireless station."
        INDEX { oriStationStatTableIndex }
        ::= { oriStationStatTable 1 }

	OriStationStatTableEntry ::=
	    SEQUENCE
	        {
	            oriStationStatTableIndex				Integer32,
	            oriStationStatTableMACAddress			MacAddress,
	            oriStationStatTableIPAddress			IpAddress,
	            oriStationStatTableInterface			Integer32,
	            oriStationStatTableName					DisplayString,
	            oriStationStatTableType					INTEGER,
	            oriStationStatTableMACProtocol			INTEGER,
	            oriStationStatTableAdminStatus			INTEGER,
	            oriStationStatTableOperStatus			INTEGER,
	            oriStationStatTableLastChange			TimeTicks,
	            oriStationStatTableLastState			INTEGER,
	            oriStationStatTableInOctets				Counter32,
	            oriStationStatTableInUcastPkts			Counter32,
	            oriStationStatTableInNUcastPkts			Counter32,
	            oriStationStatTableInDiscards			Counter32,
	            oriStationStatTableOutOctets			Counter32,
	            oriStationStatTableOutUcastPkts			Counter32,
	            oriStationStatTableOutNUcastPkts		Counter32,
	            oriStationStatTableOutDiscards			Counter32,
            oriStationStatTableInSignal				Integer32,
            oriStationStatTableInNoise				Integer32,
            oriStationStatTableRemoteSignal			Integer32,
            oriStationStatTableRemoteNoise			Integer32,
	            oriStationStatTableLastInPktTime		TimeTicks 
	        }

    oriStationStatTableIndex    OBJECT-TYPE
    SYNTAX Integer32 (0..500)
	    MAX-ACCESS read-only
	    STATUS current
	    DESCRIPTION
	        "This object represents the index of the stations statistics
        table.  This table is limited to 500 entries."
	    ::= { oriStationStatTableEntry 1 }
	    
    oriStationStatTableMACAddress    OBJECT-TYPE
	    SYNTAX MacAddress
	    MAX-ACCESS read-only
	    STATUS current
	    DESCRIPTION
        "This object represents the MAC address of the station for which 
        the statistics are gathered."
	    ::= { oriStationStatTableEntry 2 }

    oriStationStatTableIPAddress    OBJECT-TYPE
	    SYNTAX IpAddress
	    MAX-ACCESS read-only
	    STATUS current
	    DESCRIPTION
        "This object represents the IP address of the stations for which 
        the statistics are gathered. If the IP address is not known, 
        0.0.0.0 will be returned."
	    ::= { oriStationStatTableEntry 3 }

    oriStationStatTableInterface    OBJECT-TYPE
	    SYNTAX Integer32
	    MAX-ACCESS read-only
	    STATUS current
	    DESCRIPTION
        "This object represents the number of the interface on which the 
        station is last seen."
	    ::= { oriStationStatTableEntry 4 }

    oriStationStatTableName    OBJECT-TYPE
	    SYNTAX DisplayString
	    MAX-ACCESS read-only
	    STATUS current
	    DESCRIPTION
        "This object represents the name of the station.  If the name is 
        not known, an empty string will be returned."
	    ::= { oriStationStatTableEntry 5 }

    oriStationStatTableType    OBJECT-TYPE
	    SYNTAX INTEGER
	        {
            sta(1),
            wds(2),
            worpBase(3),
            worpSatellite(4),
            norc(5)
	        }
	    MAX-ACCESS read-only
	    STATUS current
	    DESCRIPTION
        "This object represents the type of station."
	    ::= { oriStationStatTableEntry 6 }

    oriStationStatTableMACProtocol    OBJECT-TYPE
	    SYNTAX INTEGER
	        {
	            ieee802dot11(1),
	            ieee802dot11a(2),
	            ieee802dot11b(3),
	            worp(4)
	        }
	    MAX-ACCESS read-only
	    STATUS current
	    DESCRIPTION
        "This object represents the MAC protocol for this station."
	    ::= { oriStationStatTableEntry 7 }

    oriStationStatTableAdminStatus    OBJECT-TYPE
	    SYNTAX INTEGER
	        {
	            up(1),
	            down(2),
	            testing(3)
	        }
	    MAX-ACCESS read-only
	    STATUS current
	    DESCRIPTION
        "This object represents the administrative state for the station.  
        The testing(3) state indicates that no operational packets can 
        be passed."
	    ::= { oriStationStatTableEntry 8 }

    oriStationStatTableOperStatus    OBJECT-TYPE
	    SYNTAX INTEGER
	        {
	            up(1),
	            down(2),
	            testing(3)
	        }
	    MAX-ACCESS read-only
	    STATUS current
	    DESCRIPTION
        "This object represents the current operational state of the 
        interface.  The testing(3) state indicates that no operational 
        packets can be passed."
	    ::= { oriStationStatTableEntry 9 }

    oriStationStatTableLastChange    OBJECT-TYPE
	    SYNTAX TimeTicks
	    MAX-ACCESS read-only
	    STATUS current
	    DESCRIPTION
        "This object represents the value of sysUpTime at the time the 
        station entered its current operational state.  If the current 
        state was entered prior to the last re-initialization of the 
        local network management subsystem, then this object contains a 
        zero value."
	    ::= { oriStationStatTableEntry 10 }

    oriStationStatTableLastState    OBJECT-TYPE
	    SYNTAX INTEGER
	        {
	            unknown(1),
	            registering(2),
	            authenticating(3),
	            registered(4),
	            timeout(5),
	            aborded(6),
	            rejected(7),
	            linktest(8)
	        }
	    MAX-ACCESS read-only
	    STATUS current
	    DESCRIPTION
        "This object represents the last state of this station."
	    ::= { oriStationStatTableEntry 11 }

    oriStationStatTableInOctets    OBJECT-TYPE
	    SYNTAX Counter32
	    MAX-ACCESS read-only
	    STATUS current
	    DESCRIPTION
	        "The total number of octets received from the station, 
	        including framing characters."
	    ::= { oriStationStatTableEntry 12 }

    oriStationStatTableInUcastPkts    OBJECT-TYPE
	    SYNTAX Counter32
	    MAX-ACCESS read-only
	    STATUS current
	    DESCRIPTION
        "This object represents the number of unicast packets from the 
        station that are further processed by either by the bridge/router 
        or by the internal host."
	    ::= { oriStationStatTableEntry 13 }

    oriStationStatTableInNUcastPkts    OBJECT-TYPE
	    SYNTAX Counter32
	    MAX-ACCESS read-only
	    STATUS current
	    DESCRIPTION
        "This object represents the number of non-unicast packets 
        (i.e. broadcast or multicast) from the station that are further 
        processed by either by the bridge/router or by the internal host."
	    ::= { oriStationStatTableEntry 14 }

    oriStationStatTableInDiscards    OBJECT-TYPE
	    SYNTAX Counter32
	    MAX-ACCESS read-only
	    STATUS current
	    DESCRIPTION
        "This object represents the number of inbound packets which were 
        chosen to be discarded even though no errors had been detected to 
        prevent their being deliverable to the internal bridge/router or 
        the internal host.  One possible reason for discarding such a 
        packet could be to lack of buffer space."
	    ::= { oriStationStatTableEntry 15 }

    oriStationStatTableOutOctets    OBJECT-TYPE
	    SYNTAX Counter32
	    MAX-ACCESS read-only
	    STATUS current
	    DESCRIPTION
        "This object represents the total number of octets send to the 
        station, including framing characters."
	    ::= { oriStationStatTableEntry 16 }

    oriStationStatTableOutUcastPkts    OBJECT-TYPE
	    SYNTAX Counter32
	    MAX-ACCESS read-only
	    STATUS current
	    DESCRIPTION
        "This object represents the number of packets that the internal 
        bridge/router or the internal host requested be transmitted to the 
        station, including those that were discarded or not sent."
	    ::= { oriStationStatTableEntry 17 }

    oriStationStatTableOutNUcastPkts    OBJECT-TYPE
	    SYNTAX Counter32
	    MAX-ACCESS read-only
	    STATUS current
	    DESCRIPTION
        "This object represents the number of packets that the internal 
        bridge/router or the internal host requested be transmitted to a 
        non-unicast (i.e. broadcast or multicast) address that includes 
        the station.  This counter includes those packets that were 
        discarded or not sent."
	    ::= { oriStationStatTableEntry 18 }

    oriStationStatTableOutDiscards    OBJECT-TYPE
	    SYNTAX Counter32
	    MAX-ACCESS read-only
	    STATUS current
	    DESCRIPTION
        "This object represents the number of outbound packets which were 
        chosen to be discarded even though no errors had been detected to 
        prevent their being deliverable to the internal bridge/router or 
        the internal host.  One possible reason for discarding such a 
        packet could be to lack of buffer space."
	    ::= { oriStationStatTableEntry 19 }

    oriStationStatTableInSignal    OBJECT-TYPE
    SYNTAX Integer32 (-102..-10)
	    MAX-ACCESS read-only
	    STATUS current
	    DESCRIPTION
        "This object represents the current signal level calculated over 
        the inbound packets from this station. This variable indicates 
        the running average of the local signal level using the algorithm 
	        (3/4*oldvalue + 1/4*newvalue)."
	    ::= { oriStationStatTableEntry 20 }

    oriStationStatTableInNoise    OBJECT-TYPE
    SYNTAX Integer32 (-102..-10)
	    MAX-ACCESS read-only
	    STATUS current
	    DESCRIPTION
        "This object represents the current noise level calculated over 
        the inbound packets from this station. This variable indicates 
        the running average of the local noise level using the algorithm 
	        (3/4*oldvalue + 1/4*newvalue)."
	    ::= { oriStationStatTableEntry 21 }

    oriStationStatTableRemoteSignal    OBJECT-TYPE
    SYNTAX Integer32 (-102..-10)
	    MAX-ACCESS read-only
	    STATUS current
	    DESCRIPTION
        "This object represents the current remote signal level calculated 
        over the inbound packets from this station on the remote station. 
        This variable indicates the running average of the remote signal 
        level using the algorithm (3/4*oldvalue + 1/4*newvalue)."
	    ::= { oriStationStatTableEntry 22 }

    oriStationStatTableRemoteNoise    OBJECT-TYPE
    SYNTAX Integer32 (-102..-10)
	    MAX-ACCESS read-only
	    STATUS current
	    DESCRIPTION
        "This object represents the current remote noise level calculated 
        over the inbound packets from this station on the remote station. 
        This variable indicates the running average of the remote noise 
        level using the algorithm (3/4*oldvalue + 1/4*newvalue)."
	    ::= { oriStationStatTableEntry 23 }

    oriStationStatTableLastInPktTime    OBJECT-TYPE
	    SYNTAX TimeTicks
	    MAX-ACCESS read-only
	    STATUS current
	    DESCRIPTION
        "This object represents the value of sysUpTime at the time the 
        last packet from the remote station was received."
	    ::= { oriStationStatTableEntry 24 }

oriStationStatStatus OBJECT-TYPE
    SYNTAX INTEGER
        {
            enable(1),
            disable(2)
        }
    MAX-ACCESS read-write
    STATUS current
    DESCRIPTION
        "This object is used to enable or disable the monitoring of the 
        wireless station statistics."
    DEFVAL { disable }
    ::= { orinocoStationStatistics 2 }

--=============================================================================
-- The Simple Network Time Protocol (SNTP) Group: orinocoSNTP
--=============================================================================

oriSNTPStatus OBJECT-TYPE
    SYNTAX INTEGER
        {
            enable(1),
            disable(2)
        }
    MAX-ACCESS read-write
    STATUS current
    DESCRIPTION
        "This object is used to enable or disable the SNTP functionality."
    DEFVAL { disable }
    ::= { orinocoSNTP 1 }

oriSNTPPrimaryServerNameOrIPAddress OBJECT-TYPE
    SYNTAX DisplayString
    MAX-ACCESS read-write
    STATUS current
    DESCRIPTION
        "This object represents the primary SNTP server IP address or host 
        name."
    ::= { orinocoSNTP 2 }

oriSNTPSecondaryServerNameOrIPAddress OBJECT-TYPE
    SYNTAX DisplayString
    MAX-ACCESS read-write
    STATUS current
    DESCRIPTION
        "This object represents the secondary SNTP server IP address or host
        name."
    ::= { orinocoSNTP 3 }

oriSNTPTimeZone OBJECT-TYPE
	SYNTAX INTEGER
		{
		    dateline(1),	
			samoa(2),
			hawaii(3),
			alaska(4),
			pacific-us(5),
			mountain-us(6),
			arizona(7),
			central-us(8),
			mexico-city(9), 
			eastern-us(10),
			indiana(11),
			atlantic-canada(12),
			santiago(13),
			newfoundland(14),
			brasilia(15),
			buenos-aires(16),
			mid-atlantic(17),
			azores(18),
			london(19),
			western-europe(20),
			eastern-europe(21),
			cairo(22), 
			russia-iraq(23),
			iran(24),
			arabian(25),
			afghanistan(26),
			pakistan(27),
			india(28),
			bangladesh(29),
			burma(30),
			bangkok(31),
			australia-wt(32), 
			hong-kong(33),
			beijing(34),  
			japan-korea(35),
			australia-ct(36),
			australia-et(37),
			central-pacific(38),
			new-zealand(39),
			tonga(40),
			western-samoa(41)
		}
	MAX-ACCESS read-write
	STATUS current
	DESCRIPTION	
	    "This parameter is used for the device to know how to adjust GMT for 
	    local time."
	::= { orinocoSNTP 4 }

oriSNTPDateAndTime OBJECT-TYPE
    SYNTAX DisplayString
    MAX-ACCESS read-only
    STATUS current
    DESCRIPTION
        "This object represents the Date and Time.  The format of this object
        is the same as the DateAndTime textual convention."
    ::= { orinocoSNTP 5 }

oriSNTPDayLightSavingTime OBJECT-TYPE
    SYNTAX INTEGER
        {
            plus-two(1),
            plus-one(2),
			unchanged(3),
			minus-one(4),
			minus-two(5)
	    }
    MAX-ACCESS read-write
    STATUS current
    DESCRIPTION
		"This parameter indicates the number of hours to adjust for 
		Daylight Saving Time."       
	DEFVAL { unchanged }
	::= { orinocoSNTP 6 }

oriSNTPYear OBJECT-TYPE
    SYNTAX Integer32
    MAX-ACCESS read-write
    STATUS current
    DESCRIPTION
        "This object represents the year.  This object can be used to manually
        configure the year in case the Date and Time is not retrieved from an
        SNTP server."
    ::= { orinocoSNTP 7 }

oriSNTPMonth OBJECT-TYPE
    SYNTAX Integer32 (1..12)
    MAX-ACCESS read-write
    STATUS current
    DESCRIPTION
        "This object represents the month.  This object can be used to manually
        configure the month in case the Date and Time is not retrieved from an
        SNTP server."
    ::= { orinocoSNTP 8 }

oriSNTPDay OBJECT-TYPE
    SYNTAX Integer32 (1..31)
    MAX-ACCESS read-write
    STATUS current
    DESCRIPTION
        "This object represents the day of the month.  This object can be used 
        to manually configure the year in case the Date and Time is not 
        retrieved from an SNTP server."
    ::= { orinocoSNTP 9 }
    
oriSNTPHour OBJECT-TYPE
    SYNTAX Integer32 (0..23)
    MAX-ACCESS read-write
    STATUS current
    DESCRIPTION
        "This object represents the hour of day.  This object can be used 
        to manually configure the hour in case the Date and Time is not 
        retrieved from an SNTP server."
    ::= { orinocoSNTP 10 }

oriSNTPMinutes OBJECT-TYPE
    SYNTAX Integer32 (0..59)
    MAX-ACCESS read-write
    STATUS current
    DESCRIPTION
        "This object represents the minutes.  This object can be used to 
        manually configure the minutes in case the Date and Time is not 
        retrieved from an SNTP server."
    ::= { orinocoSNTP 11 }

oriSNTPSeconds OBJECT-TYPE
    SYNTAX Integer32 (0..59)
    MAX-ACCESS read-write
    STATUS current
    DESCRIPTION
        "This object represents the number of seconds.  This object can be used 
        to manually configure the seconds in case the Date and Time is not 
        retrieved from an SNTP server."
    ::= { orinocoSNTP 12 }
    
--=============================================================================
-- The Configuration Related Trap Group: oriConfigurationTraps
--=============================================================================

	oriConfigurationTraps    OBJECT-IDENTITY
	    STATUS current
	    DESCRIPTION
        "This is the configuration related trap/notification group."
	    ::= { orinocoTrap 2 }

	oriTrapIPAddrAssignmentNotConfigured    NOTIFICATION-TYPE
        OBJECTS { oriGenericTrapVariable, oriTrapVarMACAddress }
	    STATUS current
	    DESCRIPTION
		"This trap is generated when the IP Address Pool Assignment 
		Type has not been configured.
		Trap Severity Level: Major."
	    ::= { oriConfigurationTraps 0 1 }

	oriTrapRADIUSNotConfigured    NOTIFICATION-TYPE
        OBJECTS { oriGenericTrapVariable, oriTrapVarMACAddress }
        STATUS current
	    DESCRIPTION
		"This trap is generated when the RADIUS configuration objects 
		have not been configured.
		Trap Severity Level: Major."
	    ::= { oriConfigurationTraps 0 2 }

	oriTrapDNSIPNotConfigured    NOTIFICATION-TYPE
        OBJECTS { oriGenericTrapVariable, oriTrapVarMACAddress }
        STATUS current
        DESCRIPTION
		"This traps is generated when the DNS IP Address has not been 
		configured.
		Trap Severity Level: Major."
	    ::= { oriConfigurationTraps 0 3 }

	oriTrapWINSIPNotConfigured    NOTIFICATION-TYPE
        OBJECTS { oriGenericTrapVariable, oriTrapVarMACAddress }
        STATUS current
	    DESCRIPTION
		"This traps is generated when the WINS or NBNS IP Address has 
		not been configured.
		Trap Severity Level: Major."
	    ::= { oriConfigurationTraps 0 4 }

     oriTrapRADIUSAuthenticationNotConfigured NOTIFICATION-TYPE
        OBJECTS { oriGenericTrapVariable, oriTrapVarMACAddress }
        STATUS current
        DESCRIPTION
        "This trap is generated when the RADIUS authentication information
        has not been configured.
        Trap Severity Level: Major."
        ::= { oriConfigurationTraps 0 5 } 
        
     oriTrapRADIUSAccountingNotConfigured NOTIFICATION-TYPE
        OBJECTS { oriGenericTrapVariable, oriTrapVarMACAddress }
        STATUS current
        DESCRIPTION
        "This trap is generated when the RADIUS accounting information
        has not been configured.
        Trap Severity Level: Major."
        ::= { oriConfigurationTraps 0 6 }

     oriTrapDuplicateIPAddressEncountered NOTIFICATION-TYPE
        OBJECTS { oriGenericTrapVariable, oriTrapVarMACAddress }
        STATUS current
        DESCRIPTION
        "This trap is generated when the device has encountered another 
        network device with he same IP Address.
        Trap Severity Level: Major."
        ::= { oriConfigurationTraps 0 7 }

	oriTrapDHCPRelayServerTableNotConfigured    NOTIFICATION-TYPE
        STATUS current
	    DESCRIPTION
        "This trap is generated when the DHCP relay agent server table is 
        empty or not configured.
        Trap Severity Level: Major."
	    ::= { oriConfigurationTraps 0 8 }
  
oriTrapWORPIfNetworkSecretNotConfigured NOTIFICATION-TYPE
        STATUS current
	    DESCRIPTION
        "This trap is generated when the system network authentication 
        shared secret is not configured.
        Trap Severity Level: Major."
	    ::= { oriConfigurationTraps 0 9 }

oriTrapVLANIDInvalidConfiguration NOTIFICATION-TYPE
    OBJECTS { oriGenericTrapVariable, oriWirelessIfNetworkName,
              oriVLANIDTableIdentifier }
    STATUS current
    DESCRIPTION
        "This trap is generated when a VLAN ID configuration is invalid.
        Trap Severity Level: Major."
    ::= { oriConfigurationTraps 0 10 }

--=============================================================================
-- The Security Related Trap Group: oriSecurityTraps
--=============================================================================

	oriSecurityTraps    OBJECT-IDENTITY
	    STATUS current
	    DESCRIPTION
        "This is the security related trap/notification group."
	    ::= { orinocoTrap 3 }

	oriTrapInvalidEncryptionKey    NOTIFICATION-TYPE
        OBJECTS { oriTrapVarUnauthorizedClientMACAddress }
        STATUS current
	    DESCRIPTION
		"This trap is generated when an invalid encryption key has been 
		detected.
		Trap Severity Level: Critical."
	    ::= { oriSecurityTraps 0 1 }

	oriTrapAuthenticationFailure    NOTIFICATION-TYPE
        OBJECTS { oriTrapVarUnauthorizedClientMACAddress, 
                  oriTrapVarFailedAuthenticationType }
        STATUS current
	    DESCRIPTION
		"This trap is generated when a client authentication failure 
		has occurred.  The authentication failures can range from:
			    - MAC Access Control Table
			    - RADIUS MAC Authentication
			    - 802.1x Authentication specifying the EAP-Type
		    - WORP Mutual Authentication
		Trap Severity Level: Major."
	    ::= { oriSecurityTraps 0 2 }

	oriTrapUnauthorizedManagerDetected    NOTIFICATION-TYPE
        OBJECTS { oriTrapVarUnauthorizedManagerIPaddress, 
                  oriTrapVarUnAuthorizedManagerCount }
        STATUS current
	    DESCRIPTION
		"This trap is generated when an unauthorized manager has 
			attempted to view and/or modify parameters.
		Trap Severity Level: Major."
        ::= { oriSecurityTraps 0 3 }

--=============================================================================
-- The Wireless Interface Card Related Trap Group: oriWirelessIfTraps
--=============================================================================

	oriWirelessIfTraps   OBJECT-IDENTITY
        STATUS current
        DESCRIPTION
        "This is the wireless interface or wireless card related
        trap/notification group."
	    ::= { orinocoTrap 4 }

	oriTrapWLCNotPresent    NOTIFICATION-TYPE
        OBJECTS { oriTrapVarWirelessCard }
        STATUS current
	    DESCRIPTION
		"This trap is generated when a wireless interface/card is not 
		present in the device.
		Trap Severity Level: Informational."
	    ::= { oriWirelessIfTraps 0 1 }

	oriTrapWLCFailure    NOTIFICATION-TYPE
        OBJECTS { oriTrapVarWirelessCard }
        STATUS current
	    DESCRIPTION
		"This trap is generated when a general failure has occured with
		the wireless interface/card.
		Trap Severity Level: Critical."
	    ::= { oriWirelessIfTraps 0 2 }

	oriTrapWLCRemoval    NOTIFICATION-TYPE
        OBJECTS { oriTrapVarWirelessCard }
        STATUS current
	    DESCRIPTION	
		"This trap is generated when the wireless interface/card has been
		removed from the device.
		Trap Severity Level: Critical."
	    ::= { oriWirelessIfTraps 0 3 }

	oriTrapWLCIncompatibleFirmware    NOTIFICATION-TYPE
        OBJECTS { oriTrapVarWirelessCard }
        STATUS current
	    DESCRIPTION
		"This trap is generated when the firmware of the wireless 
		interface/card is incompatible.
		Trap Severity Level: Critical."
	    ::= { oriWirelessIfTraps 0 4 }

    oriTrapWLCVoltageDiscrepancy NOTIFICATION-TYPE
        OBJECTS { oriTrapVarWirelessCard }
        STATUS current
        DESCRIPTION
        "This trap is generated when a non 5 volt card or 3.3 volt 
        wireless interface/card is inserted in the device.
        Trap Severity Level: Critical."
        ::= { oriWirelessIfTraps 0 5 }
     
    oriTrapWLCIncompatibleVendor NOTIFICATION-TYPE
        OBJECTS { oriTrapVarWirelessCard }
        STATUS current
        DESCRIPTION
        "This trap is generated when an incompatible wireless vendor card 
        is inserted or present in the device.
        Trap Severity Level: Critical."
        ::= { oriWirelessIfTraps 0 6 }
        
    oriTrapWLCFirmwareDownloadFailure NOTIFICATION-TYPE
        OBJECTS { oriTrapVarWirelessCard }
        STATUS current
        DESCRIPTION
            "This trap is generated when a failure occurs during the firmware
        download process of the wireless interface/card.
        Trap Severity Level: Critical."
        ::= { oriWirelessIfTraps 0 7 }

    oriTrapWLCFirmwareFailure NOTIFICATION-TYPE
        OBJECTS { oriTrapVarWirelessCard, oriGenericTrapVariable }
        STATUS current
        DESCRIPTION
        "This trap is generated when a failure occurs in the wireless
        interface/card firmware.
        Trap Severity Level: Critical."
        ::= { oriWirelessIfTraps 0 8 }

oriTrapWLCRadarInterferenceDetected NOTIFICATION-TYPE
    OBJECTS { oriTrapVarWirelessCard, oriGenericTrapVariable }
    STATUS current
    DESCRIPTION
        "This trap is generated when radar interference is detected on the
        channel being used by the wireless interface.  The generic trap
        varible provides information on the channel where interference
        was detected.
        Trap Severity Level: Major."
    ::= { oriWirelessIfTraps 0 9 }

--=============================================================================
-- The Operational Related Trap Group: oriOperationalTraps
--=============================================================================

	oriOperationalTraps    OBJECT-IDENTITY
	    STATUS current
	    DESCRIPTION
        "This is the operational related trap group group."
	    ::= { orinocoTrap 5 }

	oriTrapWatchDogTimerExpired    NOTIFICATION-TYPE
        OBJECTS { oriGenericTrapVariable, oriTrapVarMACAddress,
                  oriTrapVarTaskSuspended }
        STATUS current
	    DESCRIPTION
		"This trap is generated when the software watch dog timer 
		has expired.  This can signify that a problem has occurred 
		with one or more software modules and the device will reboot 
		itself.
		Trap Severity Level: Critical."
	    ::= { oriOperationalTraps 0 1 }

	oriTrapRADIUSServerNotResponding    NOTIFICATION-TYPE
        OBJECTS { oriGenericTrapVariable }
        STATUS current
	    DESCRIPTION
		"This trap is generated when no response is received from the
		RADIUS server(s) for authentication requests sent from the RADIUS
		client in the device.
		Trap Severity Level: Major." 
	    ::= { oriOperationalTraps 0 2 }

	oriTrapModuleNotInitialized    NOTIFICATION-TYPE
        OBJECTS { oriGenericTrapVariable }
        STATUS current
	    DESCRIPTION
		"This trap is generated when a certain software or hardware module 
			has not been initialized or failed to be initialized.
		Trap Severity Level: Major."
	    ::= { oriOperationalTraps 0 3 }

	oriTrapChangeInAdminState    NOTIFICATION-TYPE
        OBJECTS { oriTrapVarMACAddress }
        STATUS current
	    DESCRIPTION
		"This trap is generated when the administration state of the 
			device is changes either from Normal to maintenance mode or 
			vice-versa.
		Trap Severity Level: Informational."
	    ::= { oriOperationalTraps 0 4 }

	oriTrapDeviceRebooting    NOTIFICATION-TYPE
        OBJECTS { oriTrapVarMACAddress }
        STATUS current
	    DESCRIPTION
		"This trap is generated when the device has received a request 
			to be rebooted.
		Trap Severity Level: Informational."
	    ::= { oriOperationalTraps 0 5 }

	oriTrapTaskSuspended    NOTIFICATION-TYPE
        OBJECTS { oriTrapVarTaskSuspended }
        STATUS current
	    DESCRIPTION
		"This trap is generated when a task in the device has suspended.
		Trap Severity Level: Critical."
	    ::= { oriOperationalTraps 0 6 }

	oriTrapBootPFailed NOTIFICATION-TYPE
        OBJECTS { oriTrapVarMACAddress }
        STATUS current
	    DESCRIPTION
	        "This trap is generated when a response to the BootP request is
	        not received, hence the access point device is not dynamically 
	        assigned an IP Address.
        Trap Severity Level: Major."
	    ::= { oriOperationalTraps 0 7 }

	oriTrapDHCPFailed NOTIFICATION-TYPE
        OBJECTS { oriTrapVarMACAddress }
        STATUS current
	    DESCRIPTION
	        "This trap is generated when a response to the DHCP client request
	        is not received, hence the access point device is not dynamically 
	        assigned an IP Address.
        Trap Severity Level: Major."
	    ::= { oriOperationalTraps 0 8 }
	    
	oriTrapDNSClientLookupFailure NOTIFICATION-TYPE
	    OBJECTS { oriGenericTrapVariable }
	    STATUS current
	    DESCRIPTION
	          "This trap is generated when the DNS client attempts to resolve a
        specified hostname (DNS lookup) and a failure occurs.  This could be
        the result of the DNS server being unreachable or returning an error
        for the hostname lookup.  This trap specified the hostname that was 
        being resolved.
        Trap Severity Level: Major."
	    ::= { oriOperationalTraps 0 9 }
	    
oriTrapSNTPFailure NOTIFICATION-TYPE
    STATUS current
    DESCRIPTION
        "This trap is generated when SNTP service is enabled and no response 
   		is received from the configured SNTP servers.
        Trap Severity Level: Major."
    ::= { oriOperationalTraps 0 10 }

--=============================================================================
-- The Flash Memory Related Trap Group: oriFlashTraps
--=============================================================================

	oriFlashTraps    OBJECT-IDENTITY
	    STATUS current
	    DESCRIPTION
        "This is the flash memory related trap group."
		::= { orinocoTrap 6 }

	oriTrapFlashMemoryEmpty    NOTIFICATION-TYPE
        STATUS current
	    DESCRIPTION
		"This trap is generated when there is no data present in flash
		memory - either on the flash card or the onboard flash memory.
		Trap Severity Level: Informational."
	    ::= { oriFlashTraps 0 1 }

	oriTrapFlashMemoryCorrupted    NOTIFICATION-TYPE
        STATUS current
	    DESCRIPTION
		"This trap is generated when the data content of flash memory is 
			corrupted.
		Trap Severity Level: Critical."
	    ::= { oriFlashTraps 0 2 }

--=============================================================================
-- The TFTP Related Trap Group: oriTFTPTraps
--=============================================================================

	oriTFTPTraps    OBJECT-IDENTITY
	    STATUS current
	    DESCRIPTION
        "This is the TFTP related trap group."
	    ::= { orinocoTrap 7 }

	oriTrapTFTPFailedOperation    NOTIFICATION-TYPE
        OBJECTS { oriTrapVarTFTPIPAddress, oriTrapVarTFTPFilename,
                  oriTrapVarTFTPOperation }
        STATUS current
	    DESCRIPTION
		"This trap is generated when a failure has occurred with the TFTP 
			operation.
		Trap Severity Level: Major."
	    ::= { oriTFTPTraps 0 1 }

	oriTrapTFTPOperationInitiated    NOTIFICATION-TYPE
        OBJECTS { oriTrapVarTFTPIPAddress, oriTrapVarTFTPFilename,
                  oriTrapVarTFTPOperation }        
        STATUS current
	    DESCRIPTION
		"This trap is generated when a TFTP operation has been initiated.
		Trap Severity Level: Informational."
		::= { oriTFTPTraps 0 2 }

	oriTrapTFTPOperationCompleted    NOTIFICATION-TYPE
        OBJECTS { oriTrapVarTFTPIPAddress, oriTrapVarTFTPFilename,
                  oriTrapVarTFTPOperation }
        STATUS current
	    DESCRIPTION
		"This trap is generated when a TFTP operation has been completed.
		Trap Severity Level: Informational."
		::= { oriTFTPTraps 0 3 }

--=============================================================================
-- The Miscellaneous Trap Group: oriMiscTraps
--=============================================================================

    oriMiscTraps    OBJECT-IDENTITY
        STATUS current
        DESCRIPTION
        "This is the miscellaneous trap group."
	    ::= { orinocoTrap 8 }

--=============================================================================
-- The Image Related Trap Group: oriImageTraps
--=============================================================================

	oriImageTraps OBJECT-IDENTITY
	    STATUS current
	    DESCRIPTION
        "This is the image related trap group."
	    ::= { orinocoTrap 9 }

	oriTrapZeroSizeImage NOTIFICATION-TYPE
        STATUS current
	    DESCRIPTION
        "This trap is generated when a zero size image is loaded on the 
        device.
        Trap Severity Level: Major."
	    ::= { oriImageTraps 0 1 }

	oriTrapInvalidImage NOTIFICATION-TYPE
        STATUS current
	    DESCRIPTION
        "This trap is generated when an invalid image is loaded on the
        device.
        Trap Severity Level: Major."
	    ::= { oriImageTraps 0 2 }

	oriTrapImageTooLarge NOTIFICATION-TYPE
        STATUS current
	    DESCRIPTION
        "This trap is generated when the image loaded on the device 
        exceeds the size limitation of flash.
        Trap Severity Level: Major."
	    ::= { oriImageTraps 0 3 }

	oriTrapIncompatibleImage NOTIFICATION-TYPE
        STATUS current
	    DESCRIPTION
        "This trap is generated when an incompatible image is loaded on 
        the device.
        Trap Severity Level: Major."
	    ::= { oriImageTraps 0 4 }

--=============================================================================
-- The ADSL Related Trap Group: oriADSLIfTraps
--=============================================================================

	oriADSLIfTraps   OBJECT-IDENTITY
        STATUS current
        DESCRIPTION
        "This is the ADSL interface related trap group."
	    ::= { orinocoTrap 10 }

	oriADSLIfLinkUp    NOTIFICATION-TYPE     
        STATUS current
	    DESCRIPTION
		"This trap is generated when ADSL connection is up."
	    ::= { oriADSLIfTraps 0 1 }

	oriADSLIfLinkDown    NOTIFICATION-TYPE      
        STATUS current
	    DESCRIPTION
	    "This trap is generated ADSL connection is down."
	    ::= { oriADSLIfTraps 0 2 }

--=============================================================================
-- The WORP Related Trap Group: oriWORPTraps
--=============================================================================
    
	oriWORPTraps    OBJECT-IDENTITY
	    STATUS current
	    DESCRIPTION
        "This is the WORP related trap group."
	    ::= { orinocoTrap 11 }
                                    
oriWORPStationRegister NOTIFICATION-TYPE
    OBJECTS { oriTrapVarInterface, oriTrapVarMACAddress } 
	    STATUS current
	    DESCRIPTION
        "This trap is generated when a WORP satellite has registered on
        and interface of a base; a satellite will not generate this trap,
        but use oriWORPLinkUp instead.  For the station indicated, the 
        oriStationStatTableOperStatus will be up.
        Trap Severity Level: Informational."
	    ::= { oriWORPTraps 0 1 }
                                  
oriWORPStationDeRegister NOTIFICATION-TYPE
    OBJECTS { oriTrapVarInterface, oriTrapVarMACAddress } 
        STATUS current
	    DESCRIPTION
        "This trap is generated when a WORP satellite has been deleted 
        from an interface of a base; a satellite will not generate this 
        trap, but use oriWORPLinkDown instead. For the station indicated, 
        the oriStationStatTableOperStatus will be down.
        Trap Severity Level: Informational."
	    ::= { oriWORPTraps 0 2 }
  
--=============================================================================
-- The System Feature based License Related Trap Group: oriSysFeatureTraps
--=============================================================================

oriSysFeatureTraps OBJECT-IDENTITY
    STATUS current
    DESCRIPTION
        "This is the System Feature based License related trap group."
    ::= { orinocoTrap 12 }

oriTrapIncompatibleLicenseFile NOTIFICATION-TYPE
    OBJECTS { oriGenericTrapVariable } 
    STATUS current
    DESCRIPTION
        "This trap is generated when a license file in the device's flash
        memory is not compatible with the current bootloader.
        Trap Severity Level: Major."
    ::= { oriSysFeatureTraps 0 1 }

oriTrapFeatureNotSupported NOTIFICATION-TYPE
    OBJECTS { oriSystemFeatureTableCode } 
        STATUS current
	    DESCRIPTION
        "This trap is generated when a feature present in the license 
        codes is not supported by the current embedded software image.
        A newer embedded software image could support the feature or 
        there are more license that needed.
        Trap Severity Level: Informational."
    ::= { oriSysFeatureTraps 0 2 } 

oriTrapZeroLicenseFiles NOTIFICATION-TYPE 
    STATUS current
    DESCRIPTION
        "This trap is generated when a single license file is not present 
        in flash.  This causes the device to operate in default mode 
        with very limited features enabled.
        Trap Severity Level: Critical."
    ::= { oriSysFeatureTraps 0 3 }

oriTrapInvalidLicenseFile NOTIFICATION-TYPE
    OBJECTS { oriGenericTrapVariable } 
    STATUS current
    DESCRIPTION
        "This trap is generated when a license file in the device's flash 
        memory has an invalid signature and will be ignored.
        Trap Severity Level: Minor."
    ::= { oriSysFeatureTraps 0 4 }

oriTrapUselessLicense NOTIFICATION-TYPE
    OBJECTS { oriGenericTrapVariable } 
    STATUS current
    DESCRIPTION
        "This trap is generated when a license code file does not contain 
        any valid feature code.  The probably reason for this is that 
        after verification, not any of the features was meant for this 
        units MAC address.
        Trap Severity Level: Informational."
    ::= { oriSysFeatureTraps 0 5 }

--=============================================================================
-- ORiNOCO MIBs End
--=============================================================================

END
