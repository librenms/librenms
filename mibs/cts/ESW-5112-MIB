ESW-5112-MIB DEFINITIONS ::= BEGIN

	IMPORTS
		MODULE-IDENTITY, OBJECT-TYPE, NOTIFICATION-TYPE, enterprises, Counter32, Integer32, Counter64, IpAddress
			FROM SNMPv2-SMI
		DisplayString
			FROM SNMPv2-TC
		sysLocation
			FROM SNMPv2-MIB
		ifIndex
			FROM IF-MIB;

	cts MODULE-IDENTITY
		LAST-UPDATED "202605291324Z"
		ORGANIZATION "Connection Technology Systems"
		CONTACT-INFO "Email: info@ctsystem.com"
		DESCRIPTION  "MIB module for cts devices."
		::= { enterprises 9304 }

	PhysAddress ::=	OCTET STRING

	-- This data type is used to model media addresses.  For many
	-- types of media, this will be in a binary representation.
	-- For example, an ethernet address would be represented as
	-- a string of 6 octets.

	-- All representations of MAC addresses in this MIB Module use,
	-- as a textual convention (i.e., this convention does not affect
	-- their encoding), the data type:

	MacAddress ::= OCTET STRING (SIZE (6))      -- a 6 octet address in
	                                            -- the "canonical" order

	VLANPortMember ::= DisplayString (SIZE (0..27))

	swh
		OBJECT IDENTIFIER ::= { cts 100 }

	esw5112
		OBJECT IDENTIFIER ::= { swh 51122 }


-- Main

	swhSystemInformation
		OBJECT IDENTIFIER ::= { esw5112 1 }

	swhUserAccount
		OBJECT IDENTIFIER ::= { esw5112 2 }

	swhNetworkManagement
		OBJECT IDENTIFIER ::= { esw5112 3 }

	swhSwitchManagement
		OBJECT IDENTIFIER ::= { esw5112 4 }

	swhSwitchMonitor
		OBJECT IDENTIFIER ::= { esw5112 5 }

	swhSystemUtility
		OBJECT IDENTIFIER ::= { esw5112 6 }

	swhNewBootUpImage OBJECT-TYPE
		SYNTAX      INTEGER { image1(1), image2(2) }
		MAX-ACCESS  read-write
		STATUS      current
		DESCRIPTION
			"New Boot Up Image."
		::= { esw5112 15 }

	swhSaveConfiguration OBJECT-TYPE
		SYNTAX      INTEGER { normal(0), save(1) }
		MAX-ACCESS  read-write
		STATUS      current
		DESCRIPTION
			"Save Configuration to Flash ROM. (set 1 to execute this function)"
		::= { esw5112 7 }

	swhResetSystem OBJECT-TYPE
		SYNTAX      INTEGER { normal(0), reset(1) }
		MAX-ACCESS  read-write
		STATUS      current
		DESCRIPTION
			"Reset System. (set 1 to execute this function)"
		::= { esw5112 8 }

	switchTraps
		OBJECT IDENTIFIER ::= { esw5112 9 }

	swhEthernetOAM
		OBJECT IDENTIFIER ::= { esw5112 24 }


-- SystemInformation(1)

	swhCompanyInfo
		OBJECT IDENTIFIER ::= { swhSystemInformation 1 }

	swhHardwareInfo
		OBJECT IDENTIFIER ::= { swhSystemInformation 2 }


-- SystemInformation(1).CompanyInfo(1)

	swhCompanyName OBJECT-TYPE
		SYNTAX      DisplayString
		MAX-ACCESS  read-write
		STATUS      current
		DESCRIPTION
			"Company Name."
		::= { swhCompanyInfo 1 }

	swhDHCPVendorID OBJECT-TYPE
		SYNTAX      DisplayString
		MAX-ACCESS  read-write
		STATUS      current
		DESCRIPTION
			"DHCP Vendor ID."
		::= { swhCompanyInfo 7 }

	swhCLIHostname OBJECT-TYPE
		SYNTAX      DisplayString
		MAX-ACCESS  read-write
		STATUS      current
		DESCRIPTION
			"CLI Hostname."
		::= { swhCompanyInfo 6 }

	swhSyncHostnameToSysname OBJECT-TYPE
		SYNTAX      INTEGER { disable(0), enable(1) }
		MAX-ACCESS  read-write
		STATUS      current
		DESCRIPTION
			"Sync Host Name to System Name."
		::= { swhCompanyInfo 8 }


-- SystemInformation(1).HardwareInfo(2)

	swhModelName OBJECT-TYPE
		SYNTAX      DisplayString
		MAX-ACCESS  read-only
		STATUS      current
		DESCRIPTION
			"Model Name."
		::= { swhHardwareInfo 1 }

	swhBootUpImage OBJECT-TYPE
		SYNTAX      DisplayString
		MAX-ACCESS  read-only
		STATUS      current
		DESCRIPTION
			"Boot Up Image."
		::= { swhHardwareInfo 40 }

	swhNextBootUpImage OBJECT-TYPE
		SYNTAX      DisplayString
		MAX-ACCESS  read-only
		STATUS      current
		DESCRIPTION
			"Next Boot Up Image."
		::= { swhHardwareInfo 41 }

	swhImage1FirmwareVersion OBJECT-TYPE
		SYNTAX      DisplayString
		MAX-ACCESS  read-only
		STATUS      current
		DESCRIPTION
			"Image1 Firmware Version."
		::= { swhHardwareInfo 45 }

	swhImage2FirmwareVersion OBJECT-TYPE
		SYNTAX      DisplayString
		MAX-ACCESS  read-only
		STATUS      current
		DESCRIPTION
			"Image2 Firmware Version."
		::= { swhHardwareInfo 46 }

	swhMBVersion OBJECT-TYPE
		SYNTAX      DisplayString
		MAX-ACCESS  read-only
		STATUS      current
		DESCRIPTION
			"Main Board Version."
		::= { swhHardwareInfo 9 }

	swhSerialNumber OBJECT-TYPE
		SYNTAX      DisplayString
		MAX-ACCESS  read-only
		STATUS      current
		DESCRIPTION
			"Serial number of this device."
		::= { swhHardwareInfo 14 }

	swhDateCode OBJECT-TYPE
		SYNTAX      DisplayString
		MAX-ACCESS  read-only
		STATUS      current
		DESCRIPTION
			"The day of producing this device."
		::= { swhHardwareInfo 15 }

	swhCPUTemperature OBJECT-TYPE
		SYNTAX      Integer32 (-2147483648..2147483647)
		MAX-ACCESS  read-only
		STATUS      current
		DESCRIPTION
			"Current CPU Temperature(1/10 C)."
		::= { swhHardwareInfo 20 }

	swhPowerSupplyA OBJECT-TYPE
		SYNTAX      INTEGER { na(0), installed(1), not-installed(2) }
		MAX-ACCESS  read-only
		STATUS      current
		DESCRIPTION
			"Module A Power Supply exist or not."
		::= { swhHardwareInfo 24 }

	swhPowerSupplyAType OBJECT-TYPE
		SYNTAX      INTEGER { na(0), dc(1), ac(2) }
		MAX-ACCESS  read-only
		STATUS      current
		DESCRIPTION
			"Module A is DC or AC Power Supply."
		::= { swhHardwareInfo 25 }

	swhPowerSupplyAState OBJECT-TYPE
		SYNTAX      INTEGER { na(0), active(1), ng(2), ac-cut(3) }
		MAX-ACCESS  read-only
		STATUS      current
		DESCRIPTION
			"Module A Power Supply State."
		::= { swhHardwareInfo 26 }

	swhPowerSupplyB OBJECT-TYPE
		SYNTAX      INTEGER { na(0), installed(1), not-installed(2) }
		MAX-ACCESS  read-only
		STATUS      current
		DESCRIPTION
			"Module B Power Supply exist or not."
		::= { swhHardwareInfo 28 }

	swhPowerSupplyBType OBJECT-TYPE
		SYNTAX      INTEGER { na(0), dc(1), ac(2), battery(3) }
		MAX-ACCESS  read-only
		STATUS      current
		DESCRIPTION
			"Module B is DC or AC Power Supply."
		::= { swhHardwareInfo 29 }

	swhPowerSupplyBState OBJECT-TYPE
		SYNTAX      INTEGER { na(0), active(1), ng(2) }
		MAX-ACCESS  read-only
		STATUS      current
		DESCRIPTION
			"Module B Power Supply State."
		::= { swhHardwareInfo 30 }


-- UserAccount(2).UserTable(1)

	swhUserTable OBJECT-TYPE
		SYNTAX      SEQUENCE OF SwhUserEntry
		MAX-ACCESS  not-accessible
		STATUS      current
		DESCRIPTION
			"Table of user information."
		::= { swhUserAccount 1 }

	-- Table Entry
	swhUserEntry OBJECT-TYPE
		SYNTAX      SwhUserEntry
		MAX-ACCESS  not-accessible
		STATUS      current
		DESCRIPTION
			"An entry in the table, containing information about user."
		INDEX    { swhUserIndex }
		::= { swhUserTable 1 }

	SwhUserEntry ::=
		SEQUENCE {
			swhUserIndex
				INTEGER,
			swhUserEnable
				INTEGER,
			swhUserName
				DisplayString,
			swhUserPassword
				DisplayString,
			swhUserDescription
				DisplayString,
			swhUserConsoleLevel
				INTEGER
		}

	swhUserIndex OBJECT-TYPE
		SYNTAX      INTEGER (0..2147483647)
		MAX-ACCESS  not-accessible
		STATUS      current
		DESCRIPTION
			"A unique value for each index."
		::= { swhUserEntry 1 }

	swhUserEnable OBJECT-TYPE
		SYNTAX      INTEGER { disable(0), enable(1) }
		MAX-ACCESS  read-only
		STATUS      current
		DESCRIPTION
			"Enable."
		::= { swhUserEntry 3 }

	swhUserName OBJECT-TYPE
		SYNTAX      DisplayString
		MAX-ACCESS  read-only
		STATUS      current
		DESCRIPTION
			"Name."
		::= { swhUserEntry 4 }

	swhUserPassword OBJECT-TYPE
		SYNTAX      DisplayString
		MAX-ACCESS  read-only
		STATUS      current
		DESCRIPTION
			"Password."
		::= { swhUserEntry 5 }

	swhUserDescription OBJECT-TYPE
		SYNTAX      DisplayString
		MAX-ACCESS  read-only
		STATUS      current
		DESCRIPTION
			"Description."
		::= { swhUserEntry 6 }

	swhUserConsoleLevel OBJECT-TYPE
		SYNTAX      INTEGER { readonly(1), readwrite(2), administrator(3) }
		MAX-ACCESS  read-only
		STATUS      current
		DESCRIPTION
			"Console Level."
		::= { swhUserEntry 10 }


-- UserAccount(2).UserPasswordEncryption(4)

	swhUserPasswordEncryption OBJECT-TYPE
		SYNTAX      INTEGER { disable(0), md5(1), aes-128(2) }
		MAX-ACCESS  read-only
		STATUS      current
		DESCRIPTION
			"Password Encryption."
		::= { swhUserAccount 4 }


-- NetworkManagement(3)

	swhNetworkConfiguration
		OBJECT IDENTIFIER ::= { swhNetworkManagement 1 }

	swhSystemServiceConfiguration
		OBJECT IDENTIFIER ::= { swhNetworkManagement 2 }

	swhRADIUSTACACS
		OBJECT IDENTIFIER ::= { swhNetworkManagement 11 }

	swhAuth
		OBJECT IDENTIFIER ::= { swhNetworkManagement 12 }

	swhRS232TelnetConsoleConfiguration
		OBJECT IDENTIFIER ::= { swhNetworkManagement 3 }

	swhTimeServerConfiguration
		OBJECT IDENTIFIER ::= { swhNetworkManagement 7 }

	swhGlobalSetup
		OBJECT IDENTIFIER ::= { swhNetworkManagement 14 }

	swhDeviceCommunity
		OBJECT IDENTIFIER ::= { swhNetworkManagement 4 }

	swhTrapInformDestination
		OBJECT IDENTIFIER ::= { swhNetworkManagement 5 }

	swhTrapInformConfiguration
		OBJECT IDENTIFIER ::= { swhNetworkManagement 6 }

	swhSyslogConfiguration
		OBJECT IDENTIFIER ::= { swhNetworkManagement 8 }

	swhDHCPClientSetup
		OBJECT IDENTIFIER ::= { swhNetworkManagement 13 }


-- NetworkManagement(3).NetworkConfiguration(1)

	swhNetIPv4En OBJECT-TYPE
		SYNTAX      INTEGER { disable(0), enable(1) }
		MAX-ACCESS  read-write
		STATUS      current
		DESCRIPTION
			"IPv4 process."
		::= { swhNetworkConfiguration 8 }

	swhNetMacAddr OBJECT-TYPE
		SYNTAX      MacAddress
		MAX-ACCESS  read-only
		STATUS      current
		DESCRIPTION
			"The media-dependent 'physical' address."
		::= { swhNetworkConfiguration 1 }

	swhNetType OBJECT-TYPE
		SYNTAX      INTEGER { dhcp(0), manual(1) }
		MAX-ACCESS  read-write
		STATUS      current
		DESCRIPTION
			"Auto will get ip from DHCP."
		::= { swhNetworkConfiguration 2 }

	swhNetDHCPAutoRecycle OBJECT-TYPE
		SYNTAX      INTEGER { disable(0), enable(1) }
		MAX-ACCESS  read-write
		STATUS      current
		DESCRIPTION
			"DHCP Auto Recycle."
		::= { swhNetworkConfiguration 24 }

	swhNetDHCPAutoRecyclePortList OBJECT-TYPE
		SYNTAX      DisplayString
		MAX-ACCESS  read-write
		STATUS      current
		DESCRIPTION
			"DHCP Auto Recycle Port List."
		::= { swhNetworkConfiguration 25 }

	swhNetDHCPRecycle OBJECT-TYPE
		SYNTAX      INTEGER { normal(0), recycle(1) }
		MAX-ACCESS  read-write
		STATUS      current
		DESCRIPTION
			"DHCP Recycle."
		::= { swhNetworkConfiguration 23 }

	swhNetDHCPTagAlternation OBJECT-TYPE
		SYNTAX      INTEGER { disable(0), enable(1) }
		MAX-ACCESS  read-write
		STATUS      current
		DESCRIPTION
			"DHCP Tag-alternation."
		::= { swhNetworkConfiguration 57 }

	swhNetDHCPTagAlternationPortList OBJECT-TYPE
		SYNTAX      DisplayString
		MAX-ACCESS  read-write
		STATUS      current
		DESCRIPTION
			"DHCP Tag-alternation Port List."
		::= { swhNetworkConfiguration 58 }

	swhNetDHCPTagAlternationState OBJECT-TYPE
		SYNTAX      DisplayString
		MAX-ACCESS  read-only
		STATUS      current
		DESCRIPTION
			"DHCP Tag-alternation State."
		::= { swhNetworkConfiguration 59 }

	swhNetIPAddr OBJECT-TYPE
		SYNTAX      IpAddress
		MAX-ACCESS  read-write
		STATUS      current
		DESCRIPTION
			"The IP address to which this entry's addressing information pertains."
		::= { swhNetworkConfiguration 3 }

	swhNetIPMask OBJECT-TYPE
		SYNTAX      IpAddress
		MAX-ACCESS  read-write
		STATUS      current
		DESCRIPTION
			"The subnet mask associated with the IP address of 
			 this entry.  The value of the mask is an IP 
			 address with all the network bits set to 1 and all 
			 the hosts bits set to 0."
		::= { swhNetworkConfiguration 4 }

	swhNetGateway OBJECT-TYPE
		SYNTAX      IpAddress
		MAX-ACCESS  read-write
		STATUS      current
		DESCRIPTION
			"Gateway."
		::= { swhNetworkConfiguration 5 }

	swhNetCurrentIPAddr OBJECT-TYPE
		SYNTAX      IpAddress
		MAX-ACCESS  read-only
		STATUS      current
		DESCRIPTION
			"The Current IP address to which this entry's addressing information pertains."
		::= { swhNetworkConfiguration 10 }

	swhNetCurrentIPMask OBJECT-TYPE
		SYNTAX      IpAddress
		MAX-ACCESS  read-only
		STATUS      current
		DESCRIPTION
			"The Current subnet mask associated with the IP address of 
			 this entry.  The value of the mask is an IP 
			 address with all the network bits set to 1 and all 
			 the hosts bits set to 0."
		::= { swhNetworkConfiguration 11 }

	swhNetCurrentGateway OBJECT-TYPE
		SYNTAX      IpAddress
		MAX-ACCESS  read-only
		STATUS      current
		DESCRIPTION
			"Current Gateway."
		::= { swhNetworkConfiguration 12 }

	swhNetIPSourceBinding OBJECT-TYPE
		SYNTAX      INTEGER { disable(0), enable(1) }
		MAX-ACCESS  read-write
		STATUS      current
		DESCRIPTION
			"IP Source Binding."
		::= { swhNetworkConfiguration 20 }


-- NetworkManagement(3).NetworkConfiguration(1).IPSourceBindingTable(21)

	swhNetIPSourceBindingTable OBJECT-TYPE
		SYNTAX      SEQUENCE OF SwhNetIPSourceBindingEntry
		MAX-ACCESS  not-accessible
		STATUS      current
		DESCRIPTION
			"Table of Security IP."
		::= { swhNetworkConfiguration 21 }

	-- Table Entry
	swhNetIPSourceBindingEntry OBJECT-TYPE
		SYNTAX      SwhNetIPSourceBindingEntry
		MAX-ACCESS  not-accessible
		STATUS      current
		DESCRIPTION
			"An entry in the table, containing information about ip source binding."
		INDEX    { swhNetIPSourceBindingIndex }
		::= { swhNetIPSourceBindingTable 1 }

	SwhNetIPSourceBindingEntry ::=
		SEQUENCE {
			swhNetIPSourceBindingIndex
				INTEGER,
			swhNetIPSourceBindingState
				INTEGER,
			swhNetIPSourceBindingIPAddress
				DisplayString,
			swhNetIPSourceBindingIPv6Address
				DisplayString,
			swhNetIPSourceBindingPrefixLength
				INTEGER,
			swhNetIPSourceBindingDelete
				INTEGER
		}

	swhNetIPSourceBindingIndex OBJECT-TYPE
		SYNTAX      INTEGER (0..2147483647)
		MAX-ACCESS  not-accessible
		STATUS      current
		DESCRIPTION
			"A unique value for each index."
		::= { swhNetIPSourceBindingEntry 1 }

	swhNetIPSourceBindingState OBJECT-TYPE
		SYNTAX      INTEGER { disable(0), enable(1) }
		MAX-ACCESS  read-write
		STATUS      current
		DESCRIPTION
			"Security IP State."
		::= { swhNetIPSourceBindingEntry 3 }

	swhNetIPSourceBindingIPAddress OBJECT-TYPE
		SYNTAX      DisplayString
		MAX-ACCESS  read-write
		STATUS      current
		DESCRIPTION
			"Security IPv4 Address."
		::= { swhNetIPSourceBindingEntry 4 }

	swhNetIPSourceBindingIPv6Address OBJECT-TYPE
		SYNTAX      DisplayString
		MAX-ACCESS  read-write
		STATUS      current
		DESCRIPTION
			"Security IPv6 Address."
		::= { swhNetIPSourceBindingEntry 5 }

	swhNetIPSourceBindingPrefixLength OBJECT-TYPE
		SYNTAX      INTEGER (10..128)
		MAX-ACCESS  read-write
		STATUS      current
		DESCRIPTION
			"Security IP Prefix Length."
		::= { swhNetIPSourceBindingEntry 8 }

	swhNetIPSourceBindingDelete OBJECT-TYPE
		SYNTAX      INTEGER { normal(0), delete(1) }
		MAX-ACCESS  read-write
		STATUS      current
		DESCRIPTION
			"Delete this entry."
		::= { swhNetIPSourceBindingEntry 10 }


-- NetworkManagement(3).NetworkConfiguration(1).NetIPv6(32)

	swhNetIPv6En OBJECT-TYPE
		SYNTAX      INTEGER { disable(0), enable(1) }
		MAX-ACCESS  read-write
		STATUS      current
		DESCRIPTION
			"Enable / Disable IPv6 address."
		::= { swhNetworkConfiguration 32 }

	swhNetIPv6AutoConfig OBJECT-TYPE
		SYNTAX      INTEGER { disable(0), enable(1) }
		MAX-ACCESS  read-write
		STATUS      current
		DESCRIPTION
			"Configuration of IPv6 addresses using stateless autoconfig."
		::= { swhNetworkConfiguration 33 }

	swhNetIPv6LinkLocalAddr OBJECT-TYPE
		SYNTAX      DisplayString
		MAX-ACCESS  read-write
		STATUS      current
		DESCRIPTION
			"The IPv6 link-local address to which this entry's addressing information pertains."
		::= { swhNetworkConfiguration 34 }

	swhNetIPv6GlobalAddr OBJECT-TYPE
		SYNTAX      DisplayString
		MAX-ACCESS  read-write
		STATUS      current
		DESCRIPTION
			"The IPv6 address to which this entry's addressing information pertains."
		::= { swhNetworkConfiguration 35 }

	swhNetIPv6Gateway OBJECT-TYPE
		SYNTAX      DisplayString
		MAX-ACCESS  read-write
		STATUS      current
		DESCRIPTION
			"IPv6 Gateway."
		::= { swhNetworkConfiguration 36 }

	swhNetCurrentIPv6LinklocalAddr OBJECT-TYPE
		SYNTAX      DisplayString
		MAX-ACCESS  read-only
		STATUS      current
		DESCRIPTION
			"Current IPv6 link-local address."
		::= { swhNetworkConfiguration 39 }

	swhNetCurrentIPv6GatewayAddr OBJECT-TYPE
		SYNTAX      DisplayString
		MAX-ACCESS  read-only
		STATUS      current
		DESCRIPTION
			"Current IPv6 Gateway address."
		::= { swhNetworkConfiguration 40 }

	swhNetDHCPv6 OBJECT-TYPE
		SYNTAX      INTEGER { disable(0), auto(1), force(2) }
		MAX-ACCESS  read-write
		STATUS      current
		DESCRIPTION
			"Auto will get IPv6 from DHCPv6."
		::= { swhNetworkConfiguration 37 }

	swhNetRapidCommit OBJECT-TYPE
		SYNTAX      INTEGER { disable(0), enable(1) }
		MAX-ACCESS  read-write
		STATUS      current
		DESCRIPTION
			"Set DHCPv6 rapid-commit."
		::= { swhNetworkConfiguration 38 }

	swhNetCurrentDHCPv6DUID OBJECT-TYPE
		SYNTAX      DisplayString
		MAX-ACCESS  read-only
		STATUS      current
		DESCRIPTION
			"DHCPv6 Unique Identifier. (DUID)"
		::= { swhNetworkConfiguration 41 }


-- NetworkManagement(3).SystemServiceConfiguration(2)

	swhServiceTelnetThreadEn OBJECT-TYPE
		SYNTAX      INTEGER { disable(0), enable(1) }
		MAX-ACCESS  read-write
		STATUS      current
		DESCRIPTION
			"Telnet Thread."
		::= { swhSystemServiceConfiguration 1 }

	swhServiceSSHThreadEn OBJECT-TYPE
		SYNTAX      INTEGER { disable(0), enable(1) }
		MAX-ACCESS  read-write
		STATUS      current
		DESCRIPTION
			"SSH Thread."
		::= { swhSystemServiceConfiguration 10 }

	swhServiceSNMPThreadEn OBJECT-TYPE
		SYNTAX      INTEGER { disable(0), enable(1) }
		MAX-ACCESS  read-write
		STATUS      current
		DESCRIPTION
			"SNMP Thread."
		::= { swhSystemServiceConfiguration 3 }

	swhServiceWebThreadEn OBJECT-TYPE
		SYNTAX      INTEGER { disable(0), http(1), https(2) }
		MAX-ACCESS  read-write
		STATUS      current
		DESCRIPTION
			"Web Thread."
		::= { swhSystemServiceConfiguration 4 }

	swhServiceConsolePortThreadEn OBJECT-TYPE
		SYNTAX      INTEGER { disable(0), enable(1) }
		MAX-ACCESS  read-write
		STATUS      current
		DESCRIPTION
			"Console Port Thread."
		::= { swhSystemServiceConfiguration 12 }


-- NetworkManagement(3).RS232TelnetConsoleConfiguration(3)

	swhRS232BaudRate OBJECT-TYPE
		SYNTAX      INTEGER
		MAX-ACCESS  read-only
		STATUS      current
		DESCRIPTION
			"RS232 Baud Rate (bps). (9600 14400 19200 38400 57600 115200)"
		::= { swhRS232TelnetConsoleConfiguration 2 }

	swhRS232StopBits OBJECT-TYPE
		SYNTAX      INTEGER { x1(1), x1-5(2), x2(3) }
		MAX-ACCESS  read-only
		STATUS      current
		DESCRIPTION
			"RS232 Stop Bits."
		::= { swhRS232TelnetConsoleConfiguration 3 }

	swhRS232ParityCheck OBJECT-TYPE
		SYNTAX      INTEGER { none(0), even(1), odd(2), mark(3), space(4) }
		MAX-ACCESS  read-only
		STATUS      current
		DESCRIPTION
			"RS232 Parity Check."
		::= { swhRS232TelnetConsoleConfiguration 4 }

	swhRS232WordLength OBJECT-TYPE
		SYNTAX      INTEGER
		MAX-ACCESS  read-only
		STATUS      current
		DESCRIPTION
			"RS232 Word Length. (5 6 7 8)"
		::= { swhRS232TelnetConsoleConfiguration 5 }

	swhRS232FlowControl OBJECT-TYPE
		SYNTAX      INTEGER { none(0), hardware(1) }
		MAX-ACCESS  read-only
		STATUS      current
		DESCRIPTION
			"RS232 Flow Control."
		::= { swhRS232TelnetConsoleConfiguration 6 }

	swhTelnetPort OBJECT-TYPE
		SYNTAX      INTEGER (1..65535)
		MAX-ACCESS  read-write
		STATUS      current
		DESCRIPTION
			"Telnet Port. (1-65535)"
		::= { swhRS232TelnetConsoleConfiguration 8 }

	swhCLITimeOutTime OBJECT-TYPE
		SYNTAX      INTEGER (1..1440)
		MAX-ACCESS  read-write
		STATUS      current
		DESCRIPTION
			"CLI Time Out time. (1-1440)"
		::= { swhRS232TelnetConsoleConfiguration 11 }

	swhCLITimeOutTimeUnit OBJECT-TYPE
		SYNTAX      INTEGER { seconds(0), minutes(1) }
		MAX-ACCESS  read-write
		STATUS      current
		DESCRIPTION
			"CLI Time Out Unit. (0 : seconds  1 : minutes)"
		::= { swhRS232TelnetConsoleConfiguration 12 }

	swhWebTimeOutTime OBJECT-TYPE
		SYNTAX      INTEGER (1..1440)
		MAX-ACCESS  read-write
		STATUS      current
		DESCRIPTION
			"Web Time Out time. (1-1440)"
		::= { swhRS232TelnetConsoleConfiguration 13 }

	swhConsolePortFailRetry OBJECT-TYPE
		SYNTAX      INTEGER (1..10)
		MAX-ACCESS  read-write
		STATUS      current
		DESCRIPTION
			"Console port fail retry. (1-10)"
		::= { swhRS232TelnetConsoleConfiguration 14 }

	swhConsolePortFailBlockTime OBJECT-TYPE
		SYNTAX      INTEGER (1..120)
		MAX-ACCESS  read-write
		STATUS      current
		DESCRIPTION
			"Console port fail Block Time. (1-120)"
		::= { swhRS232TelnetConsoleConfiguration 15 }


-- NetworkManagement(3).DeviceCommunity(4).AgentTable(1)

	swhAgentTable OBJECT-TYPE
		SYNTAX      SEQUENCE OF SwhAgentEntry
		MAX-ACCESS  not-accessible
		STATUS      current
		DESCRIPTION
			"Table of agent."
		::= { swhDeviceCommunity 1 }

	-- Table Entry
	swhAgentEntry OBJECT-TYPE
		SYNTAX      SwhAgentEntry
		MAX-ACCESS  not-accessible
		STATUS      current
		DESCRIPTION
			"An entry in the table, containing information about SNMP agent."
		INDEX    { swhAgentIndex }
		::= { swhAgentTable 1 }

	SwhAgentEntry ::=
		SEQUENCE {
			swhAgentIndex
				INTEGER,
			swhAgentValid
				INTEGER,
			swhAgentEnable
				INTEGER,
			swhAgentCommunity
				DisplayString,
			swhAgentDescription
				DisplayString,
			swhAgentSNMPLevel
				INTEGER,
			swhAgentDelete
				INTEGER
		}

	swhAgentIndex OBJECT-TYPE
		SYNTAX      INTEGER (0..2147483647)
		MAX-ACCESS  not-accessible
		STATUS      current
		DESCRIPTION
			"A unique value for each index."
		::= { swhAgentEntry 1 }

	swhAgentValid OBJECT-TYPE
		SYNTAX      INTEGER { invalid(0), valid(1) }
		MAX-ACCESS  read-only
		STATUS      current
		DESCRIPTION
			"This entry is valid or invalid."
		::= { swhAgentEntry 2 }

	swhAgentEnable OBJECT-TYPE
		SYNTAX      INTEGER { disable(0), enable(1) }
		MAX-ACCESS  read-write
		STATUS      current
		DESCRIPTION
			"Enable."
		::= { swhAgentEntry 3 }

	swhAgentCommunity OBJECT-TYPE
		SYNTAX      DisplayString
		MAX-ACCESS  read-write
		STATUS      current
		DESCRIPTION
			"SNMP community Name."
		::= { swhAgentEntry 4 }

	swhAgentDescription OBJECT-TYPE
		SYNTAX      DisplayString
		MAX-ACCESS  read-write
		STATUS      current
		DESCRIPTION
			"Description."
		::= { swhAgentEntry 6 }

	swhAgentSNMPLevel OBJECT-TYPE
		SYNTAX      INTEGER { readonly(1), readwrite(2), administrator(3) }
		MAX-ACCESS  read-write
		STATUS      current
		DESCRIPTION
			"SNMP Level."
		::= { swhAgentEntry 9 }

	swhAgentDelete OBJECT-TYPE
		SYNTAX      INTEGER { normal(0), delete(1) }
		MAX-ACCESS  read-write
		STATUS      current
		DESCRIPTION
			"Delete this entry."
		::= { swhAgentEntry 10 }


-- NetworkManagement(3).DeviceCommunity(4).SNMPv3USMUser(5)

	swhSNMPv3USMUser
		OBJECT IDENTIFIER ::= { swhDeviceCommunity 5 }

	swhSNMPv3USMUserTable OBJECT-TYPE
		SYNTAX      SEQUENCE OF SwhSNMPv3USMUserEntry
		MAX-ACCESS  not-accessible
		STATUS      current
		DESCRIPTION
			"Table of SNMPv3 USM user."
		::= { swhSNMPv3USMUser 1 }

	-- Table Entry
	swhSNMPv3USMUserEntry OBJECT-TYPE
		SYNTAX      SwhSNMPv3USMUserEntry
		MAX-ACCESS  not-accessible
		STATUS      current
		DESCRIPTION
			"An entry in the table, containing information about SNMPv3 USM user."
		INDEX    { swhSNMPv3USMUserIndex }
		::= { swhSNMPv3USMUserTable 1 }

	swhSNMPv3Encryption OBJECT-TYPE
		SYNTAX      INTEGER { disable(0), aes-128(1) }
		MAX-ACCESS  read-write
		STATUS      current
		DESCRIPTION
			"SNMPv3 Encryption."
		::= { swhSNMPv3USMUser 2 }

	SwhSNMPv3USMUserEntry ::=
		SEQUENCE {
			swhSNMPv3USMUserIndex
				INTEGER,
			swhSNMPv3USMUserValid
				INTEGER,
			swhSNMPv3USMUserUserName
				DisplayString,
			swhSNMPv3USMUserAuthentication
				INTEGER,
			swhSNMPv3USMUserAuthPassword
				DisplayString,
			swhSNMPv3USMUserPrivate
				INTEGER,
			swhSNMPv3USMUserPrivPassword
				DisplayString
		}

	swhSNMPv3USMUserIndex OBJECT-TYPE
		SYNTAX      INTEGER (0..2147483647)
		MAX-ACCESS  not-accessible
		STATUS      current
		DESCRIPTION
			"A unique value for each index."
		::= { swhSNMPv3USMUserEntry 1 }

	swhSNMPv3USMUserValid OBJECT-TYPE
		SYNTAX      INTEGER { invalid(0), valid(1) }
		MAX-ACCESS  read-only
		STATUS      current
		DESCRIPTION
			"This entry is valid or invalid."
		::= { swhSNMPv3USMUserEntry 3 }

	swhSNMPv3USMUserUserName OBJECT-TYPE
		SYNTAX      DisplayString
		MAX-ACCESS  read-only
		STATUS      current
		DESCRIPTION
			"User Name."
		::= { swhSNMPv3USMUserEntry 7 }

	swhSNMPv3USMUserAuthentication OBJECT-TYPE
		SYNTAX      INTEGER { none(0), md5(1), sha(2) }
		MAX-ACCESS  read-write
		STATUS      current
		DESCRIPTION
			"Authentication."
		::= { swhSNMPv3USMUserEntry 9 }

	swhSNMPv3USMUserAuthPassword OBJECT-TYPE
		SYNTAX      DisplayString
		MAX-ACCESS  read-write
		STATUS      current
		DESCRIPTION
			"Authentication Password."
		::= { swhSNMPv3USMUserEntry 11 }

	swhSNMPv3USMUserPrivate OBJECT-TYPE
		SYNTAX      INTEGER { none(0), des(1), aes-128(2) }
		MAX-ACCESS  read-write
		STATUS      current
		DESCRIPTION
			"Private."
		::= { swhSNMPv3USMUserEntry 12 }

	swhSNMPv3USMUserPrivPassword OBJECT-TYPE
		SYNTAX      DisplayString
		MAX-ACCESS  read-write
		STATUS      current
		DESCRIPTION
			"Private Password."
		::= { swhSNMPv3USMUserEntry 13 }

	SwhSNMPv3USMUserAuthEntry ::=
		SEQUENCE {
			swhSNMPv3USMUserIndex
				INTEGER,
			swhSNMPv3USMUserValid
				INTEGER,
			swhSNMPv3USMUserUserName
				DisplayString,
			swhSNMPv3USMUserAuthentication
				INTEGER,
			swhSNMPv3USMUserAuthPassword
				DisplayString
		}

	SwhSNMPv3USMUserPrivEntry ::=
		SEQUENCE {
			swhSNMPv3USMUserIndex
				INTEGER,
			swhSNMPv3USMUserValid
				INTEGER,
			swhSNMPv3USMUserUserName
				DisplayString,
			swhSNMPv3USMUserPrivate
				INTEGER,
			swhSNMPv3USMUserPrivPassword
				DisplayString
		}


-- NetworkManagement(3).TrapInformDestination(5)

	swhInformSetup
		OBJECT IDENTIFIER ::= { swhTrapInformDestination 2 }


-- NetworkManagement(3).TrapInformDestination(5).TrapInformDestTable(1)

	swhTrapInformDestTable OBJECT-TYPE
		SYNTAX      SEQUENCE OF SwhTrapInformDestEntry
		MAX-ACCESS  not-accessible
		STATUS      current
		DESCRIPTION
			"Table of trap & inform destination."
		::= { swhTrapInformDestination 1 }

	-- Table Entry
	swhTrapInformDestEntry OBJECT-TYPE
		SYNTAX      SwhTrapInformDestEntry
		MAX-ACCESS  not-accessible
		STATUS      current
		DESCRIPTION
			"An entry in the table, containing information about trap & inform destination."
		INDEX    { swhTrapInformDestIndex }
		::= { swhTrapInformDestTable 1 }

	SwhTrapInformDestEntry ::=
		SEQUENCE {
			swhTrapInformDestIndex
				INTEGER,
			swhTrapInformDestEnable
				INTEGER,
			swhTrapInformDestVersion
				INTEGER,
			swhTrapInformDestType
				INTEGER,
			swhTrapInformDestIPAddr
				IpAddress,
			swhTrapInformDestIPv6Addr
				DisplayString,
			swhTrapInformDestCommunityUser
				DisplayString,
			swhTrapInformDestSecurityLevel
				INTEGER,
			swhTrapInformDestRemoteEngineID
				DisplayString
		}

	swhTrapInformDestIndex OBJECT-TYPE
		SYNTAX      INTEGER (0..2147483647)
		MAX-ACCESS  not-accessible
		STATUS      current
		DESCRIPTION
			"A unique value for each index."
		::= { swhTrapInformDestEntry 1 }

	swhTrapInformDestEnable OBJECT-TYPE
		SYNTAX      INTEGER { disable(0), enable(1) }
		MAX-ACCESS  read-write
		STATUS      current
		DESCRIPTION
			"Enable."
		::= { swhTrapInformDestEntry 3 }

	swhTrapInformDestCommunityUser OBJECT-TYPE
		SYNTAX      DisplayString
		MAX-ACCESS  read-write
		STATUS      current
		DESCRIPTION
			"SNMP community name or SNMPv3 USM user."
		::= { swhTrapInformDestEntry 4 }

	swhTrapInformDestIPAddr OBJECT-TYPE
		SYNTAX      IpAddress
		MAX-ACCESS  read-write
		STATUS      current
		DESCRIPTION
			"The IP address SNMP TRAP send to."
		::= { swhTrapInformDestEntry 8 }

	swhTrapInformDestIPv6Addr OBJECT-TYPE
		SYNTAX      DisplayString
		MAX-ACCESS  read-write
		STATUS      current
		DESCRIPTION
			"The IPv6 address SNMP TRAP send to."
		::= { swhTrapInformDestEntry 9 }

	swhTrapInformDestVersion OBJECT-TYPE
		SYNTAX      INTEGER { v1(0), v2c(1), v3(2) }
		MAX-ACCESS  read-write
		STATUS      current
		DESCRIPTION
			"SNMP Version."
		::= { swhTrapInformDestEntry 11 }

	swhTrapInformDestType OBJECT-TYPE
		SYNTAX      INTEGER { trap(0), inform(1) }
		MAX-ACCESS  read-only
		STATUS      current
		DESCRIPTION
			"SNMP Type."
		::= { swhTrapInformDestEntry 12 }

	swhTrapInformDestSecurityLevel OBJECT-TYPE
		SYNTAX      INTEGER { na(0), noauthnopriv(1), authnopriv(2), authpriv(3) }
		MAX-ACCESS  read-only
		STATUS      current
		DESCRIPTION
			"Security Level. (noAuthNoPriv, authNoPriv, authPriv)"
		::= { swhTrapInformDestEntry 13 }

	swhTrapInformDestRemoteEngineID OBJECT-TYPE
		SYNTAX      DisplayString
		MAX-ACCESS  read-only
		STATUS      current
		DESCRIPTION
			"Remote Engine ID."
		::= { swhTrapInformDestEntry 14 }


-- NetworkManagement(3).TrapInformDestination(5).InformSetup(2)

	swhRetries OBJECT-TYPE
		SYNTAX      INTEGER (0..5)
		MAX-ACCESS  read-only
		STATUS      current
		DESCRIPTION
			"Retries. (0-5 Times)"
		::= { swhInformSetup 1 }

	swhTimeout OBJECT-TYPE
		SYNTAX      INTEGER (1..30)
		MAX-ACCESS  read-only
		STATUS      current
		DESCRIPTION
			"Timeout. (1-30 Secs)"
		::= { swhInformSetup 2 }

	swhPending OBJECT-TYPE
		SYNTAX      INTEGER (1..256)
		MAX-ACCESS  read-only
		STATUS      current
		DESCRIPTION
			"Pending. (1-256 Packets)"
		::= { swhInformSetup 3 }

	swhTrapFallback OBJECT-TYPE
		SYNTAX      INTEGER { disable(0), enable(1) }
		MAX-ACCESS  read-only
		STATUS      current
		DESCRIPTION
			"Trap Fallback."
		::= { swhInformSetup 4 }

	swhFallbackRetries OBJECT-TYPE
		SYNTAX      INTEGER (0..5)
		MAX-ACCESS  read-only
		STATUS      current
		DESCRIPTION
			"Fallback Retries. (0-5 Times)"
		::= { swhInformSetup 5 }

	swhFallbackInterval OBJECT-TYPE
		SYNTAX      INTEGER (1..10)
		MAX-ACCESS  read-only
		STATUS      current
		DESCRIPTION
			"Fallback Interval. (1-10 Secs)"
		::= { swhInformSetup 6 }


-- NetworkManagement(3).TrapInformConfiguration(6)

	swhTrapInformColdStart OBJECT-TYPE
		SYNTAX      INTEGER { disable(0), enable(1) }
		MAX-ACCESS  read-write
		STATUS      current
		DESCRIPTION
			"Cold Start Trap and Inform."
		::= { swhTrapInformConfiguration 1 }

	swhTrapInformWarmStart OBJECT-TYPE
		SYNTAX      INTEGER { disable(0), enable(1) }
		MAX-ACCESS  read-write
		STATUS      current
		DESCRIPTION
			"Warm Start Trap and Inform."
		::= { swhTrapInformConfiguration 2 }

	swhTrapInformAuthenticationFailure OBJECT-TYPE
		SYNTAX      INTEGER { disable(0), enable(1) }
		MAX-ACCESS  read-write
		STATUS      current
		DESCRIPTION
			"Authentication Failure Trap and Inform."
		::= { swhTrapInformConfiguration 3 }

	swhTrapPortLink OBJECT-TYPE
		SYNTAX      INTEGER { disable(0), enable(1) }
		MAX-ACCESS  read-write
		STATUS      current
		DESCRIPTION
			"Port Link UP/Down Trap."
		::= { swhTrapInformConfiguration 4 }

	swhTrapInformPortLinkFlap OBJECT-TYPE
		SYNTAX      INTEGER { disable(0), enable(1) }
		MAX-ACCESS  read-write
		STATUS      current
		DESCRIPTION
			"Port Link Flap Trap and Inform."
		::= { swhTrapInformConfiguration 19 }

	swhTrapInformSystemPowerDown OBJECT-TYPE
		SYNTAX      INTEGER { disable(0), enable(1) }
		MAX-ACCESS  read-write
		STATUS      current
		DESCRIPTION
			"System Power Down Trap and Inform."
		::= { swhTrapInformConfiguration 5 }

	swhTrapInformCPULoading OBJECT-TYPE
		SYNTAX      INTEGER { disable(0), enable(1) }
		MAX-ACCESS  read-write
		STATUS      current
		DESCRIPTION
			"CPU Loading Trap and Inform."
		::= { swhTrapInformConfiguration 11 }

	swhTrapInformDigitalInputStart OBJECT-TYPE
		SYNTAX      INTEGER { disable(0), enable(1) }
		MAX-ACCESS  read-write
		STATUS      current
		DESCRIPTION
			"Digital Input Start Trap and Inform."
		::= { swhTrapInformConfiguration 16 }

	swhTrapInformAutoBackup OBJECT-TYPE
		SYNTAX      INTEGER { disable(0), enable(1) }
		MAX-ACCESS  read-write
		STATUS      current
		DESCRIPTION
			"Auto Backup Trap and Inform."
		::= { swhTrapInformConfiguration 13 }

	swhTrapInformStormControl OBJECT-TYPE
		SYNTAX      INTEGER { disable(0), enable(1) }
		MAX-ACCESS  read-write
		STATUS      current
		DESCRIPTION
			"Storm Control Trap and Inform."
		::= { swhTrapInformConfiguration 15 }

	swhTrapInformMACLimiter OBJECT-TYPE
		SYNTAX      INTEGER { disable(0), enable(1) }
		MAX-ACCESS  read-write
		STATUS      current
		DESCRIPTION
			"MAC Limiter Trap and Inform."
		::= { swhTrapInformConfiguration 14 }

	swhTrapInformConsolePortLink OBJECT-TYPE
		SYNTAX      INTEGER { disable(0), enable(1) }
		MAX-ACCESS  read-write
		STATUS      current
		DESCRIPTION
			"Console Port Link Up/Down Trap and Inform."
		::= { swhTrapInformConfiguration 17 }

	swhTrapInformCPUTemperature OBJECT-TYPE
		SYNTAX      INTEGER { disable(0), enable(1) }
		MAX-ACCESS  read-write
		STATUS      current
		DESCRIPTION
			"CPU Temperature Trap and Inform."
		::= { swhTrapInformConfiguration 18 }

	swhTrapInformFastRedundancy OBJECT-TYPE
		SYNTAX      INTEGER { disable(0), enable(1) }
		MAX-ACCESS  read-write
		STATUS      current
		DESCRIPTION
			"Fast Redundancy Trap and Inform."
		::= { swhTrapInformConfiguration 75 }

	swhTrapInformSFPThreshold OBJECT-TYPE
		SYNTAX      INTEGER { disable(0), enable(1) }
		MAX-ACCESS  read-write
		STATUS      current
		DESCRIPTION
			"SFP Threshold Trap and Inform."
		::= { swhTrapInformConfiguration 58 }

	swhTrapInformSystemVoltage OBJECT-TYPE
		SYNTAX      INTEGER { disable(0), enable(1) }
		MAX-ACCESS  read-write
		STATUS      current
		DESCRIPTION
			"System Voltage Trap and Inform."
		::= { swhTrapInformConfiguration 77 }

	swhTrapInformPortLoopback OBJECT-TYPE
		SYNTAX      INTEGER { disable(0), enable(1) }
		MAX-ACCESS  read-write
		STATUS      current
		DESCRIPTION
			"Port Loopback Trap and Inform."
		::= { swhTrapInformConfiguration 80 }

	swhTrapInformEthernetOAM OBJECT-TYPE
		SYNTAX      INTEGER { disable(0), enable(1) }
		MAX-ACCESS  read-write
		STATUS      current
		DESCRIPTION
			"Ethernet OAM Trap and Inform."
		::= { swhTrapInformConfiguration 79 }

	swhTrapInformSNMPInform OBJECT-TYPE
		SYNTAX      INTEGER { disable(0), enable(1) }
		MAX-ACCESS  read-write
		STATUS      current
		DESCRIPTION
			"SNMP Inform Trap and Inform."
		::= { swhTrapInformConfiguration 117 }


-- NetworkManagement(3).TimeServerConfiguration(7)

	swhTimeSync OBJECT-TYPE
		SYNTAX      INTEGER { disable(0), enable(1) }
		MAX-ACCESS  read-write
		STATUS      current
		DESCRIPTION
			"Time Synchronization."
		::= { swhTimeServerConfiguration 1 }

	swhTimeServerIPAddr OBJECT-TYPE
		SYNTAX      IpAddress
		MAX-ACCESS  read-write
		STATUS      current
		DESCRIPTION
			"1st Time Server IP Address."
		::= { swhTimeServerConfiguration 2 }

	swhTimeServerIPAddr2 OBJECT-TYPE
		SYNTAX      IpAddress
		MAX-ACCESS  read-write
		STATUS      current
		DESCRIPTION
			"2nd Time Server IP Address."
		::= { swhTimeServerConfiguration 3 }

	swhTimeServerIPv6Addr OBJECT-TYPE
		SYNTAX      DisplayString
		MAX-ACCESS  read-write
		STATUS      current
		DESCRIPTION
			"1st Time Server IPv6 Address."
		::= { swhTimeServerConfiguration 20 }

	swhTimeServerIPv6Addr2 OBJECT-TYPE
		SYNTAX      DisplayString
		MAX-ACCESS  read-write
		STATUS      current
		DESCRIPTION
			"2nd Time Server IPv6 Address."
		::= { swhTimeServerConfiguration 21 }

	swhTimeSyncInterval OBJECT-TYPE
		SYNTAX      INTEGER { hour1(1),
		                      hour2(2),
		                      hour3(3),
		                      hour4(4),
		                      hour6(5),
		                      hour8(6),
		                      hour12(7),
		                      hour24(8)
		                    }
		MAX-ACCESS  read-write
		STATUS      current
		DESCRIPTION
			"Time Synchronization Interval, unit is min."
		::= { swhTimeServerConfiguration 4 }

	swhTimeZoneIndex OBJECT-TYPE
		SYNTAX      INTEGER
		MAX-ACCESS  read-write
		STATUS      current
		DESCRIPTION
			"Time Zone. 
			 0:   UTC-11:00  Apia
			 1:   UTC-10:00  Honolulu
			 2:   UTC-9:00  Anchorage
			 3:   UTC-8:00  Vancouver
			 4:   UTC-8:00  San Francisco
			 5:   UTC-8:00  Seattle
			 6:   UTC-8:00  Los Angeles
			 7:   UTC-7:00  Phoenix
			 8:   UTC-7:00  Aklavik
			 9:   UTC-7:00  Edmonton
			10:   UTC-7:00  Denver
			11:   UTC-6:00  Guatemala
			12:   UTC-6:00  San Salvador
			13:   UTC-6:00  Tegucigalpa
			14:   UTC-6:00  Managua
			15:   UTC-6:00  Mexico City
			16:   UTC-6:00  Winnipeg
			17:   UTC-6:00  Houston
			18:   UTC-6:00  Minneapolis
			19:   UTC-6:00  St. Paul
			20:   UTC-6:00  New Orleans
			21:   UTC-6:00  Chicago
			22:   UTC-6:00  Montgomery
			23:   UTC-5:00  Indianapolis
			24:   UTC-5:00  Lima
			25:   UTC-5:00  Kingston
			26:   UTC-5:00  Bogota
			27:   UTC-5:00  Atlanta
			28:   UTC-5:00  Detroit
			29:   UTC-5:00  Havana
			30:   UTC-5:00  Toronto
			31:   UTC-5:00  Nassau
			32:   UTC-5:00  Washington DC
			33:   UTC-5:00  Ottawa
			34:   UTC-5:00  Philadelphia
			35:   UTC-5:00  New York
			36:   UTC-5:00  Montreal
			37:   UTC-5:00  Boston
			38:   UTC-4:00  Santo Domingo
			39:   UTC-4:00  La Paz
			40:   UTC-4:00  Caracas
			41:   UTC-4:00  San Juan
			42:   UTC-4:00  Santiago
			43:   UTC-4:00  Halifax
			44:   UTC-4:00  Asuncion
			45:   UTC-3:00  Buenos Aires
			46:   UTC-3:00  Montevideo
			47:   UTC-3:00  Brasilia
			48:   UTC-3:00  Sao Paulo
			49:   UTC-3:00  Rio de Janeiro
			50:   UTC-2:00  Fernando de Noronha
			51:   UTC-1:00  Praia
			52:   UTC       Reykjavik
			53:   UTC       Casablanca
			54:   UTC       Lisbon
			55:   UTC       Dublin
			56:   UTC       London
			57:   UTC+1:00  Lagos
			58:   UTC+1:00  Algiers
			59:   UTC+1:00  Madrid
			60:   UTC+1:00  Barcelona
			61:   UTC+1:00  Paris
			62:   UTC+1:00  Brussels
			63:   UTC+1:00  Amsterdam
			64:   UTC+1:00  Geneva
			65:   UTC+1:00  Zurich
			66:   UTC+1:00  Frankfurt
			67:   UTC+1:00  Oslo
			68:   UTC+1:00  Copenhagen
			69:   UTC+1:00  Rome
			70:   UTC+1:00  Berlin
			71:   UTC+1:00  Prague
			72:   UTC+1:00  Zagreb
			73:   UTC+1:00  Vienna
			74:   UTC+1:00  Stockholm
			75:   UTC+1:00  Cape Town
			76:   UTC+1:00  Budapest
			77:   UTC+1:00  Belgrade
			78:   UTC+1:00  Warsaw
			79:   UTC+2:00  Johannesburg
			80:   UTC+2:00  Harare
			81:   UTC+2:00  Cairo
			82:   UTC+2:00  Jerusalem
			83:   UTC+2:00  Sofia
			84:   UTC+2:00  Athens
			85:   UTC+2:00  Tallinn
			86:   UTC+2:00  Helsinki
			87:   UTC+2:00  Bucharest
			88:   UTC+2:00  Minsk
			89:   UTC+2:00  Istanbul
			90:   UTC+2:00  Kyiv
			91:   UTC+2:00  Odesa
			92:   UTC+2:00  Khartoum
			93:   UTC+2:00  Ankara
			94:   UTC+2:00  Beirut
			95:   UTC+2:00  Amman
			96:   UTC+3:00  Nairobi
			97:   UTC+3:00  Addis Ababa
			98:   UTC+3:00  Baghdad
			99:   UTC+3:00  Aden
			100:  UTC+3:00  Riyadh
			101:  UTC+3:00  Antananarivo
			102:  UTC+3:00  Kuwait City
			103:  UTC+3:00  Moscow
			104:  UTC+4:00  Abu Dhabi
			105:  UTC+5:00  Karachi
			106:  UTC+5:00  Tashkent
			107:  UTC+5:00  Islamabad
			108:  UTC+5:00  Lahore
			109:  UTC+5:30  Mumbai
			110:  UTC+5:30  New Delhi
			111:  UTC+5:30  Kolkata
			112:  UTC+6:00  Dhaka
			113:  UTC+7:00  Bangkok
			114:  UTC+7:00  Hanoi
			115:  UTC+7:00  Jakarta
			116:  UTC+8:00  Kuala Lumpur
			117:  UTC+8:00  Singapore
			118:  UTC+8:00  Hong Kong
			119:  UTC+8:00  Perth
			120:  UTC+8:00  Beijing
			121:  UTC+8:00  Manila
			122:  UTC+8:00  Shanghai
			123:  UTC+8:00  Taipei
			124:  UTC+9:00  Seoul
			125:  UTC+9:00  Tokyo
			126:  UTC+10:00  Melbourne
			127:  UTC+10:00  Canberra
			128:  UTC+10:00  Sydney
			129:  UTC+10:00  Brisbane
			130:  UTC+10:00  Vladivostok
			131:  UTC+11:00  Kolonia
			132:  UTC+12:00  Suva
			133:  UTC+12:00  Kamchatka
			134:  UTC+12:00  Wellington
			135:  UTC+12:00  Anadyr
			"
		::= { swhTimeServerConfiguration 5 }

	swhTimeZone OBJECT-TYPE
		SYNTAX      DisplayString
		MAX-ACCESS  read-only
		STATUS      current
		DESCRIPTION
			"Time Zone."
		::= { swhTimeServerConfiguration 6 }

	swhTimeDST OBJECT-TYPE
		SYNTAX      INTEGER { disable(0), recurring(1), date(2) }
		MAX-ACCESS  read-write
		STATUS      current
		DESCRIPTION
			"Daylight Saving Time."
		::= { swhTimeServerConfiguration 7 }

	swhTimeDSTRange OBJECT-TYPE
		SYNTAX      DisplayString
		MAX-ACCESS  read-write
		STATUS      current
		DESCRIPTION
			"DST Range when Daylight Saving Time (TimeDST) is enable."
		::= { swhTimeServerConfiguration 9 }


-- NetworkManagement(3).SyslogConfiguration(8)

	swhLogServer OBJECT-TYPE
		SYNTAX      INTEGER { disable(0), enable(1) }
		MAX-ACCESS  read-write
		STATUS      current
		DESCRIPTION
			"Log Server."
		::= { swhSyslogConfiguration 1 }

	swhLogSNTPStatus OBJECT-TYPE
		SYNTAX      INTEGER { disable(0), enable(1) }
		MAX-ACCESS  read-only
		STATUS      current
		DESCRIPTION
			"SNTP Status."
		::= { swhSyslogConfiguration 3 }

	swhLogFacility OBJECT-TYPE
		SYNTAX      INTEGER { local-0(0),
		                      local-1(1),
		                      local-2(2),
		                      local-3(3),
		                      local-4(4),
		                      local-5(5),
		                      local-6(6),
		                      local-7(7)
		                    }
		MAX-ACCESS  read-write
		STATUS      current
		DESCRIPTION
			"Log Facility Local. (0-7)"
		::= { swhSyslogConfiguration 12 }

	swhLogServerIPAddr1 OBJECT-TYPE
		SYNTAX      IpAddress
		MAX-ACCESS  read-write
		STATUS      current
		DESCRIPTION
			"Log Server IP Address 1."
		::= { swhSyslogConfiguration 4 }

	swhLogServerIPAddr2 OBJECT-TYPE
		SYNTAX      IpAddress
		MAX-ACCESS  read-write
		STATUS      current
		DESCRIPTION
			"Log Server IP Address 2."
		::= { swhSyslogConfiguration 5 }

	swhLogServerIPAddr3 OBJECT-TYPE
		SYNTAX      IpAddress
		MAX-ACCESS  read-write
		STATUS      current
		DESCRIPTION
			"Log Server IP Address 3."
		::= { swhSyslogConfiguration 6 }

	swhLogServerIPv6Addr1 OBJECT-TYPE
		SYNTAX      DisplayString
		MAX-ACCESS  read-write
		STATUS      current
		DESCRIPTION
			"Log Server IPv6 Address 1."
		::= { swhSyslogConfiguration 8 }

	swhLogServerIPv6Addr2 OBJECT-TYPE
		SYNTAX      DisplayString
		MAX-ACCESS  read-write
		STATUS      current
		DESCRIPTION
			"Log Server IPv6 Address 2."
		::= { swhSyslogConfiguration 9 }

	swhLogServerIPv6Addr3 OBJECT-TYPE
		SYNTAX      DisplayString
		MAX-ACCESS  read-write
		STATUS      current
		DESCRIPTION
			"Log Server IPv6 Address 3."
		::= { swhSyslogConfiguration 10 }


-- NetworkManagement(3).SyslogConfiguration(8).LoggingType(11)

	swhLoggingType
		OBJECT IDENTIFIER ::= { swhSyslogConfiguration 11 }

	swhLoggingTypeTerminalHistory OBJECT-TYPE
		SYNTAX      INTEGER { disable(0), enable(1) }
		MAX-ACCESS  read-write
		STATUS      current
		DESCRIPTION
			"Terminal History."
		::= { swhLoggingType 1 }


-- NetworkManagement(3).RADIUSTACACS(11)

	swhRADIUS
		OBJECT IDENTIFIER ::= { swhRADIUSTACACS 1 }

	swhTACACS
		OBJECT IDENTIFIER ::= { swhRADIUSTACACS 2 }


-- NetworkManagement(3).RADIUSTACACS(11).RADIUS(1)

	swhRADIUSSecretKeyEncryption OBJECT-TYPE
		SYNTAX      INTEGER { disable(0), aes-128(1) }
		MAX-ACCESS  read-write
		STATUS      current
		DESCRIPTION
			"RADIUS SecretKey Encryption."
		::= { swhRADIUS 1 }

	swhRADIUSRetry OBJECT-TYPE
		SYNTAX      INTEGER (0..3)
		MAX-ACCESS  read-write
		STATUS      current
		DESCRIPTION
			"The retry times of connecting to RADIUS servers."
		::= { swhRADIUS 2 }

	swhRADIUSTimeout OBJECT-TYPE
		SYNTAX      INTEGER (1..3)
		MAX-ACCESS  read-write
		STATUS      current
		DESCRIPTION
			"The timeout of connecting to RADIUS servers."
		::= { swhRADIUS 3 }

	swhRADIUS1
		OBJECT IDENTIFIER ::= { swhRADIUS 4 }

	swhRADIUS2
		OBJECT IDENTIFIER ::= { swhRADIUS 5 }


-- NetworkManagement(3).RADIUSTACACS(11).RADIUS(1).RADIUS1(4)

	swhRADIUS1Enable OBJECT-TYPE
		SYNTAX      INTEGER { disable(0), enable(1) }
		MAX-ACCESS  read-write
		STATUS      current
		DESCRIPTION
			"1st RADIUS client."
		::= { swhRADIUS1 1 }

	swhRADIUS1SecretKey OBJECT-TYPE
		SYNTAX      DisplayString
		MAX-ACCESS  read-write
		STATUS      current
		DESCRIPTION
			"The plain code for encrypting data for 1st RADIUS server port."
		::= { swhRADIUS1 2 }

	swhRADIUS1Port OBJECT-TYPE
		SYNTAX      INTEGER (0..65535)
		MAX-ACCESS  read-write
		STATUS      current
		DESCRIPTION
			"1st RADIUS server port."
		::= { swhRADIUS1 3 }

	swhRADIUS1IPAddr OBJECT-TYPE
		SYNTAX      IpAddress
		MAX-ACCESS  read-write
		STATUS      current
		DESCRIPTION
			"1st RADIUS server IP address."
		::= { swhRADIUS1 4 }

	swhRADIUS1IPv6Addr OBJECT-TYPE
		SYNTAX      DisplayString
		MAX-ACCESS  read-write
		STATUS      current
		DESCRIPTION
			"1st RADIUS server IPv6 address."
		::= { swhRADIUS1 5 }


-- NetworkManagement(3).RADIUSTACACS(11).RADIUS(1).RADIUS2(5)

	swhRADIUS2Enable OBJECT-TYPE
		SYNTAX      INTEGER { disable(0), enable(1) }
		MAX-ACCESS  read-write
		STATUS      current
		DESCRIPTION
			"2nd RADIUS client."
		::= { swhRADIUS2 1 }

	swhRADIUS2SecretKey OBJECT-TYPE
		SYNTAX      DisplayString
		MAX-ACCESS  read-write
		STATUS      current
		DESCRIPTION
			"The plain code for encrypting data for 2nd RADIUS server port."
		::= { swhRADIUS2 2 }

	swhRADIUS2Port OBJECT-TYPE
		SYNTAX      INTEGER (0..65535)
		MAX-ACCESS  read-write
		STATUS      current
		DESCRIPTION
			"2nd RADIUS server port."
		::= { swhRADIUS2 3 }

	swhRADIUS2IPAddr OBJECT-TYPE
		SYNTAX      IpAddress
		MAX-ACCESS  read-write
		STATUS      current
		DESCRIPTION
			"2nd RADIUS server IP address."
		::= { swhRADIUS2 4 }

	swhRADIUS2IPv6Addr OBJECT-TYPE
		SYNTAX      DisplayString
		MAX-ACCESS  read-write
		STATUS      current
		DESCRIPTION
			"2nd RADIUS server IPv6 address."
		::= { swhRADIUS2 5 }


-- NetworkManagement(3).RADIUSTACACS(11).TACACS(2)

	swhTACACSSecretKeyEncryption OBJECT-TYPE
		SYNTAX      INTEGER { disable(0), aes-128(1) }
		MAX-ACCESS  read-write
		STATUS      current
		DESCRIPTION
			"TACACS SecretKey Encryption."
		::= { swhTACACS 1 }

	swhTACACSRetry OBJECT-TYPE
		SYNTAX      INTEGER (0..3)
		MAX-ACCESS  read-write
		STATUS      current
		DESCRIPTION
			"The retry times of connecting to TACACS servers."
		::= { swhTACACS 2 }

	swhTACACSTimeout OBJECT-TYPE
		SYNTAX      INTEGER (1..3)
		MAX-ACCESS  read-write
		STATUS      current
		DESCRIPTION
			"The timeout of connecting to TACACS servers."
		::= { swhTACACS 3 }

	swhTACACS1
		OBJECT IDENTIFIER ::= { swhTACACS 4 }

	swhTACACS2
		OBJECT IDENTIFIER ::= { swhTACACS 5 }


-- NetworkManagement(3).RADIUSTACACS(11).TACACS(2).TACACS1(4)

	swhTACACS1Enable OBJECT-TYPE
		SYNTAX      INTEGER { disable(0), enable(1) }
		MAX-ACCESS  read-write
		STATUS      current
		DESCRIPTION
			"1st TACACS client."
		::= { swhTACACS1 1 }

	swhTACACS1SecretKey OBJECT-TYPE
		SYNTAX      DisplayString
		MAX-ACCESS  read-write
		STATUS      current
		DESCRIPTION
			"The plain code for encrypting data for 1st TACACS server port."
		::= { swhTACACS1 2 }

	swhTACACS1Port OBJECT-TYPE
		SYNTAX      INTEGER (0..65535)
		MAX-ACCESS  read-write
		STATUS      current
		DESCRIPTION
			"1st TACACS server port."
		::= { swhTACACS1 3 }

	swhTACACS1IPAddr OBJECT-TYPE
		SYNTAX      IpAddress
		MAX-ACCESS  read-write
		STATUS      current
		DESCRIPTION
			"1st TACACS server IP address."
		::= { swhTACACS1 4 }

	swhTACACS1IPv6Addr OBJECT-TYPE
		SYNTAX      DisplayString
		MAX-ACCESS  read-write
		STATUS      current
		DESCRIPTION
			"1st TACACS server IPv6 address."
		::= { swhTACACS1 5 }


-- NetworkManagement(3).RADIUSTACACS(11).TACACS(2).TACACS2(5)

	swhTACACS2Enable OBJECT-TYPE
		SYNTAX      INTEGER { disable(0), enable(1) }
		MAX-ACCESS  read-write
		STATUS      current
		DESCRIPTION
			"2nd TACACS client."
		::= { swhTACACS2 1 }

	swhTACACS2SecretKey OBJECT-TYPE
		SYNTAX      DisplayString
		MAX-ACCESS  read-write
		STATUS      current
		DESCRIPTION
			"The plain code for encrypting data for 2nd TACACS server port."
		::= { swhTACACS2 2 }

	swhTACACS2Port OBJECT-TYPE
		SYNTAX      INTEGER (0..65535)
		MAX-ACCESS  read-write
		STATUS      current
		DESCRIPTION
			"2nd TACACS server port."
		::= { swhTACACS2 3 }

	swhTACACS2IPAddr OBJECT-TYPE
		SYNTAX      IpAddress
		MAX-ACCESS  read-write
		STATUS      current
		DESCRIPTION
			"2nd TACACS server IP address."
		::= { swhTACACS2 4 }

	swhTACACS2IPv6Addr OBJECT-TYPE
		SYNTAX      DisplayString
		MAX-ACCESS  read-write
		STATUS      current
		DESCRIPTION
			"2nd TACACS server IPv6 address."
		::= { swhTACACS2 5 }


-- NetworkManagement(3).Auth(12)

	swhAuthentication
		OBJECT IDENTIFIER ::= { swhAuth 1 }


-- NetworkManagement(3).Auth(12).Authentication(1)

	swhAuthenticationContinue-to-next-method OBJECT-TYPE
		SYNTAX      INTEGER { disable(0), enable(1) }
		MAX-ACCESS  read-write
		STATUS      current
		DESCRIPTION
			"The Continue to next method. 
			 Function on authentication, the device will do 
			 the authentication with all setup authentication 
			 method when enable, only do the authentication with 
			 the first available authentication method when disable."
		::= { swhAuthentication 1 }

	swhAuthenticationAll
		OBJECT IDENTIFIER ::= { swhAuthentication 2 }

	swhAuthenticationTelnet
		OBJECT IDENTIFIER ::= { swhAuthentication 3 }

	swhAuthenticationSSH
		OBJECT IDENTIFIER ::= { swhAuthentication 4 }

	swhAuthenticationWeb
		OBJECT IDENTIFIER ::= { swhAuthentication 5 }

	swhAuthenticationConsole
		OBJECT IDENTIFIER ::= { swhAuthentication 6 }


-- NetworkManagement(3).Auth(12).Authentication(1).AuthenticationAll(2)

	swhAuthenticationAllMethod1 OBJECT-TYPE
		SYNTAX      INTEGER { local(1), radius-1(2), radius-2(3), tacacs-1(4), tacacs-2(5) }
		MAX-ACCESS  read-write
		STATUS      current
		DESCRIPTION
			"Define the first authentication method for Telnet, SSH, Web and Console at the same time. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationAll 1 }

	swhAuthenticationAllMethod2 OBJECT-TYPE
		SYNTAX      INTEGER { disable(0), local(1), radius-1(2), radius-2(3), tacacs-1(4), tacacs-2(5) }
		MAX-ACCESS  read-write
		STATUS      current
		DESCRIPTION
			"Define the first authentication method for Telnet, SSH, Web and Console at the same time. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationAll 2 }

	swhAuthenticationAllMethod3 OBJECT-TYPE
		SYNTAX      INTEGER { disable(0), local(1), radius-1(2), radius-2(3), tacacs-1(4), tacacs-2(5) }
		MAX-ACCESS  read-write
		STATUS      current
		DESCRIPTION
			"Define the first authentication method for Telnet, SSH, Web and Console at the same time. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationAll 3 }

	swhAuthenticationAllMethod4 OBJECT-TYPE
		SYNTAX      INTEGER { disable(0), local(1), radius-1(2), radius-2(3), tacacs-1(4), tacacs-2(5) }
		MAX-ACCESS  read-write
		STATUS      current
		DESCRIPTION
			"Define the first authentication method for Telnet, SSH, Web and Console at the same time. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationAll 4 }

	swhAuthenticationAllMethod5 OBJECT-TYPE
		SYNTAX      INTEGER { disable(0), local(1), radius-1(2), radius-2(3), tacacs-1(4), tacacs-2(5) }
		MAX-ACCESS  read-write
		STATUS      current
		DESCRIPTION
			"Define the first authentication method for Telnet, SSH, Web and Console at the same time. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationAll 5 }


-- NetworkManagement(3).Auth(12).Authentication(1).AuthenticationTelnet(3)

	swhAuthenticationTelnetMethod1 OBJECT-TYPE
		SYNTAX      INTEGER { local(1), radius-1(2), radius-2(3), tacacs-1(4), tacacs-2(5) }
		MAX-ACCESS  read-only
		STATUS      current
		DESCRIPTION
			"Define the first authentication method for Telnet. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationTelnet 1 }

	swhAuthenticationTelnetMethod2 OBJECT-TYPE
		SYNTAX      INTEGER { disable(0), local(1), radius-1(2), radius-2(3), tacacs-1(4), tacacs-2(5) }
		MAX-ACCESS  read-only
		STATUS      current
		DESCRIPTION
			"Define the first authentication method for Telnet. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationTelnet 2 }

	swhAuthenticationTelnetMethod3 OBJECT-TYPE
		SYNTAX      INTEGER { disable(0), local(1), radius-1(2), radius-2(3), tacacs-1(4), tacacs-2(5) }
		MAX-ACCESS  read-only
		STATUS      current
		DESCRIPTION
			"Define the first authentication method for Telnet. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationTelnet 3 }

	swhAuthenticationTelnetMethod4 OBJECT-TYPE
		SYNTAX      INTEGER { disable(0), local(1), radius-1(2), radius-2(3), tacacs-1(4), tacacs-2(5) }
		MAX-ACCESS  read-only
		STATUS      current
		DESCRIPTION
			"Define the first authentication method for Telnet. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationTelnet 4 }

	swhAuthenticationTelnetMethod5 OBJECT-TYPE
		SYNTAX      INTEGER { disable(0), local(1), radius-1(2), radius-2(3), tacacs-1(4), tacacs-2(5) }
		MAX-ACCESS  read-only
		STATUS      current
		DESCRIPTION
			"Define the first authentication method for Telnet. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationTelnet 5 }


-- NetworkManagement(3).Auth(12).Authentication(1).AuthenticationSSH(4)

	swhAuthenticationSSHMethod1 OBJECT-TYPE
		SYNTAX      INTEGER { local(1), radius-1(2), radius-2(3), tacacs-1(4), tacacs-2(5) }
		MAX-ACCESS  read-only
		STATUS      current
		DESCRIPTION
			"Define the first authentication method for SSH. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationSSH 1 }

	swhAuthenticationSSHMethod2 OBJECT-TYPE
		SYNTAX      INTEGER { disable(0), local(1), radius-1(2), radius-2(3), tacacs-1(4), tacacs-2(5) }
		MAX-ACCESS  read-only
		STATUS      current
		DESCRIPTION
			"Define the first authentication method for SSH. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationSSH 2 }

	swhAuthenticationSSHMethod3 OBJECT-TYPE
		SYNTAX      INTEGER { disable(0), local(1), radius-1(2), radius-2(3), tacacs-1(4), tacacs-2(5) }
		MAX-ACCESS  read-only
		STATUS      current
		DESCRIPTION
			"Define the first authentication method for SSH. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationSSH 3 }

	swhAuthenticationSSHMethod4 OBJECT-TYPE
		SYNTAX      INTEGER { disable(0), local(1), radius-1(2), radius-2(3), tacacs-1(4), tacacs-2(5) }
		MAX-ACCESS  read-only
		STATUS      current
		DESCRIPTION
			"Define the first authentication method for SSH. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationSSH 4 }

	swhAuthenticationSSHMethod5 OBJECT-TYPE
		SYNTAX      INTEGER { disable(0), local(1), radius-1(2), radius-2(3), tacacs-1(4), tacacs-2(5) }
		MAX-ACCESS  read-only
		STATUS      current
		DESCRIPTION
			"Define the first authentication method for SSH. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationSSH 5 }


-- NetworkManagement(3).Auth(12).Authentication(1).AuthenticationWeb(5)

	swhAuthenticationWebMethod1 OBJECT-TYPE
		SYNTAX      INTEGER { local(1), radius-1(2), radius-2(3), tacacs-1(4), tacacs-2(5) }
		MAX-ACCESS  read-only
		STATUS      current
		DESCRIPTION
			"Define the first authentication method for Web. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationWeb 1 }

	swhAuthenticationWebMethod2 OBJECT-TYPE
		SYNTAX      INTEGER { disable(0), local(1), radius-1(2), radius-2(3), tacacs-1(4), tacacs-2(5) }
		MAX-ACCESS  read-only
		STATUS      current
		DESCRIPTION
			"Define the first authentication method for Web. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationWeb 2 }

	swhAuthenticationWebMethod3 OBJECT-TYPE
		SYNTAX      INTEGER { disable(0), local(1), radius-1(2), radius-2(3), tacacs-1(4), tacacs-2(5) }
		MAX-ACCESS  read-only
		STATUS      current
		DESCRIPTION
			"Define the first authentication method for Web. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationWeb 3 }

	swhAuthenticationWebMethod4 OBJECT-TYPE
		SYNTAX      INTEGER { disable(0), local(1), radius-1(2), radius-2(3), tacacs-1(4), tacacs-2(5) }
		MAX-ACCESS  read-only
		STATUS      current
		DESCRIPTION
			"Define the first authentication method for Web. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationWeb 4 }

	swhAuthenticationWebMethod5 OBJECT-TYPE
		SYNTAX      INTEGER { disable(0), local(1), radius-1(2), radius-2(3), tacacs-1(4), tacacs-2(5) }
		MAX-ACCESS  read-only
		STATUS      current
		DESCRIPTION
			"Define the first authentication method for Web. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationWeb 5 }


-- NetworkManagement(3).Auth(12).Authentication(1).AuthenticationConsole(6)

	swhAuthenticationConsoleMethod1 OBJECT-TYPE
		SYNTAX      INTEGER { local(1), radius-1(2), radius-2(3), tacacs-1(4), tacacs-2(5) }
		MAX-ACCESS  read-only
		STATUS      current
		DESCRIPTION
			"Define the first authentication method for Console. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationConsole 1 }

	swhAuthenticationConsoleMethod2 OBJECT-TYPE
		SYNTAX      INTEGER { disable(0), local(1), radius-1(2), radius-2(3), tacacs-1(4), tacacs-2(5) }
		MAX-ACCESS  read-only
		STATUS      current
		DESCRIPTION
			"Define the first authentication method for Console. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationConsole 2 }

	swhAuthenticationConsoleMethod3 OBJECT-TYPE
		SYNTAX      INTEGER { disable(0), local(1), radius-1(2), radius-2(3), tacacs-1(4), tacacs-2(5) }
		MAX-ACCESS  read-only
		STATUS      current
		DESCRIPTION
			"Define the first authentication method for Console. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationConsole 3 }

	swhAuthenticationConsoleMethod4 OBJECT-TYPE
		SYNTAX      INTEGER { disable(0), local(1), radius-1(2), radius-2(3), tacacs-1(4), tacacs-2(5) }
		MAX-ACCESS  read-only
		STATUS      current
		DESCRIPTION
			"Define the first authentication method for Console. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationConsole 4 }

	swhAuthenticationConsoleMethod5 OBJECT-TYPE
		SYNTAX      INTEGER { disable(0), local(1), radius-1(2), radius-2(3), tacacs-1(4), tacacs-2(5) }
		MAX-ACCESS  read-only
		STATUS      current
		DESCRIPTION
			"Define the first authentication method for Console. 
			 The values of each authentication method are as follows: 
				0: authentication configured as disabled. 
				1 (local): local authentication. 
				2 (radius): RADIUS 1 authentication. 
				3 (radius): RADIUS 2 authentication. 
				4 (tacacs): TACACS 1 authentication. 
				5 (tacacs): TACACS 2 authentication. 
				First method can't be 0, and 1 can only be located before 0."
		::= { swhAuthenticationConsole 5 }


-- NetworkManagement(3).DHCPClientSetup(13)

	swhHostName
		OBJECT IDENTIFIER ::= { swhDHCPClientSetup 2 }


-- NetworkManagement(3).DHCPClientSetup(13).HostName(2)

	swhHostNameAssignedByServer OBJECT-TYPE
		SYNTAX      INTEGER { disable(0), enable(1) }
		MAX-ACCESS  read-write
		STATUS      current
		DESCRIPTION
			"Assigned by Server."
		::= { swhHostName 1 }


-- NetworkManagement(3).GlobalSetup(14)

	swhSNMPAgent OBJECT-TYPE
		SYNTAX      INTEGER { disable(0), enable(1) }
		MAX-ACCESS  read-only
		STATUS      current
		DESCRIPTION
			"SNMP Thread."
		::= { swhGlobalSetup 1 }

	swhSNMPVersion1 OBJECT-TYPE
		SYNTAX      INTEGER { disable(0), enable(1) }
		MAX-ACCESS  read-only
		STATUS      current
		DESCRIPTION
			"SNMP Version 1"
		::= { swhGlobalSetup 2 }

	swhSNMPVersion2c OBJECT-TYPE
		SYNTAX      INTEGER { disable(0), enable(1) }
		MAX-ACCESS  read-only
		STATUS      current
		DESCRIPTION
			"SNMP Version 2c"
		::= { swhGlobalSetup 3 }

	swhSNMPVersion3 OBJECT-TYPE
		SYNTAX      INTEGER { disable(0), enable(1) }
		MAX-ACCESS  read-only
		STATUS      current
		DESCRIPTION
			"SNMP Version 3"
		::= { swhGlobalSetup 4 }

	swhLocalEngineIDtoDefault OBJECT-TYPE
		SYNTAX      INTEGER { none(0), apply(1) }
		MAX-ACCESS  read-only
		STATUS      current
		DESCRIPTION
			"Local Engine ID to default"
		::= { swhGlobalSetup 5 }

	swhLocalEngineID OBJECT-TYPE
		SYNTAX      DisplayString
		MAX-ACCESS  read-only
		STATUS      current
		DESCRIPTION
			"Local Engine ID"
		::= { swhGlobalSetup 6 }


-- SwitchManagement(4)

	swhSwitchConfiguration
		OBJECT IDENTIFIER ::= { swhSwitchManagement 1 }

	swhPortConfiguration
		OBJECT IDENTIFIER ::= { swhSwitchManagement 2 }

	swhPortMirroring
		OBJECT IDENTIFIER ::= { swhSwitchManagement 15 }

	swhLinkAggregation
		OBJECT IDENTIFIER ::= { swhSwitchManagement 45 }

	swhVLANConfiguration
		OBJECT IDENTIFIER ::= { swhSwitchManagement 4 }

	swhRapidSpanningTree
		OBJECT IDENTIFIER ::= { swhSwitchManagement 40 }

	swhFastRedundancy
		OBJECT IDENTIFIER ::= { swhSwitchManagement 91 }

	swhMacAddressManagement
		OBJECT IDENTIFIER ::= { swhSwitchManagement 35 }

	swhQoSConfiguration
		OBJECT IDENTIFIER ::= { swhSwitchManagement 60 }

	swhIGMPSnooping
		OBJECT IDENTIFIER ::= { swhSwitchManagement 50 }

	swhIGMPMVR
		OBJECT IDENTIFIER ::= { swhSwitchManagement 92 }

	swhStaticMulticastConfiguration
		OBJECT IDENTIFIER ::= { swhSwitchManagement 70 }

	swhACLConfiguration
		OBJECT IDENTIFIER ::= { swhSwitchManagement 65 }

	swhSecurityConfiguration
		OBJECT IDENTIFIER ::= { swhSwitchManagement 80 }

	swhLoopDetection
		OBJECT IDENTIFIER ::= { swhSwitchManagement 13 }

	swh8021XConfiguration
		OBJECT IDENTIFIER ::= { swhSwitchManagement 55 }

	swhLLDPConfiguration
		OBJECT IDENTIFIER ::= { swhSwitchManagement 14 }

	swhLayer2ProtocolTunnel
		OBJECT IDENTIFIER ::= { swhSwitchManagement 37 }

	swhSFPPortThreshold
		OBJECT IDENTIFIER ::= { swhSwitchManagement 51 }

	swhDIConfiguration
		OBJECT IDENTIFIER ::= { swhSwitchManagement 22 }


-- SwitchManagement(4).SwitchConfiguration(1)

	swhSwitchMaxFrameSize OBJECT-TYPE
		SYNTAX      INTEGER (1518..12288)
		MAX-ACCESS  read-write
		STATUS      current
		DESCRIPTION
			"Max Frame Size."
		::= { swhSwitchConfiguration 1 }

	swhSwitchAgingTime OBJECT-TYPE
		SYNTAX      INTEGER (0..900)
		MAX-ACCESS  read-write
		STATUS      current
		DESCRIPTION
			"Mac address Aging time. (0 means never age out, 1-9 Days, 0-900 Secs)"
		::= { swhSwitchConfiguration 3 }

	swhSwitch0180C2000000to0F OBJECT-TYPE
		SYNTAX      INTEGER { disable(0), enable(1) }
		MAX-ACCESS  read-write
		STATUS      current
		DESCRIPTION
			"Filter or not filter destination address 0180C2000000-0F (IEEE 802.1D and 802.1Q standard use)."
		::= { swhSwitchConfiguration 9 }

	swhSwitch0180C2000020to2F OBJECT-TYPE
		SYNTAX      INTEGER { disable(0), enable(1) }
		MAX-ACCESS  read-write
		STATUS      current
		DESCRIPTION
			"Filter or not filter destination address 0180C2000020-2F (IEEE 802.1Q standard use)."
		::= { swhSwitchConfiguration 10 }

	swhSwitch0180C2000010 OBJECT-TYPE
		SYNTAX      INTEGER { disable(0), enable(1) }
		MAX-ACCESS  read-write
		STATUS      current
		DESCRIPTION
			"Filter or not filter destination address 0180C2000010 (IEEE 802.1D standard use)."
		::= { swhSwitchConfiguration 11 }


-- SwitchManagement(4).PortConfiguration(2)

	swhPortConfigTable OBJECT-TYPE
		SYNTAX      SEQUENCE OF SwhPortConfigEntry
		MAX-ACCESS  not-accessible
		STATUS      current
		DESCRIPTION
			"Table of port descriptive and status information."
		::= { swhPortConfiguration 1 }

	-- Table Entry
	swhPortConfigEntry OBJECT-TYPE
		SYNTAX      SwhPortConfigEntry
		MAX-ACCESS  not-accessible
		STATUS      current
		DESCRIPTION
			"An entry in the table, containing information about port config."
		INDEX    { swhPortConfigIndex }
		::= { swhPortConfigTable 1 }

	SwhPortConfigEntry ::=
		SEQUENCE {
			swhPortConfigIndex
				INTEGER,
			swhPortConfigMediaType
				INTEGER,
			swhPortConfigState
				INTEGER,
			swhPortConfigType
				INTEGER,
			swhPortConfigSpeed
				INTEGER,
			swhPortConfigDuplex
				INTEGER,
			swhPortConfigFlowControl
				INTEGER,
			swhPortConfigDescription
				DisplayString
		}

	swhPortConfigIndex OBJECT-TYPE
		SYNTAX      INTEGER (0..2147483647)
		MAX-ACCESS  not-accessible
		STATUS      current
		DESCRIPTION
			"A unique value for each index."
		::= { swhPortConfigEntry 1 }

	swhPortConfigState OBJECT-TYPE
		SYNTAX      INTEGER { disable(0), enable(1) }
		MAX-ACCESS  read-write
		STATUS      current
		DESCRIPTION
			"Port State."
		::= { swhPortConfigEntry 2 }

	swhPortConfigType OBJECT-TYPE
		SYNTAX      INTEGER { auto-negotiation(0), manual(1) }
		MAX-ACCESS  read-write
		STATUS      current
		DESCRIPTION
			"Port Type."
		::= { swhPortConfigEntry 3 }

	swhPortConfigSpeed OBJECT-TYPE
		SYNTAX      INTEGER { speed-10M(0), speed-100M(1), speed-1000M(2), auto-speed-or-sense(3), speed-10G(4), speed-2500M(5), speed-5G(6) }
		MAX-ACCESS  read-write
		STATUS      current
		DESCRIPTION
			"Port Speed 10M 100M 1000M auto-speed/auto-sense 10G 2.5G 5G. 
			 It's configuration, NOT current speed, 
			 current speed is swhPortStatusSpeed under swhSwitchMonitor. 
			 The speed of 100Mbps cannot support auto-negotiation on transceiver port."
		::= { swhPortConfigEntry 4 }

	swhPortConfigDuplex OBJECT-TYPE
		SYNTAX      INTEGER { halfDuplex(0), fullDuplex(1) }
		MAX-ACCESS  read-write
		STATUS      current
		DESCRIPTION
			"Duplex. 
			 It's configuration, NOT current duplex, 
			 current duplex is swhPortStatusDuplex under swhSwitchMonitor."
		::= { swhPortConfigEntry 5 }

	swhPortConfigFlowControl OBJECT-TYPE
		SYNTAX      INTEGER { off(0), on(1) }
		MAX-ACCESS  read-write
		STATUS      current
		DESCRIPTION
			"Flow Control."
		::= { swhPortConfigEntry 6 }

	swhPortConfigDescription OBJECT-TYPE
		SYNTAX      DisplayString
		MAX-ACCESS  read-write
		STATUS      current
		DESCRIPTION
			"Port Description."
		::= { swhPortConfigEntry 7 }

	swhPortConfigMediaType OBJECT-TYPE
		SYNTAX      INTEGER { copper(0), fiber(1) }
		MAX-ACCESS  read-only
		STATUS      current
		DESCRIPTION
			"Port Media Type."
		::= { swhPortConfigEntry 8 }


-- SwitchManagement(4).VLANConfiguration(4)

	swhPortVLANConfiguration
		OBJECT IDENTIFIER ::= { swhVLANConfiguration 1 }

	swh8021QVLANConfiguration
		OBJECT IDENTIFIER ::= { swhVLANConfiguration 2 }

	swhVLANTranslationConfiguration
		OBJECT IDENTIFIER ::= { swhVLANConfiguration 7 }

	swhSelectiveQinQConfiguration
		OBJECT IDENTIFIER ::= { swhVLANConfiguration 9 }


-- SwitchManagement(4).VLANConfiguration(4).PortVLANConfiguration(1)

	swhPortVLANConfigTable OBJECT-TYPE
		SYNTAX      SEQUENCE OF SwhPortVLANConfigEntry
		MAX-ACCESS  not-accessible
		STATUS      current
		DESCRIPTION
			"Table of port based VLAN configuration."
		::= { swhPortVLANConfiguration 1 }

	-- Table Entry
	swhPortVLANConfigEntry OBJECT-TYPE
		SYNTAX      SwhPortVLANConfigEntry
		MAX-ACCESS  not-accessible
		STATUS      current
		DESCRIPTION
			"An entry in the table, containing information about port based VLAN config."
		INDEX    { swhPortVLANConfigIndex }
		::= { swhPortVLANConfigTable 1 }

	SwhPortVLANConfigEntry ::=
		SEQUENCE {
			swhPortVLANConfigIndex
				INTEGER,
			swhPortVLANConfigValid
				INTEGER,
			swhPortVLANConfigName
				DisplayString,
			swhPortVLANConfigPort1
				INTEGER,
			swhPortVLANConfigPort2
				INTEGER,
			swhPortVLANConfigPort3
				INTEGER,
			swhPortVLANConfigPort4
				INTEGER,
			swhPortVLANConfigPort5
				INTEGER,
			swhPortVLANConfigPort6
				INTEGER,
			swhPortVLANConfigPort7
				INTEGER,
			swhPortVLANConfigPort8
				INTEGER,
			swhPortVLANConfigPort9
				INTEGER,
			swhPortVLANConfigPort10
				INTEGER,
			swhPortVLANConfigPort11
				INTEGER,
			swhPortVLANConfigPort12
				INTEGER,
			swhPortVLANConfigCPU
				INTEGER,
			swhPortVLANConfigDelete
				INTEGER
		}

	swhPortVLANConfigIndex OBJECT-TYPE
		SYNTAX      INTEGER (0..2147483647)
		MAX-ACCESS  not-accessible
		STATUS      current
		DESCRIPTION
			"A unique value for each index."
		::= { swhPortVLANConfigEntry 1 }

	swhPortVLANConfigValid OBJECT-TYPE
		SYNTAX      INTEGER { invalid(0), valid(1) }
		MAX-ACCESS  read-only
		STATUS      current
		DESCRIPTION
			"This entry is valid or invalid."
		::= { swhPortVLANConfigEntry 2 }

	swhPortVLANConfigName OBJECT-TYPE
		SYNTAX      DisplayString
		MAX-ACCESS  read-write
		STATUS      current
		DESCRIPTION
			"Port Based VLAN name."
		::= { swhPortVLANConfigEntry 4 }

	swhPortVLANConfigPort1 OBJECT-TYPE
		SYNTAX      INTEGER { b(0), v(1) }
		MAX-ACCESS  read-write
		STATUS      current
		DESCRIPTION
			"b : Blocked  v : Member"
		::= { swhPortVLANConfigEntry 5 }

	swhPortVLANConfigPort2 OBJECT-TYPE
		SYNTAX      INTEGER { b(0), v(1) }
		MAX-ACCESS  read-write
		STATUS      current
		DESCRIPTION
			"b : Blocked  v : Member"
		::= { swhPortVLANConfigEntry 6 }

	swhPortVLANConfigPort3 OBJECT-TYPE
		SYNTAX      INTEGER { b(0), v(1) }
		MAX-ACCESS  read-write
		STATUS      current
		DESCRIPTION
			"b : Blocked  v : Member"
		::= { swhPortVLANConfigEntry 7 }

	swhPortVLANConfigPort4 OBJECT-TYPE
		SYNTAX      INTEGER { b(0), v(1) }
		MAX-ACCESS  read-write
		STATUS      current
		DESCRIPTION
			"b : Blocked  v : Member"
		::= { swhPortVLANConfigEntry 8 }

	swhPortVLANConfigPort5 OBJECT-TYPE
		SYNTAX      INTEGER { b(0), v(1) }
		MAX-ACCESS  read-write
		STATUS      current
		DESCRIPTION
			"b : Blocked  v : Member"
		::= { swhPortVLANConfigEntry 9 }

	swhPortVLANConfigPort6 OBJECT-TYPE
		SYNTAX      INTEGER { b(0), v(1) }
		MAX-ACCESS  read-write
		STATUS      current
		DESCRIPTION
			"b : Blocked  v : Member"
		::= { swhPortVLANConfigEntry 10 }

	swhPortVLANConfigPort7 OBJECT-TYPE
		SYNTAX      INTEGER { b(0), v(1) }
		MAX-ACCESS  read-write
		STATUS      current
		DESCRIPTION
			"b : Blocked  v : Member"
		::= { swhPortVLANConfigEntry 11 }

	swhPortVLANConfigPort8 OBJECT-TYPE
		SYNTAX      INTEGER { b(0), v(1) }
		MAX-ACCESS  read-write
		STATUS      current
		DESCRIPTION
			"b : Blocked  v : Member"
		::= { swhPortVLANConfigEntry 12 }

	swhPortVLANConfigPort9 OBJECT-TYPE
		SYNTAX      INTEGER { b(0), v(1) }
		MAX-ACCESS  read-write
		STATUS      current
		DESCRIPTION
			"b : Blocked  v : Member"
		::= { swhPortVLANConfigEntry 13 }

	swhPortVLANConfigPort10 OBJECT-TYPE
		SYNTAX      INTEGER { b(0), v(1) }
		MAX-ACCESS  read-write
		STATUS      current
		DESCRIPTION
			"b : Blocked  v : Member"
		::= { swhPortVLANConfigEntry 14 }

	swhPortVLANConfigPort11 OBJECT-TYPE
		SYNTAX      INTEGER { b(0), v(1) }
		MAX-ACCESS  read-write
		STATUS      current
		DESCRIPTION
			"b : Blocked  v : Member"
		::= { swhPortVLANConfigEntry 15 }

	swhPortVLANConfigPort12 OBJECT-TYPE
		SYNTAX      INTEGER { b(0), v(1) }
		MAX-ACCESS  read-write
		STATUS      current
		DESCRIPTION
			"b : Blocked  v : Member"
		::= { swhPortVLANConfigEntry 16 }

	swhPortVLANConfigCPU OBJECT-TYPE
		SYNTAX      INTEGER { b(0), v(1) }
		MAX-ACCESS  read-write
		STATUS      current
		DESCRIPTION
			"b : Blocked  v : Member"
		::= { swhPortVLANConfigEntry 55 }

	swhPortVLANConfigDelete OBJECT-TYPE
		SYNTAX      INTEGER { normal(0), delete(1) }
		MAX-ACCESS  read-write
		STATUS      current
		DESCRIPTION
			"Delete this entry."
		::= { swhPortVLANConfigEntry 56 }


-- SwitchManagement(4).VLANConfiguration(4).8021QVLANConfiguration(2)

	swh8021QTrunkVLAN
		OBJECT IDENTIFIER ::= { swh8021QVLANConfiguration 1 }

	swh8021QPortVLANConfig
		OBJECT IDENTIFIER ::= { swh8021QVLANConfiguration 2 }

	swh8021QManagementVLANConfig
		OBJECT IDENTIFIER ::= { swh8021QVLANConfiguration 5 }


-- SwitchManagement(4).VLANConfiguration(4).8021QVLANConfiguration(2).8021QTrunkVLAN(1)

	swh8021QTrunkVLANTable OBJECT-TYPE
		SYNTAX      SEQUENCE OF Swh8021QTrunkVLANEntry
		MAX-ACCESS  not-accessible
		STATUS      current
		DESCRIPTION
			"Table of 802.1Q trunk VLAN."
		::= { swh8021QTrunkVLAN 1 }

	-- Table Entry
	swh8021QTrunkVLANEntry OBJECT-TYPE
		SYNTAX      Swh8021QTrunkVLANEntry
		MAX-ACCESS  not-accessible
		STATUS      current
		DESCRIPTION
			"An entry in the table, containing information about 802.1Q trunk VLAN."
		INDEX    { swh8021QTrunkVLANIndex }
		::= { swh8021QTrunkVLANTable 1 }

	Swh8021QTrunkVLANEntry ::=
		SEQUENCE {
			swh8021QTrunkVLANIndex
				INTEGER,
			swh8021QTrunkVLANValid
				INTEGER,
			swh8021QTrunkVLANVID
				INTEGER,
			swh8021QTrunkVLANName
				DisplayString,
			swh8021QTrunkVLANPort1
				INTEGER,
			swh8021QTrunkVLANPort2
				INTEGER,
			swh8021QTrunkVLANPort3
				INTEGER,
			swh8021QTrunkVLANPort4
				INTEGER,
			swh8021QTrunkVLANPort5
				INTEGER,
			swh8021QTrunkVLANPort6
				INTEGER,
			swh8021QTrunkVLANPort7
				INTEGER,
			swh8021QTrunkVLANPort8
				INTEGER,
			swh8021QTrunkVLANPort9
				INTEGER,
			swh8021QTrunkVLANPort10
				INTEGER,
			swh8021QTrunkVLANPort11
				INTEGER,
			swh8021QTrunkVLANPort12
				INTEGER,
			swh8021QTrunkVLANCPU
				INTEGER,
			swh8021QTrunkVLANDelete
				INTEGER
		}

	swh8021QTrunkVLANIndex OBJECT-TYPE
		SYNTAX      INTEGER (0..2147483647)
		MAX-ACCESS  not-accessible
		STATUS      current
		DESCRIPTION
			"A unique value for each index."
		::= { swh8021QTrunkVLANEntry 1 }

	swh8021QTrunkVLANValid OBJECT-TYPE
		SYNTAX      INTEGER { invalid(0), valid(1) }
		MAX-ACCESS  read-only
		STATUS      current
		DESCRIPTION
			"This entry is valid or invalid."
		::= { swh8021QTrunkVLANEntry 2 }

	swh8021QTrunkVLANVID OBJECT-TYPE
		SYNTAX      INTEGER (1..4094)
		MAX-ACCESS  read-write
		STATUS      current
		DESCRIPTION
			"VLAN ID. (1-4094)"
		::= { swh8021QTrunkVLANEntry 3 }

	swh8021QTrunkVLANName OBJECT-TYPE
		SYNTAX      DisplayString
		MAX-ACCESS  read-write
		STATUS      current
		DESCRIPTION
			"Trunk VLAN name."
		::= { swh8021QTrunkVLANEntry 4 }

	swh8021QTrunkVLANPort1 OBJECT-TYPE
		SYNTAX      INTEGER { b(0), v(1) }
		MAX-ACCESS  read-write
		STATUS      current
		DESCRIPTION
			"b : Blocked  v : Member"
		::= { swh8021QTrunkVLANEntry 5 }

	swh8021QTrunkVLANPort2 OBJECT-TYPE
		SYNTAX      INTEGER { b(0), v(1) }
		MAX-ACCESS  read-write
		STATUS      current
		DESCRIPTION
			"b : Blocked  v : Member"
		::= { swh8021QTrunkVLANEntry 6 }

	swh8021QTrunkVLANPort3 OBJECT-TYPE
		SYNTAX      INTEGER { b(0), v(1) }
		MAX-ACCESS  read-write
		STATUS      current
		DESCRIPTION
			"b : Blocked  v : Member"
		::= { swh8021QTrunkVLANEntry 7 }

	swh8021QTrunkVLANPort4 OBJECT-TYPE
		SYNTAX      INTEGER { b(0), v(1) }
		MAX-ACCESS  read-write
		STATUS      current
		DESCRIPTION
			"b : Blocked  v : Member"
		::= { swh8021QTrunkVLANEntry 8 }

	swh8021QTrunkVLANPort5 OBJECT-TYPE
		SYNTAX      INTEGER { b(0), v(1) }
		MAX-ACCESS  read-write
		STATUS      current
		DESCRIPTION
			"b : Blocked  v : Member"
		::= { swh8021QTrunkVLANEntry 9 }

	swh8021QTrunkVLANPort6 OBJECT-TYPE
		SYNTAX      INTEGER { b(0), v(1) }
		MAX-ACCESS  read-write
		STATUS      current
		DESCRIPTION
			"b : Blocked  v : Member"
		::= { swh8021QTrunkVLANEntry 10 }

	swh8021QTrunkVLANPort7 OBJECT-TYPE
		SYNTAX      INTEGER { b(0), v(1) }
		MAX-ACCESS  read-write
		STATUS      current
		DESCRIPTION
			"b : Blocked  v : Member"
		::= { swh8021QTrunkVLANEntry 11 }

	swh8021QTrunkVLANPort8 OBJECT-TYPE
		SYNTAX      INTEGER { b(0), v(1) }
		MAX-ACCESS  read-write
		STATUS      current
		DESCRIPTION
			"b : Blocked  v : Member"
		::= { swh8021QTrunkVLANEntry 12 }

	swh8021QTrunkVLANPort9 OBJECT-TYPE
		SYNTAX      INTEGER { b(0), v(1) }
		MAX-ACCESS  read-write
		STATUS      current
		DESCRIPTION
			"b : Blocked  v : Member"
		::= { swh8021QTrunkVLANEntry 13 }

	swh8021QTrunkVLANPort10 OBJECT-TYPE
		SYNTAX      INTEGER { b(0), v(1) }
		MAX-ACCESS  read-write
		STATUS      current
		DESCRIPTION
			"b : Blocked  v : Member"
		::= { swh8021QTrunkVLANEntry 14 }

	swh8021QTrunkVLANPort11 OBJECT-TYPE
		SYNTAX      INTEGER { b(0), v(1) }
		MAX-ACCESS  read-write
		STATUS      current
		DESCRIPTION
			"b : Blocked  v : Member"
		::= { swh8021QTrunkVLANEntry 15 }

	swh8021QTrunkVLANPort12 OBJECT-TYPE
		SYNTAX      INTEGER { b(0), v(1) }
		MAX-ACCESS  read-write
		STATUS      current
		DESCRIPTION
			"b : Blocked  v : Member"
		::= { swh8021QTrunkVLANEntry 16 }

	swh8021QTrunkVLANCPU OBJECT-TYPE
		SYNTAX      INTEGER { b(0), v(1) }
		MAX-ACCESS  read-only
		STATUS      current
		DESCRIPTION
			"b : Blocked  v : Member"
		::= { swh8021QTrunkVLANEntry 55 }

	swh8021QTrunkVLANDelete OBJECT-TYPE
		SYNTAX      INTEGER { normal(0), delete(1) }
		MAX-ACCESS  read-write
		STATUS      current
		DESCRIPTION
			"Delete this entry."
		::= { swh8021QTrunkVLANEntry 56 }


-- SwitchManagement(4).VLANConfiguration(4).8021QVLANConfiguration(2).8021QPortVLANConfig(2)

	swh8021QCPUPVID OBJECT-TYPE
		SYNTAX      INTEGER (1..4094)
		MAX-ACCESS  read-only
		STATUS      current
		DESCRIPTION
			"CPU default port VLAN ID."
		::= { swh8021QPortVLANConfig 1 }

	swh8021QTunnelEtherType OBJECT-TYPE
		SYNTAX      DisplayString
		MAX-ACCESS  read-write
		STATUS      current
		DESCRIPTION
			"802.1Q Tunnel Ether Type. (0x0000-0xFFFF)"
		::= { swh8021QPortVLANConfig 14 }


-- SwitchManagement(4).VLANConfiguration(4).8021QVLANConfiguration(2).8021QPortVLANConfig(2).8021QPortVLANConfigTable(2)

	swh8021QPortVLANConfigTable OBJECT-TYPE
		SYNTAX      SEQUENCE OF Swh8021QPortVLANConfigEntry
		MAX-ACCESS  not-accessible
		STATUS      current
		DESCRIPTION
			"Table of 802.1Q port VLAN ID configuration."
		::= { swh8021QPortVLANConfig 2 }

	-- Table Entry
	swh8021QPortVLANConfigEntry OBJECT-TYPE
		SYNTAX      Swh8021QPortVLANConfigEntry
		MAX-ACCESS  not-accessible
		STATUS      current
		DESCRIPTION
			"An entry in the table, containing information about 802.1Q port VLAN ID config."
		INDEX    { swh8021QPortVLANConfigIndex }
		::= { swh8021QPortVLANConfigTable 1 }

	Swh8021QPortVLANConfigEntry ::=
		SEQUENCE {
			swh8021QPortVLANConfigIndex
				INTEGER,
			swh8021QPortVLANConfigMode
				INTEGER,
			swh8021QPortVLANConfigPVID
				INTEGER,
			swh8021QPortVLANConfigTrunkVLAN
				DisplayString
		}

	swh8021QPortVLANConfigIndex OBJECT-TYPE
		SYNTAX      INTEGER (0..2147483647)
		MAX-ACCESS  not-accessible
		STATUS      current
		DESCRIPTION
			"A unique value for each index."
		::= { swh8021QPortVLANConfigEntry 1 }

	swh8021QPortVLANConfigPVID OBJECT-TYPE
		SYNTAX      INTEGER (1..4094)
		MAX-ACCESS  read-write
		STATUS      current
		DESCRIPTION
			"PVID. (1-4094)"
		::= { swh8021QPortVLANConfigEntry 2 }

	swh8021QPortVLANConfigMode OBJECT-TYPE
		SYNTAX      INTEGER { access(0), trunk(1), trunknative(2), dot1qtunnel(3), selectiveqinq(4) }
		MAX-ACCESS  read-write
		STATUS      current
		DESCRIPTION
			"Mode."
		::= { swh8021QPortVLANConfigEntry 20 }

	swh8021QPortVLANConfigTrunkVLAN OBJECT-TYPE
		SYNTAX      DisplayString
		MAX-ACCESS  read-write
		STATUS      current
		DESCRIPTION
			"Trunk-VLAN. (1-4094)"
		::= { swh8021QPortVLANConfigEntry 25 }


-- SwitchManagement(4).VLANConfiguration(4).8021QVLANConfiguration(2).8021QManagementVLANConfig(5)

	swh8021QManagementVLANConfigCPUVID OBJECT-TYPE
		SYNTAX      INTEGER (1..4094)
		MAX-ACCESS  read-write
		STATUS      current
		DESCRIPTION
			"CPU VLAN ID. (1-4094)"
		::= { swh8021QManagementVLANConfig 1 }

	swh8021QManagementVLANConfigVLANMode OBJECT-TYPE
		SYNTAX      INTEGER { access(0), trunk(1), trunknative(2) }
		MAX-ACCESS  read-write
		STATUS      current
		DESCRIPTION
			"VLAN Mode."
		::= { swh8021QManagementVLANConfig 3 }

	swh8021QManagementVLANConfigPort1 OBJECT-TYPE
		SYNTAX      INTEGER { b(0), v(1) }
		MAX-ACCESS  read-write
		STATUS      current
		DESCRIPTION
			"b : Blocked  v : Member"
		::= { swh8021QManagementVLANConfig 5 }

	swh8021QManagementVLANConfigPort2 OBJECT-TYPE
		SYNTAX      INTEGER { b(0), v(1) }
		MAX-ACCESS  read-write
		STATUS      current
		DESCRIPTION
			"b : Blocked  v : Member"
		::= { swh8021QManagementVLANConfig 6 }

	swh8021QManagementVLANConfigPort3 OBJECT-TYPE
		SYNTAX      INTEGER { b(0), v(1) }
		MAX-ACCESS  read-write
		STATUS      current
		DESCRIPTION
			"b : Blocked  v : Member"
		::= { swh8021QManagementVLANConfig 7 }

	swh8021QManagementVLANConfigPort4 OBJECT-TYPE
		SYNTAX      INTEGER { b(0), v(1) }
		MAX-ACCESS  read-write
		STATUS      current
		DESCRIPTION
			"b : Blocked  v : Member"
		::= { swh8021QManagementVLANConfig 8 }

	swh8021QManagementVLANConfigPort5 OBJECT-TYPE
		SYNTAX      INTEGER { b(0), v(1) }
		MAX-ACCESS  read-write
		STATUS      current
		DESCRIPTION
			"b : Blocked  v : Member"
		::= { swh8021QManagementVLANConfig 9 }

	swh8021QManagementVLANConfigPort6 OBJECT-TYPE
		SYNTAX      INTEGER { b(0), v(1) }
		MAX-ACCESS  read-write
		STATUS      current
		DESCRIPTION
			"b : Blocked  v : Member"
		::= { swh8021QManagementVLANConfig 10 }

	swh8021QManagementVLANConfigPort7 OBJECT-TYPE
		SYNTAX      INTEGER { b(0), v(1) }
		MAX-ACCESS  read-write
		STATUS      current
		DESCRIPTION
			"b : Blocked  v : Member"
		::= { swh8021QManagementVLANConfig 11 }

	swh8021QManagementVLANConfigPort8 OBJECT-TYPE
		SYNTAX      INTEGER { b(0), v(1) }
		MAX-ACCESS  read-write
		STATUS      current
		DESCRIPTION
			"b : Blocked  v : Member"
		::= { swh8021QManagementVLANConfig 12 }

	swh8021QManagementVLANConfigPort9 OBJECT-TYPE
		SYNTAX      INTEGER { b(0), v(1) }
		MAX-ACCESS  read-write
		STATUS      current
		DESCRIPTION
			"b : Blocked  v : Member"
		::= { swh8021QManagementVLANConfig 13 }

	swh8021QManagementVLANConfigPort10 OBJECT-TYPE
		SYNTAX      INTEGER { b(0), v(1) }
		MAX-ACCESS  read-write
		STATUS      current
		DESCRIPTION
			"b : Blocked  v : Member"
		::= { swh8021QManagementVLANConfig 14 }

	swh8021QManagementVLANConfigPort11 OBJECT-TYPE
		SYNTAX      INTEGER { b(0), v(1) }
		MAX-ACCESS  read-write
		STATUS      current
		DESCRIPTION
			"b : Blocked  v : Member"
		::= { swh8021QManagementVLANConfig 15 }

	swh8021QManagementVLANConfigPort12 OBJECT-TYPE
		SYNTAX      INTEGER { b(0), v(1) }
		MAX-ACCESS  read-write
		STATUS      current
		DESCRIPTION
			"b : Blocked  v : Member"
		::= { swh8021QManagementVLANConfig 16 }


-- SwitchManagement(4).VLANConfiguration(4).VLANTranslationConfiguration(7)

	swhVLANTranslationConfigVLANTranslation OBJECT-TYPE
		SYNTAX      INTEGER { disable(0), enable(1) }
		MAX-ACCESS  read-write
		STATUS      current
		DESCRIPTION
			"VLAN Translation."
		::= { swhVLANTranslationConfiguration 1 }


-- SwitchManagement(4).VLANConfiguration(4).VLANTranslationConfiguration(7).VLANTranslationConfigTable(5)

	swhVLANTranslationConfigTable OBJECT-TYPE
		SYNTAX      SEQUENCE OF SwhVLANTranslationConfigEntry
		MAX-ACCESS  not-accessible
		STATUS      current
		DESCRIPTION
			"Table of VLAN translation configuration."
		::= { swhVLANTranslationConfiguration 5 }

	-- Table Entry
	swhVLANTranslationConfigEntry OBJECT-TYPE
		SYNTAX      SwhVLANTranslationConfigEntry
		MAX-ACCESS  not-accessible
		STATUS      current
		DESCRIPTION
			"An entry in the table, containing information about VLAN translation config."
		INDEX    { swhVLANTranslationConfigIndex }
		::= { swhVLANTranslationConfigTable 1 }

	SwhVLANTranslationConfigEntry ::=
		SEQUENCE {
			swhVLANTranslationConfigIndex
				INTEGER,
			swhVLANTranslationConfigValid
				INTEGER,
			swhVLANTranslationConfigName
				DisplayString,
			swhVLANTranslationConfigPort
				INTEGER,
			swhVLANTranslationConfigOriginalVID
				INTEGER,
			swhVLANTranslationConfigMappedVID
				INTEGER,
			swhVLANTranslationConfigPriority
				INTEGER,
			swhVLANTranslationConfigDelete
				INTEGER
		}

	swhVLANTranslationConfigIndex OBJECT-TYPE
		SYNTAX      INTEGER (0..2147483647)
		MAX-ACCESS  not-accessible
		STATUS      current
		DESCRIPTION
			"A unique value for each index."
		::= { swhVLANTranslationConfigEntry 1 }

	swhVLANTranslationConfigValid OBJECT-TYPE
		SYNTAX      INTEGER { invalid(0), valid(1) }
		MAX-ACCESS  read-only
		STATUS      current
		DESCRIPTION
			"This entry is valid or invalid."
		::= { swhVLANTranslationConfigEntry 2 }

	swhVLANTranslationConfigName OBJECT-TYPE
		SYNTAX      DisplayString
		MAX-ACCESS  read-write
		STATUS      current
		DESCRIPTION
			"VLAN Translation Name."
		::= { swhVLANTranslationConfigEntry 4 }

	swhVLANTranslationConfigPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Port Number."
		::= { swhVLANTranslationConfigEntry 5 }

	swhVLANTranslationConfigOriginalVID OBJECT-TYPE
		SYNTAX      INTEGER (1..4094)
		MAX-ACCESS  read-write
		STATUS      current
		DESCRIPTION
			"Specify Original VLAN ID. (1-4094)"
		::= { swhVLANTranslationConfigEntry 6 }

	swhVLANTranslationConfigMappedVID OBJECT-TYPE
		SYNTAX      INTEGER (1..4094)
		MAX-ACCESS  read-write
		STATUS      current
		DESCRIPTION
			"Specify Translated VLAN ID. (1-4094)"
		::= { swhVLANTranslationConfigEntry 7 }

	swhVLANTranslationConfigPriority OBJECT-TYPE
		SYNTAX      INTEGER (0..7)
		MAX-ACCESS  read-write
		STATUS      current
		DESCRIPTION
			"Specify Priority. (0-7)"
		::= { swhVLANTranslationConfigEntry 8 }

	swhVLANTranslationConfigDelete OBJECT-TYPE
		SYNTAX      INTEGER { normal(0), delete(1) }
		MAX-ACCESS  read-write
		STATUS      current
		DESCRIPTION
			"Delete this entry."
		::= { swhVLANTranslationConfigEntry 10 }


-- SwitchManagement(4).VLANConfiguration(4).SelectiveQinQConfiguration(9)

	swhSelectiveQinQConfigSelectiveQinQ OBJECT-TYPE
		SYNTAX      INTEGER { disable(0), enable(1) }
		MAX-ACCESS  read-write
		STATUS      current
		DESCRIPTION
			"Selective QinQ."
		::= { swhSelectiveQinQConfiguration 1 }

	swhSelectiveQinQConfigSelectiveQinQSortBy OBJECT-TYPE
		SYNTAX      INTEGER { entry(0), port(1), inner-vid(2), outer-vid(3) }
		MAX-ACCESS  read-write
		STATUS      current
		DESCRIPTION
			"Selective QinQ SortBy."
		::= { swhSelectiveQinQConfiguration 3 }

	swhSelectiveQinQConfigSelectiveQinQDefaultTPID OBJECT-TYPE
		SYNTAX      DisplayString
		MAX-ACCESS  read-only
		STATUS      current
		DESCRIPTION
			"Default TPID. (0x0000-0xFFFF)"
		::= { swhSelectiveQinQConfiguration 6 }

	swhSelectiveQinQConfigSelectiveQinQTPID1 OBJECT-TYPE
		SYNTAX      DisplayString
		MAX-ACCESS  read-write
		STATUS      current
		DESCRIPTION
			"TPID1. (0x0000-0xFFFF)"
		::= { swhSelectiveQinQConfiguration 7 }

	swhSelectiveQinQConfigSelectiveQinQTPID2 OBJECT-TYPE
		SYNTAX      DisplayString
		MAX-ACCESS  read-write
		STATUS      current
		DESCRIPTION
			"TPID2. (0x0000-0xFFFF)"
		::= { swhSelectiveQinQConfiguration 8 }

	swhSelectiveQinQConfigSelectiveQinQTPID3 OBJECT-TYPE
		SYNTAX      DisplayString
		MAX-ACCESS  read-write
		STATUS      current
		DESCRIPTION
			"TPID3. (0x0000-0xFFFF)"
		::= { swhSelectiveQinQConfiguration 9 }


-- SwitchManagement(4).VLANConfiguration(4).SelectiveQinQConfiguration(9).SelectiveQinQConfigTable(5)

	swhSelectiveQinQConfigTable OBJECT-TYPE
		SYNTAX      SEQUENCE OF SwhSelectiveQinQConfigEntry
		MAX-ACCESS  not-accessible
		STATUS      current
		DESCRIPTION
			"Table of selective QinQ."
		::= { swhSelectiveQinQConfiguration 5 }

	-- Table Entry
	swhSelectiveQinQConfigEntry OBJECT-TYPE
		SYNTAX      SwhSelectiveQinQConfigEntry
		MAX-ACCESS  not-accessible
		STATUS      current
		DESCRIPTION
			"An entry in the table, containing information about selective QinQ."
		INDEX    { swhSelectiveQinQConfigIndex }
		::= { swhSelectiveQinQConfigTable 1 }

	SwhSelectiveQinQConfigEntry ::=
		SEQUENCE {
			swhSelectiveQinQConfigIndex
				INTEGER,
			swhSelectiveQinQConfigConfigEntry
				INTEGER,
			swhSelectiveQinQConfigValid
				INTEGER,
			swhSelectiveQinQConfigName
				DisplayString,
			swhSelectiveQinQConfigPort
				DisplayString,
			swhSelectiveQinQConfigInnerVID
				DisplayString,
			swhSelectiveQinQConfigOuterVID
				INTEGER,
			swhSelectiveQinQConfigTPID
				INTEGER,
			swhSelectiveQinQConfigEtherType
				DisplayString,
			swhSelectiveQinQConfigPriority
				INTEGER,
			swhSelectiveQinQConfigDelete
				INTEGER
		}

	swhSelectiveQinQConfigIndex OBJECT-TYPE
		SYNTAX      INTEGER (0..2147483647)
		MAX-ACCESS  not-accessible
		STATUS      current
		DESCRIPTION
			"A unique value for each index."
		::= { swhSelectiveQinQConfigEntry 1 }

	swhSelectiveQinQConfigValid OBJECT-TYPE
		SYNTAX      INTEGER { invalid(0), valid(1) }
		MAX-ACCESS  read-only
		STATUS      current
		DESCRIPTION
			"This entry is valid or invalid."
		::= { swhSelectiveQinQConfigEntry 2 }

	swhSelectiveQinQConfigName OBJECT-TYPE
		SYNTAX      DisplayString
		MAX-ACCESS  read-write
		STATUS      current
		DESCRIPTION
			"Selective QinQ Name."
		::= { swhSelectiveQinQConfigEntry 4 }

	swhSelectiveQinQConfigPort OBJECT-TYPE
		SYNTAX      DisplayString
		MAX-ACCESS  read-write
		STATUS      current
		DESCRIPTION
			"Port Number."
		::= { swhSelectiveQinQConfigEntry 5 }

	swhSelectiveQinQConfigInnerVID OBJECT-TYPE
		SYNTAX      DisplayString
		MAX-ACCESS  read-write
		STATUS      current
		DESCRIPTION
			"Specify Original VLAN ID. (1-4094)"
		::= { swhSelectiveQinQConfigEntry 6 }

	swhSelectiveQinQConfigOuterVID OBJECT-TYPE
		SYNTAX      INTEGER (1..4094)
		MAX-ACCESS  read-write
		STATUS      current
		DESCRIPTION
			"Specify Selective QinQ ID. (1-4094)"
		::= { swhSelectiveQinQConfigEntry 7 }

	swhSelectiveQinQConfigTPID OBJECT-TYPE
		SYNTAX      INTEGER { default-tpid(0), tpid1(1), tpid2(2), tpid3(3) }
		MAX-ACCESS  read-write
		STATUS      current
		DESCRIPTION
			"Specify TPID. (0-3)"
		::= { swhSelectiveQinQConfigEntry 8 }

	swhSelectiveQinQConfigPriority OBJECT-TYPE
		SYNTAX      INTEGER (0..7)
		MAX-ACCESS  read-write
		STATUS      current
		DESCRIPTION
			"Specify Priority. (0-7)"
		::= { swhSelectiveQinQConfigEntry 9 }

	swhSelectiveQinQConfigDelete OBJECT-TYPE
		SYNTAX      INTEGER { normal(0), delete(1) }
		MAX-ACCESS  read-write
		STATUS      current
		DESCRIPTION
			"Delete this entry."
		::= { swhSelectiveQinQConfigEntry 10 }

	swhSelectiveQinQConfigConfigEntry OBJECT-TYPE
		SYNTAX      INTEGER (0..2147483647)
		MAX-ACCESS  read-only
		STATUS      current
		DESCRIPTION
			"A unique value for Selective QinQ entry."
		::= { swhSelectiveQinQConfigEntry 11 }

	swhSelectiveQinQConfigEtherType OBJECT-TYPE
		SYNTAX      DisplayString
		MAX-ACCESS  read-only
		STATUS      current
		DESCRIPTION
			"Specify Ether Type."
		::= { swhSelectiveQinQConfigEntry 12 }


-- SwitchManagement(4).LoopDetection(13)

	swhLoopConfigLoopDetection OBJECT-TYPE
		SYNTAX      INTEGER { disable(0), enable(1) }
		MAX-ACCESS  read-write
		STATUS      current
		DESCRIPTION
			"Loop Detection."
		::= { swhLoopDetection 60 }

	swhLoopConfigDetectionInterval OBJECT-TYPE
		SYNTAX      INTEGER (1..20)
		MAX-ACCESS  read-write
		STATUS      current
		DESCRIPTION
			"Sending Detected Interval. (1-20 Secs)"
		::= { swhLoopDetection 63 }

	swhLoopConfigUnlockInterval OBJECT-TYPE
		SYNTAX      INTEGER (1..1440)
		MAX-ACCESS  read-write
		STATUS      current
		DESCRIPTION
			"Looped port unlock-interval. (1-1440 Mins) 
			 Set the interval to check the port is loop-free or not."
		::= { swhLoopDetection 64 }

	swhLoopConfigAllVLAN OBJECT-TYPE
		SYNTAX      INTEGER { disable(0), enable(1) }
		MAX-ACCESS  read-write
		STATUS      current
		DESCRIPTION
			"All VLAN."
		::= { swhLoopDetection 69 }

	swhLoopConfigVLAN1 OBJECT-TYPE
		SYNTAX      INTEGER (1..4094)
		MAX-ACCESS  read-write
		STATUS      current
		DESCRIPTION
			"Sending Detected VLAN ID. (1-4094)"
		::= { swhLoopDetection 65 }

	swhLoopConfigVLAN2 OBJECT-TYPE
		SYNTAX      INTEGER (1..4094)
		MAX-ACCESS  read-write
		STATUS      current
		DESCRIPTION
			"Sending Detected VLAN ID. (1-4094)"
		::= { swhLoopDetection 66 }

	swhLoopConfigVLAN3 OBJECT-TYPE
		SYNTAX      INTEGER (1..4094)
		MAX-ACCESS  read-write
		STATUS      current
		DESCRIPTION
			"Sending Detected VLAN ID. (1-4094)"
		::= { swhLoopDetection 67 }

	swhLoopConfigVLAN4 OBJECT-TYPE
		SYNTAX      INTEGER (1..4094)
		MAX-ACCESS  read-write
		STATUS      current
		DESCRIPTION
			"Sending Detected VLAN ID. (1-4094)"
		::= { swhLoopDetection 68 }

	swhLoopConfigPort1 OBJECT-TYPE
		SYNTAX      INTEGER { b(0), v(1) }
		MAX-ACCESS  read-write
		STATUS      current
		DESCRIPTION
			"b : Blocked  v : Member"
		::= { swhLoopDetection 1 }

	swhLoopConfigPort2 OBJECT-TYPE
		SYNTAX      INTEGER { b(0), v(1) }
		MAX-ACCESS  read-write
		STATUS      current
		DESCRIPTION
			"b : Blocked  v : Member"
		::= { swhLoopDetection 2 }

	swhLoopConfigPort3 OBJECT-TYPE
		SYNTAX      INTEGER { b(0), v(1) }
		MAX-ACCESS  read-write
		STATUS      current
		DESCRIPTION
			"b : Blocked  v : Member"
		::= { swhLoopDetection 3 }

	swhLoopConfigPort4 OBJECT-TYPE
		SYNTAX      INTEGER { b(0), v(1) }
		MAX-ACCESS  read-write
		STATUS      current
		DESCRIPTION
			"b : Blocked  v : Member"
		::= { swhLoopDetection 4 }

	swhLoopConfigPort5 OBJECT-TYPE
		SYNTAX      INTEGER { b(0), v(1) }
		MAX-ACCESS  read-write
		STATUS      current
		DESCRIPTION
			"b : Blocked  v : Member"
		::= { swhLoopDetection 5 }

	swhLoopConfigPort6 OBJECT-TYPE
		SYNTAX      INTEGER { b(0), v(1) }
		MAX-ACCESS  read-write
		STATUS      current
		DESCRIPTION
			"b : Blocked  v : Member"
		::= { swhLoopDetection 6 }

	swhLoopConfigPort7 OBJECT-TYPE
		SYNTAX      INTEGER { b(0), v(1) }
		MAX-ACCESS  read-write
		STATUS      current
		DESCRIPTION
			"b : Blocked  v : Member"
		::= { swhLoopDetection 7 }

	swhLoopConfigPort8 OBJECT-TYPE
		SYNTAX      INTEGER { b(0), v(1) }
		MAX-ACCESS  read-write
		STATUS      current
		DESCRIPTION
			"b : Blocked  v : Member"
		::= { swhLoopDetection 8 }

	swhLoopConfigPort9 OBJECT-TYPE
		SYNTAX      INTEGER { b(0), v(1) }
		MAX-ACCESS  read-write
		STATUS      current
		DESCRIPTION
			"b : Blocked  v : Member"
		::= { swhLoopDetection 9 }

	swhLoopConfigPort10 OBJECT-TYPE
		SYNTAX      INTEGER { b(0), v(1) }
		MAX-ACCESS  read-write
		STATUS      current
		DESCRIPTION
			"b : Blocked  v : Member"
		::= { swhLoopDetection 10 }

	swhLoopConfigPort11 OBJECT-TYPE
		SYNTAX      INTEGER { b(0), v(1) }
		MAX-ACCESS  read-write
		STATUS      current
		DESCRIPTION
			"b : Blocked  v : Member"
		::= { swhLoopDetection 11 }

	swhLoopConfigPort12 OBJECT-TYPE
		SYNTAX      INTEGER { b(0), v(1) }
		MAX-ACCESS  read-write
		STATUS      current
		DESCRIPTION
			"b : Blocked  v : Member"
		::= { swhLoopDetection 12 }


-- SwitchManagement(4).LLDPConfiguration(14)

	swhLLDPConfigEnable OBJECT-TYPE
		SYNTAX      INTEGER { disable(0), enable(1) }
		MAX-ACCESS  read-write
		STATUS      current
		DESCRIPTION
			"disable : 0  enable : 1"
		::= { swhLLDPConfiguration 100 }

	swhLLDPConfigPort1 OBJECT-TYPE
		SYNTAX      INTEGER { b(0), v(1) }
		MAX-ACCESS  read-write
		STATUS      current
		DESCRIPTION
			"b : Blocked  v : Member"
		::= { swhLLDPConfiguration 1 }

	swhLLDPConfigPort2 OBJECT-TYPE
		SYNTAX      INTEGER { b(0), v(1) }
		MAX-ACCESS  read-write
		STATUS      current
		DESCRIPTION
			"b : Blocked  v : Member"
		::= { swhLLDPConfiguration 2 }

	swhLLDPConfigPort3 OBJECT-TYPE
		SYNTAX      INTEGER { b(0), v(1) }
		MAX-ACCESS  read-write
		STATUS      current
		DESCRIPTION
			"b : Blocked  v : Member"
		::= { swhLLDPConfiguration 3 }

	swhLLDPConfigPort4 OBJECT-TYPE
		SYNTAX      INTEGER { b(0), v(1) }
		MAX-ACCESS  read-write
		STATUS      current
		DESCRIPTION
			"b : Blocked  v : Member"
		::= { swhLLDPConfiguration 4 }

	swhLLDPConfigPort5 OBJECT-TYPE
		SYNTAX      INTEGER { b(0), v(1) }
		MAX-ACCESS  read-write
		STATUS      current
		DESCRIPTION
			"b : Blocked  v : Member"
		::= { swhLLDPConfiguration 5 }

	swhLLDPConfigPort6 OBJECT-TYPE
		SYNTAX      INTEGER { b(0), v(1) }
		MAX-ACCESS  read-write
		STATUS      current
		DESCRIPTION
			"b : Blocked  v : Member"
		::= { swhLLDPConfiguration 6 }

	swhLLDPConfigPort7 OBJECT-TYPE
		SYNTAX      INTEGER { b(0), v(1) }
		MAX-ACCESS  read-write
		STATUS      current
		DESCRIPTION
			"b : Blocked  v : Member"
		::= { swhLLDPConfiguration 7 }

	swhLLDPConfigPort8 OBJECT-TYPE
		SYNTAX      INTEGER { b(0), v(1) }
		MAX-ACCESS  read-write
		STATUS      current
		DESCRIPTION
			"b : Blocked  v : Member"
		::= { swhLLDPConfiguration 8 }

	swhLLDPConfigPort9 OBJECT-TYPE
		SYNTAX      INTEGER { b(0), v(1) }
		MAX-ACCESS  read-write
		STATUS      current
		DESCRIPTION
			"b : Blocked  v : Member"
		::= { swhLLDPConfiguration 9 }

	swhLLDPConfigPort10 OBJECT-TYPE
		SYNTAX      INTEGER { b(0), v(1) }
		MAX-ACCESS  read-write
		STATUS      current
		DESCRIPTION
			"b : Blocked  v : Member"
		::= { swhLLDPConfiguration 10 }

	swhLLDPConfigPort11 OBJECT-TYPE
		SYNTAX      INTEGER { b(0), v(1) }
		MAX-ACCESS  read-write
		STATUS      current
		DESCRIPTION
			"b : Blocked  v : Member"
		::= { swhLLDPConfiguration 11 }

	swhLLDPConfigPort12 OBJECT-TYPE
		SYNTAX      INTEGER { b(0), v(1) }
		MAX-ACCESS  read-write
		STATUS      current
		DESCRIPTION
			"b : Blocked  v : Member"
		::= { swhLLDPConfiguration 12 }

	swhLLDPConfigReceiverHoldTime OBJECT-TYPE
		SYNTAX      INTEGER (1..3600)
		MAX-ACCESS  read-write
		STATUS      current
		DESCRIPTION
			"Receiver Hold-Time. (1-3600 Secs)"
		::= { swhLLDPConfiguration 90 }

	swhLLDPConfigSendingLLDPPacketInterval OBJECT-TYPE
		SYNTAX      INTEGER (1..180)
		MAX-ACCESS  read-write
		STATUS      current
		DESCRIPTION
			"Sending LLDP Packet Interval. (1-180 Secs)"
		::= { swhLLDPConfiguration 91 }

	swhLLDPConfigSendingLLDPPacketPerDiscover OBJECT-TYPE
		SYNTAX      INTEGER (1..16)
		MAX-ACCESS  read-write
		STATUS      current
		DESCRIPTION
			"Sending LLDP Packets Per Discover. (1-16 Packet)"
		::= { swhLLDPConfiguration 92 }

	swhLLDPConfigItem OBJECT-TYPE
		SYNTAX      DisplayString
		MAX-ACCESS  read-only
		STATUS      current
		DESCRIPTION
			"Selection of LLDP TLVs to send."
		::= { swhLLDPConfiguration 94 }

	swhLLDPConfigPortDescription OBJECT-TYPE
		SYNTAX      INTEGER { disable(0), enable(1) }
		MAX-ACCESS  read-write
		STATUS      current
		DESCRIPTION
			"Port Description."
		::= { swhLLDPConfiguration 95 }

	swhLLDPConfigSystemName OBJECT-TYPE
		SYNTAX      INTEGER { disable(0), enable(1) }
		MAX-ACCESS  read-write
		STATUS      current
		DESCRIPTION
			"System Name."
		::= { swhLLDPConfiguration 96 }

	swhLLDPConfigSystemDescription OBJECT-TYPE
		SYNTAX      INTEGER { disable(0), enable(1) }
		MAX-ACCESS  read-write
		STATUS      current
		DESCRIPTION
			"System Description."
		::= { swhLLDPConfiguration 97 }

	swhLLDPConfigSystemCapabilities OBJECT-TYPE
		SYNTAX      INTEGER { disable(0), enable(1) }
		MAX-ACCESS  read-write
		STATUS      current
		DESCRIPTION
			"System Capabilities."
		::= { swhLLDPConfiguration 98 }

	swhLLDPConfigManagementAddress OBJECT-TYPE
		SYNTAX      INTEGER { disable(0), enable(1) }
		MAX-ACCESS  read-write
		STATUS      current
		DESCRIPTION
			"Management Address."
		::= { swhLLDPConfiguration 99 }


-- SwitchManagement(4).PortMirroring(15)

	swhPortMirroringEnable OBJECT-TYPE
		SYNTAX      INTEGER { disable(0), enable(1) }
		MAX-ACCESS  read-write
		STATUS      current
		DESCRIPTION
			"Port Mirror."
		::= { swhPortMirroring 53 }


-- SwitchManagement(4).PortMirroring(15).PortMirrorSourcePortConfigTable(1)

	swhPortMirrorSourcePortConfigTable OBJECT-TYPE
		SYNTAX      SEQUENCE OF SwhPortMirrorSourcePortConfigEntry
		MAX-ACCESS  not-accessible
		STATUS      current
		DESCRIPTION
			"Table of port mirror source port configuration."
		::= { swhPortMirroring 1 }

	-- Table Entry
	swhPortMirrorSourcePortConfigEntry OBJECT-TYPE
		SYNTAX      SwhPortMirrorSourcePortConfigEntry
		MAX-ACCESS  not-accessible
		STATUS      current
		DESCRIPTION
			"An entry in the table, containing information about port mirror source port config."
		INDEX    { swhPortMirrorSourcePortConfigIndex }
		::= { swhPortMirrorSourcePortConfigTable 1 }

	SwhPortMirrorSourcePortConfigEntry ::=
		SEQUENCE {
			swhPortMirrorSourcePortConfigIndex
				INTEGER,
			swhPortMirrorSourcePortConfigIndexID
				INTEGER,
			swhPortMirrorSourcePortConfigState
				INTEGER,
			swhPortMirrorSourcePortConfigDestinationPort
				INTEGER,
			swhPortMirrorSourcePortConfigTXPortList
				DisplayString,
			swhPortMirrorSourcePortConfigRXPortList
				DisplayString,
			swhPortMirrorSourcePortConfigDelete
				INTEGER
		}

	swhPortMirrorSourcePortConfigIndex OBJECT-TYPE
		SYNTAX      INTEGER (0..2147483647)
		MAX-ACCESS  not-accessible
		STATUS      current
		DESCRIPTION
			"A unique value for each index."
		::= { swhPortMirrorSourcePortConfigEntry 1 }

	swhPortMirrorSourcePortConfigIndexID OBJECT-TYPE
		SYNTAX      INTEGER (1..4)
		MAX-ACCESS  read-only
		STATUS      current
		DESCRIPTION
			"Index ID."
		::= { swhPortMirrorSourcePortConfigEntry 8 }

	swhPortMirrorSourcePortConfigState OBJECT-TYPE
		SYNTAX      INTEGER { disable(0), enable(1) }
		MAX-ACCESS  read-write
		STATUS      current
		DESCRIPTION
			"State."
		::= { swhPortMirrorSourcePortConfigEntry 3 }

	swhPortMirrorSourcePortConfigDestinationPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Source Port Member."
		::= { swhPortMirrorSourcePortConfigEntry 4 }

	swhPortMirrorSourcePortConfigTXPortList OBJECT-TYPE
		SYNTAX      DisplayString
		MAX-ACCESS  read-write
		STATUS      current
		DESCRIPTION
			"Source Port TX Port List."
		::= { swhPortMirrorSourcePortConfigEntry 5 }

	swhPortMirrorSourcePortConfigRXPortList OBJECT-TYPE
		SYNTAX      DisplayString
		MAX-ACCESS  read-write
		STATUS      current
		DESCRIPTION
			"Source Port RX Port List."
		::= { swhPortMirrorSourcePortConfigEntry 6 }

	swhPortMirrorSourcePortConfigDelete OBJECT-TYPE
		SYNTAX      INTEGER { normal(0), delete(1) }
		MAX-ACCESS  read-write
		STATUS      current
		DESCRIPTION
			"Delete this entry."
		::= { swhPortMirrorSourcePortConfigEntry 7 }


-- SwitchManagement(4).DIConfiguration(22).DIConfigTable(1)

	swhDIConfigTable OBJECT-TYPE
		SYNTAX      SEQUENCE OF SwhDIConfigEntry
		MAX-ACCESS  not-accessible
		STATUS      current
		DESCRIPTION
			"Table of digital input."
		::= { swhDIConfiguration 1 }

	-- Table Entry
	swhDIConfigEntry OBJECT-TYPE
		SYNTAX      SwhDIConfigEntry
		MAX-ACCESS  not-accessible
		STATUS      current
		DESCRIPTION
			"An entry in the table, containing information about digital input."
		INDEX    { swhDIConfigIndex }
		::= { swhDIConfigTable 1 }

	SwhDIConfigEntry ::=
		SEQUENCE {
			swhDIConfigIndex
				INTEGER,
			swhDIConfigNormal
				INTEGER
		}

	swhDIConfigIndex OBJECT-TYPE
		SYNTAX      INTEGER (0..2147483647)
		MAX-ACCESS  not-accessible
		STATUS      current
		DESCRIPTION
			"A unique value for each index."
		::= { swhDIConfigEntry 1 }

	swhDIConfigNormal OBJECT-TYPE
		SYNTAX      INTEGER { close(0), open(1) }
		MAX-ACCESS  read-write
		STATUS      current
		DESCRIPTION
			"Digital input normal."
		::= { swhDIConfigEntry 2 }


-- SwitchManagement(4).MacAddressManagement(35)

	swhMACTableLearning
		OBJECT IDENTIFIER ::= { swhMacAddressManagement 1 }

	swhStaticMACTableConfiguration
		OBJECT IDENTIFIER ::= { swhMacAddressManagement 3 }


-- SwitchManagement(4).MacAddressManagement(35).MACTableLearning(1).MACTableLearningTable(2)

	swhMACTableLearningTable OBJECT-TYPE
		SYNTAX      SEQUENCE OF SwhMACTableLearningEntry
		MAX-ACCESS  not-accessible
		STATUS      current
		DESCRIPTION
			"Table of mac table learning."
		::= { swhMACTableLearning 2 }

	-- Table Entry
	swhMACTableLearningEntry OBJECT-TYPE
		SYNTAX      SwhMACTableLearningEntry
		MAX-ACCESS  not-accessible
		STATUS      current
		DESCRIPTION
			"An entry in the table, containing information about mac table learning."
		INDEX    { swhMACTableLearningIndex }
		::= { swhMACTableLearningTable 1 }

	SwhMACTableLearningEntry ::=
		SEQUENCE {
			swhMACTableLearningIndex
				INTEGER,
			swhMACTableLearningLearning
				INTEGER
		}

	swhMACTableLearningIndex OBJECT-TYPE
		SYNTAX      INTEGER (0..2147483647)
		MAX-ACCESS  not-accessible
		STATUS      current
		DESCRIPTION
			"A unique value for each index."
		::= { swhMACTableLearningEntry 1 }

	swhMACTableLearningLearning OBJECT-TYPE
		SYNTAX      INTEGER { auto(0), disable(1) }
		MAX-ACCESS  read-write
		STATUS      current
		DESCRIPTION
			"Learning."
		::= { swhMACTableLearningEntry 2 }


-- SwitchManagement(4).MacAddressManagement(35).StaticMACTableConfiguration(3)

	swhStaticMACTablePort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Per port search static mac table."
		::= { swhStaticMACTableConfiguration 1 }


-- SwitchManagement(4).MacAddressManagement(35).StaticMACTableConfiguration(3).StaticForwardTable(2)

	swhStaticForwardTable OBJECT-TYPE
		SYNTAX      SEQUENCE OF SwhStaticForwardEntry
		MAX-ACCESS  not-accessible
		STATUS      current
		DESCRIPTION
			"Table of static forwarding."
		::= { swhStaticMACTableConfiguration 2 }

	-- Table Entry
	swhStaticForwardEntry OBJECT-TYPE
		SYNTAX      SwhStaticForwardEntry
		MAX-ACCESS  not-accessible
		STATUS      current
		DESCRIPTION
			"An entry in the table, containing information about static forwarding."
		INDEX    { swhStaticForwardIndex }
		::= { swhStaticForwardTable 1 }

	SwhStaticForwardEntry ::=
		SEQUENCE {
			swhStaticForwardIndex
				INTEGER,
			swhStaticForwardValid
				INTEGER,
			swhStaticForwardMacAddress
				MacAddress,
			swhStaticForwardVID
				INTEGER,
			swhStaticForwardPort
				INTEGER,
			swhStaticForwardType
				DisplayString,
			swhStaticForwardAddtoStatic
				INTEGER,
			swhStaticForwardDelete
				INTEGER
		}

	swhStaticForwardIndex OBJECT-TYPE
		SYNTAX      INTEGER (0..2147483647)
		MAX-ACCESS  not-accessible
		STATUS      current
		DESCRIPTION
			"A unique value for each index."
		::= { swhStaticForwardEntry 1 }

	swhStaticForwardValid OBJECT-TYPE
		SYNTAX      INTEGER { invalid(0), valid(1) }
		MAX-ACCESS  read-only
		STATUS      current
		DESCRIPTION
			"This entry is valid or invalid."
		::= { swhStaticForwardEntry 2 }

	swhStaticForwardMacAddress OBJECT-TYPE
		SYNTAX      MacAddress
		MAX-ACCESS  read-write
		STATUS      current
		DESCRIPTION
			"MAC address."
		::= { swhStaticForwardEntry 3 }

	swhStaticForwardVID OBJECT-TYPE
		SYNTAX      INTEGER (1..4094)
		MAX-ACCESS  read-write
		STATUS      current
		DESCRIPTION
			"VLAN ID. (1-4094)"
		::= { swhStaticForwardEntry 4 }

	swhStaticForwardPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-only
		STATUS      current
		DESCRIPTION
			"Static forward packets to this port."
		::= { swhStaticForwardEntry 5 }

	swhStaticForwardDelete OBJECT-TYPE
		SYNTAX      INTEGER { normal(0), delete(1) }
		MAX-ACCESS  read-write
		STATUS      current
		DESCRIPTION
			"Delete this entry."
		::= { swhStaticForwardEntry 6 }

	swhStaticForwardType OBJECT-TYPE
		SYNTAX      DisplayString
		MAX-ACCESS  read-only
		STATUS      current
		DESCRIPTION
			"Type is Manual or Sticky."
		::= { swhStaticForwardEntry 7 }

	swhStaticForwardAddtoStatic OBJECT-TYPE
		SYNTAX      INTEGER { normal(0), add(1) }
		MAX-ACCESS  read-write
		STATUS      current
		DESCRIPTION
			"Add Sticky to Static."
		::= { swhStaticForwardEntry 8 }


-- SwitchManagement(4).Layer2ProtocolTunnel(37)

	swhL2PTConfigState OBJECT-TYPE
		SYNTAX      INTEGER { disable(0), enable(1) }
		MAX-ACCESS  read-write
		STATUS      current
		DESCRIPTION
			"State."
		::= { swhLayer2ProtocolTunnel 1 }

	swhL2PTConfigDestinationMACAddress OBJECT-TYPE
		SYNTAX      DisplayString
		MAX-ACCESS  read-write
		STATUS      current
		DESCRIPTION
			"Destination mac address."
		::= { swhLayer2ProtocolTunnel 2 }

	swhL2PTConfigClassOfService OBJECT-TYPE
		SYNTAX      INTEGER (0..7)
		MAX-ACCESS  read-write
		STATUS      current
		DESCRIPTION
			"Class of Service. (0-7)"
		::= { swhLayer2ProtocolTunnel 3 }


-- SwitchManagement(4).Layer2ProtocolTunnel(37).L2PTPortConfigTable(5)

	swhL2PTPortConfigTable OBJECT-TYPE
		SYNTAX      SEQUENCE OF SwhL2PTPortConfigEntry
		MAX-ACCESS  not-accessible
		STATUS      current
		DESCRIPTION
			"Table of layer 2 protocol tunneling configuration."
		::= { swhLayer2ProtocolTunnel 5 }

	-- Table Entry
	swhL2PTPortConfigEntry OBJECT-TYPE
		SYNTAX      SwhL2PTPortConfigEntry
		MAX-ACCESS  not-accessible
		STATUS      current
		DESCRIPTION
			"An entry in the table, containing information about layer 2 protocol tunneling config."
		INDEX    { swhL2PTPortConfigIndex }
		::= { swhL2PTPortConfigTable 1 }

	SwhL2PTPortConfigEntry ::=
		SEQUENCE {
			swhL2PTPortConfigIndex
				INTEGER,
			swhL2PTPortConfigPort
				DisplayString,
			swhL2PTPortConfigCDP
				INTEGER,
			swhL2PTPortConfigLLDP
				INTEGER,
			swhL2PTPortConfigSTP
				INTEGER,
			swhL2PTPortConfigVTP
				INTEGER,
			swhL2PTPortConfigLACP
				INTEGER,
			swhL2PTPortConfigPAgP
				INTEGER,
			swhL2PTPortConfigUDLD
				INTEGER,
			swhL2PTPortConfigClear
				INTEGER
		}

	swhL2PTPortConfigIndex OBJECT-TYPE
		SYNTAX      INTEGER (0..2147483647)
		MAX-ACCESS  not-accessible
		STATUS      current
		DESCRIPTION
			"A unique value for each index."
		::= { swhL2PTPortConfigEntry 1 }

	swhL2PTPortConfigPort OBJECT-TYPE
		SYNTAX      DisplayString
		MAX-ACCESS  read-only
		STATUS      current
		DESCRIPTION
			"Layer 2 Protocol Tunneling Port Number."
		::= { swhL2PTPortConfigEntry 2 }

	swhL2PTPortConfigCDP OBJECT-TYPE
		SYNTAX      INTEGER { b(0), v(1) }
		MAX-ACCESS  read-write
		STATUS      current
		DESCRIPTION
			"b : Blocked  v : Member"
		::= { swhL2PTPortConfigEntry 3 }

	swhL2PTPortConfigLLDP OBJECT-TYPE
		SYNTAX      INTEGER { b(0), v(1) }
		MAX-ACCESS  read-write
		STATUS      current
		DESCRIPTION
			"b : Blocked  v : Member"
		::= { swhL2PTPortConfigEntry 4 }

	swhL2PTPortConfigSTP OBJECT-TYPE
		SYNTAX      INTEGER { b(0), v(1) }
		MAX-ACCESS  read-write
		STATUS      current
		DESCRIPTION
			"b : Blocked  v : Member"
		::= { swhL2PTPortConfigEntry 5 }

	swhL2PTPortConfigVTP OBJECT-TYPE
		SYNTAX      INTEGER { b(0), v(1) }
		MAX-ACCESS  read-write
		STATUS      current
		DESCRIPTION
			"b : Blocked  v : Member"
		::= { swhL2PTPortConfigEntry 6 }

	swhL2PTPortConfigLACP OBJECT-TYPE
		SYNTAX      INTEGER { b(0), v(1) }
		MAX-ACCESS  read-write
		STATUS      current
		DESCRIPTION
			"b : Blocked  v : Member"
		::= { swhL2PTPortConfigEntry 7 }

	swhL2PTPortConfigPAgP OBJECT-TYPE
		SYNTAX      INTEGER { b(0), v(1) }
		MAX-ACCESS  read-write
		STATUS      current
		DESCRIPTION
			"b : Blocked  v : Member"
		::= { swhL2PTPortConfigEntry 8 }

	swhL2PTPortConfigUDLD OBJECT-TYPE
		SYNTAX      INTEGER { b(0), v(1) }
		MAX-ACCESS  read-write
		STATUS      current
		DESCRIPTION
			"b : Blocked  v : Member"
		::= { swhL2PTPortConfigEntry 9 }

	swhL2PTPortConfigClear OBJECT-TYPE
		SYNTAX      INTEGER { normal(0), clear(1) }
		MAX-ACCESS  read-write
		STATUS      current
		DESCRIPTION
			"Clear this entry."
		::= { swhL2PTPortConfigEntry 50 }


-- SwitchManagement(4).RapidSpanningTree(40)

	swhRSTPSwitchSettings
		OBJECT IDENTIFIER ::= { swhRapidSpanningTree 3 }

	swhRSTPAggregatedPortSettings
		OBJECT IDENTIFIER ::= { swhRapidSpanningTree 9 }

	swhRSTPPhysicalPortSettings
		OBJECT IDENTIFIER ::= { swhRapidSpanningTree 12 }


-- SwitchManagement(4).RapidSpanningTree(40).RSTPSwitchSettings(3)

	swhRSTPSwitchSettingsEnable OBJECT-TYPE
		SYNTAX      INTEGER { disable(0), enable(1) }
		MAX-ACCESS  read-write
		STATUS      current
		DESCRIPTION
			"State."
		::= { swhRSTPSwitchSettings 22 }

	swhRSTPSwitchSettingsSystemPriority OBJECT-TYPE
		SYNTAX      INTEGER (0..2147483647)
		MAX-ACCESS  read-only
		STATUS      current
		DESCRIPTION
			"System Priority."
		::= { swhRSTPSwitchSettings 6 }

	swhRSTPSwitchSettingsSystemPriorityIndex OBJECT-TYPE
		SYNTAX      INTEGER { priority-0(0),
		                      priority-4096(1),
		                      priority-8192(2),
		                      priority-12288(3),
		                      priority-16384(4),
		                      priority-20480(5),
		                      priority-24576(6),
		                      priority-28672(7),
		                      priority-32768(8),
		                      priority-36864(9),
		                      priority-40960(10),
		                      priority-45056(11),
		                      priority-49152(12),
		                      priority-53248(13),
		                      priority-57344(14),
		                      priority-61440(15)
		                    }
		MAX-ACCESS  read-write
		STATUS      current
		DESCRIPTION
			"Port Priority."
		::= { swhRSTPSwitchSettings 9 }

	swhRSTPSwitchSettingsMaxAge OBJECT-TYPE
		SYNTAX      INTEGER (6..40)
		MAX-ACCESS  read-write
		STATUS      current
		DESCRIPTION
			"Max Age is 6-40 hops."
		::= { swhRSTPSwitchSettings 12 }

	swhRSTPSwitchSettingsHelloTime OBJECT-TYPE
		SYNTAX      INTEGER (1..10)
		MAX-ACCESS  read-write
		STATUS      current
		DESCRIPTION
			"Hello Time is 1-10 Secs."
		::= { swhRSTPSwitchSettings 15 }

	swhRSTPSwitchSettingsForwardDelay OBJECT-TYPE
		SYNTAX      INTEGER (4..30)
		MAX-ACCESS  read-write
		STATUS      current
		DESCRIPTION
			"Forward Delay is 4-30 Secs."
		::= { swhRSTPSwitchSettings 18 }

	swhRSTPSwitchSettingsForceVersion OBJECT-TYPE
		SYNTAX      INTEGER { stp-compatible(0), normal(1) }
		MAX-ACCESS  read-write
		STATUS      current
		DESCRIPTION
			"Force Version."
		::= { swhRSTPSwitchSettings 21 }


-- SwitchManagement(4).RapidSpanningTree(40).RSTPAggregatedPortSettings(9)

	swhRSTPAggregatedPortSettingsState OBJECT-TYPE
		SYNTAX      INTEGER { disable(0), enable(1) }
		MAX-ACCESS  read-write
		STATUS      current
		DESCRIPTION
			"State."
		::= { swhRSTPAggregatedPortSettings 3 }

	swhRSTPAggregatedPortSettingsCost OBJECT-TYPE
		SYNTAX      INTEGER (1..200000000)
		MAX-ACCESS  read-write
		STATUS      current
		DESCRIPTION
			"Cost."
		::= { swhRSTPAggregatedPortSettings 6 }

	swhRSTPAggregatedPortSettingsPriority OBJECT-TYPE
		SYNTAX      INTEGER (0..2147483647)
		MAX-ACCESS  read-only
		STATUS      current
		DESCRIPTION
			"Priority."
		::= { swhRSTPAggregatedPortSettings 9 }

	swhRSTPAggregatedPortSettingsPriorityIndex OBJECT-TYPE
		SYNTAX      INTEGER { priority-0(0),
		                      priority-16(1),
		                      priority-32(2),
		                      priority-48(3),
		                      priority-64(4),
		                      priority-80(5),
		                      priority-96(6),
		                      priority-112(7),
		                      priority-128(8),
		                      priority-144(9),
		                      priority-160(10),
		                      priority-176(11),
		                      priority-192(12),
		                      priority-208(13),
		                      priority-224(14),
		                      priority-240(15)
		                    }
		MAX-ACCESS  read-write
		STATUS      current
		DESCRIPTION
			"Port Priority."
		::= { swhRSTPAggregatedPortSettings 12 }

	swhRSTPAggregatedPortSettingsEdge OBJECT-TYPE
		SYNTAX      INTEGER { disable(0), enable(1) }
		MAX-ACCESS  read-write
		STATUS      current
		DESCRIPTION
			"Edge."
		::= { swhRSTPAggregatedPortSettings 15 }

	swhRSTPAggregatedPortSettingsPoint2point OBJECT-TYPE
		SYNTAX      INTEGER { forcedtrue(0), forcedfalse(1), auto(2) }
		MAX-ACCESS  read-write
		STATUS      current
		DESCRIPTION
			"Point to Point."
		::= { swhRSTPAggregatedPortSettings 18 }


-- SwitchManagement(4).RapidSpanningTree(40).RSTPPhysicalPortSettings(12).RSTPPhysicalPortSettingsTable(3)

	swhRSTPPhysicalPortSettingsTable OBJECT-TYPE
		SYNTAX      SEQUENCE OF SwhRSTPPhysicalPortSettingsEntry
		MAX-ACCESS  not-accessible
		STATUS      current
		DESCRIPTION
			"Table of RSTP physical port descriptive and status information."
		::= { swhRSTPPhysicalPortSettings 3 }

	-- Table Entry
	swhRSTPPhysicalPortSettingsEntry OBJECT-TYPE
		SYNTAX      SwhRSTPPhysicalPortSettingsEntry
		MAX-ACCESS  not-accessible
		STATUS      current
		DESCRIPTION
			"An entry in the table, containing information about RSTP physical port settings."
		INDEX    { swhRSTPPhysicalPortSettingsIndex }
		::= { swhRSTPPhysicalPortSettingsTable 1 }

	SwhRSTPPhysicalPortSettingsEntry ::=
		SEQUENCE {
			swhRSTPPhysicalPortSettingsIndex
				INTEGER,
			swhRSTPPhysicalPortSettingsState
				INTEGER,
			swhRSTPPhysicalPortSettingsPathCost
				INTEGER,
			swhRSTPPhysicalPortSettingsPriority
				INTEGER,
			swhRSTPPhysicalPortSettingsPriorityIndex
				INTEGER,
			swhRSTPPhysicalPortSettingsEdge
				INTEGER,
			swhRSTPPhysicalPortSettingsPoint2point
				INTEGER
		}

	swhRSTPPhysicalPortSettingsIndex OBJECT-TYPE
		SYNTAX      INTEGER (0..2147483647)
		MAX-ACCESS  not-accessible
		STATUS      current
		DESCRIPTION
			"A unique value for each index."
		::= { swhRSTPPhysicalPortSettingsEntry 3 }

	swhRSTPPhysicalPortSettingsState OBJECT-TYPE
		SYNTAX      INTEGER { disable(0), enable(1) }
		MAX-ACCESS  read-write
		STATUS      current
		DESCRIPTION
			"State."
		::= { swhRSTPPhysicalPortSettingsEntry 6 }

	swhRSTPPhysicalPortSettingsEdge OBJECT-TYPE
		SYNTAX      INTEGER { disable(0), enable(1) }
		MAX-ACCESS  read-write
		STATUS      current
		DESCRIPTION
			"Edge."
		::= { swhRSTPPhysicalPortSettingsEntry 9 }

	swhRSTPPhysicalPortSettingsPathCost OBJECT-TYPE
		SYNTAX      INTEGER (0..200000000)
		MAX-ACCESS  read-write
		STATUS      current
		DESCRIPTION
			"Path Cost is 0-200000000."
		::= { swhRSTPPhysicalPortSettingsEntry 12 }

	swhRSTPPhysicalPortSettingsPriority OBJECT-TYPE
		SYNTAX      INTEGER (0..2147483647)
		MAX-ACCESS  read-only
		STATUS      current
		DESCRIPTION
			"Priority."
		::= { swhRSTPPhysicalPortSettingsEntry 15 }

	swhRSTPPhysicalPortSettingsPriorityIndex OBJECT-TYPE
		SYNTAX      INTEGER { priority-0(0),
		                      priority-16(1),
		                      priority-32(2),
		                      priority-48(3),
		                      priority-64(4),
		                      priority-80(5),
		                      priority-96(6),
		                      priority-112(7),
		                      priority-128(8),
		                      priority-144(9),
		                      priority-160(10),
		                      priority-176(11),
		                      priority-192(12),
		                      priority-208(13),
		                      priority-224(14),
		                      priority-240(15)
		                    }
		MAX-ACCESS  read-write
		STATUS      current
		DESCRIPTION
			"Port Priority."
		::= { swhRSTPPhysicalPortSettingsEntry 18 }

	swhRSTPPhysicalPortSettingsPoint2point OBJECT-TYPE
		SYNTAX      INTEGER { forcedtrue(0), forcedfalse(1), auto(2) }
		MAX-ACCESS  read-write
		STATUS      current
		DESCRIPTION
			"Point to Point."
		::= { swhRSTPPhysicalPortSettingsEntry 21 }


-- SwitchManagement(4).LinkAggregation(45)

	swhDistributionRule
		OBJECT IDENTIFIER ::= { swhLinkAggregation 1 }

	swhPortTrunkConfiguration
		OBJECT IDENTIFIER ::= { swhLinkAggregation 3 }

	swhLACPPortConfiguration
		OBJECT IDENTIFIER ::= { swhLinkAggregation 6 }


-- SwitchManagement(4).LinkAggregation(45).DistributionRule(1)

	swhDistributionRuleSourceMACAddress OBJECT-TYPE
		SYNTAX      INTEGER { disable(0), enable(1) }
		MAX-ACCESS  read-write
		STATUS      current
		DESCRIPTION
			"Source MAC Address."
		::= { swhDistributionRule 5 }

	swhDistributionRuleDestinationMACAddress OBJECT-TYPE
		SYNTAX      INTEGER { disable(0), enable(1) }
		MAX-ACCESS  read-write
		STATUS      current
		DESCRIPTION
			"Destination MAC Address."
		::= { swhDistributionRule 6 }

	swhDistributionRuleSourceIPAddress OBJECT-TYPE
		SYNTAX      INTEGER { disable(0), enable(1) }
		MAX-ACCESS  read-write
		STATUS      current
		DESCRIPTION
			"Source IP Address."
		::= { swhDistributionRule 1 }

	swhDistributionRuleDestinationIPAddress OBJECT-TYPE
		SYNTAX      INTEGER { disable(0), enable(1) }
		MAX-ACCESS  read-write
		STATUS      current
		DESCRIPTION
			"Destination IP Address."
		::= { swhDistributionRule 2 }

	swhDistributionRuleSourceL4Port OBJECT-TYPE
		SYNTAX      INTEGER { disable(0), enable(1) }
		MAX-ACCESS  read-write
		STATUS      current
		DESCRIPTION
			"Source L4 Port."
		::= { swhDistributionRule 3 }

	swhDistributionRuleDestinationL4Port OBJECT-TYPE
		SYNTAX      INTEGER { disable(0), enable(1) }
		MAX-ACCESS  read-write
		STATUS      current
		DESCRIPTION
			"Destination L4 Port."
		::= { swhDistributionRule 4 }


-- SwitchManagement(4).LinkAggregation(45).PortTrunkConfiguration(3).PortTrunkConfigTable(6)

	swhPortTrunkConfigTable OBJECT-TYPE
		SYNTAX      SEQUENCE OF SwhPortTrunkConfigEntry
		MAX-ACCESS  not-accessible
		STATUS      current
		DESCRIPTION
			"Table of port trunk configuration."
		::= { swhPortTrunkConfiguration 6 }

	-- Table Entry
	swhPortTrunkConfigEntry OBJECT-TYPE
		SYNTAX      SwhPortTrunkConfigEntry
		MAX-ACCESS  not-accessible
		STATUS      current
		DESCRIPTION
			"An entry in the table, containing information about port trunk config."
		INDEX    { swhPortTrunkConfigIndex }
		::= { swhPortTrunkConfigTable 1 }

	SwhPortTrunkConfigEntry ::=
		SEQUENCE {
			swhPortTrunkConfigIndex
				INTEGER,
			swhPortTrunkConfigValid
				INTEGER,
			swhPortTrunkConfigGroupName
				DisplayString,
			swhPortTrunkConfigPort1
				INTEGER,
			swhPortTrunkConfigPort2
				INTEGER,
			swhPortTrunkConfigPort3
				INTEGER,
			swhPortTrunkConfigPort4
				INTEGER,
			swhPortTrunkConfigPort5
				INTEGER,
			swhPortTrunkConfigPort6
				INTEGER,
			swhPortTrunkConfigPort7
				INTEGER,
			swhPortTrunkConfigPort8
				INTEGER,
			swhPortTrunkConfigPort9
				INTEGER,
			swhPortTrunkConfigPort10
				INTEGER,
			swhPortTrunkConfigPort11
				INTEGER,
			swhPortTrunkConfigPort12
				INTEGER,
			swhPortTrunkConfigDelete
				INTEGER
		}

	swhPortTrunkConfigIndex OBJECT-TYPE
		SYNTAX      INTEGER (0..2147483647)
		MAX-ACCESS  not-accessible
		STATUS      current
		DESCRIPTION
			"A unique value for each index."
		::= { swhPortTrunkConfigEntry 1 }

	swhPortTrunkConfigValid OBJECT-TYPE
		SYNTAX      INTEGER { invalid(0), valid(1) }
		MAX-ACCESS  read-only
		STATUS      current
		DESCRIPTION
			"This entry is valid or invalid."
		::= { swhPortTrunkConfigEntry 2 }

	swhPortTrunkConfigGroupName OBJECT-TYPE
		SYNTAX      DisplayString
		MAX-ACCESS  read-write
		STATUS      current
		DESCRIPTION
			"Port trunk group name."
		::= { swhPortTrunkConfigEntry 4 }

	swhPortTrunkConfigPort1 OBJECT-TYPE
		SYNTAX      INTEGER { b(0), v(1) }
		MAX-ACCESS  read-write
		STATUS      current
		DESCRIPTION
			"b : Blocked  v : Member"
		::= { swhPortTrunkConfigEntry 5 }

	swhPortTrunkConfigPort2 OBJECT-TYPE
		SYNTAX      INTEGER { b(0), v(1) }
		MAX-ACCESS  read-write
		STATUS      current
		DESCRIPTION
			"b : Blocked  v : Member"
		::= { swhPortTrunkConfigEntry 6 }

	swhPortTrunkConfigPort3 OBJECT-TYPE
		SYNTAX      INTEGER { b(0), v(1) }
		MAX-ACCESS  read-write
		STATUS      current
		DESCRIPTION
			"b : Blocked  v : Member"
		::= { swhPortTrunkConfigEntry 7 }

	swhPortTrunkConfigPort4 OBJECT-TYPE
		SYNTAX      INTEGER { b(0), v(1) }
		MAX-ACCESS  read-write
		STATUS      current
		DESCRIPTION
			"b : Blocked  v : Member"
		::= { swhPortTrunkConfigEntry 8 }

	swhPortTrunkConfigPort5 OBJECT-TYPE
		SYNTAX      INTEGER { b(0), v(1) }
		MAX-ACCESS  read-write
		STATUS      current
		DESCRIPTION
			"b : Blocked  v : Member"
		::= { swhPortTrunkConfigEntry 9 }

	swhPortTrunkConfigPort6 OBJECT-TYPE
		SYNTAX      INTEGER { b(0), v(1) }
		MAX-ACCESS  read-write
		STATUS      current
		DESCRIPTION
			"b : Blocked  v : Member"
		::= { swhPortTrunkConfigEntry 10 }

	swhPortTrunkConfigPort7 OBJECT-TYPE
		SYNTAX      INTEGER { b(0), v(1) }
		MAX-ACCESS  read-write
		STATUS      current
		DESCRIPTION
			"b : Blocked  v : Member"
		::= { swhPortTrunkConfigEntry 11 }

	swhPortTrunkConfigPort8 OBJECT-TYPE
		SYNTAX      INTEGER { b(0), v(1) }
		MAX-ACCESS  read-write
		STATUS      current
		DESCRIPTION
			"b : Blocked  v : Member"
		::= { swhPortTrunkConfigEntry 12 }

	swhPortTrunkConfigPort9 OBJECT-TYPE
		SYNTAX      INTEGER { b(0), v(1) }
		MAX-ACCESS  read-write
		STATUS      current
		DESCRIPTION
			"b : Blocked  v : Member"
		::= { swhPortTrunkConfigEntry 13 }

	swhPortTrunkConfigPort10 OBJECT-TYPE
		SYNTAX      INTEGER { b(0), v(1) }
		MAX-ACCESS  read-write
		STATUS      current
		DESCRIPTION
			"b : Blocked  v : Member"
		::= { swhPortTrunkConfigEntry 14 }

	swhPortTrunkConfigPort11 OBJECT-TYPE
		SYNTAX      INTEGER { b(0), v(1) }
		MAX-ACCESS  read-write
		STATUS      current
		DESCRIPTION
			"b : Blocked  v : Member"
		::= { swhPortTrunkConfigEntry 15 }

	swhPortTrunkConfigPort12 OBJECT-TYPE
		SYNTAX      INTEGER { b(0), v(1) }
		MAX-ACCESS  read-write
		STATUS      current
		DESCRIPTION
			"b : Blocked  v : Member"
		::= { swhPortTrunkConfigEntry 16 }

	swhPortTrunkConfigDelete OBJECT-TYPE
		SYNTAX      INTEGER { normal(0), delete(1) }
		MAX-ACCESS  read-write
		STATUS      current
		DESCRIPTION
			"Delete this entry."
		::= { swhPortTrunkConfigEntry 56 }


-- SwitchManagement(4).LinkAggregation(45).LACPPortConfiguration(6)

	swhLACPPortConfigTable OBJECT-TYPE
		SYNTAX      SEQUENCE OF SwhLACPPortConfigEntry
		MAX-ACCESS  not-accessible
		STATUS      current
		DESCRIPTION
			"Table of LACP port descriptive and status information."
		::= { swhLACPPortConfiguration 1 }

	-- Table Entry
	swhLACPPortConfigEntry OBJECT-TYPE
		SYNTAX      SwhLACPPortConfigEntry
		MAX-ACCESS  not-accessible
		STATUS      current
		DESCRIPTION
			"An entry in the table, containing information about LACP port config."
		INDEX    { swhLACPPortConfigIndex }
		::= { swhLACPPortConfigTable 1 }

	SwhLACPPortConfigEntry ::=
		SEQUENCE {
			swhLACPPortConfigIndex
				INTEGER,
			swhLACPPortConfigKeyValue
				INTEGER,
			swhLACPPortConfigRole
				INTEGER
		}

	swhLACPPortConfigIndex OBJECT-TYPE
		SYNTAX      INTEGER (0..2147483647)
		MAX-ACCESS  not-accessible
		STATUS      current
		DESCRIPTION
			"A unique value for each index."
		::= { swhLACPPortConfigEntry 3 }

	swhLACPPortConfigKeyValue OBJECT-TYPE
		SYNTAX      INTEGER (0..255)
		MAX-ACCESS  read-write
		STATUS      current
		DESCRIPTION
			"Path Cost is 0-255. (0 : auto)"
		::= { swhLACPPortConfigEntry 9 }

	swhLACPPortConfigRole OBJECT-TYPE
		SYNTAX      INTEGER { disable(0), passive(1), active(2) }
		MAX-ACCESS  read-write
		STATUS      current
		DESCRIPTION
			"Role."
		::= { swhLACPPortConfigEntry 12 }


-- SwitchManagement(4).IGMPSnooping(50)

	swhIGMPConfiguration
		OBJECT IDENTIFIER ::= { swhIGMPSnooping 1 }

	swhIGMPVIDConfiguration
		OBJECT IDENTIFIER ::= { swhIGMPSnooping 5 }

	swhIPMCSegment
		OBJECT IDENTIFIER ::= { swhIGMPSnooping 7 }

	swhIPMCProfile
		OBJECT IDENTIFIER ::= { swhIGMPSnooping 8 }

	swhIGMPFiltering
		OBJECT IDENTIFIER ::= { swhIGMPSnooping 9 }


-- SwitchManagement(4).IGMPSnooping(50).IGMPConfiguration(1)

	swhIGMPConfigSnooping OBJECT-TYPE
		SYNTAX      INTEGER { disable(0), enable(1) }
		MAX-ACCESS  read-write
		STATUS      current
		DESCRIPTION
			"IGMP Snooping."
		::= { swhIGMPConfiguration 1 }

	swhIGMPConfigSnoopingV3 OBJECT-TYPE
		SYNTAX      INTEGER { disable(0), enable(1) }
		MAX-ACCESS  read-write
		STATUS      current
		DESCRIPTION
			"IGMP Snooping V3."
		::= { swhIGMPConfiguration 60 }

	swhIGMPConfigUnregisteredIPMCFlooding OBJECT-TYPE
		SYNTAX      INTEGER { disable(0), enable(1) }
		MAX-ACCESS  read-write
		STATUS      current
		DESCRIPTION
			"Unregistered IPMC Flooding."
		::= { swhIGMPConfiguration 56 }

	swhIGMPConfigQueryInterval OBJECT-TYPE
		SYNTAX      INTEGER (1..6000)
		MAX-ACCESS  read-write
		STATUS      current
		DESCRIPTION
			"Query Interval. (Sec)"
		::= { swhIGMPConfiguration 58 }

	swhIGMPConfigQueryResponseInterval OBJECT-TYPE
		SYNTAX      INTEGER (1..255)
		MAX-ACCESS  read-write
		STATUS      current
		DESCRIPTION
			"Query Response Interval. (1/10 Sec)"
		::= { swhIGMPConfiguration 57 }

	swhIGMPConfigFastLeave OBJECT-TYPE
		SYNTAX      INTEGER { disable(0), enable(1) }
		MAX-ACCESS  read-write
		STATUS      current
		DESCRIPTION
			"Fast Leave."
		::= { swhIGMPConfiguration 2 }

	swhIGMPConfigStreamLifeTime OBJECT-TYPE
		SYNTAX      INTEGER { disable(0), enable(1) }
		MAX-ACCESS  read-write
		STATUS      current
		DESCRIPTION
			"Stream Life Time."
		::= { swhIGMPConfiguration 61 }

	swhIGMPConfigRouterPort1 OBJECT-TYPE
		SYNTAX      INTEGER { b(0), v(1) }
		MAX-ACCESS  read-write
		STATUS      current
		DESCRIPTION
			"b : Blocked  v : Member"
		::= { swhIGMPConfiguration 5 }

	swhIGMPConfigRouterPort2 OBJECT-TYPE
		SYNTAX      INTEGER { b(0), v(1) }
		MAX-ACCESS  read-write
		STATUS      current
		DESCRIPTION
			"b : Blocked  v : Member"
		::= { swhIGMPConfiguration 6 }

	swhIGMPConfigRouterPort3 OBJECT-TYPE
		SYNTAX      INTEGER { b(0), v(1) }
		MAX-ACCESS  read-write
		STATUS      current
		DESCRIPTION
			"b : Blocked  v : Member"
		::= { swhIGMPConfiguration 7 }

	swhIGMPConfigRouterPort4 OBJECT-TYPE
		SYNTAX      INTEGER { b(0), v(1) }
		MAX-ACCESS  read-write
		STATUS      current
		DESCRIPTION
			"b : Blocked  v : Member"
		::= { swhIGMPConfiguration 8 }

	swhIGMPConfigRouterPort5 OBJECT-TYPE
		SYNTAX      INTEGER { b(0), v(1) }
		MAX-ACCESS  read-write
		STATUS      current
		DESCRIPTION
			"b : Blocked  v : Member"
		::= { swhIGMPConfiguration 9 }

	swhIGMPConfigRouterPort6 OBJECT-TYPE
		SYNTAX      INTEGER { b(0), v(1) }
		MAX-ACCESS  read-write
		STATUS      current
		DESCRIPTION
			"b : Blocked  v : Member"
		::= { swhIGMPConfiguration 10 }

	swhIGMPConfigRouterPort7 OBJECT-TYPE
		SYNTAX      INTEGER { b(0), v(1) }
		MAX-ACCESS  read-write
		STATUS      current
		DESCRIPTION
			"b : Blocked  v : Member"
		::= { swhIGMPConfiguration 11 }

	swhIGMPConfigRouterPort8 OBJECT-TYPE
		SYNTAX      INTEGER { b(0), v(1) }
		MAX-ACCESS  read-write
		STATUS      current
		DESCRIPTION
			"b : Blocked  v : Member"
		::= { swhIGMPConfiguration 12 }

	swhIGMPConfigRouterPort9 OBJECT-TYPE
		SYNTAX      INTEGER { b(0), v(1) }
		MAX-ACCESS  read-write
		STATUS      current
		DESCRIPTION
			"b : Blocked  v : Member"
		::= { swhIGMPConfiguration 13 }

	swhIGMPConfigRouterPort10 OBJECT-TYPE
		SYNTAX      INTEGER { b(0), v(1) }
		MAX-ACCESS  read-write
		STATUS      current
		DESCRIPTION
			"b : Blocked  v : Member"
		::= { swhIGMPConfiguration 14 }

	swhIGMPConfigRouterPort11 OBJECT-TYPE
		SYNTAX      INTEGER { b(0), v(1) }
		MAX-ACCESS  read-write
		STATUS      current
		DESCRIPTION
			"b : Blocked  v : Member"
		::= { swhIGMPConfiguration 15 }

	swhIGMPConfigRouterPort12 OBJECT-TYPE
		SYNTAX      INTEGER { b(0), v(1) }
		MAX-ACCESS  read-write
		STATUS      current
		DESCRIPTION
			"b : Blocked  v : Member"
		::= { swhIGMPConfiguration 16 }


-- SwitchManagement(4).IGMPSnooping(50).IGMPVIDConfiguration(5).IGMPVIDConfigTable(1)

	swhIGMPVIDConfigTable OBJECT-TYPE
		SYNTAX      SEQUENCE OF SwhIGMPVIDConfigEntry
		MAX-ACCESS  not-accessible
		STATUS      current
		DESCRIPTION
			"Table of IGMP VLAN ID configuration."
		::= { swhIGMPVIDConfiguration 1 }

	-- Table Entry
	swhIGMPVIDConfigEntry OBJECT-TYPE
		SYNTAX      SwhIGMPVIDConfigEntry
		MAX-ACCESS  not-accessible
		STATUS      current
		DESCRIPTION
			"An entry in the table, containing information about IGMP VLAN ID config."
		INDEX    { swhIGMPVIDConfigIndex }
		::= { swhIGMPVIDConfigTable 1 }

	SwhIGMPVIDConfigEntry ::=
		SEQUENCE {
			swhIGMPVIDConfigIndex
				INTEGER,
			swhIGMPVIDConfigVLANID
				INTEGER,
			swhIGMPVIDConfigIsMVRVID
				INTEGER,
			swhIGMPVIDConfigVLANName
				DisplayString,
			swhIGMPVIDConfigSnooping
				INTEGER,
			swhIGMPVIDConfigQuerying
				INTEGER
		}

	swhIGMPVIDConfigIndex OBJECT-TYPE
		SYNTAX      INTEGER (0..2147483647)
		MAX-ACCESS  not-accessible
		STATUS      current
		DESCRIPTION
			"A unique value for each index."
		::= { swhIGMPVIDConfigEntry 1 }

	swhIGMPVIDConfigVLANName OBJECT-TYPE
		SYNTAX      DisplayString
		MAX-ACCESS  read-only
		STATUS      current
		DESCRIPTION
			"VLAN Name."
		::= { swhIGMPVIDConfigEntry 5 }

	swhIGMPVIDConfigVLANID OBJECT-TYPE
		SYNTAX      INTEGER (1..4094)
		MAX-ACCESS  read-only
		STATUS      current
		DESCRIPTION
			"VLAN ID. (1-4094)"
		::= { swhIGMPVIDConfigEntry 7 }

	swhIGMPVIDConfigSnooping OBJECT-TYPE
		SYNTAX      INTEGER { b(0), v(1) }
		MAX-ACCESS  read-write
		STATUS      current
		DESCRIPTION
			"b : Blocked  v : Member"
		::= { swhIGMPVIDConfigEntry 9 }

	swhIGMPVIDConfigQuerying OBJECT-TYPE
		SYNTAX      INTEGER { b(0), v(1) }
		MAX-ACCESS  read-write
		STATUS      current
		DESCRIPTION
			"b : Blocked  v : Member"
		::= { swhIGMPVIDConfigEntry 11 }

	swhIGMPVIDConfigIsMVRVID OBJECT-TYPE
		SYNTAX      INTEGER { b(0), v(1) }
		MAX-ACCESS  read-only
		STATUS      current
		DESCRIPTION
			"Is it MVR VLAN ID? (b : no, v : yes)"
		::= { swhIGMPVIDConfigEntry 12 }


-- SwitchManagement(4).IGMPSnooping(50).IPMCSegment(7)

	swhIPMCSegmentTable OBJECT-TYPE
		SYNTAX      SEQUENCE OF SwhIPMCSegmentEntry
		MAX-ACCESS  not-accessible
		STATUS      current
		DESCRIPTION
			"Table of IPMC segment."
		::= { swhIPMCSegment 1 }

	-- Table Entry
	swhIPMCSegmentEntry OBJECT-TYPE
		SYNTAX      SwhIPMCSegmentEntry
		MAX-ACCESS  not-accessible
		STATUS      current
		DESCRIPTION
			"An entry in the table, containing information about IPMC segment."
		INDEX    { swhIPMCSegmentIndex }
		::= { swhIPMCSegmentTable 1 }

	SwhIPMCSegmentEntry ::=
		SEQUENCE {
			swhIPMCSegmentIndex
				INTEGER,
			swhIPMCSegmentValid
				INTEGER,
			swhIPMCSegmentSegmentID
				INTEGER,
			swhIPMCSegmentSegmentName
				DisplayString,
			swhIPMCSegmentIPRange1
				IpAddress,
			swhIPMCSegmentIPRange2
				IpAddress,
			swhIPMCSegmentDelete
				INTEGER
		}

	swhIPMCSegmentIndex OBJECT-TYPE
		SYNTAX      INTEGER (0..2147483647)
		MAX-ACCESS  not-accessible
		STATUS      current
		DESCRIPTION
			"A unique value for each index."
		::= { swhIPMCSegmentEntry 1 }

	swhIPMCSegmentValid OBJECT-TYPE
		SYNTAX      INTEGER { invalid(0), valid(1) }
		MAX-ACCESS  read-only
		STATUS      current
		DESCRIPTION
			"This entry is valid or invalid."
		::= { swhIPMCSegmentEntry 2 }

	swhIPMCSegmentSegmentID OBJECT-TYPE
		SYNTAX      INTEGER (1..400)
		MAX-ACCESS  read-write
		STATUS      current
		DESCRIPTION
			"Segment ID. (1-400)"
		::= { swhIPMCSegmentEntry 3 }

	swhIPMCSegmentSegmentName OBJECT-TYPE
		SYNTAX      DisplayString
		MAX-ACCESS  read-write
		STATUS      current
		DESCRIPTION
			"Segment Name."
		::= { swhIPMCSegmentEntry 4 }

	swhIPMCSegmentIPRange1 OBJECT-TYPE
		SYNTAX      IpAddress
		MAX-ACCESS  read-write
		STATUS      current
		DESCRIPTION
			"IP Address. (224.0.1.0 ~ 239.255.255.255)"
		::= { swhIPMCSegmentEntry 5 }

	swhIPMCSegmentIPRange2 OBJECT-TYPE
		SYNTAX      IpAddress
		MAX-ACCESS  read-write
		STATUS      current
		DESCRIPTION
			"IP Address. (224.0.1.0 ~ 239.255.255.255)"
		::= { swhIPMCSegmentEntry 6 }

	swhIPMCSegmentDelete OBJECT-TYPE
		SYNTAX      INTEGER { normal(0), delete(1) }
		MAX-ACCESS  read-write
		STATUS      current
		DESCRIPTION
			"Delete this entry."
		::= { swhIPMCSegmentEntry 10 }


-- SwitchManagement(4).IGMPSnooping(50).IPMCProfile(8)

	swhIPMCProfileTable OBJECT-TYPE
		SYNTAX      SEQUENCE OF SwhIPMCProfileEntry
		MAX-ACCESS  not-accessible
		STATUS      current
		DESCRIPTION
			"Table of IPMC profile."
		::= { swhIPMCProfile 1 }

	-- Table Entry
	swhIPMCProfileEntry OBJECT-TYPE
		SYNTAX      SwhIPMCProfileEntry
		MAX-ACCESS  not-accessible
		STATUS      current
		DESCRIPTION
			"An entry in the table, containing information about IPMC profile."
		INDEX    { swhIPMCProfileIndex }
		::= { swhIPMCProfileTable 1 }

	SwhIPMCProfileEntry ::=
		SEQUENCE {
			swhIPMCProfileIndex
				INTEGER,
			swhIPMCProfileValid
				INTEGER,
			swhIPMCProfileProfileName
				DisplayString,
			swhIPMCProfileSegment1
				INTEGER,
			swhIPMCProfileSegment2
				INTEGER,
			swhIPMCProfileSegment3
				INTEGER,
			swhIPMCProfileSegment4
				INTEGER,
			swhIPMCProfileSegment5
				INTEGER,
			swhIPMCProfileSegment6
				INTEGER,
			swhIPMCProfileSegment7
				INTEGER,
			swhIPMCProfileSegment8
				INTEGER,
			swhIPMCProfileSegment9
				INTEGER,
			swhIPMCProfileSegment10
				INTEGER,
			swhIPMCProfileDelete
				INTEGER
		}

	swhIPMCProfileIndex OBJECT-TYPE
		SYNTAX      INTEGER (0..2147483647)
		MAX-ACCESS  not-accessible
		STATUS      current
		DESCRIPTION
			"A unique value for each index."
		::= { swhIPMCProfileEntry 1 }

	swhIPMCProfileValid OBJECT-TYPE
		SYNTAX      INTEGER { invalid(0), valid(1) }
		MAX-ACCESS  read-only
		STATUS      current
		DESCRIPTION
			"This entry is valid or invalid."
		::= { swhIPMCProfileEntry 2 }

	swhIPMCProfileProfileName OBJECT-TYPE
		SYNTAX      DisplayString
		MAX-ACCESS  read-write
		STATUS      current
		DESCRIPTION
			"Profile Name."
		::= { swhIPMCProfileEntry 3 }

	swhIPMCProfileSegment1 OBJECT-TYPE
		SYNTAX      INTEGER (1..400)
		MAX-ACCESS  read-write
		STATUS      current
		DESCRIPTION
			"Segment ID."
		::= { swhIPMCProfileEntry 4 }

	swhIPMCProfileSegment2 OBJECT-TYPE
		SYNTAX      INTEGER (1..400)
		MAX-ACCESS  read-write
		STATUS      current
		DESCRIPTION
			"Segment ID."
		::= { swhIPMCProfileEntry 5 }

	swhIPMCProfileSegment3 OBJECT-TYPE
		SYNTAX      INTEGER (1..400)
		MAX-ACCESS  read-write
		STATUS      current
		DESCRIPTION
			"Segment ID."
		::= { swhIPMCProfileEntry 6 }

	swhIPMCProfileSegment4 OBJECT-TYPE
		SYNTAX      INTEGER (1..400)
		MAX-ACCESS  read-write
		STATUS      current
		DESCRIPTION
			"Segment ID."
		::= { swhIPMCProfileEntry 7 }

	swhIPMCProfileSegment5 OBJECT-TYPE
		SYNTAX      INTEGER (1..400)
		MAX-ACCESS  read-write
		STATUS      current
		DESCRIPTION
			"Segment ID."
		::= { swhIPMCProfileEntry 8 }

	swhIPMCProfileSegment6 OBJECT-TYPE
		SYNTAX      INTEGER (1..400)
		MAX-ACCESS  read-write
		STATUS      current
		DESCRIPTION
			"Segment ID."
		::= { swhIPMCProfileEntry 9 }

	swhIPMCProfileSegment7 OBJECT-TYPE
		SYNTAX      INTEGER (1..400)
		MAX-ACCESS  read-write
		STATUS      current
		DESCRIPTION
			"Segment ID."
		::= { swhIPMCProfileEntry 10 }

	swhIPMCProfileSegment8 OBJECT-TYPE
		SYNTAX      INTEGER (1..400)
		MAX-ACCESS  read-write
		STATUS      current
		DESCRIPTION
			"Segment ID."
		::= { swhIPMCProfileEntry 11 }

	swhIPMCProfileSegment9 OBJECT-TYPE
		SYNTAX      INTEGER (1..400)
		MAX-ACCESS  read-write
		STATUS      current
		DESCRIPTION
			"Segment ID."
		::= { swhIPMCProfileEntry 12 }

	swhIPMCProfileSegment10 OBJECT-TYPE
		SYNTAX      INTEGER (1..400)
		MAX-ACCESS  read-write
		STATUS      current
		DESCRIPTION
			"Segment ID."
		::= { swhIPMCProfileEntry 13 }

	swhIPMCProfileDelete OBJECT-TYPE
		SYNTAX      INTEGER { normal(0), delete(1) }
		MAX-ACCESS  read-write
		STATUS      current
		DESCRIPTION
			"Delete this entry."
		::= { swhIPMCProfileEntry 15 }


-- SwitchManagement(4).IGMPSnooping(50).IGMPFiltering(9)

	swhIGMPFilterState OBJECT-TYPE
		SYNTAX      INTEGER { disable(0), enable(1) }
		MAX-ACCESS  read-write
		STATUS      current
		DESCRIPTION
			"IGMP Filter."
		::= { swhIGMPFiltering 2 }

	swhIGMPFilterTable OBJECT-TYPE
		SYNTAX      SEQUENCE OF SwhIGMPFilterEntry
		MAX-ACCESS  not-accessible
		STATUS      current
		DESCRIPTION
			"Table of IGMP filtering."
		::= { swhIGMPFiltering 1 }

	-- Table Entry
	swhIGMPFilterEntry OBJECT-TYPE
		SYNTAX      SwhIGMPFilterEntry
		MAX-ACCESS  not-accessible
		STATUS      current
		DESCRIPTION
			"An entry in the table, containing information about IGMP filtering."
		INDEX    { swhIGMPFilterIndex }
		::= { swhIGMPFilterTable 1 }

	SwhIGMPFilterEntry ::=
		SEQUENCE {
			swhIGMPFilterIndex
				INTEGER,
			swhIGMPFilterPortName
				DisplayString,
			swhIGMPFilterChannelLimit
				INTEGER,
			swhIGMPFilterEnable
				INTEGER,
			swhIGMPFilterIPMCProfile1
				DisplayString,
			swhIGMPFilterIPMCProfile2
				DisplayString,
			swhIGMPFilterIPMCProfile3
				DisplayString,
			swhIGMPFilterIPMCProfile4
				DisplayString
		}

	swhIGMPFilterIndex OBJECT-TYPE
		SYNTAX      INTEGER (0..2147483647)
		MAX-ACCESS  not-accessible
		STATUS      current
		DESCRIPTION
			"A unique value for each index."
		::= { swhIGMPFilterEntry 1 }

	swhIGMPFilterEnable OBJECT-TYPE
		SYNTAX      INTEGER { off(0), on(1) }
		MAX-ACCESS  read-write
		STATUS      current
		DESCRIPTION
			"Enable."
		::= { swhIGMPFilterEntry 3 }

	swhIGMPFilterPortName OBJECT-TYPE
		SYNTAX      DisplayString
		MAX-ACCESS  read-only
		STATUS      current
		DESCRIPTION
			"Port Name."
		::= { swhIGMPFilterEntry 4 }

	swhIGMPFilterIPMCProfile1 OBJECT-TYPE
		SYNTAX      DisplayString
		MAX-ACCESS  read-write
		STATUS      current
		DESCRIPTION
			"IPMC Profile 1."
		::= { swhIGMPFilterEntry 6 }

	swhIGMPFilterIPMCProfile2 OBJECT-TYPE
		SYNTAX      DisplayString
		MAX-ACCESS  read-write
		STATUS      current
		DESCRIPTION
			"IPMC Profile 2."
		::= { swhIGMPFilterEntry 7 }

	swhIGMPFilterIPMCProfile3 OBJECT-TYPE
		SYNTAX      DisplayString
		MAX-ACCESS  read-write
		STATUS      current
		DESCRIPTION
			"IPMC Profile 3."
		::= { swhIGMPFilterEntry 8 }

	swhIGMPFilterIPMCProfile4 OBJECT-TYPE
		SYNTAX      DisplayString
		MAX-ACCESS  read-write
		STATUS      current
		DESCRIPTION
			"IPMC Profile 4."
		::= { swhIGMPFilterEntry 9 }

	swhIGMPFilterChannelLimit OBJECT-TYPE
		SYNTAX      INTEGER (1..512)
		MAX-ACCESS  read-write
		STATUS      current
		DESCRIPTION
			"Channel Limit (1-512), should be larger than 1 to avoid the side effect of the UPnP packets."
		::= { swhIGMPFilterEntry 10 }


-- SwitchManagement(4).SFPPortThreshold(51)

	swhSFPPortThresholdEnable OBJECT-TYPE
		SYNTAX      INTEGER { disable(0), enable(1) }
		MAX-ACCESS  read-write
		STATUS      current
		DESCRIPTION
			"SFP Threshold."
		::= { swhSFPPortThreshold 1 }

	swhSFPPortThresholdInterval OBJECT-TYPE
		SYNTAX      INTEGER (120..86400)
		MAX-ACCESS  read-write
		STATUS      current
		DESCRIPTION
			"Threshold Interval. (120-86400)"
		::= { swhSFPPortThreshold 2 }

	swhSFPPortContinuousAlarm OBJECT-TYPE
		SYNTAX      INTEGER { disable(0), enable(1) }
		MAX-ACCESS  read-write
		STATUS      current
		DESCRIPTION
			"Continuous Alarm."
		::= { swhSFPPortThreshold 3 }

	swhSFPPortIntervalofContinuousAlarm OBJECT-TYPE
		SYNTAX      INTEGER (120..86400)
		MAX-ACCESS  read-write
		STATUS      current
		DESCRIPTION
			"Threshold Interval of Continuous Alarm. (120-86400)"
		::= { swhSFPPortThreshold 4 }

	swhSFPPortSelectList OBJECT-TYPE
		SYNTAX      DisplayString
		MAX-ACCESS  read-write
		STATUS      current
		DESCRIPTION
			"Port Select List."
		::= { swhSFPPortThreshold 9 }

	swhSFPPortThresholdTable OBJECT-TYPE
		SYNTAX      SEQUENCE OF SwhSFPPortThresholdEntry
		MAX-ACCESS  not-accessible
		STATUS      current
		DESCRIPTION
			"Table of SFP port threshold configuration."
		::= { swhSFPPortThreshold 10 }

	-- Table Entry
	swhSFPPortThresholdEntry OBJECT-TYPE
		SYNTAX      SwhSFPPortThresholdEntry
		MAX-ACCESS  not-accessible
		STATUS      current
		DESCRIPTION
			"An entry in the table, containing information about SFP port threshold config."
		INDEX    { swhSFPPortThresholdIndex }
		::= { swhSFPPortThresholdTable 1 }

	SwhSFPPortThresholdEntry ::=
		SEQUENCE {
			swhSFPPortThresholdIndex
				INTEGER,
			swhSFPPortThresholdSelect
				INTEGER,
			swhSFPPortThresholdPort
				DisplayString,
			swhSFPPortThresholdAutoDetect
				INTEGER,
			swhSFPPortThresholdTemperatureCurrent
				DisplayString,
			swhSFPPortThresholdTemperatureHighEnable
				INTEGER,
			swhSFPPortThresholdTemperatureHighAlarm
				DisplayString,
			swhSFPPortThresholdTemperatureHighWarning
				DisplayString,
			swhSFPPortThresholdTemperatureLowEnable
				INTEGER,
			swhSFPPortThresholdTemperatureLowAlarm
				DisplayString,
			swhSFPPortThresholdTemperatureLowWarning
				DisplayString,
			swhSFPPortThresholdVoltageCurrent
				DisplayString,
			swhSFPPortThresholdVoltageHighEnable
				INTEGER,
			swhSFPPortThresholdVoltageHighAlarm
				DisplayString,
			swhSFPPortThresholdVoltageHighWarning
				DisplayString,
			swhSFPPortThresholdVoltageLowEnable
				INTEGER,
			swhSFPPortThresholdVoltageLowAlarm
				DisplayString,
			swhSFPPortThresholdVoltageLowWarning
				DisplayString,
			swhSFPPortThresholdCurrentCurrent
				DisplayString,
			swhSFPPortThresholdCurrentHighEnable
				INTEGER,
			swhSFPPortThresholdCurrentHighAlarm
				DisplayString,
			swhSFPPortThresholdCurrentHighWarning
				DisplayString,
			swhSFPPortThresholdCurrentLowEnable
				INTEGER,
			swhSFPPortThresholdCurrentLowAlarm
				DisplayString,
			swhSFPPortThresholdCurrentLowWarning
				DisplayString,
			swhSFPPortThresholdTXPowerCurrent
				DisplayString,
			swhSFPPortThresholdTXPowerHighEnable
				INTEGER,
			swhSFPPortThresholdTXPowerHighAlarm
				DisplayString,
			swhSFPPortThresholdTXPowerHighWarning
				DisplayString,
			swhSFPPortThresholdTXPowerLowEnable
				INTEGER,
			swhSFPPortThresholdTXPowerLowAlarm
				DisplayString,
			swhSFPPortThresholdTXPowerLowWarning
				DisplayString,
			swhSFPPortThresholdRXPowerCurrent
				DisplayString,
			swhSFPPortThresholdRXPowerHighEnable
				INTEGER,
			swhSFPPortThresholdRXPowerHighAlarm
				DisplayString,
			swhSFPPortThresholdRXPowerHighWarning
				DisplayString,
			swhSFPPortThresholdRXPowerLowEnable
				INTEGER,
			swhSFPPortThresholdRXPowerLowAlarm
				DisplayString,
			swhSFPPortThresholdRXPowerLowWarning
				DisplayString
		}

	swhSFPPortThresholdIndex OBJECT-TYPE
		SYNTAX      INTEGER (0..2147483647)
		MAX-ACCESS  not-accessible
		STATUS      current
		DESCRIPTION
			"A unique value for each index."
		::= { swhSFPPortThresholdEntry 1 }

	swhSFPPortThresholdSelect OBJECT-TYPE
		SYNTAX      INTEGER { b(0), v(1) }
		MAX-ACCESS  read-write
		STATUS      current
		DESCRIPTION
			"Select Port. (b : Blocked  v : Member)"
		::= { swhSFPPortThresholdEntry 2 }

	swhSFPPortThresholdPort OBJECT-TYPE
		SYNTAX      DisplayString
		MAX-ACCESS  read-only
		STATUS      current
		DESCRIPTION
			"Port Name."
		::= { swhSFPPortThresholdEntry 3 }

	swhSFPPortThresholdTemperatureCurrent OBJECT-TYPE
		SYNTAX      DisplayString
		MAX-ACCESS  read-only
		STATUS      current
		DESCRIPTION
			"Temperature Current."
		::= { swhSFPPortThresholdEntry 4 }

	swhSFPPortThresholdTemperatureHighEnable OBJECT-TYPE
		SYNTAX      INTEGER { disable(0), enable(1) }
		MAX-ACCESS  read-write
		STATUS      current
		DESCRIPTION
			"Temperature High Enable."
		::= { swhSFPPortThresholdEntry 5 }

	swhSFPPortThresholdTemperatureHighAlarm OBJECT-TYPE
		SYNTAX      DisplayString
		MAX-ACCESS  read-write
		STATUS      current
		DESCRIPTION
			"Temperature High Alarm."
		::= { swhSFPPortThresholdEntry 6 }

	swhSFPPortThresholdTemperatureLowEnable OBJECT-TYPE
		SYNTAX      INTEGER { disable(0), enable(1) }
		MAX-ACCESS  read-write
		STATUS      current
		DESCRIPTION
			"Temperature Low Enable."
		::= { swhSFPPortThresholdEntry 7 }

	swhSFPPortThresholdTemperatureLowAlarm OBJECT-TYPE
		SYNTAX      DisplayString
		MAX-ACCESS  read-write
		STATUS      current
		DESCRIPTION
			"Temperature Low Alarm."
		::= { swhSFPPortThresholdEntry 8 }

	swhSFPPortThresholdVoltageCurrent OBJECT-TYPE
		SYNTAX      DisplayString
		MAX-ACCESS  read-only
		STATUS      current
		DESCRIPTION
			"Voltage Current."
		::= { swhSFPPortThresholdEntry 9 }

	swhSFPPortThresholdVoltageHighEnable OBJECT-TYPE
		SYNTAX      INTEGER { disable(0), enable(1) }
		MAX-ACCESS  read-write
		STATUS      current
		DESCRIPTION
			"Voltage High Enable."
		::= { swhSFPPortThresholdEntry 10 }

	swhSFPPortThresholdVoltageHighAlarm OBJECT-TYPE
		SYNTAX      DisplayString
		MAX-ACCESS  read-write
		STATUS      current
		DESCRIPTION
			"Voltage High Alarm."
		::= { swhSFPPortThresholdEntry 11 }

	swhSFPPortThresholdVoltageLowEnable OBJECT-TYPE
		SYNTAX      INTEGER { disable(0), enable(1) }
		MAX-ACCESS  read-write
		STATUS      current
		DESCRIPTION
			"Voltage Low Enable."
		::= { swhSFPPortThresholdEntry 12 }

	swhSFPPortThresholdVoltageLowAlarm OBJECT-TYPE
		SYNTAX      DisplayString
		MAX-ACCESS  read-write
		STATUS      current
		DESCRIPTION
			"Voltage Low Alarm."
		::= { swhSFPPortThresholdEntry 13 }

	swhSFPPortThresholdTXPowerCurrent OBJECT-TYPE
		SYNTAX      DisplayString
		MAX-ACCESS  read-only
		STATUS      current
		DESCRIPTION
			"TX Power Current."
		::= { swhSFPPortThresholdEntry 14 }

	swhSFPPortThresholdTXPowerHighEnable OBJECT-TYPE
		SYNTAX      INTEGER { disable(0), enable(1) }
		MAX-ACCESS  read-write
		STATUS      current
		DESCRIPTION
			"TX Power High Enable."
		::= { swhSFPPortThresholdEntry 15 }

	swhSFPPortThresholdTXPowerHighAlarm OBJECT-TYPE
		SYNTAX      DisplayString
		MAX-ACCESS  read-write
		STATUS      current
		DESCRIPTION
			"TX Power High Alarm."
		::= { swhSFPPortThresholdEntry 16 }

	swhSFPPortThresholdTXPowerLowEnable OBJECT-TYPE
		SYNTAX      INTEGER { disable(0), enable(1) }
		MAX-ACCESS  read-write
		STATUS      current
		DESCRIPTION
			"TX Power Low Enable."
		::= { swhSFPPortThresholdEntry 17 }

	swhSFPPortThresholdTXPowerLowAlarm OBJECT-TYPE
		SYNTAX      DisplayString
		MAX-ACCESS  read-write
		STATUS      current
		DESCRIPTION
			"TX Power Low Alarm."
		::= { swhSFPPortThresholdEntry 18 }

	swhSFPPortThresholdRXPowerCurrent OBJECT-TYPE
		SYNTAX      DisplayString
		MAX-ACCESS  read-only
		STATUS      current
		DESCRIPTION
			"RX Power Current."
		::= { swhSFPPortThresholdEntry 19 }

	swhSFPPortThresholdRXPowerHighEnable OBJECT-TYPE
		SYNTAX      INTEGER { disable(0), enable(1) }
		MAX-ACCESS  read-write
		STATUS      current
		DESCRIPTION
			"RX Power High Enable."
		::= { swhSFPPortThresholdEntry 20 }

	swhSFPPortThresholdRXPowerHighAlarm OBJECT-TYPE
		SYNTAX      DisplayString
		MAX-ACCESS  read-write
		STATUS      current
		DESCRIPTION
			"RX Power High Alarm."
		::= { swhSFPPortThresholdEntry 21 }

	swhSFPPortThresholdRXPowerLowEnable OBJECT-TYPE
		SYNTAX      INTEGER { disable(0), enable(1) }
		MAX-ACCESS  read-write
		STATUS      current
		DESCRIPTION
			"RX Power Low Enable."
		::= { swhSFPPortThresholdEntry 22 }

	swhSFPPortThresholdRXPowerLowAlarm OBJECT-TYPE
		SYNTAX      DisplayString
		MAX-ACCESS  read-write
		STATUS      current
		DESCRIPTION
			"RX Power Low Alarm."
		::= { swhSFPPortThresholdEntry 23 }

	swhSFPPortThresholdAutoDetect OBJECT-TYPE
		SYNTAX      INTEGER { disable(0), enable(1) }
		MAX-ACCESS  read-write
		STATUS      current
		DESCRIPTION
			"Auto Detect."
		::= { swhSFPPortThresholdEntry 24 }

	swhSFPPortThresholdTemperatureHighWarning OBJECT-TYPE
		SYNTAX      DisplayString
		MAX-ACCESS  read-write
		STATUS      current
		DESCRIPTION
			"Temperature High Warning."
		::= { swhSFPPortThresholdEntry 25 }

	swhSFPPortThresholdTemperatureLowWarning OBJECT-TYPE
		SYNTAX      DisplayString
		MAX-ACCESS  read-write
		STATUS      current
		DESCRIPTION
			"Temperature Low Warning."
		::= { swhSFPPortThresholdEntry 26 }

	swhSFPPortThresholdVoltageHighWarning OBJECT-TYPE
		SYNTAX      DisplayString
		MAX-ACCESS  read-write
		STATUS      current
		DESCRIPTION
			"Voltage High Warning."
		::= { swhSFPPortThresholdEntry 27 }

	swhSFPPortThresholdVoltageLowWarning OBJECT-TYPE
		SYNTAX      DisplayString
		MAX-ACCESS  read-write
		STATUS      current
		DESCRIPTION
			"Voltage Low Warning."
		::= { swhSFPPortThresholdEntry 28 }

	swhSFPPortThresholdTXPowerHighWarning OBJECT-TYPE
		SYNTAX      DisplayString
		MAX-ACCESS  read-write
		STATUS      current
		DESCRIPTION
			"TX Power High Warning."
		::= { swhSFPPortThresholdEntry 29 }

	swhSFPPortThresholdTXPowerLowWarning OBJECT-TYPE
		SYNTAX      DisplayString
		MAX-ACCESS  read-write
		STATUS      current
		DESCRIPTION
			"TX Power Low Warning."
		::= { swhSFPPortThresholdEntry 30 }

	swhSFPPortThresholdRXPowerHighWarning OBJECT-TYPE
		SYNTAX      DisplayString
		MAX-ACCESS  read-write
		STATUS      current
		DESCRIPTION
			"RX Power High Warning."
		::= { swhSFPPortThresholdEntry 31 }

	swhSFPPortThresholdRXPowerLowWarning OBJECT-TYPE
		SYNTAX      DisplayString
		MAX-ACCESS  read-write
		STATUS      current
		DESCRIPTION
			"RX Power Low Warning."
		::= { swhSFPPortThresholdEntry 32 }

	swhSFPPortThresholdCurrentCurrent OBJECT-TYPE
		SYNTAX      DisplayString
		MAX-ACCESS  read-only
		STATUS      current
		DESCRIPTION
			"Current Current."
		::= { swhSFPPortThresholdEntry 33 }

	swhSFPPortThresholdCurrentHighEnable OBJECT-TYPE
		SYNTAX      INTEGER { disable(0), enable(1) }
		MAX-ACCESS  read-write
		STATUS      current
		DESCRIPTION
			"Current High Enable."
		::= { swhSFPPortThresholdEntry 34 }

	swhSFPPortThresholdCurrentHighAlarm OBJECT-TYPE
		SYNTAX      DisplayString
		MAX-ACCESS  read-write
		STATUS      current
		DESCRIPTION
			"Current High Alarm."
		::= { swhSFPPortThresholdEntry 35 }

	swhSFPPortThresholdCurrentLowEnable OBJECT-TYPE
		SYNTAX      INTEGER { disable(0), enable(1) }
		MAX-ACCESS  read-write
		STATUS      current
		DESCRIPTION
			"Current Low Enable."
		::= { swhSFPPortThresholdEntry 36 }

	swhSFPPortThresholdCurrentLowAlarm OBJECT-TYPE
		SYNTAX      DisplayString
		MAX-ACCESS  read-write
		STATUS      current
		DESCRIPTION
			"Current Low Alarm."
		::= { swhSFPPortThresholdEntry 37 }

	swhSFPPortThresholdCurrentHighWarning OBJECT-TYPE
		SYNTAX      DisplayString
		MAX-ACCESS  read-write
		STATUS      current
		DESCRIPTION
			"Current High Warning."
		::= { swhSFPPortThresholdEntry 38 }

	swhSFPPortThresholdCurrentLowWarning OBJECT-TYPE
		SYNTAX      DisplayString
		MAX-ACCESS  read-write
		STATUS      current
		DESCRIPTION
			"Current Low Warning."
		::= { swhSFPPortThresholdEntry 39 }


-- SwitchManagement(4).8021XConfiguration(55)

	swh8021XSystemConfig
		OBJECT IDENTIFIER ::= { swh8021XConfiguration 3 }

	swh8021XPortConfig
		OBJECT IDENTIFIER ::= { swh8021XConfiguration 6 }


-- SwitchManagement(4).8021XConfiguration(55).8021XSystemConfig(3)

	swh8021XSystemConfigMode OBJECT-TYPE
		SYNTAX      INTEGER { disable(0), enable(1) }
		MAX-ACCESS  read-write
		STATUS      current
		DESCRIPTION
			"Enable."
		::= { swh8021XSystemConfig 1 }

	swh8021XSystemConfigRADIUSIP OBJECT-TYPE
		SYNTAX      DisplayString
		MAX-ACCESS  read-write
		STATUS      current
		DESCRIPTION
			"RADIUS IP."
		::= { swh8021XSystemConfig 3 }

	swh8021XSystemConfigRADIUSSecret OBJECT-TYPE
		SYNTAX      DisplayString
		MAX-ACCESS  read-write
		STATUS      current
		DESCRIPTION
			"RADIUS Secret."
		::= { swh8021XSystemConfig 5 }

	swh8021XSystemConfigSecretKeyEncryption OBJECT-TYPE
		SYNTAX      INTEGER { disable(0), aes-128(1) }
		MAX-ACCESS  read-write
		STATUS      current
		DESCRIPTION
			"Secret Key Encryption."
		::= { swh8021XSystemConfig 17 }

	swh8021XSystemConfigRauthenticationEn OBJECT-TYPE
		SYNTAX      INTEGER { disable(0), enable(1) }
		MAX-ACCESS  read-write
		STATUS      current
		DESCRIPTION
			"Reauthentication Enabled."
		::= { swh8021XSystemConfig 9 }

	swh8021XSystemConfigRadiusAssignedVLANEn OBJECT-TYPE
		SYNTAX      INTEGER { disable(0), enable(1) }
		MAX-ACCESS  read-write
		STATUS      current
		DESCRIPTION
			"RADIUS-Assigned VLAN Enabled."
		::= { swh8021XSystemConfig 15 }


-- SwitchManagement(4).8021XConfiguration(55).8021XPortConfig(6).8021XPortConfigTable(1)

	swh8021XPortConfigTable OBJECT-TYPE
		SYNTAX      SEQUENCE OF Swh8021XPortConfigEntry
		MAX-ACCESS  not-accessible
		STATUS      current
		DESCRIPTION
			"Table of 802.1X port configuration."
		::= { swh8021XPortConfig 1 }

	-- Table Entry
	swh8021XPortConfigEntry OBJECT-TYPE
		SYNTAX      Swh8021XPortConfigEntry
		MAX-ACCESS  not-accessible
		STATUS      current
		DESCRIPTION
			"An entry in the table, containing information about 802.1X port config."
		INDEX    { swh8021XPortConfigIndex }
		::= { swh8021XPortConfigTable 1 }

	Swh8021XPortConfigEntry ::=
		SEQUENCE {
			swh8021XPortConfigIndex
				INTEGER,
			swh8021XPortConfigAdminState
				INTEGER,
			swh8021XPortConfigMAB
				INTEGER,
			swh8021XPortConfigRadiusAssignedVLAN
				INTEGER,
			swh8021XPortConfigreAuthEnable
				INTEGER,
			swh8021XPortConfigreAuthSec
				INTEGER,
			swh8021XPortConfigEAPTimeout
				INTEGER,
			swh8021XPortConfigMaxreq
				INTEGER,
			swh8021XPortConfigReauthenticate
				INTEGER
		}

	swh8021XPortConfigIndex OBJECT-TYPE
		SYNTAX      INTEGER (0..2147483647)
		MAX-ACCESS  not-accessible
		STATUS      current
		DESCRIPTION
			"A unique value for each index."
		::= { swh8021XPortConfigEntry 1 }

	swh8021XPortConfigAdminState OBJECT-TYPE
		SYNTAX      INTEGER { auto(0), authorized(1), unauthorized(2) }
		MAX-ACCESS  read-write
		STATUS      current
		DESCRIPTION
			"Admin State setting is auto or authorized or unauthorized."
		::= { swh8021XPortConfigEntry 3 }

	swh8021XPortConfigReauthenticate OBJECT-TYPE
		SYNTAX      INTEGER { disable(0), enable(1) }
		MAX-ACCESS  read-write
		STATUS      current
		DESCRIPTION
			"Re-Authenticate."
		::= { swh8021XPortConfigEntry 5 }

	swh8021XPortConfigRadiusAssignedVLAN OBJECT-TYPE
		SYNTAX      INTEGER { disable(0), enable(1) }
		MAX-ACCESS  read-write
		STATUS      current
		DESCRIPTION
			"RADIUS-Assigned VLAN Enabled."
		::= { swh8021XPortConfigEntry 7 }

	swh8021XPortConfigMAB OBJECT-TYPE
		SYNTAX      INTEGER { disable(0), enable(1) }
		MAX-ACCESS  read-write
		STATUS      current
		DESCRIPTION
			"MAB."
		::= { swh8021XPortConfigEntry 9 }

	swh8021XPortConfigreAuthEnable OBJECT-TYPE
		SYNTAX      INTEGER { disable(0), enable(1) }
		MAX-ACCESS  read-write
		STATUS      current
		DESCRIPTION
			"Re-Authentication Enabled."
		::= { swh8021XPortConfigEntry 11 }

	swh8021XPortConfigreAuthSec OBJECT-TYPE
		SYNTAX      INTEGER (1..65535)
		MAX-ACCESS  read-write
		STATUS      current
		DESCRIPTION
			"Re-Authentication Period. (Secs 1-65535)"
		::= { swh8021XPortConfigEntry 13 }

	swh8021XPortConfigEAPTimeout OBJECT-TYPE
		SYNTAX      INTEGER (1..255)
		MAX-ACCESS  read-write
		STATUS      current
		DESCRIPTION
			"EAP Timeout. (Secs 1-255)"
		::= { swh8021XPortConfigEntry 15 }

	swh8021XPortConfigMaxreq OBJECT-TYPE
		SYNTAX      INTEGER (1..10)
		MAX-ACCESS  read-write
		STATUS      current
		DESCRIPTION
			"Max Request. (1-10 Times)"
		::= { swh8021XPortConfigEntry 17 }


-- SwitchManagement(4).QoSConfiguration(60)

	swhQoSConfigPriority
		OBJECT IDENTIFIER ::= { swhQoSConfiguration 1 }

	swhQoSConfigPortConfig
		OBJECT IDENTIFIER ::= { swhQoSConfiguration 3 }

	swhQoSConfigRateLimiters
		OBJECT IDENTIFIER ::= { swhQoSConfiguration 9 }


-- SwitchManagement(4).QoSConfiguration(60).QoSConfigPriority(1)

	swhQoSConfigPriorityMode OBJECT-TYPE
		SYNTAX      INTEGER { disable(0), ieee8021p(2), dscp(3) }
		MAX-ACCESS  read-write
		STATUS      current
		DESCRIPTION
			"Specify QoS mode."
		::= { swhQoSConfigPriority 1 }

	swhQoSConfigPriorityQueuingMode OBJECT-TYPE
		SYNTAX      INTEGER { weight(0), strict(1) }
		MAX-ACCESS  read-write
		STATUS      current
		DESCRIPTION
			"Specify the queue mode."
		::= { swhQoSConfigPriority 2 }

	swhQoSConfigPriorityQueueWeighted OBJECT-TYPE
		SYNTAX      DisplayString
		MAX-ACCESS  read-write
		STATUS      current
		DESCRIPTION
			"Specify as weight. (Q0:Q1:Q2:Q3:Q4:Q5:Q6:Q7), Queue is 1~127."
		::= { swhQoSConfigPriority 11 }

	swhQoSConfigPriorityManagementPriority OBJECT-TYPE
		SYNTAX      INTEGER (0..7)
		MAX-ACCESS  read-write
		STATUS      current
		DESCRIPTION
			"Specify Management Priority. (0-7)"
		::= { swhQoSConfigPriority 10 }

	swhQoSConfigPriority8021pRemarking OBJECT-TYPE
		SYNTAX      INTEGER { disable(0), enable(1) }
		MAX-ACCESS  read-write
		STATUS      current
		DESCRIPTION
			"Specify 802.1p Remarking."
		::= { swhQoSConfigPriority 30 }

	swhQoSConfigPriorityDSCPRemarking OBJECT-TYPE
		SYNTAX      INTEGER { disable(0), enable(1) }
		MAX-ACCESS  read-write
		STATUS      current
		DESCRIPTION
			"Specify DSCP Remarking."
		::= { swhQoSConfigPriority 40 }


-- SwitchManagement(4).QoSConfiguration(60).QoSConfigPriority(1).QoSConfig8021pPriorityTable(5)

	swhQoSConfig8021pPriorityTable OBJECT-TYPE
		SYNTAX      SEQUENCE OF SwhQoSConfig8021pPriorityEntry
		MAX-ACCESS  not-accessible
		STATUS      current
		DESCRIPTION
			"Table of 802.1p priority map."
		::= { swhQoSConfigPriority 5 }

	-- Table Entry
	swhQoSConfig8021pPriorityEntry OBJECT-TYPE
		SYNTAX      SwhQoSConfig8021pPriorityEntry
		MAX-ACCESS  not-accessible
		STATUS      current
		DESCRIPTION
			"An entry in the table, containing information about 802.1p priority config."
		INDEX    { swhQoSConfig8021pPriorityIndex }
		::= { swhQoSConfig8021pPriorityTable 1 }

	SwhQoSConfig8021pPriorityEntry ::=
		SEQUENCE {
			swhQoSConfig8021pPriorityIndex
				INTEGER,
			swhQoSConfig8021pPriorityPriority
				INTEGER,
			swhQoSConfig8021pPriorityQueue
				INTEGER
		}

	swhQoSConfig8021pPriorityIndex OBJECT-TYPE
		SYNTAX      INTEGER (0..2147483647)
		MAX-ACCESS  not-accessible
		STATUS      current
		DESCRIPTION
			"A unique value for each index."
		::= { swhQoSConfig8021pPriorityEntry 1 }

	swhQoSConfig8021pPriorityPriority OBJECT-TYPE
		SYNTAX      INTEGER { dot1p-0(0),
		                      dot1p-1(1),
		                      dot1p-2(2),
		                      dot1p-3(3),
		                      dot1p-4(4),
		                      dot1p-5(5),
		                      dot1p-6(6),
		                      dot1p-7(7)
		                    }
		MAX-ACCESS  read-only
		STATUS      current
		DESCRIPTION
			"802.1p priority."
		::= { swhQoSConfig8021pPriorityEntry 2 }

	swhQoSConfig8021pPriorityQueue OBJECT-TYPE
		SYNTAX      INTEGER { q0(0), q1(1), q2(2), q3(3), q4(4), q5(5), q6(6), q7(7) }
		MAX-ACCESS  read-write
		STATUS      current
		DESCRIPTION
			"Specify 802.1p bit value, Q0 Q1 Q2 Q3 Q4 Q5 Q6 Q7."
		::= { swhQoSConfig8021pPriorityEntry 3 }


-- SwitchManagement(4).QoSConfiguration(60).QoSConfigPriority(1).QoSConfigDSCPPriorityTable(6)

	swhQoSConfigDSCPPriorityTable OBJECT-TYPE
		SYNTAX      SEQUENCE OF SwhQoSConfigDSCPPriorityEntry
		MAX-ACCESS  not-accessible
		STATUS      current
		DESCRIPTION
			"Table of DSCP priority map."
		::= { swhQoSConfigPriority 6 }

	-- Table Entry
	swhQoSConfigDSCPPriorityEntry OBJECT-TYPE
		SYNTAX      SwhQoSConfigDSCPPriorityEntry
		MAX-ACCESS  not-accessible
		STATUS      current
		DESCRIPTION
			"An entry in the table, containing information about DSCP priority config."
		INDEX    { swhQoSConfigDSCPPriorityIndex }
		::= { swhQoSConfigDSCPPriorityTable 1 }

	SwhQoSConfigDSCPPriorityEntry ::=
		SEQUENCE {
			swhQoSConfigDSCPPriorityIndex
				INTEGER,
			swhQoSConfigDSCPPriorityPriority
				INTEGER,
			swhQoSConfigDSCPPriorityQueue
				INTEGER
		}

	swhQoSConfigDSCPPriorityIndex OBJECT-TYPE
		SYNTAX      INTEGER (0..2147483647)
		MAX-ACCESS  not-accessible
		STATUS      current
		DESCRIPTION
			"A unique value for each index."
		::= { swhQoSConfigDSCPPriorityEntry 1 }

	swhQoSConfigDSCPPriorityPriority OBJECT-TYPE
		SYNTAX      INTEGER { dscp-0(0), dscp-1(1), dscp-2(2), dscp-3(3),
		                      dscp-4(4), dscp-5(5), dscp-6(6), dscp-7(7),
		                      dscp-8(8), dscp-9(9), dscp-10(10), dscp-11(11),
		                      dscp-12(12), dscp-13(13), dscp-14(14), dscp-15(15),
		                      dscp-16(16), dscp-17(17), dscp-18(18), dscp-19(19),
		                      dscp-20(20), dscp-21(21), dscp-22(22), dscp-23(23),
		                      dscp-24(24), dscp-25(25), dscp-26(26), dscp-27(27),
		                      dscp-28(28), dscp-29(29), dscp-30(30), dscp-31(31),
		                      dscp-32(32), dscp-33(33), dscp-34(34), dscp-35(35),
		                      dscp-36(36), dscp-37(37), dscp-38(38), dscp-39(39),
		                      dscp-40(40), dscp-41(41), dscp-42(42), dscp-43(43),
		                      dscp-44(44), dscp-45(45), dscp-46(46), dscp-47(47),
		                      dscp-48(48), dscp-49(49), dscp-50(50), dscp-51(51),
		                      dscp-52(52), dscp-53(53), dscp-54(54), dscp-55(55),
		                      dscp-56(56), dscp-57(57), dscp-58(58), dscp-59(59),
		                      dscp-60(60), dscp-61(61), dscp-62(62), dscp-63(63)
		                    }
		MAX-ACCESS  read-only
		STATUS      current
		DESCRIPTION
			"DSCP priority."
		::= { swhQoSConfigDSCPPriorityEntry 2 }

	swhQoSConfigDSCPPriorityQueue OBJECT-TYPE
		SYNTAX      INTEGER { q0(0), q1(1), q2(2), q3(3), q4(4), q5(5), q6(6), q7(7) }
		MAX-ACCESS  read-write
		STATUS      current
		DESCRIPTION
			"Specify DSCP bit value, Q0 Q1 Q2 Q3 Q4 Q5 Q6 Q7."
		::= { swhQoSConfigDSCPPriorityEntry 3 }


-- SwitchManagement(4).QoSConfiguration(60).QoSConfigPriority(1).QoSConfig8021pRemarkingTable(31)

	swhQoSConfig8021pRemarkingTable OBJECT-TYPE
		SYNTAX      SEQUENCE OF SwhQoSConfig8021pRemarkingEntry
		MAX-ACCESS  not-accessible
		STATUS      current
		DESCRIPTION
			"Table of 802.1p remarking map."
		::= { swhQoSConfigPriority 31 }

	-- Table Entry
	swhQoSConfig8021pRemarkingEntry OBJECT-TYPE
		SYNTAX      SwhQoSConfig8021pRemarkingEntry
		MAX-ACCESS  not-accessible
		STATUS      current
		DESCRIPTION
			"An entry in the table, containing information about 802.1p remarking config."
		INDEX    { swhQoSConfig8021pRemarkingIndex }
		::= { swhQoSConfig8021pRemarkingTable 1 }

	SwhQoSConfig8021pRemarkingEntry ::=
		SEQUENCE {
			swhQoSConfig8021pRemarkingIndex
				INTEGER,
			swhQoSConfig8021pRemarkingRx8021p
				INTEGER,
			swhQoSConfig8021pRemarkingNew8021p
				INTEGER
		}

	swhQoSConfig8021pRemarkingIndex OBJECT-TYPE
		SYNTAX      INTEGER (0..2147483647)
		MAX-ACCESS  not-accessible
		STATUS      current
		DESCRIPTION
			"A unique value for each index."
		::= { swhQoSConfig8021pRemarkingEntry 1 }

	swhQoSConfig8021pRemarkingNew8021p OBJECT-TYPE
		SYNTAX      INTEGER (0..7)
		MAX-ACCESS  read-write
		STATUS      current
		DESCRIPTION
			"New-802.1p. (0-7)"
		::= { swhQoSConfig8021pRemarkingEntry 3 }

	swhQoSConfig8021pRemarkingRx8021p OBJECT-TYPE
		SYNTAX      INTEGER (0..7)
		MAX-ACCESS  read-only
		STATUS      current
		DESCRIPTION
			"Rx-802.1p. (0-7)"
		::= { swhQoSConfig8021pRemarkingEntry 5 }


-- SwitchManagement(4).QoSConfiguration(60).QoSConfigPriority(1).QoSConfigDSCPRemarkingTable(41)

	swhQoSConfigDSCPRemarkingTable OBJECT-TYPE
		SYNTAX      SEQUENCE OF SwhQoSConfigDSCPRemarkingEntry
		MAX-ACCESS  not-accessible
		STATUS      current
		DESCRIPTION
			"Table of DSCP remarking map."
		::= { swhQoSConfigPriority 41 }

	-- Table Entry
	swhQoSConfigDSCPRemarkingEntry OBJECT-TYPE
		SYNTAX      SwhQoSConfigDSCPRemarkingEntry
		MAX-ACCESS  not-accessible
		STATUS      current
		DESCRIPTION
			"An entry in the table, containing information about DSCP remarking config."
		INDEX    { swhQoSConfigDSCPRemarkingIndex }
		::= { swhQoSConfigDSCPRemarkingTable 1 }

	SwhQoSConfigDSCPRemarkingEntry ::=
		SEQUENCE {
			swhQoSConfigDSCPRemarkingIndex
				INTEGER,
			swhQoSConfigDSCPRemarkingRxDSCP
				INTEGER,
			swhQoSConfigDSCPRemarkingNewDSCP
				INTEGER
		}

	swhQoSConfigDSCPRemarkingIndex OBJECT-TYPE
		SYNTAX      INTEGER (0..2147483647)
		MAX-ACCESS  not-accessible
		STATUS      current
		DESCRIPTION
			"A unique value for each index."
		::= { swhQoSConfigDSCPRemarkingEntry 1 }

	swhQoSConfigDSCPRemarkingNewDSCP OBJECT-TYPE
		SYNTAX      INTEGER (0..63)
		MAX-ACCESS  read-write
		STATUS      current
		DESCRIPTION
			"New-DSCP. (0-63)"
		::= { swhQoSConfigDSCPRemarkingEntry 3 }

	swhQoSConfigDSCPRemarkingRxDSCP OBJECT-TYPE
		SYNTAX      INTEGER (0..63)
		MAX-ACCESS  read-write
		STATUS      current
		DESCRIPTION
			"Rx-DSCP. (0-63)"
		::= { swhQoSConfigDSCPRemarkingEntry 5 }


-- SwitchManagement(4).QoSConfiguration(60).QoSConfigPortConfig(3).QoSConfigPortConfigTable(1)

	swhQoSConfigPortConfigTable OBJECT-TYPE
		SYNTAX      SEQUENCE OF SwhQoSConfigPortConfigEntry
		MAX-ACCESS  not-accessible
		STATUS      current
		DESCRIPTION
			"Table of QoS port configuration."
		::= { swhQoSConfigPortConfig 1 }

	-- Table Entry
	swhQoSConfigPortConfigEntry OBJECT-TYPE
		SYNTAX      SwhQoSConfigPortConfigEntry
		MAX-ACCESS  not-accessible
		STATUS      current
		DESCRIPTION
			"An entry in the table, containing information about QoS port configuration."
		INDEX    { swhQoSConfigPortConfigIndex }
		::= { swhQoSConfigPortConfigTable 1 }

	SwhQoSConfigPortConfigEntry ::=
		SEQUENCE {
			swhQoSConfigPortConfigIndex
				INTEGER,
			swhQoSConfigPortConfigUserPriority
				INTEGER
		}

	swhQoSConfigPortConfigIndex OBJECT-TYPE
		SYNTAX      INTEGER (0..2147483647)
		MAX-ACCESS  not-accessible
		STATUS      current
		DESCRIPTION
			"A unique value for each index."
		::= { swhQoSConfigPortConfigEntry 1 }

	swhQoSConfigPortConfigUserPriority OBJECT-TYPE
		SYNTAX      INTEGER (0..7)
		MAX-ACCESS  read-write
		STATUS      current
		DESCRIPTION
			"User Priority. (0-7)"
		::= { swhQoSConfigPortConfigEntry 7 }


-- SwitchManagement(4).QoSConfiguration(60).QoSConfigRateLimiters(9).QoSConfigRateLimitersTable(1)

	swhQoSConfigRateLimitersTable OBJECT-TYPE
		SYNTAX      SEQUENCE OF SwhQoSConfigRateLimitersEntry
		MAX-ACCESS  not-accessible
		STATUS      current
		DESCRIPTION
			"Table of QoS rate limiters."
		::= { swhQoSConfigRateLimiters 1 }

	-- Table Entry
	swhQoSConfigRateLimitersEntry OBJECT-TYPE
		SYNTAX      SwhQoSConfigRateLimitersEntry
		MAX-ACCESS  not-accessible
		STATUS      current
		DESCRIPTION
			"An entry in the table, containing information about QoS rate limiters."
		INDEX    { swhQoSConfigRateLimitersIndex }
		::= { swhQoSConfigRateLimitersTable 1 }

	SwhQoSConfigRateLimitersEntry ::=
		SEQUENCE {
			swhQoSConfigRateLimitersIndex
				INTEGER,
			swhQoSConfigRateLimitersIngressEnable
				INTEGER,
			swhQoSConfigRateLimitersIngressRate
				INTEGER,
			swhQoSConfigRateLimitersIngressUnit
				INTEGER,
			swhQoSConfigRateLimitersEgressEnable
				INTEGER,
			swhQoSConfigRateLimitersEgressRate
				INTEGER,
			swhQoSConfigRateLimitersEgressUnit
				INTEGER
		}

	swhQoSConfigRateLimitersIndex OBJECT-TYPE
		SYNTAX      INTEGER (0..2147483647)
		MAX-ACCESS  not-accessible
		STATUS      current
		DESCRIPTION
			"A unique value for each index."
		::= { swhQoSConfigRateLimitersEntry 1 }

	swhQoSConfigRateLimitersIngressRate OBJECT-TYPE
		SYNTAX      INTEGER (500..10000000)
		MAX-ACCESS  read-write
		STATUS      current
		DESCRIPTION
			"Ingress Rate."
		::= { swhQoSConfigRateLimitersEntry 3 }

	swhQoSConfigRateLimitersEgressRate OBJECT-TYPE
		SYNTAX      INTEGER (500..10000000)
		MAX-ACCESS  read-write
		STATUS      current
		DESCRIPTION
			"Egress Rate."
		::= { swhQoSConfigRateLimitersEntry 5 }

	swhQoSConfigRateLimitersIngressEnable OBJECT-TYPE
		SYNTAX      INTEGER { disable(0), enable(1) }
		MAX-ACCESS  read-write
		STATUS      current
		DESCRIPTION
			"Ingress Enable."
		::= { swhQoSConfigRateLimitersEntry 6 }

	swhQoSConfigRateLimitersIngressUnit OBJECT-TYPE
		SYNTAX      INTEGER { kbps(0), mbps(1) }
		MAX-ACCESS  read-write
		STATUS      current
		DESCRIPTION
			"Ingress Unit."
		::= { swhQoSConfigRateLimitersEntry 7 }

	swhQoSConfigRateLimitersEgressEnable OBJECT-TYPE
		SYNTAX      INTEGER { disable(0), enable(1) }
		MAX-ACCESS  read-write
		STATUS      current
		DESCRIPTION
			"Egress Enable."
		::= { swhQoSConfigRateLimitersEntry 8 }

	swhQoSConfigRateLimitersEgressUnit OBJECT-TYPE
		SYNTAX      INTEGER { kbps(0), mbps(1) }
		MAX-ACCESS  read-write
		STATUS      current
		DESCRIPTION
			"Egress Unit."
		::= { swhQoSConfigRateLimitersEntry 9 }


-- SwitchManagement(4).ACLConfiguration(65)

	swhAccessControlListIPv4
		OBJECT IDENTIFIER ::= { swhACLConfiguration 4 }

	swhAccessControlListIPv6
		OBJECT IDENTIFIER ::= { swhACLConfiguration 5 }


-- SwitchManagement(4).ACLConfiguration(65).AccessControlListIPv4(4)

	swhAccessControlListIPv4Table OBJECT-TYPE
		SYNTAX      SEQUENCE OF SwhAccessControlListIPv4Entry
		MAX-ACCESS  not-accessible
		STATUS      current
		DESCRIPTION
			"Table of access control list."
		::= { swhAccessControlListIPv4 1 }

	-- Table Entry
	swhAccessControlListIPv4Entry OBJECT-TYPE
		SYNTAX      SwhAccessControlListIPv4Entry
		MAX-ACCESS  not-accessible
		STATUS      current
		DESCRIPTION
			"An entry in the table, containing information about access control list."
		INDEX    { swhAccessControlListIPv4Index }
		::= { swhAccessControlListIPv4Table 1 }

	SwhAccessControlListIPv4Entry ::=
		SEQUENCE {
			swhAccessControlListIPv4Index
				INTEGER,
			swhAccessControlListIPv4Valid
				INTEGER,
			swhAccessControlListIPv4RuleID
				INTEGER,
			swhAccessControlListIPv4Name
				DisplayString,
			swhAccessControlListIPv4Sequence
				INTEGER,
			swhAccessControlListIPv4Enable
				INTEGER,
			swhAccessControlListIPv4IngressPortFilter
				INTEGER,
			swhAccessControlListIPv4IngressPort
				DisplayString,
			swhAccessControlListIPv4EtherTypeFilter
				INTEGER,
			swhAccessControlListIPv4EthernetTypeValue
				DisplayString,
			swhAccessControlListIPv4VLANIDFilter
				INTEGER,
			swhAccessControlListIPv4VLANID
				INTEGER,
			swhAccessControlListIPv4SourceMACFilter
				INTEGER,
			swhAccessControlListIPv4SourceMACValue
				DisplayString,
			swhAccessControlListIPv4SourceMACMask
				DisplayString,
			swhAccessControlListIPv4DestinationMACFilter
				INTEGER,
			swhAccessControlListIPv4DestinationMACValue
				DisplayString,
			swhAccessControlListIPv4DestinationMACMask
				DisplayString,
			swhAccessControlListIPv4TOSTrafficClassFilter
				INTEGER,
			swhAccessControlListIPv4TOSTrafficClass
				DisplayString,
			swhAccessControlListIPv4ProtocolNextHeaderFilter
				INTEGER,
			swhAccessControlListIPv4ProtocolNextHeader
				DisplayString,
			swhAccessControlListIPv4IPv4SourceIPFilter
				INTEGER,
			swhAccessControlListIPv4IPv4SourceIPAddress
				DisplayString,
			swhAccessControlListIPv4IPv4SourceIPMask
				DisplayString,
			swhAccessControlListIPv4IPv4DestinationIPFilter
				INTEGER,
			swhAccessControlListIPv4IPv4DestinationIPAddress
				DisplayString,
			swhAccessControlListIPv4IPv4DestinationIPMask
				DisplayString,
			swhAccessControlListIPv4TCPUDPSourcePortFilter
				INTEGER,
			swhAccessControlListIPv4TCPUDPSourcePort
				INTEGER,
			swhAccessControlListIPv4TCPUDPSourcePortMask
				DisplayString,
			swhAccessControlListIPv4TCPUDPDestinationPortFilter
				INTEGER,
			swhAccessControlListIPv4TCPUDPDestinationPort
				INTEGER,
			swhAccessControlListIPv4TCPUDPDestinationPortMask
				DisplayString,
			swhAccessControlListIPv4Action
				INTEGER,
			swhAccessControlListIPv4PortCopy
				INTEGER,
			swhAccessControlListIPv4RateLimiter
				INTEGER,
			swhAccessControlListIPv4Apply
				INTEGER,
			swhAccessControlListIPv4Delete
				INTEGER
		}

	swhAccessControlListIPv4Index OBJECT-TYPE
		SYNTAX      INTEGER (0..2147483647)
		MAX-ACCESS  not-accessible
		STATUS      current
		DESCRIPTION
			"A unique value for each index."
		::= { swhAccessControlListIPv4Entry 1 }

	swhAccessControlListIPv4Valid OBJECT-TYPE
		SYNTAX      INTEGER { invalid(0), valid(1) }
		MAX-ACCESS  read-only
		STATUS      current
		DESCRIPTION
			"This entry is valid or invalid."
		::= { swhAccessControlListIPv4Entry 2 }

	swhAccessControlListIPv4RuleID OBJECT-TYPE
		SYNTAX      INTEGER (1..64)
		MAX-ACCESS  read-only
		STATUS      current
		DESCRIPTION
			"Rule ID. (1-64)"
		::= { swhAccessControlListIPv4Entry 3 }

	swhAccessControlListIPv4IngressPort OBJECT-TYPE
		SYNTAX      DisplayString
		MAX-ACCESS  read-write
		STATUS      current
		DESCRIPTION
			"Ingress Port List."
		::= { swhAccessControlListIPv4Entry 4 }

	swhAccessControlListIPv4Action OBJECT-TYPE
		SYNTAX      INTEGER { deny(0), permit(1), mirror(2), redirct(3) }
		MAX-ACCESS  read-write
		STATUS      current
		DESCRIPTION
			"Action."
		::= { swhAccessControlListIPv4Entry 6 }

	swhAccessControlListIPv4RateLimiter OBJECT-TYPE
		SYNTAX      INTEGER
		MAX-ACCESS  read-write
		STATUS      current
		DESCRIPTION
			"Rate Limiter is 16-10485600 Kbps, disable is 0. 
			 Value drops to upper bound when bound is exceeded (1G port: 1048560, 10G port: 10485600)"
		::= { swhAccessControlListIPv4Entry 7 }

	swhAccessControlListIPv4PortCopy OBJECT-TYPE
		SYNTAX      INTEGER
		MAX-ACCESS  read-write
		STATUS      current
		DESCRIPTION
			"Port Copy is 1-12."
		::= { swhAccessControlListIPv4Entry 8 }

	swhAccessControlListIPv4Delete OBJECT-TYPE
		SYNTAX      INTEGER { normal(0), delete(1) }
		MAX-ACCESS  read-write
		STATUS      current
		DESCRIPTION
			"Delete this entry."
		::= { swhAccessControlListIPv4Entry 10 }

	swhAccessControlListIPv4SourceMACFilter OBJECT-TYPE
		SYNTAX      INTEGER { any(0), specific(1) }
		MAX-ACCESS  read-write
		STATUS      current
		DESCRIPTION
			"Source MAC Filter is any or specific."
		::= { swhAccessControlListIPv4Entry 11 }

	swhAccessControlListIPv4SourceMACValue OBJECT-TYPE
		SYNTAX      DisplayString
		MAX-ACCESS  read-write
		STATUS      current
		DESCRIPTION
			"Source MAC Value."
		::= { swhAccessControlListIPv4Entry 12 }

	swhAccessControlListIPv4DestinationMACFilter OBJECT-TYPE
		SYNTAX      INTEGER { any(0), specific(1) }
		MAX-ACCESS  read-write
		STATUS      current
		DESCRIPTION
			"Destination MAC Filter."
		::= { swhAccessControlListIPv4Entry 13 }

	swhAccessControlListIPv4DestinationMACValue OBJECT-TYPE
		SYNTAX      DisplayString
		MAX-ACCESS  read-write
		STATUS      current
		DESCRIPTION
			"Destination MAC Value."
		::= { swhAccessControlListIPv4Entry 14 }

	swhAccessControlListIPv4VLANIDFilter OBJECT-TYPE
		SYNTAX      INTEGER { any(0), specific(1) }
		MAX-ACCESS  read-write
		STATUS      current
		DESCRIPTION
			"VLAN ID Filter."
		::= { swhAccessControlListIPv4Entry 15 }

	swhAccessControlListIPv4VLANID OBJECT-TYPE
		SYNTAX      INTEGER (1..4094)
		MAX-ACCESS  read-write
		STATUS      current
		DESCRIPTION
			"VLAN ID. (1-4094)"
		::= { swhAccessControlListIPv4Entry 16 }

	swhAccessControlListIPv4EtherTypeFilter OBJECT-TYPE
		SYNTAX      INTEGER { any(0), specific(1) }
		MAX-ACCESS  read-write
		STATUS      current
		DESCRIPTION
			"Ether Type Filter."
		::= { swhAccessControlListIPv4Entry 18 }

	swhAccessControlListIPv4EthernetTypeValue OBJECT-TYPE
		SYNTAX      DisplayString
		MAX-ACCESS  read-write
		STATUS      current
		DESCRIPTION
			"Ethernet Type Value."
		::= { swhAccessControlListIPv4Entry 19 }

	swhAccessControlListIPv4IngressPortFilter OBJECT-TYPE
		SYNTAX      INTEGER { any(0), specific(1) }
		MAX-ACCESS  read-write
		STATUS      current
		DESCRIPTION
			"Ingress Port Filter."
		::= { swhAccessControlListIPv4Entry 63 }

	swhAccessControlListIPv4SourceMACMask OBJECT-TYPE
		SYNTAX      DisplayString
		MAX-ACCESS  read-write
		STATUS      current
		DESCRIPTION
			"Source MAC Mask."
		::= { swhAccessControlListIPv4Entry 64 }

	swhAccessControlListIPv4DestinationMACMask OBJECT-TYPE
		SYNTAX      DisplayString
		MAX-ACCESS  read-write
		STATUS      current
		DESCRIPTION
			"Destination MAC Mask."
		::= { swhAccessControlListIPv4Entry 65 }

	swhAccessControlListIPv4TOSTrafficClassFilter OBJECT-TYPE
		SYNTAX      INTEGER { any(0), specific(1) }
		MAX-ACCESS  read-write
		STATUS      current
		DESCRIPTION
			"TOS/Traffic Class Filter."
		::= { swhAccessControlListIPv4Entry 66 }

	swhAccessControlListIPv4TOSTrafficClass OBJECT-TYPE
		SYNTAX      DisplayString
		MAX-ACCESS  read-write
		STATUS      current
		DESCRIPTION
			"TOS/Traffic Class. (00-FF)"
		::= { swhAccessControlListIPv4Entry 67 }

	swhAccessControlListIPv4ProtocolNextHeaderFilter OBJECT-TYPE
		SYNTAX      INTEGER { any(0), specific(1) }
		MAX-ACCESS  read-write
		STATUS      current
		DESCRIPTION
			"Protocol/Next Header Filter."
		::= { swhAccessControlListIPv4Entry 68 }

	swhAccessControlListIPv4ProtocolNextHeader OBJECT-TYPE
		SYNTAX      DisplayString
		MAX-ACCESS  read-write
		STATUS      current
		DESCRIPTION
			"Protocol/Next Header. (00-FF)"
		::= { swhAccessControlListIPv4Entry 69 }

	swhAccessControlListIPv4IPv4SourceIPFilter OBJECT-TYPE
		SYNTAX      INTEGER { any(0), network(1) }
		MAX-ACCESS  read-write
		STATUS      current
		DESCRIPTION
			"IPv4 Source IP Filter."
		::= { swhAccessControlListIPv4Entry 70 }

	swhAccessControlListIPv4IPv4SourceIPAddress OBJECT-TYPE
		SYNTAX      DisplayString
		MAX-ACCESS  read-write
		STATUS      current
		DESCRIPTION
			"IPv4 Source IP Address."
		::= { swhAccessControlListIPv4Entry 71 }

	swhAccessControlListIPv4IPv4SourceIPMask OBJECT-TYPE
		SYNTAX      DisplayString
		MAX-ACCESS  read-write
		STATUS      current
		DESCRIPTION
			"IPv4 Source IP Mask."
		::= { swhAccessControlListIPv4Entry 72 }

	swhAccessControlListIPv4IPv4DestinationIPFilter OBJECT-TYPE
		SYNTAX      INTEGER { any(0), network(1) }
		MAX-ACCESS  read-write
		STATUS      current
		DESCRIPTION
			"IPv4 Destination IP Filter."
		::= { swhAccessControlListIPv4Entry 73 }

	swhAccessControlListIPv4IPv4DestinationIPAddress OBJECT-TYPE
		SYNTAX      DisplayString
		MAX-ACCESS  read-write
		STATUS      current
		DESCRIPTION
			"IPv4 Destination IP Address."
		::= { swhAccessControlListIPv4Entry 74 }

	swhAccessControlListIPv4IPv4DestinationIPMask OBJECT-TYPE
		SYNTAX      DisplayString
		MAX-ACCESS  read-write
		STATUS      current
		DESCRIPTION
			"IPv4 Destination IP Mask."
		::= { swhAccessControlListIPv4Entry 75 }

	swhAccessControlListIPv4TCPUDPSourcePortFilter OBJECT-TYPE
		SYNTAX      INTEGER { any(0), specific(1) }
		MAX-ACCESS  read-write
		STATUS      current
		DESCRIPTION
			"TCP/UDP Source Port Filter."
		::= { swhAccessControlListIPv4Entry 82 }

	swhAccessControlListIPv4TCPUDPSourcePort OBJECT-TYPE
		SYNTAX      INTEGER (1..65535)
		MAX-ACCESS  read-write
		STATUS      current
		DESCRIPTION
			"TCP/UDP Source Port. (1-65535)"
		::= { swhAccessControlListIPv4Entry 83 }

	swhAccessControlListIPv4TCPUDPSourcePortMask OBJECT-TYPE
		SYNTAX      DisplayString
		MAX-ACCESS  read-write
		STATUS      current
		DESCRIPTION
			"TCP/UDP Source Port Mask. (0000-FFFF)"
		::= { swhAccessControlListIPv4Entry 84 }

	swhAccessControlListIPv4TCPUDPDestinationPortFilter OBJECT-TYPE
		SYNTAX      INTEGER { any(0), specific(1) }
		MAX-ACCESS  read-write
		STATUS      current
		DESCRIPTION
			"TCP/UDP Destination Port Filter."
		::= { swhAccessControlListIPv4Entry 85 }

	swhAccessControlListIPv4TCPUDPDestinationPort OBJECT-TYPE
		SYNTAX      INTEGER (1..65535)
		MAX-ACCESS  read-write
		STATUS      current
		DESCRIPTION
			"TCP/UDP Destination Port. (1-65535)"
		::= { swhAccessControlListIPv4Entry 86 }

	swhAccessControlListIPv4TCPUDPDestinationPortMask OBJECT-TYPE
		SYNTAX      DisplayString
		MAX-ACCESS  read-write
		STATUS      current
		DESCRIPTION
			"TCP/UDP Destination Port Mask. (0000-FFFF)"
		::= { swhAccessControlListIPv4Entry 87 }

	swhAccessControlListIPv4Name OBJECT-TYPE
		SYNTAX      DisplayString
		MAX-ACCESS  read-write
		STATUS      current
		DESCRIPTION
			"Name."
		::= { swhAccessControlListIPv4Entry 88 }

	swhAccessControlListIPv4Sequence OBJECT-TYPE
		SYNTAX      INTEGER
		MAX-ACCESS  read-write
		STATUS      current
		DESCRIPTION
			"Sequence."
		::= { swhAccessControlListIPv4Entry 89 }

	swhAccessControlListIPv4Enable OBJECT-TYPE
		SYNTAX      INTEGER { disable(0), enable(1) }
		MAX-ACCESS  read-write
		STATUS      current
		DESCRIPTION
			"Enable."
		::= { swhAccessControlListIPv4Entry 90 }

	swhAccessControlListIPv4Apply OBJECT-TYPE
		SYNTAX      INTEGER { none(0), apply(1) }
		MAX-ACCESS  read-write
		STATUS      current
		DESCRIPTION
			"Apply Access Control List."
		::= { swhAccessControlListIPv4Entry 200 }


-- SwitchManagement(4).ACLConfiguration(65).AccessControlListIPv6(5)

	swhAccessControlListIPv6Table OBJECT-TYPE
		SYNTAX      SEQUENCE OF SwhAccessControlListIPv6Entry
		MAX-ACCESS  not-accessible
		STATUS      current
		DESCRIPTION
			"Table of access control list."
		::= { swhAccessControlListIPv6 1 }

	-- Table Entry
	swhAccessControlListIPv6Entry OBJECT-TYPE
		SYNTAX      SwhAccessControlListIPv6Entry
		MAX-ACCESS  not-accessible
		STATUS      current
		DESCRIPTION
			"An entry in the table, containing information about access control list."
		INDEX    { swhAccessControlListIPv6Index }
		::= { swhAccessControlListIPv6Table 1 }

	SwhAccessControlListIPv6Entry ::=
		SEQUENCE {
			swhAccessControlListIPv6Index
				INTEGER,
			swhAccessControlListIPv6Valid
				INTEGER,
			swhAccessControlListIPv6RuleID
				INTEGER,
			swhAccessControlListIPv6Name
				DisplayString,
			swhAccessControlListIPv6Sequence
				INTEGER,
			swhAccessControlListIPv6Enable
				INTEGER,
			swhAccessControlListIPv6IngressPortFilter
				INTEGER,
			swhAccessControlListIPv6IngressPort
				DisplayString,
			swhAccessControlListIPv6EtherTypeFilter
				INTEGER,
			swhAccessControlListIPv6EthernetTypeValue
				DisplayString,
			swhAccessControlListIPv6VLANIDFilter
				INTEGER,
			swhAccessControlListIPv6VLANID
				INTEGER,
			swhAccessControlListIPv6SourceMACFilter
				INTEGER,
			swhAccessControlListIPv6SourceMACValue
				DisplayString,
			swhAccessControlListIPv6SourceMACMask
				DisplayString,
			swhAccessControlListIPv6DestinationMACFilter
				INTEGER,
			swhAccessControlListIPv6DestinationMACValue
				DisplayString,
			swhAccessControlListIPv6DestinationMACMask
				DisplayString,
			swhAccessControlListIPv6TOSTrafficClassFilter
				INTEGER,
			swhAccessControlListIPv6TOSTrafficClass
				DisplayString,
			swhAccessControlListIPv6ProtocolNextHeaderFilter
				INTEGER,
			swhAccessControlListIPv6ProtocolNextHeader
				DisplayString,
			swhAccessControlListIPv6IPv6SourceIPFilter
				INTEGER,
			swhAccessControlListIPv6IPv6SourceIPAddress
				DisplayString,
			swhAccessControlListIPv6IPv6SourceIPPrefix
				INTEGER,
			swhAccessControlListIPv6IPv6DestinationIPFilter
				INTEGER,
			swhAccessControlListIPv6IPv6DestinationIPAddress
				DisplayString,
			swhAccessControlListIPv6IPv6DestinationIPPrefix
				INTEGER,
			swhAccessControlListIPv6TCPUDPSourcePortFilter
				INTEGER,
			swhAccessControlListIPv6TCPUDPSourcePort
				INTEGER,
			swhAccessControlListIPv6TCPUDPSourcePortMask
				DisplayString,
			swhAccessControlListIPv6TCPUDPDestinationPortFilter
				INTEGER,
			swhAccessControlListIPv6TCPUDPDestinationPort
				INTEGER,
			swhAccessControlListIPv6TCPUDPDestinationPortMask
				DisplayString,
			swhAccessControlListIPv6Action
				INTEGER,
			swhAccessControlListIPv6PortCopy
				INTEGER,
			swhAccessControlListIPv6RateLimiter
				INTEGER,
			swhAccessControlListIPv6Apply
				INTEGER,
			swhAccessControlListIPv6Delete
				INTEGER
		}

	swhAccessControlListIPv6Index OBJECT-TYPE
		SYNTAX      INTEGER (0..2147483647)
		MAX-ACCESS  not-accessible
		STATUS      current
		DESCRIPTION
			"A unique value for each index."
		::= { swhAccessControlListIPv6Entry 1 }

	swhAccessControlListIPv6Valid OBJECT-TYPE
		SYNTAX      INTEGER { invalid(0), valid(1) }
		MAX-ACCESS  read-only
		STATUS      current
		DESCRIPTION
			"This entry is valid or invalid."
		::= { swhAccessControlListIPv6Entry 2 }

	swhAccessControlListIPv6RuleID OBJECT-TYPE
		SYNTAX      INTEGER (1..32)
		MAX-ACCESS  read-only
		STATUS      current
		DESCRIPTION
			"Rule ID. (1-32)"
		::= { swhAccessControlListIPv6Entry 3 }

	swhAccessControlListIPv6IngressPort OBJECT-TYPE
		SYNTAX      DisplayString
		MAX-ACCESS  read-write
		STATUS      current
		DESCRIPTION
			"Ingress Port List."
		::= { swhAccessControlListIPv6Entry 4 }

	swhAccessControlListIPv6Action OBJECT-TYPE
		SYNTAX      INTEGER { deny(0), permit(1), mirror(2), redirct(3) }
		MAX-ACCESS  read-write
		STATUS      current
		DESCRIPTION
			"Action."
		::= { swhAccessControlListIPv6Entry 6 }

	swhAccessControlListIPv6RateLimiter OBJECT-TYPE
		SYNTAX      INTEGER
		MAX-ACCESS  read-write
		STATUS      current
		DESCRIPTION
			"Rate Limiter is 16-10485600 Kbps, disable is 0. 
			 Value drops to upper bound when bound is exceeded (1G port: 1048560, 10G port: 10485600)"
		::= { swhAccessControlListIPv6Entry 7 }

	swhAccessControlListIPv6PortCopy OBJECT-TYPE
		SYNTAX      INTEGER
		MAX-ACCESS  read-write
		STATUS      current
		DESCRIPTION
			"Port Copy is 1-12."
		::= { swhAccessControlListIPv6Entry 8 }

	swhAccessControlListIPv6Delete OBJECT-TYPE
		SYNTAX      INTEGER { normal(0), delete(1) }
		MAX-ACCESS  read-write
		STATUS      current
		DESCRIPTION
			"Delete this entry."
		::= { swhAccessControlListIPv6Entry 10 }

	swhAccessControlListIPv6SourceMACFilter OBJECT-TYPE
		SYNTAX      INTEGER { any(0), specific(1) }
		MAX-ACCESS  read-write
		STATUS      current
		DESCRIPTION
			"Source MAC Filter is any or specific."
		::= { swhAccessControlListIPv6Entry 11 }

	swhAccessControlListIPv6SourceMACValue OBJECT-TYPE
		SYNTAX      DisplayString
		MAX-ACCESS  read-write
		STATUS      current
		DESCRIPTION
			"Source MAC Value."
		::= { swhAccessControlListIPv6Entry 12 }

	swhAccessControlListIPv6DestinationMACFilter OBJECT-TYPE
		SYNTAX      INTEGER { any(0), specific(1) }
		MAX-ACCESS  read-write
		STATUS      current
		DESCRIPTION
			"Destination MAC Filter."
		::= { swhAccessControlListIPv6Entry 13 }

	swhAccessControlListIPv6DestinationMACValue OBJECT-TYPE
		SYNTAX      DisplayString
		MAX-ACCESS  read-write
		STATUS      current
		DESCRIPTION
			"Destination MAC Value."
		::= { swhAccessControlListIPv6Entry 14 }

	swhAccessControlListIPv6VLANIDFilter OBJECT-TYPE
		SYNTAX      INTEGER { any(0), specific(1) }
		MAX-ACCESS  read-write
		STATUS      current
		DESCRIPTION
			"VLAN ID Filter."
		::= { swhAccessControlListIPv6Entry 15 }

	swhAccessControlListIPv6VLANID OBJECT-TYPE
		SYNTAX      INTEGER (1..4094)
		MAX-ACCESS  read-write
		STATUS      current
		DESCRIPTION
			"VLAN ID. (1-4094)"
		::= { swhAccessControlListIPv6Entry 16 }

	swhAccessControlListIPv6EtherTypeFilter OBJECT-TYPE
		SYNTAX      INTEGER { any(0), specific(1) }
		MAX-ACCESS  read-write
		STATUS      current
		DESCRIPTION
			"Ether Type Filter."
		::= { swhAccessControlListIPv6Entry 18 }

	swhAccessControlListIPv6EthernetTypeValue OBJECT-TYPE
		SYNTAX      DisplayString
		MAX-ACCESS  read-write
		STATUS      current
		DESCRIPTION
			"Ethernet Type Value."
		::= { swhAccessControlListIPv6Entry 19 }

	swhAccessControlListIPv6IngressPortFilter OBJECT-TYPE
		SYNTAX      INTEGER { any(0), specific(1) }
		MAX-ACCESS  read-write
		STATUS      current
		DESCRIPTION
			"Ingress Port Filter."
		::= { swhAccessControlListIPv6Entry 63 }

	swhAccessControlListIPv6SourceMACMask OBJECT-TYPE
		SYNTAX      DisplayString
		MAX-ACCESS  read-write
		STATUS      current
		DESCRIPTION
			"Source MAC Mask."
		::= { swhAccessControlListIPv6Entry 64 }

	swhAccessControlListIPv6DestinationMACMask OBJECT-TYPE
		SYNTAX      DisplayString
		MAX-ACCESS  read-write
		STATUS      current
		DESCRIPTION
			"Destination MAC Mask."
		::= { swhAccessControlListIPv6Entry 65 }

	swhAccessControlListIPv6TOSTrafficClassFilter OBJECT-TYPE
		SYNTAX      INTEGER { any(0), specific(1) }
		MAX-ACCESS  read-write
		STATUS      current
		DESCRIPTION
			"TOS/Traffic Class Filter."
		::= { swhAccessControlListIPv6Entry 66 }

	swhAccessControlListIPv6TOSTrafficClass OBJECT-TYPE
		SYNTAX      DisplayString
		MAX-ACCESS  read-write
		STATUS      current
		DESCRIPTION
			"TOS/Traffic Class. (00-FF)"
		::= { swhAccessControlListIPv6Entry 67 }

	swhAccessControlListIPv6ProtocolNextHeaderFilter OBJECT-TYPE
		SYNTAX      INTEGER { any(0), specific(1) }
		MAX-ACCESS  read-write
		STATUS      current
		DESCRIPTION
			"Protocol/Next Header Filter."
		::= { swhAccessControlListIPv6Entry 68 }

	swhAccessControlListIPv6ProtocolNextHeader OBJECT-TYPE
		SYNTAX      DisplayString
		MAX-ACCESS  read-write
		STATUS      current
		DESCRIPTION
			"Protocol/Next Header. (00-FF)"
		::= { swhAccessControlListIPv6Entry 69 }

	swhAccessControlListIPv6IPv6SourceIPFilter OBJECT-TYPE
		SYNTAX      INTEGER { any(0), network(1) }
		MAX-ACCESS  read-write
		STATUS      current
		DESCRIPTION
			"IPv6 Source IP Filter."
		::= { swhAccessControlListIPv6Entry 76 }

	swhAccessControlListIPv6IPv6SourceIPAddress OBJECT-TYPE
		SYNTAX      DisplayString
		MAX-ACCESS  read-write
		STATUS      current
		DESCRIPTION
			"IPv6 Source IP Address."
		::= { swhAccessControlListIPv6Entry 77 }

	swhAccessControlListIPv6IPv6SourceIPPrefix OBJECT-TYPE
		SYNTAX      INTEGER (10..128)
		MAX-ACCESS  read-write
		STATUS      current
		DESCRIPTION
			"IPv6 Source IP Prefix."
		::= { swhAccessControlListIPv6Entry 78 }

	swhAccessControlListIPv6IPv6DestinationIPFilter OBJECT-TYPE
		SYNTAX      INTEGER { any(0), network(1) }
		MAX-ACCESS  read-write
		STATUS      current
		DESCRIPTION
			"IPv6 Destination IP Filter."
		::= { swhAccessControlListIPv6Entry 79 }

	swhAccessControlListIPv6IPv6DestinationIPAddress OBJECT-TYPE
		SYNTAX      DisplayString
		MAX-ACCESS  read-write
		STATUS      current
		DESCRIPTION
			"IPv6 Destination IP Address."
		::= { swhAccessControlListIPv6Entry 80 }

	swhAccessControlListIPv6IPv6DestinationIPPrefix OBJECT-TYPE
		SYNTAX      INTEGER (10..128)
		MAX-ACCESS  read-write
		STATUS      current
		DESCRIPTION
			"IPv6 Destination IP Prefix."
		::= { swhAccessControlListIPv6Entry 81 }

	swhAccessControlListIPv6TCPUDPSourcePortFilter OBJECT-TYPE
		SYNTAX      INTEGER { any(0), specific(1) }
		MAX-ACCESS  read-write
		STATUS      current
		DESCRIPTION
			"TCP/UDP Source Port Filter."
		::= { swhAccessControlListIPv6Entry 82 }

	swhAccessControlListIPv6TCPUDPSourcePort OBJECT-TYPE
		SYNTAX      INTEGER (1..65535)
		MAX-ACCESS  read-write
		STATUS      current
		DESCRIPTION
			"TCP/UDP Source Port. (1-65535)"
		::= { swhAccessControlListIPv6Entry 83 }

	swhAccessControlListIPv6TCPUDPSourcePortMask OBJECT-TYPE
		SYNTAX      DisplayString
		MAX-ACCESS  read-write
		STATUS      current
		DESCRIPTION
			"TCP/UDP Source Port Mask. (0000-FFFF)"
		::= { swhAccessControlListIPv6Entry 84 }

	swhAccessControlListIPv6TCPUDPDestinationPortFilter OBJECT-TYPE
		SYNTAX      INTEGER { any(0), specific(1) }
		MAX-ACCESS  read-write
		STATUS      current
		DESCRIPTION
			"TCP/UDP Destination Port Filter."
		::= { swhAccessControlListIPv6Entry 85 }

	swhAccessControlListIPv6TCPUDPDestinationPort OBJECT-TYPE
		SYNTAX      INTEGER (1..65535)
		MAX-ACCESS  read-write
		STATUS      current
		DESCRIPTION
			"TCP/UDP Destination Port. (1-65535)"
		::= { swhAccessControlListIPv6Entry 86 }

	swhAccessControlListIPv6TCPUDPDestinationPortMask OBJECT-TYPE
		SYNTAX      DisplayString
		MAX-ACCESS  read-write
		STATUS      current
		DESCRIPTION
			"TCP/UDP Destination Port Mask. (0000-FFFF)"
		::= { swhAccessControlListIPv6Entry 87 }

	swhAccessControlListIPv6Name OBJECT-TYPE
		SYNTAX      DisplayString
		MAX-ACCESS  read-write
		STATUS      current
		DESCRIPTION
			"Name."
		::= { swhAccessControlListIPv6Entry 88 }

	swhAccessControlListIPv6Sequence OBJECT-TYPE
		SYNTAX      INTEGER
		MAX-ACCESS  read-write
		STATUS      current
		DESCRIPTION
			"Sequence."
		::= { swhAccessControlListIPv6Entry 89 }

	swhAccessControlListIPv6Enable OBJECT-TYPE
		SYNTAX      INTEGER { disable(0), enable(1) }
		MAX-ACCESS  read-write
		STATUS      current
		DESCRIPTION
			"Enable."
		::= { swhAccessControlListIPv6Entry 90 }

	swhAccessControlListIPv6Apply OBJECT-TYPE
		SYNTAX      INTEGER { none(0), apply(1) }
		MAX-ACCESS  read-write
		STATUS      current
		DESCRIPTION
			"Apply Access Control List."
		::= { swhAccessControlListIPv6Entry 200 }


-- SwitchManagement(4).StaticMulticastConfiguration(70).MulticastTable(1)

	swhMulticastTable OBJECT-TYPE
		SYNTAX      SEQUENCE OF SwhMulticastEntry
		MAX-ACCESS  not-accessible
		STATUS      current
		DESCRIPTION
			"Table of multicast."
		::= { swhStaticMulticastConfiguration 1 }

	-- Table Entry
	swhMulticastEntry OBJECT-TYPE
		SYNTAX      SwhMulticastEntry
		MAX-ACCESS  not-accessible
		STATUS      current
		DESCRIPTION
			"An entry in the table, containing information about multicast."
		INDEX    { swhMulticastIndex }
		::= { swhMulticastTable 1 }

	SwhMulticastEntry ::=
		SEQUENCE {
			swhMulticastIndex
				INTEGER,
			swhMulticastValid
				INTEGER,
			swhMulticastIPAddress
				IpAddress,
			swhMulticastIPv6Address
				DisplayString,
			swhMulticastVLANID
				INTEGER,
			swhMulticastForwardingPort
				INTEGER,
			swhMulticastDelete
				INTEGER
		}

	swhMulticastIndex OBJECT-TYPE
		SYNTAX      INTEGER (0..2147483647)
		MAX-ACCESS  not-accessible
		STATUS      current
		DESCRIPTION
			"A unique value for each index."
		::= { swhMulticastEntry 1 }

	swhMulticastValid OBJECT-TYPE
		SYNTAX      INTEGER { invalid(0), valid(1) }
		MAX-ACCESS  read-only
		STATUS      current
		DESCRIPTION
			"This entry is valid or invalid."
		::= { swhMulticastEntry 2 }

	swhMulticastIPAddress OBJECT-TYPE
		SYNTAX      IpAddress
		MAX-ACCESS  read-write
		STATUS      current
		DESCRIPTION
			"IP Address. (224.0.1.0 ~ 239.255.255.255)"
		::= { swhMulticastEntry 3 }

	swhMulticastVLANID OBJECT-TYPE
		SYNTAX      INTEGER (1..4094)
		MAX-ACCESS  read-write
		STATUS      current
		DESCRIPTION
			"VLAN ID. (1-4094)"
		::= { swhMulticastEntry 6 }

	swhMulticastForwardingPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Forwarding Port."
		::= { swhMulticastEntry 7 }

	swhMulticastDelete OBJECT-TYPE
		SYNTAX      INTEGER { normal(0), delete(1) }
		MAX-ACCESS  read-write
		STATUS      current
		DESCRIPTION
			"Delete this entry."
		::= { swhMulticastEntry 10 }

	swhMulticastIPv6Address OBJECT-TYPE
		SYNTAX      DisplayString
		MAX-ACCESS  read-write
		STATUS      current
		DESCRIPTION
			"IPv6 Address. (FF00::/8)"
		::= { swhMulticastEntry 11 }


-- SwitchManagement(4).SecurityConfiguration(80)

	swhDHCPSnooping
		OBJECT IDENTIFIER ::= { swhSecurityConfiguration 3 }

	swhDHCPOpt82Settings
		OBJECT IDENTIFIER ::= { swhSecurityConfiguration 1 }

	swhDHCPOpt82Configuration
		OBJECT IDENTIFIER ::= { swhSecurityConfiguration 7 }

	swhIPSourceGuardSettings
		OBJECT IDENTIFIER ::= { swhSecurityConfiguration 2 }

	swhPortIsolationConfiguration
		OBJECT IDENTIFIER ::= { swhSecurityConfiguration 13 }

	swhStaticIPTableConfiguration
		OBJECT IDENTIFIER ::= { swhSecurityConfiguration 4 }

	swhStormControl
		OBJECT IDENTIFIER ::= { swhSecurityConfiguration 12 }

	swhMacLimiters
		OBJECT IDENTIFIER ::= { swhSecurityConfiguration 11 }

	swhPortLinkupDelay
		OBJECT IDENTIFIER ::= { swhSecurityConfiguration 15 }

	swhPortLinkFlap
		OBJECT IDENTIFIER ::= { swhSecurityConfiguration 16 }


-- SwitchManagement(4).SecurityConfiguration(80).DHCPOpt82Settings(1)

	swhSecurityConfigDHCPOpt82RelayAgent OBJECT-TYPE
		SYNTAX      INTEGER { disable(0), enable(1) }
		MAX-ACCESS  read-write
		STATUS      current
		DESCRIPTION
			"Enable DHCP Opt82 Relay Agent, the Opt82 Port has to be used."
		::= { swhDHCPOpt82Settings 1 }

	swhSecurityConfigRemoteID OBJECT-TYPE
		SYNTAX      DisplayString
		MAX-ACCESS  read-only
		STATUS      current
		DESCRIPTION
			"Monitor Remote ID."
		::= { swhDHCPOpt82Settings 2 }

	swhSecurityConfigDHCPOpt82PortTable OBJECT-TYPE
		SYNTAX      SEQUENCE OF SwhSecurityConfigDHCPOpt82PortEntry
		MAX-ACCESS  not-accessible
		STATUS      current
		DESCRIPTION
			"Table of DHCP opt82 port."
		::= { swhDHCPOpt82Settings 3 }

	-- Table Entry
	swhSecurityConfigDHCPOpt82PortEntry OBJECT-TYPE
		SYNTAX      SwhSecurityConfigDHCPOpt82PortEntry
		MAX-ACCESS  not-accessible
		STATUS      current
		DESCRIPTION
			"An entry in the table, containing information about DHCP opt82 port."
		INDEX    { swhDHCPOpt82PortIndex }
		::= { swhSecurityConfigDHCPOpt82PortTable 1 }

	SwhSecurityConfigDHCPOpt82PortEntry ::=
		SEQUENCE {
			swhDHCPOpt82PortIndex
				INTEGER,
			swhDHCPOpt82PortOpt82Port
				INTEGER,
			swhDHCPOpt82PortTrustPort
				INTEGER
		}

	swhDHCPOpt82PortIndex OBJECT-TYPE
		SYNTAX      INTEGER (0..2147483647)
		MAX-ACCESS  not-accessible
		STATUS      current
		DESCRIPTION
			"A unique value for each index."
		::= { swhSecurityConfigDHCPOpt82PortEntry 1 }

	swhDHCPOpt82PortOpt82Port OBJECT-TYPE
		SYNTAX      INTEGER { b(0), v(1) }
		MAX-ACCESS  read-write
		STATUS      current
		DESCRIPTION
			"b : Blocked  v : Member"
		::= { swhSecurityConfigDHCPOpt82PortEntry 2 }

	swhDHCPOpt82PortTrustPort OBJECT-TYPE
		SYNTAX      INTEGER { b(0), v(1) }
		MAX-ACCESS  read-write
		STATUS      current
		DESCRIPTION
			"b : Blocked  v : Member"
		::= { swhSecurityConfigDHCPOpt82PortEntry 3 }


-- SwitchManagement(4).SecurityConfiguration(80).IPSourceGuardSettings(2)

	swhIPSourceGuardSettingsPort1 OBJECT-TYPE
		SYNTAX      INTEGER { fix-ip(0), dhcp(1), unlimited(2) }
		MAX-ACCESS  read-write
		STATUS      current
		DESCRIPTION
			"Port 1 State."
		::= { swhIPSourceGuardSettings 1 }

	swhIPSourceGuardSettingsPort2 OBJECT-TYPE
		SYNTAX      INTEGER { fix-ip(0), dhcp(1), unlimited(2) }
		MAX-ACCESS  read-write
		STATUS      current
		DESCRIPTION
			"Port 2 State."
		::= { swhIPSourceGuardSettings 2 }

	swhIPSourceGuardSettingsPort3 OBJECT-TYPE
		SYNTAX      INTEGER { fix-ip(0), dhcp(1), unlimited(2) }
		MAX-ACCESS  read-write
		STATUS      current
		DESCRIPTION
			"Port 3 State."
		::= { swhIPSourceGuardSettings 3 }

	swhIPSourceGuardSettingsPort4 OBJECT-TYPE
		SYNTAX      INTEGER { fix-ip(0), dhcp(1), unlimited(2) }
		MAX-ACCESS  read-write
		STATUS      current
		DESCRIPTION
			"Port 4 State."
		::= { swhIPSourceGuardSettings 4 }

	swhIPSourceGuardSettingsPort5 OBJECT-TYPE
		SYNTAX      INTEGER { fix-ip(0), dhcp(1), unlimited(2) }
		MAX-ACCESS  read-write
		STATUS      current
		DESCRIPTION
			"Port 5 State."
		::= { swhIPSourceGuardSettings 5 }

	swhIPSourceGuardSettingsPort6 OBJECT-TYPE
		SYNTAX      INTEGER { fix-ip(0), dhcp(1), unlimited(2) }
		MAX-ACCESS  read-write
		STATUS      current
		DESCRIPTION
			"Port 6 State."
		::= { swhIPSourceGuardSettings 6 }

	swhIPSourceGuardSettingsPort7 OBJECT-TYPE
		SYNTAX      INTEGER { fix-ip(0), dhcp(1), unlimited(2) }
		MAX-ACCESS  read-write
		STATUS      current
		DESCRIPTION
			"Port 7 State."
		::= { swhIPSourceGuardSettings 7 }

	swhIPSourceGuardSettingsPort8 OBJECT-TYPE
		SYNTAX      INTEGER { fix-ip(0), dhcp(1), unlimited(2) }
		MAX-ACCESS  read-write
		STATUS      current
		DESCRIPTION
			"Port 8 State."
		::= { swhIPSourceGuardSettings 8 }

	swhIPSourceGuardSettingsPort9 OBJECT-TYPE
		SYNTAX      INTEGER { fix-ip(0), dhcp(1), unlimited(2) }
		MAX-ACCESS  read-write
		STATUS      current
		DESCRIPTION
			"Port 9 State."
		::= { swhIPSourceGuardSettings 9 }

	swhIPSourceGuardSettingsPort10 OBJECT-TYPE
		SYNTAX      INTEGER { fix-ip(0), dhcp(1), unlimited(2) }
		MAX-ACCESS  read-write
		STATUS      current
		DESCRIPTION
			"Port 10 State."
		::= { swhIPSourceGuardSettings 10 }

	swhIPSourceGuardSettingsPort11 OBJECT-TYPE
		SYNTAX      INTEGER { fix-ip(0), dhcp(1), unlimited(2) }
		MAX-ACCESS  read-write
		STATUS      current
		DESCRIPTION
			"Port 11 State."
		::= { swhIPSourceGuardSettings 11 }

	swhIPSourceGuardSettingsPort12 OBJECT-TYPE
		SYNTAX      INTEGER { fix-ip(0), dhcp(1), unlimited(2) }
		MAX-ACCESS  read-write
		STATUS      current
		DESCRIPTION
			"Port 12 State."
		::= { swhIPSourceGuardSettings 12 }


-- SwitchManagement(4).SecurityConfiguration(80).FilterConfiguration(3)

	swhSecurityFilterConfigDHCPSnooping OBJECT-TYPE
		SYNTAX      INTEGER { disable(0), enable(1) }
		MAX-ACCESS  read-write
		STATUS      current
		DESCRIPTION
			"DHCP Snooping. When DHCP Snooping is enable, ARP/IPv4 filter will also be enable simultaneously."
		::= { swhDHCPSnooping 1 }

	swhSecurityFilterConfigDefaultDHCPInitiatedTime OBJECT-TYPE
		SYNTAX      INTEGER (0..9999)
		MAX-ACCESS  read-write
		STATUS      current
		DESCRIPTION
			"Default DHCP Initiated Time. (0-9999)"
		::= { swhDHCPSnooping 2 }

	swhSecurityFilterConfigDefaultDHCPLeasedTime OBJECT-TYPE
		SYNTAX      INTEGER (180..259200)
		MAX-ACCESS  read-write
		STATUS      current
		DESCRIPTION
			"Default DHCP Leased Time. (180-259200)"
		::= { swhDHCPSnooping 3 }

	swhSecurityFilterConfigDefaultDHCPEntryClearWhenPortLinkDown OBJECT-TYPE
		SYNTAX      INTEGER { disable(0), enable(1) }
		MAX-ACCESS  read-write
		STATUS      current
		DESCRIPTION
			"DHCP Entry Clear When Port Link Down."
		::= { swhDHCPSnooping 11 }


-- SwitchManagement(4).SecurityConfiguration(80).FilterConfiguration(3).SecurityDHCPServerTrustPort(7)

	swhSecurityDHCPServerTrustPort
		OBJECT IDENTIFIER ::= { swhDHCPSnooping 7 }


-- SwitchManagement(4).SecurityConfiguration(80).FilterConfiguration(3).SecurityDHCPServerTrustPort(7).SecurityDHCPServerTable(1)

	swhSecurityDHCPServerTable OBJECT-TYPE
		SYNTAX      SEQUENCE OF SwhSecurityDHCPServerEntry
		MAX-ACCESS  not-accessible
		STATUS      current
		DESCRIPTION
			"Table of DHCP server trust port."
		::= { swhSecurityDHCPServerTrustPort 1 }

	-- Table Entry
	swhSecurityDHCPServerEntry OBJECT-TYPE
		SYNTAX      SwhSecurityDHCPServerEntry
		MAX-ACCESS  not-accessible
		STATUS      current
		DESCRIPTION
			"An entry in the table, containing information about DHCP server trust port."
		INDEX    { swhSecurityDHCPServerIndex }
		::= { swhSecurityDHCPServerTable 1 }

	SwhSecurityDHCPServerEntry ::=
		SEQUENCE {
			swhSecurityDHCPServerIndex
				INTEGER,
			swhSecurityDHCPServerState
				INTEGER
		}

	swhSecurityDHCPServerIndex OBJECT-TYPE
		SYNTAX      INTEGER (0..2147483647)
		MAX-ACCESS  not-accessible
		STATUS      current
		DESCRIPTION
			"A unique value for each index."
		::= { swhSecurityDHCPServerEntry 1 }

	swhSecurityDHCPServerState OBJECT-TYPE
		SYNTAX      INTEGER { disable(0), enable(1) }
		MAX-ACCESS  read-write
		STATUS      current
		DESCRIPTION
			"State."
		::= { swhSecurityDHCPServerEntry 2 }


-- SwitchManagement(4).SecurityConfiguration(80).FilterConfiguration(3).SecurityDHCPServerTrustIP(8)

	swhSecurityDHCPServerTrustIP
		OBJECT IDENTIFIER ::= { swhDHCPSnooping 8 }


-- SwitchManagement(4).SecurityConfiguration(80).FilterConfiguration(3).SecurityDHCPServerTrustIP(8).SecurityDHCPServerIP(1)

	swhSecurityDHCPServerIP OBJECT-TYPE
		SYNTAX      INTEGER { disable(0), enable(1) }
		MAX-ACCESS  read-write
		STATUS      current
		DESCRIPTION
			"Security IP."
		::= { swhSecurityDHCPServerTrustIP 1 }


-- SwitchManagement(4).SecurityConfiguration(80).FilterConfiguration(3).SecurityDHCPServerTrustIP(8).SecurityDHCPServerIPTable(2)

	swhSecurityDHCPServerIPTable OBJECT-TYPE
		SYNTAX      SEQUENCE OF SwhSecurityDHCPServerIPEntry
		MAX-ACCESS  not-accessible
		STATUS      current
		DESCRIPTION
			"Table of security IP information."
		::= { swhSecurityDHCPServerTrustIP 2 }

	-- Table Entry
	swhSecurityDHCPServerIPEntry OBJECT-TYPE
		SYNTAX      SwhSecurityDHCPServerIPEntry
		MAX-ACCESS  not-accessible
		STATUS      current
		DESCRIPTION
			"An entry in the table, containing information about security IP."
		INDEX    { swhSecurityDHCPServerIPIndex }
		::= { swhSecurityDHCPServerIPTable 1 }

	SwhSecurityDHCPServerIPEntry ::=
		SEQUENCE {
			swhSecurityDHCPServerIPIndex
				INTEGER,
			swhSecurityDHCPServerIPIPAddress
				DisplayString,
			swhSecurityDHCPServerIPIPv6Address
				DisplayString,
			swhSecurityDHCPServerIPDelete
				INTEGER
		}

	swhSecurityDHCPServerIPIndex OBJECT-TYPE
		SYNTAX      INTEGER (0..2147483647)
		MAX-ACCESS  not-accessible
		STATUS      current
		DESCRIPTION
			"A unique value for each index."
		::= { swhSecurityDHCPServerIPEntry 1 }

	swhSecurityDHCPServerIPIPAddress OBJECT-TYPE
		SYNTAX      DisplayString
		MAX-ACCESS  read-write
		STATUS      current
		DESCRIPTION
			"Security IPv4 Address."
		::= { swhSecurityDHCPServerIPEntry 4 }

	swhSecurityDHCPServerIPIPv6Address OBJECT-TYPE
		SYNTAX      DisplayString
		MAX-ACCESS  read-write
		STATUS      current
		DESCRIPTION
			"Security IPv6 Address."
		::= { swhSecurityDHCPServerIPEntry 5 }

	swhSecurityDHCPServerIPDelete OBJECT-TYPE
		SYNTAX      INTEGER { normal(0), delete(1) }
		MAX-ACCESS  read-write
		STATUS      current
		DESCRIPTION
			"Delete this entry."
		::= { swhSecurityDHCPServerIPEntry 10 }


-- SwitchManagement(4).SecurityConfiguration(80).StaticIPTableConfiguration(4).StaticIPTable(1)

	swhStaticIPTable OBJECT-TYPE
		SYNTAX      SEQUENCE OF SwhStaticIPEntry
		MAX-ACCESS  not-accessible
		STATUS      current
		DESCRIPTION
			"Table of state IP."
		::= { swhStaticIPTableConfiguration 1 }

	-- Table Entry
	swhStaticIPEntry OBJECT-TYPE
		SYNTAX      SwhStaticIPEntry
		MAX-ACCESS  not-accessible
		STATUS      current
		DESCRIPTION
			"An entry in the table, containing information about state IP."
		INDEX    { swhStaticIPIndex }
		::= { swhStaticIPTable 1 }

	SwhStaticIPEntry ::=
		SEQUENCE {
			swhStaticIPIndex
				INTEGER,
			swhStaticIPValid
				INTEGER,
			swhStaticIPIPAddress
				IpAddress,
			swhStaticIPIPv6Address
				DisplayString,
			swhStaticIPVLANID
				INTEGER,
			swhStaticIPPort
				INTEGER,
			swhStaticIPDelete
				INTEGER
		}

	swhStaticIPIndex OBJECT-TYPE
		SYNTAX      INTEGER (0..2147483647)
		MAX-ACCESS  not-accessible
		STATUS      current
		DESCRIPTION
			"A unique value for each index."
		::= { swhStaticIPEntry 1 }

	swhStaticIPValid OBJECT-TYPE
		SYNTAX      INTEGER { invalid(0), valid(1) }
		MAX-ACCESS  read-only
		STATUS      current
		DESCRIPTION
			"This entry is valid or invalid."
		::= { swhStaticIPEntry 2 }

	swhStaticIPIPAddress OBJECT-TYPE
		SYNTAX      IpAddress
		MAX-ACCESS  read-write
		STATUS      current
		DESCRIPTION
			"IPv4 Address."
		::= { swhStaticIPEntry 3 }

	swhStaticIPVLANID OBJECT-TYPE
		SYNTAX      INTEGER (1..4094)
		MAX-ACCESS  read-write
		STATUS      current
		DESCRIPTION
			"VLAN ID. (1-4094)"
		::= { swhStaticIPEntry 5 }

	swhStaticIPPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Port Number."
		::= { swhStaticIPEntry 6 }

	swhStaticIPDelete OBJECT-TYPE
		SYNTAX      INTEGER { normal(0), delete(1) }
		MAX-ACCESS  read-write
		STATUS      current
		DESCRIPTION
			"Delete this entry."
		::= { swhStaticIPEntry 7 }

	swhStaticIPIPv6Address OBJECT-TYPE
		SYNTAX      DisplayString
		MAX-ACCESS  read-write
		STATUS      current
		DESCRIPTION
			"IPv6 Address."
		::= { swhStaticIPEntry 8 }


-- SwitchManagement(4).SecurityConfiguration(80).DHCPOpt82Configuration(7)

	swhDHCPOpt82CircuitIDPortList OBJECT-TYPE
		SYNTAX      DisplayString
		MAX-ACCESS  read-write
		STATUS      current
		DESCRIPTION
			"DHCP Opt82 Circuit-ID Port List."
		::= { swhDHCPOpt82Configuration 2 }

	swhDHCPOpt82CircuitIDFormattedPortList OBJECT-TYPE
		SYNTAX      DisplayString
		MAX-ACCESS  read-write
		STATUS      current
		DESCRIPTION
			"DHCP Opt82 Circuit-ID Formatted Port List."
		::= { swhDHCPOpt82Configuration 6 }

	swhDHCPOpt82RemoteIDEnable OBJECT-TYPE
		SYNTAX      INTEGER { disable(0), enable(1) }
		MAX-ACCESS  read-write
		STATUS      current
		DESCRIPTION
			"DHCP Opt82 Remote-ID Enable."
		::= { swhDHCPOpt82Configuration 4 }

	swhDHCPOpt82RemoteIDFormattedEnable OBJECT-TYPE
		SYNTAX      INTEGER { disable(0), enable(1) }
		MAX-ACCESS  read-write
		STATUS      current
		DESCRIPTION
			"DHCP Opt82 Remote-ID Formatted."
		::= { swhDHCPOpt82Configuration 7 }

	swhDHCPOpt82RemoteID OBJECT-TYPE
		SYNTAX      DisplayString
		MAX-ACCESS  read-write
		STATUS      current
		DESCRIPTION
			"DHCP Opt82 Remote-ID."
		::= { swhDHCPOpt82Configuration 5 }


-- SwitchManagement(4).SecurityConfiguration(80).DHCPOpt82Configuration(7).DHCPOpt82CircuitIDTable(3)

	swhDHCPOpt82CircuitIDTable OBJECT-TYPE
		SYNTAX      SEQUENCE OF SwhDHCPOpt82CircuitIDEntry
		MAX-ACCESS  not-accessible
		STATUS      current
		DESCRIPTION
			"Table of DHCP Opt82 Circuit-ID."
		::= { swhDHCPOpt82Configuration 3 }

	-- Table Entry
	swhDHCPOpt82CircuitIDEntry OBJECT-TYPE
		SYNTAX      SwhDHCPOpt82CircuitIDEntry
		MAX-ACCESS  not-accessible
		STATUS      current
		DESCRIPTION
			"An entry in the table, containing information about DHCP Opt82 Circuit-ID."
		INDEX    { swhDHCPOpt82CircuitIDIndex }
		::= { swhDHCPOpt82CircuitIDTable 1 }

	SwhDHCPOpt82CircuitIDEntry ::=
		SEQUENCE {
			swhDHCPOpt82CircuitIDIndex
				INTEGER,
			swhDHCPOpt82CircuitIDCircuitID
				DisplayString,
			swhDHCPOpt82CircuitIDDelete
				INTEGER
		}

	swhDHCPOpt82CircuitIDIndex OBJECT-TYPE
		SYNTAX      INTEGER (0..2147483647)
		MAX-ACCESS  not-accessible
		STATUS      current
		DESCRIPTION
			"A unique value for each index."
		::= { swhDHCPOpt82CircuitIDEntry 1 }

	swhDHCPOpt82CircuitIDCircuitID OBJECT-TYPE
		SYNTAX      DisplayString
		MAX-ACCESS  read-write
		STATUS      current
		DESCRIPTION
			"Circuit-ID."
		::= { swhDHCPOpt82CircuitIDEntry 3 }

	swhDHCPOpt82CircuitIDDelete OBJECT-TYPE
		SYNTAX      INTEGER { normal(0), delete(1) }
		MAX-ACCESS  read-write
		STATUS      current
		DESCRIPTION
			"Delete this entry."
		::= { swhDHCPOpt82CircuitIDEntry 5 }


-- SwitchManagement(4).SecurityConfiguration(80).MacLimiters(11)

	swhMacLimitersEnable OBJECT-TYPE
		SYNTAX      INTEGER { disable(0), enable(1) }
		MAX-ACCESS  read-write
		STATUS      current
		DESCRIPTION
			"Enable."
		::= { swhMacLimiters 1 }

	swhMacLimitersThresholdInterval OBJECT-TYPE
		SYNTAX      INTEGER (120..86400)
		MAX-ACCESS  read-write
		STATUS      current
		DESCRIPTION
			"Threshold Interval."
		::= { swhMacLimiters 3 }


-- SwitchManagement(4).SecurityConfiguration(80).MacLimiters(11).MACLimitersPortTable(5)

	swhMacLimitersPortTable OBJECT-TYPE
		SYNTAX      SEQUENCE OF SwhMacLimitersPortEntry
		MAX-ACCESS  not-accessible
		STATUS      current
		DESCRIPTION
			"Table of port mac limiters."
		::= { swhMacLimiters 5 }

	-- Table Entry
	swhMacLimitersPortEntry OBJECT-TYPE
		SYNTAX      SwhMacLimitersPortEntry
		MAX-ACCESS  not-accessible
		STATUS      current
		DESCRIPTION
			"An entry in the table, containing information about port mac limiters."
		INDEX    { swhMacLimitersPortIndex }
		::= { swhMacLimitersPortTable 1 }

	SwhMacLimitersPortEntry ::=
		SEQUENCE {
			swhMacLimitersPortIndex
				INTEGER,
			swhMacLimitersPortEnable
				INTEGER,
			swhMacLimitersPortLimit
				INTEGER,
			swhMacLimitersPortSticky
				INTEGER,
			swhMacLimitersPortAction
				INTEGER,
			swhMacLimitersPortUnlock
				INTEGER
		}

	swhMacLimitersPortIndex OBJECT-TYPE
		SYNTAX      INTEGER (0..2147483647)
		MAX-ACCESS  not-accessible
		STATUS      current
		DESCRIPTION
			"A unique value for each index."
		::= { swhMacLimitersPortEntry 1 }

	swhMacLimitersPortEnable OBJECT-TYPE
		SYNTAX      INTEGER { disable(0), enable(1) }
		MAX-ACCESS  read-write
		STATUS      current
		DESCRIPTION
			"Port Enable."
		::= { swhMacLimitersPortEntry 2 }

	swhMacLimitersPortLimit OBJECT-TYPE
		SYNTAX      INTEGER (1..50)
		MAX-ACCESS  read-write
		STATUS      current
		DESCRIPTION
			"Port Limit. (1-50)"
		::= { swhMacLimitersPortEntry 3 }

	swhMacLimitersPortSticky OBJECT-TYPE
		SYNTAX      INTEGER { disable(0), enable(1) }
		MAX-ACCESS  read-write
		STATUS      current
		DESCRIPTION
			"Port Sticky."
		::= { swhMacLimitersPortEntry 4 }

	swhMacLimitersPortAction OBJECT-TYPE
		SYNTAX      INTEGER { drop(1), shutdown(4) }
		MAX-ACCESS  read-write
		STATUS      current
		DESCRIPTION
			"Port Limit Action."
		::= { swhMacLimitersPortEntry 5 }

	swhMacLimitersPortUnlock OBJECT-TYPE
		SYNTAX      INTEGER { unlock(1) }
		MAX-ACCESS  read-write
		STATUS      current
		DESCRIPTION
			"Unlock."
		::= { swhMacLimitersPortEntry 6 }


-- SwitchManagement(4).SecurityConfiguration(80).StormControl(12)

	swhStormControlEnable OBJECT-TYPE
		SYNTAX      INTEGER { disable(0), enable(1) }
		MAX-ACCESS  read-write
		STATUS      current
		DESCRIPTION
			"Enable."
		::= { swhStormControl 16 }

	swhThresholdInterval OBJECT-TYPE
		SYNTAX      INTEGER (120..86400)
		MAX-ACCESS  read-write
		STATUS      current
		DESCRIPTION
			"Threshold Interval. (120-86400 Secs)"
		::= { swhStormControl 3 }


-- SwitchManagement(4).SecurityConfiguration(80).StormControl(12).StormControlTable(9)

	swhStormControlTable OBJECT-TYPE
		SYNTAX      SEQUENCE OF SwhStormControlEntry
		MAX-ACCESS  not-accessible
		STATUS      current
		DESCRIPTION
			"Table of storm control."
		::= { swhStormControl 9 }

	-- Table Entry
	swhStormControlEntry OBJECT-TYPE
		SYNTAX      SwhStormControlEntry
		MAX-ACCESS  not-accessible
		STATUS      current
		DESCRIPTION
			"An entry in the table, containing information about storm control."
		INDEX    { swhStormControlIndex }
		::= { swhStormControlTable 1 }

	SwhStormControlEntry ::=
		SEQUENCE {
			swhStormControlIndex
				INTEGER,
			swhStormControlPortConfigPort
				DisplayString,
			swhStormControlUnknownUnicastRate
				INTEGER,
			swhStormControlUnknownMulticastRate
				INTEGER,
			swhStormControlBroadcastRate
				INTEGER,
			swhStormControlAction
				INTEGER,
			swhStormControlStatus
				DisplayString,
			swhStormControlReasonOfBeingLocked
				DisplayString,
			swhStormControlUnlock
				INTEGER
		}

	swhStormControlIndex OBJECT-TYPE
		SYNTAX      INTEGER (0..2147483647)
		MAX-ACCESS  not-accessible
		STATUS      current
		DESCRIPTION
			"A unique value for each index."
		::= { swhStormControlEntry 1 }

	swhStormControlBroadcastRate OBJECT-TYPE
		SYNTAX      INTEGER { none(-1),
		                      off(0),
		                      rate-1(1),
		                      rate-2(2),
		                      rate-4(3),
		                      rate-8(4),
		                      rate-16(5),
		                      rate-32(6),
		                      rate-64(7),
		                      rate-128(8),
		                      rate-256(9),
		                      rate-512(10),
		                      rate-1K(11),
		                      rate-2K(12),
		                      rate-4K(13),
		                      rate-8K(14),
		                      rate-16K(15),
		                      rate-32K(16),
		                      rate-64K(17),
		                      rate-128K(18),
		                      rate-256K(19)
		                    }
		MAX-ACCESS  read-write
		STATUS      current
		DESCRIPTION
			"Broadcast Rate. (packets/second)"
		::= { swhStormControlEntry 8 }

	swhStormControlUnknownMulticastRate OBJECT-TYPE
		SYNTAX      INTEGER { none(-1),
		                      off(0),
		                      rate-1(1),
		                      rate-2(2),
		                      rate-4(3),
		                      rate-8(4),
		                      rate-16(5),
		                      rate-32(6),
		                      rate-64(7),
		                      rate-128(8),
		                      rate-256(9),
		                      rate-512(10),
		                      rate-1K(11),
		                      rate-2K(12),
		                      rate-4K(13),
		                      rate-8K(14),
		                      rate-16K(15),
		                      rate-32K(16),
		                      rate-64K(17),
		                      rate-128K(18),
		                      rate-256K(19)
		                    }
		MAX-ACCESS  read-write
		STATUS      current
		DESCRIPTION
			"Unknown Multicast Rate. (packets/second)"
		::= { swhStormControlEntry 10 }

	swhStormControlUnknownUnicastRate OBJECT-TYPE
		SYNTAX      INTEGER { none(-1),
		                      off(0),
		                      rate-1(1),
		                      rate-2(2),
		                      rate-4(3),
		                      rate-8(4),
		                      rate-16(5),
		                      rate-32(6),
		                      rate-64(7),
		                      rate-128(8),
		                      rate-256(9),
		                      rate-512(10),
		                      rate-1K(11),
		                      rate-2K(12),
		                      rate-4K(13),
		                      rate-8K(14),
		                      rate-16K(15),
		                      rate-32K(16),
		                      rate-64K(17),
		                      rate-128K(18),
		                      rate-256K(19)
		                    }
		MAX-ACCESS  read-write
		STATUS      current
		DESCRIPTION
			"Unknown Unicast Rate. (packets/second)"
		::= { swhStormControlEntry 11 }

	swhStormControlPortConfigPort OBJECT-TYPE
		SYNTAX      DisplayString
		MAX-ACCESS  read-only
		STATUS      current
		DESCRIPTION
			"Security Storm Control Port Number."
		::= { swhStormControlEntry 12 }

	swhStormControlAction OBJECT-TYPE
		SYNTAX      INTEGER { none(-1), drop(0), shutdown(1) }
		MAX-ACCESS  read-write
		STATUS      current
		DESCRIPTION
			"Action."
		::= { swhStormControlEntry 20 }

	swhStormControlStatus OBJECT-TYPE
		SYNTAX      DisplayString
		MAX-ACCESS  read-only
		STATUS      current
		DESCRIPTION
			"Status."
		::= { swhStormControlEntry 21 }

	swhStormControlReasonOfBeingLocked OBJECT-TYPE
		SYNTAX      DisplayString
		MAX-ACCESS  read-only
		STATUS      current
		DESCRIPTION
			"Reason of being locked."
		::= { swhStormControlEntry 22 }

	swhStormControlUnlock OBJECT-TYPE
		SYNTAX      INTEGER { none(0), unlock(1) }
		MAX-ACCESS  read-write
		STATUS      current
		DESCRIPTION
			"Unlock."
		::= { swhStormControlEntry 23 }


-- SwitchManagement(4).SecurityConfiguration(80).PortIsolationConfiguration(13)

	swhPortIsolationConfigPortIsolation OBJECT-TYPE
		SYNTAX      INTEGER { disable(0), enable(1) }
		MAX-ACCESS  read-write
		STATUS      current
		DESCRIPTION
			"Port Isolation. When you enable Port Isolation, Port Based VLAN is automatically invalid."
		::= { swhPortIsolationConfiguration 1 }

	swhPortIsolationConfigUplinkPortList OBJECT-TYPE
		SYNTAX      DisplayString
		MAX-ACCESS  read-write
		STATUS      current
		DESCRIPTION
			"Uplink Port List."
		::= { swhPortIsolationConfiguration 2 }


-- SwitchManagement(4).SecurityConfiguration(80).PortLinkupDelay(15)

	swhLinkupDelayTime OBJECT-TYPE
		SYNTAX      INTEGER (0..1200)
		MAX-ACCESS  read-write
		STATUS      current
		DESCRIPTION
			"Delay Time. (0-1200 Secs)"
		::= { swhPortLinkupDelay 1 }

	swhLinkupDelayPortList OBJECT-TYPE
		SYNTAX      DisplayString
		MAX-ACCESS  read-write
		STATUS      current
		DESCRIPTION
			"Delay Port List. (e.g: 1,2,4-7)"
		::= { swhPortLinkupDelay 2 }

	swhLinkupReleaseDelayRule OBJECT-TYPE
		SYNTAX      INTEGER { followdelaytime(0), mac-limit(1) }
		MAX-ACCESS  read-write
		STATUS      current
		DESCRIPTION
			"Release Delay Rule."
		::= { swhPortLinkupDelay 3 }

	swhLinkupReleaseDelayTriggerPortList OBJECT-TYPE
		SYNTAX      DisplayString
		MAX-ACCESS  read-write
		STATUS      current
		DESCRIPTION
			"Release Delay Trigger Port List. (e.g: 1,2,4-7)"
		::= { swhPortLinkupDelay 4 }


-- SwitchManagement(4).SecurityConfiguration(80).PortLinkFlap(16)

	swhPortLinkFlapThreshold OBJECT-TYPE
		SYNTAX      INTEGER (1..20)
		MAX-ACCESS  read-write
		STATUS      current
		DESCRIPTION
			"Threshold. (1-20 Times)"
		::= { swhPortLinkFlap 1 }


-- SwitchManagement(4).FastRedundancy(91)

	swhFastRedundancyConfigTable OBJECT-TYPE
		SYNTAX      SEQUENCE OF SwhFastRedundancyConfigEntry
		MAX-ACCESS  not-accessible
		STATUS      current
		DESCRIPTION
			"Table of fast redundancy configuration."
		::= { swhFastRedundancy 1 }

	-- Table Entry
	swhFastRedundancyConfigEntry OBJECT-TYPE
		SYNTAX      SwhFastRedundancyConfigEntry
		MAX-ACCESS  not-accessible
		STATUS      current
		DESCRIPTION
			"An entry in the table, containing information about fast redundancy config."
		INDEX    { swhFastRedundancyConfigIndex }
		::= { swhFastRedundancyConfigTable 1 }

	SwhFastRedundancyConfigEntry ::=
		SEQUENCE {
			swhFastRedundancyConfigIndex
				INTEGER,
			swhFastRedundancyConfigValid
				INTEGER,
			swhFastRedundancyConfigGroupID
				INTEGER,
			swhFastRedundancyConfigEnable
				INTEGER,
			swhFastRedundancyConfigDescription
				DisplayString,
			swhFastRedundancyConfigProtocol
				INTEGER,
			swhFastRedundancyConfigRole
				INTEGER,
			swhFastRedundancyConfigPort1
				INTEGER,
			swhFastRedundancyConfigPort1Role
				INTEGER,
			swhFastRedundancyConfigPort2
				INTEGER,
			swhFastRedundancyConfigPort2Role
				INTEGER,
			swhFastRedundancyConfigDelete
				INTEGER
		}

	swhFastRedundancyConfigIndex OBJECT-TYPE
		SYNTAX      INTEGER (0..2147483647)
		MAX-ACCESS  not-accessible
		STATUS      current
		DESCRIPTION
			"A unique value for each index."
		::= { swhFastRedundancyConfigEntry 1 }

	swhFastRedundancyConfigValid OBJECT-TYPE
		SYNTAX      INTEGER { invalid(0), valid(1) }
		MAX-ACCESS  read-only
		STATUS      current
		DESCRIPTION
			"This entry is valid or invalid."
		::= { swhFastRedundancyConfigEntry 2 }

	swhFastRedundancyConfigGroupID OBJECT-TYPE
		SYNTAX      INTEGER { id-1(1), id-2(2) }
		MAX-ACCESS  read-write
		STATUS      current
		DESCRIPTION
			"Group ID."
		::= { swhFastRedundancyConfigEntry 3 }

	swhFastRedundancyConfigDescription OBJECT-TYPE
		SYNTAX      DisplayString
		MAX-ACCESS  read-write
		STATUS      current
		DESCRIPTION
			"Description."
		::= { swhFastRedundancyConfigEntry 4 }

	swhFastRedundancyConfigProtocol OBJECT-TYPE
		SYNTAX      INTEGER { fast-ringv2(0), chain(1) }
		MAX-ACCESS  read-write
		STATUS      current
		DESCRIPTION
			"Protocol."
		::= { swhFastRedundancyConfigEntry 5 }

	swhFastRedundancyConfigEnable OBJECT-TYPE
		SYNTAX      INTEGER { disable(0), enable(1) }
		MAX-ACCESS  read-write
		STATUS      current
		DESCRIPTION
			"Enable."
		::= { swhFastRedundancyConfigEntry 6 }

	swhFastRedundancyConfigRole OBJECT-TYPE
		SYNTAX      INTEGER { disable(-1), slave(0), master(1) }
		MAX-ACCESS  read-write
		STATUS      current
		DESCRIPTION
			"Role."
		::= { swhFastRedundancyConfigEntry 7 }

	swhFastRedundancyConfigPort1 OBJECT-TYPE
		SYNTAX      INTEGER { disable(0),
		                      port01(1),
		                      port02(2),
		                      port03(3),
		                      port04(4),
		                      port05(5),
		                      port06(6),
		                      port07(7),
		                      port08(8),
		                      port09(9),
		                      port10(10),
		                      port11(11),
		                      port12(12)
		                    }
		MAX-ACCESS  read-write
		STATUS      current
		DESCRIPTION
			"Port 1 Number."
		::= { swhFastRedundancyConfigEntry 8 }

	swhFastRedundancyConfigPort1Role OBJECT-TYPE
		SYNTAX      INTEGER { member(0), head(1), tail(2) }
		MAX-ACCESS  read-write
		STATUS      current
		DESCRIPTION
			"Fast Redundancy Port 1 Role."
		::= { swhFastRedundancyConfigEntry 9 }

	swhFastRedundancyConfigPort2 OBJECT-TYPE
		SYNTAX      INTEGER { disable(0),
		                      port01(1),
		                      port02(2),
		                      port03(3),
		                      port04(4),
		                      port05(5),
		                      port06(6),
		                      port07(7),
		                      port08(8),
		                      port09(9),
		                      port10(10),
		                      port11(11),
		                      port12(12)
		                    }
		MAX-ACCESS  read-write
		STATUS      current
		DESCRIPTION
			"Port 2 Number."
		::= { swhFastRedundancyConfigEntry 10 }

	swhFastRedundancyConfigPort2Role OBJECT-TYPE
		SYNTAX      INTEGER { member(0) }
		MAX-ACCESS  read-only
		STATUS      current
		DESCRIPTION
			"Fast Redundancy Port 2 Role."
		::= { swhFastRedundancyConfigEntry 11 }

	swhFastRedundancyConfigDelete OBJECT-TYPE
		SYNTAX      INTEGER { normal(0), delete(1) }
		MAX-ACCESS  read-write
		STATUS      current
		DESCRIPTION
			"Delete this entry."
		::= { swhFastRedundancyConfigEntry 13 }


-- SwitchManagement(4).IGMPMVR(92)

	swhIGMPMVRSystem
		OBJECT IDENTIFIER ::= { swhIGMPMVR 1 }

	swhIGMPMVRPort
		OBJECT IDENTIFIER ::= { swhIGMPMVR 2 }

	swhIGMPMVRMulticast
		OBJECT IDENTIFIER ::= { swhIGMPMVR 3 }


-- SwitchManagement(4).IGMPMVR(92).IGMPMVRSystem(1)

	swhIGMPMVRSystemEnable OBJECT-TYPE
		SYNTAX      INTEGER { disable(0), enable(1) }
		MAX-ACCESS  read-write
		STATUS      current
		DESCRIPTION
			"Enable."
		::= { swhIGMPMVRSystem 1 }

	swhIGMPMVRSystemSortBy OBJECT-TYPE
		SYNTAX      INTEGER { index(0), mvr(1) }
		MAX-ACCESS  read-write
		STATUS      current
		DESCRIPTION
			"Sort By."
		::= { swhIGMPMVRSystem 2 }


-- SwitchManagement(4).IGMPMVR(92).IGMPMVRSystem(1).IGMPMVRSystemConfigTable(5)

	swhIGMPMVRSystemConfigTable OBJECT-TYPE
		SYNTAX      SEQUENCE OF SwhIGMPMVRSystemConfigEntry
		MAX-ACCESS  not-accessible
		STATUS      current
		DESCRIPTION
			"Table of IGMP MVR group."
		::= { swhIGMPMVRSystem 5 }

	-- Table Entry
	swhIGMPMVRSystemConfigEntry OBJECT-TYPE
		SYNTAX      SwhIGMPMVRSystemConfigEntry
		MAX-ACCESS  not-accessible
		STATUS      current
		DESCRIPTION
			"An entry in the table, containing information about IGMP MVR group."
		INDEX    { swhIGMPMVRSystemConfigConfig }
		::= { swhIGMPMVRSystemConfigTable 1 }

	SwhIGMPMVRSystemConfigEntry ::=
		SEQUENCE {
			swhIGMPMVRSystemConfigConfig
				INTEGER,
			swhIGMPMVRSystemConfigIndex
				INTEGER,
			swhIGMPMVRSystemConfigMVRVLAN
				INTEGER,
			swhIGMPMVRSystemConfigName
				DisplayString,
			swhIGMPMVRSystemConfigEnable
				INTEGER,
			swhIGMPMVRSystemConfigDelete
				INTEGER
		}

	swhIGMPMVRSystemConfigConfig OBJECT-TYPE
		SYNTAX      INTEGER (0..2147483647)
		MAX-ACCESS  not-accessible
		STATUS      current
		DESCRIPTION
			"A unique value for each config."
		::= { swhIGMPMVRSystemConfigEntry 1 }

	swhIGMPMVRSystemConfigIndex OBJECT-TYPE
		SYNTAX      INTEGER (0..2147483647)
		MAX-ACCESS  read-only
		STATUS      current
		DESCRIPTION
			"A unique value for each index."
		::= { swhIGMPMVRSystemConfigEntry 2 }

	swhIGMPMVRSystemConfigMVRVLAN OBJECT-TYPE
		SYNTAX      INTEGER (1..4094)
		MAX-ACCESS  read-write
		STATUS      current
		DESCRIPTION
			"MVR VLAN ID. (1-4094)"
		::= { swhIGMPMVRSystemConfigEntry 3 }

	swhIGMPMVRSystemConfigName OBJECT-TYPE
		SYNTAX      DisplayString
		MAX-ACCESS  read-write
		STATUS      current
		DESCRIPTION
			"Name."
		::= { swhIGMPMVRSystemConfigEntry 4 }

	swhIGMPMVRSystemConfigEnable OBJECT-TYPE
		SYNTAX      INTEGER { disable(0), enable(1) }
		MAX-ACCESS  read-write
		STATUS      current
		DESCRIPTION
			"Enable."
		::= { swhIGMPMVRSystemConfigEntry 5 }

	swhIGMPMVRSystemConfigDelete OBJECT-TYPE
		SYNTAX      INTEGER { normal(0), delete(1) }
		MAX-ACCESS  read-write
		STATUS      current
		DESCRIPTION
			"Delete this entry."
		::= { swhIGMPMVRSystemConfigEntry 7 }


-- SwitchManagement(4).IGMPMVR(92).IGMPMVRPort(2)

	swhIGMPMVRPortSortBy OBJECT-TYPE
		SYNTAX      INTEGER { index(0), mvr(1), port(2) }
		MAX-ACCESS  read-write
		STATUS      current
		DESCRIPTION
			"Sort By."
		::= { swhIGMPMVRPort 2 }


-- SwitchManagement(4).IGMPMVR(92).IGMPMVRPort(2).IGMPMVRPortConfigTable(5)

	swhIGMPMVRPortConfigTable OBJECT-TYPE
		SYNTAX      SEQUENCE OF SwhIGMPMVRPortConfigEntry
		MAX-ACCESS  not-accessible
		STATUS      current
		DESCRIPTION
			"Table of IGMP MVR port."
		::= { swhIGMPMVRPort 5 }

	-- Table Entry
	swhIGMPMVRPortConfigEntry OBJECT-TYPE
		SYNTAX      SwhIGMPMVRPortConfigEntry
		MAX-ACCESS  not-accessible
		STATUS      current
		DESCRIPTION
			"An entry in the table, containing information about IGMP MVR port."
		INDEX    { swhIGMPMVRPortConfigConfig }
		::= { swhIGMPMVRPortConfigTable 1 }

	SwhIGMPMVRPortConfigEntry ::=
		SEQUENCE {
			swhIGMPMVRPortConfigConfig
				INTEGER,
			swhIGMPMVRPortConfigIndex
				INTEGER,
			swhIGMPMVRPortConfigMVRVLAN
				INTEGER,
			swhIGMPMVRPortConfigPort
				INTEGER,
			swhIGMPMVRPortConfigPortType
				INTEGER,
			swhIGMPMVRPortConfigDelete
				INTEGER
		}

	swhIGMPMVRPortConfigConfig OBJECT-TYPE
		SYNTAX      INTEGER (0..2147483647)
		MAX-ACCESS  not-accessible
		STATUS      current
		DESCRIPTION
			"A unique value for each config."
		::= { swhIGMPMVRPortConfigEntry 1 }

	swhIGMPMVRPortConfigIndex OBJECT-TYPE
		SYNTAX      INTEGER (0..2147483647)
		MAX-ACCESS  read-only
		STATUS      current
		DESCRIPTION
			"A unique value for each index."
		::= { swhIGMPMVRPortConfigEntry 2 }

	swhIGMPMVRPortConfigMVRVLAN OBJECT-TYPE
		SYNTAX      INTEGER (1..4094)
		MAX-ACCESS  read-write
		STATUS      current
		DESCRIPTION
			"MVR VLAN ID. (1-4094)"
		::= { swhIGMPMVRPortConfigEntry 3 }

	swhIGMPMVRPortConfigPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Port."
		::= { swhIGMPMVRPortConfigEntry 4 }

	swhIGMPMVRPortConfigPortType OBJECT-TYPE
		SYNTAX      INTEGER { receiver(0), sender(1) }
		MAX-ACCESS  read-write
		STATUS      current
		DESCRIPTION
			"Port Type."
		::= { swhIGMPMVRPortConfigEntry 5 }

	swhIGMPMVRPortConfigDelete OBJECT-TYPE
		SYNTAX      INTEGER { normal(0), delete(1) }
		MAX-ACCESS  read-write
		STATUS      current
		DESCRIPTION
			"Delete this entry."
		::= { swhIGMPMVRPortConfigEntry 7 }


-- SwitchManagement(4).IGMPMVR(92).IGMPMVRMulticast(3)

	swhIGMPMVRMulticastSortBy OBJECT-TYPE
		SYNTAX      INTEGER { index(0), mvr(1), multicast(2) }
		MAX-ACCESS  read-write
		STATUS      current
		DESCRIPTION
			"Sort By."
		::= { swhIGMPMVRMulticast 2 }


-- SwitchManagement(4).IGMPMVR(92).IGMPMVRMulticast(3).IGMPMVRMulticastConfigTable(5)

	swhIGMPMVRMulticastConfigTable OBJECT-TYPE
		SYNTAX      SEQUENCE OF SwhIGMPMVRMulticastConfigEntry
		MAX-ACCESS  not-accessible
		STATUS      current
		DESCRIPTION
			"Table of IGMP MVR multicast."
		::= { swhIGMPMVRMulticast 5 }

	-- Table Entry
	swhIGMPMVRMulticastConfigEntry OBJECT-TYPE
		SYNTAX      SwhIGMPMVRMulticastConfigEntry
		MAX-ACCESS  not-accessible
		STATUS      current
		DESCRIPTION
			"An entry in the table, containing information about IGMP MVR multicast."
		INDEX    { swhIGMPMVRMulticastConfigConfig }
		::= { swhIGMPMVRMulticastConfigTable 1 }

	SwhIGMPMVRMulticastConfigEntry ::=
		SEQUENCE {
			swhIGMPMVRMulticastConfigConfig
				INTEGER,
			swhIGMPMVRMulticastConfigIndex
				INTEGER,
			swhIGMPMVRMulticastConfigMVRVLAN
				INTEGER,
			swhIGMPMVRMulticastConfigName
				DisplayString,
			swhIGMPMVRMulticastConfigIPType
				INTEGER,
			swhIGMPMVRMulticastConfigAll
				INTEGER,
			swhIGMPMVRMulticastConfigIPRange1
				DisplayString,
			swhIGMPMVRMulticastConfigIPRange2
				DisplayString,
			swhIGMPMVRMulticastConfigDelete
				INTEGER
		}

	swhIGMPMVRMulticastConfigConfig OBJECT-TYPE
		SYNTAX      INTEGER (0..2147483647)
		MAX-ACCESS  not-accessible
		STATUS      current
		DESCRIPTION
			"A unique value for each config."
		::= { swhIGMPMVRMulticastConfigEntry 1 }

	swhIGMPMVRMulticastConfigIndex OBJECT-TYPE
		SYNTAX      INTEGER (0..2147483647)
		MAX-ACCESS  read-only
		STATUS      current
		DESCRIPTION
			"A unique value for each index."
		::= { swhIGMPMVRMulticastConfigEntry 2 }

	swhIGMPMVRMulticastConfigMVRVLAN OBJECT-TYPE
		SYNTAX      INTEGER (1..4094)
		MAX-ACCESS  read-write
		STATUS      current
		DESCRIPTION
			"MVR VLAN ID. (1-4094)"
		::= { swhIGMPMVRMulticastConfigEntry 3 }

	swhIGMPMVRMulticastConfigIPType OBJECT-TYPE
		SYNTAX      INTEGER { ipv4(0), ipv6(1) }
		MAX-ACCESS  read-write
		STATUS      current
		DESCRIPTION
			"IP Type."
		::= { swhIGMPMVRMulticastConfigEntry 4 }

	swhIGMPMVRMulticastConfigIPRange1 OBJECT-TYPE
		SYNTAX      DisplayString
		MAX-ACCESS  read-write
		STATUS      current
		DESCRIPTION
			"IP Range1 Address."
		::= { swhIGMPMVRMulticastConfigEntry 5 }

	swhIGMPMVRMulticastConfigIPRange2 OBJECT-TYPE
		SYNTAX      DisplayString
		MAX-ACCESS  read-write
		STATUS      current
		DESCRIPTION
			"IP Range2 Address."
		::= { swhIGMPMVRMulticastConfigEntry 6 }

	swhIGMPMVRMulticastConfigDelete OBJECT-TYPE
		SYNTAX      INTEGER { normal(0), delete(1) }
		MAX-ACCESS  read-write
		STATUS      current
		DESCRIPTION
			"Delete this entry."
		::= { swhIGMPMVRMulticastConfigEntry 7 }

	swhIGMPMVRMulticastConfigName OBJECT-TYPE
		SYNTAX      DisplayString
		MAX-ACCESS  read-only
		STATUS      current
		DESCRIPTION
			"Name."
		::= { swhIGMPMVRMulticastConfigEntry 8 }

	swhIGMPMVRMulticastConfigAll OBJECT-TYPE
		SYNTAX      INTEGER { range(0), all(1) }
		MAX-ACCESS  read-write
		STATUS      current
		DESCRIPTION
			"All."
		::= { swhIGMPMVRMulticastConfigEntry 9 }


-- SwitchMonitor(5)

	swhStatistics
		OBJECT IDENTIFIER ::= { swhSwitchMonitor 45 }

	swhPortStatus
		OBJECT IDENTIFIER ::= { swhSwitchMonitor 1 }

	swhPortCountersRates
		OBJECT IDENTIFIER ::= { swhSwitchMonitor 5 }

	swhPortCountersEvents
		OBJECT IDENTIFIER ::= { swhSwitchMonitor 6 }

	swhLACPPortStatus
		OBJECT IDENTIFIER ::= { swhSwitchMonitor 22 }

	swhLACPStatistics
		OBJECT IDENTIFIER ::= { swhSwitchMonitor 24 }

	swh8021QTagVLAN
		OBJECT IDENTIFIER ::= { swhSwitchMonitor 3 }

	swhRSTPStatistics
		OBJECT IDENTIFIER ::= { swhSwitchMonitor 18 }

	swhRSTPPortStatus
		OBJECT IDENTIFIER ::= { swhSwitchMonitor 14 }

	swhRSTPBridgeOverview
		OBJECT IDENTIFIER ::= { swhSwitchMonitor 10 }

	swhFastRedundancyStatus
		OBJECT IDENTIFIER ::= { swhSwitchMonitor 52 }

	swhMacAddressTable
		OBJECT IDENTIFIER ::= { swhSwitchMonitor 7 }

	swhIGMPStatus
		OBJECT IDENTIFIER ::= { swhSwitchMonitor 26 }

	swhMLDStatus
		OBJECT IDENTIFIER ::= { swhSwitchMonitor 27 }

	swhIGMPGroupTable
		OBJECT IDENTIFIER ::= { swhSwitchMonitor 28 }

	swhMLDGroupTable
		OBJECT IDENTIFIER ::= { swhSwitchMonitor 29 }

	swhDHCPSnoopingTable
		OBJECT IDENTIFIER ::= { swhSwitchMonitor 35 }

	swhMacLimitersStatus
		OBJECT IDENTIFIER ::= { swhSwitchMonitor 39 }

	swhLoopDetectionStatus
		OBJECT IDENTIFIER ::= { swhSwitchMonitor 36 }

	swh8021XPortStatus
		OBJECT IDENTIFIER ::= { swhSwitchMonitor 32 }

	swh8021XStatistics
		OBJECT IDENTIFIER ::= { swhSwitchMonitor 33 }

	swhLLDPStatus
		OBJECT IDENTIFIER ::= { swhSwitchMonitor 11 }

	swhLayer2ProtocolTunnelStatus
		OBJECT IDENTIFIER ::= { swhSwitchMonitor 25 }

	swhCPUTemperatureStatus
		OBJECT IDENTIFIER ::= { swhSwitchMonitor 51 }

	swhSystemVoltageState
		OBJECT IDENTIFIER ::= { swhSwitchMonitor 55 }

	swhSFPInformation
		OBJECT IDENTIFIER ::= { swhSwitchMonitor 34 }

	swhDIStatus
		OBJECT IDENTIFIER ::= { swhSwitchMonitor 41 }


-- SwitchMonitor(5).PortStatus(1)

	swhPortStatusTable OBJECT-TYPE
		SYNTAX      SEQUENCE OF SwhPortStatusEntry
		MAX-ACCESS  not-accessible
		STATUS      current
		DESCRIPTION
			"Table of port status."
		::= { swhPortStatus 1 }

	-- Table Entry
	swhPortStatusEntry OBJECT-TYPE
		SYNTAX      SwhPortStatusEntry
		MAX-ACCESS  not-accessible
		STATUS      current
		DESCRIPTION
			"An entry in the table, containing information about port status."
		INDEX    { swhPortStatusIndex }
		::= { swhPortStatusTable 1 }

	SwhPortStatusEntry ::=
		SEQUENCE {
			swhPortStatusIndex
				INTEGER,
			swhPortStatusPortMedia
				INTEGER,
			swhPortStatusPortState
				INTEGER,
			swhPortStatusPortLink
				INTEGER,
			swhPortStatusPortReason
				INTEGER,
			swhPortStatusPortSpeed
				INTEGER,
			swhPortStatusPortDuplex
				INTEGER,
			swhPortStatusPortFlowCtrl
				INTEGER,
			swhPortStatusDescription
				DisplayString,
			swhPortStatusPortMACAddress
				MacAddress
		}

	swhPortStatusIndex OBJECT-TYPE
		SYNTAX      INTEGER (0..2147483647)
		MAX-ACCESS  not-accessible
		STATUS      current
		DESCRIPTION
			"A unique value for each index."
		::= { swhPortStatusEntry 1 }

	swhPortStatusDescription OBJECT-TYPE
		SYNTAX      DisplayString
		MAX-ACCESS  read-only
		STATUS      current
		DESCRIPTION
			"Port Description."
		::= { swhPortStatusEntry 2 }

	swhPortStatusPortMedia OBJECT-TYPE
		SYNTAX      INTEGER { na2(-2), na(-1), tx(1), fx(2) }
		MAX-ACCESS  read-only
		STATUS      current
		DESCRIPTION
			"Port Media Type."
		::= { swhPortStatusEntry 3 }

	swhPortStatusPortState OBJECT-TYPE
		SYNTAX      INTEGER { na2(-2), na(-1), disable(0), blocking-listening(1), learning(2), forwarding(3) }
		MAX-ACCESS  read-only
		STATUS      current
		DESCRIPTION
			"Port State."
		::= { swhPortStatusEntry 4 }

	swhPortStatusPortLink OBJECT-TYPE
		SYNTAX      INTEGER { na2(-2), na(-1), up(1), down(2), blocking(3) }
		MAX-ACCESS  read-only
		STATUS      current
		DESCRIPTION
			"Port Link."
		::= { swhPortStatusEntry 5 }

	swhPortStatusPortReason OBJECT-TYPE
		SYNTAX      INTEGER { na2(-2), na(-1), lkd(0), lpd(1), ml(2), sc(3) }
		MAX-ACCESS  read-only
		STATUS      current
		DESCRIPTION
			"Port Reason. (lkd: Link Down, lpd: Loop Detection, ml: Mac Limit, sc: Storm Control)"
		::= { swhPortStatusEntry 14 }

	swhPortStatusPortSpeed OBJECT-TYPE
		SYNTAX      INTEGER { na2(-2), na(-1) }
		MAX-ACCESS  read-only
		STATUS      current
		DESCRIPTION
			"Port Speed."
		::= { swhPortStatusEntry 6 }

	swhPortStatusPortDuplex OBJECT-TYPE
		SYNTAX      INTEGER { na2(-2), na(-1), full(1), half(2) }
		MAX-ACCESS  read-only
		STATUS      current
		DESCRIPTION
			"Port Duplex."
		::= { swhPortStatusEntry 7 }

	swhPortStatusPortFlowCtrl OBJECT-TYPE
		SYNTAX      INTEGER { na2(-2), na(-1), on(1), off(2) }
		MAX-ACCESS  read-only
		STATUS      current
		DESCRIPTION
			"Port Flow Control."
		::= { swhPortStatusEntry 8 }

	swhPortStatusPortMACAddress OBJECT-TYPE
		SYNTAX      MacAddress
		MAX-ACCESS  read-only
		STATUS      current
		DESCRIPTION
			"Port media-dependent 'physical' address."
		::= { swhPortStatusEntry 15 }


-- SwitchMonitor(5).8021QTagVLAN(3)

	swh8021QTagVLANTable OBJECT-TYPE
		SYNTAX      SEQUENCE OF Swh8021QTagVLANEntry
		MAX-ACCESS  not-accessible
		STATUS      current
		DESCRIPTION
			"Table of 802.1Q tag VLAN configuration."
		::= { swh8021QTagVLAN 1 }

	-- Table Entry
	swh8021QTagVLANEntry OBJECT-TYPE
		SYNTAX      Swh8021QTagVLANEntry
		MAX-ACCESS  not-accessible
		STATUS      current
		DESCRIPTION
			"An entry in the table, containing information about 802.1Q tag VLAN configuration."
		INDEX    { swh8021QTagVLANIndex }
		::= { swh8021QTagVLANTable 1 }

	Swh8021QTagVLANEntry ::=
		SEQUENCE {
			swh8021QTagVLANIndex
				INTEGER,
			swh8021QTagVLANVID
				INTEGER,
			swh8021QTagVLANIsMVRVID
				INTEGER,
			swh8021QTagVLANName
				DisplayString,
			swh8021QTagVLANPort1
				INTEGER,
			swh8021QTagVLANPort2
				INTEGER,
			swh8021QTagVLANPort3
				INTEGER,
			swh8021QTagVLANPort4
				INTEGER,
			swh8021QTagVLANPort5
				INTEGER,
			swh8021QTagVLANPort6
				INTEGER,
			swh8021QTagVLANPort7
				INTEGER,
			swh8021QTagVLANPort8
				INTEGER,
			swh8021QTagVLANPort9
				INTEGER,
			swh8021QTagVLANPort10
				INTEGER,
			swh8021QTagVLANPort11
				INTEGER,
			swh8021QTagVLANPort12
				INTEGER,
			swh8021QTagVLANCPU
				INTEGER
		}

	swh8021QTagVLANIndex OBJECT-TYPE
		SYNTAX      INTEGER (0..2147483647)
		MAX-ACCESS  not-accessible
		STATUS      current
		DESCRIPTION
			"A unique value for each index."
		::= { swh8021QTagVLANEntry 1 }

	swh8021QTagVLANVID OBJECT-TYPE
		SYNTAX      INTEGER (1..4094)
		MAX-ACCESS  read-only
		STATUS      current
		DESCRIPTION
			"VLAN ID. (1-4094)"
		::= { swh8021QTagVLANEntry 3 }

	swh8021QTagVLANName OBJECT-TYPE
		SYNTAX      DisplayString
		MAX-ACCESS  read-only
		STATUS      current
		DESCRIPTION
			"8021Q tag VLAN name."
		::= { swh8021QTagVLANEntry 4 }

	swh8021QTagVLANPort1 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 5 }

	swh8021QTagVLANPort2 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 6 }

	swh8021QTagVLANPort3 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 7 }

	swh8021QTagVLANPort4 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 8 }

	swh8021QTagVLANPort5 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 9 }

	swh8021QTagVLANPort6 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 10 }

	swh8021QTagVLANPort7 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 11 }

	swh8021QTagVLANPort8 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 12 }

	swh8021QTagVLANPort9 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 13 }

	swh8021QTagVLANPort10 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 14 }

	swh8021QTagVLANPort11 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 15 }

	swh8021QTagVLANPort12 OBJECT-TYPE
		SYNTAX      INTEGER { b(0), t(2), u(3), d(4), s(5), r(6), q(7) }
		MAX-ACCESS  read-only
		STATUS      current
		DESCRIPTION
			"b : Blocked  t : Tagged  u : Untagged  d : Dot1q-Tunnel  s : MVR-sender  r : MVR-receiver  q : Selective-QinQ"
		::= { swh8021QTagVLANEntry 16 }

	swh8021QTagVLANIsMVRVID OBJECT-TYPE
		SYNTAX      INTEGER { b(0), v(1) }
		MAX-ACCESS  read-only
		STATUS      current
		DESCRIPTION
			"Is it MVR VLAN ID? (b : no, v : yes)"
		::= { swh8021QTagVLANEntry 53 }

	swh8021QTagVLANCPU OBJECT-TYPE
		SYNTAX      INTEGER { b(0), v(1) }
		MAX-ACCESS  read-only
		STATUS      current
		DESCRIPTION
			"b : Blocked  v : Member"
		::= { swh8021QTagVLANEntry 55 }


-- SwitchMonitor(5).PortCountersRates(5)

	swhCountersRatesTable OBJECT-TYPE
		SYNTAX      SEQUENCE OF SwhCountersRatesEntry
		MAX-ACCESS  not-accessible
		STATUS      current
		DESCRIPTION
			"Table of port counters rates."
		::= { swhPortCountersRates 1 }

	-- Table Entry
	swhCountersRatesEntry OBJECT-TYPE
		SYNTAX      SwhCountersRatesEntry
		MAX-ACCESS  not-accessible
		STATUS      current
		DESCRIPTION
			"An entry in the table, containing information about port counters rates."
		INDEX    { swhCountersRatesIndex }
		::= { swhCountersRatesTable 1 }

	SwhCountersRatesEntry ::=
		SEQUENCE {
			swhCountersRatesIndex
				INTEGER,
			swhCountersRatesBytesReceived
				Counter32,
			swhCountersRatesFramesReceived
				Counter32,
			swhCountersRatesReceivedUtilization
				DisplayString,
			swhCountersRatesBytesSent
				Counter32,
			swhCountersRatesFramesSent
				Counter32,
			swhCountersRatesSentUtilization
				DisplayString,
			swhCountersRatesTotalBytes
				Counter32,
			swhCountersRatesTotalUtilization
				DisplayString,
			swhCountersRatesRxCRCError
				Counter32,
			swhCountersRatesRxAlignError
				Counter32,
			swhCountersRatesRxUndersize
				Counter32,
			swhCountersRatesRxFragments
				Counter32,
			swhCountersRatesRxJabbers
				Counter32,
			swhCountersRatesRxOversizeFrames
				Counter32,
			swhCountersRatesRxDroppedFrames
				Counter32,
			swhCountersRatesTxCollisions
				Counter32,
			swhCountersRatesTxDroppedFrames
				Counter32,
			swhCountersRatesTotalErrors
				Counter32,
			swhCountersRatesTotalErrorsExcludeDrop
				Counter32,
			swhCountersRatesRxFrames64Bytes
				Counter32,
			swhCountersRatesRxFrames65to127Bytes
				Counter32,
			swhCountersRatesRxFrames128to255Bytes
				Counter32,
			swhCountersRatesRxFrames256to511Bytes
				Counter32,
			swhCountersRatesRxFrames512to1023Bytes
				Counter32,
			swhCountersRatesRxFrames1024to1518Bytes
				Counter32,
			swhCountersRatesRxFrames1519toMaxBytes
				Counter32,
			swhCountersRatesRxUnicastFrames
				Counter32,
			swhCountersRatesTxUnicastFrames
				Counter32,
			swhCountersRatesRxMulticastFrames
				Counter32,
			swhCountersRatesTxMulticastFrames
				Counter32,
			swhCountersRatesRxBroadcastFrames
				Counter32,
			swhCountersRatesTxBroadcastFrames
				Counter32
		}

	swhCountersRatesIndex OBJECT-TYPE
		SYNTAX      INTEGER (0..2147483647)
		MAX-ACCESS  not-accessible
		STATUS      current
		DESCRIPTION
			"A unique value for each index."
		::= { swhCountersRatesEntry 1 }

	swhCountersRatesBytesReceived OBJECT-TYPE
		SYNTAX      Counter32
		MAX-ACCESS  read-only
		STATUS      current
		DESCRIPTION
			"Bytes Received."
		::= { swhCountersRatesEntry 2 }

	swhCountersRatesFramesReceived OBJECT-TYPE
		SYNTAX      Counter32
		MAX-ACCESS  read-only
		STATUS      current
		DESCRIPTION
			"Frames Received."
		::= { swhCountersRatesEntry 3 }

	swhCountersRatesReceivedUtilization OBJECT-TYPE
		SYNTAX      DisplayString
		MAX-ACCESS  read-only
		STATUS      current
		DESCRIPTION
			"Received Utilization."
		::= { swhCountersRatesEntry 4 }

	swhCountersRatesBytesSent OBJECT-TYPE
		SYNTAX      Counter32
		MAX-ACCESS  read-only
		STATUS      current
		DESCRIPTION
			"Bytes Sent."
		::= { swhCountersRatesEntry 5 }

	swhCountersRatesFramesSent OBJECT-TYPE
		SYNTAX      Counter32
		MAX-ACCESS  read-only
		STATUS      current
		DESCRIPTION
			"Frames Sent."
		::= { swhCountersRatesEntry 6 }

	swhCountersRatesSentUtilization OBJECT-TYPE
		SYNTAX      DisplayString
		MAX-ACCESS  read-only
		STATUS      current
		DESCRIPTION
			"Sent Utilization."
		::= { swhCountersRatesEntry 7 }

	swhCountersRatesTotalBytes OBJECT-TYPE
		SYNTAX      Counter32
		MAX-ACCESS  read-only
		STATUS      current
		DESCRIPTION
			"Total Bytes."
		::= { swhCountersRatesEntry 8 }

	swhCountersRatesTotalUtilization OBJECT-TYPE
		SYNTAX      DisplayString
		MAX-ACCESS  read-only
		STATUS      current
		DESCRIPTION
			"Total Utilization."
		::= { swhCountersRatesEntry 9 }

	swhCountersRatesRxCRCError OBJECT-TYPE
		SYNTAX      Counter32
		MAX-ACCESS  read-only
		STATUS      current
		DESCRIPTION
			"Rx CRC Error. (Units : pps)"
		::= { swhCountersRatesEntry 10 }

	swhCountersRatesRxFragments OBJECT-TYPE
		SYNTAX      Counter32
		MAX-ACCESS  read-only
		STATUS      current
		DESCRIPTION
			"Rx Fragments. (Units : pps)"
		::= { swhCountersRatesEntry 11 }

	swhCountersRatesRxAlignError OBJECT-TYPE
		SYNTAX      Counter32
		MAX-ACCESS  read-only
		STATUS      current
		DESCRIPTION
			"Rx Align Error. (Units : pps)"
		::= { swhCountersRatesEntry 13 }

	swhCountersRatesRxUndersize OBJECT-TYPE
		SYNTAX      Counter32
		MAX-ACCESS  read-only
		STATUS      current
		DESCRIPTION
			"Rx Undersize. (Units : pps)"
		::= { swhCountersRatesEntry 14 }

	swhCountersRatesRxOversizeFrames OBJECT-TYPE
		SYNTAX      Counter32
		MAX-ACCESS  read-only
		STATUS      current
		DESCRIPTION
			"Rx Oversize Frames. (Units : pps) (Rate of received packets with size over Jumbo Size.)"
		::= { swhCountersRatesEntry 15 }

	swhCountersRatesRxJabbers OBJECT-TYPE
		SYNTAX      Counter32
		MAX-ACCESS  read-only
		STATUS      current
		DESCRIPTION
			"Rx Jabbers. (Units : pps)"
		::= { swhCountersRatesEntry 16 }

	swhCountersRatesRxDroppedFrames OBJECT-TYPE
		SYNTAX      Counter32
		MAX-ACCESS  read-only
		STATUS      current
		DESCRIPTION
			"Rx Dropped Frames. (Units : pps) 
			 (Drop Reason: incorrect VLAN; 
			 transmission rate over limitation; 
			 configured filtering rules; 
			 or no forwarding destination after receiving)"
		::= { swhCountersRatesEntry 17 }

	swhCountersRatesTxDroppedFrames OBJECT-TYPE
		SYNTAX      Counter32
		MAX-ACCESS  read-only
		STATUS      current
		DESCRIPTION
			"Tx Dropped Frames. (Units : pps)"
		::= { swhCountersRatesEntry 18 }

	swhCountersRatesRxFrames64Bytes OBJECT-TYPE
		SYNTAX      Counter32
		MAX-ACCESS  read-only
		STATUS      current
		DESCRIPTION
			"Rx Frames 64 Bytes. (Units : pps)"
		::= { swhCountersRatesEntry 22 }

	swhCountersRatesRxFrames65to127Bytes OBJECT-TYPE
		SYNTAX      Counter32
		MAX-ACCESS  read-only
		STATUS      current
		DESCRIPTION
			"Rx Frames 65 to 127 Bytes. (Units : pps)"
		::= { swhCountersRatesEntry 23 }

	swhCountersRatesRxFrames128to255Bytes OBJECT-TYPE
		SYNTAX      Counter32
		MAX-ACCESS  read-only
		STATUS      current
		DESCRIPTION
			"Rx Frames 128 to 255 Bytes. (Units : pps)"
		::= { swhCountersRatesEntry 24 }

	swhCountersRatesRxFrames256to511Bytes OBJECT-TYPE
		SYNTAX      Counter32
		MAX-ACCESS  read-only
		STATUS      current
		DESCRIPTION
			"Rx Frames 256 to 511 Bytes. (Units : pps)"
		::= { swhCountersRatesEntry 25 }

	swhCountersRatesRxFrames512to1023Bytes OBJECT-TYPE
		SYNTAX      Counter32
		MAX-ACCESS  read-only
		STATUS      current
		DESCRIPTION
			"Rx Frames 512 to 1023 Bytes. (Units : pps)"
		::= { swhCountersRatesEntry 26 }

	swhCountersRatesRxUnicastFrames OBJECT-TYPE
		SYNTAX      Counter32
		MAX-ACCESS  read-only
		STATUS      current
		DESCRIPTION
			"Rx Unicast Frames. (Units : pps)"
		::= { swhCountersRatesEntry 28 }

	swhCountersRatesRxMulticastFrames OBJECT-TYPE
		SYNTAX      Counter32
		MAX-ACCESS  read-only
		STATUS      current
		DESCRIPTION
			"Rx Multicast Frames. (Units : pps)"
		::= { swhCountersRatesEntry 29 }

	swhCountersRatesRxBroadcastFrames OBJECT-TYPE
		SYNTAX      Counter32
		MAX-ACCESS  read-only
		STATUS      current
		DESCRIPTION
			"Rx Broadcast Frames. (Units : pps)"
		::= { swhCountersRatesEntry 30 }

	swhCountersRatesTxUnicastFrames OBJECT-TYPE
		SYNTAX      Counter32
		MAX-ACCESS  read-only
		STATUS      current
		DESCRIPTION
			"Tx Unicast Frames. (Units : pps)"
		::= { swhCountersRatesEntry 31 }

	swhCountersRatesTxMulticastFrames OBJECT-TYPE
		SYNTAX      Counter32
		MAX-ACCESS  read-only
		STATUS      current
		DESCRIPTION
			"Tx Multicast Frames. (Units : pps)"
		::= { swhCountersRatesEntry 32 }

	swhCountersRatesTxBroadcastFrames OBJECT-TYPE
		SYNTAX      Counter32
		MAX-ACCESS  read-only
		STATUS      current
		DESCRIPTION
			"Tx Broadcast Frames. (Units : pps)"
		::= { swhCountersRatesEntry 33 }

	swhCountersRatesTxCollisions OBJECT-TYPE
		SYNTAX      Counter32
		MAX-ACCESS  read-only
		STATUS      current
		DESCRIPTION
			"Tx Collisions. (Units : pps)"
		::= { swhCountersRatesEntry 38 }

	swhCountersRatesTotalErrors OBJECT-TYPE
		SYNTAX      Counter32
		MAX-ACCESS  read-only
		STATUS      current
		DESCRIPTION
			"Total Errors. (Units : pps)"
		::= { swhCountersRatesEntry 39 }

	swhCountersRatesRxFrames1024to1518Bytes OBJECT-TYPE
		SYNTAX      Counter32
		MAX-ACCESS  read-only
		STATUS      current
		DESCRIPTION
			"Rx Frames 1024 to 1518 Bytes. (Units : pps)"
		::= { swhCountersRatesEntry 40 }

	swhCountersRatesRxFrames1519toMaxBytes OBJECT-TYPE
		SYNTAX      Counter32
		MAX-ACCESS  read-only
		STATUS      current
		DESCRIPTION
			"Rx Frames 1519 to Max Bytes. (Units : pps) (Rate of received packets with size between 1519 to Jumbo Size.)"
		::= { swhCountersRatesEntry 41 }

	swhCountersRatesTotalErrorsExcludeDrop OBJECT-TYPE
		SYNTAX      Counter32
		MAX-ACCESS  read-only
		STATUS      current
		DESCRIPTION
			"Total Errors Exclude Drop. (Units : pps)"
		::= { swhCountersRatesEntry 43 }

	-- Counters Rates Traffic

	SwhCountersRatesTraffic ::=
		SEQUENCE {
			swhCountersRatesIndex
				INTEGER,
			swhCountersRatesBytesReceived
				Counter32,
			swhCountersRatesFramesReceived
				Counter32,
			swhCountersRatesReceivedUtilization
				DisplayString,
			swhCountersRatesBytesSent
				Counter32,
			swhCountersRatesFramesSent
				Counter32,
			swhCountersRatesSentUtilization
				DisplayString,
			swhCountersRatesTotalBytes
				Counter32,
			swhCountersRatesTotalUtilization
				DisplayString
		}

	-- Counters Rates Error

	SwhCountersRatesError ::=
		SEQUENCE {
			swhCountersRatesIndex
				INTEGER,
			swhCountersRatesRxCRCError
				Counter32,
			swhCountersRatesRxAlignError
				Counter32,
			swhCountersRatesRxUndersize
				Counter32,
			swhCountersRatesRxFragments
				Counter32,
			swhCountersRatesRxJabbers
				Counter32,
			swhCountersRatesRxOversizeFrames
				Counter32,
			swhCountersRatesRxDroppedFrames
				Counter32,
			swhCountersRatesTxCollisions
				Counter32,
			swhCountersRatesTxDroppedFrames
				Counter32,
			swhCountersRatesTotalErrors
				Counter32,
			swhCountersRatesTotalErrorsExcludeDrop
				Counter32
		}

	-- Counters Rates Analysis

	SwhCountersRatesAnalysis ::=
		SEQUENCE {
			swhCountersRatesIndex
				INTEGER,
			swhCountersRatesRxFrames64Bytes
				Counter32,
			swhCountersRatesRxFrames65to127Bytes
				Counter32,
			swhCountersRatesRxFrames128to255Bytes
				Counter32,
			swhCountersRatesRxFrames256to511Bytes
				Counter32,
			swhCountersRatesRxFrames512to1023Bytes
				Counter32,
			swhCountersRatesRxFrames1024to1518Bytes
				Counter32,
			swhCountersRatesRxFrames1519toMaxBytes
				Counter32,
			swhCountersRatesRxUnicastFrames
				Counter32,
			swhCountersRatesTxUnicastFrames
				Counter32,
			swhCountersRatesRxMulticastFrames
				Counter32,
			swhCountersRatesTxMulticastFrames
				Counter32,
			swhCountersRatesRxBroadcastFrames
				Counter32,
			swhCountersRatesTxBroadcastFrames
				Counter32
		}


-- SwitchMonitor(5).PortCountersEvents(6)

	swhCountersEventsTable OBJECT-TYPE
		SYNTAX      SEQUENCE OF SwhCountersEventsEntry
		MAX-ACCESS  not-accessible
		STATUS      current
		DESCRIPTION
			"Table of port counters events."
		::= { swhPortCountersEvents 1 }

	swhCountersEventsClearCountersOfAllPort OBJECT-TYPE
		SYNTAX      INTEGER { normal(0), clear(1) }
		MAX-ACCESS  read-write
		STATUS      current
		DESCRIPTION
			"Clear counters of all port."
		::= { swhPortCountersEvents 2 }

	-- Table Entry
	swhCountersEventsEntry OBJECT-TYPE
		SYNTAX      SwhCountersEventsEntry
		MAX-ACCESS  not-accessible
		STATUS      current
		DESCRIPTION
			"An entry in the table, containing information about port counters events."
		INDEX    { swhCountersEventsIndex }
		::= { swhCountersEventsTable 1 }

	SwhCountersEventsEntry ::=
		SEQUENCE {
			swhCountersEventsIndex
				INTEGER,
			swhCountersEventsBytesReceived
				Counter64,
			swhCountersEventsFramesReceived
				Counter64,
			swhCountersEventsBytesSent
				Counter64,
			swhCountersEventsFramesSent
				Counter64,
			swhCountersEventsTotalBytes
				Counter64,
			swhCountersEventsRxCRCError
				Counter64,
			swhCountersEventsRxAlignError
				Counter64,
			swhCountersEventsRxUndersize
				Counter64,
			swhCountersEventsRxFragments
				Counter64,
			swhCountersEventsRxJabbers
				Counter64,
			swhCountersEventsRxOversizeFrames
				Counter64,
			swhCountersEventsRxDroppedFrames
				Counter64,
			swhCountersEventsTxCollisions
				Counter64,
			swhCountersEventsTxDroppedFrames
				Counter64,
			swhCountersEventsTotalErrors
				Counter64,
			swhCountersEventsTotalErrorsExcludeDrop
				Counter64,
			swhCountersEventsRxFrames64Bytes
				Counter64,
			swhCountersEventsRxFrames65to127Bytes
				Counter64,
			swhCountersEventsRxFrames128to255Bytes
				Counter64,
			swhCountersEventsRxFrames256to511Bytes
				Counter64,
			swhCountersEventsRxFrames512to1023Bytes
				Counter64,
			swhCountersEventsRxFrames1024to1518Bytes
				Counter64,
			swhCountersEventsRxFrames1519toMaxBytes
				Counter64,
			swhCountersEventsRxUnicastFrames
				Counter64,
			swhCountersEventsTxUnicastFrames
				Counter64,
			swhCountersEventsRxMulticastFrames
				Counter64,
			swhCountersEventsTxMulticastFrames
				Counter64,
			swhCountersEventsRxBroadcastFrames
				Counter64,
			swhCountersEventsTxBroadcastFrames
				Counter64,
			swhCountersEventsClearCountersOfThisModule
				INTEGER
		}

	swhCountersEventsIndex OBJECT-TYPE
		SYNTAX      INTEGER (0..2147483647)
		MAX-ACCESS  not-accessible
		STATUS      current
		DESCRIPTION
			"A unique value for each index."
		::= { swhCountersEventsEntry 1 }

	swhCountersEventsBytesReceived OBJECT-TYPE
		SYNTAX      Counter64
		MAX-ACCESS  read-only
		STATUS      current
		DESCRIPTION
			"Bytes Received."
		::= { swhCountersEventsEntry 2 }

	swhCountersEventsFramesReceived OBJECT-TYPE
		SYNTAX      Counter64
		MAX-ACCESS  read-only
		STATUS      current
		DESCRIPTION
			"Frames Received."
		::= { swhCountersEventsEntry 3 }

	swhCountersEventsBytesSent OBJECT-TYPE
		SYNTAX      Counter64
		MAX-ACCESS  read-only
		STATUS      current
		DESCRIPTION
			"Bytes Sent."
		::= { swhCountersEventsEntry 5 }

	swhCountersEventsFramesSent OBJECT-TYPE
		SYNTAX      Counter64
		MAX-ACCESS  read-only
		STATUS      current
		DESCRIPTION
			"Frames Sent."
		::= { swhCountersEventsEntry 6 }

	swhCountersEventsTotalBytes OBJECT-TYPE
		SYNTAX      Counter64
		MAX-ACCESS  read-only
		STATUS      current
		DESCRIPTION
			"Total Bytes."
		::= { swhCountersEventsEntry 8 }

	swhCountersEventsRxCRCError OBJECT-TYPE
		SYNTAX      Counter64
		MAX-ACCESS  read-only
		STATUS      current
		DESCRIPTION
			"Rx CRC Error."
		::= { swhCountersEventsEntry 10 }

	swhCountersEventsRxFragments OBJECT-TYPE
		SYNTAX      Counter64
		MAX-ACCESS  read-only
		STATUS      current
		DESCRIPTION
			"Rx Fragments."
		::= { swhCountersEventsEntry 11 }

	swhCountersEventsRxAlignError OBJECT-TYPE
		SYNTAX      Counter64
		MAX-ACCESS  read-only
		STATUS      current
		DESCRIPTION
			"Rx Align Error."
		::= { swhCountersEventsEntry 13 }

	swhCountersEventsRxUndersize OBJECT-TYPE
		SYNTAX      Counter64
		MAX-ACCESS  read-only
		STATUS      current
		DESCRIPTION
			"Rx Undersize."
		::= { swhCountersEventsEntry 14 }

	swhCountersEventsRxOversizeFrames OBJECT-TYPE
		SYNTAX      Counter64
		MAX-ACCESS  read-only
		STATUS      current
		DESCRIPTION
			"Rx Oversize Frames. (Counter of event of received packets with size over Jumbo Size.)"
		::= { swhCountersEventsEntry 15 }

	swhCountersEventsRxJabbers OBJECT-TYPE
		SYNTAX      Counter64
		MAX-ACCESS  read-only
		STATUS      current
		DESCRIPTION
			"Rx Jabbers."
		::= { swhCountersEventsEntry 16 }

	swhCountersEventsRxDroppedFrames OBJECT-TYPE
		SYNTAX      Counter64
		MAX-ACCESS  read-only
		STATUS      current
		DESCRIPTION
			"Rx Dropped Frames. (Counter of event of received frames dropped.) 
			 (Drop Reason: incorrect VLAN; 
			 transmission rate over limitation; 
			 configured filtering rules; 
			 or no forwarding destination after receiving)"
		::= { swhCountersEventsEntry 17 }

	swhCountersEventsTxDroppedFrames OBJECT-TYPE
		SYNTAX      Counter64
		MAX-ACCESS  read-only
		STATUS      current
		DESCRIPTION
			"Tx Dropped Frames."
		::= { swhCountersEventsEntry 18 }

	swhCountersEventsRxFrames64Bytes OBJECT-TYPE
		SYNTAX      Counter64
		MAX-ACCESS  read-only
		STATUS      current
		DESCRIPTION
			"Rx Frames 64 Bytes."
		::= { swhCountersEventsEntry 22 }

	swhCountersEventsRxFrames65to127Bytes OBJECT-TYPE
		SYNTAX      Counter64
		MAX-ACCESS  read-only
		STATUS      current
		DESCRIPTION
			"Rx Frames 65 to 127 Bytes."
		::= { swhCountersEventsEntry 23 }

	swhCountersEventsRxFrames128to255Bytes OBJECT-TYPE
		SYNTAX      Counter64
		MAX-ACCESS  read-only
		STATUS      current
		DESCRIPTION
			"Rx Frames 128 to 255 Bytes."
		::= { swhCountersEventsEntry 24 }

	swhCountersEventsRxFrames256to511Bytes OBJECT-TYPE
		SYNTAX      Counter64
		MAX-ACCESS  read-only
		STATUS      current
		DESCRIPTION
			"Rx Frames 256 to 511 Bytes."
		::= { swhCountersEventsEntry 25 }

	swhCountersEventsRxFrames512to1023Bytes OBJECT-TYPE
		SYNTAX      Counter64
		MAX-ACCESS  read-only
		STATUS      current
		DESCRIPTION
			"Rx Frames 512 to 1023 Bytes."
		::= { swhCountersEventsEntry 26 }

	swhCountersEventsRxUnicastFrames OBJECT-TYPE
		SYNTAX      Counter64
		MAX-ACCESS  read-only
		STATUS      current
		DESCRIPTION
			"Rx Unicast Frames."
		::= { swhCountersEventsEntry 28 }

	swhCountersEventsRxMulticastFrames OBJECT-TYPE
		SYNTAX      Counter64
		MAX-ACCESS  read-only
		STATUS      current
		DESCRIPTION
			"Rx Multicast Frames."
		::= { swhCountersEventsEntry 29 }

	swhCountersEventsRxBroadcastFrames OBJECT-TYPE
		SYNTAX      Counter64
		MAX-ACCESS  read-only
		STATUS      current
		DESCRIPTION
			"Rx Broadcast Frames."
		::= { swhCountersEventsEntry 30 }

	swhCountersEventsTxUnicastFrames OBJECT-TYPE
		SYNTAX      Counter64
		MAX-ACCESS  read-only
		STATUS      current
		DESCRIPTION
			"Tx Unicast Frames."
		::= { swhCountersEventsEntry 31 }

	swhCountersEventsTxMulticastFrames OBJECT-TYPE
		SYNTAX      Counter64
		MAX-ACCESS  read-only
		STATUS      current
		DESCRIPTION
			"Tx Multicast Frames."
		::= { swhCountersEventsEntry 32 }

	swhCountersEventsTxBroadcastFrames OBJECT-TYPE
		SYNTAX      Counter64
		MAX-ACCESS  read-only
		STATUS      current
		DESCRIPTION
			"Tx Broadcast Frames."
		::= { swhCountersEventsEntry 33 }

	swhCountersEventsClearCountersOfThisModule OBJECT-TYPE
		SYNTAX      INTEGER { normal(0), clear(1) }
		MAX-ACCESS  read-write
		STATUS      current
		DESCRIPTION
			"Clear counters of this module."
		::= { swhCountersEventsEntry 34 }

	swhCountersEventsTxCollisions OBJECT-TYPE
		SYNTAX      Counter64
		MAX-ACCESS  read-only
		STATUS      current
		DESCRIPTION
			"Tx Collisions."
		::= { swhCountersEventsEntry 39 }

	swhCountersEventsRxFrames1024to1518Bytes OBJECT-TYPE
		SYNTAX      Counter64
		MAX-ACCESS  read-only
		STATUS      current
		DESCRIPTION
			"Rx Frames 1024 to 1518 Bytes."
		::= { swhCountersEventsEntry 40 }

	swhCountersEventsRxFrames1519toMaxBytes OBJECT-TYPE
		SYNTAX      Counter64
		MAX-ACCESS  read-only
		STATUS      current
		DESCRIPTION
			"Rx Frames 1519 to Max Bytes. (Counter of event of received packets with size between 1519 to Jumbo Size.)"
		::= { swhCountersEventsEntry 41 }

	swhCountersEventsTotalErrors OBJECT-TYPE
		SYNTAX      Counter64
		MAX-ACCESS  read-only
		STATUS      current
		DESCRIPTION
			"Total Errors."
		::= { swhCountersEventsEntry 42 }

	swhCountersEventsTotalErrorsExcludeDrop OBJECT-TYPE
		SYNTAX      Counter64
		MAX-ACCESS  read-only
		STATUS      current
		DESCRIPTION
			"Total Errors Exclude Drop."
		::= { swhCountersEventsEntry 44 }

	-- Counters Events Traffic

	SwhCountersEventsTraffic ::=
		SEQUENCE {
			swhCountersEventsIndex
				INTEGER,
			swhCountersEventsBytesReceived
				Counter64,
			swhCountersEventsFramesReceived
				Counter64,
			swhCountersEventsBytesSent
				Counter64,
			swhCountersEventsFramesSent
				Counter64,
			swhCountersEventsTotalBytes
				Counter64,
			swhCountersEventsClearCountersOfThisModule
				INTEGER
		}

	-- Counters Events Error

	SwhCountersEventsError ::=
		SEQUENCE {
			swhCountersEventsIndex
				INTEGER,
			swhCountersEventsRxCRCError
				Counter64,
			swhCountersEventsRxAlignError
				Counter64,
			swhCountersEventsRxUndersize
				Counter64,
			swhCountersEventsRxFragments
				Counter64,
			swhCountersEventsRxJabbers
				Counter64,
			swhCountersEventsRxOversizeFrames
				Counter64,
			swhCountersEventsRxDroppedFrames
				Counter64,
			swhCountersEventsTxCollisions
				Counter64,
			swhCountersEventsTxDroppedFrames
				Counter64,
			swhCountersEventsTotalErrors
				Counter64,
			swhCountersEventsTotalErrorsExcludeDrop
				Counter64,
			swhCountersEventsClearCountersOfThisModule
				INTEGER
		}

	-- Counters Events Analysis

	SwhCountersEventsAnalysis ::=
		SEQUENCE {
			swhCountersEventsIndex
				INTEGER,
			swhCountersEventsRxFrames64Bytes
				Counter64,
			swhCountersEventsRxFrames65to127Bytes
				Counter64,
			swhCountersEventsRxFrames128to255Bytes
				Counter64,
			swhCountersEventsRxFrames256to511Bytes
				Counter64,
			swhCountersEventsRxFrames512to1023Bytes
				Counter64,
			swhCountersEventsRxFrames1024to1518Bytes
				Counter64,
			swhCountersEventsRxFrames1519toMaxBytes
				Counter64,
			swhCountersEventsRxUnicastFrames
				Counter64,
			swhCountersEventsTxUnicastFrames
				Counter64,
			swhCountersEventsRxMulticastFrames
				Counter64,
			swhCountersEventsTxMulticastFrames
				Counter64,
			swhCountersEventsRxBroadcastFrames
				Counter64,
			swhCountersEventsTxBroadcastFrames
				Counter64,
			swhCountersEventsClearCountersOfThisModule
				INTEGER
		}


-- SwitchMonitor(5).MacAddressTable(7)

	swhMacAddressTotal OBJECT-TYPE
		SYNTAX      INTEGER (0..2147483647)
		MAX-ACCESS  read-only
		STATUS      current
		DESCRIPTION
			"The amount of total learned mac address."
		::= { swhMacAddressTable 1 }

	swhMacAddressState OBJECT-TYPE
		SYNTAX      DisplayString
		MAX-ACCESS  read-only
		STATUS      current
		DESCRIPTION
			"The state of mac address table."
		::= { swhMacAddressTable 2 }

	swhMacAddressFlushByPortList OBJECT-TYPE
		SYNTAX      DisplayString
		MAX-ACCESS  read-write
		STATUS      current
		DESCRIPTION
			"Flush by port list."
		::= { swhMacAddressTable 3 }

	swhMacAddressFlush OBJECT-TYPE
		SYNTAX      INTEGER { normal(0), flush-all(1), flush-by-port-list(2) }
		MAX-ACCESS  read-write
		STATUS      current
		DESCRIPTION
			"Flush mac address table."
		::= { swhMacAddressTable 4 }

	swhMacAddressSortRule OBJECT-TYPE
		SYNTAX      INTEGER { port(0), mac(1), vlan(2) }
		MAX-ACCESS  read-write
		STATUS      current
		DESCRIPTION
			"Sort the mac address table by the option."
		::= { swhMacAddressTable 5 }

	swhMacAddressType OBJECT-TYPE
		SYNTAX      INTEGER { all(0), static(1), dynamic(2) }
		MAX-ACCESS  read-write
		STATUS      current
		DESCRIPTION
			"MAC Type."
		::= { swhMacAddressTable 6 }

	swhMacAddressMACFilterRule OBJECT-TYPE
		SYNTAX      INTEGER { all(0), exclude(1), include(2) }
		MAX-ACCESS  read-write
		STATUS      current
		DESCRIPTION
			"The rule for display mac address table with filter by specific mac address."
		::= { swhMacAddressTable 7 }

	swhMacAddressMACFilter OBJECT-TYPE
		SYNTAX      DisplayString
		MAX-ACCESS  read-write
		STATUS      current
		DESCRIPTION
			"Display mac address table with filter by specific mac address."
		::= { swhMacAddressTable 8 }

	swhMacAddressFilterMask OBJECT-TYPE
		SYNTAX      DisplayString
		MAX-ACCESS  read-write
		STATUS      current
		DESCRIPTION
			"The mac address mask for display mac address table with filter by specific mac address."
		::= { swhMacAddressTable 9 }

	swhMacAddressVLANFilterRule OBJECT-TYPE
		SYNTAX      INTEGER { all(0), exclude(1), include(2) }
		MAX-ACCESS  read-write
		STATUS      current
		DESCRIPTION
			"The rule for display mac address table with filter by specific VLAN."
		::= { swhMacAddressTable 10 }

	swhMacAddressVLANFilter OBJECT-TYPE
		SYNTAX      INTEGER (0..2147483647)
		MAX-ACCESS  read-write
		STATUS      current
		DESCRIPTION
			"Display mac address table with filter by specific VLAN."
		::= { swhMacAddressTable 11 }

	swhMacAddressPortListFilterRule OBJECT-TYPE
		SYNTAX      INTEGER { all(0), exclude(1), include(2) }
		MAX-ACCESS  read-write
		STATUS      current
		DESCRIPTION
			"The rule for display mac address table with filter by specific port."
		::= { swhMacAddressTable 12 }

	swhMacAddressPortListFilter OBJECT-TYPE
		SYNTAX      DisplayString
		MAX-ACCESS  read-write
		STATUS      current
		DESCRIPTION
			"Display mac address table with filter by specific port."
		::= { swhMacAddressTable 13 }

	swhMacAddressUpdate OBJECT-TYPE
		SYNTAX      INTEGER { normal(0), update(1) }
		MAX-ACCESS  read-write
		STATUS      current
		DESCRIPTION
			"Update mac address table with filter rule."
		::= { swhMacAddressTable 14 }

	swhMacAddressPageSelect OBJECT-TYPE
		SYNTAX      INTEGER (0..2147483647)
		MAX-ACCESS  read-write
		STATUS      current
		DESCRIPTION
			"Display mac address of the page which is selected."
		::= { swhMacAddressTable 15 }

	swhMacAddressCapacity OBJECT-TYPE
		SYNTAX      INTEGER (0..2147483647)
		MAX-ACCESS  read-only
		STATUS      current
		DESCRIPTION
			"Capacity."
		::= { swhMacAddressTable 20 }

	swhMacAddressFree OBJECT-TYPE
		SYNTAX      INTEGER (0..2147483647)
		MAX-ACCESS  read-only
		STATUS      current
		DESCRIPTION
			"Free."
		::= { swhMacAddressTable 21 }

	swhMacAddressUsed OBJECT-TYPE
		SYNTAX      INTEGER (0..2147483647)
		MAX-ACCESS  read-only
		STATUS      current
		DESCRIPTION
			"Used."
		::= { swhMacAddressTable 22 }

	swhMacAddressDynamic OBJECT-TYPE
		SYNTAX      INTEGER (0..2147483647)
		MAX-ACCESS  read-only
		STATUS      current
		DESCRIPTION
			"Dynamic."
		::= { swhMacAddressTable 24 }

	swhMacAddressStatic OBJECT-TYPE
		SYNTAX      INTEGER (0..2147483647)
		MAX-ACCESS  read-only
		STATUS      current
		DESCRIPTION
			"Static."
		::= { swhMacAddressTable 25 }

	swhMacAddressInternal OBJECT-TYPE
		SYNTAX      INTEGER (0..2147483647)
		MAX-ACCESS  read-only
		STATUS      current
		DESCRIPTION
			"Internal."
		::= { swhMacAddressTable 26 }


-- SwitchMonitor(5).MacAddressTable(7).MacTableTable(16)

	swhMacTableTable OBJECT-TYPE
		SYNTAX      SEQUENCE OF SwhMacTableEntry
		MAX-ACCESS  not-accessible
		STATUS      current
		DESCRIPTION
			"Table of mac address."
		::= { swhMacAddressTable 16 }

	-- Table Entry
	swhMacTableEntry OBJECT-TYPE
		SYNTAX      SwhMacTableEntry
		MAX-ACCESS  not-accessible
		STATUS      current
		DESCRIPTION
			"An entry in the table, containing information about mac address table."
		INDEX    { swhMacTableIndex }
		::= { swhMacTableTable 1 }

	SwhMacTableEntry ::=
		SEQUENCE {
			swhMacTableIndex
				INTEGER,
			swhMacTableType
				DisplayString,
			swhMacTableAddr
				MacAddress,
			swhMacTableVID
				INTEGER,
			swhMacTablePort
				DisplayString
		}

	swhMacTableIndex OBJECT-TYPE
		SYNTAX      INTEGER (0..2147483647)
		MAX-ACCESS  not-accessible
		STATUS      current
		DESCRIPTION
			"A unique value for each index."
		::= { swhMacTableEntry 1 }

	swhMacTableAddr OBJECT-TYPE
		SYNTAX      MacAddress
		MAX-ACCESS  read-only
		STATUS      current
		DESCRIPTION
			"MAC address learned."
		::= { swhMacTableEntry 2 }

	swhMacTableVID OBJECT-TYPE
		SYNTAX      INTEGER (1..4094)
		MAX-ACCESS  read-only
		STATUS      current
		DESCRIPTION
			"MAC address learned from which vlan id."
		::= { swhMacTableEntry 3 }

	swhMacTablePort OBJECT-TYPE
		SYNTAX      DisplayString
		MAX-ACCESS  read-only
		STATUS      current
		DESCRIPTION
			"MAC address learned from which port."
		::= { swhMacTableEntry 4 }

	swhMacTableType OBJECT-TYPE
		SYNTAX      DisplayString
		MAX-ACCESS  read-only
		STATUS      current
		DESCRIPTION
			"MAC address learning type."
		::= { swhMacTableEntry 5 }


-- SwitchMonitor(5).RSTPBridgeOverview(10)

	swhRSTPBridgeTable OBJECT-TYPE
		SYNTAX      SEQUENCE OF SwhRSTPBridgeEntry
		MAX-ACCESS  not-accessible
		STATUS      current
		DESCRIPTION
			"Table of RSTP bridge overview."
		::= { swhRSTPBridgeOverview 7 }

	-- Table Entry
	swhRSTPBridgeEntry OBJECT-TYPE
		SYNTAX      SwhRSTPBridgeEntry
		MAX-ACCESS  not-accessible
		STATUS      current
		DESCRIPTION
			"An entry in the table, containing information about RSTP bridge overview."
		INDEX    { swhRSTPBridgeIndex }
		::= { swhRSTPBridgeTable 1 }

	SwhRSTPBridgeEntry ::=
		SEQUENCE {
			swhRSTPBridgeIndex
				INTEGER,
			swhRSTPBridgeBridgeID
				DisplayString,
			swhRSTPBridgeMaxAge
				INTEGER,
			swhRSTPBridgeHelloTime
				INTEGER,
			swhRSTPBridgeFwdDelay
				INTEGER,
			swhRSTPBridgeTopology
				INTEGER,
			swhRSTPBridgeRootID
				DisplayString,
			swhRSTPBridgeRootPort
				DisplayString
		}

	swhRSTPBridgeIndex OBJECT-TYPE
		SYNTAX      INTEGER (0..2147483647)
		MAX-ACCESS  not-accessible
		STATUS      current
		DESCRIPTION
			"A unique value for each index."
		::= { swhRSTPBridgeEntry 1 }

	swhRSTPBridgeBridgeID OBJECT-TYPE
		SYNTAX      DisplayString
		MAX-ACCESS  read-only
		STATUS      current
		DESCRIPTION
			"Bridge ID."
		::= { swhRSTPBridgeEntry 3 }

	swhRSTPBridgeMaxAge OBJECT-TYPE
		SYNTAX      INTEGER
		MAX-ACCESS  read-only
		STATUS      current
		DESCRIPTION
			"Max Age."
		::= { swhRSTPBridgeEntry 4 }

	swhRSTPBridgeHelloTime OBJECT-TYPE
		SYNTAX      INTEGER
		MAX-ACCESS  read-only
		STATUS      current
		DESCRIPTION
			"Hello Time."
		::= { swhRSTPBridgeEntry 5 }

	swhRSTPBridgeFwdDelay OBJECT-TYPE
		SYNTAX      INTEGER
		MAX-ACCESS  read-only
		STATUS      current
		DESCRIPTION
			"Fwd Delay."
		::= { swhRSTPBridgeEntry 6 }

	swhRSTPBridgeTopology OBJECT-TYPE
		SYNTAX      INTEGER { steady(0), changing(1) }
		MAX-ACCESS  read-only
		STATUS      current
		DESCRIPTION
			"Topology."
		::= { swhRSTPBridgeEntry 7 }

	swhRSTPBridgeRootID OBJECT-TYPE
		SYNTAX      DisplayString
		MAX-ACCESS  read-only
		STATUS      current
		DESCRIPTION
			"Root ID."
		::= { swhRSTPBridgeEntry 10 }

	swhRSTPBridgeRootPort OBJECT-TYPE
		SYNTAX      DisplayString
		MAX-ACCESS  read-only
		STATUS      current
		DESCRIPTION
			"Root Port."
		::= { swhRSTPBridgeEntry 13 }


-- SwitchMonitor(5).LLDPStatus(11).LLDPStatusTable(4)

	swhLLDPStatusTable OBJECT-TYPE
		SYNTAX      SEQUENCE OF SwhLLDPStatusEntry
		MAX-ACCESS  not-accessible
		STATUS      current
		DESCRIPTION
			"Table of LLDP status."
		::= { swhLLDPStatus 4 }

	-- Table Entry
	swhLLDPStatusEntry OBJECT-TYPE
		SYNTAX      SwhLLDPStatusEntry
		MAX-ACCESS  not-accessible
		STATUS      current
		DESCRIPTION
			"An entry in the table, containing information about LLDP status."
		INDEX    { swhLLDPStatusIndex }
		::= { swhLLDPStatusTable 1 }

	SwhLLDPStatusEntry ::=
		SEQUENCE {
			swhLLDPStatusIndex
				INTEGER,
			swhLLDPStatusChassisID
				DisplayString,
			swhLLDPStatusRemotePort
				DisplayString,
			swhLLDPStatusSystemName
				DisplayString,
			swhLLDPStatusPortDescription
				DisplayString,
			swhLLDPStatusSystemCapabilities
				DisplayString,
			swhLLDPStatusManagement1Address
				DisplayString,
			swhLLDPStatusManagement2Address
				DisplayString,
			swhLLDPStatusManagement3Address
				DisplayString,
			swhLLDPStatusManagement4Address
				DisplayString,
			swhLLDPStatusManagement5Address
				DisplayString
		}

	swhLLDPStatusIndex OBJECT-TYPE
		SYNTAX      INTEGER (0..2147483647)
		MAX-ACCESS  not-accessible
		STATUS      current
		DESCRIPTION
			"A unique value for each index."
		::= { swhLLDPStatusEntry 1 }

	swhLLDPStatusChassisID OBJECT-TYPE
		SYNTAX      DisplayString
		MAX-ACCESS  read-only
		STATUS      current
		DESCRIPTION
			"Chassis ID."
		::= { swhLLDPStatusEntry 3 }

	swhLLDPStatusRemotePort OBJECT-TYPE
		SYNTAX      DisplayString
		MAX-ACCESS  read-only
		STATUS      current
		DESCRIPTION
			"Remote Port."
		::= { swhLLDPStatusEntry 4 }

	swhLLDPStatusSystemName OBJECT-TYPE
		SYNTAX      DisplayString
		MAX-ACCESS  read-only
		STATUS      current
		DESCRIPTION
			"System Name."
		::= { swhLLDPStatusEntry 5 }

	swhLLDPStatusPortDescription OBJECT-TYPE
		SYNTAX      DisplayString
		MAX-ACCESS  read-only
		STATUS      current
		DESCRIPTION
			"Port Description."
		::= { swhLLDPStatusEntry 6 }

	swhLLDPStatusSystemCapabilities OBJECT-TYPE
		SYNTAX      DisplayString
		MAX-ACCESS  read-only
		STATUS      current
		DESCRIPTION
			"System Capabilities."
		::= { swhLLDPStatusEntry 7 }

	swhLLDPStatusManagement1Address OBJECT-TYPE
		SYNTAX      DisplayString
		MAX-ACCESS  read-only
		STATUS      current
		DESCRIPTION
			"Management 1 Address."
		::= { swhLLDPStatusEntry 8 }

	swhLLDPStatusManagement2Address OBJECT-TYPE
		SYNTAX      DisplayString
		MAX-ACCESS  read-only
		STATUS      current
		DESCRIPTION
			"Management 2 Address."
		::= { swhLLDPStatusEntry 9 }

	swhLLDPStatusManagement3Address OBJECT-TYPE
		SYNTAX      DisplayString
		MAX-ACCESS  read-only
		STATUS      current
		DESCRIPTION
			"Management 3 Address."
		::= { swhLLDPStatusEntry 10 }

	swhLLDPStatusManagement4Address OBJECT-TYPE
		SYNTAX      DisplayString
		MAX-ACCESS  read-only
		STATUS      current
		DESCRIPTION
			"Management 4 Address."
		::= { swhLLDPStatusEntry 11 }

	swhLLDPStatusManagement5Address OBJECT-TYPE
		SYNTAX      DisplayString
		MAX-ACCESS  read-only
		STATUS      current
		DESCRIPTION
			"Management 5 Address."
		::= { swhLLDPStatusEntry 12 }


-- SwitchMonitor(5).RSTPPortStatus(14).RSTPPortStatusTable(1)

	swhRSTPPortStatusTable OBJECT-TYPE
		SYNTAX      SEQUENCE OF SwhRSTPPortStatusEntry
		MAX-ACCESS  not-accessible
		STATUS      current
		DESCRIPTION
			"Table of RSTP port status."
		::= { swhRSTPPortStatus 1 }

	-- Table Entry
	swhRSTPPortStatusEntry OBJECT-TYPE
		SYNTAX      SwhRSTPPortStatusEntry
		MAX-ACCESS  not-accessible
		STATUS      current
		DESCRIPTION
			"An entry in the table, containing information about RSTP port status."
		INDEX    { swhRSTPPortStatusIndex }
		::= { swhRSTPPortStatusTable 1 }

	SwhRSTPPortStatusEntry ::=
		SEQUENCE {
			swhRSTPPortStatusIndex
				INTEGER,
			swhRSTPPortStatusPort
				DisplayString,
			swhRSTPPortStatusPathCost
				INTEGER,
			swhRSTPPortStatusEdgePort
				INTEGER,
			swhRSTPPortStatusP2pPort
				INTEGER,
			swhRSTPPortStatusProtocol
				INTEGER,
			swhRSTPPortStatusRole
				INTEGER,
			swhRSTPPortStatusPortState
				INTEGER
		}

	swhRSTPPortStatusIndex OBJECT-TYPE
		SYNTAX      INTEGER (0..2147483647)
		MAX-ACCESS  not-accessible
		STATUS      current
		DESCRIPTION
			"A unique value for each index."
		::= { swhRSTPPortStatusEntry 1 }

	swhRSTPPortStatusPathCost OBJECT-TYPE
		SYNTAX      INTEGER
		MAX-ACCESS  read-only
		STATUS      current
		DESCRIPTION
			"Path Cost."
		::= { swhRSTPPortStatusEntry 3 }

	swhRSTPPortStatusEdgePort OBJECT-TYPE
		SYNTAX      INTEGER { no(0), yes(1) }
		MAX-ACCESS  read-only
		STATUS      current
		DESCRIPTION
			"Edge Port."
		::= { swhRSTPPortStatusEntry 4 }

	swhRSTPPortStatusP2pPort OBJECT-TYPE
		SYNTAX      INTEGER { no(0), yes(1) }
		MAX-ACCESS  read-only
		STATUS      current
		DESCRIPTION
			"P2p Port."
		::= { swhRSTPPortStatusEntry 5 }

	swhRSTPPortStatusProtocol OBJECT-TYPE
		SYNTAX      INTEGER { rstp(0), stp(1) }
		MAX-ACCESS  read-only
		STATUS      current
		DESCRIPTION
			"Protocol."
		::= { swhRSTPPortStatusEntry 6 }

	swhRSTPPortStatusRole OBJECT-TYPE
		SYNTAX      INTEGER { disable(0), alternate(1), backup(2), root(3), designated(4), non-stp(5) }
		MAX-ACCESS  read-only
		STATUS      current
		DESCRIPTION
			"Role."
		::= { swhRSTPPortStatusEntry 7 }

	swhRSTPPortStatusPortState OBJECT-TYPE
		SYNTAX      INTEGER { disable(0), blocking(1), listening(2), learning(3), forwarding(4), non-stp(5) }
		MAX-ACCESS  read-only
		STATUS      current
		DESCRIPTION
			"Port State."
		::= { swhRSTPPortStatusEntry 8 }

	swhRSTPPortStatusPort OBJECT-TYPE
		SYNTAX      DisplayString
		MAX-ACCESS  read-only
		STATUS      current
		DESCRIPTION
			"Port."
		::= { swhRSTPPortStatusEntry 9 }


-- SwitchMonitor(5).RSTPStatistics(18).RSTPStatisticsTable(1)

	swhRSTPStatisticsTable OBJECT-TYPE
		SYNTAX      SEQUENCE OF SwhRSTPStatisticsEntry
		MAX-ACCESS  not-accessible
		STATUS      current
		DESCRIPTION
			"Table of RSTP statistics."
		::= { swhRSTPStatistics 1 }

	-- Table Entry
	swhRSTPStatisticsEntry OBJECT-TYPE
		SYNTAX      SwhRSTPStatisticsEntry
		MAX-ACCESS  not-accessible
		STATUS      current
		DESCRIPTION
			"An entry in the table, containing information about RSTP statistics."
		INDEX    { swhRSTPStatisticsIndex }
		::= { swhRSTPStatisticsTable 1 }

	SwhRSTPStatisticsEntry ::=
		SEQUENCE {
			swhRSTPStatisticsIndex
				INTEGER,
			swhRSTPStatisticsPort
				DisplayString,
			swhRSTPStatisticsRSTPTransmitted
				Counter32,
			swhRSTPStatisticsSTPTransmitted
				Counter32,
			swhRSTPStatisticsTCNTransmitted
				Counter32,
			swhRSTPStatisticsRSTPReceived
				Counter32,
			swhRSTPStatisticsSTPReceived
				Counter32,
			swhRSTPStatisticsTCNReceived
				Counter32,
			swhRSTPStatisticsIllegalReceived
				Counter32,
			swhRSTPStatisticsUnknownReceived
				Counter32
		}

	swhRSTPStatisticsIndex OBJECT-TYPE
		SYNTAX      INTEGER (0..2147483647)
		MAX-ACCESS  not-accessible
		STATUS      current
		DESCRIPTION
			"A unique value for each index."
		::= { swhRSTPStatisticsEntry 1 }

	swhRSTPStatisticsRSTPTransmitted OBJECT-TYPE
		SYNTAX      Counter32
		MAX-ACCESS  read-only
		STATUS      current
		DESCRIPTION
			"RSTP Transmitted."
		::= { swhRSTPStatisticsEntry 3 }

	swhRSTPStatisticsSTPTransmitted OBJECT-TYPE
		SYNTAX      Counter32
		MAX-ACCESS  read-only
		STATUS      current
		DESCRIPTION
			"STP Transmitted."
		::= { swhRSTPStatisticsEntry 5 }

	swhRSTPStatisticsTCNTransmitted OBJECT-TYPE
		SYNTAX      Counter32
		MAX-ACCESS  read-only
		STATUS      current
		DESCRIPTION
			"TCN Transmitted."
		::= { swhRSTPStatisticsEntry 7 }

	swhRSTPStatisticsRSTPReceived OBJECT-TYPE
		SYNTAX      Counter32
		MAX-ACCESS  read-only
		STATUS      current
		DESCRIPTION
			"RSTP Received."
		::= { swhRSTPStatisticsEntry 9 }

	swhRSTPStatisticsSTPReceived OBJECT-TYPE
		SYNTAX      Counter32
		MAX-ACCESS  read-only
		STATUS      current
		DESCRIPTION
			"STP Received."
		::= { swhRSTPStatisticsEntry 11 }

	swhRSTPStatisticsTCNReceived OBJECT-TYPE
		SYNTAX      Counter32
		MAX-ACCESS  read-only
		STATUS      current
		DESCRIPTION
			"TCN Received."
		::= { swhRSTPStatisticsEntry 13 }

	swhRSTPStatisticsIllegalReceived OBJECT-TYPE
		SYNTAX      Counter32
		MAX-ACCESS  read-only
		STATUS      current
		DESCRIPTION
			"Illegal Received."
		::= { swhRSTPStatisticsEntry 15 }

	swhRSTPStatisticsUnknownReceived OBJECT-TYPE
		SYNTAX      Counter32
		MAX-ACCESS  read-only
		STATUS      current
		DESCRIPTION
			"Unknown Received."
		::= { swhRSTPStatisticsEntry 17 }

	swhRSTPStatisticsPort OBJECT-TYPE
		SYNTAX      DisplayString
		MAX-ACCESS  read-only
		STATUS      current
		DESCRIPTION
			"Port."
		::= { swhRSTPStatisticsEntry 18 }


-- SwitchMonitor(5).LACPPortStatus(22)

	swhLACPPortStatusTable OBJECT-TYPE
		SYNTAX      SEQUENCE OF SwhLACPPortStatusEntry
		MAX-ACCESS  not-accessible
		STATUS      current
		DESCRIPTION
			"Table of LACP port status."
		::= { swhLACPPortStatus 1 }

	-- Table Entry
	swhLACPPortStatusEntry OBJECT-TYPE
		SYNTAX      SwhLACPPortStatusEntry
		MAX-ACCESS  not-accessible
		STATUS      current
		DESCRIPTION
			"An entry in the table, containing information about LACP port status."
		INDEX    { swhLACPPortStatusIndex }
		::= { swhLACPPortStatusTable 1 }

	SwhLACPPortStatusEntry ::=
		SEQUENCE {
			swhLACPPortStatusIndex
				INTEGER,
			swhLACPPortStatusLACPOperationalState
				INTEGER,
			swhLACPPortStatusKey
				INTEGER,
			swhLACPPortStatusAggrID
				INTEGER,
			swhLACPPortStatusPartnerID
				DisplayString,
			swhLACPPortStatusPartnerPort
				INTEGER
		}

	swhLACPPortStatusIndex OBJECT-TYPE
		SYNTAX      INTEGER (0..2147483647)
		MAX-ACCESS  not-accessible
		STATUS      current
		DESCRIPTION
			"A unique value for each index."
		::= { swhLACPPortStatusEntry 1 }

	swhLACPPortStatusPartnerPort OBJECT-TYPE
		SYNTAX      INTEGER
		MAX-ACCESS  read-only
		STATUS      current
		DESCRIPTION
			"Partner Port."
		::= { swhLACPPortStatusEntry 3 }

	swhLACPPortStatusLACPOperationalState OBJECT-TYPE
		SYNTAX      INTEGER { no(0), yes(1) }
		MAX-ACCESS  read-only
		STATUS      current
		DESCRIPTION
			"LACP Operational State."
		::= { swhLACPPortStatusEntry 4 }

	swhLACPPortStatusKey OBJECT-TYPE
		SYNTAX      INTEGER
		MAX-ACCESS  read-only
		STATUS      current
		DESCRIPTION
			"Key."
		::= { swhLACPPortStatusEntry 5 }

	swhLACPPortStatusAggrID OBJECT-TYPE
		SYNTAX      INTEGER
		MAX-ACCESS  read-only
		STATUS      current
		DESCRIPTION
			"Aggr ID."
		::= { swhLACPPortStatusEntry 6 }

	swhLACPPortStatusPartnerID OBJECT-TYPE
		SYNTAX      DisplayString
		MAX-ACCESS  read-only
		STATUS      current
		DESCRIPTION
			"Partner ID."
		::= { swhLACPPortStatusEntry 7 }


-- SwitchMonitor(5).LACPStatistics(24)

	swhLACPStatisticsTable OBJECT-TYPE
		SYNTAX      SEQUENCE OF SwhLACPStatisticsEntry
		MAX-ACCESS  not-accessible
		STATUS      current
		DESCRIPTION
			"Table of LACP statistics."
		::= { swhLACPStatistics 1 }

	swhLACPStatisticsClearCountersOfAllPort OBJECT-TYPE
		SYNTAX      INTEGER { normal(0), clear(1) }
		MAX-ACCESS  read-write
		STATUS      current
		DESCRIPTION
			"Clear counters of all port."
		::= { swhLACPStatistics 2 }

	-- Table Entry
	swhLACPStatisticsEntry OBJECT-TYPE
		SYNTAX      SwhLACPStatisticsEntry
		MAX-ACCESS  not-accessible
		STATUS      current
		DESCRIPTION
			"An entry in the table, containing information about LACP statistics."
		INDEX    { swhLACPStatisticsIndex }
		::= { swhLACPStatisticsTable 1 }

	SwhLACPStatisticsEntry ::=
		SEQUENCE {
			swhLACPStatisticsIndex
				INTEGER,
			swhLACPStatisticsLACPTransmitted
				Counter32,
			swhLACPStatisticsLACPReceived
				Counter32,
			swhLACPStatisticsIllegalReceived
				Counter32,
			swhLACPStatisticsUnknownReceived
				Counter32,
			swhLACPStatisticsClear
				INTEGER
		}

	swhLACPStatisticsIndex OBJECT-TYPE
		SYNTAX      INTEGER (0..2147483647)
		MAX-ACCESS  not-accessible
		STATUS      current
		DESCRIPTION
			"A unique value for each index."
		::= { swhLACPStatisticsEntry 1 }

	swhLACPStatisticsLACPTransmitted OBJECT-TYPE
		SYNTAX      Counter32
		MAX-ACCESS  read-only
		STATUS      current
		DESCRIPTION
			"LACP Transmitted."
		::= { swhLACPStatisticsEntry 3 }

	swhLACPStatisticsLACPReceived OBJECT-TYPE
		SYNTAX      Counter32
		MAX-ACCESS  read-only
		STATUS      current
		DESCRIPTION
			"LACP Received."
		::= { swhLACPStatisticsEntry 9 }

	swhLACPStatisticsIllegalReceived OBJECT-TYPE
		SYNTAX      Counter32
		MAX-ACCESS  read-only
		STATUS      current
		DESCRIPTION
			"Illegal Received."
		::= { swhLACPStatisticsEntry 15 }

	swhLACPStatisticsUnknownReceived OBJECT-TYPE
		SYNTAX      Counter32
		MAX-ACCESS  read-only
		STATUS      current
		DESCRIPTION
			"Unknown Received."
		::= { swhLACPStatisticsEntry 17 }

	swhLACPStatisticsClear OBJECT-TYPE
		SYNTAX      INTEGER { normal(0), clear(1) }
		MAX-ACCESS  read-write
		STATUS      current
		DESCRIPTION
			"Clear counters of this module."
		::= { swhLACPStatisticsEntry 19 }


-- SwitchMonitor(5).Layer2ProtocolTunnelStatus(25)

	swhL2PTStatusClearCountersOfAllPort OBJECT-TYPE
		SYNTAX      INTEGER { normal(0), clear(1) }
		MAX-ACCESS  read-write
		STATUS      current
		DESCRIPTION
			"Clear all layer 2 protocol tunnel status."
		::= { swhLayer2ProtocolTunnelStatus 2 }

	swhL2PTStatusPortSelect OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Display L2PT counters of the port which is selected."
		::= { swhLayer2ProtocolTunnelStatus 3 }

	swhL2PTStatusPortClear OBJECT-TYPE
		SYNTAX      INTEGER { normal(0), clear(1) }
		MAX-ACCESS  read-write
		STATUS      current
		DESCRIPTION
			"Clear this port counters."
		::= { swhLayer2ProtocolTunnelStatus 4 }


-- SwitchMonitor(5).Layer2ProtocolTunnelStatus(25).L2PTStatusTable(5)

	swhL2PTStatusTable OBJECT-TYPE
		SYNTAX      SEQUENCE OF SwhL2PTStatusEntry
		MAX-ACCESS  not-accessible
		STATUS      current
		DESCRIPTION
			"Table of L2PT counters."
		::= { swhLayer2ProtocolTunnelStatus 5 }

	-- Table Entry
	swhL2PTStatusEntry OBJECT-TYPE
		SYNTAX      SwhL2PTStatusEntry
		MAX-ACCESS  not-accessible
		STATUS      current
		DESCRIPTION
			"An entry in the table, containing information about L2PT counters."
		INDEX    { swhL2PTStatusIndex }
		::= { swhL2PTStatusTable 1 }

	SwhL2PTStatusEntry ::=
		SEQUENCE {
			swhL2PTStatusIndex
				INTEGER,
			swhL2PTStatusCounterName
				DisplayString,
			swhL2PTStatusState
				INTEGER,
			swhL2PTStatusEncapsulationCounters
				Counter32,
			swhL2PTStatusDecapsulationCounters
				Counter32
		}

	swhL2PTStatusIndex OBJECT-TYPE
		SYNTAX      INTEGER (0..2147483647)
		MAX-ACCESS  not-accessible
		STATUS      current
		DESCRIPTION
			"A unique value for each index."
		::= { swhL2PTStatusEntry 1 }

	swhL2PTStatusCounterName OBJECT-TYPE
		SYNTAX      DisplayString
		MAX-ACCESS  read-only
		STATUS      current
		DESCRIPTION
			"L2PT Counter Name."
		::= { swhL2PTStatusEntry 2 }

	swhL2PTStatusState OBJECT-TYPE
		SYNTAX      INTEGER { disable(0), enable(1) }
		MAX-ACCESS  read-only
		STATUS      current
		DESCRIPTION
			"State."
		::= { swhL2PTStatusEntry 3 }

	swhL2PTStatusEncapsulationCounters OBJECT-TYPE
		SYNTAX      Counter32
		MAX-ACCESS  read-only
		STATUS      current
		DESCRIPTION
			"Encapsulation Counters."
		::= { swhL2PTStatusEntry 4 }

	swhL2PTStatusDecapsulationCounters OBJECT-TYPE
		SYNTAX      Counter32
		MAX-ACCESS  read-only
		STATUS      current
		DESCRIPTION
			"Decapsulation Counters."
		::= { swhL2PTStatusEntry 5 }


-- SwitchMonitor(5).IGMPStatus(26)

	swhIGMPStatusTable OBJECT-TYPE
		SYNTAX      SEQUENCE OF SwhIGMPStatusEntry
		MAX-ACCESS  not-accessible
		STATUS      current
		DESCRIPTION
			"Table of IGMP status."
		::= { swhIGMPStatus 2 }

	-- Table Entry
	swhIGMPStatusEntry OBJECT-TYPE
		SYNTAX      SwhIGMPStatusEntry
		MAX-ACCESS  not-accessible
		STATUS      current
		DESCRIPTION
			"An entry in the table, containing information about IGMP status."
		INDEX    { swhIGMPStatusIndex }
		::= { swhIGMPStatusTable 1 }

	SwhIGMPStatusEntry ::=
		SEQUENCE {
			swhIGMPStatusIndex
				INTEGER,
			swhIGMPStatusVLANID
				INTEGER,
			swhIGMPStatusIsMVRVLANID
				INTEGER,
			swhIGMPStatusQuerier
				INTEGER,
			swhIGMPStatusQueriesTransmitted
				INTEGER,
			swhIGMPStatusQueriesReceived
				INTEGER,
			swhIGMPStatusV1Reports
				INTEGER,
			swhIGMPStatusV2Reports
				INTEGER,
			swhIGMPStatusV3Reports
				INTEGER,
			swhIGMPStatusV2Leaves
				INTEGER
		}

	swhIGMPStatusIndex OBJECT-TYPE
		SYNTAX      INTEGER (0..2147483647)
		MAX-ACCESS  not-accessible
		STATUS      current
		DESCRIPTION
			"A unique value for each index."
		::= { swhIGMPStatusEntry 1 }

	swhIGMPStatusVLANID OBJECT-TYPE
		SYNTAX      INTEGER (1..4094)
		MAX-ACCESS  read-only
		STATUS      current
		DESCRIPTION
			"VLAN ID. (1-4094)"
		::= { swhIGMPStatusEntry 3 }

	swhIGMPStatusQuerier OBJECT-TYPE
		SYNTAX      INTEGER { idle(0), active(1) }
		MAX-ACCESS  read-only
		STATUS      current
		DESCRIPTION
			"Querier."
		::= { swhIGMPStatusEntry 5 }

	swhIGMPStatusQueriesTransmitted OBJECT-TYPE
		SYNTAX      INTEGER
		MAX-ACCESS  read-only
		STATUS      current
		DESCRIPTION
			"Queries Transmitted."
		::= { swhIGMPStatusEntry 7 }

	swhIGMPStatusQueriesReceived OBJECT-TYPE
		SYNTAX      INTEGER
		MAX-ACCESS  read-only
		STATUS      current
		DESCRIPTION
			"Queries Received."
		::= { swhIGMPStatusEntry 9 }

	swhIGMPStatusV1Reports OBJECT-TYPE
		SYNTAX      INTEGER
		MAX-ACCESS  read-only
		STATUS      current
		DESCRIPTION
			"V1 Reports."
		::= { swhIGMPStatusEntry 11 }

	swhIGMPStatusV2Reports OBJECT-TYPE
		SYNTAX      INTEGER
		MAX-ACCESS  read-only
		STATUS      current
		DESCRIPTION
			"V2 Reports."
		::= { swhIGMPStatusEntry 13 }

	swhIGMPStatusV3Reports OBJECT-TYPE
		SYNTAX      INTEGER
		MAX-ACCESS  read-only
		STATUS      current
		DESCRIPTION
			"V3 Reports."
		::= { swhIGMPStatusEntry 15 }

	swhIGMPStatusV2Leaves OBJECT-TYPE
		SYNTAX      INTEGER
		MAX-ACCESS  read-only
		STATUS      current
		DESCRIPTION
			"V2 Leaves."
		::= { swhIGMPStatusEntry 17 }

	swhIGMPStatusIsMVRVLANID OBJECT-TYPE
		SYNTAX      INTEGER { b(0), v(1) }
		MAX-ACCESS  read-only
		STATUS      current
		DESCRIPTION
			"Is it MVR VLAN ID? (b : no, v : yes)"
		::= { swhIGMPStatusEntry 18 }


-- SwitchMonitor(5).MLDStatus(27)

	swhMLDStatusTable OBJECT-TYPE
		SYNTAX      SEQUENCE OF SwhMLDStatusEntry
		MAX-ACCESS  not-accessible
		STATUS      current
		DESCRIPTION
			"Table of MLD status."
		::= { swhMLDStatus 2 }

	-- Table Entry
	swhMLDStatusEntry OBJECT-TYPE
		SYNTAX      SwhMLDStatusEntry
		MAX-ACCESS  not-accessible
		STATUS      current
		DESCRIPTION
			"An entry in the table, containing information about MLD status."
		INDEX    { swhMLDStatusIndex }
		::= { swhMLDStatusTable 1 }

	SwhMLDStatusEntry ::=
		SEQUENCE {
			swhMLDStatusIndex
				INTEGER,
			swhMLDStatusVLANID
				INTEGER,
			swhMLDStatusIsMVRVLANID
				INTEGER,
			swhMLDStatusQuerier
				INTEGER,
			swhMLDStatusQueriesTransmitted
				INTEGER,
			swhMLDStatusQueriesReceived
				INTEGER,
			swhMLDStatusV1Reports
				INTEGER,
			swhMLDStatusV2Reports
				INTEGER,
			swhMLDStatusDone
				INTEGER
		}

	swhMLDStatusIndex OBJECT-TYPE
		SYNTAX      INTEGER (0..2147483647)
		MAX-ACCESS  not-accessible
		STATUS      current
		DESCRIPTION
			"A unique value for each index."
		::= { swhMLDStatusEntry 1 }

	swhMLDStatusVLANID OBJECT-TYPE
		SYNTAX      INTEGER (1..4094)
		MAX-ACCESS  read-only
		STATUS      current
		DESCRIPTION
			"VLAN ID. (1-4094)"
		::= { swhMLDStatusEntry 3 }

	swhMLDStatusQuerier OBJECT-TYPE
		SYNTAX      INTEGER { idle(0), active(1) }
		MAX-ACCESS  read-only
		STATUS      current
		DESCRIPTION
			"Querier."
		::= { swhMLDStatusEntry 5 }

	swhMLDStatusQueriesTransmitted OBJECT-TYPE
		SYNTAX      INTEGER
		MAX-ACCESS  read-only
		STATUS      current
		DESCRIPTION
			"Queries Transmitted."
		::= { swhMLDStatusEntry 7 }

	swhMLDStatusQueriesReceived OBJECT-TYPE
		SYNTAX      INTEGER
		MAX-ACCESS  read-only
		STATUS      current
		DESCRIPTION
			"Queries Received."
		::= { swhMLDStatusEntry 9 }

	swhMLDStatusV1Reports OBJECT-TYPE
		SYNTAX      INTEGER
		MAX-ACCESS  read-only
		STATUS      current
		DESCRIPTION
			"V1 Reports."
		::= { swhMLDStatusEntry 11 }

	swhMLDStatusV2Reports OBJECT-TYPE
		SYNTAX      INTEGER
		MAX-ACCESS  read-only
		STATUS      current
		DESCRIPTION
			"V2 Reports."
		::= { swhMLDStatusEntry 13 }

	swhMLDStatusDone OBJECT-TYPE
		SYNTAX      INTEGER
		MAX-ACCESS  read-only
		STATUS      current
		DESCRIPTION
			"Done."
		::= { swhMLDStatusEntry 15 }

	swhMLDStatusIsMVRVLANID OBJECT-TYPE
		SYNTAX      INTEGER { b(0), v(1) }
		MAX-ACCESS  read-only
		STATUS      current
		DESCRIPTION
			"Is it MVR VLAN ID? (b : no, v : yes)"
		::= { swhMLDStatusEntry 16 }


-- SwitchMonitor(5).IGMPGroupTable(28)

	swhIGMPState OBJECT-TYPE
		SYNTAX      INTEGER { disable(0), enable(1) }
		MAX-ACCESS  read-only
		STATUS      current
		DESCRIPTION
			"State."
		::= { swhIGMPGroupTable 1 }


-- SwitchMonitor(5).IGMPGroupTable(28).IGMPTableTable(2)

	swhIGMPTableTable OBJECT-TYPE
		SYNTAX      SEQUENCE OF SwhIGMPTableEntry
		MAX-ACCESS  not-accessible
		STATUS      current
		DESCRIPTION
			"Table of IGMP group."
		::= { swhIGMPGroupTable 2 }

	-- Table Entry
	swhIGMPTableEntry OBJECT-TYPE
		SYNTAX      SwhIGMPTableEntry
		MAX-ACCESS  not-accessible
		STATUS      current
		DESCRIPTION
			"An entry in the table, containing information about multicast groups, port members, queries, reports, time of aging out."
		INDEX    { swhIGMPGroupTableIndex }
		::= { swhIGMPTableTable 1 }

	SwhIGMPTableEntry ::=
		SEQUENCE {
			swhIGMPGroupTableIndex
				INTEGER,
			swhIGMPGroupTableVID
				INTEGER,
			swhIGMPGroupTableIsMVRVID
				INTEGER,
			swhIGMPGroupTableGroup
				DisplayString,
			swhIGMPGroupTablePort
				DisplayString,
			swhIGMPGroupTableLastReporter
				DisplayString,
			swhIGMPGroupTableQueryResponse
				DisplayString,
			swhIGMPGroupTableReportCount
				INTEGER,
			swhIGMPGroupTableLifeTime
				DisplayString
		}

	swhIGMPGroupTableIndex OBJECT-TYPE
		SYNTAX      INTEGER (0..2147483647)
		MAX-ACCESS  not-accessible
		STATUS      current
		DESCRIPTION
			"A unique value for each index."
		::= { swhIGMPTableEntry 1 }

	swhIGMPGroupTableGroup OBJECT-TYPE
		SYNTAX      DisplayString
		MAX-ACCESS  read-only
		STATUS      current
		DESCRIPTION
			"Group."
		::= { swhIGMPTableEntry 3 }

	swhIGMPGroupTablePort OBJECT-TYPE
		SYNTAX      DisplayString
		MAX-ACCESS  read-only
		STATUS      current
		DESCRIPTION
			"Port Number."
		::= { swhIGMPTableEntry 4 }

	swhIGMPGroupTableIsMVRVID OBJECT-TYPE
		SYNTAX      INTEGER { b(0), v(1) }
		MAX-ACCESS  read-only
		STATUS      current
		DESCRIPTION
			"Is it MVR VLAN ID? (b : no, v : yes)"
		::= { swhIGMPTableEntry 53 }

	swhIGMPGroupTableVID OBJECT-TYPE
		SYNTAX      INTEGER (1..4094)
		MAX-ACCESS  read-only
		STATUS      current
		DESCRIPTION
			"VLAN ID. (1-4094)"
		::= { swhIGMPTableEntry 60 }

	swhIGMPGroupTableLastReporter OBJECT-TYPE
		SYNTAX      DisplayString
		MAX-ACCESS  read-only
		STATUS      current
		DESCRIPTION
			"Last Reporter."
		::= { swhIGMPTableEntry 67 }

	swhIGMPGroupTableQueryResponse OBJECT-TYPE
		SYNTAX      DisplayString
		MAX-ACCESS  read-only
		STATUS      current
		DESCRIPTION
			"Query Response."
		::= { swhIGMPTableEntry 68 }

	swhIGMPGroupTableReportCount OBJECT-TYPE
		SYNTAX      INTEGER (0..2147483647)
		MAX-ACCESS  read-only
		STATUS      current
		DESCRIPTION
			"Report Count."
		::= { swhIGMPTableEntry 69 }

	swhIGMPGroupTableLifeTime OBJECT-TYPE
		SYNTAX      DisplayString
		MAX-ACCESS  read-only
		STATUS      current
		DESCRIPTION
			"Life Time."
		::= { swhIGMPTableEntry 70 }


-- SwitchMonitor(5).MLDGroupTable(29)

	swhMLDState OBJECT-TYPE
		SYNTAX      INTEGER { disable(0), enable(1) }
		MAX-ACCESS  read-only
		STATUS      current
		DESCRIPTION
			"State."
		::= { swhMLDGroupTable 1 }


-- SwitchMonitor(5).MLDGroupTable(29).MLDTableTable(2)

	swhMLDTableTable OBJECT-TYPE
		SYNTAX      SEQUENCE OF SwhMLDTableEntry
		MAX-ACCESS  not-accessible
		STATUS      current
		DESCRIPTION
			"Table of MLD group."
		::= { swhMLDGroupTable 2 }

	-- Table Entry
	swhMLDTableEntry OBJECT-TYPE
		SYNTAX      SwhMLDTableEntry
		MAX-ACCESS  not-accessible
		STATUS      current
		DESCRIPTION
			"An entry in the table, containing information about multicast groups, port members, queries, reports, time of aging out."
		INDEX    { swhMLDGroupTableIndex }
		::= { swhMLDTableTable 1 }

	SwhMLDTableEntry ::=
		SEQUENCE {
			swhMLDGroupTableIndex
				INTEGER,
			swhMLDGroupTableVID
				INTEGER,
			swhMLDGroupTableIsMVRVID
				INTEGER,
			swhMLDGroupTableGroup
				DisplayString,
			swhMLDGroupTablePort
				DisplayString,
			swhMLDGroupTableLastReporter
				DisplayString,
			swhMLDGroupTableQueryResponse
				DisplayString,
			swhMLDGroupTableReportCount
				INTEGER,
			swhMLDGroupTableLifeTime
				DisplayString
		}

	swhMLDGroupTableIndex OBJECT-TYPE
		SYNTAX      INTEGER (0..2147483647)
		MAX-ACCESS  not-accessible
		STATUS      current
		DESCRIPTION
			"A unique value for each index."
		::= { swhMLDTableEntry 1 }

	swhMLDGroupTableGroup OBJECT-TYPE
		SYNTAX      DisplayString
		MAX-ACCESS  read-only
		STATUS      current
		DESCRIPTION
			"Group."
		::= { swhMLDTableEntry 3 }

	swhMLDGroupTablePort OBJECT-TYPE
		SYNTAX      DisplayString
		MAX-ACCESS  read-only
		STATUS      current
		DESCRIPTION
			"Port Number."
		::= { swhMLDTableEntry 4 }

	swhMLDGroupTableIsMVRVID OBJECT-TYPE
		SYNTAX      INTEGER { b(0), v(1) }
		MAX-ACCESS  read-only
		STATUS      current
		DESCRIPTION
			"Is it MVR VLAN ID? (b : no, v : yes)"
		::= { swhMLDTableEntry 53 }

	swhMLDGroupTableVID OBJECT-TYPE
		SYNTAX      INTEGER (1..4094)
		MAX-ACCESS  read-only
		STATUS      current
		DESCRIPTION
			"VLAN ID. (1-4094)"
		::= { swhMLDTableEntry 60 }

	swhMLDGroupTableLastReporter OBJECT-TYPE
		SYNTAX      DisplayString
		MAX-ACCESS  read-only
		STATUS      current
		DESCRIPTION
			"Last Reporter."
		::= { swhMLDTableEntry 67 }

	swhMLDGroupTableQueryResponse OBJECT-TYPE
		SYNTAX      DisplayString
		MAX-ACCESS  read-only
		STATUS      current
		DESCRIPTION
			"Query Response."
		::= { swhMLDTableEntry 68 }

	swhMLDGroupTableReportCount OBJECT-TYPE
		SYNTAX      INTEGER (0..2147483647)
		MAX-ACCESS  read-only
		STATUS      current
		DESCRIPTION
			"Report Count."
		::= { swhMLDTableEntry 69 }

	swhMLDGroupTableLifeTime OBJECT-TYPE
		SYNTAX      DisplayString
		MAX-ACCESS  read-only
		STATUS      current
		DESCRIPTION
			"Life Time."
		::= { swhMLDTableEntry 70 }


-- SwitchMonitor(5).8021XPortStatus(32)

	swh8021XPortStatusTable OBJECT-TYPE
		SYNTAX      SEQUENCE OF Swh8021XPortStatusEntry
		MAX-ACCESS  not-accessible
		STATUS      current
		DESCRIPTION
			"Table of 802.1X port status."
		::= { swh8021XPortStatus 1 }

	-- Table Entry
	swh8021XPortStatusEntry OBJECT-TYPE
		SYNTAX      Swh8021XPortStatusEntry
		MAX-ACCESS  not-accessible
		STATUS      current
		DESCRIPTION
			"An entry in the table, containing information about 802.1X port status."
		INDEX    { swh8021XPortStatusIndex }
		::= { swh8021XPortStatusTable 1 }

	Swh8021XPortStatusEntry ::=
		SEQUENCE {
			swh8021XPortStatusIndex
				INTEGER,
			swh8021XPortStatusState
				INTEGER,
			swh8021XPortStatusLastSource
				DisplayString,
			swh8021XPortStatusLastID
				DisplayString,
			swh8021XPortStatusAssignedVLAN
				DisplayString
		}

	swh8021XPortStatusIndex OBJECT-TYPE
		SYNTAX      INTEGER (0..2147483647)
		MAX-ACCESS  not-accessible
		STATUS      current
		DESCRIPTION
			"A unique value for each index."
		::= { swh8021XPortStatusEntry 1 }

	swh8021XPortStatusState OBJECT-TYPE
		SYNTAX      INTEGER { linkdown(0), authorized(1), unauthorized(2), disabled(3) }
		MAX-ACCESS  read-only
		STATUS      current
		DESCRIPTION
			"State."
		::= { swh8021XPortStatusEntry 3 }

	swh8021XPortStatusLastSource OBJECT-TYPE
		SYNTAX      DisplayString
		MAX-ACCESS  read-only
		STATUS      current
		DESCRIPTION
			"Last Source."
		::= { swh8021XPortStatusEntry 5 }

	swh8021XPortStatusLastID OBJECT-TYPE
		SYNTAX      DisplayString
		MAX-ACCESS  read-only
		STATUS      current
		DESCRIPTION
			"Last ID."
		::= { swh8021XPortStatusEntry 7 }

	swh8021XPortStatusAssignedVLAN OBJECT-TYPE
		SYNTAX      DisplayString
		MAX-ACCESS  read-only
		STATUS      current
		DESCRIPTION
			"Assigned VLAN."
		::= { swh8021XPortStatusEntry 9 }


-- SwitchMonitor(5).8021XStatistics(33)

	swh8021XStatisticsTable OBJECT-TYPE
		SYNTAX      SEQUENCE OF Swh8021XStatisticsEntry
		MAX-ACCESS  not-accessible
		STATUS      current
		DESCRIPTION
			"Table of 802.1X statistics."
		::= { swh8021XStatistics 1 }

	swh8021XStatisticsClearCountersOfAllPort OBJECT-TYPE
		SYNTAX      INTEGER { normal(0), clear(1) }
		MAX-ACCESS  read-write
		STATUS      current
		DESCRIPTION
			"Clear counters of all port."
		::= { swh8021XStatistics 2 }

	-- Table Entry
	swh8021XStatisticsEntry OBJECT-TYPE
		SYNTAX      Swh8021XStatisticsEntry
		MAX-ACCESS  not-accessible
		STATUS      current
		DESCRIPTION
			"An entry in the table, containing information about 802.1X statistics."
		INDEX    { swh8021XStatisticsIndex }
		::= { swh8021XStatisticsTable 1 }

	Swh8021XStatisticsEntry ::=
		SEQUENCE {
			swh8021XStatisticsIndex
				INTEGER,
			swh8021XStatisticsRxTotal
				Counter32,
			swh8021XStatisticsRxResponseID
				Counter32,
			swh8021XStatisticsRxResponse
				Counter32,
			swh8021XStatisticsRxStart
				Counter32,
			swh8021XStatisticsRxLogoff
				Counter32,
			swh8021XStatisticsRxInvalidType
				Counter32,
			swh8021XStatisticsRxInvalidLength
				Counter32,
			swh8021XStatisticsRxAccessChallenges
				Counter32,
			swh8021XStatisticsRxOtherRequests
				Counter32,
			swh8021XStatisticsRxAuthSuccesses
				Counter32,
			swh8021XStatisticsRxAuthFailures
				Counter32,
			swh8021XStatisticsTxTotal
				Counter32,
			swh8021XStatisticsTxRequestID
				Counter32,
			swh8021XStatisticsTxRequest
				Counter32,
			swh8021XStatisticsTxResponses
				Counter32,
			swh8021XStatisticsClear
				INTEGER
		}

	swh8021XStatisticsIndex OBJECT-TYPE
		SYNTAX      INTEGER (0..2147483647)
		MAX-ACCESS  not-accessible
		STATUS      current
		DESCRIPTION
			"A unique value for each index."
		::= { swh8021XStatisticsEntry 1 }

	swh8021XStatisticsRxTotal OBJECT-TYPE
		SYNTAX      Counter32
		MAX-ACCESS  read-only
		STATUS      current
		DESCRIPTION
			"Rx Total."
		::= { swh8021XStatisticsEntry 2 }

	swh8021XStatisticsRxResponseID OBJECT-TYPE
		SYNTAX      Counter32
		MAX-ACCESS  read-only
		STATUS      current
		DESCRIPTION
			"Rx Response ID."
		::= { swh8021XStatisticsEntry 3 }

	swh8021XStatisticsRxResponse OBJECT-TYPE
		SYNTAX      Counter32
		MAX-ACCESS  read-only
		STATUS      current
		DESCRIPTION
			"Rx Response."
		::= { swh8021XStatisticsEntry 4 }

	swh8021XStatisticsRxStart OBJECT-TYPE
		SYNTAX      Counter32
		MAX-ACCESS  read-only
		STATUS      current
		DESCRIPTION
			"Rx Start."
		::= { swh8021XStatisticsEntry 5 }

	swh8021XStatisticsRxLogoff OBJECT-TYPE
		SYNTAX      Counter32
		MAX-ACCESS  read-only
		STATUS      current
		DESCRIPTION
			"Rx Logoff."
		::= { swh8021XStatisticsEntry 6 }

	swh8021XStatisticsRxInvalidType OBJECT-TYPE
		SYNTAX      Counter32
		MAX-ACCESS  read-only
		STATUS      current
		DESCRIPTION
			"Rx Invalid Type."
		::= { swh8021XStatisticsEntry 7 }

	swh8021XStatisticsRxInvalidLength OBJECT-TYPE
		SYNTAX      Counter32
		MAX-ACCESS  read-only
		STATUS      current
		DESCRIPTION
			"Rx Invalid Length."
		::= { swh8021XStatisticsEntry 8 }

	swh8021XStatisticsRxAccessChallenges OBJECT-TYPE
		SYNTAX      Counter32
		MAX-ACCESS  read-only
		STATUS      current
		DESCRIPTION
			"Rx Access Challenges."
		::= { swh8021XStatisticsEntry 9 }

	swh8021XStatisticsRxOtherRequests OBJECT-TYPE
		SYNTAX      Counter32
		MAX-ACCESS  read-only
		STATUS      current
		DESCRIPTION
			"Rx Other Requests."
		::= { swh8021XStatisticsEntry 10 }

	swh8021XStatisticsRxAuthSuccesses OBJECT-TYPE
		SYNTAX      Counter32
		MAX-ACCESS  read-only
		STATUS      current
		DESCRIPTION
			"Rx Auth Successes."
		::= { swh8021XStatisticsEntry 11 }

	swh8021XStatisticsRxAuthFailures OBJECT-TYPE
		SYNTAX      Counter32
		MAX-ACCESS  read-only
		STATUS      current
		DESCRIPTION
			"Rx Auth Failures."
		::= { swh8021XStatisticsEntry 12 }

	swh8021XStatisticsTxTotal OBJECT-TYPE
		SYNTAX      Counter32
		MAX-ACCESS  read-only
		STATUS      current
		DESCRIPTION
			"Tx Total."
		::= { swh8021XStatisticsEntry 13 }

	swh8021XStatisticsTxRequestID OBJECT-TYPE
		SYNTAX      Counter32
		MAX-ACCESS  read-only
		STATUS      current
		DESCRIPTION
			"Tx Request ID."
		::= { swh8021XStatisticsEntry 14 }

	swh8021XStatisticsTxRequest OBJECT-TYPE
		SYNTAX      Counter32
		MAX-ACCESS  read-only
		STATUS      current
		DESCRIPTION
			"Tx Request."
		::= { swh8021XStatisticsEntry 15 }

	swh8021XStatisticsTxResponses OBJECT-TYPE
		SYNTAX      Counter32
		MAX-ACCESS  read-only
		STATUS      current
		DESCRIPTION
			"Tx Responses."
		::= { swh8021XStatisticsEntry 16 }

	swh8021XStatisticsClear OBJECT-TYPE
		SYNTAX      INTEGER { normal(0), clear(1) }
		MAX-ACCESS  read-write
		STATUS      current
		DESCRIPTION
			"Clear counters of this module."
		::= { swh8021XStatisticsEntry 17 }


-- SwitchMonitor(5).SFPInformation(34)

	swhSFPPortInfo
		OBJECT IDENTIFIER ::= { swhSFPInformation 1 }

	swhSFPPortState
		OBJECT IDENTIFIER ::= { swhSFPInformation 2 }


-- SwitchMonitor(5).SFPInformation(34).SFPPortInfo(1).SFPPortInfoTable(1)

	swhSFPPortInfoTable OBJECT-TYPE
		SYNTAX      SEQUENCE OF SwhSFPPortInfoEntry
		MAX-ACCESS  not-accessible
		STATUS      current
		DESCRIPTION
			"Table of SFP port info."
		::= { swhSFPPortInfo 1 }

	-- Table Entry
	swhSFPPortInfoEntry OBJECT-TYPE
		SYNTAX      SwhSFPPortInfoEntry
		MAX-ACCESS  not-accessible
		STATUS      current
		DESCRIPTION
			"An entry in the table, containing information about SFP port info."
		INDEX    { swhSFPPortInfoIndex }
		::= { swhSFPPortInfoTable 1 }

	SwhSFPPortInfoEntry ::=
		SEQUENCE {
			swhSFPPortInfoIndex
				INTEGER,
			swhSFPPortInfoPortName
				DisplayString,
			swhSFPPortInfoSpeed
				DisplayString,
			swhSFPPortInfoDistance
				DisplayString,
			swhSFPPortInfoVendorName
				DisplayString,
			swhSFPPortInfoVendorPN
				DisplayString,
			swhSFPPortInfoVendorSN
				DisplayString
		}

	swhSFPPortInfoIndex OBJECT-TYPE
		SYNTAX      INTEGER (0..2147483647)
		MAX-ACCESS  not-accessible
		STATUS      current
		DESCRIPTION
			"A unique value for each index."
		::= { swhSFPPortInfoEntry 1 }

	swhSFPPortInfoPortName OBJECT-TYPE
		SYNTAX      DisplayString
		MAX-ACCESS  read-only
		STATUS      current
		DESCRIPTION
			"Port Name."
		::= { swhSFPPortInfoEntry 3 }

	swhSFPPortInfoSpeed OBJECT-TYPE
		SYNTAX      DisplayString
		MAX-ACCESS  read-only
		STATUS      current
		DESCRIPTION
			"Speed."
		::= { swhSFPPortInfoEntry 5 }

	swhSFPPortInfoDistance OBJECT-TYPE
		SYNTAX      DisplayString
		MAX-ACCESS  read-only
		STATUS      current
		DESCRIPTION
			"Distance."
		::= { swhSFPPortInfoEntry 7 }

	swhSFPPortInfoVendorName OBJECT-TYPE
		SYNTAX      DisplayString
		MAX-ACCESS  read-only
		STATUS      current
		DESCRIPTION
			"Vendor Name."
		::= { swhSFPPortInfoEntry 9 }

	swhSFPPortInfoVendorPN OBJECT-TYPE
		SYNTAX      DisplayString
		MAX-ACCESS  read-only
		STATUS      current
		DESCRIPTION
			"Vendor PN."
		::= { swhSFPPortInfoEntry 11 }

	swhSFPPortInfoVendorSN OBJECT-TYPE
		SYNTAX      DisplayString
		MAX-ACCESS  read-only
		STATUS      current
		DESCRIPTION
			"Vendor SN."
		::= { swhSFPPortInfoEntry 13 }


-- SwitchMonitor(5).SFPInformation(34).SFPPortState(2).SFPPortStateTable(1)

	swhSFPPortStateTable OBJECT-TYPE
		SYNTAX      SEQUENCE OF SwhSFPPortStateEntry
		MAX-ACCESS  not-accessible
		STATUS      current
		DESCRIPTION
			"Table of SFP Port State."
		::= { swhSFPPortState 1 }

	-- Table Entry
	swhSFPPortStateEntry OBJECT-TYPE
		SYNTAX      SwhSFPPortStateEntry
		MAX-ACCESS  not-accessible
		STATUS      current
		DESCRIPTION
			"An entry in the table, containing information about SFP Port State."
		INDEX    { swhSFPPortStateIndex }
		::= { swhSFPPortStateTable 1 }

	SwhSFPPortStateEntry ::=
		SEQUENCE {
			swhSFPPortStateIndex
				INTEGER,
			swhSFPPortStatePortName
				DisplayString,
			swhSFPPortStateTemperature
				DisplayString,
			swhSFPPortStateVoltage
				DisplayString,
			swhSFPPortStateTXBias
				DisplayString,
			swhSFPPortStateTXPower
				DisplayString,
			swhSFPPortStateRXPower
				DisplayString
		}

	swhSFPPortStateIndex OBJECT-TYPE
		SYNTAX      INTEGER (0..2147483647)
		MAX-ACCESS  not-accessible
		STATUS      current
		DESCRIPTION
			"A unique value for each index."
		::= { swhSFPPortStateEntry 1 }

	swhSFPPortStatePortName OBJECT-TYPE
		SYNTAX      DisplayString
		MAX-ACCESS  read-only
		STATUS      current
		DESCRIPTION
			"Port Name."
		::= { swhSFPPortStateEntry 3 }

	swhSFPPortStateTemperature OBJECT-TYPE
		SYNTAX      DisplayString
		MAX-ACCESS  read-only
		STATUS      current
		DESCRIPTION
			"Port Temperature. (C)"
		::= { swhSFPPortStateEntry 5 }

	swhSFPPortStateVoltage OBJECT-TYPE
		SYNTAX      DisplayString
		MAX-ACCESS  read-only
		STATUS      current
		DESCRIPTION
			"Port Voltage. (V)"
		::= { swhSFPPortStateEntry 7 }

	swhSFPPortStateTXBias OBJECT-TYPE
		SYNTAX      DisplayString
		MAX-ACCESS  read-only
		STATUS      current
		DESCRIPTION
			"Port TX Bias. (mA)"
		::= { swhSFPPortStateEntry 9 }

	swhSFPPortStateTXPower OBJECT-TYPE
		SYNTAX      DisplayString
		MAX-ACCESS  read-only
		STATUS      current
		DESCRIPTION
			"Port TX Power. (dBm)"
		::= { swhSFPPortStateEntry 11 }

	swhSFPPortStateRXPower OBJECT-TYPE
		SYNTAX      DisplayString
		MAX-ACCESS  read-only
		STATUS      current
		DESCRIPTION
			"Port RX Power. (dBm)"
		::= { swhSFPPortStateEntry 13 }


-- SwitchMonitor(5).DHCPSnoopingTable(35)

	swhDHCPSnoopingTableClearByPortList OBJECT-TYPE
		SYNTAX      DisplayString
		MAX-ACCESS  read-write
		STATUS      current
		DESCRIPTION
			"Clear by port list."
		::= { swhDHCPSnoopingTable 10 }


-- SwitchMonitor(5).DHCPSnoopingTable(35).DHCPSnoopingTableTable(7)

	swhDHCPSnoopingTableTable OBJECT-TYPE
		SYNTAX      SEQUENCE OF SwhDHCPSnoopingTableEntry
		MAX-ACCESS  not-accessible
		STATUS      current
		DESCRIPTION
			"Table of DHCP snooping table."
		::= { swhDHCPSnoopingTable 7 }

	-- Table Entry
	swhDHCPSnoopingTableEntry OBJECT-TYPE
		SYNTAX      SwhDHCPSnoopingTableEntry
		MAX-ACCESS  not-accessible
		STATUS      current
		DESCRIPTION
			"An entry in the table, containing information about DHCP snooping table."
		INDEX    { swhDHCPSnoopingTableIndex }
		::= { swhDHCPSnoopingTableTable 1 }

	SwhDHCPSnoopingTableEntry ::=
		SEQUENCE {
			swhDHCPSnoopingTableIndex
				INTEGER,
			swhDHCPSnoopingTableCliPort
				INTEGER,
			swhDHCPSnoopingTableSrvPort
				INTEGER,
			swhDHCPSnoopingTableVID
				INTEGER,
			swhDHCPSnoopingTableCliIPAddr
				IpAddress,
			swhDHCPSnoopingTableCliMacAddr
				MacAddress,
			swhDHCPSnoopingTableSrvIPAddr
				IpAddress,
			swhDHCPSnoopingTableTimeLeft
				DisplayString
		}

	swhDHCPSnoopingTableIndex OBJECT-TYPE
		SYNTAX      INTEGER (0..2147483647)
		MAX-ACCESS  not-accessible
		STATUS      current
		DESCRIPTION
			"A unique value for each index."
		::= { swhDHCPSnoopingTableEntry 1 }

	swhDHCPSnoopingTableCliPort OBJECT-TYPE
		SYNTAX      INTEGER
		MAX-ACCESS  read-only
		STATUS      current
		DESCRIPTION
			"Client Port Number."
		::= { swhDHCPSnoopingTableEntry 2 }

	swhDHCPSnoopingTableSrvPort OBJECT-TYPE
		SYNTAX      INTEGER
		MAX-ACCESS  read-only
		STATUS      current
		DESCRIPTION
			"Server Port Number."
		::= { swhDHCPSnoopingTableEntry 3 }

	swhDHCPSnoopingTableVID OBJECT-TYPE
		SYNTAX      INTEGER (1..4094)
		MAX-ACCESS  read-only
		STATUS      current
		DESCRIPTION
			"VLAN ID. (1-4094)"
		::= { swhDHCPSnoopingTableEntry 4 }

	swhDHCPSnoopingTableCliIPAddr OBJECT-TYPE
		SYNTAX      IpAddress
		MAX-ACCESS  read-only
		STATUS      current
		DESCRIPTION
			"Client IP Address."
		::= { swhDHCPSnoopingTableEntry 5 }

	swhDHCPSnoopingTableCliMacAddr OBJECT-TYPE
		SYNTAX      MacAddress
		MAX-ACCESS  read-only
		STATUS      current
		DESCRIPTION
			"Client Mac Address."
		::= { swhDHCPSnoopingTableEntry 6 }

	swhDHCPSnoopingTableSrvIPAddr OBJECT-TYPE
		SYNTAX      IpAddress
		MAX-ACCESS  read-only
		STATUS      current
		DESCRIPTION
			"Server IP Address."
		::= { swhDHCPSnoopingTableEntry 7 }

	swhDHCPSnoopingTableTimeLeft OBJECT-TYPE
		SYNTAX      DisplayString
		MAX-ACCESS  read-only
		STATUS      current
		DESCRIPTION
			"Time Left."
		::= { swhDHCPSnoopingTableEntry 8 }


-- SwitchMonitor(5).DHCPSnoopingTable(35)

	swhDHCPSnoopingTableClearByPortList OBJECT-TYPE
		SYNTAX      DisplayString
		MAX-ACCESS  read-write
		STATUS      current
		DESCRIPTION
			"Clear by port list."
		::= { swhDHCPSnoopingTable 10 }


-- SwitchMonitor(5).DHCPSnoopingTable(35).DHCPv6SnoopingTableTable(8)

	swhDHCPv6SnoopingTableTable OBJECT-TYPE
		SYNTAX      SEQUENCE OF SwhDHCPv6SnoopingTableEntry
		MAX-ACCESS  not-accessible
		STATUS      current
		DESCRIPTION
			"Table of DHCPv6 snooping table."
		::= { swhDHCPSnoopingTable 8 }

	-- Table Entry
	swhDHCPv6SnoopingTableEntry OBJECT-TYPE
		SYNTAX      SwhDHCPv6SnoopingTableEntry
		MAX-ACCESS  not-accessible
		STATUS      current
		DESCRIPTION
			"An entry in the table, containing information about DHCPv6 snooping table."
		INDEX    { swhDHCPv6SnoopingTableIndex }
		::= { swhDHCPv6SnoopingTableTable 1 }

	SwhDHCPv6SnoopingTableEntry ::=
		SEQUENCE {
			swhDHCPv6SnoopingTableIndex
				INTEGER,
			swhDHCPv6SnoopingTableCliPort
				INTEGER,
			swhDHCPv6SnoopingTableSrvPort
				INTEGER,
			swhDHCPv6SnoopingTableVID
				INTEGER,
			swhDHCPv6SnoopingTableCliIPAddr
				DisplayString,
			swhDHCPv6SnoopingTableCliMacAddr
				MacAddress,
			swhDHCPv6SnoopingTableSrvIPAddr
				DisplayString,
			swhDHCPv6SnoopingTableTimeLeft
				DisplayString
		}

	swhDHCPv6SnoopingTableIndex OBJECT-TYPE
		SYNTAX      INTEGER (0..2147483647)
		MAX-ACCESS  not-accessible
		STATUS      current
		DESCRIPTION
			"A unique value for each index."
		::= { swhDHCPv6SnoopingTableEntry 1 }

	swhDHCPv6SnoopingTableCliPort OBJECT-TYPE
		SYNTAX      INTEGER
		MAX-ACCESS  read-only
		STATUS      current
		DESCRIPTION
			"Client Port Number."
		::= { swhDHCPv6SnoopingTableEntry 2 }

	swhDHCPv6SnoopingTableSrvPort OBJECT-TYPE
		SYNTAX      INTEGER
		MAX-ACCESS  read-only
		STATUS      current
		DESCRIPTION
			"Server Port Number."
		::= { swhDHCPv6SnoopingTableEntry 3 }

	swhDHCPv6SnoopingTableVID OBJECT-TYPE
		SYNTAX      INTEGER (1..4094)
		MAX-ACCESS  read-only
		STATUS      current
		DESCRIPTION
			"VLAN ID. (1-4094)"
		::= { swhDHCPv6SnoopingTableEntry 4 }

	swhDHCPv6SnoopingTableCliIPAddr OBJECT-TYPE
		SYNTAX      DisplayString
		MAX-ACCESS  read-only
		STATUS      current
		DESCRIPTION
			"Client IPv6 Address."
		::= { swhDHCPv6SnoopingTableEntry 5 }

	swhDHCPv6SnoopingTableCliMacAddr OBJECT-TYPE
		SYNTAX      MacAddress
		MAX-ACCESS  read-only
		STATUS      current
		DESCRIPTION
			"Client Mac Address."
		::= { swhDHCPv6SnoopingTableEntry 6 }

	swhDHCPv6SnoopingTableSrvIPAddr OBJECT-TYPE
		SYNTAX      DisplayString
		MAX-ACCESS  read-only
		STATUS      current
		DESCRIPTION
			"Server IPv6 Address."
		::= { swhDHCPv6SnoopingTableEntry 7 }

	swhDHCPv6SnoopingTableTimeLeft OBJECT-TYPE
		SYNTAX      DisplayString
		MAX-ACCESS  read-only
		STATUS      current
		DESCRIPTION
			"Time Left."
		::= { swhDHCPv6SnoopingTableEntry 8 }


-- SwitchMonitor(5).LoopDetectionStatus(36)

	swhLoopDetectionStatusUpdate OBJECT-TYPE
		SYNTAX      INTEGER { normal(0), update(1) }
		MAX-ACCESS  read-write
		STATUS      current
		DESCRIPTION
			"Update Loop Status Table."
		::= { swhLoopDetectionStatus 2 }


-- SwitchMonitor(5).LoopDetectionStatus(36).LoopDetectionStatusTable(4)

	swhLoopDetectionStatusTable OBJECT-TYPE
		SYNTAX      SEQUENCE OF SwhLoopDetectionStatusEntry
		MAX-ACCESS  not-accessible
		STATUS      current
		DESCRIPTION
			"Table of loop detection status."
		::= { swhLoopDetectionStatus 4 }

	-- Table Entry
	swhLoopDetectionStatusEntry OBJECT-TYPE
		SYNTAX      SwhLoopDetectionStatusEntry
		MAX-ACCESS  not-accessible
		STATUS      current
		DESCRIPTION
			"An entry in the table, containing information about loop detection status."
		INDEX    { swhLoopDetectionStatusPort }
		::= { swhLoopDetectionStatusTable 1 }

	SwhLoopDetectionStatusEntry ::=
		SEQUENCE {
			swhLoopDetectionStatusPort
				INTEGER,
			swhLoopDetectionStatusStatus
				INTEGER,
			swhLoopDetectionStatusLockCause
				DisplayString,
			swhLoopDetectionStatusUnlock
				INTEGER
		}

	swhLoopDetectionStatusPort OBJECT-TYPE
		SYNTAX      INTEGER (0..2147483647)
		MAX-ACCESS  not-accessible
		STATUS      current
		DESCRIPTION
			"A unique value for each port index."
		::= { swhLoopDetectionStatusEntry 1 }

	swhLoopDetectionStatusLockCause OBJECT-TYPE
		SYNTAX      DisplayString
		MAX-ACCESS  read-only
		STATUS      current
		DESCRIPTION
			"Lock Cause."
		::= { swhLoopDetectionStatusEntry 3 }

	swhLoopDetectionStatusStatus OBJECT-TYPE
		SYNTAX      INTEGER { na2(-2), na(-1), un-lock(0), lock(1) }
		MAX-ACCESS  read-only
		STATUS      current
		DESCRIPTION
			"Status."
		::= { swhLoopDetectionStatusEntry 4 }

	swhLoopDetectionStatusUnlock OBJECT-TYPE
		SYNTAX      INTEGER { normal(0), unlock(1) }
		MAX-ACCESS  read-write
		STATUS      current
		DESCRIPTION
			"Unlock."
		::= { swhLoopDetectionStatusEntry 9 }


-- SwitchMonitor(5).MacLimitersStatus(39)

	swhMacLimitersStatusTable OBJECT-TYPE
		SYNTAX      SEQUENCE OF SwhMacLimitersStatusEntry
		MAX-ACCESS  not-accessible
		STATUS      current
		DESCRIPTION
			"Table of mac limiters status."
		::= { swhMacLimitersStatus 1 }

	-- Table Entry
	swhMacLimitersStatusEntry OBJECT-TYPE
		SYNTAX      SwhMacLimitersStatusEntry
		MAX-ACCESS  not-accessible
		STATUS      current
		DESCRIPTION
			"An entry in the table, containing information about mac limiters status."
		INDEX    { swhMacLimitersStatusPort }
		::= { swhMacLimitersStatusTable 1 }

	SwhMacLimitersStatusEntry ::=
		SEQUENCE {
			swhMacLimitersStatusPort
				INTEGER,
			swhMacLimitersStatusLimit
				INTEGER,
			swhMacLimitersStatusCurrent
				INTEGER,
			swhMacLimitersStatusStatus
				DisplayString
		}

	swhMacLimitersStatusPort OBJECT-TYPE
		SYNTAX      INTEGER (0..2147483647)
		MAX-ACCESS  not-accessible
		STATUS      current
		DESCRIPTION
			"A unique value for each port index."
		::= { swhMacLimitersStatusEntry 1 }

	swhMacLimitersStatusLimit OBJECT-TYPE
		SYNTAX      INTEGER { na(-1), unlocked(0), lock(1) }
		MAX-ACCESS  read-only
		STATUS      current
		DESCRIPTION
			"Limit."
		::= { swhMacLimitersStatusEntry 2 }

	swhMacLimitersStatusCurrent OBJECT-TYPE
		SYNTAX      INTEGER { na(-1) }
		MAX-ACCESS  read-only
		STATUS      current
		DESCRIPTION
			"Current."
		::= { swhMacLimitersStatusEntry 3 }

	swhMacLimitersStatusStatus OBJECT-TYPE
		SYNTAX      DisplayString
		MAX-ACCESS  read-only
		STATUS      current
		DESCRIPTION
			"Status is unlocked or locked."
		::= { swhMacLimitersStatusEntry 4 }


-- SwitchMonitor(5).DIStatus(41).DIStatusTable(1)

	swhDIStatusTable OBJECT-TYPE
		SYNTAX      SEQUENCE OF SwhDIStatusEntry
		MAX-ACCESS  not-accessible
		STATUS      current
		DESCRIPTION
			"Table of digital input status."
		::= { swhDIStatus 1 }

	-- Table Entry
	swhDIStatusEntry OBJECT-TYPE
		SYNTAX      SwhDIStatusEntry
		MAX-ACCESS  not-accessible
		STATUS      current
		DESCRIPTION
			"An entry in the table, containing information about digital input status."
		INDEX    { swhDIStatusIndex }
		::= { swhDIStatusTable 1 }

	SwhDIStatusEntry ::=
		SEQUENCE {
			swhDIStatusIndex
				INTEGER,
			swhDIStatusStatus
				INTEGER,
			swhDIStatusAlarm
				INTEGER
		}

	swhDIStatusIndex OBJECT-TYPE
		SYNTAX      INTEGER (0..2147483647)
		MAX-ACCESS  not-accessible
		STATUS      current
		DESCRIPTION
			"A unique value for each index."
		::= { swhDIStatusEntry 1 }

	swhDIStatusStatus OBJECT-TYPE
		SYNTAX      INTEGER { close(0), open(1) }
		MAX-ACCESS  read-only
		STATUS      current
		DESCRIPTION
			"Status."
		::= { swhDIStatusEntry 3 }

	swhDIStatusAlarm OBJECT-TYPE
		SYNTAX      INTEGER { off(0), on(1) }
		MAX-ACCESS  read-only
		STATUS      current
		DESCRIPTION
			"Alarm."
		::= { swhDIStatusEntry 4 }


-- SwitchMonitor(5).Statistics(45)

	swhCPUStatistics
		OBJECT IDENTIFIER ::= { swhStatistics 1 }

	swhMemoryStatistics
		OBJECT IDENTIFIER ::= { swhStatistics 2 }


-- SwitchMonitor(5).Statistics(45).CPUStatistics(1)

	swhCPUStatisticsCPULoadingNotification OBJECT-TYPE
		SYNTAX      INTEGER { disable(0), enable(1) }
		MAX-ACCESS  read-write
		STATUS      current
		DESCRIPTION
			"CPU Loading Notification."
		::= { swhCPUStatistics 13 }

	swhCPUStatisticsCPULoadingThreshold OBJECT-TYPE
		SYNTAX      INTEGER (1..99)
		MAX-ACCESS  read-write
		STATUS      current
		DESCRIPTION
			"CPU Loading Threshold."
		::= { swhCPUStatistics 1 }

	swhCPUStatisticsCPULoadingRestore OBJECT-TYPE
		SYNTAX      INTEGER (1..99)
		MAX-ACCESS  read-write
		STATUS      current
		DESCRIPTION
			"CPU Loading Restore."
		::= { swhCPUStatistics 14 }

	swhCPUStatisticsCPULoadingObservationInterval OBJECT-TYPE
		SYNTAX      INTEGER (5..86400)
		MAX-ACCESS  read-write
		STATUS      current
		DESCRIPTION
			"CPU Loading Observation Interval."
		::= { swhCPUStatistics 15 }

	swhCPUStatisticsCurrentNTPTime OBJECT-TYPE
		SYNTAX      DisplayString
		MAX-ACCESS  read-only
		STATUS      current
		DESCRIPTION
			"Current NTP Time."
		::= { swhCPUStatistics 9 }

	swhCPUStatisticsCurrentUpTime OBJECT-TYPE
		SYNTAX      DisplayString
		MAX-ACCESS  read-only
		STATUS      current
		DESCRIPTION
			"Current Up Time."
		::= { swhCPUStatistics 10 }

	swhCPUStatisticsCPULoading OBJECT-TYPE
		SYNTAX      DisplayString
		MAX-ACCESS  read-only
		STATUS      current
		DESCRIPTION
			"CPU Loading. (%)"
		::= { swhCPUStatistics 2 }

	swhCPUStatisticsAveragesRecordStartNTPTime OBJECT-TYPE
		SYNTAX      DisplayString
		MAX-ACCESS  read-only
		STATUS      current
		DESCRIPTION
			"Averages Record Start NTP Time."
		::= { swhCPUStatistics 11 }

	swhCPUStatisticsAveragesRecordStartUpTime OBJECT-TYPE
		SYNTAX      DisplayString
		MAX-ACCESS  read-only
		STATUS      current
		DESCRIPTION
			"Averages Record Start Up Time."
		::= { swhCPUStatistics 12 }

	swhCPUStatisticsLoadAverages1hour OBJECT-TYPE
		SYNTAX      DisplayString
		MAX-ACCESS  read-only
		STATUS      current
		DESCRIPTION
			"Load Averages - 1 Hour."
		::= { swhCPUStatistics 5 }

	swhCPUStatisticsLoadAverages24hours OBJECT-TYPE
		SYNTAX      DisplayString
		MAX-ACCESS  read-only
		STATUS      current
		DESCRIPTION
			"Load Averages - 24 Hours."
		::= { swhCPUStatistics 6 }

	swhCPUStatisticsLoadAverages72hours OBJECT-TYPE
		SYNTAX      DisplayString
		MAX-ACCESS  read-only
		STATUS      current
		DESCRIPTION
			"Load Averages - 72 Hours."
		::= { swhCPUStatistics 7 }

	swhCPUStatisticsLoadAveragesClear OBJECT-TYPE
		SYNTAX      INTEGER { normal(0), clear(1) }
		MAX-ACCESS  read-write
		STATUS      current
		DESCRIPTION
			"Clear Averages of CPU Loading Statistics."
		::= { swhCPUStatistics 8 }


-- SwitchMonitor(5).Statistics(45).MemoryStatistics(2)

	swhMemoryStatisticsCurrentNTPTime OBJECT-TYPE
		SYNTAX      DisplayString
		MAX-ACCESS  read-only
		STATUS      current
		DESCRIPTION
			"Current NTP Time."
		::= { swhMemoryStatistics 10 }

	swhMemoryStatisticsCurrentUpTime OBJECT-TYPE
		SYNTAX      DisplayString
		MAX-ACCESS  read-only
		STATUS      current
		DESCRIPTION
			"Current Up Time."
		::= { swhMemoryStatistics 11 }

	swhMemoryStatisticsTotalMemory OBJECT-TYPE
		SYNTAX      DisplayString
		MAX-ACCESS  read-only
		STATUS      current
		DESCRIPTION
			"Total Memory. (KByte)"
		::= { swhMemoryStatistics 5 }

	swhMemoryStatisticsMemoryUse OBJECT-TYPE
		SYNTAX      DisplayString
		MAX-ACCESS  read-only
		STATUS      current
		DESCRIPTION
			"Memory Use. (KByte)"
		::= { swhMemoryStatistics 6 }

	swhMemoryStatisticsMemoryFree OBJECT-TYPE
		SYNTAX      DisplayString
		MAX-ACCESS  read-only
		STATUS      current
		DESCRIPTION
			"Memory Free. (KByte)"
		::= { swhMemoryStatistics 7 }


-- SwitchMonitor(5).CPUTemperatureStatus(51)

	swhCPUHighTemperatureThreshold OBJECT-TYPE
		SYNTAX      INTEGER (0..95)
		MAX-ACCESS  read-write
		STATUS      current
		DESCRIPTION
			"High Temperature Threshold."
		::= { swhCPUTemperatureStatus 1 }

	swhCPUThresholdInterval OBJECT-TYPE
		SYNTAX      INTEGER (120..86400)
		MAX-ACCESS  read-write
		STATUS      current
		DESCRIPTION
			"Threshold Interval. (120-86400)"
		::= { swhCPUTemperatureStatus 2 }

	swhCPUContinuousAlarm OBJECT-TYPE
		SYNTAX      INTEGER { disable(0), enable(1) }
		MAX-ACCESS  read-write
		STATUS      current
		DESCRIPTION
			"Continuous Alarm."
		::= { swhCPUTemperatureStatus 3 }

	swhCPUCurrentCPUTemperature OBJECT-TYPE
		SYNTAX      Integer32 (-2147483648..2147483647)
		MAX-ACCESS  read-only
		STATUS      current
		DESCRIPTION
			"Current CPU Temperature. (1/10 C)"
		::= { swhCPUTemperatureStatus 5 }

	swhCPUHistoricalHighCPUTemperature OBJECT-TYPE
		SYNTAX      Integer32 (-2147483648..2147483647)
		MAX-ACCESS  read-only
		STATUS      current
		DESCRIPTION
			"Historical High CPU Temperature. (1/10 C)"
		::= { swhCPUTemperatureStatus 6 }

	swhCPUHistoricalHighElapsedTime OBJECT-TYPE
		SYNTAX      DisplayString
		MAX-ACCESS  read-only
		STATUS      current
		DESCRIPTION
			"Historical High Elapsed Time."
		::= { swhCPUTemperatureStatus 7 }

	swhCPUHistoricalLowCPUTemperature OBJECT-TYPE
		SYNTAX      Integer32 (-2147483648..2147483647)
		MAX-ACCESS  read-only
		STATUS      current
		DESCRIPTION
			"Historical Low CPU Temperature. (1/10 C)"
		::= { swhCPUTemperatureStatus 8 }

	swhCPUHistoricalLowElapsedTime OBJECT-TYPE
		SYNTAX      DisplayString
		MAX-ACCESS  read-only
		STATUS      current
		DESCRIPTION
			"Historical Low Elapsed Time."
		::= { swhCPUTemperatureStatus 9 }


-- SwitchMonitor(5).FastRedundancyStatus(52)

	swhRingStatusTimes OBJECT-TYPE
		SYNTAX      INTEGER (0..2147483647)
		MAX-ACCESS  read-only
		STATUS      current
		DESCRIPTION
			"Times."
		::= { swhFastRedundancyStatus 2 }

	swhRingStatusLastChangeTime OBJECT-TYPE
		SYNTAX      DisplayString
		MAX-ACCESS  read-only
		STATUS      current
		DESCRIPTION
			"Last Change Time."
		::= { swhFastRedundancyStatus 3 }

	swhRingStatusElapsedTime OBJECT-TYPE
		SYNTAX      DisplayString
		MAX-ACCESS  read-only
		STATUS      current
		DESCRIPTION
			"Elapsed Time."
		::= { swhFastRedundancyStatus 4 }

	swhRingStatusTopologyClear OBJECT-TYPE
		SYNTAX      INTEGER { normal(0), clear(1) }
		MAX-ACCESS  read-write
		STATUS      current
		DESCRIPTION
			"Topology Clear."
		::= { swhFastRedundancyStatus 5 }


-- SwitchMonitor(5).FastRedundancyStatus(52).FastRedundancyStatusTable(1)

	swhFastRedundancyStatusTable OBJECT-TYPE
		SYNTAX      SEQUENCE OF SwhFastRedundancyStatusEntry
		MAX-ACCESS  not-accessible
		STATUS      current
		DESCRIPTION
			"Table of fast redundancy status."
		::= { swhFastRedundancyStatus 1 }

	-- Table Entry
	swhFastRedundancyStatusEntry OBJECT-TYPE
		SYNTAX      SwhFastRedundancyStatusEntry
		MAX-ACCESS  not-accessible
		STATUS      current
		DESCRIPTION
			"An entry in the table, containing information about fast redundancy status."
		INDEX    { swhFastRedundancyStatusIndex }
		::= { swhFastRedundancyStatusTable 1 }

	SwhFastRedundancyStatusEntry ::=
		SEQUENCE {
			swhFastRedundancyStatusIndex
				INTEGER,
			swhFastRedundancyStatusGroupID
				INTEGER,
			swhFastRedundancyStatusDescription
				DisplayString,
			swhFastRedundancyStatusEnable
				INTEGER,
			swhFastRedundancyStatusProtocol
				INTEGER,
			swhFastRedundancyStatusRole
				INTEGER,
			swhFastRedundancyStatusStatus
				INTEGER,
			swhFastRedundancyStatusPort1
				INTEGER,
			swhFastRedundancyStatusPort1Role
				INTEGER,
			swhFastRedundancyStatusPort1Status
				INTEGER,
			swhFastRedundancyStatusPort2
				INTEGER,
			swhFastRedundancyStatusPort2Role
				INTEGER,
			swhFastRedundancyStatusPort2Status
				INTEGER
		}

	swhFastRedundancyStatusIndex OBJECT-TYPE
		SYNTAX      INTEGER (0..2147483647)
		MAX-ACCESS  not-accessible
		STATUS      current
		DESCRIPTION
			"A unique value for each index."
		::= { swhFastRedundancyStatusEntry 1 }

	swhFastRedundancyStatusGroupID OBJECT-TYPE
		SYNTAX      INTEGER { na(-1), id-1(1), id-2(2) }
		MAX-ACCESS  read-only
		STATUS      current
		DESCRIPTION
			"Group ID."
		::= { swhFastRedundancyStatusEntry 2 }

	swhFastRedundancyStatusDescription OBJECT-TYPE
		SYNTAX      DisplayString
		MAX-ACCESS  read-only
		STATUS      current
		DESCRIPTION
			"Description."
		::= { swhFastRedundancyStatusEntry 3 }

	swhFastRedundancyStatusEnable OBJECT-TYPE
		SYNTAX      INTEGER { na(-1), disable(0), enable(1) }
		MAX-ACCESS  read-only
		STATUS      current
		DESCRIPTION
			"Enable."
		::= { swhFastRedundancyStatusEntry 4 }

	swhFastRedundancyStatusProtocol OBJECT-TYPE
		SYNTAX      INTEGER { na(-1), fast-ringv2(0), chain(1) }
		MAX-ACCESS  read-only
		STATUS      current
		DESCRIPTION
			"Protocol."
		::= { swhFastRedundancyStatusEntry 5 }

	swhFastRedundancyStatusRole OBJECT-TYPE
		SYNTAX      INTEGER { na(-1), slave(0), master(1) }
		MAX-ACCESS  read-only
		STATUS      current
		DESCRIPTION
			"Role."
		::= { swhFastRedundancyStatusEntry 6 }

	swhFastRedundancyStatusStatus OBJECT-TYPE
		SYNTAX      INTEGER { signal-fail(-2), na(-1), healthy(0), break(1) }
		MAX-ACCESS  read-only
		STATUS      current
		DESCRIPTION
			"Status."
		::= { swhFastRedundancyStatusEntry 7 }

	swhFastRedundancyStatusPort1 OBJECT-TYPE
		SYNTAX      INTEGER { na(0),
		                      port01(1),
		                      port02(2),
		                      port03(3),
		                      port04(4),
		                      port05(5),
		                      port06(6),
		                      port07(7),
		                      port08(8),
		                      port09(9),
		                      port10(10),
		                      port11(11),
		                      port12(12)
		                    }
		MAX-ACCESS  read-only
		STATUS      current
		DESCRIPTION
			"Port 1."
		::= { swhFastRedundancyStatusEntry 8 }

	swhFastRedundancyStatusPort1Role OBJECT-TYPE
		SYNTAX      INTEGER { na(-1), member(0), head(1), tail(2) }
		MAX-ACCESS  read-only
		STATUS      current
		DESCRIPTION
			"Port 1 Role."
		::= { swhFastRedundancyStatusEntry 9 }

	swhFastRedundancyStatusPort1Status OBJECT-TYPE
		SYNTAX      INTEGER { na2(-2), na(-1), blocked(1), forwarding(4), link-down(5) }
		MAX-ACCESS  read-only
		STATUS      current
		DESCRIPTION
			"Port 1 Status."
		::= { swhFastRedundancyStatusEntry 10 }

	swhFastRedundancyStatusPort2 OBJECT-TYPE
		SYNTAX      INTEGER { na(0),
		                      port01(1),
		                      port02(2),
		                      port03(3),
		                      port04(4),
		                      port05(5),
		                      port06(6),
		                      port07(7),
		                      port08(8),
		                      port09(9),
		                      port10(10),
		                      port11(11),
		                      port12(12)
		                    }
		MAX-ACCESS  read-only
		STATUS      current
		DESCRIPTION
			"Port 2."
		::= { swhFastRedundancyStatusEntry 11 }

	swhFastRedundancyStatusPort2Role OBJECT-TYPE
		SYNTAX      INTEGER { na(-1), member(0), head(1), tail(2) }
		MAX-ACCESS  read-only
		STATUS      current
		DESCRIPTION
			"Port 2 Role."
		::= { swhFastRedundancyStatusEntry 12 }

	swhFastRedundancyStatusPort2Status OBJECT-TYPE
		SYNTAX      INTEGER { na2(-2), na(-1), blocked(1), forwarding(4), link-down(5) }
		MAX-ACCESS  read-only
		STATUS      current
		DESCRIPTION
			"Port 2 Status."
		::= { swhFastRedundancyStatusEntry 13 }


-- SwitchMonitor(5).FastRedundancyStatus(52).FastRedundancyStatisticsTable(6)

	swhFastRedundancyStatisticsTable OBJECT-TYPE
		SYNTAX      SEQUENCE OF SwhFastRedundancyStatisticsEntry
		MAX-ACCESS  not-accessible
		STATUS      current
		DESCRIPTION
			"Table of fast redundancy statistics."
		::= { swhFastRedundancyStatus 6 }

	-- Table Entry
	swhFastRedundancyStatisticsEntry OBJECT-TYPE
		SYNTAX      SwhFastRedundancyStatisticsEntry
		MAX-ACCESS  not-accessible
		STATUS      current
		DESCRIPTION
			"An entry in the table, containing information about fast redundancy statistics."
		INDEX    { swhFastRedundancyEntry }
		::= { swhFastRedundancyStatisticsTable 1 }

	SwhFastRedundancyStatisticsEntry ::=
		SEQUENCE {
			swhFastRedundancyEntry
				INTEGER,
			swhFastRedundancyTxNormal
				Counter32,
			swhFastRedundancyTxFailure
				Counter32,
			swhFastRedundancyRxNormal
				Counter32,
			swhFastRedundancyRxFailure
				Counter32,
			swhFastRedundancyCountersClear
				INTEGER
		}

	swhFastRedundancyEntry OBJECT-TYPE
		SYNTAX      INTEGER (0..2147483647)
		MAX-ACCESS  not-accessible
		STATUS      current
		DESCRIPTION
			"A unique value for each index."
		::= { swhFastRedundancyStatisticsEntry 1 }

	swhFastRedundancyTxNormal OBJECT-TYPE
		SYNTAX      Counter32
		MAX-ACCESS  read-only
		STATUS      current
		DESCRIPTION
			"Tx Normal."
		::= { swhFastRedundancyStatisticsEntry 2 }

	swhFastRedundancyTxFailure OBJECT-TYPE
		SYNTAX      Counter32
		MAX-ACCESS  read-only
		STATUS      current
		DESCRIPTION
			"Tx Failure."
		::= { swhFastRedundancyStatisticsEntry 3 }

	swhFastRedundancyRxNormal OBJECT-TYPE
		SYNTAX      Counter32
		MAX-ACCESS  read-only
		STATUS      current
		DESCRIPTION
			"Rx Normal."
		::= { swhFastRedundancyStatisticsEntry 4 }

	swhFastRedundancyRxFailure OBJECT-TYPE
		SYNTAX      Counter32
		MAX-ACCESS  read-only
		STATUS      current
		DESCRIPTION
			"Rx Failure."
		::= { swhFastRedundancyStatisticsEntry 5 }

	swhFastRedundancyCountersClear OBJECT-TYPE
		SYNTAX      INTEGER { normal(0), clear(1) }
		MAX-ACCESS  read-write
		STATUS      current
		DESCRIPTION
			"Counters Clear."
		::= { swhFastRedundancyStatisticsEntry 6 }


-- SwitchMonitor(5).SystemVoltageState(55).SystemVoltageStateTable(1)

	swhSystemVoltageStateTable OBJECT-TYPE
		SYNTAX      SEQUENCE OF SwhSystemVoltageStateEntry
		MAX-ACCESS  not-accessible
		STATUS      current
		DESCRIPTION
			"Table of system voltage state."
		::= { swhSystemVoltageState 1 }

	-- Table Entry
	swhSystemVoltageStateEntry OBJECT-TYPE
		SYNTAX      SwhSystemVoltageStateEntry
		MAX-ACCESS  not-accessible
		STATUS      current
		DESCRIPTION
			"An entry in the table, containing information about system voltage state."
		INDEX    { swhSystemVoltageStateIndex }
		::= { swhSystemVoltageStateTable 1 }

	SwhSystemVoltageStateEntry ::=
		SEQUENCE {
			swhSystemVoltageStateIndex
				INTEGER,
			swhSystemVoltageStateComponent
				DisplayString,
			swhSystemVoltageStatePresentVoltage
				INTEGER,
			swhSystemVoltageStateThresholdHigh
				INTEGER,
			swhSystemVoltageStateThresholdLow
				INTEGER,
			swhSystemVoltageStateState
				DisplayString
		}

	swhSystemVoltageStateIndex OBJECT-TYPE
		SYNTAX      INTEGER (0..2147483647)
		MAX-ACCESS  not-accessible
		STATUS      current
		DESCRIPTION
			"A unique value for each index."
		::= { swhSystemVoltageStateEntry 1 }

	swhSystemVoltageStateComponent OBJECT-TYPE
		SYNTAX      DisplayString
		MAX-ACCESS  read-only
		STATUS      current
		DESCRIPTION
			"Component."
		::= { swhSystemVoltageStateEntry 2 }

	swhSystemVoltageStatePresentVoltage OBJECT-TYPE
		SYNTAX      INTEGER (0..2147483647)
		MAX-ACCESS  read-only
		STATUS      current
		DESCRIPTION
			"Present Voltage."
		::= { swhSystemVoltageStateEntry 3 }

	swhSystemVoltageStateThresholdHigh OBJECT-TYPE
		SYNTAX      INTEGER (0..2147483647)
		MAX-ACCESS  read-only
		STATUS      current
		DESCRIPTION
			"Threshold High."
		::= { swhSystemVoltageStateEntry 4 }

	swhSystemVoltageStateThresholdLow OBJECT-TYPE
		SYNTAX      INTEGER (0..2147483647)
		MAX-ACCESS  read-only
		STATUS      current
		DESCRIPTION
			"Threshold Low."
		::= { swhSystemVoltageStateEntry 5 }

	swhSystemVoltageStateState OBJECT-TYPE
		SYNTAX      DisplayString
		MAX-ACCESS  read-only
		STATUS      current
		DESCRIPTION
			"State."
		::= { swhSystemVoltageStateEntry 6 }


-- SystemUtility(6)

	swhLoadFactorySetting
		OBJECT IDENTIFIER ::= { swhSystemUtility 1 }

	swhEventLog
		OBJECT IDENTIFIER ::= { swhSystemUtility 3 }

	swhUpdateFirmware
		OBJECT IDENTIFIER ::= { swhSystemUtility 4 }

	swhFirmwareCopy
		OBJECT IDENTIFIER ::= { swhSystemUtility 8 }

	swhAutoBackupConfiguration
		OBJECT IDENTIFIER ::= { swhSystemUtility 5 }

	swhCableDiagnostics
		OBJECT IDENTIFIER ::= { swhSystemUtility 6 }

	swhPortLinkFlapLog
		OBJECT IDENTIFIER ::= { swhSystemUtility 9 }

	swhPortLoopbackTest
		OBJECT IDENTIFIER ::= { swhSystemUtility 12 }


-- SystemUtility(6).LoadFactorySetting(1)

	swhLoadFactorySettingKeepEvent OBJECT-TYPE
		SYNTAX      INTEGER { no(0), yes(1) }
		MAX-ACCESS  read-write
		STATUS      current
		DESCRIPTION
			"Keep Event."
		::= { swhLoadFactorySetting 2 }

	swhLoadFactorySettingKeepIP OBJECT-TYPE
		SYNTAX      INTEGER { no(0), yes(1) }
		MAX-ACCESS  read-write
		STATUS      current
		DESCRIPTION
			"Keep IP."
		::= { swhLoadFactorySetting 3 }

	swhLoadFactorySettingReset OBJECT-TYPE
		SYNTAX      INTEGER { normal(0), reset(1) }
		MAX-ACCESS  read-write
		STATUS      current
		DESCRIPTION
			"Reset."
		::= { swhLoadFactorySetting 1 }


-- SystemUtility(6).EventLog(3)

	swhEventLogTable OBJECT-TYPE
		SYNTAX      SEQUENCE OF SwhEventLogEntry
		MAX-ACCESS  not-accessible
		STATUS      current
		DESCRIPTION
			"Table of event log."
		::= { swhEventLog 1 }

	swhEventLogClear OBJECT-TYPE
		SYNTAX      INTEGER { normal(0), clear(1) }
		MAX-ACCESS  read-write
		STATUS      current
		DESCRIPTION
			"Clear."
		::= { swhEventLog 2 }

	swhEventLogRecord OBJECT-TYPE
		SYNTAX      INTEGER { disable(0), enable(1) }
		MAX-ACCESS  read-write
		STATUS      current
		DESCRIPTION
			"Record."
		::= { swhEventLog 3 }

	swhEventLogSequence OBJECT-TYPE
		SYNTAX      INTEGER { newest-to-oldest(0), oldest-to-newest(1) }
		MAX-ACCESS  read-write
		STATUS      current
		DESCRIPTION
			"Sequence."
		::= { swhEventLog 4 }

	swhEventLogStart OBJECT-TYPE
		SYNTAX      INTEGER (0..2147483647)
		MAX-ACCESS  read-write
		STATUS      current
		DESCRIPTION
			"Start from."
		::= { swhEventLog 5 }

	swhEventLogEntries OBJECT-TYPE
		SYNTAX      INTEGER (0..2147483647)
		MAX-ACCESS  read-write
		STATUS      current
		DESCRIPTION
			"Entries per page."
		::= { swhEventLog 6 }

	swhEventLogTimePolicy OBJECT-TYPE
		SYNTAX      INTEGER { all-time(0), exclued(1), include(2) }
		MAX-ACCESS  read-write
		STATUS      current
		DESCRIPTION
			"Time Policy."
		::= { swhEventLog 10 }

	swhEventLogTimeRange OBJECT-TYPE
		SYNTAX      INTEGER { up-time(0), ntp-time(1) }
		MAX-ACCESS  read-write
		STATUS      current
		DESCRIPTION
			"Time Range."
		::= { swhEventLog 11 }

	swhEventLogUpTimeStartHour OBJECT-TYPE
		SYNTAX      INTEGER (0..2147483647)
		MAX-ACCESS  read-write
		STATUS      current
		DESCRIPTION
			"Start Hour of Event Up Time. (0-23)"
		::= { swhEventLog 12 }

	swhEventLogUpTimeStartMin OBJECT-TYPE
		SYNTAX      INTEGER (0..2147483647)
		MAX-ACCESS  read-write
		STATUS      current
		DESCRIPTION
			"Start Minute of Event Up Time. (0-59)"
		::= { swhEventLog 13 }

	swhEventLogUpTimeStartDay OBJECT-TYPE
		SYNTAX      INTEGER (0..2147483647)
		MAX-ACCESS  read-write
		STATUS      current
		DESCRIPTION
			"Start Day of Event Up Time. (0-9999)"
		::= { swhEventLog 14 }

	swhEventLogUpTimeEndHour OBJECT-TYPE
		SYNTAX      INTEGER (0..2147483647)
		MAX-ACCESS  read-write
		STATUS      current
		DESCRIPTION
			"End Hour of Event Up Time. (0-23)"
		::= { swhEventLog 15 }

	swhEventLogUpTimeEndMin OBJECT-TYPE
		SYNTAX      INTEGER (0..2147483647)
		MAX-ACCESS  read-write
		STATUS      current
		DESCRIPTION
			"End Minute of Event Up Time. (0-59)"
		::= { swhEventLog 16 }

	swhEventLogUpTimeEndDay OBJECT-TYPE
		SYNTAX      INTEGER (0..2147483647)
		MAX-ACCESS  read-write
		STATUS      current
		DESCRIPTION
			"End Day of Event Up Time. (0-9999)"
		::= { swhEventLog 17 }

	swhEventLogNTPStartHour OBJECT-TYPE
		SYNTAX      INTEGER (0..2147483647)
		MAX-ACCESS  read-write
		STATUS      current
		DESCRIPTION
			"Start Hour of Event NTP Time. (0-23)"
		::= { swhEventLog 18 }

	swhEventLogNTPStartMin OBJECT-TYPE
		SYNTAX      INTEGER (0..2147483647)
		MAX-ACCESS  read-write
		STATUS      current
		DESCRIPTION
			"Start Minute of Event NTP Time. (0-59)"
		::= { swhEventLog 19 }

	swhEventLogNTPStartDay OBJECT-TYPE
		SYNTAX      INTEGER (0..2147483647)
		MAX-ACCESS  read-write
		STATUS      current
		DESCRIPTION
			"Start Day of Event NTP Time. (1-31)"
		::= { swhEventLog 20 }

	swhEventLogNTPStartMonth OBJECT-TYPE
		SYNTAX      INTEGER (0..2147483647)
		MAX-ACCESS  read-write
		STATUS      current
		DESCRIPTION
			"Start Month of Event NTP Time. (1-12)"
		::= { swhEventLog 21 }

	swhEventLogNTPStartYear OBJECT-TYPE
		SYNTAX      INTEGER (0..2147483647)
		MAX-ACCESS  read-write
		STATUS      current
		DESCRIPTION
			"Start Year of Event NTP Time. (2021-2037)"
		::= { swhEventLog 22 }

	swhEventLogNTPEndHour OBJECT-TYPE
		SYNTAX      INTEGER (0..2147483647)
		MAX-ACCESS  read-write
		STATUS      current
		DESCRIPTION
			"End Hour of Event NTP Time. (0-23)"
		::= { swhEventLog 23 }

	swhEventLogNTPEndMin OBJECT-TYPE
		SYNTAX      INTEGER (0..2147483647)
		MAX-ACCESS  read-write
		STATUS      current
		DESCRIPTION
			"End Minute of Event NTP Time. (0-59)"
		::= { swhEventLog 24 }

	swhEventLogNTPEndDay OBJECT-TYPE
		SYNTAX      INTEGER (0..2147483647)
		MAX-ACCESS  read-write
		STATUS      current
		DESCRIPTION
			"End Day of Event NTP Time. (1-31)"
		::= { swhEventLog 25 }

	swhEventLogNTPEndMonth OBJECT-TYPE
		SYNTAX      INTEGER (0..2147483647)
		MAX-ACCESS  read-write
		STATUS      current
		DESCRIPTION
			"End Month of Event NTP Time. (1-12)"
		::= { swhEventLog 26 }

	swhEventLogNTPEndYear OBJECT-TYPE
		SYNTAX      INTEGER (0..2147483647)
		MAX-ACCESS  read-write
		STATUS      current
		DESCRIPTION
			"End Year of Event NTP Time. (2021-2037)"
		::= { swhEventLog 27 }

	swhEventLogItemPolicy OBJECT-TYPE
		SYNTAX      INTEGER { all-item(0), exclued(1), include(2) }
		MAX-ACCESS  read-write
		STATUS      current
		DESCRIPTION
			"Policy."
		::= { swhEventLog 28 }

	swhEventLogItemList OBJECT-TYPE
		SYNTAX      DisplayString
		MAX-ACCESS  read-write
		STATUS      current
		DESCRIPTION
			"Event Log Item List: 
			 1. Information 
			 2. Warning 
			 3. Error 
			 4. Auto backup failed 
			 5. Auto backup succeeded 
			 6. CLI disconnected 
			 7. Cold start 
			 8. Console port link 
			 9. CPU loading 
			 10. CPU temperature failed 
			 11. CPU temperature normal 
			 12. CPU temperature overheat 
			 13. DHCP snooping 
			 14. Digital input abnormal 
			 15. Digital input normal 
			 16. Ethernet OAM peer state 
			 17. Ethernet OAM link monitoring 
			 18. Ethernet OAM remote loopback 
			 19. Fast redundancy abnormal 
			 20. Fast redundancy normal 
			 21. Fast redundancy signal fail 
			 22. Link down 
			 23. Link up 
			 24. Login 
			 25. Login failed 
			 26. Logout 
			 27. Loop detection 
			 28. MAC limit 
			 29. Port loopback test 
			 30. Power module down 
			 31. SFP RX power OK 
			 32. SFP RX power overheat 
			 33. SFP RX power too low 
			 34. SFP temperature ok 
			 35. SFP temperature overheat 
			 36. SFP temperature too low 
			 37. SFP TX power ok 
			 38. SFP TX power overheat 
			 39. SFP TX power too low 
			 40. SFP voltage ok 
			 41. SFP voltage overheat 
			 42. SFP voltage too low 
			 43. SNMP inform 
			 44. Storm control 
			 45. System voltage warning 
			 46. Update failed 
			 47. Warm start"
		::= { swhEventLog 29 }

	swhEventLogItemSelected OBJECT-TYPE
		SYNTAX      DisplayString
		MAX-ACCESS  read-only
		STATUS      current
		DESCRIPTION
			"Selected."
		::= { swhEventLog 30 }

	swhEventLogPageSelect OBJECT-TYPE
		SYNTAX      INTEGER (0..2147483647)
		MAX-ACCESS  read-write
		STATUS      current
		DESCRIPTION
			"Page Select."
		::= { swhEventLog 8 }

	swhEventLogPageTotal OBJECT-TYPE
		SYNTAX      INTEGER (0..2147483647)
		MAX-ACCESS  read-only
		STATUS      current
		DESCRIPTION
			"Page Total."
		::= { swhEventLog 9 }

	swhEventLogFilterReset OBJECT-TYPE
		SYNTAX      INTEGER { normal(0), reset(1) }
		MAX-ACCESS  read-write
		STATUS      current
		DESCRIPTION
			"Reset Event Log Filter Configuration."
		::= { swhEventLog 7 }

	-- Table Entry
	swhEventLogEntry OBJECT-TYPE
		SYNTAX      SwhEventLogEntry
		MAX-ACCESS  not-accessible
		STATUS      current
		DESCRIPTION
			"An entry in the table, containing information about event log."
		INDEX    { swhEventLogIndex }
		::= { swhEventLogTable 1 }

	SwhEventLogEntry ::=
		SEQUENCE {
			swhEventLogIndex
				INTEGER,
			swhEventLogNumber
				INTEGER,
			swhEventLogType
				INTEGER,
			swhEventLogNTPTime
				DisplayString,
			swhEventLogUpTime
				DisplayString,
			swhEventLogDescription
				DisplayString
		}

	swhEventLogIndex OBJECT-TYPE
		SYNTAX      INTEGER (0..2147483647)
		MAX-ACCESS  not-accessible
		STATUS      current
		DESCRIPTION
			"A unique value for each index."
		::= { swhEventLogEntry 1 }

	swhEventLogType OBJECT-TYPE
		SYNTAX      INTEGER { error(1000), warning(2000), information(3000) }
		MAX-ACCESS  read-only
		STATUS      current
		DESCRIPTION
			"Type. 
			 error: some funtions not work 
			 warning: to warn something, ex. login failed 
			 information: just something happened"
		::= { swhEventLogEntry 2 }

	swhEventLogNTPTime OBJECT-TYPE
		SYNTAX      DisplayString
		MAX-ACCESS  read-only
		STATUS      current
		DESCRIPTION
			"NTP Time, it is local time."
		::= { swhEventLogEntry 3 }

	swhEventLogUpTime OBJECT-TYPE
		SYNTAX      DisplayString
		MAX-ACCESS  read-only
		STATUS      current
		DESCRIPTION
			"Up Time, it is system up time."
		::= { swhEventLogEntry 4 }

	swhEventLogDescription OBJECT-TYPE
		SYNTAX      DisplayString
		MAX-ACCESS  read-only
		STATUS      current
		DESCRIPTION
			"Description."
		::= { swhEventLogEntry 5 }

	swhEventLogNumber OBJECT-TYPE
		SYNTAX      INTEGER (0..2147483647)
		MAX-ACCESS  read-only
		STATUS      current
		DESCRIPTION
			"A unique value for event log index number."
		::= { swhEventLogEntry 11 }


-- SystemUtility(6).UpdateFirmware(4)

	swhUpdateProtocol OBJECT-TYPE
		SYNTAX      INTEGER { tftp(0), ftp(1) }
		MAX-ACCESS  read-write
		STATUS      current
		DESCRIPTION
			"Update file from TFTP or FTP server."
		::= { swhUpdateFirmware 1 }

	swhUpdateFileType OBJECT-TYPE
		SYNTAX      INTEGER { firmware(0), configuration(1) }
		MAX-ACCESS  read-write
		STATUS      current
		DESCRIPTION
			"File Type."
		::= { swhUpdateFirmware 2 }

	swhUpdateConfigeType OBJECT-TYPE
		SYNTAX      INTEGER { running(0), default(1) , startup(2) }
		MAX-ACCESS  read-write
		STATUS      current
		DESCRIPTION
			"Confige Type."
		::= { swhUpdateFirmware 15 }

	swhUpdateImageOption OBJECT-TYPE
		SYNTAX      INTEGER { image1(1), image2(2) }
		MAX-ACCESS  read-write
		STATUS      current
		DESCRIPTION
			"Image Option."
		::= { swhUpdateFirmware 16 }

	swhUpdateServerIPAddr OBJECT-TYPE
		SYNTAX      IpAddress
		MAX-ACCESS  read-write
		STATUS      current
		DESCRIPTION
			"TFTP/FTP server IP address."
		::= { swhUpdateFirmware 3 }

	swhUpdateServerIPv6Addr OBJECT-TYPE
		SYNTAX      DisplayString
		MAX-ACCESS  read-write
		STATUS      current
		DESCRIPTION
			"TFTP/FTP server IPv6 address."
		::= { swhUpdateFirmware 13 }

	swhUpdateUserName OBJECT-TYPE
		SYNTAX      DisplayString
		MAX-ACCESS  read-write
		STATUS      current
		DESCRIPTION
			"FTP server login user name."
		::= { swhUpdateFirmware 4 }

	swhUpdatePassword OBJECT-TYPE
		SYNTAX      DisplayString
		MAX-ACCESS  read-write
		STATUS      current
		DESCRIPTION
			"FTP server login password."
		::= { swhUpdateFirmware 5 }

	swhUpdateFileLocation OBJECT-TYPE
		SYNTAX      DisplayString
		MAX-ACCESS  read-write
		STATUS      current
		DESCRIPTION
			"File Location."
		::= { swhUpdateFirmware 6 }

	swhUpdatePut OBJECT-TYPE
		SYNTAX      INTEGER { normal(0), put(1) }
		MAX-ACCESS  read-write
		STATUS      current
		DESCRIPTION
			"Put file to server."
		::= { swhUpdateFirmware 8 }

	swhUpdateUpdate OBJECT-TYPE
		SYNTAX      INTEGER { normal(0), update(1) }
		MAX-ACCESS  read-write
		STATUS      current
		DESCRIPTION
			"Get configuration or firmware, then update it. 
			 When update succeeded, system will reboot automatically."
		::= { swhUpdateFirmware 10 }

	swhUpdateState OBJECT-TYPE
		SYNTAX      DisplayString
		MAX-ACCESS  read-only
		STATUS      current
		DESCRIPTION
			"Messages for getting/putting file, updating config/firmware."
		::= { swhUpdateFirmware 12 }


-- SystemUtility(6).AutoBackupConfiguration(5)

	swhBackupNTPStatus OBJECT-TYPE
		SYNTAX      DisplayString
		MAX-ACCESS  read-only
		STATUS      current
		DESCRIPTION
			"NTP Status."
		::= { swhAutoBackupConfiguration 14 }

	swhBackupAutoBackup OBJECT-TYPE
		SYNTAX      INTEGER { disable(0), enable(1) }
		MAX-ACCESS  read-write
		STATUS      current
		DESCRIPTION
			"Auto Backup. 
			 In order for the Auto Backup function to work properly, 
			 the NTP function must be enabled for the device to acquire local time information."
		::= { swhAutoBackupConfiguration 2 }

	swhBackupBackupTime OBJECT-TYPE
		SYNTAX      INTEGER (0..23)
		MAX-ACCESS  read-write
		STATUS      current
		DESCRIPTION
			"Backup time at which hour of a day."
		::= { swhAutoBackupConfiguration 3 }

	swhBackupProtocol OBJECT-TYPE
		SYNTAX      INTEGER { tftp(0), ftp(1) }
		MAX-ACCESS  read-write
		STATUS      current
		DESCRIPTION
			"Backup file from TFTP or FTP server."
		::= { swhAutoBackupConfiguration 4 }

	swhBackupFileType OBJECT-TYPE
		SYNTAX      INTEGER { configuration(1) }
		MAX-ACCESS  read-only
		STATUS      current
		DESCRIPTION
			"Backup File Type."
		::= { swhAutoBackupConfiguration 5 }

	swhBackupServerIPAddr OBJECT-TYPE
		SYNTAX      DisplayString
		MAX-ACCESS  read-write
		STATUS      current
		DESCRIPTION
			"TFTP/FTP server IP address."
		::= { swhAutoBackupConfiguration 6 }

	swhBackupUserName OBJECT-TYPE
		SYNTAX      DisplayString
		MAX-ACCESS  read-write
		STATUS      current
		DESCRIPTION
			"FTP server login user name."
		::= { swhAutoBackupConfiguration 7 }

	swhBackupPassword OBJECT-TYPE
		SYNTAX      DisplayString
		MAX-ACCESS  read-write
		STATUS      current
		DESCRIPTION
			"FTP server login password."
		::= { swhAutoBackupConfiguration 8 }

	swhBackupFileDirectory OBJECT-TYPE
		SYNTAX      DisplayString
		MAX-ACCESS  read-write
		STATUS      current
		DESCRIPTION
			"File Directory."
		::= { swhAutoBackupConfiguration 9 }

	swhBackupFileName OBJECT-TYPE
		SYNTAX      DisplayString
		MAX-ACCESS  read-only
		STATUS      current
		DESCRIPTION
			"File Name."
		::= { swhAutoBackupConfiguration 10 }

	swhBackupBackupState OBJECT-TYPE
		SYNTAX      DisplayString
		MAX-ACCESS  read-only
		STATUS      current
		DESCRIPTION
			"Messages for backup."
		::= { swhAutoBackupConfiguration 12 }


-- SystemUtility(6).CableDiagnostics(6)

	swhCableDiagnosticsPortNumber OBJECT-TYPE
		SYNTAX      INTEGER { port01(0),
		                      port02(1),
		                      port03(2),
		                      port04(3),
		                      port05(4),
		                      port06(5),
		                      port07(6),
		                      port08(7),
		                      port09(8),
		                      port10(9)
		                    }
		MAX-ACCESS  read-write
		STATUS      current
		DESCRIPTION
			"Port Number. 
			 The cable diagnosis function may affect services on the interface in a short period of time, 
			 and the interface in up state may alternate between up and down. 
			 The test result is only for reference and may be inaccurate when 
			 the interface is in the Up state or the remote interface is shut down. 
			 If the target interface works at a rate of 10Mbps, 
			 please disconnect the remote interface first before starting the cable diagnosis function. 
			 Note: Please re-select the port number to use the cable test on the same port."
		::= { swhCableDiagnostics 1 }

	swhCableDiagnosticsPortType OBJECT-TYPE
		SYNTAX      DisplayString
		MAX-ACCESS  read-only
		STATUS      current
		DESCRIPTION
			"Port Type."
		::= { swhCableDiagnostics 2 }

	swhCableDiagnosticsPortSpeed OBJECT-TYPE
		SYNTAX      DisplayString
		MAX-ACCESS  read-only
		STATUS      current
		DESCRIPTION
			"Port Speed."
		::= { swhCableDiagnostics 3 }


-- SystemUtility(6).CableDiagnostics(6).CableDiagnosticsTable(5)

	swhCableDiagnosticsTable OBJECT-TYPE
		SYNTAX      SEQUENCE OF SwhCableDiagnosticsEntry
		MAX-ACCESS  not-accessible
		STATUS      current
		DESCRIPTION
			"Table of cable diagnostics."
		::= { swhCableDiagnostics 5 }

	-- Table Entry
	swhCableDiagnosticsEntry OBJECT-TYPE
		SYNTAX      SwhCableDiagnosticsEntry
		MAX-ACCESS  not-accessible
		STATUS      current
		DESCRIPTION
			"An entry in the table, containing information about cable diagnostics."
		INDEX    { swhCableDiagnosticsIndex }
		::= { swhCableDiagnosticsTable 1 }

	SwhCableDiagnosticsEntry ::=
		SEQUENCE {
			swhCableDiagnosticsIndex
				INTEGER,
			swhCableDiagnosticsLocalPair
				DisplayString,
			swhCableDiagnosticsPairStatus
				DisplayString,
			swhCableDiagnosticsCableLength
				DisplayString
		}

	swhCableDiagnosticsIndex OBJECT-TYPE
		SYNTAX      INTEGER (0..2147483647)
		MAX-ACCESS  not-accessible
		STATUS      current
		DESCRIPTION
			"A unique value for each index."
		::= { swhCableDiagnosticsEntry 1 }

	swhCableDiagnosticsLocalPair OBJECT-TYPE
		SYNTAX      DisplayString
		MAX-ACCESS  read-only
		STATUS      current
		DESCRIPTION
			"Local Pair."
		::= { swhCableDiagnosticsEntry 2 }

	swhCableDiagnosticsCableLength OBJECT-TYPE
		SYNTAX      DisplayString
		MAX-ACCESS  read-only
		STATUS      current
		DESCRIPTION
			"Cable Length. (m)"
		::= { swhCableDiagnosticsEntry 3 }

	swhCableDiagnosticsPairStatus OBJECT-TYPE
		SYNTAX      DisplayString
		MAX-ACCESS  read-only
		STATUS      current
		DESCRIPTION
			"Pair Status."
		::= { swhCableDiagnosticsEntry 4 }


-- SystemUtility(6).FirmwareCopy(8)

	swhFirmwareCopyImage OBJECT-TYPE
		SYNTAX      INTEGER { normal(0), copy(1) }
		MAX-ACCESS  read-write
		STATUS      current
		DESCRIPTION
			"Current image-1 copy to backup image-2 or Current image-2 copy to backup image-1."
		::= { swhFirmwareCopy 1 }

	swhFirmwareCopyStatus OBJECT-TYPE
		SYNTAX      DisplayString
		MAX-ACCESS  read-only
		STATUS      current
		DESCRIPTION
			"Copy Status."
		::= { swhFirmwareCopy 4 }

	swhFirmwareCurrentBootImage OBJECT-TYPE
		SYNTAX      DisplayString
		MAX-ACCESS  read-only
		STATUS      current
		DESCRIPTION
			"Current Boot Image."
		::= { swhFirmwareCopy 5 }

	swhFirmwareConfiguredBootImage OBJECT-TYPE
		SYNTAX      DisplayString
		MAX-ACCESS  read-only
		STATUS      current
		DESCRIPTION
			"Configured Boot Image."
		::= { swhFirmwareCopy 6 }

	swhFirmwareImage1Version OBJECT-TYPE
		SYNTAX      DisplayString
		MAX-ACCESS  read-only
		STATUS      current
		DESCRIPTION
			"Image-1 Version."
		::= { swhFirmwareCopy 7 }

	swhFirmwareImage2Version OBJECT-TYPE
		SYNTAX      DisplayString
		MAX-ACCESS  read-only
		STATUS      current
		DESCRIPTION
			"Image-2 Version."
		::= { swhFirmwareCopy 8 }


-- SystemUtility(6).PortLinkFlapLog(9)

	swhPortLinkFlapLogPort OBJECT-TYPE
		SYNTAX      INTEGER { port01(0),
		                      port02(1),
		                      port03(2),
		                      port04(3),
		                      port05(4),
		                      port06(5),
		                      port07(6),
		                      port08(7),
		                      port09(8),
		                      port10(9),
		                      port11(10),
		                      port12(11)
		                    }
		MAX-ACCESS  read-write
		STATUS      current
		DESCRIPTION
			"Per port search link flap log."
		::= { swhPortLinkFlapLog 1 }

	swhPortLinkFlapLogClear OBJECT-TYPE
		SYNTAX      INTEGER { normal(0), clear(1) }
		MAX-ACCESS  read-write
		STATUS      current
		DESCRIPTION
			"Clear link flap log."
		::= { swhPortLinkFlapLog 2 }

	swhPortLinkFlapLogLocalTime OBJECT-TYPE
		SYNTAX      DisplayString
		MAX-ACCESS  read-only
		STATUS      current
		DESCRIPTION
			"Local Time."
		::= { swhPortLinkFlapLog 3 }

	swhPortLinkFlapLogTotalPortFlaps OBJECT-TYPE
		SYNTAX      INTEGER (0..2147483647)
		MAX-ACCESS  read-only
		STATUS      current
		DESCRIPTION
			"Total Port Flaps."
		::= { swhPortLinkFlapLog 4 }


-- SystemUtility(6).PortLinkFlapLog(9).PortLinkFlapLogTable(5)

	swhPortLinkFlapLogTable OBJECT-TYPE
		SYNTAX      SEQUENCE OF SwhPortLinkFlapLogEntry
		MAX-ACCESS  not-accessible
		STATUS      current
		DESCRIPTION
			"Table of port link flap log."
		::= { swhPortLinkFlapLog 5 }

	-- Table Entry
	swhPortLinkFlapLogEntry OBJECT-TYPE
		SYNTAX      SwhPortLinkFlapLogEntry
		MAX-ACCESS  not-accessible
		STATUS      current
		DESCRIPTION
			"An entry in the table, containing information about port link flap log."
		INDEX    { swhPortLinkFlapLogIndex }
		::= { swhPortLinkFlapLogTable 1 }

	SwhPortLinkFlapLogEntry ::=
		SEQUENCE {
			swhPortLinkFlapLogIndex
				INTEGER,
			swhPortLinkFlapLogNumber
				INTEGER,
			swhPortLinkFlapLogNTPTime
				DisplayString,
			swhPortLinkFlapLogUpTime
				DisplayString,
			swhPortLinkFlapLogPortStatus
				DisplayString,
			swhPortLinkFlapLogDescription
				DisplayString,
			swhPortLinkFlapLogWhenFlapped
				DisplayString,
			swhPortLinkFlapLogStatusDuration
				DisplayString,
			swhPortLinkFlapLogSFPRXPower
				DisplayString
		}

	swhPortLinkFlapLogIndex OBJECT-TYPE
		SYNTAX      INTEGER (0..2147483647)
		MAX-ACCESS  not-accessible
		STATUS      current
		DESCRIPTION
			"A unique value for each index."
		::= { swhPortLinkFlapLogEntry 1 }

	swhPortLinkFlapLogNumber OBJECT-TYPE
		SYNTAX      INTEGER (0..2147483647)
		MAX-ACCESS  read-only
		STATUS      current
		DESCRIPTION
			"A unique value for port link flap log index number."
		::= { swhPortLinkFlapLogEntry 2 }

	swhPortLinkFlapLogNTPTime OBJECT-TYPE
		SYNTAX      DisplayString
		MAX-ACCESS  read-only
		STATUS      current
		DESCRIPTION
			"NTP Time, it is local time."
		::= { swhPortLinkFlapLogEntry 3 }

	swhPortLinkFlapLogUpTime OBJECT-TYPE
		SYNTAX      DisplayString
		MAX-ACCESS  read-only
		STATUS      current
		DESCRIPTION
			"Up Time, it is system up time."
		::= { swhPortLinkFlapLogEntry 4 }

	swhPortLinkFlapLogPortStatus OBJECT-TYPE
		SYNTAX      DisplayString
		MAX-ACCESS  read-only
		STATUS      current
		DESCRIPTION
			"Port Status."
		::= { swhPortLinkFlapLogEntry 5 }

	swhPortLinkFlapLogDescription OBJECT-TYPE
		SYNTAX      DisplayString
		MAX-ACCESS  read-only
		STATUS      current
		DESCRIPTION
			"Description."
		::= { swhPortLinkFlapLogEntry 6 }

	swhPortLinkFlapLogWhenFlapped OBJECT-TYPE
		SYNTAX      DisplayString
		MAX-ACCESS  read-only
		STATUS      current
		DESCRIPTION
			"When Flapped."
		::= { swhPortLinkFlapLogEntry 7 }

	swhPortLinkFlapLogStatusDuration OBJECT-TYPE
		SYNTAX      DisplayString
		MAX-ACCESS  read-only
		STATUS      current
		DESCRIPTION
			"Status Duration."
		::= { swhPortLinkFlapLogEntry 8 }

	swhPortLinkFlapLogSFPRXPower OBJECT-TYPE
		SYNTAX      DisplayString
		MAX-ACCESS  read-only
		STATUS      current
		DESCRIPTION
			"SFP RX Power. (dBm)"
		::= { swhPortLinkFlapLogEntry 9 }


-- SystemUtility(6).PortLoopbackTest(12).PortLoopbackTestTable(1)

	swhPortLoopbackTestTable OBJECT-TYPE
		SYNTAX      SEQUENCE OF SwhPortLoopbackTestEntry
		MAX-ACCESS  not-accessible
		STATUS      current
		DESCRIPTION
			"Table of Port Loopback Test."
		::= { swhPortLoopbackTest 1 }

	-- Table Entry
	swhPortLoopbackTestEntry OBJECT-TYPE
		SYNTAX      SwhPortLoopbackTestEntry
		MAX-ACCESS  not-accessible
		STATUS      current
		DESCRIPTION
			"An entry in the table, containing information about Port Loopback Test."
		INDEX    { swhPortLoopbackTestPort }
		::= { swhPortLoopbackTestTable 1 }

	SwhPortLoopbackTestEntry ::=
		SEQUENCE {
			swhPortLoopbackTestPort
				INTEGER,
			swhPortLoopbackTestLoopbackStatus
				DisplayString,
			swhPortLoopbackTestDuration
				INTEGER,
			swhPortLoopbackTestRemainingTime
				DisplayString,
			swhPortLoopbackTestActiontStart
				INTEGER,
			swhPortLoopbackTestActionStop
				INTEGER,
			swhPortLoopbackTestLastRun
				DisplayString
		}

	swhPortLoopbackTestPort OBJECT-TYPE
		SYNTAX      INTEGER (0..2147483647)
		MAX-ACCESS  not-accessible
		STATUS      current
		DESCRIPTION
			"A unique value for each port."
		::= { swhPortLoopbackTestEntry 1 }

	swhPortLoopbackTestLoopbackStatus OBJECT-TYPE
		SYNTAX      DisplayString
		MAX-ACCESS  read-only
		STATUS      current
		DESCRIPTION
			"Loopback Status."
		::= { swhPortLoopbackTestEntry 2 }

	swhPortLoopbackTestDuration OBJECT-TYPE
		SYNTAX      INTEGER (1..10)
		MAX-ACCESS  read-write
		STATUS      current
		DESCRIPTION
			"Duration. (1-10)"
		::= { swhPortLoopbackTestEntry 3 }

	swhPortLoopbackTestRemainingTime OBJECT-TYPE
		SYNTAX      DisplayString
		MAX-ACCESS  read-only
		STATUS      current
		DESCRIPTION
			"Remaining Time."
		::= { swhPortLoopbackTestEntry 4 }

	swhPortLoopbackTestActiontStart OBJECT-TYPE
		SYNTAX      INTEGER { normal(0), start(1) }
		MAX-ACCESS  read-write
		STATUS      current
		DESCRIPTION
			"Actiont Start."
		::= { swhPortLoopbackTestEntry 5 }

	swhPortLoopbackTestActionStop OBJECT-TYPE
		SYNTAX      INTEGER { normal(0), stop(1) }
		MAX-ACCESS  read-write
		STATUS      current
		DESCRIPTION
			"Action Stop."
		::= { swhPortLoopbackTestEntry 6 }

	swhPortLoopbackTestLastRun OBJECT-TYPE
		SYNTAX      DisplayString
		MAX-ACCESS  read-only
		STATUS      current
		DESCRIPTION
			"Last Run."
		::= { swhPortLoopbackTestEntry 7 }


-- Traps(9)

	swhSystemPowerDown NOTIFICATION-TYPE
		STATUS        current
		--&ACTIONS    { critical }
		--&MESG       "System Power Down"
		DESCRIPTION   "When system power down, send this trap."
		::= { switchTraps 1 }

	swhFaultAlarm NOTIFICATION-TYPE
		OBJECTS       { ifIndex, sysLocation }
		STATUS        current
		--&ACTIONS    { warning }
		--&MESG       "$2"
		DESCRIPTION   "When fault Alarm, send this trap."
		::= { switchTraps 8 }

	swhWarningAlarm NOTIFICATION-TYPE
		OBJECTS       { ifIndex, sysLocation }
		STATUS        current
		--&ACTIONS    { warning }
		--&MESG       "$2"
		DESCRIPTION   "When Warning Alarm, send this trap."
		::= { switchTraps 9 }

	swhMinorAlarm NOTIFICATION-TYPE
		OBJECTS       { ifIndex, sysLocation }
		STATUS        current
		--&ACTIONS    { minor }
		--&MESG       "$2"
		DESCRIPTION   "When Minor Alarm, send this trap."
		::= { switchTraps 10 }

	swhCriticalAlarm NOTIFICATION-TYPE
		OBJECTS       { ifIndex, sysLocation }
		STATUS        current
		--&ACTIONS    { critical }
		--&MESG       "$2"
		DESCRIPTION   "When Critical Alarm(Alert), send this trap."
		::= { switchTraps 12 }

	swhLoopBack NOTIFICATION-TYPE
		OBJECTS       { ifIndex, sysLocation }
		STATUS        current
		--&ACTIONS    { warning }
		--&MESG       "$2"
		DESCRIPTION   "When Loop back, send this trap."
		::= { switchTraps 13 }

	swhNormalAlarm NOTIFICATION-TYPE
		OBJECTS       { ifIndex, sysLocation }
		STATUS        current
		--&ACTIONS    { normal }
		--&MESG       "$2"
		DESCRIPTION   "When Normal Alarm(Information), send this trap."
		::= { switchTraps 16 }

	swhCaseFanState NOTIFICATION-TYPE
		OBJECTS       { ifIndex, sysLocation }
		STATUS        current
		--&ACTIONS    { warning }
		--&MESG       "Fan $1 $2"
		DESCRIPTION   "Fan State."
		::= { switchTraps 19 }

	swhSystemPowerOn NOTIFICATION-TYPE
		OBJECTS       { ifIndex, sysLocation }
		STATUS        current
		--&ACTIONS    { critical }
		--&MESG       "$2"
		DESCRIPTION   "When system power up, send this trap."
		::= { switchTraps 20 }

	swhSystemPowerUp NOTIFICATION-TYPE
		STATUS        current
		--&ACTIONS    { normal }
		--&MESG       "System Power Up"
		DESCRIPTION   "When system power up, send this trap."
		::= { switchTraps 21 }

	swhSystemUp NOTIFICATION-TYPE
		STATUS        current
		--&ACTIONS    { normal }
		--&MESG       "System Up"
		DESCRIPTION   "When system up, send this trap."
		::= { switchTraps 25 }


-- EthernetOAM(24)

	swhOAMSetup
		OBJECT IDENTIFIER ::= { swhEthernetOAM 1 }

	swhOAMLoopback
		OBJECT IDENTIFIER ::= { swhEthernetOAM 2 }

	swhOAMStatus
		OBJECT IDENTIFIER ::= { swhEthernetOAM 3 }

	swhOAMStatistics
		OBJECT IDENTIFIER ::= { swhEthernetOAM 4 }

	swhOAMRemoteModule
		OBJECT IDENTIFIER ::= { swhEthernetOAM 5 }


-- EthernetOAM(24).OAMSetup(1)

	swhOAMState OBJECT-TYPE
		SYNTAX      INTEGER { disable(0), enable(1) }
		MAX-ACCESS  read-write
		STATUS      current
		DESCRIPTION
			"OAM State."
		::= { swhOAMSetup 1 }

	swhOAMSetupTable OBJECT-TYPE
		SYNTAX      SEQUENCE OF SwhOAMSetupEntry
		MAX-ACCESS  not-accessible
		STATUS      current
		DESCRIPTION
			"Table of OAM setup."
		::= { swhOAMSetup 5 }

	-- Table Entry
	swhOAMSetupEntry OBJECT-TYPE
		SYNTAX      SwhOAMSetupEntry
		MAX-ACCESS  not-accessible
		STATUS      current
		DESCRIPTION
			"An entry in the table, containing information about OAM setup."
		INDEX    { swhOAMSetupPort }
		::= { swhOAMSetupTable 1 }

	SwhOAMSetupEntry ::=
		SEQUENCE {
			swhOAMSetupPort
				INTEGER,
			swhOAMSetupOAMEnable
				INTEGER,
			swhOAMSetupOAMMode
				INTEGER,
			swhOAMSetupRemoteTimeout
				INTEGER,
			swhOAMSetupOperationalStatus
				DisplayString,
			swhOAMSetupRestartOAMSession
				INTEGER
		}

	swhOAMSetupPort OBJECT-TYPE
		SYNTAX      INTEGER (0..2147483647)
		MAX-ACCESS  read-only
		STATUS      current
		DESCRIPTION
			"A unique value for each port."
		::= { swhOAMSetupEntry 1 }

	swhOAMSetupOAMEnable OBJECT-TYPE
		SYNTAX      INTEGER { disable(0), enable(1) }
		MAX-ACCESS  read-write
		STATUS      current
		DESCRIPTION
			"OAM Enable."
		::= { swhOAMSetupEntry 2 }

	swhOAMSetupOAMMode OBJECT-TYPE
		SYNTAX      INTEGER { passive(0), active(1) }
		MAX-ACCESS  read-write
		STATUS      current
		DESCRIPTION
			"OAM Mode."
		::= { swhOAMSetupEntry 3 }

	swhOAMSetupRemoteTimeout OBJECT-TYPE
		SYNTAX      INTEGER (5..30)
		MAX-ACCESS  read-write
		STATUS      current
		DESCRIPTION
			"Remote Timeout. (5-30)"
		::= { swhOAMSetupEntry 4 }

	swhOAMSetupOperationalStatus OBJECT-TYPE
		SYNTAX      DisplayString
		MAX-ACCESS  read-only
		STATUS      current
		DESCRIPTION
			"Operational Status."
		::= { swhOAMSetupEntry 5 }

	swhOAMSetupRestartOAMSession OBJECT-TYPE
		SYNTAX      INTEGER { normal(0), restart(1) }
		MAX-ACCESS  read-write
		STATUS      current
		DESCRIPTION
			"Restart OAM Session."
		::= { swhOAMSetupEntry 6 }


-- EthernetOAM(24).OAMLoopback(2)

	swhOAMLoopbackTable OBJECT-TYPE
		SYNTAX      SEQUENCE OF SwhOAMLoopbackEntry
		MAX-ACCESS  not-accessible
		STATUS      current
		DESCRIPTION
			"Table of loopback control."
		::= { swhOAMLoopback 5 }

	-- Table Entry
	swhOAMLoopbackEntry OBJECT-TYPE
		SYNTAX      SwhOAMLoopbackEntry
		MAX-ACCESS  not-accessible
		STATUS      current
		DESCRIPTION
			"An entry in the table, containing information about loopback control."
		INDEX    { swhOAMLoopbackPort }
		::= { swhOAMLoopbackTable 1 }

	SwhOAMLoopbackEntry ::=
		SEQUENCE {
			swhOAMLoopbackPort
				INTEGER,
			swhOAMLoopbackIgnoreRequest
				INTEGER,
			swhOAMLoopbackOAMState
				INTEGER,
			swhOAMLoopbackOAMMode
				DisplayString,
			swhOAMLoopbackOperationalStatus
				DisplayString,
			swhOAMLoopbackLoopbackStatus
				DisplayString,
			swhOAMLoopbackRemainingTime
				DisplayString,
			swhOAMLoopbackRemoteRequestStart
				INTEGER,
			swhOAMLoopbackRemoteRequestStop
				INTEGER,
			swhOAMLoopbackDuration
				INTEGER
		}

	swhOAMLoopbackPort OBJECT-TYPE
		SYNTAX      INTEGER (0..2147483647)
		MAX-ACCESS  read-only
		STATUS      current
		DESCRIPTION
			"A unique value for each port."
		::= { swhOAMLoopbackEntry 1 }

	swhOAMLoopbackIgnoreRequest OBJECT-TYPE
		SYNTAX      INTEGER { disable(0), enable(1) }
		MAX-ACCESS  read-write
		STATUS      current
		DESCRIPTION
			"Ignore Request."
		::= { swhOAMLoopbackEntry 2 }

	swhOAMLoopbackOAMState OBJECT-TYPE
		SYNTAX      INTEGER { disable(0), enable(1) }
		MAX-ACCESS  read-only
		STATUS      current
		DESCRIPTION
			"OAM State."
		::= { swhOAMLoopbackEntry 3 }

	swhOAMLoopbackOAMMode OBJECT-TYPE
		SYNTAX      DisplayString
		MAX-ACCESS  read-only
		STATUS      current
		DESCRIPTION
			"OAM Mode."
		::= { swhOAMLoopbackEntry 4 }

	swhOAMLoopbackOperationalStatus OBJECT-TYPE
		SYNTAX      DisplayString
		MAX-ACCESS  read-only
		STATUS      current
		DESCRIPTION
			"Operational Status."
		::= { swhOAMLoopbackEntry 5 }

	swhOAMLoopbackLoopbackStatus OBJECT-TYPE
		SYNTAX      DisplayString
		MAX-ACCESS  read-only
		STATUS      current
		DESCRIPTION
			"Loopback Status."
		::= { swhOAMLoopbackEntry 6 }

	swhOAMLoopbackRemainingTime OBJECT-TYPE
		SYNTAX      DisplayString
		MAX-ACCESS  read-only
		STATUS      current
		DESCRIPTION
			"Remaining Time."
		::= { swhOAMLoopbackEntry 7 }

	swhOAMLoopbackRemoteRequestStart OBJECT-TYPE
		SYNTAX      INTEGER { normal(0), start(1) }
		MAX-ACCESS  read-write
		STATUS      current
		DESCRIPTION
			"Remote Loopback Request Start."
		::= { swhOAMLoopbackEntry 8 }

	swhOAMLoopbackRemoteRequestStop OBJECT-TYPE
		SYNTAX      INTEGER { normal(0), stop(1) }
		MAX-ACCESS  read-write
		STATUS      current
		DESCRIPTION
			"Remote Loopback Request Stop."
		::= { swhOAMLoopbackEntry 9 }

	swhOAMLoopbackDuration OBJECT-TYPE
		SYNTAX      INTEGER (0..10)
		MAX-ACCESS  read-write
		STATUS      current
		DESCRIPTION
			"Duration. (0-10)"
		::= { swhOAMLoopbackEntry 10 }


-- EthernetOAM(24).OAMStatus(3)

	swhNeighborInformation
		OBJECT IDENTIFIER ::= { swhOAMStatus 1 }

	swhOAMFlags
		OBJECT IDENTIFIER ::= { swhOAMStatus 2 }

	swhOAMInformationTLVs
		OBJECT IDENTIFIER ::= { swhOAMStatus 3 }


-- EthernetOAM(24).OAMStatus(3).NeighborInformation(1)

	swhNeighborInfoTable OBJECT-TYPE
		SYNTAX      SEQUENCE OF SwhNeighborInfoEntry
		MAX-ACCESS  not-accessible
		STATUS      current
		DESCRIPTION
			"Table of neighbor information."
		::= { swhNeighborInformation 5 }

	-- Table Entry
	swhNeighborInfoEntry OBJECT-TYPE
		SYNTAX      SwhNeighborInfoEntry
		MAX-ACCESS  not-accessible
		STATUS      current
		DESCRIPTION
			"An entry in the table, containing information about neighbor information."
		INDEX    { swhNeighborInfoPort }
		::= { swhNeighborInfoTable 1 }

	SwhNeighborInfoEntry ::=
		SEQUENCE {
			swhNeighborInfoPort
				INTEGER,
			swhNeighborInfoMACAddress
				DisplayString,
			swhNeighborInfoVendor
				DisplayString,
			swhNeighborInfoPDURevision
				DisplayString,
			swhNeighborInfoMaxOAMPDUSize
				DisplayString
		}

	swhNeighborInfoPort OBJECT-TYPE
		SYNTAX      INTEGER (0..2147483647)
		MAX-ACCESS  read-only
		STATUS      current
		DESCRIPTION
			"A unique value for each port."
		::= { swhNeighborInfoEntry 1 }

	swhNeighborInfoMACAddress OBJECT-TYPE
		SYNTAX      DisplayString
		MAX-ACCESS  read-only
		STATUS      current
		DESCRIPTION
			"MAC Address."
		::= { swhNeighborInfoEntry 2 }

	swhNeighborInfoVendor OBJECT-TYPE
		SYNTAX      DisplayString
		MAX-ACCESS  read-only
		STATUS      current
		DESCRIPTION
			"Vendor (OUI)."
		::= { swhNeighborInfoEntry 3 }

	swhNeighborInfoPDURevision OBJECT-TYPE
		SYNTAX      DisplayString
		MAX-ACCESS  read-only
		STATUS      current
		DESCRIPTION
			"PDU Revision."
		::= { swhNeighborInfoEntry 4 }

	swhNeighborInfoMaxOAMPDUSize OBJECT-TYPE
		SYNTAX      DisplayString
		MAX-ACCESS  read-only
		STATUS      current
		DESCRIPTION
			"Max OAMPDU Size(Bytes)."
		::= { swhNeighborInfoEntry 5 }


-- EthernetOAM(24).OAMStatus(3).OAMFlags(2)

	swhOAMFlagsTable OBJECT-TYPE
		SYNTAX      SEQUENCE OF SwhOAMFlagsEntry
		MAX-ACCESS  not-accessible
		STATUS      current
		DESCRIPTION
			"Table of OAM flags."
		::= { swhOAMFlags 5 }

	-- Table Entry
	swhOAMFlagsEntry OBJECT-TYPE
		SYNTAX      SwhOAMFlagsEntry
		MAX-ACCESS  not-accessible
		STATUS      current
		DESCRIPTION
			"An entry in the table, containing information about OAM flags."
		INDEX    { swhOAMFlagsPort }
		::= { swhOAMFlagsTable 1 }

	SwhOAMFlagsEntry ::=
		SEQUENCE {
			swhOAMFlagsPort
				INTEGER,
			swhOAMFlagsOAMMode
				INTEGER,
			swhOAMFlagsLocalRemoteStable
				DisplayString,
			swhOAMFlagsLocalRemoteEvaluating
				DisplayString,
			swhOAMFlagsLocalLocalStable
				DisplayString,
			swhOAMFlagsLocalLocalEvaluating
				DisplayString,
			swhOAMFlagsLocalCriticalEvent
				DisplayString,
			swhOAMFlagsLocalDyingGasp
				DisplayString,
			swhOAMFlagsLocalLinkFault
				DisplayString,
			swhOAMFlagsRemoteRemoteStable
				DisplayString,
			swhOAMFlagsRemoteRemoteEvaluating
				DisplayString,
			swhOAMFlagsRemoteLocalStable
				DisplayString,
			swhOAMFlagsRemoteLocalEvaluating
				DisplayString,
			swhOAMFlagsRemoteCriticalEvent
				DisplayString,
			swhOAMFlagsRemoteDyingGasp
				DisplayString,
			swhOAMFlagsRemoteLinkFault
				DisplayString
		}

	swhOAMFlagsPort OBJECT-TYPE
		SYNTAX      INTEGER (0..2147483647)
		MAX-ACCESS  read-only
		STATUS      current
		DESCRIPTION
			"A unique value for each port."
		::= { swhOAMFlagsEntry 1 }

	swhOAMFlagsOAMMode OBJECT-TYPE
		SYNTAX      INTEGER { disable(0), enable(1) }
		MAX-ACCESS  read-only
		STATUS      current
		DESCRIPTION
			"OAM Mode."
		::= { swhOAMFlagsEntry 2 }

	swhOAMFlagsLocalRemoteStable OBJECT-TYPE
		SYNTAX      DisplayString
		MAX-ACCESS  read-only
		STATUS      current
		DESCRIPTION
			"Local Remote Stable."
		::= { swhOAMFlagsEntry 3 }

	swhOAMFlagsLocalRemoteEvaluating OBJECT-TYPE
		SYNTAX      DisplayString
		MAX-ACCESS  read-only
		STATUS      current
		DESCRIPTION
			"Local Remote Evaluating."
		::= { swhOAMFlagsEntry 4 }

	swhOAMFlagsLocalLocalStable OBJECT-TYPE
		SYNTAX      DisplayString
		MAX-ACCESS  read-only
		STATUS      current
		DESCRIPTION
			"Local Local Stable."
		::= { swhOAMFlagsEntry 5 }

	swhOAMFlagsLocalLocalEvaluating OBJECT-TYPE
		SYNTAX      DisplayString
		MAX-ACCESS  read-only
		STATUS      current
		DESCRIPTION
			"Local Local Evaluating."
		::= { swhOAMFlagsEntry 6 }

	swhOAMFlagsLocalCriticalEvent OBJECT-TYPE
		SYNTAX      DisplayString
		MAX-ACCESS  read-only
		STATUS      current
		DESCRIPTION
			"Local Critical Event."
		::= { swhOAMFlagsEntry 7 }

	swhOAMFlagsLocalDyingGasp OBJECT-TYPE
		SYNTAX      DisplayString
		MAX-ACCESS  read-only
		STATUS      current
		DESCRIPTION
			"Local Dying Gasp."
		::= { swhOAMFlagsEntry 8 }

	swhOAMFlagsLocalLinkFault OBJECT-TYPE
		SYNTAX      DisplayString
		MAX-ACCESS  read-only
		STATUS      current
		DESCRIPTION
			"Local Link Fault."
		::= { swhOAMFlagsEntry 9 }

	swhOAMFlagsRemoteRemoteStable OBJECT-TYPE
		SYNTAX      DisplayString
		MAX-ACCESS  read-only
		STATUS      current
		DESCRIPTION
			"Remote Remote Stable."
		::= { swhOAMFlagsEntry 10 }

	swhOAMFlagsRemoteRemoteEvaluating OBJECT-TYPE
		SYNTAX      DisplayString
		MAX-ACCESS  read-only
		STATUS      current
		DESCRIPTION
			"Remote Remote Evaluating."
		::= { swhOAMFlagsEntry 11 }

	swhOAMFlagsRemoteLocalStable OBJECT-TYPE
		SYNTAX      DisplayString
		MAX-ACCESS  read-only
		STATUS      current
		DESCRIPTION
			"Remote Local Stable."
		::= { swhOAMFlagsEntry 12 }

	swhOAMFlagsRemoteLocalEvaluating OBJECT-TYPE
		SYNTAX      DisplayString
		MAX-ACCESS  read-only
		STATUS      current
		DESCRIPTION
			"Remote Local Evaluating."
		::= { swhOAMFlagsEntry 13 }

	swhOAMFlagsRemoteCriticalEvent OBJECT-TYPE
		SYNTAX      DisplayString
		MAX-ACCESS  read-only
		STATUS      current
		DESCRIPTION
			"Remote Critical Event."
		::= { swhOAMFlagsEntry 14 }

	swhOAMFlagsRemoteDyingGasp OBJECT-TYPE
		SYNTAX      DisplayString
		MAX-ACCESS  read-only
		STATUS      current
		DESCRIPTION
			"Remote Dying Gasp."
		::= { swhOAMFlagsEntry 15 }

	swhOAMFlagsRemoteLinkFault OBJECT-TYPE
		SYNTAX      DisplayString
		MAX-ACCESS  read-only
		STATUS      current
		DESCRIPTION
			"Remote Link Fault."
		::= { swhOAMFlagsEntry 16 }


-- EthernetOAM(24).OAMStatus(3).OAMInformationTLVs(3)

	swhOAMInfoTLVsTable OBJECT-TYPE
		SYNTAX      SEQUENCE OF SwhOAMInfoTLVsEntry
		MAX-ACCESS  not-accessible
		STATUS      current
		DESCRIPTION
			"Table of OAM information TLVs."
		::= { swhOAMInformationTLVs 5 }

	-- Table Entry
	swhOAMInfoTLVsEntry OBJECT-TYPE
		SYNTAX      SwhOAMInfoTLVsEntry
		MAX-ACCESS  not-accessible
		STATUS      current
		DESCRIPTION
			"An entry in the table, containing information about OAM information TLVs."
		INDEX    { swhOAMInfoTLVsPort }
		::= { swhOAMInfoTLVsTable 1 }

	SwhOAMInfoTLVsEntry ::=
		SEQUENCE {
			swhOAMInfoTLVsPort
				INTEGER,
			swhOAMInfoTLVsOAMState
				INTEGER,
			swhOAMInfoTLVsLocalOAMMode
				DisplayString,
			swhOAMInfoTLVsLocalVariableRetrieval
				DisplayString,
			swhOAMInfoTLVsLocalLinkEvents
				DisplayString,
			swhOAMInfoTLVsLocalLoopback
				DisplayString,
			swhOAMInfoTLVsLocalUnidirectional
				DisplayString,
			swhOAMInfoTLVsRemoteOAMMode
				DisplayString,
			swhOAMInfoTLVsRemoteVariableRetrieval
				DisplayString,
			swhOAMInfoTLVsRemoteLinkEvents
				DisplayString,
			swhOAMInfoTLVsRemoteLoopback
				DisplayString,
			swhOAMInfoTLVsRemoteUnidirectional
				DisplayString
		}

	swhOAMInfoTLVsPort OBJECT-TYPE
		SYNTAX      INTEGER (0..2147483647)
		MAX-ACCESS  read-only
		STATUS      current
		DESCRIPTION
			"A unique value for each port."
		::= { swhOAMInfoTLVsEntry 1 }

	swhOAMInfoTLVsOAMState OBJECT-TYPE
		SYNTAX      INTEGER { disable(0), enable(1) }
		MAX-ACCESS  read-only
		STATUS      current
		DESCRIPTION
			"OAM State."
		::= { swhOAMInfoTLVsEntry 2 }

	swhOAMInfoTLVsLocalOAMMode OBJECT-TYPE
		SYNTAX      DisplayString
		MAX-ACCESS  read-only
		STATUS      current
		DESCRIPTION
			"Local OAM Mode."
		::= { swhOAMInfoTLVsEntry 3 }

	swhOAMInfoTLVsLocalVariableRetrieval OBJECT-TYPE
		SYNTAX      DisplayString
		MAX-ACCESS  read-only
		STATUS      current
		DESCRIPTION
			"Local Variable Retrieval."
		::= { swhOAMInfoTLVsEntry 4 }

	swhOAMInfoTLVsLocalLinkEvents OBJECT-TYPE
		SYNTAX      DisplayString
		MAX-ACCESS  read-only
		STATUS      current
		DESCRIPTION
			"Local Link Events."
		::= { swhOAMInfoTLVsEntry 5 }

	swhOAMInfoTLVsLocalLoopback OBJECT-TYPE
		SYNTAX      DisplayString
		MAX-ACCESS  read-only
		STATUS      current
		DESCRIPTION
			"Local Loopback."
		::= { swhOAMInfoTLVsEntry 6 }

	swhOAMInfoTLVsLocalUnidirectional OBJECT-TYPE
		SYNTAX      DisplayString
		MAX-ACCESS  read-only
		STATUS      current
		DESCRIPTION
			"Local Unidirectional."
		::= { swhOAMInfoTLVsEntry 7 }

	swhOAMInfoTLVsRemoteOAMMode OBJECT-TYPE
		SYNTAX      DisplayString
		MAX-ACCESS  read-only
		STATUS      current
		DESCRIPTION
			"Remote OAM Mode."
		::= { swhOAMInfoTLVsEntry 8 }

	swhOAMInfoTLVsRemoteVariableRetrieval OBJECT-TYPE
		SYNTAX      DisplayString
		MAX-ACCESS  read-only
		STATUS      current
		DESCRIPTION
			"Remote Variable Retrieval."
		::= { swhOAMInfoTLVsEntry 9 }

	swhOAMInfoTLVsRemoteLinkEvents OBJECT-TYPE
		SYNTAX      DisplayString
		MAX-ACCESS  read-only
		STATUS      current
		DESCRIPTION
			"Remote Link Events."
		::= { swhOAMInfoTLVsEntry 10 }

	swhOAMInfoTLVsRemoteLoopback OBJECT-TYPE
		SYNTAX      DisplayString
		MAX-ACCESS  read-only
		STATUS      current
		DESCRIPTION
			"Remote Loopback."
		::= { swhOAMInfoTLVsEntry 11 }

	swhOAMInfoTLVsRemoteUnidirectional OBJECT-TYPE
		SYNTAX      DisplayString
		MAX-ACCESS  read-only
		STATUS      current
		DESCRIPTION
			"Remote Unidirectional."
		::= { swhOAMInfoTLVsEntry 12 }


-- EthernetOAM(24).OAMStatistics(4)

	swhOAMStatisticsClearOfAllPort OBJECT-TYPE
		SYNTAX      INTEGER { normal(0), clear(1) }
		MAX-ACCESS  read-write
		STATUS      current
		DESCRIPTION
			"Clear counters of all port."
		::= { swhOAMStatistics 1 }

	swhOAMStatisticsTable OBJECT-TYPE
		SYNTAX      SEQUENCE OF SwhOAMStatisticsEntry
		MAX-ACCESS  not-accessible
		STATUS      current
		DESCRIPTION
			"Table of OAM statistics."
		::= { swhOAMStatistics 5 }

	-- Table Entry
	swhOAMStatisticsEntry OBJECT-TYPE
		SYNTAX      SwhOAMStatisticsEntry
		MAX-ACCESS  not-accessible
		STATUS      current
		DESCRIPTION
			"An entry in the table, containing information about OAM statistics."
		INDEX    { swhOAMStatisticsPort }
		::= { swhOAMStatisticsTable 1 }

	SwhOAMStatisticsEntry ::=
		SEQUENCE {
			swhOAMStatisticsPort
				INTEGER,
			swhOAMStatisticsRxInformation
				Counter32,
			swhOAMStatisticsTxInformation
				Counter32,
			swhOAMStatisticsRxEventNotification
				Counter32,
			swhOAMStatisticsTxEventNotification
				Counter32,
			swhOAMStatisticsRxLoopbackControl
				Counter32,
			swhOAMStatisticsTxLoopbackControl
				Counter32,
			swhOAMStatisticsRxOrganizationSpecific
				Counter32,
			swhOAMStatisticsTxOrganizationSpecific
				Counter32,
			swhOAMStatisticsRxDyingGasp
				Counter32,
			swhOAMStatisticsRxCriticalEvent
				Counter32,
			swhOAMStatisticsClear
				INTEGER
		}

	swhOAMStatisticsPort OBJECT-TYPE
		SYNTAX      INTEGER (0..2147483647)
		MAX-ACCESS  read-only
		STATUS      current
		DESCRIPTION
			"A unique value for each port."
		::= { swhOAMStatisticsEntry 1 }

	swhOAMStatisticsRxInformation OBJECT-TYPE
		SYNTAX      Counter32
		MAX-ACCESS  read-only
		STATUS      current
		DESCRIPTION
			"Rx Information."
		::= { swhOAMStatisticsEntry 2 }

	swhOAMStatisticsTxInformation OBJECT-TYPE
		SYNTAX      Counter32
		MAX-ACCESS  read-only
		STATUS      current
		DESCRIPTION
			"Tx Information."
		::= { swhOAMStatisticsEntry 3 }

	swhOAMStatisticsRxEventNotification OBJECT-TYPE
		SYNTAX      Counter32
		MAX-ACCESS  read-only
		STATUS      current
		DESCRIPTION
			"Rx Event Notification."
		::= { swhOAMStatisticsEntry 4 }

	swhOAMStatisticsTxEventNotification OBJECT-TYPE
		SYNTAX      Counter32
		MAX-ACCESS  read-only
		STATUS      current
		DESCRIPTION
			"Tx Event Notification."
		::= { swhOAMStatisticsEntry 5 }

	swhOAMStatisticsRxLoopbackControl OBJECT-TYPE
		SYNTAX      Counter32
		MAX-ACCESS  read-only
		STATUS      current
		DESCRIPTION
			"Rx Loopback Control."
		::= { swhOAMStatisticsEntry 6 }

	swhOAMStatisticsTxLoopbackControl OBJECT-TYPE
		SYNTAX      Counter32
		MAX-ACCESS  read-only
		STATUS      current
		DESCRIPTION
			"Tx Loopback Control."
		::= { swhOAMStatisticsEntry 7 }

	swhOAMStatisticsRxOrganizationSpecific OBJECT-TYPE
		SYNTAX      Counter32
		MAX-ACCESS  read-only
		STATUS      current
		DESCRIPTION
			"Rx Organization Specific."
		::= { swhOAMStatisticsEntry 8 }

	swhOAMStatisticsTxOrganizationSpecific OBJECT-TYPE
		SYNTAX      Counter32
		MAX-ACCESS  read-only
		STATUS      current
		DESCRIPTION
			"Tx Organization Specific."
		::= { swhOAMStatisticsEntry 9 }

	swhOAMStatisticsRxDyingGasp OBJECT-TYPE
		SYNTAX      Counter32
		MAX-ACCESS  read-only
		STATUS      current
		DESCRIPTION
			"Rx Dying Gasp."
		::= { swhOAMStatisticsEntry 10 }

	swhOAMStatisticsRxCriticalEvent OBJECT-TYPE
		SYNTAX      Counter32
		MAX-ACCESS  read-only
		STATUS      current
		DESCRIPTION
			"Rx Critical Event."
		::= { swhOAMStatisticsEntry 11 }

	swhOAMStatisticsClear OBJECT-TYPE
		SYNTAX      INTEGER { normal(0), clear(1) }
		MAX-ACCESS  read-write
		STATUS      current
		DESCRIPTION
			"Clear this entry."
		::= { swhOAMStatisticsEntry 50 }


-- EthernetOAM(24).OAMRemoteModule(5)

	swhRemoteModuleManagement
		OBJECT IDENTIFIER ::= { swhOAMRemoteModule 1 }

	swhRemoteModuleConfiguration
		OBJECT IDENTIFIER ::= { swhOAMRemoteModule 2 }

	swhRemoteModuleInformation
		OBJECT IDENTIFIER ::= { swhOAMRemoteModule 3 }

	swhRemoteModuleDiagnostics
		OBJECT IDENTIFIER ::= { swhOAMRemoteModule 4 }


-- EthernetOAM(24).OAMRemoteModule(5).RemoteModuleManagement(1)

	swhRemoteModuleUpgradeAllModule OBJECT-TYPE
		SYNTAX      INTEGER { normal(0), update(1) }
		MAX-ACCESS  read-write
		STATUS      current
		DESCRIPTION
			"Upgrade all remote module."
		::= { swhRemoteModuleManagement 1 }

	swhRemoteModuleRebootAllModule OBJECT-TYPE
		SYNTAX      INTEGER { normal(0), reboot(1) }
		MAX-ACCESS  read-write
		STATUS      current
		DESCRIPTION
			"Reboot all remote module."
		::= { swhRemoteModuleManagement 2 }


-- EthernetOAM(24).OAMRemoteModule(5).RemoteModuleManagement(1).RemoteModuleMgmt(5)

	swhRemoteModuleMgmtTable OBJECT-TYPE
		SYNTAX      SEQUENCE OF SwhRemoteModuleMgmtEntry
		MAX-ACCESS  not-accessible
		STATUS      current
		DESCRIPTION
			"Table of remote module management."
		::= { swhRemoteModuleManagement 5 }

	-- Table Entry
	swhRemoteModuleMgmtEntry OBJECT-TYPE
		SYNTAX      SwhRemoteModuleMgmtEntry
		MAX-ACCESS  not-accessible
		STATUS      current
		DESCRIPTION
			"An entry in the table, containing information about remote module management."
		INDEX    { swhRemoteModuleMgmtPort }
		::= { swhRemoteModuleMgmtTable 1 }

	SwhRemoteModuleMgmtEntry ::=
		SEQUENCE {
			swhRemoteModuleMgmtPort
				INTEGER,
			swhRemoteModuleMgmtDescription
				DisplayString,
			swhRemoteModuleMgmtModelName
				DisplayString,
			swhRemoteModuleMgmtStatus
				DisplayString,
			swhRemoteModuleMgmtHWVersion
				DisplayString,
			swhRemoteModuleMgmtFWVersion
				DisplayString,
			swhRemoteModuleMgmtBootVersion
				DisplayString,
			swhRemoteModuleMgmtUpgrade
				INTEGER,
			swhRemoteModuleMgmtReboot
				INTEGER
		}

	swhRemoteModuleMgmtPort OBJECT-TYPE
		SYNTAX      INTEGER (0..2147483647)
		MAX-ACCESS  read-only
		STATUS      current
		DESCRIPTION
			"A unique value for each port."
		::= { swhRemoteModuleMgmtEntry 1 }

	swhRemoteModuleMgmtDescription OBJECT-TYPE
		SYNTAX      DisplayString
		MAX-ACCESS  read-write
		STATUS      current
		DESCRIPTION
			"Description."
		::= { swhRemoteModuleMgmtEntry 2 }

	swhRemoteModuleMgmtModelName OBJECT-TYPE
		SYNTAX      DisplayString
		MAX-ACCESS  read-only
		STATUS      current
		DESCRIPTION
			"Model Name."
		::= { swhRemoteModuleMgmtEntry 3 }

	swhRemoteModuleMgmtStatus OBJECT-TYPE
		SYNTAX      DisplayString
		MAX-ACCESS  read-only
		STATUS      current
		DESCRIPTION
			"Status."
		::= { swhRemoteModuleMgmtEntry 4 }

	swhRemoteModuleMgmtHWVersion OBJECT-TYPE
		SYNTAX      DisplayString
		MAX-ACCESS  read-only
		STATUS      current
		DESCRIPTION
			"HW Version."
		::= { swhRemoteModuleMgmtEntry 5 }

	swhRemoteModuleMgmtFWVersion OBJECT-TYPE
		SYNTAX      DisplayString
		MAX-ACCESS  read-only
		STATUS      current
		DESCRIPTION
			"FW Version."
		::= { swhRemoteModuleMgmtEntry 6 }

	swhRemoteModuleMgmtBootVersion OBJECT-TYPE
		SYNTAX      DisplayString
		MAX-ACCESS  read-only
		STATUS      current
		DESCRIPTION
			"Boot Version."
		::= { swhRemoteModuleMgmtEntry 7 }

	swhRemoteModuleMgmtUpgrade OBJECT-TYPE
		SYNTAX      INTEGER { nosupport(0), idle(1), apply(2) }
		MAX-ACCESS  read-write
		STATUS      current
		DESCRIPTION
			"Upgrade Module."
		::= { swhRemoteModuleMgmtEntry 8 }

	swhRemoteModuleMgmtReboot OBJECT-TYPE
		SYNTAX      INTEGER { nosupport(0), idle(1), apply(2) }
		MAX-ACCESS  read-write
		STATUS      current
		DESCRIPTION
			"Reboot Module."
		::= { swhRemoteModuleMgmtEntry 9 }


-- EthernetOAM(24).OAMRemoteModule(5).RemoteModuleConfiguration(2)


-- EthernetOAM(24).OAMRemoteModule(5).RemoteModuleConfiguration(2).Port1RemoteConfiguration(1)

	swhPort1RemoteConfiguration
		OBJECT IDENTIFIER ::= { swhRemoteModuleConfiguration 1 }


-- EthernetOAM(24).OAMRemoteModule(5).RemoteModuleConfiguration(2).Port1RemoteConfiguration(1).Port1MCT3512Configuration(1)

	swhPort1MCT3512Configuration
		OBJECT IDENTIFIER ::= { swhPort1RemoteConfiguration 1 }


-- EthernetOAM(24).OAMRemoteModule(5).RemoteModuleConfiguration(2).Port1RemoteConfiguration(1).Port1MCT3512Configuration(1).Port1MCT3512Config(1)

	swhPort1MCT3512Config
		OBJECT IDENTIFIER ::= { swhPort1MCT3512Configuration 1 }

	swhPort1MCT3512ConfigDetectedModule OBJECT-TYPE
		SYNTAX      DisplayString
		MAX-ACCESS  read-only
		STATUS      current
		DESCRIPTION
			"Detected Module."
		::= { swhPort1MCT3512Config 1 }

	swhPort1MCT3512ConfigDIPSwitchSetting OBJECT-TYPE
		SYNTAX      DisplayString
		MAX-ACCESS  read-only
		STATUS      current
		DESCRIPTION
			"DIP Switch (PIN 8) Setting."
		::= { swhPort1MCT3512Config 2 }


-- EthernetOAM(24).OAMRemoteModule(5).RemoteModuleConfiguration(2).Port1RemoteConfiguration(1).Port1MCT3512Configuration(1).Port1MCT3512PortSetup(2)

	swhPort1MCT3512PortSetup
		OBJECT IDENTIFIER ::= { swhPort1MCT3512Configuration 2 }

	swhPort1MCT3512PortSetupTable OBJECT-TYPE
		SYNTAX      SEQUENCE OF SwhPort1MCT3512PortSetupEntry
		MAX-ACCESS  not-accessible
		STATUS      current
		DESCRIPTION
			"Table of remote module port setup."
		::= { swhPort1MCT3512PortSetup 5 }

	-- Table Entry
	swhPort1MCT3512PortSetupEntry OBJECT-TYPE
		SYNTAX      SwhPort1MCT3512PortSetupEntry
		MAX-ACCESS  not-accessible
		STATUS      current
		DESCRIPTION
			"An entry in the table, containing information about remote module port setup."
		INDEX    { swhPort1MCT3512PortSetupPort }
		::= { swhPort1MCT3512PortSetupTable 1 }

	SwhPort1MCT3512PortSetupEntry ::=
		SEQUENCE {
			swhPort1MCT3512PortSetupPort
				INTEGER,
			swhPort1MCT3512PortSetupMediaType
				DisplayString,
			swhPort1MCT3512PortSetupPortState
				INTEGER,
			swhPort1MCT3512PortSetupPortType
				INTEGER,
			swhPort1MCT3512PortSetupPortSpeed
				INTEGER,
			swhPort1MCT3512PortSetupPortDuplex
				INTEGER
		}

	swhPort1MCT3512PortSetupPort OBJECT-TYPE
		SYNTAX      INTEGER (0..2147483647)
		MAX-ACCESS  read-only
		STATUS      current
		DESCRIPTION
			"A unique value for each port."
		::= { swhPort1MCT3512PortSetupEntry 1 }

	swhPort1MCT3512PortSetupMediaType OBJECT-TYPE
		SYNTAX      DisplayString
		MAX-ACCESS  read-only
		STATUS      current
		DESCRIPTION
			"Media Type."
		::= { swhPort1MCT3512PortSetupEntry 2 }

	swhPort1MCT3512PortSetupPortState OBJECT-TYPE
		SYNTAX      INTEGER { disable(0), enable(1) }
		MAX-ACCESS  read-write
		STATUS      current
		DESCRIPTION
			"Port State."
		::= { swhPort1MCT3512PortSetupEntry 3 }

	swhPort1MCT3512PortSetupPortType OBJECT-TYPE
		SYNTAX      INTEGER { manual(0), auto-negotiation(1) }
		MAX-ACCESS  read-write
		STATUS      current
		DESCRIPTION
			"Port Type."
		::= { swhPort1MCT3512PortSetupEntry 4 }

	swhPort1MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort1MCT3512PortSetupEntry 5 }

	swhPort1MCT3512PortSetupPortDuplex OBJECT-TYPE
		SYNTAX      INTEGER { halfDuplex(0), fullDuplex(1) }
		MAX-ACCESS  read-write
		STATUS      current
		DESCRIPTION
			"Port Duplex."
		::= { swhPort1MCT3512PortSetupEntry 6 }


-- EthernetOAM(24).OAMRemoteModule(5).RemoteModuleConfiguration(2).Port1RemoteConfiguration(1).Port1MCT3512Configuration(1).Port1MCT3512VLANSetup(3)

	swhPort1MCT3512VLANSetup
		OBJECT IDENTIFIER ::= { swhPort1MCT3512Configuration 3 }

	swhPort1MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort1MCT3512VLANSetup 1 }

	swhPort1MCT3512VLANSetupISPMode OBJECT-TYPE
		SYNTAX      INTEGER { disable(0), enable(1) }
		MAX-ACCESS  read-write
		STATUS      current
		DESCRIPTION
			"Remote Module ISP Mode."
		::= { swhPort1MCT3512VLANSetup 2 }

	swhPort1MCT3512VLANSetupStagEtherType OBJECT-TYPE
		SYNTAX      DisplayString
		MAX-ACCESS  read-write
		STATUS      current
		DESCRIPTION
			"Remote Module Stag EtherType."
		::= { swhPort1MCT3512VLANSetup 3 }

	swhPort1MCT3512VLANSetupTable OBJECT-TYPE
		SYNTAX      SEQUENCE OF SwhPort1MCT3512VLANSetupEntry
		MAX-ACCESS  not-accessible
		STATUS      current
		DESCRIPTION
			"Table of remote module VLAN setup."
		::= { swhPort1MCT3512VLANSetup 5 }

	-- Table Entry
	swhPort1MCT3512VLANSetupEntry OBJECT-TYPE
		SYNTAX      SwhPort1MCT3512VLANSetupEntry
		MAX-ACCESS  not-accessible
		STATUS      current
		DESCRIPTION
			"An entry in the table, containing information about remote module VLAN setup."
		INDEX    { swhPort1MCT3512VLANSetupPort }
		::= { swhPort1MCT3512VLANSetupTable 1 }

	SwhPort1MCT3512VLANSetupEntry ::=
		SEQUENCE {
			swhPort1MCT3512VLANSetupPort
				INTEGER,
			swhPort1MCT3512VLANSetupMediaType
				DisplayString,
			swhPort1MCT3512VLANSetupMode
				INTEGER,
			swhPort1MCT3512VLANSetupPVID
				INTEGER,
			swhPort1MCT3512VLANSetupTrunkVLAN
				DisplayString,
			swhPort1MCT3512VLANSetupStagVID
				INTEGER,
			swhPort1MCT3512VLANSetupISPPort
				INTEGER
		}

	swhPort1MCT3512VLANSetupPort OBJECT-TYPE
		SYNTAX      INTEGER (0..2147483647)
		MAX-ACCESS  read-only
		STATUS      current
		DESCRIPTION
			"A unique value for each port."
		::= { swhPort1MCT3512VLANSetupEntry 1 }

	swhPort1MCT3512VLANSetupMediaType OBJECT-TYPE
		SYNTAX      DisplayString
		MAX-ACCESS  read-only
		STATUS      current
		DESCRIPTION
			"Remote Module Port Media Type."
		::= { swhPort1MCT3512VLANSetupEntry 2 }

	swhPort1MCT3512VLANSetupMode OBJECT-TYPE
		SYNTAX      INTEGER { access(0), trunk(1), trunknative(2) }
		MAX-ACCESS  read-write
		STATUS      current
		DESCRIPTION
			"Remote Module Port Mode."
		::= { swhPort1MCT3512VLANSetupEntry 3 }

	swhPort1MCT3512VLANSetupPVID OBJECT-TYPE
		SYNTAX      INTEGER (1..4093)
		MAX-ACCESS  read-write
		STATUS      current
		DESCRIPTION
			"Remote Module Port PVID."
		::= { swhPort1MCT3512VLANSetupEntry 4 }

	swhPort1MCT3512VLANSetupTrunkVLAN OBJECT-TYPE
		SYNTAX      DisplayString
		MAX-ACCESS  read-write
		STATUS      current
		DESCRIPTION
			"Remote Module Port Trunk VLAN."
		::= { swhPort1MCT3512VLANSetupEntry 5 }

	swhPort1MCT3512VLANSetupStagVID OBJECT-TYPE
		SYNTAX      INTEGER (1..4093)
		MAX-ACCESS  read-write
		STATUS      current
		DESCRIPTION
			"Remote Module Port Stag VID."
		::= { swhPort1MCT3512VLANSetupEntry 6 }

	swhPort1MCT3512VLANSetupISPPort OBJECT-TYPE
		SYNTAX      INTEGER { disable(0), enable(1) }
		MAX-ACCESS  read-write
		STATUS      current
		DESCRIPTION
			"Remote Module Port ISP Port."
		::= { swhPort1MCT3512VLANSetupEntry 7 }


-- EthernetOAM(24).OAMRemoteModule(5).RemoteModuleConfiguration(2).Port1RemoteConfiguration(1).Port1MCT3512Configuration(1).Port1MCT3512RateLimit(4)

	swhPort1MCT3512RateLimit
		OBJECT IDENTIFIER ::= { swhPort1MCT3512Configuration 4 }

	swhPort1MCT3512RateLimitTable OBJECT-TYPE
		SYNTAX      SEQUENCE OF SwhPort1MCT3512RateLimitEntry
		MAX-ACCESS  not-accessible
		STATUS      current
		DESCRIPTION
			"Table of remote module QoS rate limit."
		::= { swhPort1MCT3512RateLimit 5 }

	-- Table Entry
	swhPort1MCT3512RateLimitEntry OBJECT-TYPE
		SYNTAX      SwhPort1MCT3512RateLimitEntry
		MAX-ACCESS  not-accessible
		STATUS      current
		DESCRIPTION
			"An entry in the table, containing information about remote module QoS rate limit."
		INDEX    { swhPort1MCT3512RateLimitPort }
		::= { swhPort1MCT3512RateLimitTable 1 }

	SwhPort1MCT3512RateLimitEntry ::=
		SEQUENCE {
			swhPort1MCT3512RateLimitPort
				INTEGER,
			swhPort1MCT3512RateLimitMediaType
				DisplayString,
			swhPort1MCT3512RateLimitIngressEn
				INTEGER,
			swhPort1MCT3512RateLimitIngressRate
				INTEGER,
			swhPort1MCT3512RateLimitEgressEn
				INTEGER,
			swhPort1MCT3512RateLimitEgressRate
				INTEGER
		}

	swhPort1MCT3512RateLimitPort OBJECT-TYPE
		SYNTAX      INTEGER (0..2147483647)
		MAX-ACCESS  read-only
		STATUS      current
		DESCRIPTION
			"A unique value for each port."
		::= { swhPort1MCT3512RateLimitEntry 1 }

	swhPort1MCT3512RateLimitMediaType OBJECT-TYPE
		SYNTAX      DisplayString
		MAX-ACCESS  read-only
		STATUS      current
		DESCRIPTION
			"Remote Module Port Media Type."
		::= { swhPort1MCT3512RateLimitEntry 2 }

	swhPort1MCT3512RateLimitIngressEn OBJECT-TYPE
		SYNTAX      INTEGER { disable(0), enable(1) }
		MAX-ACCESS  read-write
		STATUS      current
		DESCRIPTION
			"Remote Module Port Ingress Enable."
		::= { swhPort1MCT3512RateLimitEntry 3 }

	swhPort1MCT3512RateLimitIngressRate OBJECT-TYPE
		SYNTAX      INTEGER (32..1000000)
		MAX-ACCESS  read-write
		STATUS      current
		DESCRIPTION
			"Remote Module Port Ingress Rate (32-1000000) kbps."
		::= { swhPort1MCT3512RateLimitEntry 4 }

	swhPort1MCT3512RateLimitEgressEn OBJECT-TYPE
		SYNTAX      INTEGER { disable(0), enable(1) }
		MAX-ACCESS  read-write
		STATUS      current
		DESCRIPTION
			"Remote Module Port Egress Enable."
		::= { swhPort1MCT3512RateLimitEntry 5 }

	swhPort1MCT3512RateLimitEgressRate OBJECT-TYPE
		SYNTAX      INTEGER (32..1000000)
		MAX-ACCESS  read-write
		STATUS      current
		DESCRIPTION
			"Remote Module Port Egress Rate (32-1000000) kbps."
		::= { swhPort1MCT3512RateLimitEntry 6 }


-- EthernetOAM(24).OAMRemoteModule(5).RemoteModuleConfiguration(2).Port1RemoteConfiguration(1).Port1MCT3512Configuration(1).Port1MCT3512StormControl(5)

	swhPort1MCT3512StormControl
		OBJECT IDENTIFIER ::= { swhPort1MCT3512Configuration 5 }

	swhPort1MCT3512StormControlEnable OBJECT-TYPE
		SYNTAX      INTEGER { disable(0), enable(1) }
		MAX-ACCESS  read-write
		STATUS      current
		DESCRIPTION
			"Remote Module Storm Control."
		::= { swhPort1MCT3512StormControl 1 }

	swhPort1MCT3512StormControlRate OBJECT-TYPE
		SYNTAX      INTEGER (32..1000000)
		MAX-ACCESS  read-write
		STATUS      current
		DESCRIPTION
			"Remote Module Rate (32-1000000) kbps."
		::= { swhPort1MCT3512StormControl 2 }

	swhPort1MCT3512StormControlBandwidth OBJECT-TYPE
		SYNTAX      DisplayString
		MAX-ACCESS  read-only
		STATUS      current
		DESCRIPTION
			"Remote Module Bandwidth (bps)."
		::= { swhPort1MCT3512StormControl 3 }


-- EthernetOAM(24).OAMRemoteModule(5).RemoteModuleConfiguration(2).Port1RemoteConfiguration(1).Port1MCT3512Configuration(1).Port1MCT3512LANFollowsWAN(6)

	swhPort1MCT3512LANFollowsWAN
		OBJECT IDENTIFIER ::= { swhPort1MCT3512Configuration 6 }

	swhPort1MCT3512LANFollowsWANEnable OBJECT-TYPE
		SYNTAX      INTEGER { disable(0), enable(1) }
		MAX-ACCESS  read-write
		STATUS      current
		DESCRIPTION
			"Remote Module LAN Follows WAN."
		::= { swhPort1MCT3512LANFollowsWAN 1 }


-- EthernetOAM(24).OAMRemoteModule(5).RemoteModuleConfiguration(2).Port2RemoteConfiguration(2)

	swhPort2RemoteConfiguration
		OBJECT IDENTIFIER ::= { swhRemoteModuleConfiguration 2 }


-- EthernetOAM(24).OAMRemoteModule(5).RemoteModuleConfiguration(2).Port2RemoteConfiguration(2).Port2MCT3512Configuration(1)

	swhPort2MCT3512Configuration
		OBJECT IDENTIFIER ::= { swhPort2RemoteConfiguration 1 }


-- EthernetOAM(24).OAMRemoteModule(5).RemoteModuleConfiguration(2).Port2RemoteConfiguration(2).Port2MCT3512Configuration(1).Port2MCT3512Config(1)

	swhPort2MCT3512Config
		OBJECT IDENTIFIER ::= { swhPort2MCT3512Configuration 1 }

	swhPort2MCT3512ConfigDetectedModule OBJECT-TYPE
		SYNTAX      DisplayString
		MAX-ACCESS  read-only
		STATUS      current
		DESCRIPTION
			"Detected Module."
		::= { swhPort2MCT3512Config 1 }

	swhPort2MCT3512ConfigDIPSwitchSetting OBJECT-TYPE
		SYNTAX      DisplayString
		MAX-ACCESS  read-only
		STATUS      current
		DESCRIPTION
			"DIP Switch (PIN 8) Setting."
		::= { swhPort2MCT3512Config 2 }


-- EthernetOAM(24).OAMRemoteModule(5).RemoteModuleConfiguration(2).Port2RemoteConfiguration(2).Port2MCT3512Configuration(1).Port2MCT3512PortSetup(2)

	swhPort2MCT3512PortSetup
		OBJECT IDENTIFIER ::= { swhPort2MCT3512Configuration 2 }

	swhPort2MCT3512PortSetupTable OBJECT-TYPE
		SYNTAX      SEQUENCE OF SwhPort2MCT3512PortSetupEntry
		MAX-ACCESS  not-accessible
		STATUS      current
		DESCRIPTION
			"Table of remote module port setup."
		::= { swhPort2MCT3512PortSetup 5 }

	-- Table Entry
	swhPort2MCT3512PortSetupEntry OBJECT-TYPE
		SYNTAX      SwhPort2MCT3512PortSetupEntry
		MAX-ACCESS  not-accessible
		STATUS      current
		DESCRIPTION
			"An entry in the table, containing information about remote module port setup."
		INDEX    { swhPort2MCT3512PortSetupPort }
		::= { swhPort2MCT3512PortSetupTable 1 }

	SwhPort2MCT3512PortSetupEntry ::=
		SEQUENCE {
			swhPort2MCT3512PortSetupPort
				INTEGER,
			swhPort2MCT3512PortSetupMediaType
				DisplayString,
			swhPort2MCT3512PortSetupPortState
				INTEGER,
			swhPort2MCT3512PortSetupPortType
				INTEGER,
			swhPort2MCT3512PortSetupPortSpeed
				INTEGER,
			swhPort2MCT3512PortSetupPortDuplex
				INTEGER
		}

	swhPort2MCT3512PortSetupPort OBJECT-TYPE
		SYNTAX      INTEGER (0..2147483647)
		MAX-ACCESS  read-only
		STATUS      current
		DESCRIPTION
			"A unique value for each port."
		::= { swhPort2MCT3512PortSetupEntry 1 }

	swhPort2MCT3512PortSetupMediaType OBJECT-TYPE
		SYNTAX      DisplayString
		MAX-ACCESS  read-only
		STATUS      current
		DESCRIPTION
			"Media Type."
		::= { swhPort2MCT3512PortSetupEntry 2 }

	swhPort2MCT3512PortSetupPortState OBJECT-TYPE
		SYNTAX      INTEGER { disable(0), enable(1) }
		MAX-ACCESS  read-write
		STATUS      current
		DESCRIPTION
			"Port State."
		::= { swhPort2MCT3512PortSetupEntry 3 }

	swhPort2MCT3512PortSetupPortType OBJECT-TYPE
		SYNTAX      INTEGER { manual(0), auto-negotiation(1) }
		MAX-ACCESS  read-write
		STATUS      current
		DESCRIPTION
			"Port Type."
		::= { swhPort2MCT3512PortSetupEntry 4 }

	swhPort2MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort2MCT3512PortSetupEntry 5 }

	swhPort2MCT3512PortSetupPortDuplex OBJECT-TYPE
		SYNTAX      INTEGER { halfDuplex(0), fullDuplex(1) }
		MAX-ACCESS  read-write
		STATUS      current
		DESCRIPTION
			"Port Duplex."
		::= { swhPort2MCT3512PortSetupEntry 6 }


-- EthernetOAM(24).OAMRemoteModule(5).RemoteModuleConfiguration(2).Port2RemoteConfiguration(2).Port2MCT3512Configuration(1).Port2MCT3512VLANSetup(3)

	swhPort2MCT3512VLANSetup
		OBJECT IDENTIFIER ::= { swhPort2MCT3512Configuration 3 }

	swhPort2MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort2MCT3512VLANSetup 1 }

	swhPort2MCT3512VLANSetupISPMode OBJECT-TYPE
		SYNTAX      INTEGER { disable(0), enable(1) }
		MAX-ACCESS  read-write
		STATUS      current
		DESCRIPTION
			"Remote Module ISP Mode."
		::= { swhPort2MCT3512VLANSetup 2 }

	swhPort2MCT3512VLANSetupStagEtherType OBJECT-TYPE
		SYNTAX      DisplayString
		MAX-ACCESS  read-write
		STATUS      current
		DESCRIPTION
			"Remote Module Stag EtherType."
		::= { swhPort2MCT3512VLANSetup 3 }

	swhPort2MCT3512VLANSetupTable OBJECT-TYPE
		SYNTAX      SEQUENCE OF SwhPort2MCT3512VLANSetupEntry
		MAX-ACCESS  not-accessible
		STATUS      current
		DESCRIPTION
			"Table of remote module VLAN setup."
		::= { swhPort2MCT3512VLANSetup 5 }

	-- Table Entry
	swhPort2MCT3512VLANSetupEntry OBJECT-TYPE
		SYNTAX      SwhPort2MCT3512VLANSetupEntry
		MAX-ACCESS  not-accessible
		STATUS      current
		DESCRIPTION
			"An entry in the table, containing information about remote module VLAN setup."
		INDEX    { swhPort2MCT3512VLANSetupPort }
		::= { swhPort2MCT3512VLANSetupTable 1 }

	SwhPort2MCT3512VLANSetupEntry ::=
		SEQUENCE {
			swhPort2MCT3512VLANSetupPort
				INTEGER,
			swhPort2MCT3512VLANSetupMediaType
				DisplayString,
			swhPort2MCT3512VLANSetupMode
				INTEGER,
			swhPort2MCT3512VLANSetupPVID
				INTEGER,
			swhPort2MCT3512VLANSetupTrunkVLAN
				DisplayString,
			swhPort2MCT3512VLANSetupStagVID
				INTEGER,
			swhPort2MCT3512VLANSetupISPPort
				INTEGER
		}

	swhPort2MCT3512VLANSetupPort OBJECT-TYPE
		SYNTAX      INTEGER (0..2147483647)
		MAX-ACCESS  read-only
		STATUS      current
		DESCRIPTION
			"A unique value for each port."
		::= { swhPort2MCT3512VLANSetupEntry 1 }

	swhPort2MCT3512VLANSetupMediaType OBJECT-TYPE
		SYNTAX      DisplayString
		MAX-ACCESS  read-only
		STATUS      current
		DESCRIPTION
			"Remote Module Port Media Type."
		::= { swhPort2MCT3512VLANSetupEntry 2 }

	swhPort2MCT3512VLANSetupMode OBJECT-TYPE
		SYNTAX      INTEGER { access(0), trunk(1), trunknative(2) }
		MAX-ACCESS  read-write
		STATUS      current
		DESCRIPTION
			"Remote Module Port Mode."
		::= { swhPort2MCT3512VLANSetupEntry 3 }

	swhPort2MCT3512VLANSetupPVID OBJECT-TYPE
		SYNTAX      INTEGER (1..4093)
		MAX-ACCESS  read-write
		STATUS      current
		DESCRIPTION
			"Remote Module Port PVID."
		::= { swhPort2MCT3512VLANSetupEntry 4 }

	swhPort2MCT3512VLANSetupTrunkVLAN OBJECT-TYPE
		SYNTAX      DisplayString
		MAX-ACCESS  read-write
		STATUS      current
		DESCRIPTION
			"Remote Module Port Trunk VLAN."
		::= { swhPort2MCT3512VLANSetupEntry 5 }

	swhPort2MCT3512VLANSetupStagVID OBJECT-TYPE
		SYNTAX      INTEGER (1..4093)
		MAX-ACCESS  read-write
		STATUS      current
		DESCRIPTION
			"Remote Module Port Stag VID."
		::= { swhPort2MCT3512VLANSetupEntry 6 }

	swhPort2MCT3512VLANSetupISPPort OBJECT-TYPE
		SYNTAX      INTEGER { disable(0), enable(1) }
		MAX-ACCESS  read-write
		STATUS      current
		DESCRIPTION
			"Remote Module Port ISP Port."
		::= { swhPort2MCT3512VLANSetupEntry 7 }


-- EthernetOAM(24).OAMRemoteModule(5).RemoteModuleConfiguration(2).Port2RemoteConfiguration(2).Port2MCT3512Configuration(1).Port2MCT3512RateLimit(4)

	swhPort2MCT3512RateLimit
		OBJECT IDENTIFIER ::= { swhPort2MCT3512Configuration 4 }

	swhPort2MCT3512RateLimitTable OBJECT-TYPE
		SYNTAX      SEQUENCE OF SwhPort2MCT3512RateLimitEntry
		MAX-ACCESS  not-accessible
		STATUS      current
		DESCRIPTION
			"Table of remote module QoS rate limit."
		::= { swhPort2MCT3512RateLimit 5 }

	-- Table Entry
	swhPort2MCT3512RateLimitEntry OBJECT-TYPE
		SYNTAX      SwhPort2MCT3512RateLimitEntry
		MAX-ACCESS  not-accessible
		STATUS      current
		DESCRIPTION
			"An entry in the table, containing information about remote module QoS rate limit."
		INDEX    { swhPort2MCT3512RateLimitPort }
		::= { swhPort2MCT3512RateLimitTable 1 }

	SwhPort2MCT3512RateLimitEntry ::=
		SEQUENCE {
			swhPort2MCT3512RateLimitPort
				INTEGER,
			swhPort2MCT3512RateLimitMediaType
				DisplayString,
			swhPort2MCT3512RateLimitIngressEn
				INTEGER,
			swhPort2MCT3512RateLimitIngressRate
				INTEGER,
			swhPort2MCT3512RateLimitEgressEn
				INTEGER,
			swhPort2MCT3512RateLimitEgressRate
				INTEGER
		}

	swhPort2MCT3512RateLimitPort OBJECT-TYPE
		SYNTAX      INTEGER (0..2147483647)
		MAX-ACCESS  read-only
		STATUS      current
		DESCRIPTION
			"A unique value for each port."
		::= { swhPort2MCT3512RateLimitEntry 1 }

	swhPort2MCT3512RateLimitMediaType OBJECT-TYPE
		SYNTAX      DisplayString
		MAX-ACCESS  read-only
		STATUS      current
		DESCRIPTION
			"Remote Module Port Media Type."
		::= { swhPort2MCT3512RateLimitEntry 2 }

	swhPort2MCT3512RateLimitIngressEn OBJECT-TYPE
		SYNTAX      INTEGER { disable(0), enable(1) }
		MAX-ACCESS  read-write
		STATUS      current
		DESCRIPTION
			"Remote Module Port Ingress Enable."
		::= { swhPort2MCT3512RateLimitEntry 3 }

	swhPort2MCT3512RateLimitIngressRate OBJECT-TYPE
		SYNTAX      INTEGER (32..1000000)
		MAX-ACCESS  read-write
		STATUS      current
		DESCRIPTION
			"Remote Module Port Ingress Rate (32-1000000) kbps."
		::= { swhPort2MCT3512RateLimitEntry 4 }

	swhPort2MCT3512RateLimitEgressEn OBJECT-TYPE
		SYNTAX      INTEGER { disable(0), enable(1) }
		MAX-ACCESS  read-write
		STATUS      current
		DESCRIPTION
			"Remote Module Port Egress Enable."
		::= { swhPort2MCT3512RateLimitEntry 5 }

	swhPort2MCT3512RateLimitEgressRate OBJECT-TYPE
		SYNTAX      INTEGER (32..1000000)
		MAX-ACCESS  read-write
		STATUS      current
		DESCRIPTION
			"Remote Module Port Egress Rate (32-1000000) kbps."
		::= { swhPort2MCT3512RateLimitEntry 6 }


-- EthernetOAM(24).OAMRemoteModule(5).RemoteModuleConfiguration(2).Port2RemoteConfiguration(2).Port2MCT3512Configuration(1).Port2MCT3512StormControl(5)

	swhPort2MCT3512StormControl
		OBJECT IDENTIFIER ::= { swhPort2MCT3512Configuration 5 }

	swhPort2MCT3512StormControlEnable OBJECT-TYPE
		SYNTAX      INTEGER { disable(0), enable(1) }
		MAX-ACCESS  read-write
		STATUS      current
		DESCRIPTION
			"Remote Module Storm Control."
		::= { swhPort2MCT3512StormControl 1 }

	swhPort2MCT3512StormControlRate OBJECT-TYPE
		SYNTAX      INTEGER (32..1000000)
		MAX-ACCESS  read-write
		STATUS      current
		DESCRIPTION
			"Remote Module Rate (32-1000000) kbps."
		::= { swhPort2MCT3512StormControl 2 }

	swhPort2MCT3512StormControlBandwidth OBJECT-TYPE
		SYNTAX      DisplayString
		MAX-ACCESS  read-only
		STATUS      current
		DESCRIPTION
			"Remote Module Bandwidth (bps)."
		::= { swhPort2MCT3512StormControl 3 }


-- EthernetOAM(24).OAMRemoteModule(5).RemoteModuleConfiguration(2).Port2RemoteConfiguration(2).Port2MCT3512Configuration(1).Port2MCT3512LANFollowsWAN(6)

	swhPort2MCT3512LANFollowsWAN
		OBJECT IDENTIFIER ::= { swhPort2MCT3512Configuration 6 }

	swhPort2MCT3512LANFollowsWANEnable OBJECT-TYPE
		SYNTAX      INTEGER { disable(0), enable(1) }
		MAX-ACCESS  read-write
		STATUS      current
		DESCRIPTION
			"Remote Module LAN Follows WAN."
		::= { swhPort2MCT3512LANFollowsWAN 1 }


-- EthernetOAM(24).OAMRemoteModule(5).RemoteModuleConfiguration(2).Port3RemoteConfiguration(3)

	swhPort3RemoteConfiguration
		OBJECT IDENTIFIER ::= { swhRemoteModuleConfiguration 3 }


-- EthernetOAM(24).OAMRemoteModule(5).RemoteModuleConfiguration(2).Port3RemoteConfiguration(3).Port3MCT3512Configuration(1)

	swhPort3MCT3512Configuration
		OBJECT IDENTIFIER ::= { swhPort3RemoteConfiguration 1 }


-- EthernetOAM(24).OAMRemoteModule(5).RemoteModuleConfiguration(2).Port3RemoteConfiguration(3).Port3MCT3512Configuration(1).Port3MCT3512Config(1)

	swhPort3MCT3512Config
		OBJECT IDENTIFIER ::= { swhPort3MCT3512Configuration 1 }

	swhPort3MCT3512ConfigDetectedModule OBJECT-TYPE
		SYNTAX      DisplayString
		MAX-ACCESS  read-only
		STATUS      current
		DESCRIPTION
			"Detected Module."
		::= { swhPort3MCT3512Config 1 }

	swhPort3MCT3512ConfigDIPSwitchSetting OBJECT-TYPE
		SYNTAX      DisplayString
		MAX-ACCESS  read-only
		STATUS      current
		DESCRIPTION
			"DIP Switch (PIN 8) Setting."
		::= { swhPort3MCT3512Config 2 }


-- EthernetOAM(24).OAMRemoteModule(5).RemoteModuleConfiguration(2).Port3RemoteConfiguration(3).Port3MCT3512Configuration(1).Port3MCT3512PortSetup(2)

	swhPort3MCT3512PortSetup
		OBJECT IDENTIFIER ::= { swhPort3MCT3512Configuration 2 }

	swhPort3MCT3512PortSetupTable OBJECT-TYPE
		SYNTAX      SEQUENCE OF SwhPort3MCT3512PortSetupEntry
		MAX-ACCESS  not-accessible
		STATUS      current
		DESCRIPTION
			"Table of remote module port setup."
		::= { swhPort3MCT3512PortSetup 5 }

	-- Table Entry
	swhPort3MCT3512PortSetupEntry OBJECT-TYPE
		SYNTAX      SwhPort3MCT3512PortSetupEntry
		MAX-ACCESS  not-accessible
		STATUS      current
		DESCRIPTION
			"An entry in the table, containing information about remote module port setup."
		INDEX    { swhPort3MCT3512PortSetupPort }
		::= { swhPort3MCT3512PortSetupTable 1 }

	SwhPort3MCT3512PortSetupEntry ::=
		SEQUENCE {
			swhPort3MCT3512PortSetupPort
				INTEGER,
			swhPort3MCT3512PortSetupMediaType
				DisplayString,
			swhPort3MCT3512PortSetupPortState
				INTEGER,
			swhPort3MCT3512PortSetupPortType
				INTEGER,
			swhPort3MCT3512PortSetupPortSpeed
				INTEGER,
			swhPort3MCT3512PortSetupPortDuplex
				INTEGER
		}

	swhPort3MCT3512PortSetupPort OBJECT-TYPE
		SYNTAX      INTEGER (0..2147483647)
		MAX-ACCESS  read-only
		STATUS      current
		DESCRIPTION
			"A unique value for each port."
		::= { swhPort3MCT3512PortSetupEntry 1 }

	swhPort3MCT3512PortSetupMediaType OBJECT-TYPE
		SYNTAX      DisplayString
		MAX-ACCESS  read-only
		STATUS      current
		DESCRIPTION
			"Media Type."
		::= { swhPort3MCT3512PortSetupEntry 2 }

	swhPort3MCT3512PortSetupPortState OBJECT-TYPE
		SYNTAX      INTEGER { disable(0), enable(1) }
		MAX-ACCESS  read-write
		STATUS      current
		DESCRIPTION
			"Port State."
		::= { swhPort3MCT3512PortSetupEntry 3 }

	swhPort3MCT3512PortSetupPortType OBJECT-TYPE
		SYNTAX      INTEGER { manual(0), auto-negotiation(1) }
		MAX-ACCESS  read-write
		STATUS      current
		DESCRIPTION
			"Port Type."
		::= { swhPort3MCT3512PortSetupEntry 4 }

	swhPort3MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort3MCT3512PortSetupEntry 5 }

	swhPort3MCT3512PortSetupPortDuplex OBJECT-TYPE
		SYNTAX      INTEGER { halfDuplex(0), fullDuplex(1) }
		MAX-ACCESS  read-write
		STATUS      current
		DESCRIPTION
			"Port Duplex."
		::= { swhPort3MCT3512PortSetupEntry 6 }


-- EthernetOAM(24).OAMRemoteModule(5).RemoteModuleConfiguration(2).Port3RemoteConfiguration(3).Port3MCT3512Configuration(1).Port3MCT3512VLANSetup(3)

	swhPort3MCT3512VLANSetup
		OBJECT IDENTIFIER ::= { swhPort3MCT3512Configuration 3 }

	swhPort3MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort3MCT3512VLANSetup 1 }

	swhPort3MCT3512VLANSetupISPMode OBJECT-TYPE
		SYNTAX      INTEGER { disable(0), enable(1) }
		MAX-ACCESS  read-write
		STATUS      current
		DESCRIPTION
			"Remote Module ISP Mode."
		::= { swhPort3MCT3512VLANSetup 2 }

	swhPort3MCT3512VLANSetupStagEtherType OBJECT-TYPE
		SYNTAX      DisplayString
		MAX-ACCESS  read-write
		STATUS      current
		DESCRIPTION
			"Remote Module Stag EtherType."
		::= { swhPort3MCT3512VLANSetup 3 }

	swhPort3MCT3512VLANSetupTable OBJECT-TYPE
		SYNTAX      SEQUENCE OF SwhPort3MCT3512VLANSetupEntry
		MAX-ACCESS  not-accessible
		STATUS      current
		DESCRIPTION
			"Table of remote module VLAN setup."
		::= { swhPort3MCT3512VLANSetup 5 }

	-- Table Entry
	swhPort3MCT3512VLANSetupEntry OBJECT-TYPE
		SYNTAX      SwhPort3MCT3512VLANSetupEntry
		MAX-ACCESS  not-accessible
		STATUS      current
		DESCRIPTION
			"An entry in the table, containing information about remote module VLAN setup."
		INDEX    { swhPort3MCT3512VLANSetupPort }
		::= { swhPort3MCT3512VLANSetupTable 1 }

	SwhPort3MCT3512VLANSetupEntry ::=
		SEQUENCE {
			swhPort3MCT3512VLANSetupPort
				INTEGER,
			swhPort3MCT3512VLANSetupMediaType
				DisplayString,
			swhPort3MCT3512VLANSetupMode
				INTEGER,
			swhPort3MCT3512VLANSetupPVID
				INTEGER,
			swhPort3MCT3512VLANSetupTrunkVLAN
				DisplayString,
			swhPort3MCT3512VLANSetupStagVID
				INTEGER,
			swhPort3MCT3512VLANSetupISPPort
				INTEGER
		}

	swhPort3MCT3512VLANSetupPort OBJECT-TYPE
		SYNTAX      INTEGER (0..2147483647)
		MAX-ACCESS  read-only
		STATUS      current
		DESCRIPTION
			"A unique value for each port."
		::= { swhPort3MCT3512VLANSetupEntry 1 }

	swhPort3MCT3512VLANSetupMediaType OBJECT-TYPE
		SYNTAX      DisplayString
		MAX-ACCESS  read-only
		STATUS      current
		DESCRIPTION
			"Remote Module Port Media Type."
		::= { swhPort3MCT3512VLANSetupEntry 2 }

	swhPort3MCT3512VLANSetupMode OBJECT-TYPE
		SYNTAX      INTEGER { access(0), trunk(1), trunknative(2) }
		MAX-ACCESS  read-write
		STATUS      current
		DESCRIPTION
			"Remote Module Port Mode."
		::= { swhPort3MCT3512VLANSetupEntry 3 }

	swhPort3MCT3512VLANSetupPVID OBJECT-TYPE
		SYNTAX      INTEGER (1..4093)
		MAX-ACCESS  read-write
		STATUS      current
		DESCRIPTION
			"Remote Module Port PVID."
		::= { swhPort3MCT3512VLANSetupEntry 4 }

	swhPort3MCT3512VLANSetupTrunkVLAN OBJECT-TYPE
		SYNTAX      DisplayString
		MAX-ACCESS  read-write
		STATUS      current
		DESCRIPTION
			"Remote Module Port Trunk VLAN."
		::= { swhPort3MCT3512VLANSetupEntry 5 }

	swhPort3MCT3512VLANSetupStagVID OBJECT-TYPE
		SYNTAX      INTEGER (1..4093)
		MAX-ACCESS  read-write
		STATUS      current
		DESCRIPTION
			"Remote Module Port Stag VID."
		::= { swhPort3MCT3512VLANSetupEntry 6 }

	swhPort3MCT3512VLANSetupISPPort OBJECT-TYPE
		SYNTAX      INTEGER { disable(0), enable(1) }
		MAX-ACCESS  read-write
		STATUS      current
		DESCRIPTION
			"Remote Module Port ISP Port."
		::= { swhPort3MCT3512VLANSetupEntry 7 }


-- EthernetOAM(24).OAMRemoteModule(5).RemoteModuleConfiguration(2).Port3RemoteConfiguration(3).Port3MCT3512Configuration(1).Port3MCT3512RateLimit(4)

	swhPort3MCT3512RateLimit
		OBJECT IDENTIFIER ::= { swhPort3MCT3512Configuration 4 }

	swhPort3MCT3512RateLimitTable OBJECT-TYPE
		SYNTAX      SEQUENCE OF SwhPort3MCT3512RateLimitEntry
		MAX-ACCESS  not-accessible
		STATUS      current
		DESCRIPTION
			"Table of remote module QoS rate limit."
		::= { swhPort3MCT3512RateLimit 5 }

	-- Table Entry
	swhPort3MCT3512RateLimitEntry OBJECT-TYPE
		SYNTAX      SwhPort3MCT3512RateLimitEntry
		MAX-ACCESS  not-accessible
		STATUS      current
		DESCRIPTION
			"An entry in the table, containing information about remote module QoS rate limit."
		INDEX    { swhPort3MCT3512RateLimitPort }
		::= { swhPort3MCT3512RateLimitTable 1 }

	SwhPort3MCT3512RateLimitEntry ::=
		SEQUENCE {
			swhPort3MCT3512RateLimitPort
				INTEGER,
			swhPort3MCT3512RateLimitMediaType
				DisplayString,
			swhPort3MCT3512RateLimitIngressEn
				INTEGER,
			swhPort3MCT3512RateLimitIngressRate
				INTEGER,
			swhPort3MCT3512RateLimitEgressEn
				INTEGER,
			swhPort3MCT3512RateLimitEgressRate
				INTEGER
		}

	swhPort3MCT3512RateLimitPort OBJECT-TYPE
		SYNTAX      INTEGER (0..2147483647)
		MAX-ACCESS  read-only
		STATUS      current
		DESCRIPTION
			"A unique value for each port."
		::= { swhPort3MCT3512RateLimitEntry 1 }

	swhPort3MCT3512RateLimitMediaType OBJECT-TYPE
		SYNTAX      DisplayString
		MAX-ACCESS  read-only
		STATUS      current
		DESCRIPTION
			"Remote Module Port Media Type."
		::= { swhPort3MCT3512RateLimitEntry 2 }

	swhPort3MCT3512RateLimitIngressEn OBJECT-TYPE
		SYNTAX      INTEGER { disable(0), enable(1) }
		MAX-ACCESS  read-write
		STATUS      current
		DESCRIPTION
			"Remote Module Port Ingress Enable."
		::= { swhPort3MCT3512RateLimitEntry 3 }

	swhPort3MCT3512RateLimitIngressRate OBJECT-TYPE
		SYNTAX      INTEGER (32..1000000)
		MAX-ACCESS  read-write
		STATUS      current
		DESCRIPTION
			"Remote Module Port Ingress Rate (32-1000000) kbps."
		::= { swhPort3MCT3512RateLimitEntry 4 }

	swhPort3MCT3512RateLimitEgressEn OBJECT-TYPE
		SYNTAX      INTEGER { disable(0), enable(1) }
		MAX-ACCESS  read-write
		STATUS      current
		DESCRIPTION
			"Remote Module Port Egress Enable."
		::= { swhPort3MCT3512RateLimitEntry 5 }

	swhPort3MCT3512RateLimitEgressRate OBJECT-TYPE
		SYNTAX      INTEGER (32..1000000)
		MAX-ACCESS  read-write
		STATUS      current
		DESCRIPTION
			"Remote Module Port Egress Rate (32-1000000) kbps."
		::= { swhPort3MCT3512RateLimitEntry 6 }


-- EthernetOAM(24).OAMRemoteModule(5).RemoteModuleConfiguration(2).Port3RemoteConfiguration(3).Port3MCT3512Configuration(1).Port3MCT3512StormControl(5)

	swhPort3MCT3512StormControl
		OBJECT IDENTIFIER ::= { swhPort3MCT3512Configuration 5 }

	swhPort3MCT3512StormControlEnable OBJECT-TYPE
		SYNTAX      INTEGER { disable(0), enable(1) }
		MAX-ACCESS  read-write
		STATUS      current
		DESCRIPTION
			"Remote Module Storm Control."
		::= { swhPort3MCT3512StormControl 1 }

	swhPort3MCT3512StormControlRate OBJECT-TYPE
		SYNTAX      INTEGER (32..1000000)
		MAX-ACCESS  read-write
		STATUS      current
		DESCRIPTION
			"Remote Module Rate (32-1000000) kbps."
		::= { swhPort3MCT3512StormControl 2 }

	swhPort3MCT3512StormControlBandwidth OBJECT-TYPE
		SYNTAX      DisplayString
		MAX-ACCESS  read-only
		STATUS      current
		DESCRIPTION
			"Remote Module Bandwidth (bps)."
		::= { swhPort3MCT3512StormControl 3 }


-- EthernetOAM(24).OAMRemoteModule(5).RemoteModuleConfiguration(2).Port3RemoteConfiguration(3).Port3MCT3512Configuration(1).Port3MCT3512LANFollowsWAN(6)

	swhPort3MCT3512LANFollowsWAN
		OBJECT IDENTIFIER ::= { swhPort3MCT3512Configuration 6 }

	swhPort3MCT3512LANFollowsWANEnable OBJECT-TYPE
		SYNTAX      INTEGER { disable(0), enable(1) }
		MAX-ACCESS  read-write
		STATUS      current
		DESCRIPTION
			"Remote Module LAN Follows WAN."
		::= { swhPort3MCT3512LANFollowsWAN 1 }


-- EthernetOAM(24).OAMRemoteModule(5).RemoteModuleConfiguration(2).Port4RemoteConfiguration(4)

	swhPort4RemoteConfiguration
		OBJECT IDENTIFIER ::= { swhRemoteModuleConfiguration 4 }


-- EthernetOAM(24).OAMRemoteModule(5).RemoteModuleConfiguration(2).Port4RemoteConfiguration(4).Port4MCT3512Configuration(1)

	swhPort4MCT3512Configuration
		OBJECT IDENTIFIER ::= { swhPort4RemoteConfiguration 1 }


-- EthernetOAM(24).OAMRemoteModule(5).RemoteModuleConfiguration(2).Port4RemoteConfiguration(4).Port4MCT3512Configuration(1).Port4MCT3512Config(1)

	swhPort4MCT3512Config
		OBJECT IDENTIFIER ::= { swhPort4MCT3512Configuration 1 }

	swhPort4MCT3512ConfigDetectedModule OBJECT-TYPE
		SYNTAX      DisplayString
		MAX-ACCESS  read-only
		STATUS      current
		DESCRIPTION
			"Detected Module."
		::= { swhPort4MCT3512Config 1 }

	swhPort4MCT3512ConfigDIPSwitchSetting OBJECT-TYPE
		SYNTAX      DisplayString
		MAX-ACCESS  read-only
		STATUS      current
		DESCRIPTION
			"DIP Switch (PIN 8) Setting."
		::= { swhPort4MCT3512Config 2 }


-- EthernetOAM(24).OAMRemoteModule(5).RemoteModuleConfiguration(2).Port4RemoteConfiguration(4).Port4MCT3512Configuration(1).Port4MCT3512PortSetup(2)

	swhPort4MCT3512PortSetup
		OBJECT IDENTIFIER ::= { swhPort4MCT3512Configuration 2 }

	swhPort4MCT3512PortSetupTable OBJECT-TYPE
		SYNTAX      SEQUENCE OF SwhPort4MCT3512PortSetupEntry
		MAX-ACCESS  not-accessible
		STATUS      current
		DESCRIPTION
			"Table of remote module port setup."
		::= { swhPort4MCT3512PortSetup 5 }

	-- Table Entry
	swhPort4MCT3512PortSetupEntry OBJECT-TYPE
		SYNTAX      SwhPort4MCT3512PortSetupEntry
		MAX-ACCESS  not-accessible
		STATUS      current
		DESCRIPTION
			"An entry in the table, containing information about remote module port setup."
		INDEX    { swhPort4MCT3512PortSetupPort }
		::= { swhPort4MCT3512PortSetupTable 1 }

	SwhPort4MCT3512PortSetupEntry ::=
		SEQUENCE {
			swhPort4MCT3512PortSetupPort
				INTEGER,
			swhPort4MCT3512PortSetupMediaType
				DisplayString,
			swhPort4MCT3512PortSetupPortState
				INTEGER,
			swhPort4MCT3512PortSetupPortType
				INTEGER,
			swhPort4MCT3512PortSetupPortSpeed
				INTEGER,
			swhPort4MCT3512PortSetupPortDuplex
				INTEGER
		}

	swhPort4MCT3512PortSetupPort OBJECT-TYPE
		SYNTAX      INTEGER (0..2147483647)
		MAX-ACCESS  read-only
		STATUS      current
		DESCRIPTION
			"A unique value for each port."
		::= { swhPort4MCT3512PortSetupEntry 1 }

	swhPort4MCT3512PortSetupMediaType OBJECT-TYPE
		SYNTAX      DisplayString
		MAX-ACCESS  read-only
		STATUS      current
		DESCRIPTION
			"Media Type."
		::= { swhPort4MCT3512PortSetupEntry 2 }

	swhPort4MCT3512PortSetupPortState OBJECT-TYPE
		SYNTAX      INTEGER { disable(0), enable(1) }
		MAX-ACCESS  read-write
		STATUS      current
		DESCRIPTION
			"Port State."
		::= { swhPort4MCT3512PortSetupEntry 3 }

	swhPort4MCT3512PortSetupPortType OBJECT-TYPE
		SYNTAX      INTEGER { manual(0), auto-negotiation(1) }
		MAX-ACCESS  read-write
		STATUS      current
		DESCRIPTION
			"Port Type."
		::= { swhPort4MCT3512PortSetupEntry 4 }

	swhPort4MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort4MCT3512PortSetupEntry 5 }

	swhPort4MCT3512PortSetupPortDuplex OBJECT-TYPE
		SYNTAX      INTEGER { halfDuplex(0), fullDuplex(1) }
		MAX-ACCESS  read-write
		STATUS      current
		DESCRIPTION
			"Port Duplex."
		::= { swhPort4MCT3512PortSetupEntry 6 }


-- EthernetOAM(24).OAMRemoteModule(5).RemoteModuleConfiguration(2).Port4RemoteConfiguration(4).Port4MCT3512Configuration(1).Port4MCT3512VLANSetup(3)

	swhPort4MCT3512VLANSetup
		OBJECT IDENTIFIER ::= { swhPort4MCT3512Configuration 3 }

	swhPort4MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort4MCT3512VLANSetup 1 }

	swhPort4MCT3512VLANSetupISPMode OBJECT-TYPE
		SYNTAX      INTEGER { disable(0), enable(1) }
		MAX-ACCESS  read-write
		STATUS      current
		DESCRIPTION
			"Remote Module ISP Mode."
		::= { swhPort4MCT3512VLANSetup 2 }

	swhPort4MCT3512VLANSetupStagEtherType OBJECT-TYPE
		SYNTAX      DisplayString
		MAX-ACCESS  read-write
		STATUS      current
		DESCRIPTION
			"Remote Module Stag EtherType."
		::= { swhPort4MCT3512VLANSetup 3 }

	swhPort4MCT3512VLANSetupTable OBJECT-TYPE
		SYNTAX      SEQUENCE OF SwhPort4MCT3512VLANSetupEntry
		MAX-ACCESS  not-accessible
		STATUS      current
		DESCRIPTION
			"Table of remote module VLAN setup."
		::= { swhPort4MCT3512VLANSetup 5 }

	-- Table Entry
	swhPort4MCT3512VLANSetupEntry OBJECT-TYPE
		SYNTAX      SwhPort4MCT3512VLANSetupEntry
		MAX-ACCESS  not-accessible
		STATUS      current
		DESCRIPTION
			"An entry in the table, containing information about remote module VLAN setup."
		INDEX    { swhPort4MCT3512VLANSetupPort }
		::= { swhPort4MCT3512VLANSetupTable 1 }

	SwhPort4MCT3512VLANSetupEntry ::=
		SEQUENCE {
			swhPort4MCT3512VLANSetupPort
				INTEGER,
			swhPort4MCT3512VLANSetupMediaType
				DisplayString,
			swhPort4MCT3512VLANSetupMode
				INTEGER,
			swhPort4MCT3512VLANSetupPVID
				INTEGER,
			swhPort4MCT3512VLANSetupTrunkVLAN
				DisplayString,
			swhPort4MCT3512VLANSetupStagVID
				INTEGER,
			swhPort4MCT3512VLANSetupISPPort
				INTEGER
		}

	swhPort4MCT3512VLANSetupPort OBJECT-TYPE
		SYNTAX      INTEGER (0..2147483647)
		MAX-ACCESS  read-only
		STATUS      current
		DESCRIPTION
			"A unique value for each port."
		::= { swhPort4MCT3512VLANSetupEntry 1 }

	swhPort4MCT3512VLANSetupMediaType OBJECT-TYPE
		SYNTAX      DisplayString
		MAX-ACCESS  read-only
		STATUS      current
		DESCRIPTION
			"Remote Module Port Media Type."
		::= { swhPort4MCT3512VLANSetupEntry 2 }

	swhPort4MCT3512VLANSetupMode OBJECT-TYPE
		SYNTAX      INTEGER { access(0), trunk(1), trunknative(2) }
		MAX-ACCESS  read-write
		STATUS      current
		DESCRIPTION
			"Remote Module Port Mode."
		::= { swhPort4MCT3512VLANSetupEntry 3 }

	swhPort4MCT3512VLANSetupPVID OBJECT-TYPE
		SYNTAX      INTEGER (1..4093)
		MAX-ACCESS  read-write
		STATUS      current
		DESCRIPTION
			"Remote Module Port PVID."
		::= { swhPort4MCT3512VLANSetupEntry 4 }

	swhPort4MCT3512VLANSetupTrunkVLAN OBJECT-TYPE
		SYNTAX      DisplayString
		MAX-ACCESS  read-write
		STATUS      current
		DESCRIPTION
			"Remote Module Port Trunk VLAN."
		::= { swhPort4MCT3512VLANSetupEntry 5 }

	swhPort4MCT3512VLANSetupStagVID OBJECT-TYPE
		SYNTAX      INTEGER (1..4093)
		MAX-ACCESS  read-write
		STATUS      current
		DESCRIPTION
			"Remote Module Port Stag VID."
		::= { swhPort4MCT3512VLANSetupEntry 6 }

	swhPort4MCT3512VLANSetupISPPort OBJECT-TYPE
		SYNTAX      INTEGER { disable(0), enable(1) }
		MAX-ACCESS  read-write
		STATUS      current
		DESCRIPTION
			"Remote Module Port ISP Port."
		::= { swhPort4MCT3512VLANSetupEntry 7 }


-- EthernetOAM(24).OAMRemoteModule(5).RemoteModuleConfiguration(2).Port4RemoteConfiguration(4).Port4MCT3512Configuration(1).Port4MCT3512RateLimit(4)

	swhPort4MCT3512RateLimit
		OBJECT IDENTIFIER ::= { swhPort4MCT3512Configuration 4 }

	swhPort4MCT3512RateLimitTable OBJECT-TYPE
		SYNTAX      SEQUENCE OF SwhPort4MCT3512RateLimitEntry
		MAX-ACCESS  not-accessible
		STATUS      current
		DESCRIPTION
			"Table of remote module QoS rate limit."
		::= { swhPort4MCT3512RateLimit 5 }

	-- Table Entry
	swhPort4MCT3512RateLimitEntry OBJECT-TYPE
		SYNTAX      SwhPort4MCT3512RateLimitEntry
		MAX-ACCESS  not-accessible
		STATUS      current
		DESCRIPTION
			"An entry in the table, containing information about remote module QoS rate limit."
		INDEX    { swhPort4MCT3512RateLimitPort }
		::= { swhPort4MCT3512RateLimitTable 1 }

	SwhPort4MCT3512RateLimitEntry ::=
		SEQUENCE {
			swhPort4MCT3512RateLimitPort
				INTEGER,
			swhPort4MCT3512RateLimitMediaType
				DisplayString,
			swhPort4MCT3512RateLimitIngressEn
				INTEGER,
			swhPort4MCT3512RateLimitIngressRate
				INTEGER,
			swhPort4MCT3512RateLimitEgressEn
				INTEGER,
			swhPort4MCT3512RateLimitEgressRate
				INTEGER
		}

	swhPort4MCT3512RateLimitPort OBJECT-TYPE
		SYNTAX      INTEGER (0..2147483647)
		MAX-ACCESS  read-only
		STATUS      current
		DESCRIPTION
			"A unique value for each port."
		::= { swhPort4MCT3512RateLimitEntry 1 }

	swhPort4MCT3512RateLimitMediaType OBJECT-TYPE
		SYNTAX      DisplayString
		MAX-ACCESS  read-only
		STATUS      current
		DESCRIPTION
			"Remote Module Port Media Type."
		::= { swhPort4MCT3512RateLimitEntry 2 }

	swhPort4MCT3512RateLimitIngressEn OBJECT-TYPE
		SYNTAX      INTEGER { disable(0), enable(1) }
		MAX-ACCESS  read-write
		STATUS      current
		DESCRIPTION
			"Remote Module Port Ingress Enable."
		::= { swhPort4MCT3512RateLimitEntry 3 }

	swhPort4MCT3512RateLimitIngressRate OBJECT-TYPE
		SYNTAX      INTEGER (32..1000000)
		MAX-ACCESS  read-write
		STATUS      current
		DESCRIPTION
			"Remote Module Port Ingress Rate (32-1000000) kbps."
		::= { swhPort4MCT3512RateLimitEntry 4 }

	swhPort4MCT3512RateLimitEgressEn OBJECT-TYPE
		SYNTAX      INTEGER { disable(0), enable(1) }
		MAX-ACCESS  read-write
		STATUS      current
		DESCRIPTION
			"Remote Module Port Egress Enable."
		::= { swhPort4MCT3512RateLimitEntry 5 }

	swhPort4MCT3512RateLimitEgressRate OBJECT-TYPE
		SYNTAX      INTEGER (32..1000000)
		MAX-ACCESS  read-write
		STATUS      current
		DESCRIPTION
			"Remote Module Port Egress Rate (32-1000000) kbps."
		::= { swhPort4MCT3512RateLimitEntry 6 }


-- EthernetOAM(24).OAMRemoteModule(5).RemoteModuleConfiguration(2).Port4RemoteConfiguration(4).Port4MCT3512Configuration(1).Port4MCT3512StormControl(5)

	swhPort4MCT3512StormControl
		OBJECT IDENTIFIER ::= { swhPort4MCT3512Configuration 5 }

	swhPort4MCT3512StormControlEnable OBJECT-TYPE
		SYNTAX      INTEGER { disable(0), enable(1) }
		MAX-ACCESS  read-write
		STATUS      current
		DESCRIPTION
			"Remote Module Storm Control."
		::= { swhPort4MCT3512StormControl 1 }

	swhPort4MCT3512StormControlRate OBJECT-TYPE
		SYNTAX      INTEGER (32..1000000)
		MAX-ACCESS  read-write
		STATUS      current
		DESCRIPTION
			"Remote Module Rate (32-1000000) kbps."
		::= { swhPort4MCT3512StormControl 2 }

	swhPort4MCT3512StormControlBandwidth OBJECT-TYPE
		SYNTAX      DisplayString
		MAX-ACCESS  read-only
		STATUS      current
		DESCRIPTION
			"Remote Module Bandwidth (bps)."
		::= { swhPort4MCT3512StormControl 3 }


-- EthernetOAM(24).OAMRemoteModule(5).RemoteModuleConfiguration(2).Port4RemoteConfiguration(4).Port4MCT3512Configuration(1).Port4MCT3512LANFollowsWAN(6)

	swhPort4MCT3512LANFollowsWAN
		OBJECT IDENTIFIER ::= { swhPort4MCT3512Configuration 6 }

	swhPort4MCT3512LANFollowsWANEnable OBJECT-TYPE
		SYNTAX      INTEGER { disable(0), enable(1) }
		MAX-ACCESS  read-write
		STATUS      current
		DESCRIPTION
			"Remote Module LAN Follows WAN."
		::= { swhPort4MCT3512LANFollowsWAN 1 }


-- EthernetOAM(24).OAMRemoteModule(5).RemoteModuleConfiguration(2).Port5RemoteConfiguration(5)

	swhPort5RemoteConfiguration
		OBJECT IDENTIFIER ::= { swhRemoteModuleConfiguration 5 }


-- EthernetOAM(24).OAMRemoteModule(5).RemoteModuleConfiguration(2).Port5RemoteConfiguration(5).Port5MCT3512Configuration(1)

	swhPort5MCT3512Configuration
		OBJECT IDENTIFIER ::= { swhPort5RemoteConfiguration 1 }


-- EthernetOAM(24).OAMRemoteModule(5).RemoteModuleConfiguration(2).Port5RemoteConfiguration(5).Port5MCT3512Configuration(1).Port5MCT3512Config(1)

	swhPort5MCT3512Config
		OBJECT IDENTIFIER ::= { swhPort5MCT3512Configuration 1 }

	swhPort5MCT3512ConfigDetectedModule OBJECT-TYPE
		SYNTAX      DisplayString
		MAX-ACCESS  read-only
		STATUS      current
		DESCRIPTION
			"Detected Module."
		::= { swhPort5MCT3512Config 1 }

	swhPort5MCT3512ConfigDIPSwitchSetting OBJECT-TYPE
		SYNTAX      DisplayString
		MAX-ACCESS  read-only
		STATUS      current
		DESCRIPTION
			"DIP Switch (PIN 8) Setting."
		::= { swhPort5MCT3512Config 2 }


-- EthernetOAM(24).OAMRemoteModule(5).RemoteModuleConfiguration(2).Port5RemoteConfiguration(5).Port5MCT3512Configuration(1).Port5MCT3512PortSetup(2)

	swhPort5MCT3512PortSetup
		OBJECT IDENTIFIER ::= { swhPort5MCT3512Configuration 2 }

	swhPort5MCT3512PortSetupTable OBJECT-TYPE
		SYNTAX      SEQUENCE OF SwhPort5MCT3512PortSetupEntry
		MAX-ACCESS  not-accessible
		STATUS      current
		DESCRIPTION
			"Table of remote module port setup."
		::= { swhPort5MCT3512PortSetup 5 }

	-- Table Entry
	swhPort5MCT3512PortSetupEntry OBJECT-TYPE
		SYNTAX      SwhPort5MCT3512PortSetupEntry
		MAX-ACCESS  not-accessible
		STATUS      current
		DESCRIPTION
			"An entry in the table, containing information about remote module port setup."
		INDEX    { swhPort5MCT3512PortSetupPort }
		::= { swhPort5MCT3512PortSetupTable 1 }

	SwhPort5MCT3512PortSetupEntry ::=
		SEQUENCE {
			swhPort5MCT3512PortSetupPort
				INTEGER,
			swhPort5MCT3512PortSetupMediaType
				DisplayString,
			swhPort5MCT3512PortSetupPortState
				INTEGER,
			swhPort5MCT3512PortSetupPortType
				INTEGER,
			swhPort5MCT3512PortSetupPortSpeed
				INTEGER,
			swhPort5MCT3512PortSetupPortDuplex
				INTEGER
		}

	swhPort5MCT3512PortSetupPort OBJECT-TYPE
		SYNTAX      INTEGER (0..2147483647)
		MAX-ACCESS  read-only
		STATUS      current
		DESCRIPTION
			"A unique value for each port."
		::= { swhPort5MCT3512PortSetupEntry 1 }

	swhPort5MCT3512PortSetupMediaType OBJECT-TYPE
		SYNTAX      DisplayString
		MAX-ACCESS  read-only
		STATUS      current
		DESCRIPTION
			"Media Type."
		::= { swhPort5MCT3512PortSetupEntry 2 }

	swhPort5MCT3512PortSetupPortState OBJECT-TYPE
		SYNTAX      INTEGER { disable(0), enable(1) }
		MAX-ACCESS  read-write
		STATUS      current
		DESCRIPTION
			"Port State."
		::= { swhPort5MCT3512PortSetupEntry 3 }

	swhPort5MCT3512PortSetupPortType OBJECT-TYPE
		SYNTAX      INTEGER { manual(0), auto-negotiation(1) }
		MAX-ACCESS  read-write
		STATUS      current
		DESCRIPTION
			"Port Type."
		::= { swhPort5MCT3512PortSetupEntry 4 }

	swhPort5MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort5MCT3512PortSetupEntry 5 }

	swhPort5MCT3512PortSetupPortDuplex OBJECT-TYPE
		SYNTAX      INTEGER { halfDuplex(0), fullDuplex(1) }
		MAX-ACCESS  read-write
		STATUS      current
		DESCRIPTION
			"Port Duplex."
		::= { swhPort5MCT3512PortSetupEntry 6 }


-- EthernetOAM(24).OAMRemoteModule(5).RemoteModuleConfiguration(2).Port5RemoteConfiguration(5).Port5MCT3512Configuration(1).Port5MCT3512VLANSetup(3)

	swhPort5MCT3512VLANSetup
		OBJECT IDENTIFIER ::= { swhPort5MCT3512Configuration 3 }

	swhPort5MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort5MCT3512VLANSetup 1 }

	swhPort5MCT3512VLANSetupISPMode OBJECT-TYPE
		SYNTAX      INTEGER { disable(0), enable(1) }
		MAX-ACCESS  read-write
		STATUS      current
		DESCRIPTION
			"Remote Module ISP Mode."
		::= { swhPort5MCT3512VLANSetup 2 }

	swhPort5MCT3512VLANSetupStagEtherType OBJECT-TYPE
		SYNTAX      DisplayString
		MAX-ACCESS  read-write
		STATUS      current
		DESCRIPTION
			"Remote Module Stag EtherType."
		::= { swhPort5MCT3512VLANSetup 3 }

	swhPort5MCT3512VLANSetupTable OBJECT-TYPE
		SYNTAX      SEQUENCE OF SwhPort5MCT3512VLANSetupEntry
		MAX-ACCESS  not-accessible
		STATUS      current
		DESCRIPTION
			"Table of remote module VLAN setup."
		::= { swhPort5MCT3512VLANSetup 5 }

	-- Table Entry
	swhPort5MCT3512VLANSetupEntry OBJECT-TYPE
		SYNTAX      SwhPort5MCT3512VLANSetupEntry
		MAX-ACCESS  not-accessible
		STATUS      current
		DESCRIPTION
			"An entry in the table, containing information about remote module VLAN setup."
		INDEX    { swhPort5MCT3512VLANSetupPort }
		::= { swhPort5MCT3512VLANSetupTable 1 }

	SwhPort5MCT3512VLANSetupEntry ::=
		SEQUENCE {
			swhPort5MCT3512VLANSetupPort
				INTEGER,
			swhPort5MCT3512VLANSetupMediaType
				DisplayString,
			swhPort5MCT3512VLANSetupMode
				INTEGER,
			swhPort5MCT3512VLANSetupPVID
				INTEGER,
			swhPort5MCT3512VLANSetupTrunkVLAN
				DisplayString,
			swhPort5MCT3512VLANSetupStagVID
				INTEGER,
			swhPort5MCT3512VLANSetupISPPort
				INTEGER
		}

	swhPort5MCT3512VLANSetupPort OBJECT-TYPE
		SYNTAX      INTEGER (0..2147483647)
		MAX-ACCESS  read-only
		STATUS      current
		DESCRIPTION
			"A unique value for each port."
		::= { swhPort5MCT3512VLANSetupEntry 1 }

	swhPort5MCT3512VLANSetupMediaType OBJECT-TYPE
		SYNTAX      DisplayString
		MAX-ACCESS  read-only
		STATUS      current
		DESCRIPTION
			"Remote Module Port Media Type."
		::= { swhPort5MCT3512VLANSetupEntry 2 }

	swhPort5MCT3512VLANSetupMode OBJECT-TYPE
		SYNTAX      INTEGER { access(0), trunk(1), trunknative(2) }
		MAX-ACCESS  read-write
		STATUS      current
		DESCRIPTION
			"Remote Module Port Mode."
		::= { swhPort5MCT3512VLANSetupEntry 3 }

	swhPort5MCT3512VLANSetupPVID OBJECT-TYPE
		SYNTAX      INTEGER (1..4093)
		MAX-ACCESS  read-write
		STATUS      current
		DESCRIPTION
			"Remote Module Port PVID."
		::= { swhPort5MCT3512VLANSetupEntry 4 }

	swhPort5MCT3512VLANSetupTrunkVLAN OBJECT-TYPE
		SYNTAX      DisplayString
		MAX-ACCESS  read-write
		STATUS      current
		DESCRIPTION
			"Remote Module Port Trunk VLAN."
		::= { swhPort5MCT3512VLANSetupEntry 5 }

	swhPort5MCT3512VLANSetupStagVID OBJECT-TYPE
		SYNTAX      INTEGER (1..4093)
		MAX-ACCESS  read-write
		STATUS      current
		DESCRIPTION
			"Remote Module Port Stag VID."
		::= { swhPort5MCT3512VLANSetupEntry 6 }

	swhPort5MCT3512VLANSetupISPPort OBJECT-TYPE
		SYNTAX      INTEGER { disable(0), enable(1) }
		MAX-ACCESS  read-write
		STATUS      current
		DESCRIPTION
			"Remote Module Port ISP Port."
		::= { swhPort5MCT3512VLANSetupEntry 7 }


-- EthernetOAM(24).OAMRemoteModule(5).RemoteModuleConfiguration(2).Port5RemoteConfiguration(5).Port5MCT3512Configuration(1).Port5MCT3512RateLimit(4)

	swhPort5MCT3512RateLimit
		OBJECT IDENTIFIER ::= { swhPort5MCT3512Configuration 4 }

	swhPort5MCT3512RateLimitTable OBJECT-TYPE
		SYNTAX      SEQUENCE OF SwhPort5MCT3512RateLimitEntry
		MAX-ACCESS  not-accessible
		STATUS      current
		DESCRIPTION
			"Table of remote module QoS rate limit."
		::= { swhPort5MCT3512RateLimit 5 }

	-- Table Entry
	swhPort5MCT3512RateLimitEntry OBJECT-TYPE
		SYNTAX      SwhPort5MCT3512RateLimitEntry
		MAX-ACCESS  not-accessible
		STATUS      current
		DESCRIPTION
			"An entry in the table, containing information about remote module QoS rate limit."
		INDEX    { swhPort5MCT3512RateLimitPort }
		::= { swhPort5MCT3512RateLimitTable 1 }

	SwhPort5MCT3512RateLimitEntry ::=
		SEQUENCE {
			swhPort5MCT3512RateLimitPort
				INTEGER,
			swhPort5MCT3512RateLimitMediaType
				DisplayString,
			swhPort5MCT3512RateLimitIngressEn
				INTEGER,
			swhPort5MCT3512RateLimitIngressRate
				INTEGER,
			swhPort5MCT3512RateLimitEgressEn
				INTEGER,
			swhPort5MCT3512RateLimitEgressRate
				INTEGER
		}

	swhPort5MCT3512RateLimitPort OBJECT-TYPE
		SYNTAX      INTEGER (0..2147483647)
		MAX-ACCESS  read-only
		STATUS      current
		DESCRIPTION
			"A unique value for each port."
		::= { swhPort5MCT3512RateLimitEntry 1 }

	swhPort5MCT3512RateLimitMediaType OBJECT-TYPE
		SYNTAX      DisplayString
		MAX-ACCESS  read-only
		STATUS      current
		DESCRIPTION
			"Remote Module Port Media Type."
		::= { swhPort5MCT3512RateLimitEntry 2 }

	swhPort5MCT3512RateLimitIngressEn OBJECT-TYPE
		SYNTAX      INTEGER { disable(0), enable(1) }
		MAX-ACCESS  read-write
		STATUS      current
		DESCRIPTION
			"Remote Module Port Ingress Enable."
		::= { swhPort5MCT3512RateLimitEntry 3 }

	swhPort5MCT3512RateLimitIngressRate OBJECT-TYPE
		SYNTAX      INTEGER (32..1000000)
		MAX-ACCESS  read-write
		STATUS      current
		DESCRIPTION
			"Remote Module Port Ingress Rate (32-1000000) kbps."
		::= { swhPort5MCT3512RateLimitEntry 4 }

	swhPort5MCT3512RateLimitEgressEn OBJECT-TYPE
		SYNTAX      INTEGER { disable(0), enable(1) }
		MAX-ACCESS  read-write
		STATUS      current
		DESCRIPTION
			"Remote Module Port Egress Enable."
		::= { swhPort5MCT3512RateLimitEntry 5 }

	swhPort5MCT3512RateLimitEgressRate OBJECT-TYPE
		SYNTAX      INTEGER (32..1000000)
		MAX-ACCESS  read-write
		STATUS      current
		DESCRIPTION
			"Remote Module Port Egress Rate (32-1000000) kbps."
		::= { swhPort5MCT3512RateLimitEntry 6 }


-- EthernetOAM(24).OAMRemoteModule(5).RemoteModuleConfiguration(2).Port5RemoteConfiguration(5).Port5MCT3512Configuration(1).Port5MCT3512StormControl(5)

	swhPort5MCT3512StormControl
		OBJECT IDENTIFIER ::= { swhPort5MCT3512Configuration 5 }

	swhPort5MCT3512StormControlEnable OBJECT-TYPE
		SYNTAX      INTEGER { disable(0), enable(1) }
		MAX-ACCESS  read-write
		STATUS      current
		DESCRIPTION
			"Remote Module Storm Control."
		::= { swhPort5MCT3512StormControl 1 }

	swhPort5MCT3512StormControlRate OBJECT-TYPE
		SYNTAX      INTEGER (32..1000000)
		MAX-ACCESS  read-write
		STATUS      current
		DESCRIPTION
			"Remote Module Rate (32-1000000) kbps."
		::= { swhPort5MCT3512StormControl 2 }

	swhPort5MCT3512StormControlBandwidth OBJECT-TYPE
		SYNTAX      DisplayString
		MAX-ACCESS  read-only
		STATUS      current
		DESCRIPTION
			"Remote Module Bandwidth (bps)."
		::= { swhPort5MCT3512StormControl 3 }


-- EthernetOAM(24).OAMRemoteModule(5).RemoteModuleConfiguration(2).Port5RemoteConfiguration(5).Port5MCT3512Configuration(1).Port5MCT3512LANFollowsWAN(6)

	swhPort5MCT3512LANFollowsWAN
		OBJECT IDENTIFIER ::= { swhPort5MCT3512Configuration 6 }

	swhPort5MCT3512LANFollowsWANEnable OBJECT-TYPE
		SYNTAX      INTEGER { disable(0), enable(1) }
		MAX-ACCESS  read-write
		STATUS      current
		DESCRIPTION
			"Remote Module LAN Follows WAN."
		::= { swhPort5MCT3512LANFollowsWAN 1 }


-- EthernetOAM(24).OAMRemoteModule(5).RemoteModuleConfiguration(2).Port6RemoteConfiguration(6)

	swhPort6RemoteConfiguration
		OBJECT IDENTIFIER ::= { swhRemoteModuleConfiguration 6 }


-- EthernetOAM(24).OAMRemoteModule(5).RemoteModuleConfiguration(2).Port6RemoteConfiguration(6).Port6MCT3512Configuration(1)

	swhPort6MCT3512Configuration
		OBJECT IDENTIFIER ::= { swhPort6RemoteConfiguration 1 }


-- EthernetOAM(24).OAMRemoteModule(5).RemoteModuleConfiguration(2).Port6RemoteConfiguration(6).Port6MCT3512Configuration(1).Port6MCT3512Config(1)

	swhPort6MCT3512Config
		OBJECT IDENTIFIER ::= { swhPort6MCT3512Configuration 1 }

	swhPort6MCT3512ConfigDetectedModule OBJECT-TYPE
		SYNTAX      DisplayString
		MAX-ACCESS  read-only
		STATUS      current
		DESCRIPTION
			"Detected Module."
		::= { swhPort6MCT3512Config 1 }

	swhPort6MCT3512ConfigDIPSwitchSetting OBJECT-TYPE
		SYNTAX      DisplayString
		MAX-ACCESS  read-only
		STATUS      current
		DESCRIPTION
			"DIP Switch (PIN 8) Setting."
		::= { swhPort6MCT3512Config 2 }


-- EthernetOAM(24).OAMRemoteModule(5).RemoteModuleConfiguration(2).Port6RemoteConfiguration(6).Port6MCT3512Configuration(1).Port6MCT3512PortSetup(2)

	swhPort6MCT3512PortSetup
		OBJECT IDENTIFIER ::= { swhPort6MCT3512Configuration 2 }

	swhPort6MCT3512PortSetupTable OBJECT-TYPE
		SYNTAX      SEQUENCE OF SwhPort6MCT3512PortSetupEntry
		MAX-ACCESS  not-accessible
		STATUS      current
		DESCRIPTION
			"Table of remote module port setup."
		::= { swhPort6MCT3512PortSetup 5 }

	-- Table Entry
	swhPort6MCT3512PortSetupEntry OBJECT-TYPE
		SYNTAX      SwhPort6MCT3512PortSetupEntry
		MAX-ACCESS  not-accessible
		STATUS      current
		DESCRIPTION
			"An entry in the table, containing information about remote module port setup."
		INDEX    { swhPort6MCT3512PortSetupPort }
		::= { swhPort6MCT3512PortSetupTable 1 }

	SwhPort6MCT3512PortSetupEntry ::=
		SEQUENCE {
			swhPort6MCT3512PortSetupPort
				INTEGER,
			swhPort6MCT3512PortSetupMediaType
				DisplayString,
			swhPort6MCT3512PortSetupPortState
				INTEGER,
			swhPort6MCT3512PortSetupPortType
				INTEGER,
			swhPort6MCT3512PortSetupPortSpeed
				INTEGER,
			swhPort6MCT3512PortSetupPortDuplex
				INTEGER
		}

	swhPort6MCT3512PortSetupPort OBJECT-TYPE
		SYNTAX      INTEGER (0..2147483647)
		MAX-ACCESS  read-only
		STATUS      current
		DESCRIPTION
			"A unique value for each port."
		::= { swhPort6MCT3512PortSetupEntry 1 }

	swhPort6MCT3512PortSetupMediaType OBJECT-TYPE
		SYNTAX      DisplayString
		MAX-ACCESS  read-only
		STATUS      current
		DESCRIPTION
			"Media Type."
		::= { swhPort6MCT3512PortSetupEntry 2 }

	swhPort6MCT3512PortSetupPortState OBJECT-TYPE
		SYNTAX      INTEGER { disable(0), enable(1) }
		MAX-ACCESS  read-write
		STATUS      current
		DESCRIPTION
			"Port State."
		::= { swhPort6MCT3512PortSetupEntry 3 }

	swhPort6MCT3512PortSetupPortType OBJECT-TYPE
		SYNTAX      INTEGER { manual(0), auto-negotiation(1) }
		MAX-ACCESS  read-write
		STATUS      current
		DESCRIPTION
			"Port Type."
		::= { swhPort6MCT3512PortSetupEntry 4 }

	swhPort6MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort6MCT3512PortSetupEntry 5 }

	swhPort6MCT3512PortSetupPortDuplex OBJECT-TYPE
		SYNTAX      INTEGER { halfDuplex(0), fullDuplex(1) }
		MAX-ACCESS  read-write
		STATUS      current
		DESCRIPTION
			"Port Duplex."
		::= { swhPort6MCT3512PortSetupEntry 6 }


-- EthernetOAM(24).OAMRemoteModule(5).RemoteModuleConfiguration(2).Port6RemoteConfiguration(6).Port6MCT3512Configuration(1).Port6MCT3512VLANSetup(3)

	swhPort6MCT3512VLANSetup
		OBJECT IDENTIFIER ::= { swhPort6MCT3512Configuration 3 }

	swhPort6MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort6MCT3512VLANSetup 1 }

	swhPort6MCT3512VLANSetupISPMode OBJECT-TYPE
		SYNTAX      INTEGER { disable(0), enable(1) }
		MAX-ACCESS  read-write
		STATUS      current
		DESCRIPTION
			"Remote Module ISP Mode."
		::= { swhPort6MCT3512VLANSetup 2 }

	swhPort6MCT3512VLANSetupStagEtherType OBJECT-TYPE
		SYNTAX      DisplayString
		MAX-ACCESS  read-write
		STATUS      current
		DESCRIPTION
			"Remote Module Stag EtherType."
		::= { swhPort6MCT3512VLANSetup 3 }

	swhPort6MCT3512VLANSetupTable OBJECT-TYPE
		SYNTAX      SEQUENCE OF SwhPort6MCT3512VLANSetupEntry
		MAX-ACCESS  not-accessible
		STATUS      current
		DESCRIPTION
			"Table of remote module VLAN setup."
		::= { swhPort6MCT3512VLANSetup 5 }

	-- Table Entry
	swhPort6MCT3512VLANSetupEntry OBJECT-TYPE
		SYNTAX      SwhPort6MCT3512VLANSetupEntry
		MAX-ACCESS  not-accessible
		STATUS      current
		DESCRIPTION
			"An entry in the table, containing information about remote module VLAN setup."
		INDEX    { swhPort6MCT3512VLANSetupPort }
		::= { swhPort6MCT3512VLANSetupTable 1 }

	SwhPort6MCT3512VLANSetupEntry ::=
		SEQUENCE {
			swhPort6MCT3512VLANSetupPort
				INTEGER,
			swhPort6MCT3512VLANSetupMediaType
				DisplayString,
			swhPort6MCT3512VLANSetupMode
				INTEGER,
			swhPort6MCT3512VLANSetupPVID
				INTEGER,
			swhPort6MCT3512VLANSetupTrunkVLAN
				DisplayString,
			swhPort6MCT3512VLANSetupStagVID
				INTEGER,
			swhPort6MCT3512VLANSetupISPPort
				INTEGER
		}

	swhPort6MCT3512VLANSetupPort OBJECT-TYPE
		SYNTAX      INTEGER (0..2147483647)
		MAX-ACCESS  read-only
		STATUS      current
		DESCRIPTION
			"A unique value for each port."
		::= { swhPort6MCT3512VLANSetupEntry 1 }

	swhPort6MCT3512VLANSetupMediaType OBJECT-TYPE
		SYNTAX      DisplayString
		MAX-ACCESS  read-only
		STATUS      current
		DESCRIPTION
			"Remote Module Port Media Type."
		::= { swhPort6MCT3512VLANSetupEntry 2 }

	swhPort6MCT3512VLANSetupMode OBJECT-TYPE
		SYNTAX      INTEGER { access(0), trunk(1), trunknative(2) }
		MAX-ACCESS  read-write
		STATUS      current
		DESCRIPTION
			"Remote Module Port Mode."
		::= { swhPort6MCT3512VLANSetupEntry 3 }

	swhPort6MCT3512VLANSetupPVID OBJECT-TYPE
		SYNTAX      INTEGER (1..4093)
		MAX-ACCESS  read-write
		STATUS      current
		DESCRIPTION
			"Remote Module Port PVID."
		::= { swhPort6MCT3512VLANSetupEntry 4 }

	swhPort6MCT3512VLANSetupTrunkVLAN OBJECT-TYPE
		SYNTAX      DisplayString
		MAX-ACCESS  read-write
		STATUS      current
		DESCRIPTION
			"Remote Module Port Trunk VLAN."
		::= { swhPort6MCT3512VLANSetupEntry 5 }

	swhPort6MCT3512VLANSetupStagVID OBJECT-TYPE
		SYNTAX      INTEGER (1..4093)
		MAX-ACCESS  read-write
		STATUS      current
		DESCRIPTION
			"Remote Module Port Stag VID."
		::= { swhPort6MCT3512VLANSetupEntry 6 }

	swhPort6MCT3512VLANSetupISPPort OBJECT-TYPE
		SYNTAX      INTEGER { disable(0), enable(1) }
		MAX-ACCESS  read-write
		STATUS      current
		DESCRIPTION
			"Remote Module Port ISP Port."
		::= { swhPort6MCT3512VLANSetupEntry 7 }


-- EthernetOAM(24).OAMRemoteModule(5).RemoteModuleConfiguration(2).Port6RemoteConfiguration(6).Port6MCT3512Configuration(1).Port6MCT3512RateLimit(4)

	swhPort6MCT3512RateLimit
		OBJECT IDENTIFIER ::= { swhPort6MCT3512Configuration 4 }

	swhPort6MCT3512RateLimitTable OBJECT-TYPE
		SYNTAX      SEQUENCE OF SwhPort6MCT3512RateLimitEntry
		MAX-ACCESS  not-accessible
		STATUS      current
		DESCRIPTION
			"Table of remote module QoS rate limit."
		::= { swhPort6MCT3512RateLimit 5 }

	-- Table Entry
	swhPort6MCT3512RateLimitEntry OBJECT-TYPE
		SYNTAX      SwhPort6MCT3512RateLimitEntry
		MAX-ACCESS  not-accessible
		STATUS      current
		DESCRIPTION
			"An entry in the table, containing information about remote module QoS rate limit."
		INDEX    { swhPort6MCT3512RateLimitPort }
		::= { swhPort6MCT3512RateLimitTable 1 }

	SwhPort6MCT3512RateLimitEntry ::=
		SEQUENCE {
			swhPort6MCT3512RateLimitPort
				INTEGER,
			swhPort6MCT3512RateLimitMediaType
				DisplayString,
			swhPort6MCT3512RateLimitIngressEn
				INTEGER,
			swhPort6MCT3512RateLimitIngressRate
				INTEGER,
			swhPort6MCT3512RateLimitEgressEn
				INTEGER,
			swhPort6MCT3512RateLimitEgressRate
				INTEGER
		}

	swhPort6MCT3512RateLimitPort OBJECT-TYPE
		SYNTAX      INTEGER (0..2147483647)
		MAX-ACCESS  read-only
		STATUS      current
		DESCRIPTION
			"A unique value for each port."
		::= { swhPort6MCT3512RateLimitEntry 1 }

	swhPort6MCT3512RateLimitMediaType OBJECT-TYPE
		SYNTAX      DisplayString
		MAX-ACCESS  read-only
		STATUS      current
		DESCRIPTION
			"Remote Module Port Media Type."
		::= { swhPort6MCT3512RateLimitEntry 2 }

	swhPort6MCT3512RateLimitIngressEn OBJECT-TYPE
		SYNTAX      INTEGER { disable(0), enable(1) }
		MAX-ACCESS  read-write
		STATUS      current
		DESCRIPTION
			"Remote Module Port Ingress Enable."
		::= { swhPort6MCT3512RateLimitEntry 3 }

	swhPort6MCT3512RateLimitIngressRate OBJECT-TYPE
		SYNTAX      INTEGER (32..1000000)
		MAX-ACCESS  read-write
		STATUS      current
		DESCRIPTION
			"Remote Module Port Ingress Rate (32-1000000) kbps."
		::= { swhPort6MCT3512RateLimitEntry 4 }

	swhPort6MCT3512RateLimitEgressEn OBJECT-TYPE
		SYNTAX      INTEGER { disable(0), enable(1) }
		MAX-ACCESS  read-write
		STATUS      current
		DESCRIPTION
			"Remote Module Port Egress Enable."
		::= { swhPort6MCT3512RateLimitEntry 5 }

	swhPort6MCT3512RateLimitEgressRate OBJECT-TYPE
		SYNTAX      INTEGER (32..1000000)
		MAX-ACCESS  read-write
		STATUS      current
		DESCRIPTION
			"Remote Module Port Egress Rate (32-1000000) kbps."
		::= { swhPort6MCT3512RateLimitEntry 6 }


-- EthernetOAM(24).OAMRemoteModule(5).RemoteModuleConfiguration(2).Port6RemoteConfiguration(6).Port6MCT3512Configuration(1).Port6MCT3512StormControl(5)

	swhPort6MCT3512StormControl
		OBJECT IDENTIFIER ::= { swhPort6MCT3512Configuration 5 }

	swhPort6MCT3512StormControlEnable OBJECT-TYPE
		SYNTAX      INTEGER { disable(0), enable(1) }
		MAX-ACCESS  read-write
		STATUS      current
		DESCRIPTION
			"Remote Module Storm Control."
		::= { swhPort6MCT3512StormControl 1 }

	swhPort6MCT3512StormControlRate OBJECT-TYPE
		SYNTAX      INTEGER (32..1000000)
		MAX-ACCESS  read-write
		STATUS      current
		DESCRIPTION
			"Remote Module Rate (32-1000000) kbps."
		::= { swhPort6MCT3512StormControl 2 }

	swhPort6MCT3512StormControlBandwidth OBJECT-TYPE
		SYNTAX      DisplayString
		MAX-ACCESS  read-only
		STATUS      current
		DESCRIPTION
			"Remote Module Bandwidth (bps)."
		::= { swhPort6MCT3512StormControl 3 }


-- EthernetOAM(24).OAMRemoteModule(5).RemoteModuleConfiguration(2).Port6RemoteConfiguration(6).Port6MCT3512Configuration(1).Port6MCT3512LANFollowsWAN(6)

	swhPort6MCT3512LANFollowsWAN
		OBJECT IDENTIFIER ::= { swhPort6MCT3512Configuration 6 }

	swhPort6MCT3512LANFollowsWANEnable OBJECT-TYPE
		SYNTAX      INTEGER { disable(0), enable(1) }
		MAX-ACCESS  read-write
		STATUS      current
		DESCRIPTION
			"Remote Module LAN Follows WAN."
		::= { swhPort6MCT3512LANFollowsWAN 1 }


-- EthernetOAM(24).OAMRemoteModule(5).RemoteModuleConfiguration(2).Port7RemoteConfiguration(7)

	swhPort7RemoteConfiguration
		OBJECT IDENTIFIER ::= { swhRemoteModuleConfiguration 7 }


-- EthernetOAM(24).OAMRemoteModule(5).RemoteModuleConfiguration(2).Port7RemoteConfiguration(7).Port7MCT3512Configuration(1)

	swhPort7MCT3512Configuration
		OBJECT IDENTIFIER ::= { swhPort7RemoteConfiguration 1 }


-- EthernetOAM(24).OAMRemoteModule(5).RemoteModuleConfiguration(2).Port7RemoteConfiguration(7).Port7MCT3512Configuration(1).Port7MCT3512Config(1)

	swhPort7MCT3512Config
		OBJECT IDENTIFIER ::= { swhPort7MCT3512Configuration 1 }

	swhPort7MCT3512ConfigDetectedModule OBJECT-TYPE
		SYNTAX      DisplayString
		MAX-ACCESS  read-only
		STATUS      current
		DESCRIPTION
			"Detected Module."
		::= { swhPort7MCT3512Config 1 }

	swhPort7MCT3512ConfigDIPSwitchSetting OBJECT-TYPE
		SYNTAX      DisplayString
		MAX-ACCESS  read-only
		STATUS      current
		DESCRIPTION
			"DIP Switch (PIN 8) Setting."
		::= { swhPort7MCT3512Config 2 }


-- EthernetOAM(24).OAMRemoteModule(5).RemoteModuleConfiguration(2).Port7RemoteConfiguration(7).Port7MCT3512Configuration(1).Port7MCT3512PortSetup(2)

	swhPort7MCT3512PortSetup
		OBJECT IDENTIFIER ::= { swhPort7MCT3512Configuration 2 }

	swhPort7MCT3512PortSetupTable OBJECT-TYPE
		SYNTAX      SEQUENCE OF SwhPort7MCT3512PortSetupEntry
		MAX-ACCESS  not-accessible
		STATUS      current
		DESCRIPTION
			"Table of remote module port setup."
		::= { swhPort7MCT3512PortSetup 5 }

	-- Table Entry
	swhPort7MCT3512PortSetupEntry OBJECT-TYPE
		SYNTAX      SwhPort7MCT3512PortSetupEntry
		MAX-ACCESS  not-accessible
		STATUS      current
		DESCRIPTION
			"An entry in the table, containing information about remote module port setup."
		INDEX    { swhPort7MCT3512PortSetupPort }
		::= { swhPort7MCT3512PortSetupTable 1 }

	SwhPort7MCT3512PortSetupEntry ::=
		SEQUENCE {
			swhPort7MCT3512PortSetupPort
				INTEGER,
			swhPort7MCT3512PortSetupMediaType
				DisplayString,
			swhPort7MCT3512PortSetupPortState
				INTEGER,
			swhPort7MCT3512PortSetupPortType
				INTEGER,
			swhPort7MCT3512PortSetupPortSpeed
				INTEGER,
			swhPort7MCT3512PortSetupPortDuplex
				INTEGER
		}

	swhPort7MCT3512PortSetupPort OBJECT-TYPE
		SYNTAX      INTEGER (0..2147483647)
		MAX-ACCESS  read-only
		STATUS      current
		DESCRIPTION
			"A unique value for each port."
		::= { swhPort7MCT3512PortSetupEntry 1 }

	swhPort7MCT3512PortSetupMediaType OBJECT-TYPE
		SYNTAX      DisplayString
		MAX-ACCESS  read-only
		STATUS      current
		DESCRIPTION
			"Media Type."
		::= { swhPort7MCT3512PortSetupEntry 2 }

	swhPort7MCT3512PortSetupPortState OBJECT-TYPE
		SYNTAX      INTEGER { disable(0), enable(1) }
		MAX-ACCESS  read-write
		STATUS      current
		DESCRIPTION
			"Port State."
		::= { swhPort7MCT3512PortSetupEntry 3 }

	swhPort7MCT3512PortSetupPortType OBJECT-TYPE
		SYNTAX      INTEGER { manual(0), auto-negotiation(1) }
		MAX-ACCESS  read-write
		STATUS      current
		DESCRIPTION
			"Port Type."
		::= { swhPort7MCT3512PortSetupEntry 4 }

	swhPort7MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort7MCT3512PortSetupEntry 5 }

	swhPort7MCT3512PortSetupPortDuplex OBJECT-TYPE
		SYNTAX      INTEGER { halfDuplex(0), fullDuplex(1) }
		MAX-ACCESS  read-write
		STATUS      current
		DESCRIPTION
			"Port Duplex."
		::= { swhPort7MCT3512PortSetupEntry 6 }


-- EthernetOAM(24).OAMRemoteModule(5).RemoteModuleConfiguration(2).Port7RemoteConfiguration(7).Port7MCT3512Configuration(1).Port7MCT3512VLANSetup(3)

	swhPort7MCT3512VLANSetup
		OBJECT IDENTIFIER ::= { swhPort7MCT3512Configuration 3 }

	swhPort7MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort7MCT3512VLANSetup 1 }

	swhPort7MCT3512VLANSetupISPMode OBJECT-TYPE
		SYNTAX      INTEGER { disable(0), enable(1) }
		MAX-ACCESS  read-write
		STATUS      current
		DESCRIPTION
			"Remote Module ISP Mode."
		::= { swhPort7MCT3512VLANSetup 2 }

	swhPort7MCT3512VLANSetupStagEtherType OBJECT-TYPE
		SYNTAX      DisplayString
		MAX-ACCESS  read-write
		STATUS      current
		DESCRIPTION
			"Remote Module Stag EtherType."
		::= { swhPort7MCT3512VLANSetup 3 }

	swhPort7MCT3512VLANSetupTable OBJECT-TYPE
		SYNTAX      SEQUENCE OF SwhPort7MCT3512VLANSetupEntry
		MAX-ACCESS  not-accessible
		STATUS      current
		DESCRIPTION
			"Table of remote module VLAN setup."
		::= { swhPort7MCT3512VLANSetup 5 }

	-- Table Entry
	swhPort7MCT3512VLANSetupEntry OBJECT-TYPE
		SYNTAX      SwhPort7MCT3512VLANSetupEntry
		MAX-ACCESS  not-accessible
		STATUS      current
		DESCRIPTION
			"An entry in the table, containing information about remote module VLAN setup."
		INDEX    { swhPort7MCT3512VLANSetupPort }
		::= { swhPort7MCT3512VLANSetupTable 1 }

	SwhPort7MCT3512VLANSetupEntry ::=
		SEQUENCE {
			swhPort7MCT3512VLANSetupPort
				INTEGER,
			swhPort7MCT3512VLANSetupMediaType
				DisplayString,
			swhPort7MCT3512VLANSetupMode
				INTEGER,
			swhPort7MCT3512VLANSetupPVID
				INTEGER,
			swhPort7MCT3512VLANSetupTrunkVLAN
				DisplayString,
			swhPort7MCT3512VLANSetupStagVID
				INTEGER,
			swhPort7MCT3512VLANSetupISPPort
				INTEGER
		}

	swhPort7MCT3512VLANSetupPort OBJECT-TYPE
		SYNTAX      INTEGER (0..2147483647)
		MAX-ACCESS  read-only
		STATUS      current
		DESCRIPTION
			"A unique value for each port."
		::= { swhPort7MCT3512VLANSetupEntry 1 }

	swhPort7MCT3512VLANSetupMediaType OBJECT-TYPE
		SYNTAX      DisplayString
		MAX-ACCESS  read-only
		STATUS      current
		DESCRIPTION
			"Remote Module Port Media Type."
		::= { swhPort7MCT3512VLANSetupEntry 2 }

	swhPort7MCT3512VLANSetupMode OBJECT-TYPE
		SYNTAX      INTEGER { access(0), trunk(1), trunknative(2) }
		MAX-ACCESS  read-write
		STATUS      current
		DESCRIPTION
			"Remote Module Port Mode."
		::= { swhPort7MCT3512VLANSetupEntry 3 }

	swhPort7MCT3512VLANSetupPVID OBJECT-TYPE
		SYNTAX      INTEGER (1..4093)
		MAX-ACCESS  read-write
		STATUS      current
		DESCRIPTION
			"Remote Module Port PVID."
		::= { swhPort7MCT3512VLANSetupEntry 4 }

	swhPort7MCT3512VLANSetupTrunkVLAN OBJECT-TYPE
		SYNTAX      DisplayString
		MAX-ACCESS  read-write
		STATUS      current
		DESCRIPTION
			"Remote Module Port Trunk VLAN."
		::= { swhPort7MCT3512VLANSetupEntry 5 }

	swhPort7MCT3512VLANSetupStagVID OBJECT-TYPE
		SYNTAX      INTEGER (1..4093)
		MAX-ACCESS  read-write
		STATUS      current
		DESCRIPTION
			"Remote Module Port Stag VID."
		::= { swhPort7MCT3512VLANSetupEntry 6 }

	swhPort7MCT3512VLANSetupISPPort OBJECT-TYPE
		SYNTAX      INTEGER { disable(0), enable(1) }
		MAX-ACCESS  read-write
		STATUS      current
		DESCRIPTION
			"Remote Module Port ISP Port."
		::= { swhPort7MCT3512VLANSetupEntry 7 }


-- EthernetOAM(24).OAMRemoteModule(5).RemoteModuleConfiguration(2).Port7RemoteConfiguration(7).Port7MCT3512Configuration(1).Port7MCT3512RateLimit(4)

	swhPort7MCT3512RateLimit
		OBJECT IDENTIFIER ::= { swhPort7MCT3512Configuration 4 }

	swhPort7MCT3512RateLimitTable OBJECT-TYPE
		SYNTAX      SEQUENCE OF SwhPort7MCT3512RateLimitEntry
		MAX-ACCESS  not-accessible
		STATUS      current
		DESCRIPTION
			"Table of remote module QoS rate limit."
		::= { swhPort7MCT3512RateLimit 5 }

	-- Table Entry
	swhPort7MCT3512RateLimitEntry OBJECT-TYPE
		SYNTAX      SwhPort7MCT3512RateLimitEntry
		MAX-ACCESS  not-accessible
		STATUS      current
		DESCRIPTION
			"An entry in the table, containing information about remote module QoS rate limit."
		INDEX    { swhPort7MCT3512RateLimitPort }
		::= { swhPort7MCT3512RateLimitTable 1 }

	SwhPort7MCT3512RateLimitEntry ::=
		SEQUENCE {
			swhPort7MCT3512RateLimitPort
				INTEGER,
			swhPort7MCT3512RateLimitMediaType
				DisplayString,
			swhPort7MCT3512RateLimitIngressEn
				INTEGER,
			swhPort7MCT3512RateLimitIngressRate
				INTEGER,
			swhPort7MCT3512RateLimitEgressEn
				INTEGER,
			swhPort7MCT3512RateLimitEgressRate
				INTEGER
		}

	swhPort7MCT3512RateLimitPort OBJECT-TYPE
		SYNTAX      INTEGER (0..2147483647)
		MAX-ACCESS  read-only
		STATUS      current
		DESCRIPTION
			"A unique value for each port."
		::= { swhPort7MCT3512RateLimitEntry 1 }

	swhPort7MCT3512RateLimitMediaType OBJECT-TYPE
		SYNTAX      DisplayString
		MAX-ACCESS  read-only
		STATUS      current
		DESCRIPTION
			"Remote Module Port Media Type."
		::= { swhPort7MCT3512RateLimitEntry 2 }

	swhPort7MCT3512RateLimitIngressEn OBJECT-TYPE
		SYNTAX      INTEGER { disable(0), enable(1) }
		MAX-ACCESS  read-write
		STATUS      current
		DESCRIPTION
			"Remote Module Port Ingress Enable."
		::= { swhPort7MCT3512RateLimitEntry 3 }

	swhPort7MCT3512RateLimitIngressRate OBJECT-TYPE
		SYNTAX      INTEGER (32..1000000)
		MAX-ACCESS  read-write
		STATUS      current
		DESCRIPTION
			"Remote Module Port Ingress Rate (32-1000000) kbps."
		::= { swhPort7MCT3512RateLimitEntry 4 }

	swhPort7MCT3512RateLimitEgressEn OBJECT-TYPE
		SYNTAX      INTEGER { disable(0), enable(1) }
		MAX-ACCESS  read-write
		STATUS      current
		DESCRIPTION
			"Remote Module Port Egress Enable."
		::= { swhPort7MCT3512RateLimitEntry 5 }

	swhPort7MCT3512RateLimitEgressRate OBJECT-TYPE
		SYNTAX      INTEGER (32..1000000)
		MAX-ACCESS  read-write
		STATUS      current
		DESCRIPTION
			"Remote Module Port Egress Rate (32-1000000) kbps."
		::= { swhPort7MCT3512RateLimitEntry 6 }


-- EthernetOAM(24).OAMRemoteModule(5).RemoteModuleConfiguration(2).Port7RemoteConfiguration(7).Port7MCT3512Configuration(1).Port7MCT3512StormControl(5)

	swhPort7MCT3512StormControl
		OBJECT IDENTIFIER ::= { swhPort7MCT3512Configuration 5 }

	swhPort7MCT3512StormControlEnable OBJECT-TYPE
		SYNTAX      INTEGER { disable(0), enable(1) }
		MAX-ACCESS  read-write
		STATUS      current
		DESCRIPTION
			"Remote Module Storm Control."
		::= { swhPort7MCT3512StormControl 1 }

	swhPort7MCT3512StormControlRate OBJECT-TYPE
		SYNTAX      INTEGER (32..1000000)
		MAX-ACCESS  read-write
		STATUS      current
		DESCRIPTION
			"Remote Module Rate (32-1000000) kbps."
		::= { swhPort7MCT3512StormControl 2 }

	swhPort7MCT3512StormControlBandwidth OBJECT-TYPE
		SYNTAX      DisplayString
		MAX-ACCESS  read-only
		STATUS      current
		DESCRIPTION
			"Remote Module Bandwidth (bps)."
		::= { swhPort7MCT3512StormControl 3 }


-- EthernetOAM(24).OAMRemoteModule(5).RemoteModuleConfiguration(2).Port7RemoteConfiguration(7).Port7MCT3512Configuration(1).Port7MCT3512LANFollowsWAN(6)

	swhPort7MCT3512LANFollowsWAN
		OBJECT IDENTIFIER ::= { swhPort7MCT3512Configuration 6 }

	swhPort7MCT3512LANFollowsWANEnable OBJECT-TYPE
		SYNTAX      INTEGER { disable(0), enable(1) }
		MAX-ACCESS  read-write
		STATUS      current
		DESCRIPTION
			"Remote Module LAN Follows WAN."
		::= { swhPort7MCT3512LANFollowsWAN 1 }


-- EthernetOAM(24).OAMRemoteModule(5).RemoteModuleConfiguration(2).Port8RemoteConfiguration(8)

	swhPort8RemoteConfiguration
		OBJECT IDENTIFIER ::= { swhRemoteModuleConfiguration 8 }


-- EthernetOAM(24).OAMRemoteModule(5).RemoteModuleConfiguration(2).Port8RemoteConfiguration(8).Port8MCT3512Configuration(1)

	swhPort8MCT3512Configuration
		OBJECT IDENTIFIER ::= { swhPort8RemoteConfiguration 1 }


-- EthernetOAM(24).OAMRemoteModule(5).RemoteModuleConfiguration(2).Port8RemoteConfiguration(8).Port8MCT3512Configuration(1).Port8MCT3512Config(1)

	swhPort8MCT3512Config
		OBJECT IDENTIFIER ::= { swhPort8MCT3512Configuration 1 }

	swhPort8MCT3512ConfigDetectedModule OBJECT-TYPE
		SYNTAX      DisplayString
		MAX-ACCESS  read-only
		STATUS      current
		DESCRIPTION
			"Detected Module."
		::= { swhPort8MCT3512Config 1 }

	swhPort8MCT3512ConfigDIPSwitchSetting OBJECT-TYPE
		SYNTAX      DisplayString
		MAX-ACCESS  read-only
		STATUS      current
		DESCRIPTION
			"DIP Switch (PIN 8) Setting."
		::= { swhPort8MCT3512Config 2 }


-- EthernetOAM(24).OAMRemoteModule(5).RemoteModuleConfiguration(2).Port8RemoteConfiguration(8).Port8MCT3512Configuration(1).Port8MCT3512PortSetup(2)

	swhPort8MCT3512PortSetup
		OBJECT IDENTIFIER ::= { swhPort8MCT3512Configuration 2 }

	swhPort8MCT3512PortSetupTable OBJECT-TYPE
		SYNTAX      SEQUENCE OF SwhPort8MCT3512PortSetupEntry
		MAX-ACCESS  not-accessible
		STATUS      current
		DESCRIPTION
			"Table of remote module port setup."
		::= { swhPort8MCT3512PortSetup 5 }

	-- Table Entry
	swhPort8MCT3512PortSetupEntry OBJECT-TYPE
		SYNTAX      SwhPort8MCT3512PortSetupEntry
		MAX-ACCESS  not-accessible
		STATUS      current
		DESCRIPTION
			"An entry in the table, containing information about remote module port setup."
		INDEX    { swhPort8MCT3512PortSetupPort }
		::= { swhPort8MCT3512PortSetupTable 1 }

	SwhPort8MCT3512PortSetupEntry ::=
		SEQUENCE {
			swhPort8MCT3512PortSetupPort
				INTEGER,
			swhPort8MCT3512PortSetupMediaType
				DisplayString,
			swhPort8MCT3512PortSetupPortState
				INTEGER,
			swhPort8MCT3512PortSetupPortType
				INTEGER,
			swhPort8MCT3512PortSetupPortSpeed
				INTEGER,
			swhPort8MCT3512PortSetupPortDuplex
				INTEGER
		}

	swhPort8MCT3512PortSetupPort OBJECT-TYPE
		SYNTAX      INTEGER (0..2147483647)
		MAX-ACCESS  read-only
		STATUS      current
		DESCRIPTION
			"A unique value for each port."
		::= { swhPort8MCT3512PortSetupEntry 1 }

	swhPort8MCT3512PortSetupMediaType OBJECT-TYPE
		SYNTAX      DisplayString
		MAX-ACCESS  read-only
		STATUS      current
		DESCRIPTION
			"Media Type."
		::= { swhPort8MCT3512PortSetupEntry 2 }

	swhPort8MCT3512PortSetupPortState OBJECT-TYPE
		SYNTAX      INTEGER { disable(0), enable(1) }
		MAX-ACCESS  read-write
		STATUS      current
		DESCRIPTION
			"Port State."
		::= { swhPort8MCT3512PortSetupEntry 3 }

	swhPort8MCT3512PortSetupPortType OBJECT-TYPE
		SYNTAX      INTEGER { manual(0), auto-negotiation(1) }
		MAX-ACCESS  read-write
		STATUS      current
		DESCRIPTION
			"Port Type."
		::= { swhPort8MCT3512PortSetupEntry 4 }

	swhPort8MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort8MCT3512PortSetupEntry 5 }

	swhPort8MCT3512PortSetupPortDuplex OBJECT-TYPE
		SYNTAX      INTEGER { halfDuplex(0), fullDuplex(1) }
		MAX-ACCESS  read-write
		STATUS      current
		DESCRIPTION
			"Port Duplex."
		::= { swhPort8MCT3512PortSetupEntry 6 }


-- EthernetOAM(24).OAMRemoteModule(5).RemoteModuleConfiguration(2).Port8RemoteConfiguration(8).Port8MCT3512Configuration(1).Port8MCT3512VLANSetup(3)

	swhPort8MCT3512VLANSetup
		OBJECT IDENTIFIER ::= { swhPort8MCT3512Configuration 3 }

	swhPort8MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort8MCT3512VLANSetup 1 }

	swhPort8MCT3512VLANSetupISPMode OBJECT-TYPE
		SYNTAX      INTEGER { disable(0), enable(1) }
		MAX-ACCESS  read-write
		STATUS      current
		DESCRIPTION
			"Remote Module ISP Mode."
		::= { swhPort8MCT3512VLANSetup 2 }

	swhPort8MCT3512VLANSetupStagEtherType OBJECT-TYPE
		SYNTAX      DisplayString
		MAX-ACCESS  read-write
		STATUS      current
		DESCRIPTION
			"Remote Module Stag EtherType."
		::= { swhPort8MCT3512VLANSetup 3 }

	swhPort8MCT3512VLANSetupTable OBJECT-TYPE
		SYNTAX      SEQUENCE OF SwhPort8MCT3512VLANSetupEntry
		MAX-ACCESS  not-accessible
		STATUS      current
		DESCRIPTION
			"Table of remote module VLAN setup."
		::= { swhPort8MCT3512VLANSetup 5 }

	-- Table Entry
	swhPort8MCT3512VLANSetupEntry OBJECT-TYPE
		SYNTAX      SwhPort8MCT3512VLANSetupEntry
		MAX-ACCESS  not-accessible
		STATUS      current
		DESCRIPTION
			"An entry in the table, containing information about remote module VLAN setup."
		INDEX    { swhPort8MCT3512VLANSetupPort }
		::= { swhPort8MCT3512VLANSetupTable 1 }

	SwhPort8MCT3512VLANSetupEntry ::=
		SEQUENCE {
			swhPort8MCT3512VLANSetupPort
				INTEGER,
			swhPort8MCT3512VLANSetupMediaType
				DisplayString,
			swhPort8MCT3512VLANSetupMode
				INTEGER,
			swhPort8MCT3512VLANSetupPVID
				INTEGER,
			swhPort8MCT3512VLANSetupTrunkVLAN
				DisplayString,
			swhPort8MCT3512VLANSetupStagVID
				INTEGER,
			swhPort8MCT3512VLANSetupISPPort
				INTEGER
		}

	swhPort8MCT3512VLANSetupPort OBJECT-TYPE
		SYNTAX      INTEGER (0..2147483647)
		MAX-ACCESS  read-only
		STATUS      current
		DESCRIPTION
			"A unique value for each port."
		::= { swhPort8MCT3512VLANSetupEntry 1 }

	swhPort8MCT3512VLANSetupMediaType OBJECT-TYPE
		SYNTAX      DisplayString
		MAX-ACCESS  read-only
		STATUS      current
		DESCRIPTION
			"Remote Module Port Media Type."
		::= { swhPort8MCT3512VLANSetupEntry 2 }

	swhPort8MCT3512VLANSetupMode OBJECT-TYPE
		SYNTAX      INTEGER { access(0), trunk(1), trunknative(2) }
		MAX-ACCESS  read-write
		STATUS      current
		DESCRIPTION
			"Remote Module Port Mode."
		::= { swhPort8MCT3512VLANSetupEntry 3 }

	swhPort8MCT3512VLANSetupPVID OBJECT-TYPE
		SYNTAX      INTEGER (1..4093)
		MAX-ACCESS  read-write
		STATUS      current
		DESCRIPTION
			"Remote Module Port PVID."
		::= { swhPort8MCT3512VLANSetupEntry 4 }

	swhPort8MCT3512VLANSetupTrunkVLAN OBJECT-TYPE
		SYNTAX      DisplayString
		MAX-ACCESS  read-write
		STATUS      current
		DESCRIPTION
			"Remote Module Port Trunk VLAN."
		::= { swhPort8MCT3512VLANSetupEntry 5 }

	swhPort8MCT3512VLANSetupStagVID OBJECT-TYPE
		SYNTAX      INTEGER (1..4093)
		MAX-ACCESS  read-write
		STATUS      current
		DESCRIPTION
			"Remote Module Port Stag VID."
		::= { swhPort8MCT3512VLANSetupEntry 6 }

	swhPort8MCT3512VLANSetupISPPort OBJECT-TYPE
		SYNTAX      INTEGER { disable(0), enable(1) }
		MAX-ACCESS  read-write
		STATUS      current
		DESCRIPTION
			"Remote Module Port ISP Port."
		::= { swhPort8MCT3512VLANSetupEntry 7 }


-- EthernetOAM(24).OAMRemoteModule(5).RemoteModuleConfiguration(2).Port8RemoteConfiguration(8).Port8MCT3512Configuration(1).Port8MCT3512RateLimit(4)

	swhPort8MCT3512RateLimit
		OBJECT IDENTIFIER ::= { swhPort8MCT3512Configuration 4 }

	swhPort8MCT3512RateLimitTable OBJECT-TYPE
		SYNTAX      SEQUENCE OF SwhPort8MCT3512RateLimitEntry
		MAX-ACCESS  not-accessible
		STATUS      current
		DESCRIPTION
			"Table of remote module QoS rate limit."
		::= { swhPort8MCT3512RateLimit 5 }

	-- Table Entry
	swhPort8MCT3512RateLimitEntry OBJECT-TYPE
		SYNTAX      SwhPort8MCT3512RateLimitEntry
		MAX-ACCESS  not-accessible
		STATUS      current
		DESCRIPTION
			"An entry in the table, containing information about remote module QoS rate limit."
		INDEX    { swhPort8MCT3512RateLimitPort }
		::= { swhPort8MCT3512RateLimitTable 1 }

	SwhPort8MCT3512RateLimitEntry ::=
		SEQUENCE {
			swhPort8MCT3512RateLimitPort
				INTEGER,
			swhPort8MCT3512RateLimitMediaType
				DisplayString,
			swhPort8MCT3512RateLimitIngressEn
				INTEGER,
			swhPort8MCT3512RateLimitIngressRate
				INTEGER,
			swhPort8MCT3512RateLimitEgressEn
				INTEGER,
			swhPort8MCT3512RateLimitEgressRate
				INTEGER
		}

	swhPort8MCT3512RateLimitPort OBJECT-TYPE
		SYNTAX      INTEGER (0..2147483647)
		MAX-ACCESS  read-only
		STATUS      current
		DESCRIPTION
			"A unique value for each port."
		::= { swhPort8MCT3512RateLimitEntry 1 }

	swhPort8MCT3512RateLimitMediaType OBJECT-TYPE
		SYNTAX      DisplayString
		MAX-ACCESS  read-only
		STATUS      current
		DESCRIPTION
			"Remote Module Port Media Type."
		::= { swhPort8MCT3512RateLimitEntry 2 }

	swhPort8MCT3512RateLimitIngressEn OBJECT-TYPE
		SYNTAX      INTEGER { disable(0), enable(1) }
		MAX-ACCESS  read-write
		STATUS      current
		DESCRIPTION
			"Remote Module Port Ingress Enable."
		::= { swhPort8MCT3512RateLimitEntry 3 }

	swhPort8MCT3512RateLimitIngressRate OBJECT-TYPE
		SYNTAX      INTEGER (32..1000000)
		MAX-ACCESS  read-write
		STATUS      current
		DESCRIPTION
			"Remote Module Port Ingress Rate (32-1000000) kbps."
		::= { swhPort8MCT3512RateLimitEntry 4 }

	swhPort8MCT3512RateLimitEgressEn OBJECT-TYPE
		SYNTAX      INTEGER { disable(0), enable(1) }
		MAX-ACCESS  read-write
		STATUS      current
		DESCRIPTION
			"Remote Module Port Egress Enable."
		::= { swhPort8MCT3512RateLimitEntry 5 }

	swhPort8MCT3512RateLimitEgressRate OBJECT-TYPE
		SYNTAX      INTEGER (32..1000000)
		MAX-ACCESS  read-write
		STATUS      current
		DESCRIPTION
			"Remote Module Port Egress Rate (32-1000000) kbps."
		::= { swhPort8MCT3512RateLimitEntry 6 }


-- EthernetOAM(24).OAMRemoteModule(5).RemoteModuleConfiguration(2).Port8RemoteConfiguration(8).Port8MCT3512Configuration(1).Port8MCT3512StormControl(5)

	swhPort8MCT3512StormControl
		OBJECT IDENTIFIER ::= { swhPort8MCT3512Configuration 5 }

	swhPort8MCT3512StormControlEnable OBJECT-TYPE
		SYNTAX      INTEGER { disable(0), enable(1) }
		MAX-ACCESS  read-write
		STATUS      current
		DESCRIPTION
			"Remote Module Storm Control."
		::= { swhPort8MCT3512StormControl 1 }

	swhPort8MCT3512StormControlRate OBJECT-TYPE
		SYNTAX      INTEGER (32..1000000)
		MAX-ACCESS  read-write
		STATUS      current
		DESCRIPTION
			"Remote Module Rate (32-1000000) kbps."
		::= { swhPort8MCT3512StormControl 2 }

	swhPort8MCT3512StormControlBandwidth OBJECT-TYPE
		SYNTAX      DisplayString
		MAX-ACCESS  read-only
		STATUS      current
		DESCRIPTION
			"Remote Module Bandwidth (bps)."
		::= { swhPort8MCT3512StormControl 3 }


-- EthernetOAM(24).OAMRemoteModule(5).RemoteModuleConfiguration(2).Port8RemoteConfiguration(8).Port8MCT3512Configuration(1).Port8MCT3512LANFollowsWAN(6)

	swhPort8MCT3512LANFollowsWAN
		OBJECT IDENTIFIER ::= { swhPort8MCT3512Configuration 6 }

	swhPort8MCT3512LANFollowsWANEnable OBJECT-TYPE
		SYNTAX      INTEGER { disable(0), enable(1) }
		MAX-ACCESS  read-write
		STATUS      current
		DESCRIPTION
			"Remote Module LAN Follows WAN."
		::= { swhPort8MCT3512LANFollowsWAN 1 }


-- EthernetOAM(24).OAMRemoteModule(5).RemoteModuleConfiguration(2).Port9RemoteConfiguration(9)

	swhPort9RemoteConfiguration
		OBJECT IDENTIFIER ::= { swhRemoteModuleConfiguration 9 }


-- EthernetOAM(24).OAMRemoteModule(5).RemoteModuleConfiguration(2).Port9RemoteConfiguration(9).Port9MCT3512Configuration(1)

	swhPort9MCT3512Configuration
		OBJECT IDENTIFIER ::= { swhPort9RemoteConfiguration 1 }


-- EthernetOAM(24).OAMRemoteModule(5).RemoteModuleConfiguration(2).Port9RemoteConfiguration(9).Port9MCT3512Configuration(1).Port9MCT3512Config(1)

	swhPort9MCT3512Config
		OBJECT IDENTIFIER ::= { swhPort9MCT3512Configuration 1 }

	swhPort9MCT3512ConfigDetectedModule OBJECT-TYPE
		SYNTAX      DisplayString
		MAX-ACCESS  read-only
		STATUS      current
		DESCRIPTION
			"Detected Module."
		::= { swhPort9MCT3512Config 1 }

	swhPort9MCT3512ConfigDIPSwitchSetting OBJECT-TYPE
		SYNTAX      DisplayString
		MAX-ACCESS  read-only
		STATUS      current
		DESCRIPTION
			"DIP Switch (PIN 8) Setting."
		::= { swhPort9MCT3512Config 2 }


-- EthernetOAM(24).OAMRemoteModule(5).RemoteModuleConfiguration(2).Port9RemoteConfiguration(9).Port9MCT3512Configuration(1).Port9MCT3512PortSetup(2)

	swhPort9MCT3512PortSetup
		OBJECT IDENTIFIER ::= { swhPort9MCT3512Configuration 2 }

	swhPort9MCT3512PortSetupTable OBJECT-TYPE
		SYNTAX      SEQUENCE OF SwhPort9MCT3512PortSetupEntry
		MAX-ACCESS  not-accessible
		STATUS      current
		DESCRIPTION
			"Table of remote module port setup."
		::= { swhPort9MCT3512PortSetup 5 }

	-- Table Entry
	swhPort9MCT3512PortSetupEntry OBJECT-TYPE
		SYNTAX      SwhPort9MCT3512PortSetupEntry
		MAX-ACCESS  not-accessible
		STATUS      current
		DESCRIPTION
			"An entry in the table, containing information about remote module port setup."
		INDEX    { swhPort9MCT3512PortSetupPort }
		::= { swhPort9MCT3512PortSetupTable 1 }

	SwhPort9MCT3512PortSetupEntry ::=
		SEQUENCE {
			swhPort9MCT3512PortSetupPort
				INTEGER,
			swhPort9MCT3512PortSetupMediaType
				DisplayString,
			swhPort9MCT3512PortSetupPortState
				INTEGER,
			swhPort9MCT3512PortSetupPortType
				INTEGER,
			swhPort9MCT3512PortSetupPortSpeed
				INTEGER,
			swhPort9MCT3512PortSetupPortDuplex
				INTEGER
		}

	swhPort9MCT3512PortSetupPort OBJECT-TYPE
		SYNTAX      INTEGER (0..2147483647)
		MAX-ACCESS  read-only
		STATUS      current
		DESCRIPTION
			"A unique value for each port."
		::= { swhPort9MCT3512PortSetupEntry 1 }

	swhPort9MCT3512PortSetupMediaType OBJECT-TYPE
		SYNTAX      DisplayString
		MAX-ACCESS  read-only
		STATUS      current
		DESCRIPTION
			"Media Type."
		::= { swhPort9MCT3512PortSetupEntry 2 }

	swhPort9MCT3512PortSetupPortState OBJECT-TYPE
		SYNTAX      INTEGER { disable(0), enable(1) }
		MAX-ACCESS  read-write
		STATUS      current
		DESCRIPTION
			"Port State."
		::= { swhPort9MCT3512PortSetupEntry 3 }

	swhPort9MCT3512PortSetupPortType OBJECT-TYPE
		SYNTAX      INTEGER { manual(0), auto-negotiation(1) }
		MAX-ACCESS  read-write
		STATUS      current
		DESCRIPTION
			"Port Type."
		::= { swhPort9MCT3512PortSetupEntry 4 }

	swhPort9MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort9MCT3512PortSetupEntry 5 }

	swhPort9MCT3512PortSetupPortDuplex OBJECT-TYPE
		SYNTAX      INTEGER { halfDuplex(0), fullDuplex(1) }
		MAX-ACCESS  read-write
		STATUS      current
		DESCRIPTION
			"Port Duplex."
		::= { swhPort9MCT3512PortSetupEntry 6 }


-- EthernetOAM(24).OAMRemoteModule(5).RemoteModuleConfiguration(2).Port9RemoteConfiguration(9).Port9MCT3512Configuration(1).Port9MCT3512VLANSetup(3)

	swhPort9MCT3512VLANSetup
		OBJECT IDENTIFIER ::= { swhPort9MCT3512Configuration 3 }

	swhPort9MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort9MCT3512VLANSetup 1 }

	swhPort9MCT3512VLANSetupISPMode OBJECT-TYPE
		SYNTAX      INTEGER { disable(0), enable(1) }
		MAX-ACCESS  read-write
		STATUS      current
		DESCRIPTION
			"Remote Module ISP Mode."
		::= { swhPort9MCT3512VLANSetup 2 }

	swhPort9MCT3512VLANSetupStagEtherType OBJECT-TYPE
		SYNTAX      DisplayString
		MAX-ACCESS  read-write
		STATUS      current
		DESCRIPTION
			"Remote Module Stag EtherType."
		::= { swhPort9MCT3512VLANSetup 3 }

	swhPort9MCT3512VLANSetupTable OBJECT-TYPE
		SYNTAX      SEQUENCE OF SwhPort9MCT3512VLANSetupEntry
		MAX-ACCESS  not-accessible
		STATUS      current
		DESCRIPTION
			"Table of remote module VLAN setup."
		::= { swhPort9MCT3512VLANSetup 5 }

	-- Table Entry
	swhPort9MCT3512VLANSetupEntry OBJECT-TYPE
		SYNTAX      SwhPort9MCT3512VLANSetupEntry
		MAX-ACCESS  not-accessible
		STATUS      current
		DESCRIPTION
			"An entry in the table, containing information about remote module VLAN setup."
		INDEX    { swhPort9MCT3512VLANSetupPort }
		::= { swhPort9MCT3512VLANSetupTable 1 }

	SwhPort9MCT3512VLANSetupEntry ::=
		SEQUENCE {
			swhPort9MCT3512VLANSetupPort
				INTEGER,
			swhPort9MCT3512VLANSetupMediaType
				DisplayString,
			swhPort9MCT3512VLANSetupMode
				INTEGER,
			swhPort9MCT3512VLANSetupPVID
				INTEGER,
			swhPort9MCT3512VLANSetupTrunkVLAN
				DisplayString,
			swhPort9MCT3512VLANSetupStagVID
				INTEGER,
			swhPort9MCT3512VLANSetupISPPort
				INTEGER
		}

	swhPort9MCT3512VLANSetupPort OBJECT-TYPE
		SYNTAX      INTEGER (0..2147483647)
		MAX-ACCESS  read-only
		STATUS      current
		DESCRIPTION
			"A unique value for each port."
		::= { swhPort9MCT3512VLANSetupEntry 1 }

	swhPort9MCT3512VLANSetupMediaType OBJECT-TYPE
		SYNTAX      DisplayString
		MAX-ACCESS  read-only
		STATUS      current
		DESCRIPTION
			"Remote Module Port Media Type."
		::= { swhPort9MCT3512VLANSetupEntry 2 }

	swhPort9MCT3512VLANSetupMode OBJECT-TYPE
		SYNTAX      INTEGER { access(0), trunk(1), trunknative(2) }
		MAX-ACCESS  read-write
		STATUS      current
		DESCRIPTION
			"Remote Module Port Mode."
		::= { swhPort9MCT3512VLANSetupEntry 3 }

	swhPort9MCT3512VLANSetupPVID OBJECT-TYPE
		SYNTAX      INTEGER (1..4093)
		MAX-ACCESS  read-write
		STATUS      current
		DESCRIPTION
			"Remote Module Port PVID."
		::= { swhPort9MCT3512VLANSetupEntry 4 }

	swhPort9MCT3512VLANSetupTrunkVLAN OBJECT-TYPE
		SYNTAX      DisplayString
		MAX-ACCESS  read-write
		STATUS      current
		DESCRIPTION
			"Remote Module Port Trunk VLAN."
		::= { swhPort9MCT3512VLANSetupEntry 5 }

	swhPort9MCT3512VLANSetupStagVID OBJECT-TYPE
		SYNTAX      INTEGER (1..4093)
		MAX-ACCESS  read-write
		STATUS      current
		DESCRIPTION
			"Remote Module Port Stag VID."
		::= { swhPort9MCT3512VLANSetupEntry 6 }

	swhPort9MCT3512VLANSetupISPPort OBJECT-TYPE
		SYNTAX      INTEGER { disable(0), enable(1) }
		MAX-ACCESS  read-write
		STATUS      current
		DESCRIPTION
			"Remote Module Port ISP Port."
		::= { swhPort9MCT3512VLANSetupEntry 7 }


-- EthernetOAM(24).OAMRemoteModule(5).RemoteModuleConfiguration(2).Port9RemoteConfiguration(9).Port9MCT3512Configuration(1).Port9MCT3512RateLimit(4)

	swhPort9MCT3512RateLimit
		OBJECT IDENTIFIER ::= { swhPort9MCT3512Configuration 4 }

	swhPort9MCT3512RateLimitTable OBJECT-TYPE
		SYNTAX      SEQUENCE OF SwhPort9MCT3512RateLimitEntry
		MAX-ACCESS  not-accessible
		STATUS      current
		DESCRIPTION
			"Table of remote module QoS rate limit."
		::= { swhPort9MCT3512RateLimit 5 }

	-- Table Entry
	swhPort9MCT3512RateLimitEntry OBJECT-TYPE
		SYNTAX      SwhPort9MCT3512RateLimitEntry
		MAX-ACCESS  not-accessible
		STATUS      current
		DESCRIPTION
			"An entry in the table, containing information about remote module QoS rate limit."
		INDEX    { swhPort9MCT3512RateLimitPort }
		::= { swhPort9MCT3512RateLimitTable 1 }

	SwhPort9MCT3512RateLimitEntry ::=
		SEQUENCE {
			swhPort9MCT3512RateLimitPort
				INTEGER,
			swhPort9MCT3512RateLimitMediaType
				DisplayString,
			swhPort9MCT3512RateLimitIngressEn
				INTEGER,
			swhPort9MCT3512RateLimitIngressRate
				INTEGER,
			swhPort9MCT3512RateLimitEgressEn
				INTEGER,
			swhPort9MCT3512RateLimitEgressRate
				INTEGER
		}

	swhPort9MCT3512RateLimitPort OBJECT-TYPE
		SYNTAX      INTEGER (0..2147483647)
		MAX-ACCESS  read-only
		STATUS      current
		DESCRIPTION
			"A unique value for each port."
		::= { swhPort9MCT3512RateLimitEntry 1 }

	swhPort9MCT3512RateLimitMediaType OBJECT-TYPE
		SYNTAX      DisplayString
		MAX-ACCESS  read-only
		STATUS      current
		DESCRIPTION
			"Remote Module Port Media Type."
		::= { swhPort9MCT3512RateLimitEntry 2 }

	swhPort9MCT3512RateLimitIngressEn OBJECT-TYPE
		SYNTAX      INTEGER { disable(0), enable(1) }
		MAX-ACCESS  read-write
		STATUS      current
		DESCRIPTION
			"Remote Module Port Ingress Enable."
		::= { swhPort9MCT3512RateLimitEntry 3 }

	swhPort9MCT3512RateLimitIngressRate OBJECT-TYPE
		SYNTAX      INTEGER (32..1000000)
		MAX-ACCESS  read-write
		STATUS      current
		DESCRIPTION
			"Remote Module Port Ingress Rate (32-1000000) kbps."
		::= { swhPort9MCT3512RateLimitEntry 4 }

	swhPort9MCT3512RateLimitEgressEn OBJECT-TYPE
		SYNTAX      INTEGER { disable(0), enable(1) }
		MAX-ACCESS  read-write
		STATUS      current
		DESCRIPTION
			"Remote Module Port Egress Enable."
		::= { swhPort9MCT3512RateLimitEntry 5 }

	swhPort9MCT3512RateLimitEgressRate OBJECT-TYPE
		SYNTAX      INTEGER (32..1000000)
		MAX-ACCESS  read-write
		STATUS      current
		DESCRIPTION
			"Remote Module Port Egress Rate (32-1000000) kbps."
		::= { swhPort9MCT3512RateLimitEntry 6 }


-- EthernetOAM(24).OAMRemoteModule(5).RemoteModuleConfiguration(2).Port9RemoteConfiguration(9).Port9MCT3512Configuration(1).Port9MCT3512StormControl(5)

	swhPort9MCT3512StormControl
		OBJECT IDENTIFIER ::= { swhPort9MCT3512Configuration 5 }

	swhPort9MCT3512StormControlEnable OBJECT-TYPE
		SYNTAX      INTEGER { disable(0), enable(1) }
		MAX-ACCESS  read-write
		STATUS      current
		DESCRIPTION
			"Remote Module Storm Control."
		::= { swhPort9MCT3512StormControl 1 }

	swhPort9MCT3512StormControlRate OBJECT-TYPE
		SYNTAX      INTEGER (32..1000000)
		MAX-ACCESS  read-write
		STATUS      current
		DESCRIPTION
			"Remote Module Rate (32-1000000) kbps."
		::= { swhPort9MCT3512StormControl 2 }

	swhPort9MCT3512StormControlBandwidth OBJECT-TYPE
		SYNTAX      DisplayString
		MAX-ACCESS  read-only
		STATUS      current
		DESCRIPTION
			"Remote Module Bandwidth (bps)."
		::= { swhPort9MCT3512StormControl 3 }


-- EthernetOAM(24).OAMRemoteModule(5).RemoteModuleConfiguration(2).Port9RemoteConfiguration(9).Port9MCT3512Configuration(1).Port9MCT3512LANFollowsWAN(6)

	swhPort9MCT3512LANFollowsWAN
		OBJECT IDENTIFIER ::= { swhPort9MCT3512Configuration 6 }

	swhPort9MCT3512LANFollowsWANEnable OBJECT-TYPE
		SYNTAX      INTEGER { disable(0), enable(1) }
		MAX-ACCESS  read-write
		STATUS      current
		DESCRIPTION
			"Remote Module LAN Follows WAN."
		::= { swhPort9MCT3512LANFollowsWAN 1 }


-- EthernetOAM(24).OAMRemoteModule(5).RemoteModuleConfiguration(2).Port10RemoteConfiguration(10)

	swhPort10RemoteConfiguration
		OBJECT IDENTIFIER ::= { swhRemoteModuleConfiguration 10 }


-- EthernetOAM(24).OAMRemoteModule(5).RemoteModuleConfiguration(2).Port10RemoteConfiguration(10).Port10MCT3512Configuration(1)

	swhPort10MCT3512Configuration
		OBJECT IDENTIFIER ::= { swhPort10RemoteConfiguration 1 }


-- EthernetOAM(24).OAMRemoteModule(5).RemoteModuleConfiguration(2).Port10RemoteConfiguration(10).Port10MCT3512Configuration(1).Port10MCT3512Config(1)

	swhPort10MCT3512Config
		OBJECT IDENTIFIER ::= { swhPort10MCT3512Configuration 1 }

	swhPort10MCT3512ConfigDetectedModule OBJECT-TYPE
		SYNTAX      DisplayString
		MAX-ACCESS  read-only
		STATUS      current
		DESCRIPTION
			"Detected Module."
		::= { swhPort10MCT3512Config 1 }

	swhPort10MCT3512ConfigDIPSwitchSetting OBJECT-TYPE
		SYNTAX      DisplayString
		MAX-ACCESS  read-only
		STATUS      current
		DESCRIPTION
			"DIP Switch (PIN 8) Setting."
		::= { swhPort10MCT3512Config 2 }


-- EthernetOAM(24).OAMRemoteModule(5).RemoteModuleConfiguration(2).Port10RemoteConfiguration(10).Port10MCT3512Configuration(1).Port10MCT3512PortSetup(2)

	swhPort10MCT3512PortSetup
		OBJECT IDENTIFIER ::= { swhPort10MCT3512Configuration 2 }

	swhPort10MCT3512PortSetupTable OBJECT-TYPE
		SYNTAX      SEQUENCE OF SwhPort10MCT3512PortSetupEntry
		MAX-ACCESS  not-accessible
		STATUS      current
		DESCRIPTION
			"Table of remote module port setup."
		::= { swhPort10MCT3512PortSetup 5 }

	-- Table Entry
	swhPort10MCT3512PortSetupEntry OBJECT-TYPE
		SYNTAX      SwhPort10MCT3512PortSetupEntry
		MAX-ACCESS  not-accessible
		STATUS      current
		DESCRIPTION
			"An entry in the table, containing information about remote module port setup."
		INDEX    { swhPort10MCT3512PortSetupPort }
		::= { swhPort10MCT3512PortSetupTable 1 }

	SwhPort10MCT3512PortSetupEntry ::=
		SEQUENCE {
			swhPort10MCT3512PortSetupPort
				INTEGER,
			swhPort10MCT3512PortSetupMediaType
				DisplayString,
			swhPort10MCT3512PortSetupPortState
				INTEGER,
			swhPort10MCT3512PortSetupPortType
				INTEGER,
			swhPort10MCT3512PortSetupPortSpeed
				INTEGER,
			swhPort10MCT3512PortSetupPortDuplex
				INTEGER
		}

	swhPort10MCT3512PortSetupPort OBJECT-TYPE
		SYNTAX      INTEGER (0..2147483647)
		MAX-ACCESS  read-only
		STATUS      current
		DESCRIPTION
			"A unique value for each port."
		::= { swhPort10MCT3512PortSetupEntry 1 }

	swhPort10MCT3512PortSetupMediaType OBJECT-TYPE
		SYNTAX      DisplayString
		MAX-ACCESS  read-only
		STATUS      current
		DESCRIPTION
			"Media Type."
		::= { swhPort10MCT3512PortSetupEntry 2 }

	swhPort10MCT3512PortSetupPortState OBJECT-TYPE
		SYNTAX      INTEGER { disable(0), enable(1) }
		MAX-ACCESS  read-write
		STATUS      current
		DESCRIPTION
			"Port State."
		::= { swhPort10MCT3512PortSetupEntry 3 }

	swhPort10MCT3512PortSetupPortType OBJECT-TYPE
		SYNTAX      INTEGER { manual(0), auto-negotiation(1) }
		MAX-ACCESS  read-write
		STATUS      current
		DESCRIPTION
			"Port Type."
		::= { swhPort10MCT3512PortSetupEntry 4 }

	swhPort10MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort10MCT3512PortSetupEntry 5 }

	swhPort10MCT3512PortSetupPortDuplex OBJECT-TYPE
		SYNTAX      INTEGER { halfDuplex(0), fullDuplex(1) }
		MAX-ACCESS  read-write
		STATUS      current
		DESCRIPTION
			"Port Duplex."
		::= { swhPort10MCT3512PortSetupEntry 6 }


-- EthernetOAM(24).OAMRemoteModule(5).RemoteModuleConfiguration(2).Port10RemoteConfiguration(10).Port10MCT3512Configuration(1).Port10MCT3512VLANSetup(3)

	swhPort10MCT3512VLANSetup
		OBJECT IDENTIFIER ::= { swhPort10MCT3512Configuration 3 }

	swhPort10MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort10MCT3512VLANSetup 1 }

	swhPort10MCT3512VLANSetupISPMode OBJECT-TYPE
		SYNTAX      INTEGER { disable(0), enable(1) }
		MAX-ACCESS  read-write
		STATUS      current
		DESCRIPTION
			"Remote Module ISP Mode."
		::= { swhPort10MCT3512VLANSetup 2 }

	swhPort10MCT3512VLANSetupStagEtherType OBJECT-TYPE
		SYNTAX      DisplayString
		MAX-ACCESS  read-write
		STATUS      current
		DESCRIPTION
			"Remote Module Stag EtherType."
		::= { swhPort10MCT3512VLANSetup 3 }

	swhPort10MCT3512VLANSetupTable OBJECT-TYPE
		SYNTAX      SEQUENCE OF SwhPort10MCT3512VLANSetupEntry
		MAX-ACCESS  not-accessible
		STATUS      current
		DESCRIPTION
			"Table of remote module VLAN setup."
		::= { swhPort10MCT3512VLANSetup 5 }

	-- Table Entry
	swhPort10MCT3512VLANSetupEntry OBJECT-TYPE
		SYNTAX      SwhPort10MCT3512VLANSetupEntry
		MAX-ACCESS  not-accessible
		STATUS      current
		DESCRIPTION
			"An entry in the table, containing information about remote module VLAN setup."
		INDEX    { swhPort10MCT3512VLANSetupPort }
		::= { swhPort10MCT3512VLANSetupTable 1 }

	SwhPort10MCT3512VLANSetupEntry ::=
		SEQUENCE {
			swhPort10MCT3512VLANSetupPort
				INTEGER,
			swhPort10MCT3512VLANSetupMediaType
				DisplayString,
			swhPort10MCT3512VLANSetupMode
				INTEGER,
			swhPort10MCT3512VLANSetupPVID
				INTEGER,
			swhPort10MCT3512VLANSetupTrunkVLAN
				DisplayString,
			swhPort10MCT3512VLANSetupStagVID
				INTEGER,
			swhPort10MCT3512VLANSetupISPPort
				INTEGER
		}

	swhPort10MCT3512VLANSetupPort OBJECT-TYPE
		SYNTAX      INTEGER (0..2147483647)
		MAX-ACCESS  read-only
		STATUS      current
		DESCRIPTION
			"A unique value for each port."
		::= { swhPort10MCT3512VLANSetupEntry 1 }

	swhPort10MCT3512VLANSetupMediaType OBJECT-TYPE
		SYNTAX      DisplayString
		MAX-ACCESS  read-only
		STATUS      current
		DESCRIPTION
			"Remote Module Port Media Type."
		::= { swhPort10MCT3512VLANSetupEntry 2 }

	swhPort10MCT3512VLANSetupMode OBJECT-TYPE
		SYNTAX      INTEGER { access(0), trunk(1), trunknative(2) }
		MAX-ACCESS  read-write
		STATUS      current
		DESCRIPTION
			"Remote Module Port Mode."
		::= { swhPort10MCT3512VLANSetupEntry 3 }

	swhPort10MCT3512VLANSetupPVID OBJECT-TYPE
		SYNTAX      INTEGER (1..4093)
		MAX-ACCESS  read-write
		STATUS      current
		DESCRIPTION
			"Remote Module Port PVID."
		::= { swhPort10MCT3512VLANSetupEntry 4 }

	swhPort10MCT3512VLANSetupTrunkVLAN OBJECT-TYPE
		SYNTAX      DisplayString
		MAX-ACCESS  read-write
		STATUS      current
		DESCRIPTION
			"Remote Module Port Trunk VLAN."
		::= { swhPort10MCT3512VLANSetupEntry 5 }

	swhPort10MCT3512VLANSetupStagVID OBJECT-TYPE
		SYNTAX      INTEGER (1..4093)
		MAX-ACCESS  read-write
		STATUS      current
		DESCRIPTION
			"Remote Module Port Stag VID."
		::= { swhPort10MCT3512VLANSetupEntry 6 }

	swhPort10MCT3512VLANSetupISPPort OBJECT-TYPE
		SYNTAX      INTEGER { disable(0), enable(1) }
		MAX-ACCESS  read-write
		STATUS      current
		DESCRIPTION
			"Remote Module Port ISP Port."
		::= { swhPort10MCT3512VLANSetupEntry 7 }


-- EthernetOAM(24).OAMRemoteModule(5).RemoteModuleConfiguration(2).Port10RemoteConfiguration(10).Port10MCT3512Configuration(1).Port10MCT3512RateLimit(4)

	swhPort10MCT3512RateLimit
		OBJECT IDENTIFIER ::= { swhPort10MCT3512Configuration 4 }

	swhPort10MCT3512RateLimitTable OBJECT-TYPE
		SYNTAX      SEQUENCE OF SwhPort10MCT3512RateLimitEntry
		MAX-ACCESS  not-accessible
		STATUS      current
		DESCRIPTION
			"Table of remote module QoS rate limit."
		::= { swhPort10MCT3512RateLimit 5 }

	-- Table Entry
	swhPort10MCT3512RateLimitEntry OBJECT-TYPE
		SYNTAX      SwhPort10MCT3512RateLimitEntry
		MAX-ACCESS  not-accessible
		STATUS      current
		DESCRIPTION
			"An entry in the table, containing information about remote module QoS rate limit."
		INDEX    { swhPort10MCT3512RateLimitPort }
		::= { swhPort10MCT3512RateLimitTable 1 }

	SwhPort10MCT3512RateLimitEntry ::=
		SEQUENCE {
			swhPort10MCT3512RateLimitPort
				INTEGER,
			swhPort10MCT3512RateLimitMediaType
				DisplayString,
			swhPort10MCT3512RateLimitIngressEn
				INTEGER,
			swhPort10MCT3512RateLimitIngressRate
				INTEGER,
			swhPort10MCT3512RateLimitEgressEn
				INTEGER,
			swhPort10MCT3512RateLimitEgressRate
				INTEGER
		}

	swhPort10MCT3512RateLimitPort OBJECT-TYPE
		SYNTAX      INTEGER (0..2147483647)
		MAX-ACCESS  read-only
		STATUS      current
		DESCRIPTION
			"A unique value for each port."
		::= { swhPort10MCT3512RateLimitEntry 1 }

	swhPort10MCT3512RateLimitMediaType OBJECT-TYPE
		SYNTAX      DisplayString
		MAX-ACCESS  read-only
		STATUS      current
		DESCRIPTION
			"Remote Module Port Media Type."
		::= { swhPort10MCT3512RateLimitEntry 2 }

	swhPort10MCT3512RateLimitIngressEn OBJECT-TYPE
		SYNTAX      INTEGER { disable(0), enable(1) }
		MAX-ACCESS  read-write
		STATUS      current
		DESCRIPTION
			"Remote Module Port Ingress Enable."
		::= { swhPort10MCT3512RateLimitEntry 3 }

	swhPort10MCT3512RateLimitIngressRate OBJECT-TYPE
		SYNTAX      INTEGER (32..1000000)
		MAX-ACCESS  read-write
		STATUS      current
		DESCRIPTION
			"Remote Module Port Ingress Rate (32-1000000) kbps."
		::= { swhPort10MCT3512RateLimitEntry 4 }

	swhPort10MCT3512RateLimitEgressEn OBJECT-TYPE
		SYNTAX      INTEGER { disable(0), enable(1) }
		MAX-ACCESS  read-write
		STATUS      current
		DESCRIPTION
			"Remote Module Port Egress Enable."
		::= { swhPort10MCT3512RateLimitEntry 5 }

	swhPort10MCT3512RateLimitEgressRate OBJECT-TYPE
		SYNTAX      INTEGER (32..1000000)
		MAX-ACCESS  read-write
		STATUS      current
		DESCRIPTION
			"Remote Module Port Egress Rate (32-1000000) kbps."
		::= { swhPort10MCT3512RateLimitEntry 6 }


-- EthernetOAM(24).OAMRemoteModule(5).RemoteModuleConfiguration(2).Port10RemoteConfiguration(10).Port10MCT3512Configuration(1).Port10MCT3512StormControl(5)

	swhPort10MCT3512StormControl
		OBJECT IDENTIFIER ::= { swhPort10MCT3512Configuration 5 }

	swhPort10MCT3512StormControlEnable OBJECT-TYPE
		SYNTAX      INTEGER { disable(0), enable(1) }
		MAX-ACCESS  read-write
		STATUS      current
		DESCRIPTION
			"Remote Module Storm Control."
		::= { swhPort10MCT3512StormControl 1 }

	swhPort10MCT3512StormControlRate OBJECT-TYPE
		SYNTAX      INTEGER (32..1000000)
		MAX-ACCESS  read-write
		STATUS      current
		DESCRIPTION
			"Remote Module Rate (32-1000000) kbps."
		::= { swhPort10MCT3512StormControl 2 }

	swhPort10MCT3512StormControlBandwidth OBJECT-TYPE
		SYNTAX      DisplayString
		MAX-ACCESS  read-only
		STATUS      current
		DESCRIPTION
			"Remote Module Bandwidth (bps)."
		::= { swhPort10MCT3512StormControl 3 }


-- EthernetOAM(24).OAMRemoteModule(5).RemoteModuleConfiguration(2).Port10RemoteConfiguration(10).Port10MCT3512Configuration(1).Port10MCT3512LANFollowsWAN(6)

	swhPort10MCT3512LANFollowsWAN
		OBJECT IDENTIFIER ::= { swhPort10MCT3512Configuration 6 }

	swhPort10MCT3512LANFollowsWANEnable OBJECT-TYPE
		SYNTAX      INTEGER { disable(0), enable(1) }
		MAX-ACCESS  read-write
		STATUS      current
		DESCRIPTION
			"Remote Module LAN Follows WAN."
		::= { swhPort10MCT3512LANFollowsWAN 1 }


-- EthernetOAM(24).OAMRemoteModule(5).RemoteModuleConfiguration(2).Port11RemoteConfiguration(11)

	swhPort11RemoteConfiguration
		OBJECT IDENTIFIER ::= { swhRemoteModuleConfiguration 11 }


-- EthernetOAM(24).OAMRemoteModule(5).RemoteModuleConfiguration(2).Port11RemoteConfiguration(11).Port11MCT3512Configuration(1)

	swhPort11MCT3512Configuration
		OBJECT IDENTIFIER ::= { swhPort11RemoteConfiguration 1 }


-- EthernetOAM(24).OAMRemoteModule(5).RemoteModuleConfiguration(2).Port11RemoteConfiguration(11).Port11MCT3512Configuration(1).Port11MCT3512Config(1)

	swhPort11MCT3512Config
		OBJECT IDENTIFIER ::= { swhPort11MCT3512Configuration 1 }

	swhPort11MCT3512ConfigDetectedModule OBJECT-TYPE
		SYNTAX      DisplayString
		MAX-ACCESS  read-only
		STATUS      current
		DESCRIPTION
			"Detected Module."
		::= { swhPort11MCT3512Config 1 }

	swhPort11MCT3512ConfigDIPSwitchSetting OBJECT-TYPE
		SYNTAX      DisplayString
		MAX-ACCESS  read-only
		STATUS      current
		DESCRIPTION
			"DIP Switch (PIN 8) Setting."
		::= { swhPort11MCT3512Config 2 }


-- EthernetOAM(24).OAMRemoteModule(5).RemoteModuleConfiguration(2).Port11RemoteConfiguration(11).Port11MCT3512Configuration(1).Port11MCT3512PortSetup(2)

	swhPort11MCT3512PortSetup
		OBJECT IDENTIFIER ::= { swhPort11MCT3512Configuration 2 }

	swhPort11MCT3512PortSetupTable OBJECT-TYPE
		SYNTAX      SEQUENCE OF SwhPort11MCT3512PortSetupEntry
		MAX-ACCESS  not-accessible
		STATUS      current
		DESCRIPTION
			"Table of remote module port setup."
		::= { swhPort11MCT3512PortSetup 5 }

	-- Table Entry
	swhPort11MCT3512PortSetupEntry OBJECT-TYPE
		SYNTAX      SwhPort11MCT3512PortSetupEntry
		MAX-ACCESS  not-accessible
		STATUS      current
		DESCRIPTION
			"An entry in the table, containing information about remote module port setup."
		INDEX    { swhPort11MCT3512PortSetupPort }
		::= { swhPort11MCT3512PortSetupTable 1 }

	SwhPort11MCT3512PortSetupEntry ::=
		SEQUENCE {
			swhPort11MCT3512PortSetupPort
				INTEGER,
			swhPort11MCT3512PortSetupMediaType
				DisplayString,
			swhPort11MCT3512PortSetupPortState
				INTEGER,
			swhPort11MCT3512PortSetupPortType
				INTEGER,
			swhPort11MCT3512PortSetupPortSpeed
				INTEGER,
			swhPort11MCT3512PortSetupPortDuplex
				INTEGER
		}

	swhPort11MCT3512PortSetupPort OBJECT-TYPE
		SYNTAX      INTEGER (0..2147483647)
		MAX-ACCESS  read-only
		STATUS      current
		DESCRIPTION
			"A unique value for each port."
		::= { swhPort11MCT3512PortSetupEntry 1 }

	swhPort11MCT3512PortSetupMediaType OBJECT-TYPE
		SYNTAX      DisplayString
		MAX-ACCESS  read-only
		STATUS      current
		DESCRIPTION
			"Media Type."
		::= { swhPort11MCT3512PortSetupEntry 2 }

	swhPort11MCT3512PortSetupPortState OBJECT-TYPE
		SYNTAX      INTEGER { disable(0), enable(1) }
		MAX-ACCESS  read-write
		STATUS      current
		DESCRIPTION
			"Port State."
		::= { swhPort11MCT3512PortSetupEntry 3 }

	swhPort11MCT3512PortSetupPortType OBJECT-TYPE
		SYNTAX      INTEGER { manual(0), auto-negotiation(1) }
		MAX-ACCESS  read-write
		STATUS      current
		DESCRIPTION
			"Port Type."
		::= { swhPort11MCT3512PortSetupEntry 4 }

	swhPort11MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort11MCT3512PortSetupEntry 5 }

	swhPort11MCT3512PortSetupPortDuplex OBJECT-TYPE
		SYNTAX      INTEGER { halfDuplex(0), fullDuplex(1) }
		MAX-ACCESS  read-write
		STATUS      current
		DESCRIPTION
			"Port Duplex."
		::= { swhPort11MCT3512PortSetupEntry 6 }


-- EthernetOAM(24).OAMRemoteModule(5).RemoteModuleConfiguration(2).Port11RemoteConfiguration(11).Port11MCT3512Configuration(1).Port11MCT3512VLANSetup(3)

	swhPort11MCT3512VLANSetup
		OBJECT IDENTIFIER ::= { swhPort11MCT3512Configuration 3 }

	swhPort11MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort11MCT3512VLANSetup 1 }

	swhPort11MCT3512VLANSetupISPMode OBJECT-TYPE
		SYNTAX      INTEGER { disable(0), enable(1) }
		MAX-ACCESS  read-write
		STATUS      current
		DESCRIPTION
			"Remote Module ISP Mode."
		::= { swhPort11MCT3512VLANSetup 2 }

	swhPort11MCT3512VLANSetupStagEtherType OBJECT-TYPE
		SYNTAX      DisplayString
		MAX-ACCESS  read-write
		STATUS      current
		DESCRIPTION
			"Remote Module Stag EtherType."
		::= { swhPort11MCT3512VLANSetup 3 }

	swhPort11MCT3512VLANSetupTable OBJECT-TYPE
		SYNTAX      SEQUENCE OF SwhPort11MCT3512VLANSetupEntry
		MAX-ACCESS  not-accessible
		STATUS      current
		DESCRIPTION
			"Table of remote module VLAN setup."
		::= { swhPort11MCT3512VLANSetup 5 }

	-- Table Entry
	swhPort11MCT3512VLANSetupEntry OBJECT-TYPE
		SYNTAX      SwhPort11MCT3512VLANSetupEntry
		MAX-ACCESS  not-accessible
		STATUS      current
		DESCRIPTION
			"An entry in the table, containing information about remote module VLAN setup."
		INDEX    { swhPort11MCT3512VLANSetupPort }
		::= { swhPort11MCT3512VLANSetupTable 1 }

	SwhPort11MCT3512VLANSetupEntry ::=
		SEQUENCE {
			swhPort11MCT3512VLANSetupPort
				INTEGER,
			swhPort11MCT3512VLANSetupMediaType
				DisplayString,
			swhPort11MCT3512VLANSetupMode
				INTEGER,
			swhPort11MCT3512VLANSetupPVID
				INTEGER,
			swhPort11MCT3512VLANSetupTrunkVLAN
				DisplayString,
			swhPort11MCT3512VLANSetupStagVID
				INTEGER,
			swhPort11MCT3512VLANSetupISPPort
				INTEGER
		}

	swhPort11MCT3512VLANSetupPort OBJECT-TYPE
		SYNTAX      INTEGER (0..2147483647)
		MAX-ACCESS  read-only
		STATUS      current
		DESCRIPTION
			"A unique value for each port."
		::= { swhPort11MCT3512VLANSetupEntry 1 }

	swhPort11MCT3512VLANSetupMediaType OBJECT-TYPE
		SYNTAX      DisplayString
		MAX-ACCESS  read-only
		STATUS      current
		DESCRIPTION
			"Remote Module Port Media Type."
		::= { swhPort11MCT3512VLANSetupEntry 2 }

	swhPort11MCT3512VLANSetupMode OBJECT-TYPE
		SYNTAX      INTEGER { access(0), trunk(1), trunknative(2) }
		MAX-ACCESS  read-write
		STATUS      current
		DESCRIPTION
			"Remote Module Port Mode."
		::= { swhPort11MCT3512VLANSetupEntry 3 }

	swhPort11MCT3512VLANSetupPVID OBJECT-TYPE
		SYNTAX      INTEGER (1..4093)
		MAX-ACCESS  read-write
		STATUS      current
		DESCRIPTION
			"Remote Module Port PVID."
		::= { swhPort11MCT3512VLANSetupEntry 4 }

	swhPort11MCT3512VLANSetupTrunkVLAN OBJECT-TYPE
		SYNTAX      DisplayString
		MAX-ACCESS  read-write
		STATUS      current
		DESCRIPTION
			"Remote Module Port Trunk VLAN."
		::= { swhPort11MCT3512VLANSetupEntry 5 }

	swhPort11MCT3512VLANSetupStagVID OBJECT-TYPE
		SYNTAX      INTEGER (1..4093)
		MAX-ACCESS  read-write
		STATUS      current
		DESCRIPTION
			"Remote Module Port Stag VID."
		::= { swhPort11MCT3512VLANSetupEntry 6 }

	swhPort11MCT3512VLANSetupISPPort OBJECT-TYPE
		SYNTAX      INTEGER { disable(0), enable(1) }
		MAX-ACCESS  read-write
		STATUS      current
		DESCRIPTION
			"Remote Module Port ISP Port."
		::= { swhPort11MCT3512VLANSetupEntry 7 }


-- EthernetOAM(24).OAMRemoteModule(5).RemoteModuleConfiguration(2).Port11RemoteConfiguration(11).Port11MCT3512Configuration(1).Port11MCT3512RateLimit(4)

	swhPort11MCT3512RateLimit
		OBJECT IDENTIFIER ::= { swhPort11MCT3512Configuration 4 }

	swhPort11MCT3512RateLimitTable OBJECT-TYPE
		SYNTAX      SEQUENCE OF SwhPort11MCT3512RateLimitEntry
		MAX-ACCESS  not-accessible
		STATUS      current
		DESCRIPTION
			"Table of remote module QoS rate limit."
		::= { swhPort11MCT3512RateLimit 5 }

	-- Table Entry
	swhPort11MCT3512RateLimitEntry OBJECT-TYPE
		SYNTAX      SwhPort11MCT3512RateLimitEntry
		MAX-ACCESS  not-accessible
		STATUS      current
		DESCRIPTION
			"An entry in the table, containing information about remote module QoS rate limit."
		INDEX    { swhPort11MCT3512RateLimitPort }
		::= { swhPort11MCT3512RateLimitTable 1 }

	SwhPort11MCT3512RateLimitEntry ::=
		SEQUENCE {
			swhPort11MCT3512RateLimitPort
				INTEGER,
			swhPort11MCT3512RateLimitMediaType
				DisplayString,
			swhPort11MCT3512RateLimitIngressEn
				INTEGER,
			swhPort11MCT3512RateLimitIngressRate
				INTEGER,
			swhPort11MCT3512RateLimitEgressEn
				INTEGER,
			swhPort11MCT3512RateLimitEgressRate
				INTEGER
		}

	swhPort11MCT3512RateLimitPort OBJECT-TYPE
		SYNTAX      INTEGER (0..2147483647)
		MAX-ACCESS  read-only
		STATUS      current
		DESCRIPTION
			"A unique value for each port."
		::= { swhPort11MCT3512RateLimitEntry 1 }

	swhPort11MCT3512RateLimitMediaType OBJECT-TYPE
		SYNTAX      DisplayString
		MAX-ACCESS  read-only
		STATUS      current
		DESCRIPTION
			"Remote Module Port Media Type."
		::= { swhPort11MCT3512RateLimitEntry 2 }

	swhPort11MCT3512RateLimitIngressEn OBJECT-TYPE
		SYNTAX      INTEGER { disable(0), enable(1) }
		MAX-ACCESS  read-write
		STATUS      current
		DESCRIPTION
			"Remote Module Port Ingress Enable."
		::= { swhPort11MCT3512RateLimitEntry 3 }

	swhPort11MCT3512RateLimitIngressRate OBJECT-TYPE
		SYNTAX      INTEGER (32..1000000)
		MAX-ACCESS  read-write
		STATUS      current
		DESCRIPTION
			"Remote Module Port Ingress Rate (32-1000000) kbps."
		::= { swhPort11MCT3512RateLimitEntry 4 }

	swhPort11MCT3512RateLimitEgressEn OBJECT-TYPE
		SYNTAX      INTEGER { disable(0), enable(1) }
		MAX-ACCESS  read-write
		STATUS      current
		DESCRIPTION
			"Remote Module Port Egress Enable."
		::= { swhPort11MCT3512RateLimitEntry 5 }

	swhPort11MCT3512RateLimitEgressRate OBJECT-TYPE
		SYNTAX      INTEGER (32..1000000)
		MAX-ACCESS  read-write
		STATUS      current
		DESCRIPTION
			"Remote Module Port Egress Rate (32-1000000) kbps."
		::= { swhPort11MCT3512RateLimitEntry 6 }


-- EthernetOAM(24).OAMRemoteModule(5).RemoteModuleConfiguration(2).Port11RemoteConfiguration(11).Port11MCT3512Configuration(1).Port11MCT3512StormControl(5)

	swhPort11MCT3512StormControl
		OBJECT IDENTIFIER ::= { swhPort11MCT3512Configuration 5 }

	swhPort11MCT3512StormControlEnable OBJECT-TYPE
		SYNTAX      INTEGER { disable(0), enable(1) }
		MAX-ACCESS  read-write
		STATUS      current
		DESCRIPTION
			"Remote Module Storm Control."
		::= { swhPort11MCT3512StormControl 1 }

	swhPort11MCT3512StormControlRate OBJECT-TYPE
		SYNTAX      INTEGER (32..1000000)
		MAX-ACCESS  read-write
		STATUS      current
		DESCRIPTION
			"Remote Module Rate (32-1000000) kbps."
		::= { swhPort11MCT3512StormControl 2 }

	swhPort11MCT3512StormControlBandwidth OBJECT-TYPE
		SYNTAX      DisplayString
		MAX-ACCESS  read-only
		STATUS      current
		DESCRIPTION
			"Remote Module Bandwidth (bps)."
		::= { swhPort11MCT3512StormControl 3 }


-- EthernetOAM(24).OAMRemoteModule(5).RemoteModuleConfiguration(2).Port11RemoteConfiguration(11).Port11MCT3512Configuration(1).Port11MCT3512LANFollowsWAN(6)

	swhPort11MCT3512LANFollowsWAN
		OBJECT IDENTIFIER ::= { swhPort11MCT3512Configuration 6 }

	swhPort11MCT3512LANFollowsWANEnable OBJECT-TYPE
		SYNTAX      INTEGER { disable(0), enable(1) }
		MAX-ACCESS  read-write
		STATUS      current
		DESCRIPTION
			"Remote Module LAN Follows WAN."
		::= { swhPort11MCT3512LANFollowsWAN 1 }


-- EthernetOAM(24).OAMRemoteModule(5).RemoteModuleConfiguration(2).Port12RemoteConfiguration(12)

	swhPort12RemoteConfiguration
		OBJECT IDENTIFIER ::= { swhRemoteModuleConfiguration 12 }


-- EthernetOAM(24).OAMRemoteModule(5).RemoteModuleConfiguration(2).Port12RemoteConfiguration(12).Port12MCT3512Configuration(1)

	swhPort12MCT3512Configuration
		OBJECT IDENTIFIER ::= { swhPort12RemoteConfiguration 1 }


-- EthernetOAM(24).OAMRemoteModule(5).RemoteModuleConfiguration(2).Port12RemoteConfiguration(12).Port12MCT3512Configuration(1).Port12MCT3512Config(1)

	swhPort12MCT3512Config
		OBJECT IDENTIFIER ::= { swhPort12MCT3512Configuration 1 }

	swhPort12MCT3512ConfigDetectedModule OBJECT-TYPE
		SYNTAX      DisplayString
		MAX-ACCESS  read-only
		STATUS      current
		DESCRIPTION
			"Detected Module."
		::= { swhPort12MCT3512Config 1 }

	swhPort12MCT3512ConfigDIPSwitchSetting OBJECT-TYPE
		SYNTAX      DisplayString
		MAX-ACCESS  read-only
		STATUS      current
		DESCRIPTION
			"DIP Switch (PIN 8) Setting."
		::= { swhPort12MCT3512Config 2 }


-- EthernetOAM(24).OAMRemoteModule(5).RemoteModuleConfiguration(2).Port12RemoteConfiguration(12).Port12MCT3512Configuration(1).Port12MCT3512PortSetup(2)

	swhPort12MCT3512PortSetup
		OBJECT IDENTIFIER ::= { swhPort12MCT3512Configuration 2 }

	swhPort12MCT3512PortSetupTable OBJECT-TYPE
		SYNTAX      SEQUENCE OF SwhPort12MCT3512PortSetupEntry
		MAX-ACCESS  not-accessible
		STATUS      current
		DESCRIPTION
			"Table of remote module port setup."
		::= { swhPort12MCT3512PortSetup 5 }

	-- Table Entry
	swhPort12MCT3512PortSetupEntry OBJECT-TYPE
		SYNTAX      SwhPort12MCT3512PortSetupEntry
		MAX-ACCESS  not-accessible
		STATUS      current
		DESCRIPTION
			"An entry in the table, containing information about remote module port setup."
		INDEX    { swhPort12MCT3512PortSetupPort }
		::= { swhPort12MCT3512PortSetupTable 1 }

	SwhPort12MCT3512PortSetupEntry ::=
		SEQUENCE {
			swhPort12MCT3512PortSetupPort
				INTEGER,
			swhPort12MCT3512PortSetupMediaType
				DisplayString,
			swhPort12MCT3512PortSetupPortState
				INTEGER,
			swhPort12MCT3512PortSetupPortType
				INTEGER,
			swhPort12MCT3512PortSetupPortSpeed
				INTEGER,
			swhPort12MCT3512PortSetupPortDuplex
				INTEGER
		}

	swhPort12MCT3512PortSetupPort OBJECT-TYPE
		SYNTAX      INTEGER (0..2147483647)
		MAX-ACCESS  read-only
		STATUS      current
		DESCRIPTION
			"A unique value for each port."
		::= { swhPort12MCT3512PortSetupEntry 1 }

	swhPort12MCT3512PortSetupMediaType OBJECT-TYPE
		SYNTAX      DisplayString
		MAX-ACCESS  read-only
		STATUS      current
		DESCRIPTION
			"Media Type."
		::= { swhPort12MCT3512PortSetupEntry 2 }

	swhPort12MCT3512PortSetupPortState OBJECT-TYPE
		SYNTAX      INTEGER { disable(0), enable(1) }
		MAX-ACCESS  read-write
		STATUS      current
		DESCRIPTION
			"Port State."
		::= { swhPort12MCT3512PortSetupEntry 3 }

	swhPort12MCT3512PortSetupPortType OBJECT-TYPE
		SYNTAX      INTEGER { manual(0), auto-negotiation(1) }
		MAX-ACCESS  read-write
		STATUS      current
		DESCRIPTION
			"Port Type."
		::= { swhPort12MCT3512PortSetupEntry 4 }

	swhPort12MCT3512PortSetupPortSpeed OBJECT-TYPE
		SYNTAX      INTEGER { speed-10M(0), speed-100M(1), speed-1000M(2), auto-sense(3) }
		MAX-ACCESS  read-write
		STATUS      current
		DESCRIPTION
			"Port Speed."
		::= { swhPort12MCT3512PortSetupEntry 5 }

	swhPort12MCT3512PortSetupPortDuplex OBJECT-TYPE
		SYNTAX      INTEGER { halfDuplex(0), fullDuplex(1) }
		MAX-ACCESS  read-write
		STATUS      current
		DESCRIPTION
			"Port Duplex."
		::= { swhPort12MCT3512PortSetupEntry 6 }


-- EthernetOAM(24).OAMRemoteModule(5).RemoteModuleConfiguration(2).Port12RemoteConfiguration(12).Port12MCT3512Configuration(1).Port12MCT3512VLANSetup(3)

	swhPort12MCT3512VLANSetup
		OBJECT IDENTIFIER ::= { swhPort12MCT3512Configuration 3 }

	swhPort12MCT3512VLANSetupVLANMode OBJECT-TYPE
		SYNTAX      INTEGER { disable(0), tagvlan(1), bypassctag(2) }
		MAX-ACCESS  read-write
		STATUS      current
		DESCRIPTION
			"Remote Module 802.1q Tag VLAN Mode."
		::= { swhPort12MCT3512VLANSetup 1 }

	swhPort12MCT3512VLANSetupISPMode OBJECT-TYPE
		SYNTAX      INTEGER { disable(0), enable(1) }
		MAX-ACCESS  read-write
		STATUS      current
		DESCRIPTION
			"Remote Module ISP Mode."
		::= { swhPort12MCT3512VLANSetup 2 }

	swhPort12MCT3512VLANSetupStagEtherType OBJECT-TYPE
		SYNTAX      DisplayString
		MAX-ACCESS  read-write
		STATUS      current
		DESCRIPTION
			"Remote Module Stag EtherType."
		::= { swhPort12MCT3512VLANSetup 3 }

	swhPort12MCT3512VLANSetupTable OBJECT-TYPE
		SYNTAX      SEQUENCE OF SwhPort12MCT3512VLANSetupEntry
		MAX-ACCESS  not-accessible
		STATUS      current
		DESCRIPTION
			"Table of remote module VLAN setup."
		::= { swhPort12MCT3512VLANSetup 5 }

	-- Table Entry
	swhPort12MCT3512VLANSetupEntry OBJECT-TYPE
		SYNTAX      SwhPort12MCT3512VLANSetupEntry
		MAX-ACCESS  not-accessible
		STATUS      current
		DESCRIPTION
			"An entry in the table, containing information about remote module VLAN setup."
		INDEX    { swhPort12MCT3512VLANSetupPort }
		::= { swhPort12MCT3512VLANSetupTable 1 }

	SwhPort12MCT3512VLANSetupEntry ::=
		SEQUENCE {
			swhPort12MCT3512VLANSetupPort
				INTEGER,
			swhPort12MCT3512VLANSetupMediaType
				DisplayString,
			swhPort12MCT3512VLANSetupMode
				INTEGER,
			swhPort12MCT3512VLANSetupPVID
				INTEGER,
			swhPort12MCT3512VLANSetupTrunkVLAN
				DisplayString,
			swhPort12MCT3512VLANSetupStagVID
				INTEGER,
			swhPort12MCT3512VLANSetupISPPort
				INTEGER
		}

	swhPort12MCT3512VLANSetupPort OBJECT-TYPE
		SYNTAX      INTEGER (0..2147483647)
		MAX-ACCESS  read-only
		STATUS      current
		DESCRIPTION
			"A unique value for each port."
		::= { swhPort12MCT3512VLANSetupEntry 1 }

	swhPort12MCT3512VLANSetupMediaType OBJECT-TYPE
		SYNTAX      DisplayString
		MAX-ACCESS  read-only
		STATUS      current
		DESCRIPTION
			"Remote Module Port Media Type."
		::= { swhPort12MCT3512VLANSetupEntry 2 }

	swhPort12MCT3512VLANSetupMode OBJECT-TYPE
		SYNTAX      INTEGER { access(0), trunk(1), trunknative(2) }
		MAX-ACCESS  read-write
		STATUS      current
		DESCRIPTION
			"Remote Module Port Mode."
		::= { swhPort12MCT3512VLANSetupEntry 3 }

	swhPort12MCT3512VLANSetupPVID OBJECT-TYPE
		SYNTAX      INTEGER (1..4093)
		MAX-ACCESS  read-write
		STATUS      current
		DESCRIPTION
			"Remote Module Port PVID."
		::= { swhPort12MCT3512VLANSetupEntry 4 }

	swhPort12MCT3512VLANSetupTrunkVLAN OBJECT-TYPE
		SYNTAX      DisplayString
		MAX-ACCESS  read-write
		STATUS      current
		DESCRIPTION
			"Remote Module Port Trunk VLAN."
		::= { swhPort12MCT3512VLANSetupEntry 5 }

	swhPort12MCT3512VLANSetupStagVID OBJECT-TYPE
		SYNTAX      INTEGER (1..4093)
		MAX-ACCESS  read-write
		STATUS      current
		DESCRIPTION
			"Remote Module Port Stag VID."
		::= { swhPort12MCT3512VLANSetupEntry 6 }

	swhPort12MCT3512VLANSetupISPPort OBJECT-TYPE
		SYNTAX      INTEGER { disable(0), enable(1) }
		MAX-ACCESS  read-write
		STATUS      current
		DESCRIPTION
			"Remote Module Port ISP Port."
		::= { swhPort12MCT3512VLANSetupEntry 7 }


-- EthernetOAM(24).OAMRemoteModule(5).RemoteModuleConfiguration(2).Port12RemoteConfiguration(12).Port12MCT3512Configuration(1).Port12MCT3512RateLimit(4)

	swhPort12MCT3512RateLimit
		OBJECT IDENTIFIER ::= { swhPort12MCT3512Configuration 4 }

	swhPort12MCT3512RateLimitTable OBJECT-TYPE
		SYNTAX      SEQUENCE OF SwhPort12MCT3512RateLimitEntry
		MAX-ACCESS  not-accessible
		STATUS      current
		DESCRIPTION
			"Table of remote module QoS rate limit."
		::= { swhPort12MCT3512RateLimit 5 }

	-- Table Entry
	swhPort12MCT3512RateLimitEntry OBJECT-TYPE
		SYNTAX      SwhPort12MCT3512RateLimitEntry
		MAX-ACCESS  not-accessible
		STATUS      current
		DESCRIPTION
			"An entry in the table, containing information about remote module QoS rate limit."
		INDEX    { swhPort12MCT3512RateLimitPort }
		::= { swhPort12MCT3512RateLimitTable 1 }

	SwhPort12MCT3512RateLimitEntry ::=
		SEQUENCE {
			swhPort12MCT3512RateLimitPort
				INTEGER,
			swhPort12MCT3512RateLimitMediaType
				DisplayString,
			swhPort12MCT3512RateLimitIngressEn
				INTEGER,
			swhPort12MCT3512RateLimitIngressRate
				INTEGER,
			swhPort12MCT3512RateLimitEgressEn
				INTEGER,
			swhPort12MCT3512RateLimitEgressRate
				INTEGER
		}

	swhPort12MCT3512RateLimitPort OBJECT-TYPE
		SYNTAX      INTEGER (0..2147483647)
		MAX-ACCESS  read-only
		STATUS      current
		DESCRIPTION
			"A unique value for each port."
		::= { swhPort12MCT3512RateLimitEntry 1 }

	swhPort12MCT3512RateLimitMediaType OBJECT-TYPE
		SYNTAX      DisplayString
		MAX-ACCESS  read-only
		STATUS      current
		DESCRIPTION
			"Remote Module Port Media Type."
		::= { swhPort12MCT3512RateLimitEntry 2 }

	swhPort12MCT3512RateLimitIngressEn OBJECT-TYPE
		SYNTAX      INTEGER { disable(0), enable(1) }
		MAX-ACCESS  read-write
		STATUS      current
		DESCRIPTION
			"Remote Module Port Ingress Enable."
		::= { swhPort12MCT3512RateLimitEntry 3 }

	swhPort12MCT3512RateLimitIngressRate OBJECT-TYPE
		SYNTAX      INTEGER (32..1000000)
		MAX-ACCESS  read-write
		STATUS      current
		DESCRIPTION
			"Remote Module Port Ingress Rate (32-1000000) kbps."
		::= { swhPort12MCT3512RateLimitEntry 4 }

	swhPort12MCT3512RateLimitEgressEn OBJECT-TYPE
		SYNTAX      INTEGER { disable(0), enable(1) }
		MAX-ACCESS  read-write
		STATUS      current
		DESCRIPTION
			"Remote Module Port Egress Enable."
		::= { swhPort12MCT3512RateLimitEntry 5 }

	swhPort12MCT3512RateLimitEgressRate OBJECT-TYPE
		SYNTAX      INTEGER (32..1000000)
		MAX-ACCESS  read-write
		STATUS      current
		DESCRIPTION
			"Remote Module Port Egress Rate (32-1000000) kbps."
		::= { swhPort12MCT3512RateLimitEntry 6 }


-- EthernetOAM(24).OAMRemoteModule(5).RemoteModuleConfiguration(2).Port12RemoteConfiguration(12).Port12MCT3512Configuration(1).Port12MCT3512StormControl(5)

	swhPort12MCT3512StormControl
		OBJECT IDENTIFIER ::= { swhPort12MCT3512Configuration 5 }

	swhPort12MCT3512StormControlEnable OBJECT-TYPE
		SYNTAX      INTEGER { disable(0), enable(1) }
		MAX-ACCESS  read-write
		STATUS      current
		DESCRIPTION
			"Remote Module Storm Control."
		::= { swhPort12MCT3512StormControl 1 }

	swhPort12MCT3512StormControlRate OBJECT-TYPE
		SYNTAX      INTEGER (32..1000000)
		MAX-ACCESS  read-write
		STATUS      current
		DESCRIPTION
			"Remote Module Rate (32-1000000) kbps."
		::= { swhPort12MCT3512StormControl 2 }

	swhPort12MCT3512StormControlBandwidth OBJECT-TYPE
		SYNTAX      DisplayString
		MAX-ACCESS  read-only
		STATUS      current
		DESCRIPTION
			"Remote Module Bandwidth (bps)."
		::= { swhPort12MCT3512StormControl 3 }


-- EthernetOAM(24).OAMRemoteModule(5).RemoteModuleConfiguration(2).Port12RemoteConfiguration(12).Port12MCT3512Configuration(1).Port12MCT3512LANFollowsWAN(6)

	swhPort12MCT3512LANFollowsWAN
		OBJECT IDENTIFIER ::= { swhPort12MCT3512Configuration 6 }

	swhPort12MCT3512LANFollowsWANEnable OBJECT-TYPE
		SYNTAX      INTEGER { disable(0), enable(1) }
		MAX-ACCESS  read-write
		STATUS      current
		DESCRIPTION
			"Remote Module LAN Follows WAN."
		::= { swhPort12MCT3512LANFollowsWAN 1 }


-- EthernetOAM(24).OAMRemoteModule(5).RemoteModuleInformation(3)

	swhRemotePortStatisticsAllClear OBJECT-TYPE
		SYNTAX      INTEGER { normal(0), clear(1) }
		MAX-ACCESS  read-write
		STATUS      current
		DESCRIPTION
			"Clear counters of all port."
		::= { swhRemoteModuleInformation 1 }


-- EthernetOAM(24).OAMRemoteModule(5).RemoteModuleInformation(3).Port1RemoteInformation(11)

	swhPort1RemoteInformation
		OBJECT IDENTIFIER ::= { swhRemoteModuleInformation 11 }

	swhPort1RemoteInfoTable OBJECT-TYPE
		SYNTAX      SEQUENCE OF SwhPort1RemoteInfoEntry
		MAX-ACCESS  not-accessible
		STATUS      current
		DESCRIPTION
			"Table of remote information."
		::= { swhPort1RemoteInformation 4 }

	-- Table Entry
	swhPort1RemoteInfoEntry OBJECT-TYPE
		SYNTAX      SwhPort1RemoteInfoEntry
		MAX-ACCESS  not-accessible
		STATUS      current
		DESCRIPTION
			"An entry in the table, containing information about remote information."
		INDEX    { swhPort1RemoteInfoIndex }
		::= { swhPort1RemoteInfoTable 1 }

	SwhPort1RemoteInfoEntry ::=
		SEQUENCE {
			swhPort1RemoteInfoIndex
				INTEGER,
			swhPort1RemoteInfoResult
				DisplayString
		}

	swhPort1RemoteInfoIndex OBJECT-TYPE
		SYNTAX      INTEGER (0..2147483647)
		MAX-ACCESS  read-only
		STATUS      current
		DESCRIPTION
			"A unique value for each pin."
		::= { swhPort1RemoteInfoEntry 1 }

	swhPort1RemoteInfoResult OBJECT-TYPE
		SYNTAX      DisplayString
		MAX-ACCESS  read-only
		STATUS      current
		DESCRIPTION
			"Result."
		::= { swhPort1RemoteInfoEntry 2 }


-- EthernetOAM(24).OAMRemoteModule(5).RemoteModuleInformation(3).Port1RemoteInformation(11).Port1RemotePortStatus(5)

	swhPort1RemotePortStatus
		OBJECT IDENTIFIER ::= { swhPort1RemoteInformation 5 }

	swhPort1RemotePortStatusDescription OBJECT-TYPE
		SYNTAX      DisplayString
		MAX-ACCESS  read-only
		STATUS      current
		DESCRIPTION
			"Description."
		::= { swhPort1RemotePortStatus 1 }

	swhPort1RemotePortStatusModelName OBJECT-TYPE
		SYNTAX      DisplayString
		MAX-ACCESS  read-only
		STATUS      current
		DESCRIPTION
			"Model Name."
		::= { swhPort1RemotePortStatus 2 }

	swhPort1RemotePortStatusTable OBJECT-TYPE
		SYNTAX      SEQUENCE OF SwhPort1RemotePortStatusEntry
		MAX-ACCESS  not-accessible
		STATUS      current
		DESCRIPTION
			"Table of remote port status."
		::= { swhPort1RemotePortStatus 5 }

	-- Table Entry
	swhPort1RemotePortStatusEntry OBJECT-TYPE
		SYNTAX      SwhPort1RemotePortStatusEntry
		MAX-ACCESS  not-accessible
		STATUS      current
		DESCRIPTION
			"An entry in the table, containing information about remote port status."
		INDEX    { swhPort1RemotePortStatusIndex }
		::= { swhPort1RemotePortStatusTable 1 }

	SwhPort1RemotePortStatusEntry ::=
		SEQUENCE {
			swhPort1RemotePortStatusIndex
				INTEGER,
			swhPort1RemotePortStatusNeighborPort
				DisplayString,
			swhPort1RemotePortStatusMediaType
				DisplayString,
			swhPort1RemotePortStatusPortState
				DisplayString,
			swhPort1RemotePortStatusLinkState
				DisplayString,
			swhPort1RemotePortStatusType
				DisplayString,
			swhPort1RemotePortStatusSpeed
				DisplayString,
			swhPort1RemotePortStatusDuplex
				DisplayString
		}

	swhPort1RemotePortStatusIndex OBJECT-TYPE
		SYNTAX      INTEGER (0..2147483647)
		MAX-ACCESS  read-only
		STATUS      current
		DESCRIPTION
			"A unique value for each index."
		::= { swhPort1RemotePortStatusEntry 1 }

	swhPort1RemotePortStatusNeighborPort OBJECT-TYPE
		SYNTAX      DisplayString
		MAX-ACCESS  read-only
		STATUS      current
		DESCRIPTION
			"Neighbor Port."
		::= { swhPort1RemotePortStatusEntry 2 }

	swhPort1RemotePortStatusMediaType OBJECT-TYPE
		SYNTAX      DisplayString
		MAX-ACCESS  read-only
		STATUS      current
		DESCRIPTION
			"Media Type."
		::= { swhPort1RemotePortStatusEntry 3 }

	swhPort1RemotePortStatusPortState OBJECT-TYPE
		SYNTAX      DisplayString
		MAX-ACCESS  read-only
		STATUS      current
		DESCRIPTION
			"Port State."
		::= { swhPort1RemotePortStatusEntry 4 }

	swhPort1RemotePortStatusLinkState OBJECT-TYPE
		SYNTAX      DisplayString
		MAX-ACCESS  read-only
		STATUS      current
		DESCRIPTION
			"Link State."
		::= { swhPort1RemotePortStatusEntry 5 }

	swhPort1RemotePortStatusType OBJECT-TYPE
		SYNTAX      DisplayString
		MAX-ACCESS  read-only
		STATUS      current
		DESCRIPTION
			"Type."
		::= { swhPort1RemotePortStatusEntry 6 }

	swhPort1RemotePortStatusSpeed OBJECT-TYPE
		SYNTAX      DisplayString
		MAX-ACCESS  read-only
		STATUS      current
		DESCRIPTION
			"Speed."
		::= { swhPort1RemotePortStatusEntry 7 }

	swhPort1RemotePortStatusDuplex OBJECT-TYPE
		SYNTAX      DisplayString
		MAX-ACCESS  read-only
		STATUS      current
		DESCRIPTION
			"Duplex."
		::= { swhPort1RemotePortStatusEntry 8 }


-- EthernetOAM(24).OAMRemoteModule(5).RemoteModuleInformation(3).Port1RemoteInformation(11).Port1RemotePortStatistics(6)

	swhPort1RemotePortStatistics
		OBJECT IDENTIFIER ::= { swhPort1RemoteInformation 6 }

	swhPort1RemotePortStatisticsModelName OBJECT-TYPE
		SYNTAX      DisplayString
		MAX-ACCESS  read-only
		STATUS      current
		DESCRIPTION
			"Model Name."
		::= { swhPort1RemotePortStatistics 2 }

	swhPort1RemotePortStatisticsClear OBJECT-TYPE
		SYNTAX      INTEGER { normal(0), clear(1) }
		MAX-ACCESS  read-write
		STATUS      current
		DESCRIPTION
			"Clear this entry."
		::= { swhPort1RemotePortStatistics 4 }

	swhPort1RemotePortStatisticsTable OBJECT-TYPE
		SYNTAX      SEQUENCE OF SwhPort1RemotePortStatisticsEntry
		MAX-ACCESS  not-accessible
		STATUS      current
		DESCRIPTION
			"Table of remote port statistics."
		::= { swhPort1RemotePortStatistics 5 }

	-- Table Entry
	swhPort1RemotePortStatisticsEntry OBJECT-TYPE
		SYNTAX      SwhPort1RemotePortStatisticsEntry
		MAX-ACCESS  not-accessible
		STATUS      current
		DESCRIPTION
			"An entry in the table, containing information about remote port statistics."
		INDEX    { swhPort1RemotePortStatisticsIndex }
		::= { swhPort1RemotePortStatisticsTable 1 }

	SwhPort1RemotePortStatisticsEntry ::=
		SEQUENCE {
			swhPort1RemotePortStatisticsIndex
				INTEGER,
			swhPort1RemotePortStatisticsNeighborPort
				DisplayString,
			swhPort1RemotePortStatisticsMediaType
				DisplayString,
			swhPort1RemotePortStatisticsBytesReceived
				DisplayString,
			swhPort1RemotePortStatisticsFramesReceived
				DisplayString,
			swhPort1RemotePortStatisticsReceivedUtilization
				DisplayString,
			swhPort1RemotePortStatisticsBytesSent
				DisplayString,
			swhPort1RemotePortStatisticsFramesSent
				DisplayString,
			swhPort1RemotePortStatisticsSentUtilization
				DisplayString,
			swhPort1RemotePortStatisticsRxTotalErrors
				DisplayString
		}

	swhPort1RemotePortStatisticsIndex OBJECT-TYPE
		SYNTAX      INTEGER (0..2147483647)
		MAX-ACCESS  read-only
		STATUS      current
		DESCRIPTION
			"A unique value for each index."
		::= { swhPort1RemotePortStatisticsEntry 1 }

	swhPort1RemotePortStatisticsNeighborPort OBJECT-TYPE
		SYNTAX      DisplayString
		MAX-ACCESS  read-only
		STATUS      current
		DESCRIPTION
			"Neighbor Port."
		::= { swhPort1RemotePortStatisticsEntry 2 }

	swhPort1RemotePortStatisticsMediaType OBJECT-TYPE
		SYNTAX      DisplayString
		MAX-ACCESS  read-only
		STATUS      current
		DESCRIPTION
			"Media Type."
		::= { swhPort1RemotePortStatisticsEntry 3 }

	swhPort1RemotePortStatisticsBytesReceived OBJECT-TYPE
		SYNTAX      DisplayString
		MAX-ACCESS  read-only
		STATUS      current
		DESCRIPTION
			"Bytes Received."
		::= { swhPort1RemotePortStatisticsEntry 4 }

	swhPort1RemotePortStatisticsFramesReceived OBJECT-TYPE
		SYNTAX      DisplayString
		MAX-ACCESS  read-only
		STATUS      current
		DESCRIPTION
			"Frames Received."
		::= { swhPort1RemotePortStatisticsEntry 5 }

	swhPort1RemotePortStatisticsReceivedUtilization OBJECT-TYPE
		SYNTAX      DisplayString
		MAX-ACCESS  read-only
		STATUS      current
		DESCRIPTION
			"Received Utilization."
		::= { swhPort1RemotePortStatisticsEntry 6 }

	swhPort1RemotePortStatisticsBytesSent OBJECT-TYPE
		SYNTAX      DisplayString
		MAX-ACCESS  read-only
		STATUS      current
		DESCRIPTION
			"Bytes Sent."
		::= { swhPort1RemotePortStatisticsEntry 7 }

	swhPort1RemotePortStatisticsFramesSent OBJECT-TYPE
		SYNTAX      DisplayString
		MAX-ACCESS  read-only
		STATUS      current
		DESCRIPTION
			"Frames Sent."
		::= { swhPort1RemotePortStatisticsEntry 8 }

	swhPort1RemotePortStatisticsSentUtilization OBJECT-TYPE
		SYNTAX      DisplayString
		MAX-ACCESS  read-only
		STATUS      current
		DESCRIPTION
			"Sent Utilization."
		::= { swhPort1RemotePortStatisticsEntry 9 }

	swhPort1RemotePortStatisticsRxTotalErrors OBJECT-TYPE
		SYNTAX      DisplayString
		MAX-ACCESS  read-only
		STATUS      current
		DESCRIPTION
			"Rx Total Errors."
		::= { swhPort1RemotePortStatisticsEntry 10 }


-- EthernetOAM(24).OAMRemoteModule(5).RemoteModuleInformation(3).Port2RemoteInformation(12)

	swhPort2RemoteInformation
		OBJECT IDENTIFIER ::= { swhRemoteModuleInformation 12 }

	swhPort2RemoteInfoTable OBJECT-TYPE
		SYNTAX      SEQUENCE OF SwhPort2RemoteInfoEntry
		MAX-ACCESS  not-accessible
		STATUS      current
		DESCRIPTION
			"Table of remote information."
		::= { swhPort2RemoteInformation 4 }

	-- Table Entry
	swhPort2RemoteInfoEntry OBJECT-TYPE
		SYNTAX      SwhPort2RemoteInfoEntry
		MAX-ACCESS  not-accessible
		STATUS      current
		DESCRIPTION
			"An entry in the table, containing information about remote information."
		INDEX    { swhPort2RemoteInfoIndex }
		::= { swhPort2RemoteInfoTable 1 }

	SwhPort2RemoteInfoEntry ::=
		SEQUENCE {
			swhPort2RemoteInfoIndex
				INTEGER,
			swhPort2RemoteInfoResult
				DisplayString
		}

	swhPort2RemoteInfoIndex OBJECT-TYPE
		SYNTAX      INTEGER (0..2147483647)
		MAX-ACCESS  read-only
		STATUS      current
		DESCRIPTION
			"A unique value for each pin."
		::= { swhPort2RemoteInfoEntry 1 }

	swhPort2RemoteInfoResult OBJECT-TYPE
		SYNTAX      DisplayString
		MAX-ACCESS  read-only
		STATUS      current
		DESCRIPTION
			"Result."
		::= { swhPort2RemoteInfoEntry 2 }


-- EthernetOAM(24).OAMRemoteModule(5).RemoteModuleInformation(3).Port2RemoteInformation(12).Port2RemotePortStatus(5)

	swhPort2RemotePortStatus
		OBJECT IDENTIFIER ::= { swhPort2RemoteInformation 5 }

	swhPort2RemotePortStatusDescription OBJECT-TYPE
		SYNTAX      DisplayString
		MAX-ACCESS  read-only
		STATUS      current
		DESCRIPTION
			"Description."
		::= { swhPort2RemotePortStatus 1 }

	swhPort2RemotePortStatusModelName OBJECT-TYPE
		SYNTAX      DisplayString
		MAX-ACCESS  read-only
		STATUS      current
		DESCRIPTION
			"Model Name."
		::= { swhPort2RemotePortStatus 2 }

	swhPort2RemotePortStatusTable OBJECT-TYPE
		SYNTAX      SEQUENCE OF SwhPort2RemotePortStatusEntry
		MAX-ACCESS  not-accessible
		STATUS      current
		DESCRIPTION
			"Table of remote port status."
		::= { swhPort2RemotePortStatus 5 }

	-- Table Entry
	swhPort2RemotePortStatusEntry OBJECT-TYPE
		SYNTAX      SwhPort2RemotePortStatusEntry
		MAX-ACCESS  not-accessible
		STATUS      current
		DESCRIPTION
			"An entry in the table, containing information about remote port status."
		INDEX    { swhPort2RemotePortStatusIndex }
		::= { swhPort2RemotePortStatusTable 1 }

	SwhPort2RemotePortStatusEntry ::=
		SEQUENCE {
			swhPort2RemotePortStatusIndex
				INTEGER,
			swhPort2RemotePortStatusNeighborPort
				DisplayString,
			swhPort2RemotePortStatusMediaType
				DisplayString,
			swhPort2RemotePortStatusPortState
				DisplayString,
			swhPort2RemotePortStatusLinkState
				DisplayString,
			swhPort2RemotePortStatusType
				DisplayString,
			swhPort2RemotePortStatusSpeed
				DisplayString,
			swhPort2RemotePortStatusDuplex
				DisplayString
		}

	swhPort2RemotePortStatusIndex OBJECT-TYPE
		SYNTAX      INTEGER (0..2147483647)
		MAX-ACCESS  read-only
		STATUS      current
		DESCRIPTION
			"A unique value for each index."
		::= { swhPort2RemotePortStatusEntry 1 }

	swhPort2RemotePortStatusNeighborPort OBJECT-TYPE
		SYNTAX      DisplayString
		MAX-ACCESS  read-only
		STATUS      current
		DESCRIPTION
			"Neighbor Port."
		::= { swhPort2RemotePortStatusEntry 2 }

	swhPort2RemotePortStatusMediaType OBJECT-TYPE
		SYNTAX      DisplayString
		MAX-ACCESS  read-only
		STATUS      current
		DESCRIPTION
			"Media Type."
		::= { swhPort2RemotePortStatusEntry 3 }

	swhPort2RemotePortStatusPortState OBJECT-TYPE
		SYNTAX      DisplayString
		MAX-ACCESS  read-only
		STATUS      current
		DESCRIPTION
			"Port State."
		::= { swhPort2RemotePortStatusEntry 4 }

	swhPort2RemotePortStatusLinkState OBJECT-TYPE
		SYNTAX      DisplayString
		MAX-ACCESS  read-only
		STATUS      current
		DESCRIPTION
			"Link State."
		::= { swhPort2RemotePortStatusEntry 5 }

	swhPort2RemotePortStatusType OBJECT-TYPE
		SYNTAX      DisplayString
		MAX-ACCESS  read-only
		STATUS      current
		DESCRIPTION
			"Type."
		::= { swhPort2RemotePortStatusEntry 6 }

	swhPort2RemotePortStatusSpeed OBJECT-TYPE
		SYNTAX      DisplayString
		MAX-ACCESS  read-only
		STATUS      current
		DESCRIPTION
			"Speed."
		::= { swhPort2RemotePortStatusEntry 7 }

	swhPort2RemotePortStatusDuplex OBJECT-TYPE
		SYNTAX      DisplayString
		MAX-ACCESS  read-only
		STATUS      current
		DESCRIPTION
			"Duplex."
		::= { swhPort2RemotePortStatusEntry 8 }


-- EthernetOAM(24).OAMRemoteModule(5).RemoteModuleInformation(3).Port2RemoteInformation(12).Port2RemotePortStatistics(6)

	swhPort2RemotePortStatistics
		OBJECT IDENTIFIER ::= { swhPort2RemoteInformation 6 }

	swhPort2RemotePortStatisticsModelName OBJECT-TYPE
		SYNTAX      DisplayString
		MAX-ACCESS  read-only
		STATUS      current
		DESCRIPTION
			"Model Name."
		::= { swhPort2RemotePortStatistics 2 }

	swhPort2RemotePortStatisticsClear OBJECT-TYPE
		SYNTAX      INTEGER { normal(0), clear(1) }
		MAX-ACCESS  read-write
		STATUS      current
		DESCRIPTION
			"Clear this entry."
		::= { swhPort2RemotePortStatistics 4 }

	swhPort2RemotePortStatisticsTable OBJECT-TYPE
		SYNTAX      SEQUENCE OF SwhPort2RemotePortStatisticsEntry
		MAX-ACCESS  not-accessible
		STATUS      current
		DESCRIPTION
			"Table of remote port statistics."
		::= { swhPort2RemotePortStatistics 5 }

	-- Table Entry
	swhPort2RemotePortStatisticsEntry OBJECT-TYPE
		SYNTAX      SwhPort2RemotePortStatisticsEntry
		MAX-ACCESS  not-accessible
		STATUS      current
		DESCRIPTION
			"An entry in the table, containing information about remote port statistics."
		INDEX    { swhPort2RemotePortStatisticsIndex }
		::= { swhPort2RemotePortStatisticsTable 1 }

	SwhPort2RemotePortStatisticsEntry ::=
		SEQUENCE {
			swhPort2RemotePortStatisticsIndex
				INTEGER,
			swhPort2RemotePortStatisticsNeighborPort
				DisplayString,
			swhPort2RemotePortStatisticsMediaType
				DisplayString,
			swhPort2RemotePortStatisticsBytesReceived
				DisplayString,
			swhPort2RemotePortStatisticsFramesReceived
				DisplayString,
			swhPort2RemotePortStatisticsReceivedUtilization
				DisplayString,
			swhPort2RemotePortStatisticsBytesSent
				DisplayString,
			swhPort2RemotePortStatisticsFramesSent
				DisplayString,
			swhPort2RemotePortStatisticsSentUtilization
				DisplayString,
			swhPort2RemotePortStatisticsRxTotalErrors
				DisplayString
		}

	swhPort2RemotePortStatisticsIndex OBJECT-TYPE
		SYNTAX      INTEGER (0..2147483647)
		MAX-ACCESS  read-only
		STATUS      current
		DESCRIPTION
			"A unique value for each index."
		::= { swhPort2RemotePortStatisticsEntry 1 }

	swhPort2RemotePortStatisticsNeighborPort OBJECT-TYPE
		SYNTAX      DisplayString
		MAX-ACCESS  read-only
		STATUS      current
		DESCRIPTION
			"Neighbor Port."
		::= { swhPort2RemotePortStatisticsEntry 2 }

	swhPort2RemotePortStatisticsMediaType OBJECT-TYPE
		SYNTAX      DisplayString
		MAX-ACCESS  read-only
		STATUS      current
		DESCRIPTION
			"Media Type."
		::= { swhPort2RemotePortStatisticsEntry 3 }

	swhPort2RemotePortStatisticsBytesReceived OBJECT-TYPE
		SYNTAX      DisplayString
		MAX-ACCESS  read-only
		STATUS      current
		DESCRIPTION
			"Bytes Received."
		::= { swhPort2RemotePortStatisticsEntry 4 }

	swhPort2RemotePortStatisticsFramesReceived OBJECT-TYPE
		SYNTAX      DisplayString
		MAX-ACCESS  read-only
		STATUS      current
		DESCRIPTION
			"Frames Received."
		::= { swhPort2RemotePortStatisticsEntry 5 }

	swhPort2RemotePortStatisticsReceivedUtilization OBJECT-TYPE
		SYNTAX      DisplayString
		MAX-ACCESS  read-only
		STATUS      current
		DESCRIPTION
			"Received Utilization."
		::= { swhPort2RemotePortStatisticsEntry 6 }

	swhPort2RemotePortStatisticsBytesSent OBJECT-TYPE
		SYNTAX      DisplayString
		MAX-ACCESS  read-only
		STATUS      current
		DESCRIPTION
			"Bytes Sent."
		::= { swhPort2RemotePortStatisticsEntry 7 }

	swhPort2RemotePortStatisticsFramesSent OBJECT-TYPE
		SYNTAX      DisplayString
		MAX-ACCESS  read-only
		STATUS      current
		DESCRIPTION
			"Frames Sent."
		::= { swhPort2RemotePortStatisticsEntry 8 }

	swhPort2RemotePortStatisticsSentUtilization OBJECT-TYPE
		SYNTAX      DisplayString
		MAX-ACCESS  read-only
		STATUS      current
		DESCRIPTION
			"Sent Utilization."
		::= { swhPort2RemotePortStatisticsEntry 9 }

	swhPort2RemotePortStatisticsRxTotalErrors OBJECT-TYPE
		SYNTAX      DisplayString
		MAX-ACCESS  read-only
		STATUS      current
		DESCRIPTION
			"Rx Total Errors."
		::= { swhPort2RemotePortStatisticsEntry 10 }


-- EthernetOAM(24).OAMRemoteModule(5).RemoteModuleInformation(3).Port3RemoteInformation(13)

	swhPort3RemoteInformation
		OBJECT IDENTIFIER ::= { swhRemoteModuleInformation 13 }

	swhPort3RemoteInfoTable OBJECT-TYPE
		SYNTAX      SEQUENCE OF SwhPort3RemoteInfoEntry
		MAX-ACCESS  not-accessible
		STATUS      current
		DESCRIPTION
			"Table of remote information."
		::= { swhPort3RemoteInformation 4 }

	-- Table Entry
	swhPort3RemoteInfoEntry OBJECT-TYPE
		SYNTAX      SwhPort3RemoteInfoEntry
		MAX-ACCESS  not-accessible
		STATUS      current
		DESCRIPTION
			"An entry in the table, containing information about remote information."
		INDEX    { swhPort3RemoteInfoIndex }
		::= { swhPort3RemoteInfoTable 1 }

	SwhPort3RemoteInfoEntry ::=
		SEQUENCE {
			swhPort3RemoteInfoIndex
				INTEGER,
			swhPort3RemoteInfoResult
				DisplayString
		}

	swhPort3RemoteInfoIndex OBJECT-TYPE
		SYNTAX      INTEGER (0..2147483647)
		MAX-ACCESS  read-only
		STATUS      current
		DESCRIPTION
			"A unique value for each pin."
		::= { swhPort3RemoteInfoEntry 1 }

	swhPort3RemoteInfoResult OBJECT-TYPE
		SYNTAX      DisplayString
		MAX-ACCESS  read-only
		STATUS      current
		DESCRIPTION
			"Result."
		::= { swhPort3RemoteInfoEntry 2 }


-- EthernetOAM(24).OAMRemoteModule(5).RemoteModuleInformation(3).Port3RemoteInformation(13).Port3RemotePortStatus(5)

	swhPort3RemotePortStatus
		OBJECT IDENTIFIER ::= { swhPort3RemoteInformation 5 }

	swhPort3RemotePortStatusDescription OBJECT-TYPE
		SYNTAX      DisplayString
		MAX-ACCESS  read-only
		STATUS      current
		DESCRIPTION
			"Description."
		::= { swhPort3RemotePortStatus 1 }

	swhPort3RemotePortStatusModelName OBJECT-TYPE
		SYNTAX      DisplayString
		MAX-ACCESS  read-only
		STATUS      current
		DESCRIPTION
			"Model Name."
		::= { swhPort3RemotePortStatus 2 }

	swhPort3RemotePortStatusTable OBJECT-TYPE
		SYNTAX      SEQUENCE OF SwhPort3RemotePortStatusEntry
		MAX-ACCESS  not-accessible
		STATUS      current
		DESCRIPTION
			"Table of remote port status."
		::= { swhPort3RemotePortStatus 5 }

	-- Table Entry
	swhPort3RemotePortStatusEntry OBJECT-TYPE
		SYNTAX      SwhPort3RemotePortStatusEntry
		MAX-ACCESS  not-accessible
		STATUS      current
		DESCRIPTION
			"An entry in the table, containing information about remote port status."
		INDEX    { swhPort3RemotePortStatusIndex }
		::= { swhPort3RemotePortStatusTable 1 }

	SwhPort3RemotePortStatusEntry ::=
		SEQUENCE {
			swhPort3RemotePortStatusIndex
				INTEGER,
			swhPort3RemotePortStatusNeighborPort
				DisplayString,
			swhPort3RemotePortStatusMediaType
				DisplayString,
			swhPort3RemotePortStatusPortState
				DisplayString,
			swhPort3RemotePortStatusLinkState
				DisplayString,
			swhPort3RemotePortStatusType
				DisplayString,
			swhPort3RemotePortStatusSpeed
				DisplayString,
			swhPort3RemotePortStatusDuplex
				DisplayString
		}

	swhPort3RemotePortStatusIndex OBJECT-TYPE
		SYNTAX      INTEGER (0..2147483647)
		MAX-ACCESS  read-only
		STATUS      current
		DESCRIPTION
			"A unique value for each index."
		::= { swhPort3RemotePortStatusEntry 1 }

	swhPort3RemotePortStatusNeighborPort OBJECT-TYPE
		SYNTAX      DisplayString
		MAX-ACCESS  read-only
		STATUS      current
		DESCRIPTION
			"Neighbor Port."
		::= { swhPort3RemotePortStatusEntry 2 }

	swhPort3RemotePortStatusMediaType OBJECT-TYPE
		SYNTAX      DisplayString
		MAX-ACCESS  read-only
		STATUS      current
		DESCRIPTION
			"Media Type."
		::= { swhPort3RemotePortStatusEntry 3 }

	swhPort3RemotePortStatusPortState OBJECT-TYPE
		SYNTAX      DisplayString
		MAX-ACCESS  read-only
		STATUS      current
		DESCRIPTION
			"Port State."
		::= { swhPort3RemotePortStatusEntry 4 }

	swhPort3RemotePortStatusLinkState OBJECT-TYPE
		SYNTAX      DisplayString
		MAX-ACCESS  read-only
		STATUS      current
		DESCRIPTION
			"Link State."
		::= { swhPort3RemotePortStatusEntry 5 }

	swhPort3RemotePortStatusType OBJECT-TYPE
		SYNTAX      DisplayString
		MAX-ACCESS  read-only
		STATUS      current
		DESCRIPTION
			"Type."
		::= { swhPort3RemotePortStatusEntry 6 }

	swhPort3RemotePortStatusSpeed OBJECT-TYPE
		SYNTAX      DisplayString
		MAX-ACCESS  read-only
		STATUS      current
		DESCRIPTION
			"Speed."
		::= { swhPort3RemotePortStatusEntry 7 }

	swhPort3RemotePortStatusDuplex OBJECT-TYPE
		SYNTAX      DisplayString
		MAX-ACCESS  read-only
		STATUS      current
		DESCRIPTION
			"Duplex."
		::= { swhPort3RemotePortStatusEntry 8 }


-- EthernetOAM(24).OAMRemoteModule(5).RemoteModuleInformation(3).Port3RemoteInformation(13).Port3RemotePortStatistics(6)

	swhPort3RemotePortStatistics
		OBJECT IDENTIFIER ::= { swhPort3RemoteInformation 6 }

	swhPort3RemotePortStatisticsModelName OBJECT-TYPE
		SYNTAX      DisplayString
		MAX-ACCESS  read-only
		STATUS      current
		DESCRIPTION
			"Model Name."
		::= { swhPort3RemotePortStatistics 2 }

	swhPort3RemotePortStatisticsClear OBJECT-TYPE
		SYNTAX      INTEGER { normal(0), clear(1) }
		MAX-ACCESS  read-write
		STATUS      current
		DESCRIPTION
			"Clear this entry."
		::= { swhPort3RemotePortStatistics 4 }

	swhPort3RemotePortStatisticsTable OBJECT-TYPE
		SYNTAX      SEQUENCE OF SwhPort3RemotePortStatisticsEntry
		MAX-ACCESS  not-accessible
		STATUS      current
		DESCRIPTION
			"Table of remote port statistics."
		::= { swhPort3RemotePortStatistics 5 }

	-- Table Entry
	swhPort3RemotePortStatisticsEntry OBJECT-TYPE
		SYNTAX      SwhPort3RemotePortStatisticsEntry
		MAX-ACCESS  not-accessible
		STATUS      current
		DESCRIPTION
			"An entry in the table, containing information about remote port statistics."
		INDEX    { swhPort3RemotePortStatisticsIndex }
		::= { swhPort3RemotePortStatisticsTable 1 }

	SwhPort3RemotePortStatisticsEntry ::=
		SEQUENCE {
			swhPort3RemotePortStatisticsIndex
				INTEGER,
			swhPort3RemotePortStatisticsNeighborPort
				DisplayString,
			swhPort3RemotePortStatisticsMediaType
				DisplayString,
			swhPort3RemotePortStatisticsBytesReceived
				DisplayString,
			swhPort3RemotePortStatisticsFramesReceived
				DisplayString,
			swhPort3RemotePortStatisticsReceivedUtilization
				DisplayString,
			swhPort3RemotePortStatisticsBytesSent
				DisplayString,
			swhPort3RemotePortStatisticsFramesSent
				DisplayString,
			swhPort3RemotePortStatisticsSentUtilization
				DisplayString,
			swhPort3RemotePortStatisticsRxTotalErrors
				DisplayString
		}

	swhPort3RemotePortStatisticsIndex OBJECT-TYPE
		SYNTAX      INTEGER (0..2147483647)
		MAX-ACCESS  read-only
		STATUS      current
		DESCRIPTION
			"A unique value for each index."
		::= { swhPort3RemotePortStatisticsEntry 1 }

	swhPort3RemotePortStatisticsNeighborPort OBJECT-TYPE
		SYNTAX      DisplayString
		MAX-ACCESS  read-only
		STATUS      current
		DESCRIPTION
			"Neighbor Port."
		::= { swhPort3RemotePortStatisticsEntry 2 }

	swhPort3RemotePortStatisticsMediaType OBJECT-TYPE
		SYNTAX      DisplayString
		MAX-ACCESS  read-only
		STATUS      current
		DESCRIPTION
			"Media Type."
		::= { swhPort3RemotePortStatisticsEntry 3 }

	swhPort3RemotePortStatisticsBytesReceived OBJECT-TYPE
		SYNTAX      DisplayString
		MAX-ACCESS  read-only
		STATUS      current
		DESCRIPTION
			"Bytes Received."
		::= { swhPort3RemotePortStatisticsEntry 4 }

	swhPort3RemotePortStatisticsFramesReceived OBJECT-TYPE
		SYNTAX      DisplayString
		MAX-ACCESS  read-only
		STATUS      current
		DESCRIPTION
			"Frames Received."
		::= { swhPort3RemotePortStatisticsEntry 5 }

	swhPort3RemotePortStatisticsReceivedUtilization OBJECT-TYPE
		SYNTAX      DisplayString
		MAX-ACCESS  read-only
		STATUS      current
		DESCRIPTION
			"Received Utilization."
		::= { swhPort3RemotePortStatisticsEntry 6 }

	swhPort3RemotePortStatisticsBytesSent OBJECT-TYPE
		SYNTAX      DisplayString
		MAX-ACCESS  read-only
		STATUS      current
		DESCRIPTION
			"Bytes Sent."
		::= { swhPort3RemotePortStatisticsEntry 7 }

	swhPort3RemotePortStatisticsFramesSent OBJECT-TYPE
		SYNTAX      DisplayString
		MAX-ACCESS  read-only
		STATUS      current
		DESCRIPTION
			"Frames Sent."
		::= { swhPort3RemotePortStatisticsEntry 8 }

	swhPort3RemotePortStatisticsSentUtilization OBJECT-TYPE
		SYNTAX      DisplayString
		MAX-ACCESS  read-only
		STATUS      current
		DESCRIPTION
			"Sent Utilization."
		::= { swhPort3RemotePortStatisticsEntry 9 }

	swhPort3RemotePortStatisticsRxTotalErrors OBJECT-TYPE
		SYNTAX      DisplayString
		MAX-ACCESS  read-only
		STATUS      current
		DESCRIPTION
			"Rx Total Errors."
		::= { swhPort3RemotePortStatisticsEntry 10 }


-- EthernetOAM(24).OAMRemoteModule(5).RemoteModuleInformation(3).Port4RemoteInformation(14)

	swhPort4RemoteInformation
		OBJECT IDENTIFIER ::= { swhRemoteModuleInformation 14 }

	swhPort4RemoteInfoTable OBJECT-TYPE
		SYNTAX      SEQUENCE OF SwhPort4RemoteInfoEntry
		MAX-ACCESS  not-accessible
		STATUS      current
		DESCRIPTION
			"Table of remote information."
		::= { swhPort4RemoteInformation 4 }

	-- Table Entry
	swhPort4RemoteInfoEntry OBJECT-TYPE
		SYNTAX      SwhPort4RemoteInfoEntry
		MAX-ACCESS  not-accessible
		STATUS      current
		DESCRIPTION
			"An entry in the table, containing information about remote information."
		INDEX    { swhPort4RemoteInfoIndex }
		::= { swhPort4RemoteInfoTable 1 }

	SwhPort4RemoteInfoEntry ::=
		SEQUENCE {
			swhPort4RemoteInfoIndex
				INTEGER,
			swhPort4RemoteInfoResult
				DisplayString
		}

	swhPort4RemoteInfoIndex OBJECT-TYPE
		SYNTAX      INTEGER (0..2147483647)
		MAX-ACCESS  read-only
		STATUS      current
		DESCRIPTION
			"A unique value for each pin."
		::= { swhPort4RemoteInfoEntry 1 }

	swhPort4RemoteInfoResult OBJECT-TYPE
		SYNTAX      DisplayString
		MAX-ACCESS  read-only
		STATUS      current
		DESCRIPTION
			"Result."
		::= { swhPort4RemoteInfoEntry 2 }


-- EthernetOAM(24).OAMRemoteModule(5).RemoteModuleInformation(3).Port4RemoteInformation(14).Port4RemotePortStatus(5)

	swhPort4RemotePortStatus
		OBJECT IDENTIFIER ::= { swhPort4RemoteInformation 5 }

	swhPort4RemotePortStatusDescription OBJECT-TYPE
		SYNTAX      DisplayString
		MAX-ACCESS  read-only
		STATUS      current
		DESCRIPTION
			"Description."
		::= { swhPort4RemotePortStatus 1 }

	swhPort4RemotePortStatusModelName OBJECT-TYPE
		SYNTAX      DisplayString
		MAX-ACCESS  read-only
		STATUS      current
		DESCRIPTION
			"Model Name."
		::= { swhPort4RemotePortStatus 2 }

	swhPort4RemotePortStatusTable OBJECT-TYPE
		SYNTAX      SEQUENCE OF SwhPort4RemotePortStatusEntry
		MAX-ACCESS  not-accessible
		STATUS      current
		DESCRIPTION
			"Table of remote port status."
		::= { swhPort4RemotePortStatus 5 }

	-- Table Entry
	swhPort4RemotePortStatusEntry OBJECT-TYPE
		SYNTAX      SwhPort4RemotePortStatusEntry
		MAX-ACCESS  not-accessible
		STATUS      current
		DESCRIPTION
			"An entry in the table, containing information about remote port status."
		INDEX    { swhPort4RemotePortStatusIndex }
		::= { swhPort4RemotePortStatusTable 1 }

	SwhPort4RemotePortStatusEntry ::=
		SEQUENCE {
			swhPort4RemotePortStatusIndex
				INTEGER,
			swhPort4RemotePortStatusNeighborPort
				DisplayString,
			swhPort4RemotePortStatusMediaType
				DisplayString,
			swhPort4RemotePortStatusPortState
				DisplayString,
			swhPort4RemotePortStatusLinkState
				DisplayString,
			swhPort4RemotePortStatusType
				DisplayString,
			swhPort4RemotePortStatusSpeed
				DisplayString,
			swhPort4RemotePortStatusDuplex
				DisplayString
		}

	swhPort4RemotePortStatusIndex OBJECT-TYPE
		SYNTAX      INTEGER (0..2147483647)
		MAX-ACCESS  read-only
		STATUS      current
		DESCRIPTION
			"A unique value for each index."
		::= { swhPort4RemotePortStatusEntry 1 }

	swhPort4RemotePortStatusNeighborPort OBJECT-TYPE
		SYNTAX      DisplayString
		MAX-ACCESS  read-only
		STATUS      current
		DESCRIPTION
			"Neighbor Port."
		::= { swhPort4RemotePortStatusEntry 2 }

	swhPort4RemotePortStatusMediaType OBJECT-TYPE
		SYNTAX      DisplayString
		MAX-ACCESS  read-only
		STATUS      current
		DESCRIPTION
			"Media Type."
		::= { swhPort4RemotePortStatusEntry 3 }

	swhPort4RemotePortStatusPortState OBJECT-TYPE
		SYNTAX      DisplayString
		MAX-ACCESS  read-only
		STATUS      current
		DESCRIPTION
			"Port State."
		::= { swhPort4RemotePortStatusEntry 4 }

	swhPort4RemotePortStatusLinkState OBJECT-TYPE
		SYNTAX      DisplayString
		MAX-ACCESS  read-only
		STATUS      current
		DESCRIPTION
			"Link State."
		::= { swhPort4RemotePortStatusEntry 5 }

	swhPort4RemotePortStatusType OBJECT-TYPE
		SYNTAX      DisplayString
		MAX-ACCESS  read-only
		STATUS      current
		DESCRIPTION
			"Type."
		::= { swhPort4RemotePortStatusEntry 6 }

	swhPort4RemotePortStatusSpeed OBJECT-TYPE
		SYNTAX      DisplayString
		MAX-ACCESS  read-only
		STATUS      current
		DESCRIPTION
			"Speed."
		::= { swhPort4RemotePortStatusEntry 7 }

	swhPort4RemotePortStatusDuplex OBJECT-TYPE
		SYNTAX      DisplayString
		MAX-ACCESS  read-only
		STATUS      current
		DESCRIPTION
			"Duplex."
		::= { swhPort4RemotePortStatusEntry 8 }


-- EthernetOAM(24).OAMRemoteModule(5).RemoteModuleInformation(3).Port4RemoteInformation(14).Port4RemotePortStatistics(6)

	swhPort4RemotePortStatistics
		OBJECT IDENTIFIER ::= { swhPort4RemoteInformation 6 }

	swhPort4RemotePortStatisticsModelName OBJECT-TYPE
		SYNTAX      DisplayString
		MAX-ACCESS  read-only
		STATUS      current
		DESCRIPTION
			"Model Name."
		::= { swhPort4RemotePortStatistics 2 }

	swhPort4RemotePortStatisticsClear OBJECT-TYPE
		SYNTAX      INTEGER { normal(0), clear(1) }
		MAX-ACCESS  read-write
		STATUS      current
		DESCRIPTION
			"Clear this entry."
		::= { swhPort4RemotePortStatistics 4 }

	swhPort4RemotePortStatisticsTable OBJECT-TYPE
		SYNTAX      SEQUENCE OF SwhPort4RemotePortStatisticsEntry
		MAX-ACCESS  not-accessible
		STATUS      current
		DESCRIPTION
			"Table of remote port statistics."
		::= { swhPort4RemotePortStatistics 5 }

	-- Table Entry
	swhPort4RemotePortStatisticsEntry OBJECT-TYPE
		SYNTAX      SwhPort4RemotePortStatisticsEntry
		MAX-ACCESS  not-accessible
		STATUS      current
		DESCRIPTION
			"An entry in the table, containing information about remote port statistics."
		INDEX    { swhPort4RemotePortStatisticsIndex }
		::= { swhPort4RemotePortStatisticsTable 1 }

	SwhPort4RemotePortStatisticsEntry ::=
		SEQUENCE {
			swhPort4RemotePortStatisticsIndex
				INTEGER,
			swhPort4RemotePortStatisticsNeighborPort
				DisplayString,
			swhPort4RemotePortStatisticsMediaType
				DisplayString,
			swhPort4RemotePortStatisticsBytesReceived
				DisplayString,
			swhPort4RemotePortStatisticsFramesReceived
				DisplayString,
			swhPort4RemotePortStatisticsReceivedUtilization
				DisplayString,
			swhPort4RemotePortStatisticsBytesSent
				DisplayString,
			swhPort4RemotePortStatisticsFramesSent
				DisplayString,
			swhPort4RemotePortStatisticsSentUtilization
				DisplayString,
			swhPort4RemotePortStatisticsRxTotalErrors
				DisplayString
		}

	swhPort4RemotePortStatisticsIndex OBJECT-TYPE
		SYNTAX      INTEGER (0..2147483647)
		MAX-ACCESS  read-only
		STATUS      current
		DESCRIPTION
			"A unique value for each index."
		::= { swhPort4RemotePortStatisticsEntry 1 }

	swhPort4RemotePortStatisticsNeighborPort OBJECT-TYPE
		SYNTAX      DisplayString
		MAX-ACCESS  read-only
		STATUS      current
		DESCRIPTION
			"Neighbor Port."
		::= { swhPort4RemotePortStatisticsEntry 2 }

	swhPort4RemotePortStatisticsMediaType OBJECT-TYPE
		SYNTAX      DisplayString
		MAX-ACCESS  read-only
		STATUS      current
		DESCRIPTION
			"Media Type."
		::= { swhPort4RemotePortStatisticsEntry 3 }

	swhPort4RemotePortStatisticsBytesReceived OBJECT-TYPE
		SYNTAX      DisplayString
		MAX-ACCESS  read-only
		STATUS      current
		DESCRIPTION
			"Bytes Received."
		::= { swhPort4RemotePortStatisticsEntry 4 }

	swhPort4RemotePortStatisticsFramesReceived OBJECT-TYPE
		SYNTAX      DisplayString
		MAX-ACCESS  read-only
		STATUS      current
		DESCRIPTION
			"Frames Received."
		::= { swhPort4RemotePortStatisticsEntry 5 }

	swhPort4RemotePortStatisticsReceivedUtilization OBJECT-TYPE
		SYNTAX      DisplayString
		MAX-ACCESS  read-only
		STATUS      current
		DESCRIPTION
			"Received Utilization."
		::= { swhPort4RemotePortStatisticsEntry 6 }

	swhPort4RemotePortStatisticsBytesSent OBJECT-TYPE
		SYNTAX      DisplayString
		MAX-ACCESS  read-only
		STATUS      current
		DESCRIPTION
			"Bytes Sent."
		::= { swhPort4RemotePortStatisticsEntry 7 }

	swhPort4RemotePortStatisticsFramesSent OBJECT-TYPE
		SYNTAX      DisplayString
		MAX-ACCESS  read-only
		STATUS      current
		DESCRIPTION
			"Frames Sent."
		::= { swhPort4RemotePortStatisticsEntry 8 }

	swhPort4RemotePortStatisticsSentUtilization OBJECT-TYPE
		SYNTAX      DisplayString
		MAX-ACCESS  read-only
		STATUS      current
		DESCRIPTION
			"Sent Utilization."
		::= { swhPort4RemotePortStatisticsEntry 9 }

	swhPort4RemotePortStatisticsRxTotalErrors OBJECT-TYPE
		SYNTAX      DisplayString
		MAX-ACCESS  read-only
		STATUS      current
		DESCRIPTION
			"Rx Total Errors."
		::= { swhPort4RemotePortStatisticsEntry 10 }


-- EthernetOAM(24).OAMRemoteModule(5).RemoteModuleInformation(3).Port5RemoteInformation(15)

	swhPort5RemoteInformation
		OBJECT IDENTIFIER ::= { swhRemoteModuleInformation 15 }

	swhPort5RemoteInfoTable OBJECT-TYPE
		SYNTAX      SEQUENCE OF SwhPort5RemoteInfoEntry
		MAX-ACCESS  not-accessible
		STATUS      current
		DESCRIPTION
			"Table of remote information."
		::= { swhPort5RemoteInformation 4 }

	-- Table Entry
	swhPort5RemoteInfoEntry OBJECT-TYPE
		SYNTAX      SwhPort5RemoteInfoEntry
		MAX-ACCESS  not-accessible
		STATUS      current
		DESCRIPTION
			"An entry in the table, containing information about remote information."
		INDEX    { swhPort5RemoteInfoIndex }
		::= { swhPort5RemoteInfoTable 1 }

	SwhPort5RemoteInfoEntry ::=
		SEQUENCE {
			swhPort5RemoteInfoIndex
				INTEGER,
			swhPort5RemoteInfoResult
				DisplayString
		}

	swhPort5RemoteInfoIndex OBJECT-TYPE
		SYNTAX      INTEGER (0..2147483647)
		MAX-ACCESS  read-only
		STATUS      current
		DESCRIPTION
			"A unique value for each pin."
		::= { swhPort5RemoteInfoEntry 1 }

	swhPort5RemoteInfoResult OBJECT-TYPE
		SYNTAX      DisplayString
		MAX-ACCESS  read-only
		STATUS      current
		DESCRIPTION
			"Result."
		::= { swhPort5RemoteInfoEntry 2 }


-- EthernetOAM(24).OAMRemoteModule(5).RemoteModuleInformation(3).Port5RemoteInformation(15).Port5RemotePortStatus(5)

	swhPort5RemotePortStatus
		OBJECT IDENTIFIER ::= { swhPort5RemoteInformation 5 }

	swhPort5RemotePortStatusDescription OBJECT-TYPE
		SYNTAX      DisplayString
		MAX-ACCESS  read-only
		STATUS      current
		DESCRIPTION
			"Description."
		::= { swhPort5RemotePortStatus 1 }

	swhPort5RemotePortStatusModelName OBJECT-TYPE
		SYNTAX      DisplayString
		MAX-ACCESS  read-only
		STATUS      current
		DESCRIPTION
			"Model Name."
		::= { swhPort5RemotePortStatus 2 }

	swhPort5RemotePortStatusTable OBJECT-TYPE
		SYNTAX      SEQUENCE OF SwhPort5RemotePortStatusEntry
		MAX-ACCESS  not-accessible
		STATUS      current
		DESCRIPTION
			"Table of remote port status."
		::= { swhPort5RemotePortStatus 5 }

	-- Table Entry
	swhPort5RemotePortStatusEntry OBJECT-TYPE
		SYNTAX      SwhPort5RemotePortStatusEntry
		MAX-ACCESS  not-accessible
		STATUS      current
		DESCRIPTION
			"An entry in the table, containing information about remote port status."
		INDEX    { swhPort5RemotePortStatusIndex }
		::= { swhPort5RemotePortStatusTable 1 }

	SwhPort5RemotePortStatusEntry ::=
		SEQUENCE {
			swhPort5RemotePortStatusIndex
				INTEGER,
			swhPort5RemotePortStatusNeighborPort
				DisplayString,
			swhPort5RemotePortStatusMediaType
				DisplayString,
			swhPort5RemotePortStatusPortState
				DisplayString,
			swhPort5RemotePortStatusLinkState
				DisplayString,
			swhPort5RemotePortStatusType
				DisplayString,
			swhPort5RemotePortStatusSpeed
				DisplayString,
			swhPort5RemotePortStatusDuplex
				DisplayString
		}

	swhPort5RemotePortStatusIndex OBJECT-TYPE
		SYNTAX      INTEGER (0..2147483647)
		MAX-ACCESS  read-only
		STATUS      current
		DESCRIPTION
			"A unique value for each index."
		::= { swhPort5RemotePortStatusEntry 1 }

	swhPort5RemotePortStatusNeighborPort OBJECT-TYPE
		SYNTAX      DisplayString
		MAX-ACCESS  read-only
		STATUS      current
		DESCRIPTION
			"Neighbor Port."
		::= { swhPort5RemotePortStatusEntry 2 }

	swhPort5RemotePortStatusMediaType OBJECT-TYPE
		SYNTAX      DisplayString
		MAX-ACCESS  read-only
		STATUS      current
		DESCRIPTION
			"Media Type."
		::= { swhPort5RemotePortStatusEntry 3 }

	swhPort5RemotePortStatusPortState OBJECT-TYPE
		SYNTAX      DisplayString
		MAX-ACCESS  read-only
		STATUS      current
		DESCRIPTION
			"Port State."
		::= { swhPort5RemotePortStatusEntry 4 }

	swhPort5RemotePortStatusLinkState OBJECT-TYPE
		SYNTAX      DisplayString
		MAX-ACCESS  read-only
		STATUS      current
		DESCRIPTION
			"Link State."
		::= { swhPort5RemotePortStatusEntry 5 }

	swhPort5RemotePortStatusType OBJECT-TYPE
		SYNTAX      DisplayString
		MAX-ACCESS  read-only
		STATUS      current
		DESCRIPTION
			"Type."
		::= { swhPort5RemotePortStatusEntry 6 }

	swhPort5RemotePortStatusSpeed OBJECT-TYPE
		SYNTAX      DisplayString
		MAX-ACCESS  read-only
		STATUS      current
		DESCRIPTION
			"Speed."
		::= { swhPort5RemotePortStatusEntry 7 }

	swhPort5RemotePortStatusDuplex OBJECT-TYPE
		SYNTAX      DisplayString
		MAX-ACCESS  read-only
		STATUS      current
		DESCRIPTION
			"Duplex."
		::= { swhPort5RemotePortStatusEntry 8 }


-- EthernetOAM(24).OAMRemoteModule(5).RemoteModuleInformation(3).Port5RemoteInformation(15).Port5RemotePortStatistics(6)

	swhPort5RemotePortStatistics
		OBJECT IDENTIFIER ::= { swhPort5RemoteInformation 6 }

	swhPort5RemotePortStatisticsModelName OBJECT-TYPE
		SYNTAX      DisplayString
		MAX-ACCESS  read-only
		STATUS      current
		DESCRIPTION
			"Model Name."
		::= { swhPort5RemotePortStatistics 2 }

	swhPort5RemotePortStatisticsClear OBJECT-TYPE
		SYNTAX      INTEGER { normal(0), clear(1) }
		MAX-ACCESS  read-write
		STATUS      current
		DESCRIPTION
			"Clear this entry."
		::= { swhPort5RemotePortStatistics 4 }

	swhPort5RemotePortStatisticsTable OBJECT-TYPE
		SYNTAX      SEQUENCE OF SwhPort5RemotePortStatisticsEntry
		MAX-ACCESS  not-accessible
		STATUS      current
		DESCRIPTION
			"Table of remote port statistics."
		::= { swhPort5RemotePortStatistics 5 }

	-- Table Entry
	swhPort5RemotePortStatisticsEntry OBJECT-TYPE
		SYNTAX      SwhPort5RemotePortStatisticsEntry
		MAX-ACCESS  not-accessible
		STATUS      current
		DESCRIPTION
			"An entry in the table, containing information about remote port statistics."
		INDEX    { swhPort5RemotePortStatisticsIndex }
		::= { swhPort5RemotePortStatisticsTable 1 }

	SwhPort5RemotePortStatisticsEntry ::=
		SEQUENCE {
			swhPort5RemotePortStatisticsIndex
				INTEGER,
			swhPort5RemotePortStatisticsNeighborPort
				DisplayString,
			swhPort5RemotePortStatisticsMediaType
				DisplayString,
			swhPort5RemotePortStatisticsBytesReceived
				DisplayString,
			swhPort5RemotePortStatisticsFramesReceived
				DisplayString,
			swhPort5RemotePortStatisticsReceivedUtilization
				DisplayString,
			swhPort5RemotePortStatisticsBytesSent
				DisplayString,
			swhPort5RemotePortStatisticsFramesSent
				DisplayString,
			swhPort5RemotePortStatisticsSentUtilization
				DisplayString,
			swhPort5RemotePortStatisticsRxTotalErrors
				DisplayString
		}

	swhPort5RemotePortStatisticsIndex OBJECT-TYPE
		SYNTAX      INTEGER (0..2147483647)
		MAX-ACCESS  read-only
		STATUS      current
		DESCRIPTION
			"A unique value for each index."
		::= { swhPort5RemotePortStatisticsEntry 1 }

	swhPort5RemotePortStatisticsNeighborPort OBJECT-TYPE
		SYNTAX      DisplayString
		MAX-ACCESS  read-only
		STATUS      current
		DESCRIPTION
			"Neighbor Port."
		::= { swhPort5RemotePortStatisticsEntry 2 }

	swhPort5RemotePortStatisticsMediaType OBJECT-TYPE
		SYNTAX      DisplayString
		MAX-ACCESS  read-only
		STATUS      current
		DESCRIPTION
			"Media Type."
		::= { swhPort5RemotePortStatisticsEntry 3 }

	swhPort5RemotePortStatisticsBytesReceived OBJECT-TYPE
		SYNTAX      DisplayString
		MAX-ACCESS  read-only
		STATUS      current
		DESCRIPTION
			"Bytes Received."
		::= { swhPort5RemotePortStatisticsEntry 4 }

	swhPort5RemotePortStatisticsFramesReceived OBJECT-TYPE
		SYNTAX      DisplayString
		MAX-ACCESS  read-only
		STATUS      current
		DESCRIPTION
			"Frames Received."
		::= { swhPort5RemotePortStatisticsEntry 5 }

	swhPort5RemotePortStatisticsReceivedUtilization OBJECT-TYPE
		SYNTAX      DisplayString
		MAX-ACCESS  read-only
		STATUS      current
		DESCRIPTION
			"Received Utilization."
		::= { swhPort5RemotePortStatisticsEntry 6 }

	swhPort5RemotePortStatisticsBytesSent OBJECT-TYPE
		SYNTAX      DisplayString
		MAX-ACCESS  read-only
		STATUS      current
		DESCRIPTION
			"Bytes Sent."
		::= { swhPort5RemotePortStatisticsEntry 7 }

	swhPort5RemotePortStatisticsFramesSent OBJECT-TYPE
		SYNTAX      DisplayString
		MAX-ACCESS  read-only
		STATUS      current
		DESCRIPTION
			"Frames Sent."
		::= { swhPort5RemotePortStatisticsEntry 8 }

	swhPort5RemotePortStatisticsSentUtilization OBJECT-TYPE
		SYNTAX      DisplayString
		MAX-ACCESS  read-only
		STATUS      current
		DESCRIPTION
			"Sent Utilization."
		::= { swhPort5RemotePortStatisticsEntry 9 }

	swhPort5RemotePortStatisticsRxTotalErrors OBJECT-TYPE
		SYNTAX      DisplayString
		MAX-ACCESS  read-only
		STATUS      current
		DESCRIPTION
			"Rx Total Errors."
		::= { swhPort5RemotePortStatisticsEntry 10 }


-- EthernetOAM(24).OAMRemoteModule(5).RemoteModuleInformation(3).Port6RemoteInformation(16)

	swhPort6RemoteInformation
		OBJECT IDENTIFIER ::= { swhRemoteModuleInformation 16 }

	swhPort6RemoteInfoTable OBJECT-TYPE
		SYNTAX      SEQUENCE OF SwhPort6RemoteInfoEntry
		MAX-ACCESS  not-accessible
		STATUS      current
		DESCRIPTION
			"Table of remote information."
		::= { swhPort6RemoteInformation 4 }

	-- Table Entry
	swhPort6RemoteInfoEntry OBJECT-TYPE
		SYNTAX      SwhPort6RemoteInfoEntry
		MAX-ACCESS  not-accessible
		STATUS      current
		DESCRIPTION
			"An entry in the table, containing information about remote information."
		INDEX    { swhPort6RemoteInfoIndex }
		::= { swhPort6RemoteInfoTable 1 }

	SwhPort6RemoteInfoEntry ::=
		SEQUENCE {
			swhPort6RemoteInfoIndex
				INTEGER,
			swhPort6RemoteInfoResult
				DisplayString
		}

	swhPort6RemoteInfoIndex OBJECT-TYPE
		SYNTAX      INTEGER (0..2147483647)
		MAX-ACCESS  read-only
		STATUS      current
		DESCRIPTION
			"A unique value for each pin."
		::= { swhPort6RemoteInfoEntry 1 }

	swhPort6RemoteInfoResult OBJECT-TYPE
		SYNTAX      DisplayString
		MAX-ACCESS  read-only
		STATUS      current
		DESCRIPTION
			"Result."
		::= { swhPort6RemoteInfoEntry 2 }


-- EthernetOAM(24).OAMRemoteModule(5).RemoteModuleInformation(3).Port6RemoteInformation(16).Port6RemotePortStatus(5)

	swhPort6RemotePortStatus
		OBJECT IDENTIFIER ::= { swhPort6RemoteInformation 5 }

	swhPort6RemotePortStatusDescription OBJECT-TYPE
		SYNTAX      DisplayString
		MAX-ACCESS  read-only
		STATUS      current
		DESCRIPTION
			"Description."
		::= { swhPort6RemotePortStatus 1 }

	swhPort6RemotePortStatusModelName OBJECT-TYPE
		SYNTAX      DisplayString
		MAX-ACCESS  read-only
		STATUS      current
		DESCRIPTION
			"Model Name."
		::= { swhPort6RemotePortStatus 2 }

	swhPort6RemotePortStatusTable OBJECT-TYPE
		SYNTAX      SEQUENCE OF SwhPort6RemotePortStatusEntry
		MAX-ACCESS  not-accessible
		STATUS      current
		DESCRIPTION
			"Table of remote port status."
		::= { swhPort6RemotePortStatus 5 }

	-- Table Entry
	swhPort6RemotePortStatusEntry OBJECT-TYPE
		SYNTAX      SwhPort6RemotePortStatusEntry
		MAX-ACCESS  not-accessible
		STATUS      current
		DESCRIPTION
			"An entry in the table, containing information about remote port status."
		INDEX    { swhPort6RemotePortStatusIndex }
		::= { swhPort6RemotePortStatusTable 1 }

	SwhPort6RemotePortStatusEntry ::=
		SEQUENCE {
			swhPort6RemotePortStatusIndex
				INTEGER,
			swhPort6RemotePortStatusNeighborPort
				DisplayString,
			swhPort6RemotePortStatusMediaType
				DisplayString,
			swhPort6RemotePortStatusPortState
				DisplayString,
			swhPort6RemotePortStatusLinkState
				DisplayString,
			swhPort6RemotePortStatusType
				DisplayString,
			swhPort6RemotePortStatusSpeed
				DisplayString,
			swhPort6RemotePortStatusDuplex
				DisplayString
		}

	swhPort6RemotePortStatusIndex OBJECT-TYPE
		SYNTAX      INTEGER (0..2147483647)
		MAX-ACCESS  read-only
		STATUS      current
		DESCRIPTION
			"A unique value for each index."
		::= { swhPort6RemotePortStatusEntry 1 }

	swhPort6RemotePortStatusNeighborPort OBJECT-TYPE
		SYNTAX      DisplayString
		MAX-ACCESS  read-only
		STATUS      current
		DESCRIPTION
			"Neighbor Port."
		::= { swhPort6RemotePortStatusEntry 2 }

	swhPort6RemotePortStatusMediaType OBJECT-TYPE
		SYNTAX      DisplayString
		MAX-ACCESS  read-only
		STATUS      current
		DESCRIPTION
			"Media Type."
		::= { swhPort6RemotePortStatusEntry 3 }

	swhPort6RemotePortStatusPortState OBJECT-TYPE
		SYNTAX      DisplayString
		MAX-ACCESS  read-only
		STATUS      current
		DESCRIPTION
			"Port State."
		::= { swhPort6RemotePortStatusEntry 4 }

	swhPort6RemotePortStatusLinkState OBJECT-TYPE
		SYNTAX      DisplayString
		MAX-ACCESS  read-only
		STATUS      current
		DESCRIPTION
			"Link State."
		::= { swhPort6RemotePortStatusEntry 5 }

	swhPort6RemotePortStatusType OBJECT-TYPE
		SYNTAX      DisplayString
		MAX-ACCESS  read-only
		STATUS      current
		DESCRIPTION
			"Type."
		::= { swhPort6RemotePortStatusEntry 6 }

	swhPort6RemotePortStatusSpeed OBJECT-TYPE
		SYNTAX      DisplayString
		MAX-ACCESS  read-only
		STATUS      current
		DESCRIPTION
			"Speed."
		::= { swhPort6RemotePortStatusEntry 7 }

	swhPort6RemotePortStatusDuplex OBJECT-TYPE
		SYNTAX      DisplayString
		MAX-ACCESS  read-only
		STATUS      current
		DESCRIPTION
			"Duplex."
		::= { swhPort6RemotePortStatusEntry 8 }


-- EthernetOAM(24).OAMRemoteModule(5).RemoteModuleInformation(3).Port6RemoteInformation(16).Port6RemotePortStatistics(6)

	swhPort6RemotePortStatistics
		OBJECT IDENTIFIER ::= { swhPort6RemoteInformation 6 }

	swhPort6RemotePortStatisticsModelName OBJECT-TYPE
		SYNTAX      DisplayString
		MAX-ACCESS  read-only
		STATUS      current
		DESCRIPTION
			"Model Name."
		::= { swhPort6RemotePortStatistics 2 }

	swhPort6RemotePortStatisticsClear OBJECT-TYPE
		SYNTAX      INTEGER { normal(0), clear(1) }
		MAX-ACCESS  read-write
		STATUS      current
		DESCRIPTION
			"Clear this entry."
		::= { swhPort6RemotePortStatistics 4 }

	swhPort6RemotePortStatisticsTable OBJECT-TYPE
		SYNTAX      SEQUENCE OF SwhPort6RemotePortStatisticsEntry
		MAX-ACCESS  not-accessible
		STATUS      current
		DESCRIPTION
			"Table of remote port statistics."
		::= { swhPort6RemotePortStatistics 5 }

	-- Table Entry
	swhPort6RemotePortStatisticsEntry OBJECT-TYPE
		SYNTAX      SwhPort6RemotePortStatisticsEntry
		MAX-ACCESS  not-accessible
		STATUS      current
		DESCRIPTION
			"An entry in the table, containing information about remote port statistics."
		INDEX    { swhPort6RemotePortStatisticsIndex }
		::= { swhPort6RemotePortStatisticsTable 1 }

	SwhPort6RemotePortStatisticsEntry ::=
		SEQUENCE {
			swhPort6RemotePortStatisticsIndex
				INTEGER,
			swhPort6RemotePortStatisticsNeighborPort
				DisplayString,
			swhPort6RemotePortStatisticsMediaType
				DisplayString,
			swhPort6RemotePortStatisticsBytesReceived
				DisplayString,
			swhPort6RemotePortStatisticsFramesReceived
				DisplayString,
			swhPort6RemotePortStatisticsReceivedUtilization
				DisplayString,
			swhPort6RemotePortStatisticsBytesSent
				DisplayString,
			swhPort6RemotePortStatisticsFramesSent
				DisplayString,
			swhPort6RemotePortStatisticsSentUtilization
				DisplayString,
			swhPort6RemotePortStatisticsRxTotalErrors
				DisplayString
		}

	swhPort6RemotePortStatisticsIndex OBJECT-TYPE
		SYNTAX      INTEGER (0..2147483647)
		MAX-ACCESS  read-only
		STATUS      current
		DESCRIPTION
			"A unique value for each index."
		::= { swhPort6RemotePortStatisticsEntry 1 }

	swhPort6RemotePortStatisticsNeighborPort OBJECT-TYPE
		SYNTAX      DisplayString
		MAX-ACCESS  read-only
		STATUS      current
		DESCRIPTION
			"Neighbor Port."
		::= { swhPort6RemotePortStatisticsEntry 2 }

	swhPort6RemotePortStatisticsMediaType OBJECT-TYPE
		SYNTAX      DisplayString
		MAX-ACCESS  read-only
		STATUS      current
		DESCRIPTION
			"Media Type."
		::= { swhPort6RemotePortStatisticsEntry 3 }

	swhPort6RemotePortStatisticsBytesReceived OBJECT-TYPE
		SYNTAX      DisplayString
		MAX-ACCESS  read-only
		STATUS      current
		DESCRIPTION
			"Bytes Received."
		::= { swhPort6RemotePortStatisticsEntry 4 }

	swhPort6RemotePortStatisticsFramesReceived OBJECT-TYPE
		SYNTAX      DisplayString
		MAX-ACCESS  read-only
		STATUS      current
		DESCRIPTION
			"Frames Received."
		::= { swhPort6RemotePortStatisticsEntry 5 }

	swhPort6RemotePortStatisticsReceivedUtilization OBJECT-TYPE
		SYNTAX      DisplayString
		MAX-ACCESS  read-only
		STATUS      current
		DESCRIPTION
			"Received Utilization."
		::= { swhPort6RemotePortStatisticsEntry 6 }

	swhPort6RemotePortStatisticsBytesSent OBJECT-TYPE
		SYNTAX      DisplayString
		MAX-ACCESS  read-only
		STATUS      current
		DESCRIPTION
			"Bytes Sent."
		::= { swhPort6RemotePortStatisticsEntry 7 }

	swhPort6RemotePortStatisticsFramesSent OBJECT-TYPE
		SYNTAX      DisplayString
		MAX-ACCESS  read-only
		STATUS      current
		DESCRIPTION
			"Frames Sent."
		::= { swhPort6RemotePortStatisticsEntry 8 }

	swhPort6RemotePortStatisticsSentUtilization OBJECT-TYPE
		SYNTAX      DisplayString
		MAX-ACCESS  read-only
		STATUS      current
		DESCRIPTION
			"Sent Utilization."
		::= { swhPort6RemotePortStatisticsEntry 9 }

	swhPort6RemotePortStatisticsRxTotalErrors OBJECT-TYPE
		SYNTAX      DisplayString
		MAX-ACCESS  read-only
		STATUS      current
		DESCRIPTION
			"Rx Total Errors."
		::= { swhPort6RemotePortStatisticsEntry 10 }


-- EthernetOAM(24).OAMRemoteModule(5).RemoteModuleInformation(3).Port7RemoteInformation(17)

	swhPort7RemoteInformation
		OBJECT IDENTIFIER ::= { swhRemoteModuleInformation 17 }

	swhPort7RemoteInfoTable OBJECT-TYPE
		SYNTAX      SEQUENCE OF SwhPort7RemoteInfoEntry
		MAX-ACCESS  not-accessible
		STATUS      current
		DESCRIPTION
			"Table of remote information."
		::= { swhPort7RemoteInformation 4 }

	-- Table Entry
	swhPort7RemoteInfoEntry OBJECT-TYPE
		SYNTAX      SwhPort7RemoteInfoEntry
		MAX-ACCESS  not-accessible
		STATUS      current
		DESCRIPTION
			"An entry in the table, containing information about remote information."
		INDEX    { swhPort7RemoteInfoIndex }
		::= { swhPort7RemoteInfoTable 1 }

	SwhPort7RemoteInfoEntry ::=
		SEQUENCE {
			swhPort7RemoteInfoIndex
				INTEGER,
			swhPort7RemoteInfoResult
				DisplayString
		}

	swhPort7RemoteInfoIndex OBJECT-TYPE
		SYNTAX      INTEGER (0..2147483647)
		MAX-ACCESS  read-only
		STATUS      current
		DESCRIPTION
			"A unique value for each pin."
		::= { swhPort7RemoteInfoEntry 1 }

	swhPort7RemoteInfoResult OBJECT-TYPE
		SYNTAX      DisplayString
		MAX-ACCESS  read-only
		STATUS      current
		DESCRIPTION
			"Result."
		::= { swhPort7RemoteInfoEntry 2 }


-- EthernetOAM(24).OAMRemoteModule(5).RemoteModuleInformation(3).Port7RemoteInformation(17).Port7RemotePortStatus(5)

	swhPort7RemotePortStatus
		OBJECT IDENTIFIER ::= { swhPort7RemoteInformation 5 }

	swhPort7RemotePortStatusDescription OBJECT-TYPE
		SYNTAX      DisplayString
		MAX-ACCESS  read-only
		STATUS      current
		DESCRIPTION
			"Description."
		::= { swhPort7RemotePortStatus 1 }

	swhPort7RemotePortStatusModelName OBJECT-TYPE
		SYNTAX      DisplayString
		MAX-ACCESS  read-only
		STATUS      current
		DESCRIPTION
			"Model Name."
		::= { swhPort7RemotePortStatus 2 }

	swhPort7RemotePortStatusTable OBJECT-TYPE
		SYNTAX      SEQUENCE OF SwhPort7RemotePortStatusEntry
		MAX-ACCESS  not-accessible
		STATUS      current
		DESCRIPTION
			"Table of remote port status."
		::= { swhPort7RemotePortStatus 5 }

	-- Table Entry
	swhPort7RemotePortStatusEntry OBJECT-TYPE
		SYNTAX      SwhPort7RemotePortStatusEntry
		MAX-ACCESS  not-accessible
		STATUS      current
		DESCRIPTION
			"An entry in the table, containing information about remote port status."
		INDEX    { swhPort7RemotePortStatusIndex }
		::= { swhPort7RemotePortStatusTable 1 }

	SwhPort7RemotePortStatusEntry ::=
		SEQUENCE {
			swhPort7RemotePortStatusIndex
				INTEGER,
			swhPort7RemotePortStatusNeighborPort
				DisplayString,
			swhPort7RemotePortStatusMediaType
				DisplayString,
			swhPort7RemotePortStatusPortState
				DisplayString,
			swhPort7RemotePortStatusLinkState
				DisplayString,
			swhPort7RemotePortStatusType
				DisplayString,
			swhPort7RemotePortStatusSpeed
				DisplayString,
			swhPort7RemotePortStatusDuplex
				DisplayString
		}

	swhPort7RemotePortStatusIndex OBJECT-TYPE
		SYNTAX      INTEGER (0..2147483647)
		MAX-ACCESS  read-only
		STATUS      current
		DESCRIPTION
			"A unique value for each index."
		::= { swhPort7RemotePortStatusEntry 1 }

	swhPort7RemotePortStatusNeighborPort OBJECT-TYPE
		SYNTAX      DisplayString
		MAX-ACCESS  read-only
		STATUS      current
		DESCRIPTION
			"Neighbor Port."
		::= { swhPort7RemotePortStatusEntry 2 }

	swhPort7RemotePortStatusMediaType OBJECT-TYPE
		SYNTAX      DisplayString
		MAX-ACCESS  read-only
		STATUS      current
		DESCRIPTION
			"Media Type."
		::= { swhPort7RemotePortStatusEntry 3 }

	swhPort7RemotePortStatusPortState OBJECT-TYPE
		SYNTAX      DisplayString
		MAX-ACCESS  read-only
		STATUS      current
		DESCRIPTION
			"Port State."
		::= { swhPort7RemotePortStatusEntry 4 }

	swhPort7RemotePortStatusLinkState OBJECT-TYPE
		SYNTAX      DisplayString
		MAX-ACCESS  read-only
		STATUS      current
		DESCRIPTION
			"Link State."
		::= { swhPort7RemotePortStatusEntry 5 }

	swhPort7RemotePortStatusType OBJECT-TYPE
		SYNTAX      DisplayString
		MAX-ACCESS  read-only
		STATUS      current
		DESCRIPTION
			"Type."
		::= { swhPort7RemotePortStatusEntry 6 }

	swhPort7RemotePortStatusSpeed OBJECT-TYPE
		SYNTAX      DisplayString
		MAX-ACCESS  read-only
		STATUS      current
		DESCRIPTION
			"Speed."
		::= { swhPort7RemotePortStatusEntry 7 }

	swhPort7RemotePortStatusDuplex OBJECT-TYPE
		SYNTAX      DisplayString
		MAX-ACCESS  read-only
		STATUS      current
		DESCRIPTION
			"Duplex."
		::= { swhPort7RemotePortStatusEntry 8 }


-- EthernetOAM(24).OAMRemoteModule(5).RemoteModuleInformation(3).Port7RemoteInformation(17).Port7RemotePortStatistics(6)

	swhPort7RemotePortStatistics
		OBJECT IDENTIFIER ::= { swhPort7RemoteInformation 6 }

	swhPort7RemotePortStatisticsModelName OBJECT-TYPE
		SYNTAX      DisplayString
		MAX-ACCESS  read-only
		STATUS      current
		DESCRIPTION
			"Model Name."
		::= { swhPort7RemotePortStatistics 2 }

	swhPort7RemotePortStatisticsClear OBJECT-TYPE
		SYNTAX      INTEGER { normal(0), clear(1) }
		MAX-ACCESS  read-write
		STATUS      current
		DESCRIPTION
			"Clear this entry."
		::= { swhPort7RemotePortStatistics 4 }

	swhPort7RemotePortStatisticsTable OBJECT-TYPE
		SYNTAX      SEQUENCE OF SwhPort7RemotePortStatisticsEntry
		MAX-ACCESS  not-accessible
		STATUS      current
		DESCRIPTION
			"Table of remote port statistics."
		::= { swhPort7RemotePortStatistics 5 }

	-- Table Entry
	swhPort7RemotePortStatisticsEntry OBJECT-TYPE
		SYNTAX      SwhPort7RemotePortStatisticsEntry
		MAX-ACCESS  not-accessible
		STATUS      current
		DESCRIPTION
			"An entry in the table, containing information about remote port statistics."
		INDEX    { swhPort7RemotePortStatisticsIndex }
		::= { swhPort7RemotePortStatisticsTable 1 }

	SwhPort7RemotePortStatisticsEntry ::=
		SEQUENCE {
			swhPort7RemotePortStatisticsIndex
				INTEGER,
			swhPort7RemotePortStatisticsNeighborPort
				DisplayString,
			swhPort7RemotePortStatisticsMediaType
				DisplayString,
			swhPort7RemotePortStatisticsBytesReceived
				DisplayString,
			swhPort7RemotePortStatisticsFramesReceived
				DisplayString,
			swhPort7RemotePortStatisticsReceivedUtilization
				DisplayString,
			swhPort7RemotePortStatisticsBytesSent
				DisplayString,
			swhPort7RemotePortStatisticsFramesSent
				DisplayString,
			swhPort7RemotePortStatisticsSentUtilization
				DisplayString,
			swhPort7RemotePortStatisticsRxTotalErrors
				DisplayString
		}

	swhPort7RemotePortStatisticsIndex OBJECT-TYPE
		SYNTAX      INTEGER (0..2147483647)
		MAX-ACCESS  read-only
		STATUS      current
		DESCRIPTION
			"A unique value for each index."
		::= { swhPort7RemotePortStatisticsEntry 1 }

	swhPort7RemotePortStatisticsNeighborPort OBJECT-TYPE
		SYNTAX      DisplayString
		MAX-ACCESS  read-only
		STATUS      current
		DESCRIPTION
			"Neighbor Port."
		::= { swhPort7RemotePortStatisticsEntry 2 }

	swhPort7RemotePortStatisticsMediaType OBJECT-TYPE
		SYNTAX      DisplayString
		MAX-ACCESS  read-only
		STATUS      current
		DESCRIPTION
			"Media Type."
		::= { swhPort7RemotePortStatisticsEntry 3 }

	swhPort7RemotePortStatisticsBytesReceived OBJECT-TYPE
		SYNTAX      DisplayString
		MAX-ACCESS  read-only
		STATUS      current
		DESCRIPTION
			"Bytes Received."
		::= { swhPort7RemotePortStatisticsEntry 4 }

	swhPort7RemotePortStatisticsFramesReceived OBJECT-TYPE
		SYNTAX      DisplayString
		MAX-ACCESS  read-only
		STATUS      current
		DESCRIPTION
			"Frames Received."
		::= { swhPort7RemotePortStatisticsEntry 5 }

	swhPort7RemotePortStatisticsReceivedUtilization OBJECT-TYPE
		SYNTAX      DisplayString
		MAX-ACCESS  read-only
		STATUS      current
		DESCRIPTION
			"Received Utilization."
		::= { swhPort7RemotePortStatisticsEntry 6 }

	swhPort7RemotePortStatisticsBytesSent OBJECT-TYPE
		SYNTAX      DisplayString
		MAX-ACCESS  read-only
		STATUS      current
		DESCRIPTION
			"Bytes Sent."
		::= { swhPort7RemotePortStatisticsEntry 7 }

	swhPort7RemotePortStatisticsFramesSent OBJECT-TYPE
		SYNTAX      DisplayString
		MAX-ACCESS  read-only
		STATUS      current
		DESCRIPTION
			"Frames Sent."
		::= { swhPort7RemotePortStatisticsEntry 8 }

	swhPort7RemotePortStatisticsSentUtilization OBJECT-TYPE
		SYNTAX      DisplayString
		MAX-ACCESS  read-only
		STATUS      current
		DESCRIPTION
			"Sent Utilization."
		::= { swhPort7RemotePortStatisticsEntry 9 }

	swhPort7RemotePortStatisticsRxTotalErrors OBJECT-TYPE
		SYNTAX      DisplayString
		MAX-ACCESS  read-only
		STATUS      current
		DESCRIPTION
			"Rx Total Errors."
		::= { swhPort7RemotePortStatisticsEntry 10 }


-- EthernetOAM(24).OAMRemoteModule(5).RemoteModuleInformation(3).Port8RemoteInformation(18)

	swhPort8RemoteInformation
		OBJECT IDENTIFIER ::= { swhRemoteModuleInformation 18 }

	swhPort8RemoteInfoTable OBJECT-TYPE
		SYNTAX      SEQUENCE OF SwhPort8RemoteInfoEntry
		MAX-ACCESS  not-accessible
		STATUS      current
		DESCRIPTION
			"Table of remote information."
		::= { swhPort8RemoteInformation 4 }

	-- Table Entry
	swhPort8RemoteInfoEntry OBJECT-TYPE
		SYNTAX      SwhPort8RemoteInfoEntry
		MAX-ACCESS  not-accessible
		STATUS      current
		DESCRIPTION
			"An entry in the table, containing information about remote information."
		INDEX    { swhPort8RemoteInfoIndex }
		::= { swhPort8RemoteInfoTable 1 }

	SwhPort8RemoteInfoEntry ::=
		SEQUENCE {
			swhPort8RemoteInfoIndex
				INTEGER,
			swhPort8RemoteInfoResult
				DisplayString
		}

	swhPort8RemoteInfoIndex OBJECT-TYPE
		SYNTAX      INTEGER (0..2147483647)
		MAX-ACCESS  read-only
		STATUS      current
		DESCRIPTION
			"A unique value for each pin."
		::= { swhPort8RemoteInfoEntry 1 }

	swhPort8RemoteInfoResult OBJECT-TYPE
		SYNTAX      DisplayString
		MAX-ACCESS  read-only
		STATUS      current
		DESCRIPTION
			"Result."
		::= { swhPort8RemoteInfoEntry 2 }


-- EthernetOAM(24).OAMRemoteModule(5).RemoteModuleInformation(3).Port8RemoteInformation(18).Port8RemotePortStatus(5)

	swhPort8RemotePortStatus
		OBJECT IDENTIFIER ::= { swhPort8RemoteInformation 5 }

	swhPort8RemotePortStatusDescription OBJECT-TYPE
		SYNTAX      DisplayString
		MAX-ACCESS  read-only
		STATUS      current
		DESCRIPTION
			"Description."
		::= { swhPort8RemotePortStatus 1 }

	swhPort8RemotePortStatusModelName OBJECT-TYPE
		SYNTAX      DisplayString
		MAX-ACCESS  read-only
		STATUS      current
		DESCRIPTION
			"Model Name."
		::= { swhPort8RemotePortStatus 2 }

	swhPort8RemotePortStatusTable OBJECT-TYPE
		SYNTAX      SEQUENCE OF SwhPort8RemotePortStatusEntry
		MAX-ACCESS  not-accessible
		STATUS      current
		DESCRIPTION
			"Table of remote port status."
		::= { swhPort8RemotePortStatus 5 }

	-- Table Entry
	swhPort8RemotePortStatusEntry OBJECT-TYPE
		SYNTAX      SwhPort8RemotePortStatusEntry
		MAX-ACCESS  not-accessible
		STATUS      current
		DESCRIPTION
			"An entry in the table, containing information about remote port status."
		INDEX    { swhPort8RemotePortStatusIndex }
		::= { swhPort8RemotePortStatusTable 1 }

	SwhPort8RemotePortStatusEntry ::=
		SEQUENCE {
			swhPort8RemotePortStatusIndex
				INTEGER,
			swhPort8RemotePortStatusNeighborPort
				DisplayString,
			swhPort8RemotePortStatusMediaType
				DisplayString,
			swhPort8RemotePortStatusPortState
				DisplayString,
			swhPort8RemotePortStatusLinkState
				DisplayString,
			swhPort8RemotePortStatusType
				DisplayString,
			swhPort8RemotePortStatusSpeed
				DisplayString,
			swhPort8RemotePortStatusDuplex
				DisplayString
		}

	swhPort8RemotePortStatusIndex OBJECT-TYPE
		SYNTAX      INTEGER (0..2147483647)
		MAX-ACCESS  read-only
		STATUS      current
		DESCRIPTION
			"A unique value for each index."
		::= { swhPort8RemotePortStatusEntry 1 }

	swhPort8RemotePortStatusNeighborPort OBJECT-TYPE
		SYNTAX      DisplayString
		MAX-ACCESS  read-only
		STATUS      current
		DESCRIPTION
			"Neighbor Port."
		::= { swhPort8RemotePortStatusEntry 2 }

	swhPort8RemotePortStatusMediaType OBJECT-TYPE
		SYNTAX      DisplayString
		MAX-ACCESS  read-only
		STATUS      current
		DESCRIPTION
			"Media Type."
		::= { swhPort8RemotePortStatusEntry 3 }

	swhPort8RemotePortStatusPortState OBJECT-TYPE
		SYNTAX      DisplayString
		MAX-ACCESS  read-only
		STATUS      current
		DESCRIPTION
			"Port State."
		::= { swhPort8RemotePortStatusEntry 4 }

	swhPort8RemotePortStatusLinkState OBJECT-TYPE
		SYNTAX      DisplayString
		MAX-ACCESS  read-only
		STATUS      current
		DESCRIPTION
			"Link State."
		::= { swhPort8RemotePortStatusEntry 5 }

	swhPort8RemotePortStatusType OBJECT-TYPE
		SYNTAX      DisplayString
		MAX-ACCESS  read-only
		STATUS      current
		DESCRIPTION
			"Type."
		::= { swhPort8RemotePortStatusEntry 6 }

	swhPort8RemotePortStatusSpeed OBJECT-TYPE
		SYNTAX      DisplayString
		MAX-ACCESS  read-only
		STATUS      current
		DESCRIPTION
			"Speed."
		::= { swhPort8RemotePortStatusEntry 7 }

	swhPort8RemotePortStatusDuplex OBJECT-TYPE
		SYNTAX      DisplayString
		MAX-ACCESS  read-only
		STATUS      current
		DESCRIPTION
			"Duplex."
		::= { swhPort8RemotePortStatusEntry 8 }


-- EthernetOAM(24).OAMRemoteModule(5).RemoteModuleInformation(3).Port8RemoteInformation(18).Port8RemotePortStatistics(6)

	swhPort8RemotePortStatistics
		OBJECT IDENTIFIER ::= { swhPort8RemoteInformation 6 }

	swhPort8RemotePortStatisticsModelName OBJECT-TYPE
		SYNTAX      DisplayString
		MAX-ACCESS  read-only
		STATUS      current
		DESCRIPTION
			"Model Name."
		::= { swhPort8RemotePortStatistics 2 }

	swhPort8RemotePortStatisticsClear OBJECT-TYPE
		SYNTAX      INTEGER { normal(0), clear(1) }
		MAX-ACCESS  read-write
		STATUS      current
		DESCRIPTION
			"Clear this entry."
		::= { swhPort8RemotePortStatistics 4 }

	swhPort8RemotePortStatisticsTable OBJECT-TYPE
		SYNTAX      SEQUENCE OF SwhPort8RemotePortStatisticsEntry
		MAX-ACCESS  not-accessible
		STATUS      current
		DESCRIPTION
			"Table of remote port statistics."
		::= { swhPort8RemotePortStatistics 5 }

	-- Table Entry
	swhPort8RemotePortStatisticsEntry OBJECT-TYPE
		SYNTAX      SwhPort8RemotePortStatisticsEntry
		MAX-ACCESS  not-accessible
		STATUS      current
		DESCRIPTION
			"An entry in the table, containing information about remote port statistics."
		INDEX    { swhPort8RemotePortStatisticsIndex }
		::= { swhPort8RemotePortStatisticsTable 1 }

	SwhPort8RemotePortStatisticsEntry ::=
		SEQUENCE {
			swhPort8RemotePortStatisticsIndex
				INTEGER,
			swhPort8RemotePortStatisticsNeighborPort
				DisplayString,
			swhPort8RemotePortStatisticsMediaType
				DisplayString,
			swhPort8RemotePortStatisticsBytesReceived
				DisplayString,
			swhPort8RemotePortStatisticsFramesReceived
				DisplayString,
			swhPort8RemotePortStatisticsReceivedUtilization
				DisplayString,
			swhPort8RemotePortStatisticsBytesSent
				DisplayString,
			swhPort8RemotePortStatisticsFramesSent
				DisplayString,
			swhPort8RemotePortStatisticsSentUtilization
				DisplayString,
			swhPort8RemotePortStatisticsRxTotalErrors
				DisplayString
		}

	swhPort8RemotePortStatisticsIndex OBJECT-TYPE
		SYNTAX      INTEGER (0..2147483647)
		MAX-ACCESS  read-only
		STATUS      current
		DESCRIPTION
			"A unique value for each index."
		::= { swhPort8RemotePortStatisticsEntry 1 }

	swhPort8RemotePortStatisticsNeighborPort OBJECT-TYPE
		SYNTAX      DisplayString
		MAX-ACCESS  read-only
		STATUS      current
		DESCRIPTION
			"Neighbor Port."
		::= { swhPort8RemotePortStatisticsEntry 2 }

	swhPort8RemotePortStatisticsMediaType OBJECT-TYPE
		SYNTAX      DisplayString
		MAX-ACCESS  read-only
		STATUS      current
		DESCRIPTION
			"Media Type."
		::= { swhPort8RemotePortStatisticsEntry 3 }

	swhPort8RemotePortStatisticsBytesReceived OBJECT-TYPE
		SYNTAX      DisplayString
		MAX-ACCESS  read-only
		STATUS      current
		DESCRIPTION
			"Bytes Received."
		::= { swhPort8RemotePortStatisticsEntry 4 }

	swhPort8RemotePortStatisticsFramesReceived OBJECT-TYPE
		SYNTAX      DisplayString
		MAX-ACCESS  read-only
		STATUS      current
		DESCRIPTION
			"Frames Received."
		::= { swhPort8RemotePortStatisticsEntry 5 }

	swhPort8RemotePortStatisticsReceivedUtilization OBJECT-TYPE
		SYNTAX      DisplayString
		MAX-ACCESS  read-only
		STATUS      current
		DESCRIPTION
			"Received Utilization."
		::= { swhPort8RemotePortStatisticsEntry 6 }

	swhPort8RemotePortStatisticsBytesSent OBJECT-TYPE
		SYNTAX      DisplayString
		MAX-ACCESS  read-only
		STATUS      current
		DESCRIPTION
			"Bytes Sent."
		::= { swhPort8RemotePortStatisticsEntry 7 }

	swhPort8RemotePortStatisticsFramesSent OBJECT-TYPE
		SYNTAX      DisplayString
		MAX-ACCESS  read-only
		STATUS      current
		DESCRIPTION
			"Frames Sent."
		::= { swhPort8RemotePortStatisticsEntry 8 }

	swhPort8RemotePortStatisticsSentUtilization OBJECT-TYPE
		SYNTAX      DisplayString
		MAX-ACCESS  read-only
		STATUS      current
		DESCRIPTION
			"Sent Utilization."
		::= { swhPort8RemotePortStatisticsEntry 9 }

	swhPort8RemotePortStatisticsRxTotalErrors OBJECT-TYPE
		SYNTAX      DisplayString
		MAX-ACCESS  read-only
		STATUS      current
		DESCRIPTION
			"Rx Total Errors."
		::= { swhPort8RemotePortStatisticsEntry 10 }


-- EthernetOAM(24).OAMRemoteModule(5).RemoteModuleInformation(3).Port9RemoteInformation(19)

	swhPort9RemoteInformation
		OBJECT IDENTIFIER ::= { swhRemoteModuleInformation 19 }

	swhPort9RemoteInfoTable OBJECT-TYPE
		SYNTAX      SEQUENCE OF SwhPort9RemoteInfoEntry
		MAX-ACCESS  not-accessible
		STATUS      current
		DESCRIPTION
			"Table of remote information."
		::= { swhPort9RemoteInformation 4 }

	-- Table Entry
	swhPort9RemoteInfoEntry OBJECT-TYPE
		SYNTAX      SwhPort9RemoteInfoEntry
		MAX-ACCESS  not-accessible
		STATUS      current
		DESCRIPTION
			"An entry in the table, containing information about remote information."
		INDEX    { swhPort9RemoteInfoIndex }
		::= { swhPort9RemoteInfoTable 1 }

	SwhPort9RemoteInfoEntry ::=
		SEQUENCE {
			swhPort9RemoteInfoIndex
				INTEGER,
			swhPort9RemoteInfoResult
				DisplayString
		}

	swhPort9RemoteInfoIndex OBJECT-TYPE
		SYNTAX      INTEGER (0..2147483647)
		MAX-ACCESS  read-only
		STATUS      current
		DESCRIPTION
			"A unique value for each pin."
		::= { swhPort9RemoteInfoEntry 1 }

	swhPort9RemoteInfoResult OBJECT-TYPE
		SYNTAX      DisplayString
		MAX-ACCESS  read-only
		STATUS      current
		DESCRIPTION
			"Result."
		::= { swhPort9RemoteInfoEntry 2 }


-- EthernetOAM(24).OAMRemoteModule(5).RemoteModuleInformation(3).Port9RemoteInformation(19).Port9RemotePortStatus(5)

	swhPort9RemotePortStatus
		OBJECT IDENTIFIER ::= { swhPort9RemoteInformation 5 }

	swhPort9RemotePortStatusDescription OBJECT-TYPE
		SYNTAX      DisplayString
		MAX-ACCESS  read-only
		STATUS      current
		DESCRIPTION
			"Description."
		::= { swhPort9RemotePortStatus 1 }

	swhPort9RemotePortStatusModelName OBJECT-TYPE
		SYNTAX      DisplayString
		MAX-ACCESS  read-only
		STATUS      current
		DESCRIPTION
			"Model Name."
		::= { swhPort9RemotePortStatus 2 }

	swhPort9RemotePortStatusTable OBJECT-TYPE
		SYNTAX      SEQUENCE OF SwhPort9RemotePortStatusEntry
		MAX-ACCESS  not-accessible
		STATUS      current
		DESCRIPTION
			"Table of remote port status."
		::= { swhPort9RemotePortStatus 5 }

	-- Table Entry
	swhPort9RemotePortStatusEntry OBJECT-TYPE
		SYNTAX      SwhPort9RemotePortStatusEntry
		MAX-ACCESS  not-accessible
		STATUS      current
		DESCRIPTION
			"An entry in the table, containing information about remote port status."
		INDEX    { swhPort9RemotePortStatusIndex }
		::= { swhPort9RemotePortStatusTable 1 }

	SwhPort9RemotePortStatusEntry ::=
		SEQUENCE {
			swhPort9RemotePortStatusIndex
				INTEGER,
			swhPort9RemotePortStatusNeighborPort
				DisplayString,
			swhPort9RemotePortStatusMediaType
				DisplayString,
			swhPort9RemotePortStatusPortState
				DisplayString,
			swhPort9RemotePortStatusLinkState
				DisplayString,
			swhPort9RemotePortStatusType
				DisplayString,
			swhPort9RemotePortStatusSpeed
				DisplayString,
			swhPort9RemotePortStatusDuplex
				DisplayString
		}

	swhPort9RemotePortStatusIndex OBJECT-TYPE
		SYNTAX      INTEGER (0..2147483647)
		MAX-ACCESS  read-only
		STATUS      current
		DESCRIPTION
			"A unique value for each index."
		::= { swhPort9RemotePortStatusEntry 1 }

	swhPort9RemotePortStatusNeighborPort OBJECT-TYPE
		SYNTAX      DisplayString
		MAX-ACCESS  read-only
		STATUS      current
		DESCRIPTION
			"Neighbor Port."
		::= { swhPort9RemotePortStatusEntry 2 }

	swhPort9RemotePortStatusMediaType OBJECT-TYPE
		SYNTAX      DisplayString
		MAX-ACCESS  read-only
		STATUS      current
		DESCRIPTION
			"Media Type."
		::= { swhPort9RemotePortStatusEntry 3 }

	swhPort9RemotePortStatusPortState OBJECT-TYPE
		SYNTAX      DisplayString
		MAX-ACCESS  read-only
		STATUS      current
		DESCRIPTION
			"Port State."
		::= { swhPort9RemotePortStatusEntry 4 }

	swhPort9RemotePortStatusLinkState OBJECT-TYPE
		SYNTAX      DisplayString
		MAX-ACCESS  read-only
		STATUS      current
		DESCRIPTION
			"Link State."
		::= { swhPort9RemotePortStatusEntry 5 }

	swhPort9RemotePortStatusType OBJECT-TYPE
		SYNTAX      DisplayString
		MAX-ACCESS  read-only
		STATUS      current
		DESCRIPTION
			"Type."
		::= { swhPort9RemotePortStatusEntry 6 }

	swhPort9RemotePortStatusSpeed OBJECT-TYPE
		SYNTAX      DisplayString
		MAX-ACCESS  read-only
		STATUS      current
		DESCRIPTION
			"Speed."
		::= { swhPort9RemotePortStatusEntry 7 }

	swhPort9RemotePortStatusDuplex OBJECT-TYPE
		SYNTAX      DisplayString
		MAX-ACCESS  read-only
		STATUS      current
		DESCRIPTION
			"Duplex."
		::= { swhPort9RemotePortStatusEntry 8 }


-- EthernetOAM(24).OAMRemoteModule(5).RemoteModuleInformation(3).Port9RemoteInformation(19).Port9RemotePortStatistics(6)

	swhPort9RemotePortStatistics
		OBJECT IDENTIFIER ::= { swhPort9RemoteInformation 6 }

	swhPort9RemotePortStatisticsModelName OBJECT-TYPE
		SYNTAX      DisplayString
		MAX-ACCESS  read-only
		STATUS      current
		DESCRIPTION
			"Model Name."
		::= { swhPort9RemotePortStatistics 2 }

	swhPort9RemotePortStatisticsClear OBJECT-TYPE
		SYNTAX      INTEGER { normal(0), clear(1) }
		MAX-ACCESS  read-write
		STATUS      current
		DESCRIPTION
			"Clear this entry."
		::= { swhPort9RemotePortStatistics 4 }

	swhPort9RemotePortStatisticsTable OBJECT-TYPE
		SYNTAX      SEQUENCE OF SwhPort9RemotePortStatisticsEntry
		MAX-ACCESS  not-accessible
		STATUS      current
		DESCRIPTION
			"Table of remote port statistics."
		::= { swhPort9RemotePortStatistics 5 }

	-- Table Entry
	swhPort9RemotePortStatisticsEntry OBJECT-TYPE
		SYNTAX      SwhPort9RemotePortStatisticsEntry
		MAX-ACCESS  not-accessible
		STATUS      current
		DESCRIPTION
			"An entry in the table, containing information about remote port statistics."
		INDEX    { swhPort9RemotePortStatisticsIndex }
		::= { swhPort9RemotePortStatisticsTable 1 }

	SwhPort9RemotePortStatisticsEntry ::=
		SEQUENCE {
			swhPort9RemotePortStatisticsIndex
				INTEGER,
			swhPort9RemotePortStatisticsNeighborPort
				DisplayString,
			swhPort9RemotePortStatisticsMediaType
				DisplayString,
			swhPort9RemotePortStatisticsBytesReceived
				DisplayString,
			swhPort9RemotePortStatisticsFramesReceived
				DisplayString,
			swhPort9RemotePortStatisticsReceivedUtilization
				DisplayString,
			swhPort9RemotePortStatisticsBytesSent
				DisplayString,
			swhPort9RemotePortStatisticsFramesSent
				DisplayString,
			swhPort9RemotePortStatisticsSentUtilization
				DisplayString,
			swhPort9RemotePortStatisticsRxTotalErrors
				DisplayString
		}

	swhPort9RemotePortStatisticsIndex OBJECT-TYPE
		SYNTAX      INTEGER (0..2147483647)
		MAX-ACCESS  read-only
		STATUS      current
		DESCRIPTION
			"A unique value for each index."
		::= { swhPort9RemotePortStatisticsEntry 1 }

	swhPort9RemotePortStatisticsNeighborPort OBJECT-TYPE
		SYNTAX      DisplayString
		MAX-ACCESS  read-only
		STATUS      current
		DESCRIPTION
			"Neighbor Port."
		::= { swhPort9RemotePortStatisticsEntry 2 }

	swhPort9RemotePortStatisticsMediaType OBJECT-TYPE
		SYNTAX      DisplayString
		MAX-ACCESS  read-only
		STATUS      current
		DESCRIPTION
			"Media Type."
		::= { swhPort9RemotePortStatisticsEntry 3 }

	swhPort9RemotePortStatisticsBytesReceived OBJECT-TYPE
		SYNTAX      DisplayString
		MAX-ACCESS  read-only
		STATUS      current
		DESCRIPTION
			"Bytes Received."
		::= { swhPort9RemotePortStatisticsEntry 4 }

	swhPort9RemotePortStatisticsFramesReceived OBJECT-TYPE
		SYNTAX      DisplayString
		MAX-ACCESS  read-only
		STATUS      current
		DESCRIPTION
			"Frames Received."
		::= { swhPort9RemotePortStatisticsEntry 5 }

	swhPort9RemotePortStatisticsReceivedUtilization OBJECT-TYPE
		SYNTAX      DisplayString
		MAX-ACCESS  read-only
		STATUS      current
		DESCRIPTION
			"Received Utilization."
		::= { swhPort9RemotePortStatisticsEntry 6 }

	swhPort9RemotePortStatisticsBytesSent OBJECT-TYPE
		SYNTAX      DisplayString
		MAX-ACCESS  read-only
		STATUS      current
		DESCRIPTION
			"Bytes Sent."
		::= { swhPort9RemotePortStatisticsEntry 7 }

	swhPort9RemotePortStatisticsFramesSent OBJECT-TYPE
		SYNTAX      DisplayString
		MAX-ACCESS  read-only
		STATUS      current
		DESCRIPTION
			"Frames Sent."
		::= { swhPort9RemotePortStatisticsEntry 8 }

	swhPort9RemotePortStatisticsSentUtilization OBJECT-TYPE
		SYNTAX      DisplayString
		MAX-ACCESS  read-only
		STATUS      current
		DESCRIPTION
			"Sent Utilization."
		::= { swhPort9RemotePortStatisticsEntry 9 }

	swhPort9RemotePortStatisticsRxTotalErrors OBJECT-TYPE
		SYNTAX      DisplayString
		MAX-ACCESS  read-only
		STATUS      current
		DESCRIPTION
			"Rx Total Errors."
		::= { swhPort9RemotePortStatisticsEntry 10 }


-- EthernetOAM(24).OAMRemoteModule(5).RemoteModuleInformation(3).Port10RemoteInformation(20)

	swhPort10RemoteInformation
		OBJECT IDENTIFIER ::= { swhRemoteModuleInformation 20 }

	swhPort10RemoteInfoTable OBJECT-TYPE
		SYNTAX      SEQUENCE OF SwhPort10RemoteInfoEntry
		MAX-ACCESS  not-accessible
		STATUS      current
		DESCRIPTION
			"Table of remote information."
		::= { swhPort10RemoteInformation 4 }

	-- Table Entry
	swhPort10RemoteInfoEntry OBJECT-TYPE
		SYNTAX      SwhPort10RemoteInfoEntry
		MAX-ACCESS  not-accessible
		STATUS      current
		DESCRIPTION
			"An entry in the table, containing information about remote information."
		INDEX    { swhPort10RemoteInfoIndex }
		::= { swhPort10RemoteInfoTable 1 }

	SwhPort10RemoteInfoEntry ::=
		SEQUENCE {
			swhPort10RemoteInfoIndex
				INTEGER,
			swhPort10RemoteInfoResult
				DisplayString
		}

	swhPort10RemoteInfoIndex OBJECT-TYPE
		SYNTAX      INTEGER (0..2147483647)
		MAX-ACCESS  read-only
		STATUS      current
		DESCRIPTION
			"A unique value for each pin."
		::= { swhPort10RemoteInfoEntry 1 }

	swhPort10RemoteInfoResult OBJECT-TYPE
		SYNTAX      DisplayString
		MAX-ACCESS  read-only
		STATUS      current
		DESCRIPTION
			"Result."
		::= { swhPort10RemoteInfoEntry 2 }


-- EthernetOAM(24).OAMRemoteModule(5).RemoteModuleInformation(3).Port10RemoteInformation(20).Port10RemotePortStatus(5)

	swhPort10RemotePortStatus
		OBJECT IDENTIFIER ::= { swhPort10RemoteInformation 5 }

	swhPort10RemotePortStatusDescription OBJECT-TYPE
		SYNTAX      DisplayString
		MAX-ACCESS  read-only
		STATUS      current
		DESCRIPTION
			"Description."
		::= { swhPort10RemotePortStatus 1 }

	swhPort10RemotePortStatusModelName OBJECT-TYPE
		SYNTAX      DisplayString
		MAX-ACCESS  read-only
		STATUS      current
		DESCRIPTION
			"Model Name."
		::= { swhPort10RemotePortStatus 2 }

	swhPort10RemotePortStatusTable OBJECT-TYPE
		SYNTAX      SEQUENCE OF SwhPort10RemotePortStatusEntry
		MAX-ACCESS  not-accessible
		STATUS      current
		DESCRIPTION
			"Table of remote port status."
		::= { swhPort10RemotePortStatus 5 }

	-- Table Entry
	swhPort10RemotePortStatusEntry OBJECT-TYPE
		SYNTAX      SwhPort10RemotePortStatusEntry
		MAX-ACCESS  not-accessible
		STATUS      current
		DESCRIPTION
			"An entry in the table, containing information about remote port status."
		INDEX    { swhPort10RemotePortStatusIndex }
		::= { swhPort10RemotePortStatusTable 1 }

	SwhPort10RemotePortStatusEntry ::=
		SEQUENCE {
			swhPort10RemotePortStatusIndex
				INTEGER,
			swhPort10RemotePortStatusNeighborPort
				DisplayString,
			swhPort10RemotePortStatusMediaType
				DisplayString,
			swhPort10RemotePortStatusPortState
				DisplayString,
			swhPort10RemotePortStatusLinkState
				DisplayString,
			swhPort10RemotePortStatusType
				DisplayString,
			swhPort10RemotePortStatusSpeed
				DisplayString,
			swhPort10RemotePortStatusDuplex
				DisplayString
		}

	swhPort10RemotePortStatusIndex OBJECT-TYPE
		SYNTAX      INTEGER (0..2147483647)
		MAX-ACCESS  read-only
		STATUS      current
		DESCRIPTION
			"A unique value for each index."
		::= { swhPort10RemotePortStatusEntry 1 }

	swhPort10RemotePortStatusNeighborPort OBJECT-TYPE
		SYNTAX      DisplayString
		MAX-ACCESS  read-only
		STATUS      current
		DESCRIPTION
			"Neighbor Port."
		::= { swhPort10RemotePortStatusEntry 2 }

	swhPort10RemotePortStatusMediaType OBJECT-TYPE
		SYNTAX      DisplayString
		MAX-ACCESS  read-only
		STATUS      current
		DESCRIPTION
			"Media Type."
		::= { swhPort10RemotePortStatusEntry 3 }

	swhPort10RemotePortStatusPortState OBJECT-TYPE
		SYNTAX      DisplayString
		MAX-ACCESS  read-only
		STATUS      current
		DESCRIPTION
			"Port State."
		::= { swhPort10RemotePortStatusEntry 4 }

	swhPort10RemotePortStatusLinkState OBJECT-TYPE
		SYNTAX      DisplayString
		MAX-ACCESS  read-only
		STATUS      current
		DESCRIPTION
			"Link State."
		::= { swhPort10RemotePortStatusEntry 5 }

	swhPort10RemotePortStatusType OBJECT-TYPE
		SYNTAX      DisplayString
		MAX-ACCESS  read-only
		STATUS      current
		DESCRIPTION
			"Type."
		::= { swhPort10RemotePortStatusEntry 6 }

	swhPort10RemotePortStatusSpeed OBJECT-TYPE
		SYNTAX      DisplayString
		MAX-ACCESS  read-only
		STATUS      current
		DESCRIPTION
			"Speed."
		::= { swhPort10RemotePortStatusEntry 7 }

	swhPort10RemotePortStatusDuplex OBJECT-TYPE
		SYNTAX      DisplayString
		MAX-ACCESS  read-only
		STATUS      current
		DESCRIPTION
			"Duplex."
		::= { swhPort10RemotePortStatusEntry 8 }


-- EthernetOAM(24).OAMRemoteModule(5).RemoteModuleInformation(3).Port10RemoteInformation(20).Port10RemotePortStatistics(6)

	swhPort10RemotePortStatistics
		OBJECT IDENTIFIER ::= { swhPort10RemoteInformation 6 }

	swhPort10RemotePortStatisticsModelName OBJECT-TYPE
		SYNTAX      DisplayString
		MAX-ACCESS  read-only
		STATUS      current
		DESCRIPTION
			"Model Name."
		::= { swhPort10RemotePortStatistics 2 }

	swhPort10RemotePortStatisticsClear OBJECT-TYPE
		SYNTAX      INTEGER { normal(0), clear(1) }
		MAX-ACCESS  read-write
		STATUS      current
		DESCRIPTION
			"Clear this entry."
		::= { swhPort10RemotePortStatistics 4 }

	swhPort10RemotePortStatisticsTable OBJECT-TYPE
		SYNTAX      SEQUENCE OF SwhPort10RemotePortStatisticsEntry
		MAX-ACCESS  not-accessible
		STATUS      current
		DESCRIPTION
			"Table of remote port statistics."
		::= { swhPort10RemotePortStatistics 5 }

	-- Table Entry
	swhPort10RemotePortStatisticsEntry OBJECT-TYPE
		SYNTAX      SwhPort10RemotePortStatisticsEntry
		MAX-ACCESS  not-accessible
		STATUS      current
		DESCRIPTION
			"An entry in the table, containing information about remote port statistics."
		INDEX    { swhPort10RemotePortStatisticsIndex }
		::= { swhPort10RemotePortStatisticsTable 1 }

	SwhPort10RemotePortStatisticsEntry ::=
		SEQUENCE {
			swhPort10RemotePortStatisticsIndex
				INTEGER,
			swhPort10RemotePortStatisticsNeighborPort
				DisplayString,
			swhPort10RemotePortStatisticsMediaType
				DisplayString,
			swhPort10RemotePortStatisticsBytesReceived
				DisplayString,
			swhPort10RemotePortStatisticsFramesReceived
				DisplayString,
			swhPort10RemotePortStatisticsReceivedUtilization
				DisplayString,
			swhPort10RemotePortStatisticsBytesSent
				DisplayString,
			swhPort10RemotePortStatisticsFramesSent
				DisplayString,
			swhPort10RemotePortStatisticsSentUtilization
				DisplayString,
			swhPort10RemotePortStatisticsRxTotalErrors
				DisplayString
		}

	swhPort10RemotePortStatisticsIndex OBJECT-TYPE
		SYNTAX      INTEGER (0..2147483647)
		MAX-ACCESS  read-only
		STATUS      current
		DESCRIPTION
			"A unique value for each index."
		::= { swhPort10RemotePortStatisticsEntry 1 }

	swhPort10RemotePortStatisticsNeighborPort OBJECT-TYPE
		SYNTAX      DisplayString
		MAX-ACCESS  read-only
		STATUS      current
		DESCRIPTION
			"Neighbor Port."
		::= { swhPort10RemotePortStatisticsEntry 2 }

	swhPort10RemotePortStatisticsMediaType OBJECT-TYPE
		SYNTAX      DisplayString
		MAX-ACCESS  read-only
		STATUS      current
		DESCRIPTION
			"Media Type."
		::= { swhPort10RemotePortStatisticsEntry 3 }

	swhPort10RemotePortStatisticsBytesReceived OBJECT-TYPE
		SYNTAX      DisplayString
		MAX-ACCESS  read-only
		STATUS      current
		DESCRIPTION
			"Bytes Received."
		::= { swhPort10RemotePortStatisticsEntry 4 }

	swhPort10RemotePortStatisticsFramesReceived OBJECT-TYPE
		SYNTAX      DisplayString
		MAX-ACCESS  read-only
		STATUS      current
		DESCRIPTION
			"Frames Received."
		::= { swhPort10RemotePortStatisticsEntry 5 }

	swhPort10RemotePortStatisticsReceivedUtilization OBJECT-TYPE
		SYNTAX      DisplayString
		MAX-ACCESS  read-only
		STATUS      current
		DESCRIPTION
			"Received Utilization."
		::= { swhPort10RemotePortStatisticsEntry 6 }

	swhPort10RemotePortStatisticsBytesSent OBJECT-TYPE
		SYNTAX      DisplayString
		MAX-ACCESS  read-only
		STATUS      current
		DESCRIPTION
			"Bytes Sent."
		::= { swhPort10RemotePortStatisticsEntry 7 }

	swhPort10RemotePortStatisticsFramesSent OBJECT-TYPE
		SYNTAX      DisplayString
		MAX-ACCESS  read-only
		STATUS      current
		DESCRIPTION
			"Frames Sent."
		::= { swhPort10RemotePortStatisticsEntry 8 }

	swhPort10RemotePortStatisticsSentUtilization OBJECT-TYPE
		SYNTAX      DisplayString
		MAX-ACCESS  read-only
		STATUS      current
		DESCRIPTION
			"Sent Utilization."
		::= { swhPort10RemotePortStatisticsEntry 9 }

	swhPort10RemotePortStatisticsRxTotalErrors OBJECT-TYPE
		SYNTAX      DisplayString
		MAX-ACCESS  read-only
		STATUS      current
		DESCRIPTION
			"Rx Total Errors."
		::= { swhPort10RemotePortStatisticsEntry 10 }


-- EthernetOAM(24).OAMRemoteModule(5).RemoteModuleInformation(3).Port11RemoteInformation(21)

	swhPort11RemoteInformation
		OBJECT IDENTIFIER ::= { swhRemoteModuleInformation 21 }

	swhPort11RemoteInfoTable OBJECT-TYPE
		SYNTAX      SEQUENCE OF SwhPort11RemoteInfoEntry
		MAX-ACCESS  not-accessible
		STATUS      current
		DESCRIPTION
			"Table of remote information."
		::= { swhPort11RemoteInformation 4 }

	-- Table Entry
	swhPort11RemoteInfoEntry OBJECT-TYPE
		SYNTAX      SwhPort11RemoteInfoEntry
		MAX-ACCESS  not-accessible
		STATUS      current
		DESCRIPTION
			"An entry in the table, containing information about remote information."
		INDEX    { swhPort11RemoteInfoIndex }
		::= { swhPort11RemoteInfoTable 1 }

	SwhPort11RemoteInfoEntry ::=
		SEQUENCE {
			swhPort11RemoteInfoIndex
				INTEGER,
			swhPort11RemoteInfoResult
				DisplayString
		}

	swhPort11RemoteInfoIndex OBJECT-TYPE
		SYNTAX      INTEGER (0..2147483647)
		MAX-ACCESS  read-only
		STATUS      current
		DESCRIPTION
			"A unique value for each pin."
		::= { swhPort11RemoteInfoEntry 1 }

	swhPort11RemoteInfoResult OBJECT-TYPE
		SYNTAX      DisplayString
		MAX-ACCESS  read-only
		STATUS      current
		DESCRIPTION
			"Result."
		::= { swhPort11RemoteInfoEntry 2 }


-- EthernetOAM(24).OAMRemoteModule(5).RemoteModuleInformation(3).Port11RemoteInformation(21).Port11RemotePortStatus(5)

	swhPort11RemotePortStatus
		OBJECT IDENTIFIER ::= { swhPort11RemoteInformation 5 }

	swhPort11RemotePortStatusDescription OBJECT-TYPE
		SYNTAX      DisplayString
		MAX-ACCESS  read-only
		STATUS      current
		DESCRIPTION
			"Description."
		::= { swhPort11RemotePortStatus 1 }

	swhPort11RemotePortStatusModelName OBJECT-TYPE
		SYNTAX      DisplayString
		MAX-ACCESS  read-only
		STATUS      current
		DESCRIPTION
			"Model Name."
		::= { swhPort11RemotePortStatus 2 }

	swhPort11RemotePortStatusTable OBJECT-TYPE
		SYNTAX      SEQUENCE OF SwhPort11RemotePortStatusEntry
		MAX-ACCESS  not-accessible
		STATUS      current
		DESCRIPTION
			"Table of remote port status."
		::= { swhPort11RemotePortStatus 5 }

	-- Table Entry
	swhPort11RemotePortStatusEntry OBJECT-TYPE
		SYNTAX      SwhPort11RemotePortStatusEntry
		MAX-ACCESS  not-accessible
		STATUS      current
		DESCRIPTION
			"An entry in the table, containing information about remote port status."
		INDEX    { swhPort11RemotePortStatusIndex }
		::= { swhPort11RemotePortStatusTable 1 }

	SwhPort11RemotePortStatusEntry ::=
		SEQUENCE {
			swhPort11RemotePortStatusIndex
				INTEGER,
			swhPort11RemotePortStatusNeighborPort
				DisplayString,
			swhPort11RemotePortStatusMediaType
				DisplayString,
			swhPort11RemotePortStatusPortState
				DisplayString,
			swhPort11RemotePortStatusLinkState
				DisplayString,
			swhPort11RemotePortStatusType
				DisplayString,
			swhPort11RemotePortStatusSpeed
				DisplayString,
			swhPort11RemotePortStatusDuplex
				DisplayString
		}

	swhPort11RemotePortStatusIndex OBJECT-TYPE
		SYNTAX      INTEGER (0..2147483647)
		MAX-ACCESS  read-only
		STATUS      current
		DESCRIPTION
			"A unique value for each index."
		::= { swhPort11RemotePortStatusEntry 1 }

	swhPort11RemotePortStatusNeighborPort OBJECT-TYPE
		SYNTAX      DisplayString
		MAX-ACCESS  read-only
		STATUS      current
		DESCRIPTION
			"Neighbor Port."
		::= { swhPort11RemotePortStatusEntry 2 }

	swhPort11RemotePortStatusMediaType OBJECT-TYPE
		SYNTAX      DisplayString
		MAX-ACCESS  read-only
		STATUS      current
		DESCRIPTION
			"Media Type."
		::= { swhPort11RemotePortStatusEntry 3 }

	swhPort11RemotePortStatusPortState OBJECT-TYPE
		SYNTAX      DisplayString
		MAX-ACCESS  read-only
		STATUS      current
		DESCRIPTION
			"Port State."
		::= { swhPort11RemotePortStatusEntry 4 }

	swhPort11RemotePortStatusLinkState OBJECT-TYPE
		SYNTAX      DisplayString
		MAX-ACCESS  read-only
		STATUS      current
		DESCRIPTION
			"Link State."
		::= { swhPort11RemotePortStatusEntry 5 }

	swhPort11RemotePortStatusType OBJECT-TYPE
		SYNTAX      DisplayString
		MAX-ACCESS  read-only
		STATUS      current
		DESCRIPTION
			"Type."
		::= { swhPort11RemotePortStatusEntry 6 }

	swhPort11RemotePortStatusSpeed OBJECT-TYPE
		SYNTAX      DisplayString
		MAX-ACCESS  read-only
		STATUS      current
		DESCRIPTION
			"Speed."
		::= { swhPort11RemotePortStatusEntry 7 }

	swhPort11RemotePortStatusDuplex OBJECT-TYPE
		SYNTAX      DisplayString
		MAX-ACCESS  read-only
		STATUS      current
		DESCRIPTION
			"Duplex."
		::= { swhPort11RemotePortStatusEntry 8 }


-- EthernetOAM(24).OAMRemoteModule(5).RemoteModuleInformation(3).Port11RemoteInformation(21).Port11RemotePortStatistics(6)

	swhPort11RemotePortStatistics
		OBJECT IDENTIFIER ::= { swhPort11RemoteInformation 6 }

	swhPort11RemotePortStatisticsModelName OBJECT-TYPE
		SYNTAX      DisplayString
		MAX-ACCESS  read-only
		STATUS      current
		DESCRIPTION
			"Model Name."
		::= { swhPort11RemotePortStatistics 2 }

	swhPort11RemotePortStatisticsClear OBJECT-TYPE
		SYNTAX      INTEGER { normal(0), clear(1) }
		MAX-ACCESS  read-write
		STATUS      current
		DESCRIPTION
			"Clear this entry."
		::= { swhPort11RemotePortStatistics 4 }

	swhPort11RemotePortStatisticsTable OBJECT-TYPE
		SYNTAX      SEQUENCE OF SwhPort11RemotePortStatisticsEntry
		MAX-ACCESS  not-accessible
		STATUS      current
		DESCRIPTION
			"Table of remote port statistics."
		::= { swhPort11RemotePortStatistics 5 }

	-- Table Entry
	swhPort11RemotePortStatisticsEntry OBJECT-TYPE
		SYNTAX      SwhPort11RemotePortStatisticsEntry
		MAX-ACCESS  not-accessible
		STATUS      current
		DESCRIPTION
			"An entry in the table, containing information about remote port statistics."
		INDEX    { swhPort11RemotePortStatisticsIndex }
		::= { swhPort11RemotePortStatisticsTable 1 }

	SwhPort11RemotePortStatisticsEntry ::=
		SEQUENCE {
			swhPort11RemotePortStatisticsIndex
				INTEGER,
			swhPort11RemotePortStatisticsNeighborPort
				DisplayString,
			swhPort11RemotePortStatisticsMediaType
				DisplayString,
			swhPort11RemotePortStatisticsBytesReceived
				DisplayString,
			swhPort11RemotePortStatisticsFramesReceived
				DisplayString,
			swhPort11RemotePortStatisticsReceivedUtilization
				DisplayString,
			swhPort11RemotePortStatisticsBytesSent
				DisplayString,
			swhPort11RemotePortStatisticsFramesSent
				DisplayString,
			swhPort11RemotePortStatisticsSentUtilization
				DisplayString,
			swhPort11RemotePortStatisticsRxTotalErrors
				DisplayString
		}

	swhPort11RemotePortStatisticsIndex OBJECT-TYPE
		SYNTAX      INTEGER (0..2147483647)
		MAX-ACCESS  read-only
		STATUS      current
		DESCRIPTION
			"A unique value for each index."
		::= { swhPort11RemotePortStatisticsEntry 1 }

	swhPort11RemotePortStatisticsNeighborPort OBJECT-TYPE
		SYNTAX      DisplayString
		MAX-ACCESS  read-only
		STATUS      current
		DESCRIPTION
			"Neighbor Port."
		::= { swhPort11RemotePortStatisticsEntry 2 }

	swhPort11RemotePortStatisticsMediaType OBJECT-TYPE
		SYNTAX      DisplayString
		MAX-ACCESS  read-only
		STATUS      current
		DESCRIPTION
			"Media Type."
		::= { swhPort11RemotePortStatisticsEntry 3 }

	swhPort11RemotePortStatisticsBytesReceived OBJECT-TYPE
		SYNTAX      DisplayString
		MAX-ACCESS  read-only
		STATUS      current
		DESCRIPTION
			"Bytes Received."
		::= { swhPort11RemotePortStatisticsEntry 4 }

	swhPort11RemotePortStatisticsFramesReceived OBJECT-TYPE
		SYNTAX      DisplayString
		MAX-ACCESS  read-only
		STATUS      current
		DESCRIPTION
			"Frames Received."
		::= { swhPort11RemotePortStatisticsEntry 5 }

	swhPort11RemotePortStatisticsReceivedUtilization OBJECT-TYPE
		SYNTAX      DisplayString
		MAX-ACCESS  read-only
		STATUS      current
		DESCRIPTION
			"Received Utilization."
		::= { swhPort11RemotePortStatisticsEntry 6 }

	swhPort11RemotePortStatisticsBytesSent OBJECT-TYPE
		SYNTAX      DisplayString
		MAX-ACCESS  read-only
		STATUS      current
		DESCRIPTION
			"Bytes Sent."
		::= { swhPort11RemotePortStatisticsEntry 7 }

	swhPort11RemotePortStatisticsFramesSent OBJECT-TYPE
		SYNTAX      DisplayString
		MAX-ACCESS  read-only
		STATUS      current
		DESCRIPTION
			"Frames Sent."
		::= { swhPort11RemotePortStatisticsEntry 8 }

	swhPort11RemotePortStatisticsSentUtilization OBJECT-TYPE
		SYNTAX      DisplayString
		MAX-ACCESS  read-only
		STATUS      current
		DESCRIPTION
			"Sent Utilization."
		::= { swhPort11RemotePortStatisticsEntry 9 }

	swhPort11RemotePortStatisticsRxTotalErrors OBJECT-TYPE
		SYNTAX      DisplayString
		MAX-ACCESS  read-only
		STATUS      current
		DESCRIPTION
			"Rx Total Errors."
		::= { swhPort11RemotePortStatisticsEntry 10 }


-- EthernetOAM(24).OAMRemoteModule(5).RemoteModuleInformation(3).Port12RemoteInformation(22)

	swhPort12RemoteInformation
		OBJECT IDENTIFIER ::= { swhRemoteModuleInformation 22 }

	swhPort12RemoteInfoTable OBJECT-TYPE
		SYNTAX      SEQUENCE OF SwhPort12RemoteInfoEntry
		MAX-ACCESS  not-accessible
		STATUS      current
		DESCRIPTION
			"Table of remote information."
		::= { swhPort12RemoteInformation 4 }

	-- Table Entry
	swhPort12RemoteInfoEntry OBJECT-TYPE
		SYNTAX      SwhPort12RemoteInfoEntry
		MAX-ACCESS  not-accessible
		STATUS      current
		DESCRIPTION
			"An entry in the table, containing information about remote information."
		INDEX    { swhPort12RemoteInfoIndex }
		::= { swhPort12RemoteInfoTable 1 }

	SwhPort12RemoteInfoEntry ::=
		SEQUENCE {
			swhPort12RemoteInfoIndex
				INTEGER,
			swhPort12RemoteInfoResult
				DisplayString
		}

	swhPort12RemoteInfoIndex OBJECT-TYPE
		SYNTAX      INTEGER (0..2147483647)
		MAX-ACCESS  read-only
		STATUS      current
		DESCRIPTION
			"A unique value for each pin."
		::= { swhPort12RemoteInfoEntry 1 }

	swhPort12RemoteInfoResult OBJECT-TYPE
		SYNTAX      DisplayString
		MAX-ACCESS  read-only
		STATUS      current
		DESCRIPTION
			"Result."
		::= { swhPort12RemoteInfoEntry 2 }


-- EthernetOAM(24).OAMRemoteModule(5).RemoteModuleInformation(3).Port12RemoteInformation(22).Port12RemotePortStatus(5)

	swhPort12RemotePortStatus
		OBJECT IDENTIFIER ::= { swhPort12RemoteInformation 5 }

	swhPort12RemotePortStatusDescription OBJECT-TYPE
		SYNTAX      DisplayString
		MAX-ACCESS  read-only
		STATUS      current
		DESCRIPTION
			"Description."
		::= { swhPort12RemotePortStatus 1 }

	swhPort12RemotePortStatusModelName OBJECT-TYPE
		SYNTAX      DisplayString
		MAX-ACCESS  read-only
		STATUS      current
		DESCRIPTION
			"Model Name."
		::= { swhPort12RemotePortStatus 2 }

	swhPort12RemotePortStatusTable OBJECT-TYPE
		SYNTAX      SEQUENCE OF SwhPort12RemotePortStatusEntry
		MAX-ACCESS  not-accessible
		STATUS      current
		DESCRIPTION
			"Table of remote port status."
		::= { swhPort12RemotePortStatus 5 }

	-- Table Entry
	swhPort12RemotePortStatusEntry OBJECT-TYPE
		SYNTAX      SwhPort12RemotePortStatusEntry
		MAX-ACCESS  not-accessible
		STATUS      current
		DESCRIPTION
			"An entry in the table, containing information about remote port status."
		INDEX    { swhPort12RemotePortStatusIndex }
		::= { swhPort12RemotePortStatusTable 1 }

	SwhPort12RemotePortStatusEntry ::=
		SEQUENCE {
			swhPort12RemotePortStatusIndex
				INTEGER,
			swhPort12RemotePortStatusNeighborPort
				DisplayString,
			swhPort12RemotePortStatusMediaType
				DisplayString,
			swhPort12RemotePortStatusPortState
				DisplayString,
			swhPort12RemotePortStatusLinkState
				DisplayString,
			swhPort12RemotePortStatusType
				DisplayString,
			swhPort12RemotePortStatusSpeed
				DisplayString,
			swhPort12RemotePortStatusDuplex
				DisplayString
		}

	swhPort12RemotePortStatusIndex OBJECT-TYPE
		SYNTAX      INTEGER (0..2147483647)
		MAX-ACCESS  read-only
		STATUS      current
		DESCRIPTION
			"A unique value for each index."
		::= { swhPort12RemotePortStatusEntry 1 }

	swhPort12RemotePortStatusNeighborPort OBJECT-TYPE
		SYNTAX      DisplayString
		MAX-ACCESS  read-only
		STATUS      current
		DESCRIPTION
			"Neighbor Port."
		::= { swhPort12RemotePortStatusEntry 2 }

	swhPort12RemotePortStatusMediaType OBJECT-TYPE
		SYNTAX      DisplayString
		MAX-ACCESS  read-only
		STATUS      current
		DESCRIPTION
			"Media Type."
		::= { swhPort12RemotePortStatusEntry 3 }

	swhPort12RemotePortStatusPortState OBJECT-TYPE
		SYNTAX      DisplayString
		MAX-ACCESS  read-only
		STATUS      current
		DESCRIPTION
			"Port State."
		::= { swhPort12RemotePortStatusEntry 4 }

	swhPort12RemotePortStatusLinkState OBJECT-TYPE
		SYNTAX      DisplayString
		MAX-ACCESS  read-only
		STATUS      current
		DESCRIPTION
			"Link State."
		::= { swhPort12RemotePortStatusEntry 5 }

	swhPort12RemotePortStatusType OBJECT-TYPE
		SYNTAX      DisplayString
		MAX-ACCESS  read-only
		STATUS      current
		DESCRIPTION
			"Type."
		::= { swhPort12RemotePortStatusEntry 6 }

	swhPort12RemotePortStatusSpeed OBJECT-TYPE
		SYNTAX      DisplayString
		MAX-ACCESS  read-only
		STATUS      current
		DESCRIPTION
			"Speed."
		::= { swhPort12RemotePortStatusEntry 7 }

	swhPort12RemotePortStatusDuplex OBJECT-TYPE
		SYNTAX      DisplayString
		MAX-ACCESS  read-only
		STATUS      current
		DESCRIPTION
			"Duplex."
		::= { swhPort12RemotePortStatusEntry 8 }


-- EthernetOAM(24).OAMRemoteModule(5).RemoteModuleInformation(3).Port12RemoteInformation(22).Port12RemotePortStatistics(6)

	swhPort12RemotePortStatistics
		OBJECT IDENTIFIER ::= { swhPort12RemoteInformation 6 }

	swhPort12RemotePortStatisticsModelName OBJECT-TYPE
		SYNTAX      DisplayString
		MAX-ACCESS  read-only
		STATUS      current
		DESCRIPTION
			"Model Name."
		::= { swhPort12RemotePortStatistics 2 }

	swhPort12RemotePortStatisticsClear OBJECT-TYPE
		SYNTAX      INTEGER { normal(0), clear(1) }
		MAX-ACCESS  read-write
		STATUS      current
		DESCRIPTION
			"Clear this entry."
		::= { swhPort12RemotePortStatistics 4 }

	swhPort12RemotePortStatisticsTable OBJECT-TYPE
		SYNTAX      SEQUENCE OF SwhPort12RemotePortStatisticsEntry
		MAX-ACCESS  not-accessible
		STATUS      current
		DESCRIPTION
			"Table of remote port statistics."
		::= { swhPort12RemotePortStatistics 5 }

	-- Table Entry
	swhPort12RemotePortStatisticsEntry OBJECT-TYPE
		SYNTAX      SwhPort12RemotePortStatisticsEntry
		MAX-ACCESS  not-accessible
		STATUS      current
		DESCRIPTION
			"An entry in the table, containing information about remote port statistics."
		INDEX    { swhPort12RemotePortStatisticsIndex }
		::= { swhPort12RemotePortStatisticsTable 1 }

	SwhPort12RemotePortStatisticsEntry ::=
		SEQUENCE {
			swhPort12RemotePortStatisticsIndex
				INTEGER,
			swhPort12RemotePortStatisticsNeighborPort
				DisplayString,
			swhPort12RemotePortStatisticsMediaType
				DisplayString,
			swhPort12RemotePortStatisticsBytesReceived
				DisplayString,
			swhPort12RemotePortStatisticsFramesReceived
				DisplayString,
			swhPort12RemotePortStatisticsReceivedUtilization
				DisplayString,
			swhPort12RemotePortStatisticsBytesSent
				DisplayString,
			swhPort12RemotePortStatisticsFramesSent
				DisplayString,
			swhPort12RemotePortStatisticsSentUtilization
				DisplayString,
			swhPort12RemotePortStatisticsRxTotalErrors
				DisplayString
		}

	swhPort12RemotePortStatisticsIndex OBJECT-TYPE
		SYNTAX      INTEGER (0..2147483647)
		MAX-ACCESS  read-only
		STATUS      current
		DESCRIPTION
			"A unique value for each index."
		::= { swhPort12RemotePortStatisticsEntry 1 }

	swhPort12RemotePortStatisticsNeighborPort OBJECT-TYPE
		SYNTAX      DisplayString
		MAX-ACCESS  read-only
		STATUS      current
		DESCRIPTION
			"Neighbor Port."
		::= { swhPort12RemotePortStatisticsEntry 2 }

	swhPort12RemotePortStatisticsMediaType OBJECT-TYPE
		SYNTAX      DisplayString
		MAX-ACCESS  read-only
		STATUS      current
		DESCRIPTION
			"Media Type."
		::= { swhPort12RemotePortStatisticsEntry 3 }

	swhPort12RemotePortStatisticsBytesReceived OBJECT-TYPE
		SYNTAX      DisplayString
		MAX-ACCESS  read-only
		STATUS      current
		DESCRIPTION
			"Bytes Received."
		::= { swhPort12RemotePortStatisticsEntry 4 }

	swhPort12RemotePortStatisticsFramesReceived OBJECT-TYPE
		SYNTAX      DisplayString
		MAX-ACCESS  read-only
		STATUS      current
		DESCRIPTION
			"Frames Received."
		::= { swhPort12RemotePortStatisticsEntry 5 }

	swhPort12RemotePortStatisticsReceivedUtilization OBJECT-TYPE
		SYNTAX      DisplayString
		MAX-ACCESS  read-only
		STATUS      current
		DESCRIPTION
			"Received Utilization."
		::= { swhPort12RemotePortStatisticsEntry 6 }

	swhPort12RemotePortStatisticsBytesSent OBJECT-TYPE
		SYNTAX      DisplayString
		MAX-ACCESS  read-only
		STATUS      current
		DESCRIPTION
			"Bytes Sent."
		::= { swhPort12RemotePortStatisticsEntry 7 }

	swhPort12RemotePortStatisticsFramesSent OBJECT-TYPE
		SYNTAX      DisplayString
		MAX-ACCESS  read-only
		STATUS      current
		DESCRIPTION
			"Frames Sent."
		::= { swhPort12RemotePortStatisticsEntry 8 }

	swhPort12RemotePortStatisticsSentUtilization OBJECT-TYPE
		SYNTAX      DisplayString
		MAX-ACCESS  read-only
		STATUS      current
		DESCRIPTION
			"Sent Utilization."
		::= { swhPort12RemotePortStatisticsEntry 9 }

	swhPort12RemotePortStatisticsRxTotalErrors OBJECT-TYPE
		SYNTAX      DisplayString
		MAX-ACCESS  read-only
		STATUS      current
		DESCRIPTION
			"Rx Total Errors."
		::= { swhPort12RemotePortStatisticsEntry 10 }


-- EthernetOAM(24).OAMRemoteModule(5).RemoteModuleDiagnostics(4)

	swhRemoteModuleDiagTable OBJECT-TYPE
		SYNTAX      SEQUENCE OF SwhRemoteModuleDiagEntry
		MAX-ACCESS  not-accessible
		STATUS      current
		DESCRIPTION
			"Table of remote module diagnostics."
		::= { swhRemoteModuleDiagnostics 5 }

	-- Table Entry
	swhRemoteModuleDiagEntry OBJECT-TYPE
		SYNTAX      SwhRemoteModuleDiagEntry
		MAX-ACCESS  not-accessible
		STATUS      current
		DESCRIPTION
			"An entry in the table, containing information about remote module diagnostics."
		INDEX    { swhRemoteModuleDiagPort }
		::= { swhRemoteModuleDiagTable 1 }

	SwhRemoteModuleDiagEntry ::=
		SEQUENCE {
			swhRemoteModuleDiagPort
				INTEGER,
			swhRemoteModuleDiagTestPackets
				DisplayString,
			swhRemoteModuleDiagStatus
				DisplayString,
			swhRemoteModuleDiagDiagnose
				INTEGER,
			swhRemoteModuleDiagReceiveFrames
				DisplayString,
			swhRemoteModuleDiagResult
				DisplayString
		}

	swhRemoteModuleDiagPort OBJECT-TYPE
		SYNTAX      INTEGER (0..2147483647)
		MAX-ACCESS  read-only
		STATUS      current
		DESCRIPTION
			"A unique value for each port."
		::= { swhRemoteModuleDiagEntry 1 }

	swhRemoteModuleDiagTestPackets OBJECT-TYPE
		SYNTAX      DisplayString
		MAX-ACCESS  read-only
		STATUS      current
		DESCRIPTION
			"Number of Test Packets."
		::= { swhRemoteModuleDiagEntry 2 }

	swhRemoteModuleDiagStatus OBJECT-TYPE
		SYNTAX      DisplayString
		MAX-ACCESS  read-only
		STATUS      current
		DESCRIPTION
			"Status."
		::= { swhRemoteModuleDiagEntry 3 }

	swhRemoteModuleDiagDiagnose OBJECT-TYPE
		SYNTAX      INTEGER { normal(0), start(1) }
		MAX-ACCESS  read-write
		STATUS      current
		DESCRIPTION
			"Diagnose."
		::= { swhRemoteModuleDiagEntry 4 }

	swhRemoteModuleDiagReceiveFrames OBJECT-TYPE
		SYNTAX      DisplayString
		MAX-ACCESS  read-only
		STATUS      current
		DESCRIPTION
			"Loopback Receive Frames."
		::= { swhRemoteModuleDiagEntry 5 }

	swhRemoteModuleDiagResult OBJECT-TYPE
		SYNTAX      DisplayString
		MAX-ACCESS  read-only
		STATUS      current
		DESCRIPTION
			"Result."
		::= { swhRemoteModuleDiagEntry 6 }

END
