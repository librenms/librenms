--
-- WIS-BRIDGE-MIB.my
-- MIB generated by MG-SOFT Visual MIB Builder Version 5.0  Build 250
-- Wednesday, December 18, 2024 at 15:37:20
--

	WIS-BRIDGE-MIB DEFINITIONS ::= BEGIN
 
		IMPORTS
			OBJECT-GROUP, MODULE-COMPLIANCE			
				FROM SNMPv2-CONF			
			TimeTicks, IpAddress, Integer32, Gauge32, Counter64, 
			OBJECT-TYPE, MODULE-IDENTITY			
				FROM SNMPv2-SMI			
			TruthValue, DisplayString, MacAddress			
				FROM SNMPv2-TC			
			wisMIB, wisBridgeGroups			
				FROM WIS-MIB;
	
	
		wisBridge MODULE-IDENTITY 
			LAST-UPDATED "202410030000Z"		-- October 03, 2024 at 00:00 GMT
			ORGANIZATION 
				"WIS Networks, Inc."
			CONTACT-INFO 
				"support@wis.com"
			DESCRIPTION 
				"The Bridge MIB module for wis Networks, Inc. entities"
			REVISION "201710030000Z"		-- October 03, 2017 at 00:00 GMT
			DESCRIPTION 
				"wisBridge revision"
			::= { wisMIB 4 }

		
	
	
--
-- Node definitions
--
	
		wisBridgeStatusGroup OBJECT-GROUP
			OBJECTS { wisStaName, wisStaSignal, wisStaNoiseFloor, wisStaDistance, wisStaCcq, 
				wisStaAmp, wisStaAmq, wisStaAmc, wisStaLastIp, wisStaTxRate, 
				wisStaRxRate, wisStaTxBytes, wisStaRxBytes, wisStaConnTime, wisStaLocalCINR, 
				wisStaTxCapacity, wisStaRxCapacity, wisStaTxAirtime, wisStaRxAirtime, wisStaTxLatency, 
				wisRadioMode, wisRadioCCode, wisRadioFreq, wisRadioDfsEnabled, wisRadioTxPower, 
				wisRadioDistance, wisRadioChainmask, wisRadioAntenna, wisRadioRssi, wisRadioRssiMgmt, 
				wisRadioRssiExt, wisWlStatSsid, wisWlStatHideSsid, wisWlStatApMac, wisWlStatSignal, 
				wisWlStatRssi, wisWlStatCcq, wisWlStatNoiseFloor, wisWlStatTxRate, wisWlStatRxRate, 
				wisWlStatSecurity, wisWlStatWdsEnabled, wisWlStatApRepeater, wisWlStatChanWidth, wisWlStatStaCount, 
				wisHostLocaltime, wisHostWirelessInfo, wisHostProductName, wisHostNetrole, wisHostCpuLoad, 
				wisHostTemperature }
			STATUS current
			DESCRIPTION 
				"Status and statistics for Wis Bridge monitoring"
			::= { wisBridgeGroups 1 }

		
		wisBridgeStatusCompliance MODULE-COMPLIANCE
			STATUS current
			DESCRIPTION 
				"The compliance statement for Wis Bridge entities."
			MODULE -- this module
				GROUP wisBridgeStatusGroup
					DESCRIPTION 
						"This group is for Ubiquiti systems."
			::= { wisBridgeGroups 2 }

		
		wisRadioTable OBJECT-TYPE
			SYNTAX SEQUENCE OF WisRadioEntry
			MAX-ACCESS not-accessible
			STATUS current
			DESCRIPTION
				"Radio status & statistics"
			::= { wisBridge 1 }

		
		wisRadioEntry OBJECT-TYPE
			SYNTAX WisRadioEntry
			MAX-ACCESS not-accessible
			STATUS current
			DESCRIPTION
				"An entry in the wisRadioTable"
			INDEX { wisRadioIndex }
			::= { wisRadioTable 1 }

		
		WisRadioEntry ::=
			SEQUENCE { 
				wisRadioIndex
					Integer32,
				wisRadioMode
					INTEGER,
				wisRadioCCode
					Integer32,
				wisRadioFreq
					Integer32,
				wisRadioDfsEnabled
					TruthValue,
				wisRadioTxPower
					Integer32,
				wisRadioDistance
					Integer32,
				wisRadioChainmask
					Integer32,
				wisRadioAntenna
					DisplayString
			 }

		wisRadioIndex OBJECT-TYPE
			SYNTAX Integer32 (1..255)
			MAX-ACCESS not-accessible
			STATUS current
			DESCRIPTION
				"Index for the wisRadioTable"
			::= { wisRadioEntry 1 }

		
		wisRadioMode OBJECT-TYPE
			SYNTAX INTEGER
				{
				sta(1),
				ap(2),
				aprepeater(3),
				apwds(4)
				}
			MAX-ACCESS read-only
			STATUS current
			DESCRIPTION
				"Radio mode"
			::= { wisRadioEntry 2 }

		
		wisRadioCCode OBJECT-TYPE
			SYNTAX Integer32
			MAX-ACCESS read-only
			STATUS current
			DESCRIPTION
				"Country code"
			::= { wisRadioEntry 3 }

		
		wisRadioFreq OBJECT-TYPE
			SYNTAX Integer32 (1..65535)
			MAX-ACCESS read-only
			STATUS current
			DESCRIPTION
				"Operating frequency"
			::= { wisRadioEntry 4 }

		
		wisRadioDfsEnabled OBJECT-TYPE
			SYNTAX TruthValue
			MAX-ACCESS read-only
			STATUS current
			DESCRIPTION
				"DFS status"
			::= { wisRadioEntry 5 }

		
		wisRadioTxPower OBJECT-TYPE
			SYNTAX Integer32 (1..65535)
			MAX-ACCESS read-only
			STATUS current
			DESCRIPTION
				"Transmit power"
			::= { wisRadioEntry 6 }

		
		wisRadioDistance OBJECT-TYPE
			SYNTAX Integer32 (1..65535)
			MAX-ACCESS read-only
			STATUS current
			DESCRIPTION
				"Distance"
			::= { wisRadioEntry 7 }

		
		wisRadioChainmask OBJECT-TYPE
			SYNTAX Integer32 (1..255)
			MAX-ACCESS read-only
			STATUS current
			DESCRIPTION
				"Chainmask"
			::= { wisRadioEntry 8 }

		
		wisRadioAntenna OBJECT-TYPE
			SYNTAX DisplayString
			MAX-ACCESS read-only
			STATUS current
			DESCRIPTION
				"Antenna"
			::= { wisRadioEntry 9 }

		
		wisRadioRssiTable OBJECT-TYPE
			SYNTAX SEQUENCE OF WisRadioRssiEntry
			MAX-ACCESS not-accessible
			STATUS current
			DESCRIPTION
				"Radio RSSI per chain"
			::= { wisBridge 2 }

		
		wisRadioRssiEntry OBJECT-TYPE
			SYNTAX WisRadioRssiEntry
			MAX-ACCESS not-accessible
			STATUS current
			DESCRIPTION
				"An entry in the wisRadioRssiTable"
			INDEX { wisRadioIndex, wisRadioRssiIndex }
			::= { wisRadioRssiTable 1 }

		
		WisRadioRssiEntry ::=
			SEQUENCE { 
				wisRadioRssiIndex
					Integer32,
				wisRadioRssi
					Integer32,
				wisRadioRssiMgmt
					Integer32,
				wisRadioRssiExt
					Integer32
			 }

		wisRadioRssiIndex OBJECT-TYPE
			SYNTAX Integer32 (1..255)
			MAX-ACCESS not-accessible
			STATUS current
			DESCRIPTION
				"Index for the wisRadioRssiTable"
			::= { wisRadioRssiEntry 1 }

		
		wisRadioRssi OBJECT-TYPE
			SYNTAX Integer32
			MAX-ACCESS read-only
			STATUS current
			DESCRIPTION
				"Data frames rssi per chain"
			::= { wisRadioRssiEntry 2 }

		
		wisRadioRssiMgmt OBJECT-TYPE
			SYNTAX Integer32
			MAX-ACCESS read-only
			STATUS current
			DESCRIPTION
				"Management frames rssi per chain"
			::= { wisRadioRssiEntry 3 }

		
		wisRadioRssiExt OBJECT-TYPE
			SYNTAX Integer32
			MAX-ACCESS read-only
			STATUS current
			DESCRIPTION
				"Extension channel rssi per chain"
			::= { wisRadioRssiEntry 4 }

		
		wisWlStatTable OBJECT-TYPE
			SYNTAX SEQUENCE OF WisWlStatEntry
			MAX-ACCESS not-accessible
			STATUS current
			DESCRIPTION
				"Wireless statistics"
			::= { wisBridge 3 }

		
		wisWlStatEntry OBJECT-TYPE
			SYNTAX WisWlStatEntry
			MAX-ACCESS not-accessible
			STATUS current
			DESCRIPTION
				"An entry in the wisWlStatTable"
			INDEX { wisWlStatIndex }
			::= { wisWlStatTable 1 }

		
		WisWlStatEntry ::=
			SEQUENCE { 
				wisWlStatIndex
					Integer32,
				wisWlStatSsid
					DisplayString,
				wisWlStatHideSsid
					TruthValue,
				wisWlStatApMac
					MacAddress,
				wisWlStatSignal
					Integer32,
				wisWlStatRssi
					Integer32,
				wisWlStatCcq
					Integer32,
				wisWlStatNoiseFloor
					Integer32,
				wisWlStatTxRate
					Integer32,
				wisWlStatRxRate
					Integer32,
				wisWlStatSecurity
					DisplayString,
				wisWlStatWdsEnabled
					TruthValue,
				wisWlStatApRepeater
					TruthValue,
				wisWlStatChanWidth
					Integer32,
				wisWlStatStaCount
					Gauge32
			 }

		wisWlStatIndex OBJECT-TYPE
			SYNTAX Integer32 (1..255)
			MAX-ACCESS not-accessible
			STATUS current
			DESCRIPTION
				"Index for the wisWlStatTable"
			::= { wisWlStatEntry 1 }

		
		wisWlStatSsid OBJECT-TYPE
			SYNTAX DisplayString
			MAX-ACCESS read-only
			STATUS current
			DESCRIPTION
				"SSID"
			::= { wisWlStatEntry 2 }

		
		wisWlStatHideSsid OBJECT-TYPE
			SYNTAX TruthValue
			MAX-ACCESS read-only
			STATUS current
			DESCRIPTION
				"Hide SSID - on/off"
			::= { wisWlStatEntry 3 }

		
		wisWlStatApMac OBJECT-TYPE
			SYNTAX MacAddress
			MAX-ACCESS read-only
			STATUS current
			DESCRIPTION
				"AP MAC address"
			::= { wisWlStatEntry 4 }

		
		wisWlStatSignal OBJECT-TYPE
			SYNTAX Integer32
			MAX-ACCESS read-only
			STATUS current
			DESCRIPTION
				"Signal strength, dBm"
			::= { wisWlStatEntry 5 }

		
		wisWlStatRssi OBJECT-TYPE
			SYNTAX Integer32
			MAX-ACCESS read-only
			STATUS current
			DESCRIPTION
				"RSSI, dBm"
			::= { wisWlStatEntry 6 }

		
		wisWlStatCcq OBJECT-TYPE
			SYNTAX Integer32
			MAX-ACCESS read-only
			STATUS current
			DESCRIPTION
				"CCQ in %"
			::= { wisWlStatEntry 7 }

		
		wisWlStatNoiseFloor OBJECT-TYPE
			SYNTAX Integer32
			MAX-ACCESS read-only
			STATUS current
			DESCRIPTION
				"Noise floor"
			::= { wisWlStatEntry 8 }

		
		wisWlStatTxRate OBJECT-TYPE
			SYNTAX Integer32
			MAX-ACCESS read-only
			STATUS current
			DESCRIPTION
				"TX rate"
			::= { wisWlStatEntry 9 }

		
		wisWlStatRxRate OBJECT-TYPE
			SYNTAX Integer32
			MAX-ACCESS read-only
			STATUS current
			DESCRIPTION
				"RX rate"
			::= { wisWlStatEntry 10 }

		
		wisWlStatSecurity OBJECT-TYPE
			SYNTAX DisplayString
			MAX-ACCESS read-only
			STATUS current
			DESCRIPTION
				"Wireless security mode"
			::= { wisWlStatEntry 11 }

		
		wisWlStatWdsEnabled OBJECT-TYPE
			SYNTAX TruthValue
			MAX-ACCESS read-only
			STATUS current
			DESCRIPTION
				"WDS - on/off"
			::= { wisWlStatEntry 12 }

		
		wisWlStatApRepeater OBJECT-TYPE
			SYNTAX TruthValue
			MAX-ACCESS read-only
			STATUS current
			DESCRIPTION
				"AP repeater - on/off"
			::= { wisWlStatEntry 13 }

		
		wisWlStatChanWidth OBJECT-TYPE
			SYNTAX Integer32
			MAX-ACCESS read-only
			STATUS current
			DESCRIPTION
				"Channel Width"
			::= { wisWlStatEntry 14 }

		
		wisWlStatStaCount OBJECT-TYPE
			SYNTAX Gauge32
			MAX-ACCESS read-only
			STATUS current
			DESCRIPTION
				"Station count"
			::= { wisWlStatEntry 15 }

		
		wisStaTable OBJECT-TYPE
			SYNTAX SEQUENCE OF WisStaEntry
			MAX-ACCESS not-accessible
			STATUS current
			DESCRIPTION
				"Station list"
			::= { wisBridge 4 }

		
		wisStaEntry OBJECT-TYPE
			SYNTAX WisStaEntry
			MAX-ACCESS not-accessible
			STATUS current
			DESCRIPTION
				"An entry in the wisStaEntry"
			INDEX { wisWlStatIndex, wisStaMac }
			::= { wisStaTable 1 }

		
		WisStaEntry ::=
			SEQUENCE { 
				wisStaMac
					MacAddress,
				wisStaName
					DisplayString,
				wisStaSignal
					Integer32,
				wisStaNoiseFloor
					Integer32,
				wisStaDistance
					Integer32,
				wisStaCcq
					Integer32,
				wisStaAmp
					Integer32,
				wisStaAmq
					Integer32,
				wisStaAmc
					Integer32,
				wisStaLastIp
					IpAddress,
				wisStaTxRate
					Integer32,
				wisStaRxRate
					Integer32,
				wisStaTxBytes
					Counter64,
				wisStaRxBytes
					Counter64,
				wisStaConnTime
					TimeTicks,
				wisStaLocalCINR
					Integer32,
				wisStaTxCapacity
					Integer32,
				wisStaRxCapacity
					Integer32,
				wisStaTxAirtime
					Integer32,
				wisStaRxAirtime
					Integer32,
				wisStaTxLatency
					Integer32
			 }

		wisStaMac OBJECT-TYPE
			SYNTAX MacAddress
			MAX-ACCESS not-accessible
			STATUS current
			DESCRIPTION
				"Station MAC address"
			::= { wisStaEntry 1 }

		
		wisStaName OBJECT-TYPE
			SYNTAX DisplayString
			MAX-ACCESS read-only
			STATUS current
			DESCRIPTION
				"Station name"
			::= { wisStaEntry 2 }

		
		wisStaSignal OBJECT-TYPE
			SYNTAX Integer32
			MAX-ACCESS read-only
			STATUS current
			DESCRIPTION
				"Signal strength, dBm"
			::= { wisStaEntry 3 }

		
		wisStaNoiseFloor OBJECT-TYPE
			SYNTAX Integer32
			MAX-ACCESS read-only
			STATUS current
			DESCRIPTION
				"Noise floor"
			::= { wisStaEntry 4 }

		
		wisStaDistance OBJECT-TYPE
			SYNTAX Integer32 (1..65535)
			MAX-ACCESS read-only
			STATUS current
			DESCRIPTION
				"Distance"
			::= { wisStaEntry 5 }

		
		wisStaCcq OBJECT-TYPE
			SYNTAX Integer32
			MAX-ACCESS read-only
			STATUS current
			DESCRIPTION
				"CCQ in %"
			::= { wisStaEntry 6 }

		
		wisStaAmp OBJECT-TYPE
			SYNTAX Integer32
			MAX-ACCESS read-only
			STATUS current
			DESCRIPTION
				"wisBridge priority"
			::= { wisStaEntry 7 }

		
		wisStaAmq OBJECT-TYPE
			SYNTAX Integer32
			MAX-ACCESS read-only
			STATUS current
			DESCRIPTION
				"wisBridge quality"
			::= { wisStaEntry 8 }

		
		wisStaAmc OBJECT-TYPE
			SYNTAX Integer32
			MAX-ACCESS read-only
			STATUS current
			DESCRIPTION
				"wisBridge capacity"
			::= { wisStaEntry 9 }

		
		wisStaLastIp OBJECT-TYPE
			SYNTAX IpAddress
			MAX-ACCESS read-only
			STATUS current
			DESCRIPTION
				"Last known IP address"
			::= { wisStaEntry 10 }

		
		wisStaTxRate OBJECT-TYPE
			SYNTAX Integer32
			MAX-ACCESS read-only
			STATUS current
			DESCRIPTION
				"TX rate"
			::= { wisStaEntry 11 }

		
		wisStaRxRate OBJECT-TYPE
			SYNTAX Integer32
			MAX-ACCESS read-only
			STATUS current
			DESCRIPTION
				"RX rate"
			::= { wisStaEntry 12 }

		
		wisStaTxBytes OBJECT-TYPE
			SYNTAX Counter64
			MAX-ACCESS read-only
			STATUS current
			DESCRIPTION
				"TX bytes"
			::= { wisStaEntry 13 }

		
		wisStaRxBytes OBJECT-TYPE
			SYNTAX Counter64
			MAX-ACCESS read-only
			STATUS current
			DESCRIPTION
				"TX rate"
			::= { wisStaEntry 14 }

		
		wisStaConnTime OBJECT-TYPE
			SYNTAX TimeTicks
			MAX-ACCESS read-only
			STATUS current
			DESCRIPTION
				"Connection Time in seconds"
			::= { wisStaEntry 15 }

		
		wisStaLocalCINR OBJECT-TYPE
			SYNTAX Integer32
			MAX-ACCESS read-only
			STATUS current
			DESCRIPTION
				"Local CINR"
			::= { wisStaEntry 16 }

		
		wisStaTxCapacity OBJECT-TYPE
			SYNTAX Integer32
			MAX-ACCESS read-only
			STATUS current
			DESCRIPTION
				"Uplink Capacity in Kbps"
			::= { wisStaEntry 17 }

		
		wisStaRxCapacity OBJECT-TYPE
			SYNTAX Integer32
			MAX-ACCESS read-only
			STATUS current
			DESCRIPTION
				"Downlink Capacity in Kbps"
			::= { wisStaEntry 18 }

		
		wisStaTxAirtime OBJECT-TYPE
			SYNTAX Integer32
			MAX-ACCESS read-only
			STATUS current
			DESCRIPTION
				"Uplink Airtime in % multiplied by 10"
			::= { wisStaEntry 19 }

		
		wisStaRxAirtime OBJECT-TYPE
			SYNTAX Integer32
			MAX-ACCESS read-only
			STATUS current
			DESCRIPTION
				"Downlink Airtime in % multiplied by 10"
			::= { wisStaEntry 20 }

		
		wisStaTxLatency OBJECT-TYPE
			SYNTAX Integer32
			MAX-ACCESS read-only
			STATUS current
			DESCRIPTION
				"Uplink Latency in milliseconds"
			::= { wisStaEntry 21 }

		
		wisHostInfo OBJECT IDENTIFIER ::= { wisBridge 5 }

		
		wisHostProductName OBJECT-TYPE
			SYNTAX DisplayString
			MAX-ACCESS read-only
			STATUS current
			DESCRIPTION
				"Product Name"
			::= { wisHostInfo 1 }

		
		wisHostWirelessInfo OBJECT-TYPE
			SYNTAX DisplayString
			MAX-ACCESS read-only
			STATUS current
			DESCRIPTION
				"Wireless Info"
			::= { wisHostInfo 2 }

		
		wisHostCpuLoad OBJECT-TYPE
			SYNTAX Integer32 (0..65535)
			MAX-ACCESS read-only
			STATUS current
			DESCRIPTION
				"Host CPU load"
			::= { wisHostInfo 3 }

		
		wisHostTemperature OBJECT-TYPE
			SYNTAX Integer32 (0..255)
			MAX-ACCESS read-only
			STATUS current
			DESCRIPTION
				"Host system temperature"
			::= { wisHostInfo 4 }

		
		wisHostLocaltime OBJECT-TYPE
			SYNTAX DisplayString
			MAX-ACCESS read-only
			STATUS current
			DESCRIPTION
				"Host local time"
			::= { wisHostInfo 5 }

		
		wisHostNetrole OBJECT-TYPE
			SYNTAX INTEGER
				{
				unknown(0),
				bridge(1),
				router(2),
				soho(3)
				}
			MAX-ACCESS read-only
			STATUS current
			DESCRIPTION
				"Radio mode"
			::= { wisHostInfo 6 }

		
	
	END

--
-- WIS-BRIDGE-MIB.my
--
