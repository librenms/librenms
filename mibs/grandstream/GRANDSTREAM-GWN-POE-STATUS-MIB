GRANDSTREAM-GWN-POE-STATUS-MIB DEFINITIONS ::= BEGIN

  IMPORTS
      enterprises, Integer32, OBJECT-TYPE
          FROM SNMPv2-SMI;

  grandstream  OBJECT IDENTIFIER ::= { enterprises 42397 }
  gwnProducts  OBJECT IDENTIFIER ::= { grandstream 1 }
  gwnSwitchMIB OBJECT IDENTIFIER ::= { gwnProducts 4 }
  gwnPoeExt    OBJECT IDENTIFIER ::= { gwnSwitchMIB 8 }
  gwnPoeStatus OBJECT IDENTIFIER ::= { gwnPoeExt 3 }

  gwnPoeInput  OBJECT IDENTIFIER ::= { gwnPoeStatus 1 }

  gwnPoeInputVoltage OBJECT-TYPE
      SYNTAX      Integer32
      MAX-ACCESS  read-only
      STATUS      current
      DESCRIPTION "PoE input supply voltage in millivolts."
      ::= { gwnPoeInput 1 }

  gwnPoePortTable OBJECT-TYPE
      SYNTAX      SEQUENCE OF GwnPoePortEntry
      MAX-ACCESS  not-accessible
      STATUS      current
      DESCRIPTION "PoE per-port status table."
      ::= { gwnPoeStatus 3 }

  gwnPoePortEntry OBJECT-TYPE
      SYNTAX      GwnPoePortEntry
      MAX-ACCESS  not-accessible
      STATUS      current
      DESCRIPTION "PoE port entry."
      INDEX { gwnPoePortIndex }
      ::= { gwnPoePortTable 1 }

  GwnPoePortEntry ::= SEQUENCE {
      gwnPoePortIndex   Integer32,
      gwnPoePortVoltage Integer32,
      gwnPoePortPower   Integer32
  }

  gwnPoePortIndex OBJECT-TYPE
      SYNTAX      Integer32 (1..16)
      MAX-ACCESS  not-accessible
      STATUS      current
      DESCRIPTION "PoE port number."
      ::= { gwnPoePortEntry 1 }

  gwnPoePortVoltage OBJECT-TYPE
      SYNTAX      Integer32
      MAX-ACCESS  read-only
      STATUS      current
      DESCRIPTION "PoE port output voltage in millivolts."
      ::= { gwnPoePortEntry 2 }

  gwnPoePortPower OBJECT-TYPE
      SYNTAX      Integer32
      MAX-ACCESS  read-only
      STATUS      current
      DESCRIPTION "PoE port power draw in milliwatts."
      ::= { gwnPoePortEntry 3 }

  gwnPoeSummary OBJECT IDENTIFIER ::= { gwnPoeStatus 4 }

  gwnPoeTotalBudget OBJECT-TYPE
      SYNTAX      Integer32
      MAX-ACCESS  read-only
      STATUS      current
      DESCRIPTION "Total PoE power budget in milliwatts."
      ::= { gwnPoeSummary 1 }

  gwnPoeTotalUsed OBJECT-TYPE
      SYNTAX      Integer32
      MAX-ACCESS  read-only
      STATUS      current
      DESCRIPTION "Total PoE power currently used in milliwatts."
      ::= { gwnPoeSummary 2 }

  END
