-- Copyright 2021 Grandstream Networks, Inc. All Rights Reserved.

GRANDSTREAM-GWN-PRODUCTS-MIB DEFINITIONS ::= BEGIN

IMPORTS
    ifIndex, InterfaceIndex
		FROM IF-MIB
    DisplayString FROM SNMPv2-TC
    MODULE-IDENTITY, OBJECT-TYPE, NOTIFICATION-TYPE, IpAddress, Counter32, TimeTicks, Integer32
        FROM SNMPv2-SMI
    gwnProducts
        FROM GRANDSTREAM-GWN-ROOT-MIB;

gwnAp MODULE-IDENTITY
    LAST-UPDATED "202110280001Z"
    ORGANIZATION "Grandstream Networks, Inc."
    CONTACT-INFO ""
    DESCRIPTION
    "Grandstream GWN AP product OID registration mib."
    ::= { gwnProducts 1 }

gwnRouter MODULE-IDENTITY
    LAST-UPDATED "202110280001Z"
    ORGANIZATION "Grandstream Networks, Inc."
    CONTACT-INFO ""
    DESCRIPTION
    "Grandstream GWN Router product OID registration mib."
    ::= { gwnProducts 2 }

gwnProductsCommonSystem MODULE-IDENTITY
    LAST-UPDATED "202110280001Z"
    ORGANIZATION "Grandstream Networks, Inc."
    CONTACT-INFO ""
    DESCRIPTION
    "Grandstream GWN CommonSystem product OID registration mib."
    ::= { gwnProducts 3 }

-- Scalars and Tables
--

-- 1.3.6.1.4.1.42397.1.1
-- gwnAp

-- 1.3.6.1.4.1.42397.1.2
-- gwnRouter

-- 1.3.6.1.4.1.42397.1.3
-- gwnProductsCommonSystem

-- 1.3.6.1.4.1.42397.1.3.1
gwnSystemInfo OBJECT IDENTIFIER ::= { gwnProductsCommonSystem 1 }

-- 1.3.6.1.4.1.42397.1.3.1.1
gwnDeviceModel OBJECT-TYPE
    SYNTAX DisplayString
    MAX-ACCESS read-only
    STATUS current
    DESCRIPTION "Device Model."
    ::= { gwnSystemInfo 1 }

-- 1.3.6.1.4.1.42397.1.3.1.2
gwnDeviceName OBJECT-TYPE
    SYNTAX DisplayString
    MAX-ACCESS read-only
    STATUS current
    DESCRIPTION "Device Name."
    ::= { gwnSystemInfo 2 }

-- 1.3.6.1.4.1.42397.1.3.1.3
gwnDeviceMac OBJECT-TYPE
    SYNTAX DisplayString
    MAX-ACCESS read-only
    STATUS current
    DESCRIPTION "Device Mac."
    ::= { gwnSystemInfo 3 }

-- 1.3.6.1.4.1.42397.1.3.1.4
gwnDeviceVersion OBJECT-TYPE
    SYNTAX DisplayString
    MAX-ACCESS read-only
    STATUS current
    DESCRIPTION "Device Version."
    ::= { gwnSystemInfo 4 }

-- 1.3.6.1.4.1.42397.1.3.1.5
gwnDeviceIPv4Address OBJECT-TYPE
    SYNTAX DisplayString
    MAX-ACCESS read-only
    STATUS current
    DESCRIPTION "Device IPv4."
    ::= { gwnSystemInfo 5 }

-- 1.3.6.1.4.1.42397.1.3.1.6
gwnDeviceIPv6Address OBJECT-TYPE
    SYNTAX DisplayString
    MAX-ACCESS read-only
    STATUS current
    DESCRIPTION "Device IPv6."
    ::= { gwnSystemInfo 6 }

-- 1.3.6.1.4.1.42397.1.3.1.7
gwnDeviceUptime OBJECT-TYPE
    SYNTAX Counter32
    MAX-ACCESS read-only
    STATUS current
    DESCRIPTION "Device Uptime."
    ::= { gwnSystemInfo 7 }	

-- 1.3.6.1.4.1.42397.1.3.1.8
gwnSnmpUptime OBJECT-TYPE
    SYNTAX TimeTicks
    MAX-ACCESS read-only
    STATUS current
    DESCRIPTION "Snmpd Uptime."
    ::= { gwnSystemInfo 8 }

-- 1.3.6.1.4.1.42397.1.3.1.9
gwnDeviceSn OBJECT-TYPE
    SYNTAX DisplayString
    MAX-ACCESS read-only
    STATUS current
    DESCRIPTION "Device SN."
    ::= { gwnSystemInfo 9 }

END
