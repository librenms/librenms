GS-UCM63XX-SNMP-MIB DEFINITIONS ::= BEGIN

IMPORTS
    OBJECT-TYPE, NOTIFICATION-TYPE, MODULE-IDENTITY,
    Integer32, Opaque, enterprises, Counter32, Unsigned32
        FROM SNMPv2-SMI

    TEXTUAL-CONVENTION, DisplayString, TruthValue
    FROM SNMPv2-TC;

gsobject MODULE-IDENTITY
    LAST-UPDATED "201910100000Z"
    ORGANIZATION "grandstream"
    CONTACT-INFO
     "postal:   Wes Hardaker
                    P.O. Box 382
                    Davis CA  95617

          email:    net-snmp-coders@lists.sourceforge.net"
    DESCRIPTION
    "grandStream infrastructure of the Net-SNMP project enterprise MIB tree"
    REVISION     "201910100000Z"
    DESCRIPTION
    "First draft"
    ::= { enterprises 12581 }

gsprocessobject OBJECT IDENTIFIER ::= { gsobject 50 }

--
-- Node definitions
--

--  Node definitions
--
-- 1.3.6.1.4.1.12581
		-- 1.3.6.1.4.1.12581.2
		IppbxMib OBJECT IDENTIFIER ::= { gsobject 2 }


--  1.3.6.1.4.1.12581.2.1
		-- 1.3.6.1.4.1.12581.2.1
		sCdr OBJECT IDENTIFIER ::= { IppbxMib 1 }

--  1.3.6.1.4.1.12581.2.1.1
		-- 1.3.6.1.4.1.12581.2.1.1
		sTotalCalls OBJECT-TYPE
			SYNTAX INTEGER
			ACCESS read-only
			STATUS mandatory
			DESCRIPTION
				"Description."
			::= { sCdr 1 }

--  1.3.6.1.4.1.12581.2.1.2
		-- 1.3.6.1.4.1.12581.2.1.2
		sInternalCalls OBJECT-TYPE
			SYNTAX INTEGER
			ACCESS read-only
			STATUS mandatory
			DESCRIPTION
				"Description."
			::= { sCdr 2 }

--  1.3.6.1.4.1.12581.2.1.3
		-- 1.3.6.1.4.1.12581.2.1.3
		sOutboundCalls OBJECT-TYPE
			SYNTAX INTEGER
			ACCESS read-only
			STATUS mandatory
			DESCRIPTION
				"Description."
			::= { sCdr 3 }

--  1.3.6.1.4.1.12581.2.1.4
		-- 1.3.6.1.4.1.12581.2.1.4
		sInboundCalls OBJECT-TYPE
			SYNTAX INTEGER
			ACCESS read-only
			STATUS mandatory
			DESCRIPTION
				"Description."
			::= { sCdr 4 }

--  1.3.6.1.4.1.12581.2.1.5
		-- 1.3.6.1.4.1.12581.2.1.5
		sAnsweredCalls OBJECT-TYPE
			SYNTAX INTEGER
			ACCESS read-only
			STATUS mandatory
			DESCRIPTION
				"Description."
			::= { sCdr 5 }

--  1.3.6.1.4.1.12581.2.1.6
		-- 1.3.6.1.4.1.12581.2.1.6
		sFailedCalls OBJECT-TYPE
			SYNTAX INTEGER
			ACCESS read-only
			STATUS mandatory
			DESCRIPTION
				"Description."
			::= { sCdr 6 }

--  1.3.6.1.4.1.12581.2.1.7
		-- 1.3.6.1.4.1.12581.2.1.7
		sBusyCalls OBJECT-TYPE
			SYNTAX INTEGER
			ACCESS read-only
			STATUS mandatory
			DESCRIPTION
				"Description."
			::= { sCdr 7 }

--  1.3.6.1.4.1.12581.2.1.8
		-- 1.3.6.1.4.1.12581.2.1.8
		sNoAnsweredCalls OBJECT-TYPE
			SYNTAX INTEGER
			ACCESS read-only
			STATUS mandatory
			DESCRIPTION
				"Description."
			::= { sCdr 8 }

--  1.3.6.1.4.1.12581.2.2
		-- 1.3.6.1.4.1.12581.2.2
		sSysinfo OBJECT IDENTIFIER ::= { IppbxMib 2 }


--  1.3.6.1.4.1.12581.2.2.1
		-- 1.3.6.1.4.1.12581.2.2.1
		sProductType OBJECT-TYPE
			SYNTAX OCTET STRING
			ACCESS read-only
			STATUS mandatory
			DESCRIPTION
				"Description."
			::= { sSysinfo 1 }

--  1.3.6.1.4.1.12581.2.2.2
		-- 1.3.6.1.4.1.12581.2.2.2
		sHardwareVersion OBJECT-TYPE
			SYNTAX OCTET STRING
			ACCESS read-only
			STATUS mandatory
			DESCRIPTION
				"Description."
			::= { sSysinfo 2 }

--  1.3.6.1.4.1.12581.2.2.3
		-- 1.3.6.1.4.1.12581.2.2.3
		sFirmwareVersion OBJECT-TYPE
			SYNTAX OCTET STRING
			ACCESS read-only
			STATUS mandatory
			DESCRIPTION
				"Description."
			::= { sSysinfo 3 }

--  1.3.6.1.4.1.12581.2.2.4
		-- 1.3.6.1.4.1.12581.2.2.4
		sSerialNumber OBJECT-TYPE
			SYNTAX OCTET STRING
			ACCESS read-only
			STATUS mandatory
			DESCRIPTION
				"Description."
			::= { sSysinfo 4 }

--  1.3.6.1.4.1.12581.2.2.5
		-- 1.3.6.1.4.1.12581.2.2.5
		sUptime OBJECT-TYPE
			SYNTAX OCTET STRING
			ACCESS read-only
			STATUS mandatory
			DESCRIPTION
				"Description."
			::= { sSysinfo 5 }

--  1.3.6.1.4.1.12581.2.2.6
		-- 1.3.6.1.4.1.12581.2.2.6
		sDiskUsage OBJECT-TYPE
			SYNTAX OCTET STRING
			ACCESS read-only
			STATUS mandatory
			DESCRIPTION
				"Description."
			::= { sSysinfo 6 }

--  1.3.6.1.4.1.12581.2.2.7
		-- 1.3.6.1.4.1.12581.2.2.7
		sMemoryUsage OBJECT-TYPE
			SYNTAX OCTET STRING
			ACCESS read-only
			STATUS mandatory
			DESCRIPTION
				"Description."
			::= { sSysinfo 7 }

--  1.3.6.1.4.1.12581.2.2.8
		-- 1.3.6.1.4.1.12581.2.2.8
		sCpuUsage OBJECT-TYPE
			SYNTAX OCTET STRING
			ACCESS read-only
			STATUS mandatory
			DESCRIPTION
				"Description."
			::= { sSysinfo 8 }

--  1.3.6.1.4.1.12581.2.2.9
		-- 1.3.6.1.4.1.12581.2.2.9
		concurrentCall OBJECT-TYPE
			SYNTAX INTEGER
			ACCESS read-only
			STATUS mandatory
			DESCRIPTION
				"Description."
			::= { sSysinfo 9 }

--  1.3.6.1.4.1.12581.2.2.10
		-- 1.3.6.1.4.1.12581.2.2.10
		sHostName OBJECT-TYPE
			SYNTAX DisplayString (SIZE (0..255))
			ACCESS read-only
			STATUS mandatory
			DESCRIPTION
				"Description."
			::= { sSysinfo 10 }

--  1.3.6.1.4.1.12581.2.3
		-- 1.3.6.1.4.1.12581.2.3
		sNetstatus OBJECT IDENTIFIER ::= { IppbxMib 3 }


--  1.3.6.1.4.1.12581.2.3.1
		-- 1.3.6.1.4.1.12581.2.3.1
		sLanStatus OBJECT-TYPE
			SYNTAX OCTET STRING
			ACCESS read-only
			STATUS mandatory
			DESCRIPTION
				"Description."
			::= { sNetstatus 1 }

--  1.3.6.1.4.1.12581.2.3.2
		-- 1.3.6.1.4.1.12581.2.3.2
		sLanMac OBJECT-TYPE
			SYNTAX OCTET STRING
			ACCESS read-only
			STATUS mandatory
			DESCRIPTION
				"Description."
			::= { sNetstatus 2 }

--  1.3.6.1.4.1.12581.2.3.3
		-- 1.3.6.1.4.1.12581.2.3.3
		sLanIpaddress OBJECT-TYPE
			SYNTAX OCTET STRING
			ACCESS read-only
			STATUS mandatory
			DESCRIPTION
				"Description."
			::= { sNetstatus 3 }

--  1.3.6.1.4.1.12581.2.3.4
		-- 1.3.6.1.4.1.12581.2.3.4
		sLanSubnetMask OBJECT-TYPE
			SYNTAX OCTET STRING
			ACCESS read-only
			STATUS mandatory
			DESCRIPTION
				"Description."
			::= { sNetstatus 4 }

--  1.3.6.1.4.1.12581.2.3.5
		-- 1.3.6.1.4.1.12581.2.3.5
		sLanGateWay OBJECT-TYPE
			SYNTAX OCTET STRING
			ACCESS read-only
			STATUS mandatory
			DESCRIPTION
				"Description."
			::= { sNetstatus 5 }

--  1.3.6.1.4.1.12581.2.3.6
		-- 1.3.6.1.4.1.12581.2.3.5
		sLanMode OBJECT-TYPE
			SYNTAX OCTET STRING
			ACCESS read-only
			STATUS mandatory
			DESCRIPTION
				"Description."
			::= { sNetstatus 6 }

--  1.3.6.1.4.1.12581.2.3.7
		-- 1.3.6.1.4.1.12581.2.3.7
		sLanDns OBJECT-TYPE
			SYNTAX OCTET STRING
			ACCESS read-only
			STATUS mandatory
			DESCRIPTION
				"Description."
			::= { sNetstatus 7 }


--  1.3.6.1.4.1.12581.2.3.8
		-- 1.3.6.1.4.1.12581.2.3.8
		sWanStatus OBJECT-TYPE
			SYNTAX OCTET STRING
			ACCESS read-only
			STATUS mandatory
			DESCRIPTION
				"Description."
			::= { sNetstatus 8 }

--  1.3.6.1.4.1.12581.2.3.9
		-- 1.3.6.1.4.1.12581.2.3.9
		sWanMac OBJECT-TYPE
			SYNTAX OCTET STRING
			ACCESS read-only
			STATUS mandatory
			DESCRIPTION
				"Description."
			::= { sNetstatus 9 }

--  1.3.6.1.4.1.12581.2.3.10
		-- 1.3.6.1.4.1.12581.2.3.10
		sWanIpaddress OBJECT-TYPE
			SYNTAX OCTET STRING
			ACCESS read-only
			STATUS mandatory
			DESCRIPTION
				"Description."
			::= { sNetstatus 10 }

--  1.3.6.1.4.1.12581.2.3.11
		-- 1.3.6.1.4.1.12581.2.3.11
		sWanSubnetMask OBJECT-TYPE
			SYNTAX OCTET STRING
			ACCESS read-only
			STATUS mandatory
			DESCRIPTION
				"Description."
			::= { sNetstatus 11 }

--  1.3.6.1.4.1.12581.2.3.12
		-- 1.3.6.1.4.1.12581.2.3.12
		sWanGateWay OBJECT-TYPE
			SYNTAX OCTET STRING
			ACCESS read-only
			STATUS mandatory
			DESCRIPTION
				"Description."
			::= { sNetstatus 12 }

--  1.3.6.1.4.1.12581.2.3.13
		-- 1.3.6.1.4.1.12581.2.3.13
		sWanMode OBJECT-TYPE
			SYNTAX OCTET STRING
			ACCESS read-only
			STATUS mandatory
			DESCRIPTION
				"Description."
			::= { sNetstatus 13 }

--  1.3.6.1.4.1.12581.2.3.14
		-- 1.3.6.1.4.1.12581.2.3.14
		sWanDns OBJECT-TYPE
			SYNTAX OCTET STRING
			ACCESS read-only
			STATUS mandatory
			DESCRIPTION
				"Description."
			::= { sNetstatus 14 }

--  1.3.6.1.4.1.12581.2.4
		-- 1.3.6.1.4.1.12581.2.4
		sExtensions OBJECT IDENTIFIER ::= { IppbxMib 4 }


--  1.3.6.1.4.1.12581.2.4.1
		-- 1.3.6.1.4.1.12581.2.4.1
		sExternsionsTable OBJECT-TYPE
			SYNTAX SEQUENCE OF SExternsionsEntry
			ACCESS not-accessible
			STATUS mandatory
			DESCRIPTION
				"Description."
			::= { sExtensions 1 }


--  1.3.6.1.4.1.12581.2.4.1.1
		-- 1.3.6.1.4.1.12581.2.4.1.1
		sExternsionsEntry OBJECT-TYPE
			SYNTAX SExternsionsEntry
			ACCESS not-accessible
			STATUS mandatory
			DESCRIPTION
				"Description."
			INDEX { sExternsionsIndex }
			::= { sExternsionsTable 1 }


		SExternsionsEntry ::=
			SEQUENCE {
				sExternsionsIndex
					INTEGER,
				sExternsionsNum
					OCTET STRING,
				sExternsionsStatus
					OCTET STRING,
				sExternsionsVoiceMail
					OCTET STRING,
				sExternsionsType
					OCTET STRING
			 }

--  1.3.6.1.4.1.12581.2.4.1.1.1
		-- 1.3.6.1.4.1.12581.2.4.1.1.1
		sExternsionsIndex OBJECT-TYPE
			SYNTAX INTEGER (0..5000)
			ACCESS read-only
			STATUS mandatory
			DESCRIPTION
				"Description."
			::= { sExternsionsEntry 1 }



--  1.3.6.1.4.1.12581.2.4.1.1.2
		-- 1.3.6.1.4.1.12581.2.4.1.1.2
		sExternsionsNum OBJECT-TYPE
			SYNTAX OCTET STRING
			ACCESS read-only
			STATUS mandatory
			DESCRIPTION
				"Description."
			::= { sExternsionsEntry 2 }


--  1.3.6.1.4.1.12581.2.4.1.1.3
		-- 1.3.6.1.4.1.12581.2.4.1.1.3
		sExternsionsStatus OBJECT-TYPE
			SYNTAX OCTET STRING
			ACCESS read-only
			STATUS mandatory
			DESCRIPTION
				"Description."
			::= { sExternsionsEntry 3 }


--  1.3.6.1.4.1.12581.2.4.1.1.4
		-- 1.3.6.1.4.1.12581.2.4.1.1.4
		sExternsionsVoiceMail OBJECT-TYPE
			SYNTAX OCTET STRING
			ACCESS read-only
			STATUS mandatory
			DESCRIPTION
				"Description."
			::= { sExternsionsEntry 4 }


--  1.3.6.1.4.1.12581.2.4.1.1.5
		-- 1.3.6.1.4.1.12581.2.4.1.1.5
		sExternsionsType OBJECT-TYPE
			SYNTAX OCTET STRING
			ACCESS read-only
			STATUS mandatory
			DESCRIPTION
				"Description."
			::= { sExternsionsEntry 5 }

--  1.3.6.1.4.1.12581.2.5
		-- 1.3.6.1.4.1.12581.2.5
		sTrunks OBJECT IDENTIFIER ::= { IppbxMib 5 }


--  1.3.6.1.4.1.12581.2.5.1
		-- 1.3.6.1.4.1.12581.2.5.1
		sTrunksTable OBJECT-TYPE
			SYNTAX SEQUENCE OF sTrunksEntry
			ACCESS not-accessible
			STATUS mandatory
			DESCRIPTION
				"Description."
			::= { sTrunks 1 }


--  1.3.6.1.4.1.12581.2.5.1.1
		-- 1.3.6.1.4.1.12581.2.5.1.1
		sTrunksEntry OBJECT-TYPE
			SYNTAX sTrunksEntry
			ACCESS not-accessible
			STATUS mandatory
			DESCRIPTION
				"Description."
			INDEX { sTrunksIndex }
			::= { sTrunksTable 1 }


		sTrunksEntry ::=
			SEQUENCE {
				sTrunksIndex
					INTEGER,
				sTrunksName
					DisplayString (SIZE (0..255)),
				sTrunksType
					OCTET STRING,
				sTrunksStatus
					OCTET STRING,
				sTrunksHostName
					OCTET STRING,
				sTrunksUserName
					OCTET STRING
			 }

--  1.3.6.1.4.1.12581.2.5.1.1.1
		-- 1.3.6.1.4.1.12581.2.5.1.1.1
		sTrunksIndex OBJECT-TYPE
			SYNTAX INTEGER (0..	2000)
			ACCESS read-only
			STATUS mandatory
			DESCRIPTION
				"Description."
			::= { sTrunksEntry 1 }



--  1.3.6.1.4.1.12581.2.5.1.1.2
		-- 1.3.6.1.4.1.12581.2.5.1.1.2
		sTrunksName OBJECT-TYPE
			SYNTAX DisplayString (SIZE (0..255))
			ACCESS read-only
			STATUS mandatory
			DESCRIPTION
				"Description."
			::= { sTrunksEntry 2 }


--  1.3.6.1.4.1.12581.2.3.1.1.3
		-- 1.3.6.1.4.1.12581.2.5.1.1.3
		sTrunksType OBJECT-TYPE
			SYNTAX OCTET STRING
			ACCESS read-only
			STATUS mandatory
			DESCRIPTION
				"Description."
			::= { sTrunksEntry 3 }


--  1.3.6.1.4.1.12581.2.5.1.1.4
		-- 1.3.6.1.4.1.12581.2.5.1.1.4
		sTrunksStatus OBJECT-TYPE
			SYNTAX OCTET STRING
			ACCESS read-only
			STATUS mandatory
			DESCRIPTION
				"Description."
			::= { sTrunksEntry 4 }


--  1.3.6.1.4.1.12581.2.5.1.1.5
		-- 1.3.6.1.4.1.12581.2.5.1.1.5
		sTrunksHostName OBJECT-TYPE
			SYNTAX OCTET STRING
			ACCESS read-only
			STATUS mandatory
			DESCRIPTION
				"Description."
			::= { sTrunksEntry 5 }

--  1.3.6.1.4.1.12581.2.5.1.1.6
		-- 1.3.6.1.4.1.12581.2.5.1.1.6
		sTrunksUserName OBJECT-TYPE
			SYNTAX OCTET STRING
			ACCESS read-only
			STATUS mandatory
			DESCRIPTION
				"Description."
			::= { sTrunksEntry 6 }

--  1.3.6.1.4.1.12581.2.6
		-- 1.3.6.1.4.1.12581.2.6
		sFail2ban OBJECT IDENTIFIER ::= { IppbxMib 6 }


--  1.3.6.1.4.1.12581.2.5.1
		-- 1.3.6.1.4.1.12581.2.5.1
		sFail2banTable OBJECT-TYPE
			SYNTAX SEQUENCE OF sFail2banEntry
			ACCESS not-accessible
			STATUS mandatory
			DESCRIPTION
				"Description."
			::= { sFail2ban 1 }


--  1.3.6.1.4.1.12581.2.6.1.1
		-- 1.3.6.1.4.1.12581.2.6.1.1
		sFail2banEntry OBJECT-TYPE
			SYNTAX sFail2banEntry
			ACCESS not-accessible
			STATUS mandatory
			DESCRIPTION
				"Description."
			INDEX { sFail2banIndex }
			::= { sFail2banTable 1 }


		sFail2banEntry ::=
			SEQUENCE {
				sFail2banIndex
					INTEGER,
				sFail2banIp
					OCTET STRING,
				sFail2banProtocol
					OCTET STRING,
				sFail2banBanTime
					OCTET STRING
			 }

--  1.3.6.1.4.1.12581.2.6.1.1.1
		-- 1.3.6.1.4.1.12581.2.6.1.1.1
		sFail2banIndex OBJECT-TYPE
			SYNTAX INTEGER (0..	2000)
			ACCESS read-only
			STATUS mandatory
			DESCRIPTION
				"Description."
			::= { sFail2banEntry 1 }



--  1.3.6.1.4.1.12581.2.6.1.1.2
		-- 1.3.6.1.4.1.12581.2.6.1.1.2
		sFail2banIp OBJECT-TYPE
			SYNTAX OCTET STRING
			ACCESS read-only
			STATUS mandatory
			DESCRIPTION
				"Description."
			::= { sFail2banEntry 2 }


--  1.3.6.1.4.1.12581.2.6.1.1.3
		-- 1.3.6.1.4.1.12581.2.6.1.1.3
		sFail2banProtocol OBJECT-TYPE
			SYNTAX OCTET STRING
			ACCESS read-only
			STATUS mandatory
			DESCRIPTION
				"Description."
			::= { sFail2banEntry 3 }


--  1.3.6.1.4.1.12581.2.6.1.1.4
		-- 1.3.6.1.4.1.12581.2.6.1.1.4
		sFail2banBanTime OBJECT-TYPE
			SYNTAX OCTET STRING
			ACCESS read-only
			STATUS mandatory
			DESCRIPTION
				"Description."
			::= { sFail2banEntry 4 }




GSErrorFlag ::= TEXTUAL-CONVENTION
    STATUS      current
    DESCRIPTION
        "Represents a possible error condition"
    SYNTAX INTEGER  { noError(0),  error(1) }

GSCrashFlag ::= TEXTUAL-CONVENTION
    STATUS      current
    DESCRIPTION
        "Determine whether a crash occurs in a process."
    SYNTAX INTEGER  { noCrash(0),  Crash(1) }

gsProcessName  OBJECT-TYPE
    SYNTAX  DisplayString
    MAX-ACCESS  read-only
    STATUS  current
    DESCRIPTION
    "The coredump file name."
    ::= { gsprocessobject 1 }

gsProcessCrash OBJECT-TYPE
    SYNTAX  GSCrashFlag
    MAX-ACCESS  read-only
    STATUS  current
    DESCRIPTION
    "Determine whether a crash occurs in a process."
    ::= { gsprocessobject 2 }

gsProcessCoreDumpName OBJECT-TYPE
    SYNTAX  DisplayString
    MAX-ACCESS  read-only
    STATUS  current
    DESCRIPTION
    "The coredump file name."
    ::= { gsprocessobject 3 }



--  Trap definitions
--
    sTraps OBJECT IDENTIFIER ::= { IppbxMib 7 }

    diskUsageTrap TRAP-TYPE
        ENTERPRISE sTraps
        DESCRIPTION
            "Disk usage is over than 95%."
        ::=  3

    cpuUsageTrap TRAP-TYPE
        ENTERPRISE sTraps
        DESCRIPTION
            "cpu usage is over than 90%."
        ::=  1

    memoryUsageTrap TRAP-TYPE
        ENTERPRISE sTraps
        DESCRIPTION
            "Memory usage is over than 90%."
        ::=  2


    END
