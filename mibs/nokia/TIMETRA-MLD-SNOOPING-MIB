TIMETRA-MLD-SNOOPING-MIB DEFINITIONS ::= BEGIN

IMPORTS
    eMplsTEPLblTEPAddrType,
    eMplsTEPLblTEPAddress,
    eMplsTEPLblTEPLabel, eVxlanVNI,
    eVxlanVTEPAddr, eVxlanVTEPAddrType,
    vxlanVNI, vxlanVTEPAddr,
    vxlanVTEPAddrType, vxlanVTEPAddress
                                                         FROM ALCATEL-IGMP-SNOOPING-MIB
    InterfaceIndexOrZero
                                                         FROM IF-MIB
    InetAddress, InetAddressType
                                                         FROM INET-ADDRESS-MIB
    MODULE-COMPLIANCE, NOTIFICATION-GROUP,
    OBJECT-GROUP
                                                         FROM SNMPv2-CONF
    Counter32, Integer32, IpAddress,
    MODULE-IDENTITY, NOTIFICATION-TYPE,
    OBJECT-TYPE, TimeTicks, Unsigned32
                                                         FROM SNMPv2-SMI
    DisplayString, RowStatus,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    tmnxMcacLagPortsDown, tmnxMcacLevelId
                                                         FROM TIMETRA-MCAST-CAC-MIB
    sapEncapValue, sapPortId
                                                         FROM TIMETRA-SAP-MIB
    sdpBindId
                                                         FROM TIMETRA-SDP-MIB
    SdpId, svcId
                                                         FROM TIMETRA-SERV-MIB
    TItemDescription,
    TPolicyStatementNameOrEmpty,
    TmnxAdminState, TmnxEncapVal,
    TmnxIgmpGroupFilterMode,
    TmnxIgmpSnpgGroupType,
    TmnxMldGroupFilterMode,
    TmnxMldGroupType, TmnxMldVersion,
    TmnxOperState, TmnxPortID, TmnxServId,
    TmnxVRtrIDOrZero, TmnxVcIdOrNone
                                                         FROM TIMETRA-TC-MIB
    ;

timetraMldSnoopingMIBModule      MODULE-IDENTITY
    LAST-UPDATED "201601010000Z"
    ORGANIZATION "Nokia"
    CONTACT-INFO
        "Nokia SROS Support
         Web: http://www.nokia.com"
    DESCRIPTION
        "This document is the SNMP MIB module to manage and provision the
         Multicast Listener Discovery (MLD) snooping feature protocol for the
         Nokia SROS device.

         Copyright 2008-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201601010000Z"
    DESCRIPTION
        "Rev 14.0               01 Jan 2016 00:00
         14.0 release of the TIMETRA-MLD-SNOOPING-MIB."

    REVISION    "200801010000Z"
    DESCRIPTION
        "Rev 0.1                01 Jan 2008 00:00
         Initial version of the TIMETRA-MLD-SNOOPING-MIB."

    ::= { timetraSRMIBModules 45 }

TmnxMldSnpgLocation              ::= TEXTUAL-CONVENTION
    STATUS      current
    DESCRIPTION
        "The data type TmnxMldSnpgLocation represents the type of the local
         interface:
         - 'sap(1)'     : sap interface
         - 'sdp(2)'     : mesh-sdp or spoke-sdp interface
         - 'rvpls(3)'   : rvpls
         - 'vxlan(4)'   : vxlan endpoint for ethernet vpn
         - 'evpnMpls(5)': evpn mpls"
    SYNTAX      INTEGER {
        sap      (1),
        sdp      (2),
        rvpls    (3),
        vxlan    (4),
        evpnMpls (5)
    }

tmnxMldSnoopingObjs              OBJECT IDENTIFIER ::= { tmnxSRObjs 45 }

tmnxMldSnoopingTlsObjs           OBJECT IDENTIFIER ::= { tmnxMldSnoopingObjs 1 }

tlsMldSnpgConfigTableLastChange  OBJECT-TYPE
    SYNTAX      TimeStamp
    MAX-ACCESS  read-only
    STATUS      current
    DESCRIPTION
        "The value of the object tlsMldSnpgConfigTableLastChange indicates the
         value of sysUpTime at the time of the last modification of an entry in
         the tlsMldSnpgConfigTable."
    ::= { tmnxMldSnoopingTlsObjs 1 }

tlsMldSnpgConfigTable            OBJECT-TYPE
    SYNTAX      SEQUENCE OF TlsMldSnpgConfigEntry
    MAX-ACCESS  not-accessible
    STATUS      current
    DESCRIPTION
        "The table tlsMldSnpgConfigTable contains objects to configure the MLD
         snooping feature within a Tls service."
    ::= { tmnxMldSnoopingTlsObjs 2 }

tlsMldSnpgConfigEntry            OBJECT-TYPE
    SYNTAX      TlsMldSnpgConfigEntry
    MAX-ACCESS  not-accessible
    STATUS      current
    DESCRIPTION
        "Each row represents an instance of MLD snooping running within a Tls
         service.

         Entries in this table cannot be created or deleted via SNMP
         operations. An entry in this table will be created by the agent upon
         creation of a new Tls service (svcTlsInfoTable). The entry is
         destroyed when the Tls service is removed."
    INDEX       { svcId }
    ::= { tlsMldSnpgConfigTable 1 }

TlsMldSnpgConfigEntry            ::= SEQUENCE
{
    tlsMldSnpgCfgLastChangeTime      TimeStamp,
    tlsMldSnpgCfgAdminState          TmnxAdminState,
    tlsMldSnpgCfgGenQueryIntvl       Unsigned32,
    tlsMldSnpgCfgRobustCount         Unsigned32,
    tlsMldSnpgCfgReportSrcAddrType   InetAddressType,
    tlsMldSnpgCfgReportSrcAddr       InetAddress,
    tlsMldSnpgCfgQuerySrcAddrType    InetAddressType,
    tlsMldSnpgCfgQuerySrcAddr        InetAddress,
    tlsMldSnpgCfgMvrAdminState       TmnxAdminState,
    tlsMldSnpgCfgMvrDescription      TItemDescription,
    tlsMldSnpgCfgMvrPolicy           TPolicyStatementNameOrEmpty,
    tlsMldSnpgCfgFwdIpv6McastToInt   TruthValue,
    tlsMldSnpgCfgRvplsMrouter        TruthValue,
    tlsMldSnpgCfgTxSmetRoutes        Unsigned32,
    tlsMldSnpgCfgEvpnProxy           TmnxAdminState
}

tlsMldSnpgCfgLastChangeTime      OBJECT-TYPE
    SYNTAX      TimeStamp
    MAX-ACCESS  read-only
    STATUS      current
    DESCRIPTION
        "The value of the object tlsMldSnpgCfgLastChangeTime indicates the
         sysUpTime at the time of the last modification of this entry."
    ::= { tlsMldSnpgConfigEntry 1 }

tlsMldSnpgCfgAdminState          OBJECT-TYPE
    SYNTAX      TmnxAdminState
    MAX-ACCESS  read-write
    STATUS      current
    DESCRIPTION
        "The value of the object tlsMldSnpgCfgAdminState specifies the
         administrative state of the MLD snooping feature associated with this
         Tls."
    DEFVAL      { outOfService }
    ::= { tlsMldSnpgConfigEntry 2 }

tlsMldSnpgCfgGenQueryIntvl       OBJECT-TYPE
    SYNTAX      Unsigned32 (1..65535)
    UNITS       "seconds"
    MAX-ACCESS  read-write
    STATUS      current
    DESCRIPTION
        "The value of the object tlsMldSnpgCfgGenQueryIntvl specifies the
         Queriers Query Interval when the Query Interval is not sent in the
         Query PDU or when it is set to zero in the Query PDU.

         For these networks, this object needs to be set to the same value as
         what is configured on the Querier."
    DEFVAL      { 125 }
    ::= { tlsMldSnpgConfigEntry 3 }

tlsMldSnpgCfgRobustCount         OBJECT-TYPE
    SYNTAX      Unsigned32 (1..255)
    MAX-ACCESS  read-write
    STATUS      current
    DESCRIPTION
        "The value of the object tlsMldSnpgCfgRobustCount specifies the
         Querier's Robustness Variable when the Robustness Variable is not sent
         in the Query PDU or when it is set to zero in the Query PDU.

         For these networks, this object needs to be set to the same value as
         what is configured on the Querier."
    DEFVAL      { 2 }
    ::= { tlsMldSnpgConfigEntry 4 }

tlsMldSnpgCfgReportSrcAddrType   OBJECT-TYPE
    SYNTAX      InetAddressType
    MAX-ACCESS  read-write
    STATUS      current
    DESCRIPTION
        "The value of the object tlsMldSnpgCfgReportSrcAddrType specifies the
         type of tlsMldSnpgCfgReportSrcAddr.

         When setting the value of this object, the value of
         tlsMldSnpgCfgReportSrcAddr must be set as well in the same SNMP SET
         PDU."
    DEFVAL      { unknown }
    ::= { tlsMldSnpgConfigEntry 5 }

tlsMldSnpgCfgReportSrcAddr       OBJECT-TYPE
    SYNTAX      InetAddress (SIZE (0|16))
    MAX-ACCESS  read-write
    STATUS      current
    DESCRIPTION
        "The value of the object tlsMldSnpgCfgReportSrcAddr specifies the link
         local source IP address used when generating MLD reports.

         When setting the value of this object, the value of
         tlsMldSnpgCfgReportSrcAddrType must be set as well in the same SNMP
         SET PDU."
    DEFVAL      { ''H }
    ::= { tlsMldSnpgConfigEntry 6 }

tlsMldSnpgCfgQuerySrcAddrType    OBJECT-TYPE
    SYNTAX      InetAddressType
    MAX-ACCESS  read-write
    STATUS      current
    DESCRIPTION
        "The value of the object tlsMldSnpgCfgQuerySrcAddrType specifies the
         type of tlsMldSnpgCfgQuerySrcAddr.

         When setting the value of this object, the value of
         tlsMldSnpgCfgQuerySrcAddr must be set as well in the same SNMP SET
         PDU."
    DEFVAL      { unknown }
    ::= { tlsMldSnpgConfigEntry 7 }

tlsMldSnpgCfgQuerySrcAddr        OBJECT-TYPE
    SYNTAX      InetAddress (SIZE (0|16))
    MAX-ACCESS  read-write
    STATUS      current
    DESCRIPTION
        "The value of the object tlsMldSnpgCfgQuerySrcAddr specifies the link
         local source IP address used when generating MLD queries.

         When setting the value of this object, the value of
         tlsMldSnpgCfgQuerySrcAddrType must be set as well in the same SNMP SET
         PDU."
    DEFVAL      { ''H }
    ::= { tlsMldSnpgConfigEntry 8 }

tlsMldSnpgCfgMvrAdminState       OBJECT-TYPE
    SYNTAX      TmnxAdminState
    MAX-ACCESS  read-write
    STATUS      current
    DESCRIPTION
        "The value of the object tlsMldSnpgCfgMvrAdminState specifies the
         administrative state of the MLD snooping Multicast VPLS Registration
         feature associated with this Tls."
    DEFVAL      { outOfService }
    ::= { tlsMldSnpgConfigEntry 9 }

tlsMldSnpgCfgMvrDescription      OBJECT-TYPE
    SYNTAX      TItemDescription
    MAX-ACCESS  read-write
    STATUS      current
    DESCRIPTION
        "The value of the object tlsMldSnpgCfgMvrDescription specifies a user
         provided description for the MLD snooping Multicast VPLS Registration
         configuration associated with this Tls."
    DEFVAL      { "" }
    ::= { tlsMldSnpgConfigEntry 10 }

tlsMldSnpgCfgMvrPolicy           OBJECT-TYPE
    SYNTAX      TPolicyStatementNameOrEmpty
    MAX-ACCESS  read-write
    STATUS      current
    DESCRIPTION
        "The value of the object tlsMldSnpgCfgMvrPolicy specifies the policy
         statement that is applied to decide whether or not a multicast group
         learned on a SAP with the object sapMldSnpgCfgMvrFromVplsId set to
         this Tls, can be joined to this Tls.

         If an empty string is provided, all groups learned on these SAPs are
         joined without applying a policy."
    DEFVAL      { "" }
    ::= { tlsMldSnpgConfigEntry 11 }

tlsMldSnpgCfgFwdIpv6McastToInt   OBJECT-TYPE
    SYNTAX      TruthValue
    MAX-ACCESS  read-write
    STATUS      current
    DESCRIPTION
        "The value of the object tlsMldSnpgCfgFwdIpv6McastToInt specifies
         whether or not to forward IPv6 multicast traffic from the VPLS to the
         Routed-VPLS L3 interface."
    DEFVAL      { false }
    ::= { tlsMldSnpgConfigEntry 12 }

tlsMldSnpgCfgRvplsMrouter        OBJECT-TYPE
    SYNTAX      TruthValue
    MAX-ACCESS  read-write
    STATUS      current
    DESCRIPTION
        "The value of the object tlsMldSnpgCfgRvplsMrouter specifies whether a
         multicast router is attached behind the Routed-VPLS L3 interface."
    DEFVAL      { false }
    ::= { tlsMldSnpgConfigEntry 13 }

tlsMldSnpgCfgTxSmetRoutes        OBJECT-TYPE
    SYNTAX      Unsigned32
    MAX-ACCESS  read-only
    STATUS      current
    DESCRIPTION
        "tlsMldSnpgCfgTxSmetRoutes is the number of advertised BGP Smet routes
         on this service."
    ::= { tlsMldSnpgConfigEntry 14 }

tlsMldSnpgCfgEvpnProxy           OBJECT-TYPE
    SYNTAX      TmnxAdminState
    MAX-ACCESS  read-write
    STATUS      current
    DESCRIPTION
        "tlsMldSnpgCfgEvpnProxy specifies whether evpn-proxy  mode is enabled
         on this service."
    DEFVAL      { outOfService }
    ::= { tlsMldSnpgConfigEntry 15 }

tlsMldSnpgQuerierTable           OBJECT-TYPE
    SYNTAX      SEQUENCE OF TlsMldSnpgQuerierEntry
    MAX-ACCESS  not-accessible
    STATUS      current
    DESCRIPTION
        "The table tlsMldSnpgQuerierTable contains information related to the
         active MLD Querier found in each Tls Service."
    ::= { tmnxMldSnoopingTlsObjs 3 }

tlsMldSnpgQuerierEntry           OBJECT-TYPE
    SYNTAX      TlsMldSnpgQuerierEntry
    MAX-ACCESS  not-accessible
    STATUS      current
    DESCRIPTION
        "Each row represents information on the active MLD Querier within a Tls
         service.

         Entries in this table cannot be created or deleted via SNMP
         operations. An entry in this table will be created by the agent upon
         detection of an MLD Querier in a Tls service for which MLD snooping is
         enabled (via tlsMldSnpgCfgAdminState)."
    INDEX       { svcId }
    ::= { tlsMldSnpgQuerierTable 1 }

TlsMldSnpgQuerierEntry           ::= SEQUENCE
{
    tlsMldSnpgQuerierVersion         TmnxMldVersion,
    tlsMldSnpgQuerierAddressType     InetAddressType,
    tlsMldSnpgQuerierAddress         InetAddress,
    tlsMldSnpgQuerierLocale          TmnxMldSnpgLocation,
    tlsMldSnpgQuerierPortId          TmnxPortID,
    tlsMldSnpgQuerierEncapValue      TmnxEncapVal,
    tlsMldSnpgQuerierSdpId           SdpId,
    tlsMldSnpgQuerierVcId            TmnxVcIdOrNone,
    tlsMldSnpgQuerierUpTime          TimeTicks,
    tlsMldSnpgQuerierExpiryTime      Unsigned32,
    tlsMldSnpgQuerierGenQueryIntvl   Unsigned32,
    tlsMldSnpgQuerierGenRespIntvl    Unsigned32,
    tlsMldSnpgQuerierRobustCount     Unsigned32,
    tlsMldSnpgQuerierVRtrId          TmnxVRtrIDOrZero,
    tlsMldSnpgQuerierIfIndex         InterfaceIndexOrZero,
    tlsMldSnpgQuerierVTEPAddr        IpAddress,
    tlsMldSnpgQuerierVNI             Unsigned32
}

tlsMldSnpgQuerierVersion         OBJECT-TYPE
    SYNTAX      TmnxMldVersion
    MAX-ACCESS  read-only
    STATUS      current
    DESCRIPTION
        "The value of the object tlsMldSnpgQuerierVersion indicates the version
         of the MLD protocol that is sent by the active MLD Querier detected in
         this Tls."
    ::= { tlsMldSnpgQuerierEntry 1 }

tlsMldSnpgQuerierAddressType     OBJECT-TYPE
    SYNTAX      InetAddressType
    MAX-ACCESS  read-only
    STATUS      current
    DESCRIPTION
        "The value of the object tlsMldSnpgQuerierAddressType indicates the
         type of tlsMldSnpgQuerierAddress."
    ::= { tlsMldSnpgQuerierEntry 2 }

tlsMldSnpgQuerierAddress         OBJECT-TYPE
    SYNTAX      InetAddress (SIZE (4|16))
    MAX-ACCESS  read-only
    STATUS      current
    DESCRIPTION
        "The value of the object tlsMldSnpgQuerierAddress indicates the source
         IP address used by MLD queries sent out by the active Querier."
    ::= { tlsMldSnpgQuerierEntry 3 }

tlsMldSnpgQuerierLocale          OBJECT-TYPE
    SYNTAX      TmnxMldSnpgLocation
    MAX-ACCESS  read-only
    STATUS      current
    DESCRIPTION
        "The value of the object tlsMldSnpgQuerierLocale indicates where the
         Querier was detected.

         An MLD Querier found on a local SAP has the value 'sap(1)'. An MLD
         Querier detected on an SDP has the value 'sdp(2)'."
    ::= { tlsMldSnpgQuerierEntry 4 }

tlsMldSnpgQuerierPortId          OBJECT-TYPE
    SYNTAX      TmnxPortID
    MAX-ACCESS  read-only
    STATUS      current
    DESCRIPTION
        "The value of the object tlsMldSnpgQuerierPortId indicates, together
         with tlsMldSnpgQuerierEncapValue, the SAP on which the active Querier
         is detected.

         The value of this object is only meaningful when the value of
         tlsMldSnpgQuerierLocale is 'sap(1)'."
    ::= { tlsMldSnpgQuerierEntry 5 }

tlsMldSnpgQuerierEncapValue      OBJECT-TYPE
    SYNTAX      TmnxEncapVal
    MAX-ACCESS  read-only
    STATUS      current
    DESCRIPTION
        "The value of the object tlsMldSnpgQuerierEncapValue indicates,
         together with the object tlsMldSnpgQuerierPortId, the SAP on which the
         active Querier is detected.

         The value of this object is only meaningful when the value of
         tlsMldSnpgQuerierLocale is 'sap(1)'."
    ::= { tlsMldSnpgQuerierEntry 6 }

tlsMldSnpgQuerierSdpId           OBJECT-TYPE
    SYNTAX      SdpId
    MAX-ACCESS  read-only
    STATUS      current
    DESCRIPTION
        "The value of the object tlsMldSnpgQuerierSdpId indicates, together
         with the object tlsMldSnpgQuerierVcId, the SDP Binding on which the
         active Querier is detected.

         The value of this object is only meaningful when the value of
         tlsMldSnpgQuerierLocale is 'sdp(2)'."
    ::= { tlsMldSnpgQuerierEntry 7 }

tlsMldSnpgQuerierVcId            OBJECT-TYPE
    SYNTAX      TmnxVcIdOrNone
    MAX-ACCESS  read-only
    STATUS      current
    DESCRIPTION
        "The value of the object tlsMldSnpgQuerierVcId indicates, together with
         the object tlsMldSnpgQuerierSdpId, the SDP Binding on which the active
         Querier is detected.

         The value of this object is only meaningful when the value of
         tlsMldSnpgQuerierLocale is 'sdp(2)'."
    ::= { tlsMldSnpgQuerierEntry 8 }

tlsMldSnpgQuerierUpTime          OBJECT-TYPE
    SYNTAX      TimeTicks
    MAX-ACCESS  read-only
    STATUS      current
    DESCRIPTION
        "The value of the object tlsMldSnpgQuerierUpTime indicates how long (in
         centiseconds) that this Querier has been known as the current active
         MLD Querier."
    ::= { tlsMldSnpgQuerierEntry 9 }

tlsMldSnpgQuerierExpiryTime      OBJECT-TYPE
    SYNTAX      Unsigned32
    UNITS       "seconds"
    MAX-ACCESS  read-only
    STATUS      current
    DESCRIPTION
        "The value of the object tlsMldSnpgQuerierExpiryTime indicates the time
         in seconds after which this Querier is no longer known as the current
         active MLD Querier."
    ::= { tlsMldSnpgQuerierEntry 10 }

tlsMldSnpgQuerierGenQueryIntvl   OBJECT-TYPE
    SYNTAX      Unsigned32
    UNITS       "seconds"
    MAX-ACCESS  read-only
    STATUS      current
    DESCRIPTION
        "The value of the object tlsMldSnpgQuerierGenQueryIntvl indicates the
         General Query Interval used by the active Querier."
    ::= { tlsMldSnpgQuerierEntry 11 }

tlsMldSnpgQuerierGenRespIntvl    OBJECT-TYPE
    SYNTAX      Unsigned32
    UNITS       "deciseconds"
    MAX-ACCESS  read-only
    STATUS      current
    DESCRIPTION
        "The value of the object tlsMldSnpgQuerierGenRespIntvl indicates the
         General Query Response interval (in 1/10 seconds) used by the active
         Querier."
    ::= { tlsMldSnpgQuerierEntry 12 }

tlsMldSnpgQuerierRobustCount     OBJECT-TYPE
    SYNTAX      Unsigned32
    MAX-ACCESS  read-only
    STATUS      current
    DESCRIPTION
        "The value of the object tlsMldSnpgQuerierRobustCount indicates the
         Robust Count value used by the active Querier."
    ::= { tlsMldSnpgQuerierEntry 13 }

tlsMldSnpgQuerierVRtrId          OBJECT-TYPE
    SYNTAX      TmnxVRtrIDOrZero
    MAX-ACCESS  read-only
    STATUS      current
    DESCRIPTION
        "The value of the object tlsMldSnpgQuerierVRtrId indicates together
         with the object tlsMldSnpgQuerierIfIndex, the rvpls interface on which
         the active Querier is detected.

         The value of this object is only meaningful when the value of
         tlsMldSnpgQuerierLocale is 'rvpls(3)'."
    ::= { tlsMldSnpgQuerierEntry 14 }

tlsMldSnpgQuerierIfIndex         OBJECT-TYPE
    SYNTAX      InterfaceIndexOrZero
    MAX-ACCESS  read-only
    STATUS      current
    DESCRIPTION
        "The value of the object tlsMldSnpgQuerierIfIndex indicates together
         with the object tlsMldSnpgQuerierVRtrId, the rvpls interface on which
         the active Querier is detected.

         The value of this object is only meaningful when the value of
         tlsMldSnpgQuerierLocale is 'rvpls(3)'."
    ::= { tlsMldSnpgQuerierEntry 15 }

tlsMldSnpgQuerierVTEPAddr        OBJECT-TYPE
    SYNTAX      IpAddress
    MAX-ACCESS  read-only
    STATUS      current
    DESCRIPTION
        "The value of the object tlsMldSnpgQuerierVTEPAddr indicates VXLAN
         (virtual extensible LAN) Tunnel Endpoint address of ethernet VPN
         (EVPN) destination on which the active Querier is detected.

         The value of this object is only meaningful when the value of
         tlsMldSnpgQuerierLocale is 'vxlan(4)'."
    ::= { tlsMldSnpgQuerierEntry 16 }

tlsMldSnpgQuerierVNI             OBJECT-TYPE
    SYNTAX      Unsigned32
    MAX-ACCESS  read-only
    STATUS      current
    DESCRIPTION
        "The value of the object tlsMldSnpgQuerierVNI indicates VXLAN (virtual
         extensible LAN) Network Identifier (VNI) of the endpoint of ethernet
         VPN (EVPN) destination interface on which the active Querier is
         detected.

         The value of this object is only meaningful when the value of
         tlsMldSnpgQuerierLocale is 'vxlan(4)'."
    ::= { tlsMldSnpgQuerierEntry 17 }

tlsMldSnpgProxyGroupTable        OBJECT-TYPE
    SYNTAX      SEQUENCE OF TlsMldSnpgProxyGroupEntry
    MAX-ACCESS  not-accessible
    STATUS      current
    DESCRIPTION
        "The table tlsMldSnpgProxyGroupTable contains, together with the table
         tlsMldSnpgProxyGrpSrcTable, multicast group address information
         collected by MLD snooping for this Tls.

         The content of this table is used by the system to 'proxy-report'
         towards the MLD Querier."
    ::= { tmnxMldSnoopingTlsObjs 4 }

tlsMldSnpgProxyGroupEntry        OBJECT-TYPE
    SYNTAX      TlsMldSnpgProxyGroupEntry
    MAX-ACCESS  not-accessible
    STATUS      current
    DESCRIPTION
        "Each entry in this table contains information about a multicast group
         address known in this Tls.

         If a group source list is present, it is described in the
         corresponding entries of the tlsMldSnpgProxyGrpSrcTable table."
    INDEX       {
        svcId,
        tlsMldSnpgProxyGroupAddressType,
        tlsMldSnpgProxyGroupAddress
    }
    ::= { tlsMldSnpgProxyGroupTable 1 }

TlsMldSnpgProxyGroupEntry        ::= SEQUENCE
{
    tlsMldSnpgProxyGroupAddressType  InetAddressType,
    tlsMldSnpgProxyGroupAddress      InetAddress,
    tlsMldSnpgProxyGroupFilterMode   TmnxMldGroupFilterMode,
    tlsMldSnpgProxyGroupUpTime       TimeTicks
}

tlsMldSnpgProxyGroupAddressType  OBJECT-TYPE
    SYNTAX      InetAddressType
    MAX-ACCESS  not-accessible
    STATUS      current
    DESCRIPTION
        "The value of the object tlsMldSnpgProxyGroupAddressType indicates the
         type of tlsMldSnpgProxyGroupAddress."
    ::= { tlsMldSnpgProxyGroupEntry 1 }

tlsMldSnpgProxyGroupAddress      OBJECT-TYPE
    SYNTAX      InetAddress (SIZE (4|16))
    MAX-ACCESS  not-accessible
    STATUS      current
    DESCRIPTION
        "The value of the object tlsMldSnpgProxyGroupAddress indicates the IP
         multicast group address for which this entry contains information."
    ::= { tlsMldSnpgProxyGroupEntry 2 }

tlsMldSnpgProxyGroupFilterMode   OBJECT-TYPE
    SYNTAX      TmnxMldGroupFilterMode
    MAX-ACCESS  read-only
    STATUS      current
    DESCRIPTION
        "The value of the object tlsMldSnpgProxyGroupFilterMode indicates the
         filter-mode for this group."
    ::= { tlsMldSnpgProxyGroupEntry 3 }

tlsMldSnpgProxyGroupUpTime       OBJECT-TYPE
    SYNTAX      TimeTicks
    MAX-ACCESS  read-only
    STATUS      current
    DESCRIPTION
        "The value of the object tlsMldSnpgProxyGroupUpTime indicates how long
         (in centiseconds) that the group address already exists in the
         database."
    ::= { tlsMldSnpgProxyGroupEntry 4 }

tlsMldSnpgProxyGrpSrcTable       OBJECT-TYPE
    SYNTAX      SEQUENCE OF TlsMldSnpgProxyGrpSrcEntry
    MAX-ACCESS  not-accessible
    STATUS      current
    DESCRIPTION
        "The table tlsMldSnpgProxyGrpSrcTable lists the IPv6 multicast sources
         corresponding to the IPv6 multicast groups listed in the
         tlsMldSnpgProxyGroupTable."
    ::= { tmnxMldSnoopingTlsObjs 5 }

tlsMldSnpgProxyGrpSrcEntry       OBJECT-TYPE
    SYNTAX      TlsMldSnpgProxyGrpSrcEntry
    MAX-ACCESS  not-accessible
    STATUS      current
    DESCRIPTION
        "tlsMldSnpgProxyGrpSrcEntry describes an entry in the
         tlsMldSnpgProxyGrpSrcTable.

         Each entry represents an IPv6 multicast source for which the system is
         interested/not interested in receiving multicast traffic from."
    INDEX       {
        svcId,
        tlsMldSnpgProxyGroupAddressType,
        tlsMldSnpgProxyGroupAddress,
        tlsMldSnpgProxyGrpSrcAddrTp,
        tlsMldSnpgProxyGrpSrcAddr
    }
    ::= { tlsMldSnpgProxyGrpSrcTable 1 }

TlsMldSnpgProxyGrpSrcEntry       ::= SEQUENCE
{
    tlsMldSnpgProxyGrpSrcAddrTp      InetAddressType,
    tlsMldSnpgProxyGrpSrcAddr        InetAddress,
    tlsMldSnpgProxyGrpSrcUpTime      TimeTicks
}

tlsMldSnpgProxyGrpSrcAddrTp      OBJECT-TYPE
    SYNTAX      InetAddressType
    MAX-ACCESS  not-accessible
    STATUS      current
    DESCRIPTION
        "The value of the object tlsMldSnpgProxyGrpSrcAddrTp indicates the type
         of tlsMldSnpgProxyGrpSrcAddr."
    ::= { tlsMldSnpgProxyGrpSrcEntry 1 }

tlsMldSnpgProxyGrpSrcAddr        OBJECT-TYPE
    SYNTAX      InetAddress (SIZE (4|16))
    MAX-ACCESS  not-accessible
    STATUS      current
    DESCRIPTION
        "The value of the object tlsMldSnpgProxyGrpSrcAddr indicates the IPv6
         multicast source address."
    ::= { tlsMldSnpgProxyGrpSrcEntry 2 }

tlsMldSnpgProxyGrpSrcUpTime      OBJECT-TYPE
    SYNTAX      TimeTicks
    MAX-ACCESS  read-only
    STATUS      current
    DESCRIPTION
        "The value of the object tlsMldSnpgProxyGrpSrcUpTime indicates how long
         (in centiseconds) that the source address already exists in the
         database."
    ::= { tlsMldSnpgProxyGrpSrcEntry 3 }

tlsMldSnpgMRouterTable           OBJECT-TYPE
    SYNTAX      SEQUENCE OF TlsMldSnpgMRouterEntry
    MAX-ACCESS  not-accessible
    STATUS      current
    DESCRIPTION
        "The table tlsMldSnpgMRouterTable contains information related to the
         multicast routers found in each Tls Service."
    ::= { tmnxMldSnoopingTlsObjs 6 }

tlsMldSnpgMRouterEntry           OBJECT-TYPE
    SYNTAX      TlsMldSnpgMRouterEntry
    MAX-ACCESS  not-accessible
    STATUS      current
    DESCRIPTION
        "Each row contains information about one specific multicast router
         known within a Tls service.

         Entries in this table cannot be created or deleted via SNMP
         operations. An entry in this table will be created by the agent upon
         detection of a multicast router in a Tls service for which MLD
         snooping is enabled (via tlsMldSnpgCfgAdminState)."
    INDEX       {
        svcId,
        tlsMldSnpgMRouterAddressType,
        tlsMldSnpgMRouterAddress
    }
    ::= { tlsMldSnpgMRouterTable 1 }

TlsMldSnpgMRouterEntry           ::= SEQUENCE
{
    tlsMldSnpgMRouterAddressType     InetAddressType,
    tlsMldSnpgMRouterAddress         InetAddress,
    tlsMldSnpgMRouterLocale          TmnxMldSnpgLocation,
    tlsMldSnpgMRouterPortId          TmnxPortID,
    tlsMldSnpgMRouterEncapValue      TmnxEncapVal,
    tlsMldSnpgMRouterSdpId           SdpId,
    tlsMldSnpgMRouterVcId            TmnxVcIdOrNone,
    tlsMldSnpgMRouterVersion         TmnxMldVersion,
    tlsMldSnpgMRouterExpiryTime      Unsigned32,
    tlsMldSnpgMRouterUpTime          TimeTicks,
    tlsMldSnpgMRouterGenQueryIntvl   Unsigned32,
    tlsMldSnpgMRouterGenRespIntvl    Unsigned32,
    tlsMldSnpgMRouterRobustCount     Unsigned32,
    tlsMldSnpgMRouterVRtrId          TmnxVRtrIDOrZero,
    tlsMldSnpgMRouterIfIndex         InterfaceIndexOrZero,
    tlsMldSnpgMRouterVTEPAddr        IpAddress,
    tlsMldSnpgMRouterVNI             Unsigned32
}

tlsMldSnpgMRouterAddressType     OBJECT-TYPE
    SYNTAX      InetAddressType
    MAX-ACCESS  not-accessible
    STATUS      current
    DESCRIPTION
        "The value of the object tlsMldSnpgMRouterAddressType indicates the
         type of tlsMldSnpgMRouterAddress."
    ::= { tlsMldSnpgMRouterEntry 1 }

tlsMldSnpgMRouterAddress         OBJECT-TYPE
    SYNTAX      InetAddress (SIZE (4|16))
    MAX-ACCESS  not-accessible
    STATUS      current
    DESCRIPTION
        "The value of the object tlsMldSnpgMRouterAddress indicates the source
         IP address used by MLD queries sent out by this multicast router."
    ::= { tlsMldSnpgMRouterEntry 2 }

tlsMldSnpgMRouterLocale          OBJECT-TYPE
    SYNTAX      TmnxMldSnpgLocation
    MAX-ACCESS  read-only
    STATUS      current
    DESCRIPTION
        "The value of the object tlsMldSnpgMRouterLocale indicates where this
         multicast router was detected.

         A multicast router found on a local SAP has the value 'sap(1)'. A
         multicast router detected on an SDP has the value 'sdp(2)'."
    ::= { tlsMldSnpgMRouterEntry 3 }

tlsMldSnpgMRouterPortId          OBJECT-TYPE
    SYNTAX      TmnxPortID
    MAX-ACCESS  read-only
    STATUS      current
    DESCRIPTION
        "The value of the object tlsMldSnpgMRouterPortId indicates, together
         with the object tlsMldSnpgMRouterEncapValue, the SAP on which this
         multicast router is detected.

         The value of this object is only meaningful when the value of
         tlsMldSnpgMRouterLocale is 'sap(1)'."
    ::= { tlsMldSnpgMRouterEntry 4 }

tlsMldSnpgMRouterEncapValue      OBJECT-TYPE
    SYNTAX      TmnxEncapVal
    MAX-ACCESS  read-only
    STATUS      current
    DESCRIPTION
        "The value of the object tlsMldSnpgMRouterEncapValue indicates,
         together with the object tlsMldSnpgMRouterPortId, the SAP on which
         this multicast router is detected.

         The value of this object is only meaningful when the value of
         tlsMldSnpgMRouterLocale is 'sap(1)'."
    ::= { tlsMldSnpgMRouterEntry 5 }

tlsMldSnpgMRouterSdpId           OBJECT-TYPE
    SYNTAX      SdpId
    MAX-ACCESS  read-only
    STATUS      current
    DESCRIPTION
        "The value of the object tlsMldSnpgMRouterSdpId indicates, together
         with the object tlsMldSnpgMRouterVcId, the SDP Bind on which this
         multicast router is detected.

         The value of this object is only meaningful when the value of
         tlsMldSnpgMRouterLocale is 'sdp(2)'."
    ::= { tlsMldSnpgMRouterEntry 6 }

tlsMldSnpgMRouterVcId            OBJECT-TYPE
    SYNTAX      TmnxVcIdOrNone
    MAX-ACCESS  read-only
    STATUS      current
    DESCRIPTION
        "The value of the object tlsMldSnpgMRouterVcId indicates, together with
         the object tlsMldSnpgMRouterSdpId, the SDP Bind on which this
         multicast router is detected.

         The value of this object is only meaningful when the value of
         tlsMldSnpgMRouterLocale is 'sdp(2)'."
    ::= { tlsMldSnpgMRouterEntry 7 }

tlsMldSnpgMRouterVersion         OBJECT-TYPE
    SYNTAX      TmnxMldVersion
    MAX-ACCESS  read-only
    STATUS      current
    DESCRIPTION
        "The value of the object tlsMldSnpgMRouterVersion indicates the version
         of the MLD protocol used by this multicast router."
    ::= { tlsMldSnpgMRouterEntry 8 }

tlsMldSnpgMRouterExpiryTime      OBJECT-TYPE
    SYNTAX      Unsigned32
    UNITS       "seconds"
    MAX-ACCESS  read-only
    STATUS      current
    DESCRIPTION
        "The value of the object tlsMldSnpgMRouterExpiryTime indicates the time
         in seconds after which this multicast router is no longer known in
         this Tls."
    ::= { tlsMldSnpgMRouterEntry 9 }

tlsMldSnpgMRouterUpTime          OBJECT-TYPE
    SYNTAX      TimeTicks
    MAX-ACCESS  read-only
    STATUS      current
    DESCRIPTION
        "The value of the object tlsMldSnpgMRouterUpTime indicates how long (in
         centiseconds) that this multicast router has been known in this Tls."
    ::= { tlsMldSnpgMRouterEntry 10 }

tlsMldSnpgMRouterGenQueryIntvl   OBJECT-TYPE
    SYNTAX      Unsigned32
    UNITS       "seconds"
    MAX-ACCESS  read-only
    STATUS      current
    DESCRIPTION
        "The value of the object tlsMldSnpgMRouterGenQueryIntvl indicates the
         General Query Interval used by this multicast router."
    ::= { tlsMldSnpgMRouterEntry 11 }

tlsMldSnpgMRouterGenRespIntvl    OBJECT-TYPE
    SYNTAX      Unsigned32
    UNITS       "deciseconds"
    MAX-ACCESS  read-only
    STATUS      current
    DESCRIPTION
        "The value of the object tlsMldSnpgMRouterGenRespIntvl indicates the
         General Query Response interval (in 1/10 seconds) used by this
         multicast router."
    ::= { tlsMldSnpgMRouterEntry 12 }

tlsMldSnpgMRouterRobustCount     OBJECT-TYPE
    SYNTAX      Unsigned32
    MAX-ACCESS  read-only
    STATUS      current
    DESCRIPTION
        "The value of the object tlsMldSnpgMRouterRobustCount indicates the
         Robust Count value used by this multicast router."
    ::= { tlsMldSnpgMRouterEntry 13 }

tlsMldSnpgMRouterVRtrId          OBJECT-TYPE
    SYNTAX      TmnxVRtrIDOrZero
    MAX-ACCESS  read-only
    STATUS      current
    DESCRIPTION
        "The value of the object tlsMldSnpgMRouterVRtrId indicates, together
         with the object tlsMldSnpgMRouterIfIndex, the rvpls interface on which
         this multicast router is detected.

         The value of this object is only meaningful when the value of
         tlsMldSnpgMRouterLocale is 'rvpls(3)'."
    ::= { tlsMldSnpgMRouterEntry 14 }

tlsMldSnpgMRouterIfIndex         OBJECT-TYPE
    SYNTAX      InterfaceIndexOrZero
    MAX-ACCESS  read-only
    STATUS      current
    DESCRIPTION
        "The value of the object tlsMldSnpgMRouterIfIndex indicates, together
         with the object tlsMldSnpgMRouterVRtrId, the rvpls interface on which
         this multicast router is detected.

         The value of this object is only meaningful when the value of
         tlsMldSnpgMRouterLocale is 'rvpls(3)'."
    ::= { tlsMldSnpgMRouterEntry 15 }

tlsMldSnpgMRouterVTEPAddr        OBJECT-TYPE
    SYNTAX      IpAddress
    MAX-ACCESS  read-only
    STATUS      current
    DESCRIPTION
        "The value of the object tlsMldSnpgMRouterVTEPAddr indicates VXLAN
         (virtual extensible LAN) Tunnel Endpoint address of ethernet VPN
         (EVPN) destination on which this multicast router is detected.

         The value of this object is only meaningful when the value of
         tlsMldSnpgMRouterLocale is 'vxlan(4)'."
    ::= { tlsMldSnpgMRouterEntry 16 }

tlsMldSnpgMRouterVNI             OBJECT-TYPE
    SYNTAX      Unsigned32
    MAX-ACCESS  read-only
    STATUS      current
    DESCRIPTION
        "The value of the object tlsMldSnpgMRouterVNI indicates VXLAN (virtual
         extensible LAN) Network Identifier (VNI) of the endpoint of ethernet
         VPN (EVPN) destination interface on which this multicast router is
         detected.

         The value of this object is only meaningful when the value of
         tlsMldSnpgMRouterLocale is 'vxlan(4)'."
    ::= { tlsMldSnpgMRouterEntry 17 }

tlsMldSnpgEvpnProxyGroupTable    OBJECT-TYPE
    SYNTAX      SEQUENCE OF TlsMldSnpgEvpnProxyGroupEntry
    MAX-ACCESS  not-accessible
    STATUS      current
    DESCRIPTION
        "The table tlsMldSnpgEvpnProxyGroupTable contains, together with the
         table tlsMldSnpgEvpnProxyGrpSrcTable, multicast group address
         information collected by MLD snooping for this Tls.

         The content of this table is used by the system to 'proxy-report'
         towards Bgp IMET destinations supporting evpn-proxy."
    ::= { tmnxMldSnoopingTlsObjs 7 }

tlsMldSnpgEvpnProxyGroupEntry    OBJECT-TYPE
    SYNTAX      TlsMldSnpgEvpnProxyGroupEntry
    MAX-ACCESS  not-accessible
    STATUS      current
    DESCRIPTION
        "Each entry in this table contains information about a multicast group
         address known in this Tls.

         If a group source list is present, it is described in the
         corresponding entries of the tlsMldSnpgEvpnProxyGrpSrcTable table."
    INDEX       {
        svcId,
        tlsMldSnpgEvpnProxyGrpAddressTp,
        tlsMldSnpgEvpnProxyGrpAddress
    }
    ::= { tlsMldSnpgEvpnProxyGroupTable 1 }

TlsMldSnpgEvpnProxyGroupEntry    ::= SEQUENCE
{
    tlsMldSnpgEvpnProxyGrpAddressTp  InetAddressType,
    tlsMldSnpgEvpnProxyGrpAddress    InetAddress,
    tlsMldSnpgEvpnProxyGrpFilterMode TmnxMldGroupFilterMode,
    tlsMldSnpgEvpnProxyGrpUpTime     TimeTicks,
    tlsMldSnpgEvpnProxyGrpV1Support  TruthValue,
    tlsMldSnpgEvpnProxyGrpV2Support  TruthValue
}

tlsMldSnpgEvpnProxyGrpAddressTp  OBJECT-TYPE
    SYNTAX      InetAddressType
    MAX-ACCESS  not-accessible
    STATUS      current
    DESCRIPTION
        "The value of the object tlsMldSnpgEvpnProxyGrpAddressTp indicates the
         type of tlsMldSnpgEvpnProxyGrpAddress."
    ::= { tlsMldSnpgEvpnProxyGroupEntry 1 }

tlsMldSnpgEvpnProxyGrpAddress    OBJECT-TYPE
    SYNTAX      InetAddress (SIZE (4|16))
    MAX-ACCESS  not-accessible
    STATUS      current
    DESCRIPTION
        "The value of the object tlsMldSnpgEvpnProxyGrpAddress indicates the IP
         multicast group address for which this entry contains information."
    ::= { tlsMldSnpgEvpnProxyGroupEntry 2 }

tlsMldSnpgEvpnProxyGrpFilterMode OBJECT-TYPE
    SYNTAX      TmnxMldGroupFilterMode
    MAX-ACCESS  read-only
    STATUS      current
    DESCRIPTION
        "The value of the object tlsMldSnpgEvpnProxyGrpFilterMode indicates the
         filter-mode for this group."
    ::= { tlsMldSnpgEvpnProxyGroupEntry 3 }

tlsMldSnpgEvpnProxyGrpUpTime     OBJECT-TYPE
    SYNTAX      TimeTicks
    MAX-ACCESS  read-only
    STATUS      current
    DESCRIPTION
        "The value of the object tlsMldSnpgEvpnProxyGrpUpTime indicates how
         long (in centiseconds) that the group address already exists in the
         database."
    ::= { tlsMldSnpgEvpnProxyGroupEntry 4 }

tlsMldSnpgEvpnProxyGrpV1Support  OBJECT-TYPE
    SYNTAX      TruthValue
    MAX-ACCESS  read-only
    STATUS      current
    DESCRIPTION
        "The value of the object tlsMldSnpgEvpnProxyGrpV1Support indicates
         whether MLD Version 1 is supported for this group address."
    ::= { tlsMldSnpgEvpnProxyGroupEntry 5 }

tlsMldSnpgEvpnProxyGrpV2Support  OBJECT-TYPE
    SYNTAX      TruthValue
    MAX-ACCESS  read-only
    STATUS      current
    DESCRIPTION
        "The value of the object tlsMldSnpgEvpnProxyGrpV2Support indicates
         whether MLD Version 2 is supported for this group address."
    ::= { tlsMldSnpgEvpnProxyGroupEntry 6 }

tlsMldSnpgEvpnProxyGrpSrcTable   OBJECT-TYPE
    SYNTAX      SEQUENCE OF TlsMldSnpgEvpnProxyGrpSrcEntry
    MAX-ACCESS  not-accessible
    STATUS      current
    DESCRIPTION
        "The table tlsMldSnpgEvpnProxyGrpSrcTable lists the IPv6 multicast
         sources corresponding to the IPv6 multicast groups listed in the
         tlsMldSnpgEvpnProxyGroupTable."
    ::= { tmnxMldSnoopingTlsObjs 8 }

tlsMldSnpgEvpnProxyGrpSrcEntry   OBJECT-TYPE
    SYNTAX      TlsMldSnpgEvpnProxyGrpSrcEntry
    MAX-ACCESS  not-accessible
    STATUS      current
    DESCRIPTION
        "tlsMldSnpgEvpnProxyGrpSrcEntry describes an entry in the
         tlsMldSnpgEvpnProxyGrpSrcTable.

         Each entry represents an IPv6 multicast source for which the system is
         interested/not interested in receiving multicast traffic from."
    INDEX       {
        svcId,
        tlsMldSnpgEvpnProxyGrpAddressTp,
        tlsMldSnpgEvpnProxyGrpAddress,
        tlsMldSnpgEvpnProxyGrpSrcAddrTp,
        tlsMldSnpgEvpnProxyGrpSrcAddr
    }
    ::= { tlsMldSnpgEvpnProxyGrpSrcTable 1 }

TlsMldSnpgEvpnProxyGrpSrcEntry   ::= SEQUENCE
{
    tlsMldSnpgEvpnProxyGrpSrcAddrTp  InetAddressType,
    tlsMldSnpgEvpnProxyGrpSrcAddr    InetAddress,
    tlsMldSnpgEvpnProxyGrpSrcUpTime  TimeTicks
}

tlsMldSnpgEvpnProxyGrpSrcAddrTp  OBJECT-TYPE
    SYNTAX      InetAddressType
    MAX-ACCESS  not-accessible
    STATUS      current
    DESCRIPTION
        "The value of the object tlsMldSnpgEvpnProxyGrpSrcAddrTp indicates the
         type of tlsMldSnpgEvpnProxyGrpSrcAddr."
    ::= { tlsMldSnpgEvpnProxyGrpSrcEntry 1 }

tlsMldSnpgEvpnProxyGrpSrcAddr    OBJECT-TYPE
    SYNTAX      InetAddress (SIZE (4|16))
    MAX-ACCESS  not-accessible
    STATUS      current
    DESCRIPTION
        "The value of the object tlsMldSnpgEvpnProxyGrpSrcAddr indicates the
         IPv6 multicast source address."
    ::= { tlsMldSnpgEvpnProxyGrpSrcEntry 2 }

tlsMldSnpgEvpnProxyGrpSrcUpTime  OBJECT-TYPE
    SYNTAX      TimeTicks
    MAX-ACCESS  read-only
    STATUS      current
    DESCRIPTION
        "The value of the object tlsMldSnpgEvpnProxyGrpSrcUpTime indicates how
         long (in centiseconds) that the source address already exists in the
         database."
    ::= { tlsMldSnpgEvpnProxyGrpSrcEntry 3 }

tmnxMldSnoopingSapObjs           OBJECT IDENTIFIER ::= { tmnxMldSnoopingObjs 2 }

sapMldSnpgConfigTableLastChange  OBJECT-TYPE
    SYNTAX      TimeStamp
    MAX-ACCESS  read-only
    STATUS      current
    DESCRIPTION
        "The value of the object sapMldSnpgConfigTableLastChange indicates the
         value of sysUpTime at the time of the last modification of an entry in
         the sapMldSnpgConfigTable."
    ::= { tmnxMldSnoopingSapObjs 1 }

sapMldSnpgConfigTable            OBJECT-TYPE
    SYNTAX      SEQUENCE OF SapMldSnpgConfigEntry
    MAX-ACCESS  not-accessible
    STATUS      current
    DESCRIPTION
        "The  sapMldSnpgConfigTable contains objects to configure the MLD
         snooping feature on a SAP within a Tls."
    ::= { tmnxMldSnoopingSapObjs 2 }

sapMldSnpgConfigEntry            OBJECT-TYPE
    SYNTAX      SapMldSnpgConfigEntry
    MAX-ACCESS  not-accessible
    STATUS      current
    DESCRIPTION
        "Each row contains MLD snooping configuration parameters for a SAP
         within a Tls.

         Entries in this table cannot be created or deleted via SNMP
         operations. An entry in this table will be created by the agent upon
         creation of a new SAP (sapTlsInfoTable). The entry is destroyed when
         the SAP or Tls service is removed."
    INDEX       {
        svcId,
        sapPortId,
        sapEncapValue
    }
    ::= { sapMldSnpgConfigTable 1 }

SapMldSnpgConfigEntry            ::= SEQUENCE
{
    sapMldSnpgCfgLastChangeTime      TimeStamp,
    sapMldSnpgCfgImportPlcy          TPolicyStatementNameOrEmpty,
    sapMldSnpgCfgFastLeave           TmnxAdminState,
    sapMldSnpgCfgMRouter             TruthValue,
    sapMldSnpgCfgSendQueries         TmnxAdminState,
    sapMldSnpgCfgGenQueryIntvl       Unsigned32,
    sapMldSnpgCfgQueryRespIntvl      Unsigned32,
    sapMldSnpgCfgRobustCount         Unsigned32,
    sapMldSnpgCfgLastMembIntvl       Unsigned32,
    sapMldSnpgCfgMaxNbrGrps          Integer32,
    sapMldSnpgCfgMvrFromVplsId       TmnxServId,
    sapMldSnpgCfgMvrToSapPortId      TmnxPortID,
    sapMldSnpgCfgMvrToSapEncapVal    TmnxEncapVal,
    sapMldSnpgCfgVersion             TmnxMldVersion,
    sapMldSnpgCfgDisRtrAlertChk      TruthValue,
    sapMldSnpgCfgMcacPolicyName      TPolicyStatementNameOrEmpty,
    sapMldSnpgCfgMcacUnconstBW       Integer32,
    sapMldSnpgCfgMcacPrRsvMndBW      Integer32,
    sapMldSnpgCfgMcacConstAdmSt      TmnxAdminState,
    sapMldSnpgCfgMcacinUseMandBw     Unsigned32,
    sapMldSnpgCfgMcacinUseOpnlBw     Unsigned32,
    sapMldSnpgCfgMcacAvailMandBw     Unsigned32,
    sapMldSnpgCfgMcacAvailOpnlBw     Unsigned32,
    sapMldSnpgCfgMcacValInTrans      TruthValue,
    sapMldSnpgCfgMcacUseLagPortWt    TruthValue,
    sapMldSnpgCfgMcacIfPolicyName    TPolicyStatementNameOrEmpty
}

sapMldSnpgCfgLastChangeTime      OBJECT-TYPE
    SYNTAX      TimeStamp
    MAX-ACCESS  read-only
    STATUS      current
    DESCRIPTION
        "The value of the object sapMldSnpgCfgLastChangeTime indicates the
         sysUpTime at the time of the last modification of this entry."
    ::= { sapMldSnpgConfigEntry 1 }

sapMldSnpgCfgImportPlcy          OBJECT-TYPE
    SYNTAX      TPolicyStatementNameOrEmpty
    MAX-ACCESS  read-write
    STATUS      current
    DESCRIPTION
        "The value of the object sapMldSnpgCfgImportPlcy specifies the policy
         statement that must be applied to all incoming MLD messages on this
         SAP."
    DEFVAL      { "" }
    ::= { sapMldSnpgConfigEntry 2 }

sapMldSnpgCfgFastLeave           OBJECT-TYPE
    SYNTAX      TmnxAdminState
    MAX-ACCESS  read-write
    STATUS      current
    DESCRIPTION
        "The value of the object sapMldSnpgCfgFastLeave specifies whether fast
         leave is allowed on this SAP.

         If set to 'inService(2)', the system prunes the port on which an MLD
         'leave' message has been received, without waiting for the Group
         Specific Query to timeout."
    DEFVAL      { outOfService }
    ::= { sapMldSnpgConfigEntry 3 }

sapMldSnpgCfgMRouter             OBJECT-TYPE
    SYNTAX      TruthValue
    MAX-ACCESS  read-write
    STATUS      current
    DESCRIPTION
        "The value of the object sapMldSnpgCfgMRouter specifies whether a
         multicast router is attached behind this SAP.

         If sapMldSnpgCfgSendQueries is set to 'inService(2)', the system acts
         as if this object was set to 'false(2)'."
    DEFVAL      { false }
    ::= { sapMldSnpgConfigEntry 4 }

sapMldSnpgCfgSendQueries         OBJECT-TYPE
    SYNTAX      TmnxAdminState
    MAX-ACCESS  read-write
    STATUS      current
    DESCRIPTION
        "The value of the object sapMldSnpgCfgSendQueries specifies whether the
         system generates General Queries by itself on this SAP."
    DEFVAL      { outOfService }
    ::= { sapMldSnpgConfigEntry 5 }

sapMldSnpgCfgGenQueryIntvl       OBJECT-TYPE
    SYNTAX      Unsigned32 (2..1024)
    UNITS       "seconds"
    MAX-ACCESS  read-write
    STATUS      current
    DESCRIPTION
        "The value of the object sapMldSnpgCfgGenQueryIntvl specifies the
         interval (in seconds) between two consecutive general queries sent by
         the system on this SAP.

         The value of this object is only meaningful when the value of
         sapMldSnpgCfgSendQueries is 'inService(2)'."
    DEFVAL      { 125 }
    ::= { sapMldSnpgConfigEntry 6 }

sapMldSnpgCfgQueryRespIntvl      OBJECT-TYPE
    SYNTAX      Unsigned32 (1..1023)
    UNITS       "seconds"
    MAX-ACCESS  read-write
    STATUS      current
    DESCRIPTION
        "The value of the object sapMldSnpgCfgQueryRespIntvl specifies the
         maximum response time (in seconds) advertised in MLD queries.

         The value of this object is only meaningful when the value of
         sapMldSnpgCfgSendQueries is 'inService(2)'."
    DEFVAL      { 10 }
    ::= { sapMldSnpgConfigEntry 7 }

sapMldSnpgCfgRobustCount         OBJECT-TYPE
    SYNTAX      Unsigned32 (2..7)
    MAX-ACCESS  read-write
    STATUS      current
    DESCRIPTION
        "The value of the object sapMldSnpgCfgRobustCount specifies the
         robustness variable on this SAP.

         This object allows tuning for the expected packet loss on this SAP. If
         a SAP is expected to be lossy, the Robustness Variable may be
         increased. MLD snooping is robust to (Robustness Variable-1) packet
         losses.

         The value of this object is only meaningful when the value of
         sapMldSnpgCfgSendQueries is 'inService(2)'."
    DEFVAL      { 2 }
    ::= { sapMldSnpgConfigEntry 8 }

sapMldSnpgCfgLastMembIntvl       OBJECT-TYPE
    SYNTAX      Unsigned32 (1..50)
    UNITS       "deciseconds"
    MAX-ACCESS  read-write
    STATUS      current
    DESCRIPTION
        "The value of the object sapMldSnpgCfgLastMembIntvl specifies the Max
         Response Time (in deciseconds) used in Group-Specific and
         Group-Source-Specific Queries sent in response to 'leave' messages.
         This is also the amount of time between Group-Specific Query messages.

         This value may be tuned to modify the leave latency of the network. A
         reduced value results in reduced time to detect the loss of the last
         member of a group."
    DEFVAL      { 10 }
    ::= { sapMldSnpgConfigEntry 9 }

sapMldSnpgCfgMaxNbrGrps          OBJECT-TYPE
    SYNTAX      Integer32 (0..16000)
    MAX-ACCESS  read-write
    STATUS      current
    DESCRIPTION
        "The value of the object sapMldSnpgCfgMaxNbrGrps specifies how many
         group addresses are allowed for this SAP.

         The value 0 means that no limit is imposed."
    DEFVAL      { 0 }
    ::= { sapMldSnpgConfigEntry 10 }

sapMldSnpgCfgMvrFromVplsId       OBJECT-TYPE
    SYNTAX      TmnxServId
    MAX-ACCESS  read-write
    STATUS      current
    DESCRIPTION
        "The value of the object sapMldSnpgCfgMvrFromVplsId specifies from
         which Tls the multicast streams corresponding to the groups learned
         via this SAP are copied.

         Groups which cannot be joined to the corresponding MVR Tls (because
         MVR is not up or the configured MVR policy rejects the group) copy the
         multicast streams from the local Tls if MLD snooping is up (i.e.
         tlsMldSnpgCfgAdminState is 'inService(2)')."
    DEFVAL      { 0 }
    ::= { sapMldSnpgConfigEntry 11 }

sapMldSnpgCfgMvrToSapPortId      OBJECT-TYPE
    SYNTAX      TmnxPortID
    MAX-ACCESS  read-write
    STATUS      current
    DESCRIPTION
        "The value of the object sapMldSnpgCfgMvrToSapPortId specifies,
         together with sapMldSnpgCfgMvrToSapEncapVal, the SAP to which the
         multicast streams corresponding to the groups learned via this SAP are
         copied. As a consequence, the streams will not exit this SAP anymore."
    DEFVAL      { 0 }
    ::= { sapMldSnpgConfigEntry 12 }

sapMldSnpgCfgMvrToSapEncapVal    OBJECT-TYPE
    SYNTAX      TmnxEncapVal
    MAX-ACCESS  read-write
    STATUS      current
    DESCRIPTION
        "The value of the object sapMldSnpgCfgMvrToSapEncapVal specifies,
         together with sapMldSnpgCfgMvrToSapPortId, the SAP to which the
         multicast streams corresponding to the groups learned via this SAP are
         copied. As a consequence, the streams will not exit this SAP anymore."
    DEFVAL      { 0 }
    ::= { sapMldSnpgConfigEntry 13 }

sapMldSnpgCfgVersion             OBJECT-TYPE
    SYNTAX      TmnxMldVersion
    MAX-ACCESS  read-write
    STATUS      current
    DESCRIPTION
        "The value of the object sapMldSnpgCfgVersion specifies the version of
         MLD running on this SAP."
    DEFVAL      { version2 }
    ::= { sapMldSnpgConfigEntry 14 }

sapMldSnpgCfgDisRtrAlertChk      OBJECT-TYPE
    SYNTAX      TruthValue
    MAX-ACCESS  read-write
    STATUS      current
    DESCRIPTION
        "sapMldSnpgCfgDisRtrAlertChk is used to enable/disable router alert
         checking for IGMP messages received on this sap.

         If this flag is set to 'true', checking is disabled."
    DEFVAL      { false }
    ::= { sapMldSnpgConfigEntry 15 }

sapMldSnpgCfgMcacPolicyName      OBJECT-TYPE
    SYNTAX      TPolicyStatementNameOrEmpty
    MAX-ACCESS  read-write
    STATUS      current
    DESCRIPTION
        "The value of sapMldSnpgCfgMcacPolicyName specifies the name of the
         multicast CAC (Connection Admission Control) policy."
    DEFVAL      { "" }
    ::= { sapMldSnpgConfigEntry 16 }

sapMldSnpgCfgMcacUnconstBW       OBJECT-TYPE
    SYNTAX      Integer32 (-1 | 0..2147483647)
    UNITS       "kilobps"
    MAX-ACCESS  read-write
    STATUS      current
    DESCRIPTION
        "The value of sapMldSnpgCfgMcacUnconstBW specifies the bandwidth
         assigned for interface's multicast CAC policy traffic in kilobits per
         second(kbps).

         If the default value of '-1' is set, there is no constraint on
         bandwidth allocated at the interface.

         If the value of sapMldSnpgCfgMcacUnconstBW is set to '0' and if a
         multicast CAC policy is assigned on the interface, then no group
         (channel) from that policy is allowed on that interface."
    DEFVAL      { -1 }
    ::= { sapMldSnpgConfigEntry 17 }

sapMldSnpgCfgMcacPrRsvMndBW      OBJECT-TYPE
    SYNTAX      Integer32 (-1 | 0..2147483647)
    UNITS       "kilobps"
    MAX-ACCESS  read-write
    STATUS      current
    DESCRIPTION
        "The value of sapMldSnpgCfgMcacPrRsvMndBW specifies the bandwidth
         pre-reserved for all the mandatory channels on a given interface in
         kilobits per second(kbps).

         If the value of sapMldSnpgCfgMcacUnconstBW is '0', no mandatory
         channels are allowed. If the value of sapMldSnpgCfgMcacPrRsvMndBW is
         '-1', then all mandatory and optional channels are allowed.

         If the value of sapMldSnpgCfgMcacPrRsvMndBW is equal to the value of
         sapMldSnpgCfgMcacUnconstBW, then all the unconstrained bandwidth on a
         given interface is allocated to mandatory channels configured through
         multicast CAC policy on that interface and no optional groups
         (channels) are allowed.

         The value of sapMldSnpgCfgMcacPrRsvMndBW should always be less than or
         equal to that of sapMldSnpgCfgMcacUnconstBW. An attempt to set the
         value of sapMldSnpgCfgMcacPrRsvMndBW greater than that of
         sapMldSnpgCfgMcacUnconstBW will result in inconsistent value error."
    DEFVAL      { -1 }
    ::= { sapMldSnpgConfigEntry 18 }

sapMldSnpgCfgMcacConstAdmSt      OBJECT-TYPE
    SYNTAX      TmnxAdminState
    MAX-ACCESS  read-write
    STATUS      current
    DESCRIPTION
        "The value of sapMldSnpgCfgMcacConstAdmSt specifies the administrative
         state of the multicast CAC policy's constraints."
    DEFVAL      { inService }
    ::= { sapMldSnpgConfigEntry 19 }

sapMldSnpgCfgMcacinUseMandBw     OBJECT-TYPE
    SYNTAX      Unsigned32
    UNITS       "kilobps"
    MAX-ACCESS  read-only
    STATUS      current
    DESCRIPTION
        "The value of sapMldSnpgCfgMcacinUseMandBw indicates the in-use
         bandwidth in kilobits per second(kbps) for the mandatory channels for
         this protocol interface instance."
    ::= { sapMldSnpgConfigEntry 20 }

sapMldSnpgCfgMcacinUseOpnlBw     OBJECT-TYPE
    SYNTAX      Unsigned32
    UNITS       "kilobps"
    MAX-ACCESS  read-only
    STATUS      current
    DESCRIPTION
        "The value of sapMldSnpgCfgMcacinUseOpnlBw indicates the in-use
         bandwidth in kilobits per second(kbps) for the optional channels for
         this protocol interface instance."
    ::= { sapMldSnpgConfigEntry 21 }

sapMldSnpgCfgMcacAvailMandBw     OBJECT-TYPE
    SYNTAX      Unsigned32
    UNITS       "kilobps"
    MAX-ACCESS  read-only
    STATUS      current
    DESCRIPTION
        "The value of sapMldSnpgCfgMcacAvailMandBw indicates the pre-reserved
         bandwidth in kilobits per second(kbps) for the mandatory channels for
         this interface instance."
    ::= { sapMldSnpgConfigEntry 22 }

sapMldSnpgCfgMcacAvailOpnlBw     OBJECT-TYPE
    SYNTAX      Unsigned32
    UNITS       "kilobps"
    MAX-ACCESS  read-only
    STATUS      current
    DESCRIPTION
        "The value of sapMldSnpgCfgMcacAvailOpnlBw indicates the available
         bandwidth in kilobits per second(kbps) for this interface instance."
    ::= { sapMldSnpgConfigEntry 23 }

sapMldSnpgCfgMcacValInTrans      OBJECT-TYPE
    SYNTAX      TruthValue
    MAX-ACCESS  read-only
    STATUS      current
    DESCRIPTION
        "The value of sapMldSnpgCfgMcacValInTrans indicates that the
         operational (available and in-use mandatory/optional) value for the
         following objects are in transition due to configuration change:

         sapMldSnpgCfgMcacinUseMandBw sapMldSnpgCfgMcacinUseOpnlBw
         sapMldSnpgCfgMcacAvailMandBw sapMldSnpgCfgMcacAvailOpnlBw

         When multicast CAC Policy is applied on the interface for the join of
         the next channel, the operational values will be recalculated and
         applied to the above objects and the value for
         sapMldSnpgCfgMcacValInTrans will be set to 'false(2)'.

         If the value of sapMldSnpgCfgMcacValInTrans is 'true(1)' then the
         values are in transition."
    ::= { sapMldSnpgConfigEntry 24 }

sapMldSnpgCfgMcacUseLagPortWt    OBJECT-TYPE
    SYNTAX      TruthValue
    MAX-ACCESS  read-write
    STATUS      current
    DESCRIPTION
        "The value of sapMldSnpgCfgMcacUseLagPortWt specifies if this system
         must use the LAG port weight while calculating Multicast CAC
         constraints.

         The LAG port weight is configured with the object
         TIMETRA-LAG-MIB::tLagPortWeightSpeed."
    DEFVAL      { false }
    ::= { sapMldSnpgConfigEntry 25 }

sapMldSnpgCfgMcacIfPolicyName    OBJECT-TYPE
    SYNTAX      TPolicyStatementNameOrEmpty
    MAX-ACCESS  read-write
    STATUS      current
    DESCRIPTION
        "The value of sapMldSnpgCfgMcacIfPolicyName specifies the name of the
         multicast CAC (Connection Admission Control) interface policy."
    DEFVAL      { "" }
    ::= { sapMldSnpgConfigEntry 26 }

sapMldSnpgGroupTable             OBJECT-TYPE
    SYNTAX      SEQUENCE OF SapMldSnpgGroupEntry
    MAX-ACCESS  not-accessible
    STATUS      current
    DESCRIPTION
        "sapMldSnpgGroupTable contains, together with the table
         sapMldSnpgGrpSrcTable, multicast group address information collected
         by MLD snooping for each SAP."
    ::= { tmnxMldSnoopingSapObjs 3 }

sapMldSnpgGroupEntry             OBJECT-TYPE
    SYNTAX      SapMldSnpgGroupEntry
    MAX-ACCESS  not-accessible
    STATUS      current
    DESCRIPTION
        "Each entry in this table indicates a multicast group address learned
         by MLD snooping on this SAP.

         If a source list is present, it is described in the corresponding
         entries of the sapMldSnpgGrpSrcTable table."
    INDEX       {
        svcId,
        sapPortId,
        sapEncapValue,
        sapMldSnpgGrpAddressType,
        sapMldSnpgGrpAddress
    }
    ::= { sapMldSnpgGroupTable 1 }

SapMldSnpgGroupEntry             ::= SEQUENCE
{
    sapMldSnpgGrpAddressType         InetAddressType,
    sapMldSnpgGrpAddress             InetAddress,
    sapMldSnpgGrpType                TmnxMldGroupType,
    sapMldSnpgGrpFilterMode          TmnxMldGroupFilterMode,
    sapMldSnpgGrpUpTime              TimeTicks,
    sapMldSnpgGrpExpiryTime          Unsigned32,
    sapMldSnpgGrpCompatMode          Unsigned32,
    sapMldSnpgGrpV1HostExpTime       Unsigned32,
    sapMldSnpgGrpMvrFromVplsId       TmnxServId,
    sapMldSnpgGrpMvrToSapPortId      TmnxPortID,
    sapMldSnpgGrpMvrToSapEncapVal    TmnxEncapVal
}

sapMldSnpgGrpAddressType         OBJECT-TYPE
    SYNTAX      InetAddressType
    MAX-ACCESS  not-accessible
    STATUS      current
    DESCRIPTION
        "The value of the object sapMldSnpgGrpAddressType indicates the type of
         sapMldSnpgGrpAddress."
    ::= { sapMldSnpgGroupEntry 1 }

sapMldSnpgGrpAddress             OBJECT-TYPE
    SYNTAX      InetAddress (SIZE (4|16))
    MAX-ACCESS  not-accessible
    STATUS      current
    DESCRIPTION
        "The value of the object sapMldSnpgGrpAddress indicates the IPv6
         multicast group address for which this entry contains information."
    ::= { sapMldSnpgGroupEntry 2 }

sapMldSnpgGrpType                OBJECT-TYPE
    SYNTAX      TmnxMldGroupType
    MAX-ACCESS  read-only
    STATUS      current
    DESCRIPTION
        "The value of the object sapMldSnpgGrpType indicates whether this entry
         was learned dynamically or was statically configured."
    ::= { sapMldSnpgGroupEntry 3 }

sapMldSnpgGrpFilterMode          OBJECT-TYPE
    SYNTAX      TmnxMldGroupFilterMode
    MAX-ACCESS  read-only
    STATUS      current
    DESCRIPTION
        "The value of the object sapMldSnpgGrpFilterMode indicates the
         filter-mode for this group."
    ::= { sapMldSnpgGroupEntry 4 }

sapMldSnpgGrpUpTime              OBJECT-TYPE
    SYNTAX      TimeTicks
    MAX-ACCESS  read-only
    STATUS      current
    DESCRIPTION
        "The value of the object sapMldSnpgGrpUpTime indicates how long (in
         centiseconds) that the group address already exists in the database
         for this SAP."
    ::= { sapMldSnpgGroupEntry 5 }

sapMldSnpgGrpExpiryTime          OBJECT-TYPE
    SYNTAX      Unsigned32
    UNITS       "seconds"
    MAX-ACCESS  read-only
    STATUS      current
    DESCRIPTION
        "The value of the object sapMldSnpgGrpExpiryTime indicates the amount
         of time remaining before this entry will be aged out."
    ::= { sapMldSnpgGroupEntry 6 }

sapMldSnpgGrpCompatMode          OBJECT-TYPE
    SYNTAX      Unsigned32
    MAX-ACCESS  read-only
    STATUS      current
    DESCRIPTION
        "The value of the object sapMldSnpgGrpCompatMode indicates
         the MLD version applicable  on this SAP for this multicast group
         address. This corresponds to the lowest version seen for this group
         address on this SAP."
    ::= { sapMldSnpgGroupEntry 7 }

sapMldSnpgGrpV1HostExpTime       OBJECT-TYPE
    SYNTAX      Unsigned32
    UNITS       "seconds"
    MAX-ACCESS  read-only
    STATUS      current
    DESCRIPTION
        "The value of the object sapMldSnpgGrpV1HostExpTime indicates the time
         remaining until the system will assume that there are no longer any
         MLDv1 members on this SAP.

         Upon hearing any MLDv1 Membership Report, this value is reset to the
         group membership interval. While this time remaining is non-zero, the
         system ignores any MLDv2 'leave' messages for this group that it
         receives on this SAP."
    ::= { sapMldSnpgGroupEntry 8 }

sapMldSnpgGrpMvrFromVplsId       OBJECT-TYPE
    SYNTAX      TmnxServId
    MAX-ACCESS  read-only
    STATUS      current
    DESCRIPTION
        "The value of the object sapMldSnpgGrpMvrFromVplsId indicates from
         which Tls the multicast streams corresponding to this group are
         copied.

         A value of 0 means that MVR is not applicable for this group and the
         corresponding streams is copied from the local Tls."
    ::= { sapMldSnpgGroupEntry 9 }

sapMldSnpgGrpMvrToSapPortId      OBJECT-TYPE
    SYNTAX      TmnxPortID
    MAX-ACCESS  read-only
    STATUS      current
    DESCRIPTION
        "The value of the object sapMldSnpgGrpMvrToSapPortId indicates,
         together with sapMldSnpgGrpMvrToSapEncapVal, the SAP to which the
         multicast streams corresponding to this group are copied.

         If both values are 0, the corresponding streams are copied to this
         local SAP."
    ::= { sapMldSnpgGroupEntry 10 }

sapMldSnpgGrpMvrToSapEncapVal    OBJECT-TYPE
    SYNTAX      TmnxEncapVal
    MAX-ACCESS  read-only
    STATUS      current
    DESCRIPTION
        "The value of the object sapMldSnpgGrpMvrToSapEncapVal indicates,
         together with sapMldSnpgGrpMvrToSapPortId, the SAP to which the
         multicast streams corresponding to this group are copied.

         If both values are 0, the corresponding streams are copied to this
         local SAP."
    ::= { sapMldSnpgGroupEntry 11 }

sapMldSnpgGrpSrcTable            OBJECT-TYPE
    SYNTAX      SEQUENCE OF SapMldSnpgGrpSrcEntry
    MAX-ACCESS  not-accessible
    STATUS      current
    DESCRIPTION
        "sapMldSnpgGrpSrcTable lists the IPv6 multicast sources corresponding
         to the IPv6 multicast groups listed in the sapMldSnpgGroupTable."
    ::= { tmnxMldSnoopingSapObjs 4 }

sapMldSnpgGrpSrcEntry            OBJECT-TYPE
    SYNTAX      SapMldSnpgGrpSrcEntry
    MAX-ACCESS  not-accessible
    STATUS      current
    DESCRIPTION
        "An entry in the sapMldSnpgGrpSrcTable. Each entry represents a source
         address from which receivers are interested/not interested in
         receiving multicast traffic from."
    INDEX       {
        svcId,
        sapPortId,
        sapEncapValue,
        sapMldSnpgGrpAddressType,
        sapMldSnpgGrpAddress,
        sapMldSnpgGrpSrcAddrType,
        sapMldSnpgGrpSrcAddr
    }
    ::= { sapMldSnpgGrpSrcTable 1 }

SapMldSnpgGrpSrcEntry            ::= SEQUENCE
{
    sapMldSnpgGrpSrcAddrType         InetAddressType,
    sapMldSnpgGrpSrcAddr             InetAddress,
    sapMldSnpgGrpSrcType             TmnxMldGroupType,
    sapMldSnpgGrpSrcUpTime           TimeTicks,
    sapMldSnpgGrpSrcExpiryTime       Unsigned32,
    sapMldSnpgGrpSrcFwdOrBlk         INTEGER
}

sapMldSnpgGrpSrcAddrType         OBJECT-TYPE
    SYNTAX      InetAddressType
    MAX-ACCESS  not-accessible
    STATUS      current
    DESCRIPTION
        "The value of the object sapMldSnpgGrpSrcAddrType indicates the type of
         sapMldSnpgGrpSrcAddr."
    ::= { sapMldSnpgGrpSrcEntry 1 }

sapMldSnpgGrpSrcAddr             OBJECT-TYPE
    SYNTAX      InetAddress (SIZE (4|16))
    MAX-ACCESS  not-accessible
    STATUS      current
    DESCRIPTION
        "The value of the object sapMldSnpgGrpSrcAddr indicates the address of
         the source sending multicast traffic to the group identified by
         sapMldSnpgGrpAddress.

         If the value of sapMldSnpgGrpFilterMode corresponding to this entry is
         'include(1)', the receivers are interested in receiving traffic from
         this source.

         If the value of sapMldSnpgGrpFilterMode corresponding to this entry is
         'exclude(2)', the receivers are not interested in receiving traffic
         from this source."
    ::= { sapMldSnpgGrpSrcEntry 2 }

sapMldSnpgGrpSrcType             OBJECT-TYPE
    SYNTAX      TmnxMldGroupType
    MAX-ACCESS  read-only
    STATUS      current
    DESCRIPTION
        "The value of the object sapMldSnpgGrpSrcType indicates how this source
         entry was learned.

         If this source entry was learned, this object is set to 'dynamic(2)'.
         For statically configured sources, this object is set to 'static(1)'."
    ::= { sapMldSnpgGrpSrcEntry 3 }

sapMldSnpgGrpSrcUpTime           OBJECT-TYPE
    SYNTAX      TimeTicks
    MAX-ACCESS  read-only
    STATUS      current
    DESCRIPTION
        "The value of the object sapMldSnpgGrpSrcUpTime indicates how long (in
         centiseconds) that the source address already exists in the database
         for this SAP."
    ::= { sapMldSnpgGrpSrcEntry 4 }

sapMldSnpgGrpSrcExpiryTime       OBJECT-TYPE
    SYNTAX      Unsigned32
    UNITS       "seconds"
    MAX-ACCESS  read-only
    STATUS      current
    DESCRIPTION
        "The value of the object sapMldSnpgGrpSrcExpiryTime indicates the
         minimum amount of time remaining before this entry will be aged out.

         If the value of sapMldSnpgGrpSrcExpiryTime is non-zero and the value
         of sapMldSnpgGrpFilterMode corresponding to this entry is
         'include(1)', it means that there are currently one or more systems
         which desire to receive multicast traffic for this source.

         If this timer expires and the value of sapMldSnpgGrpFilterMode is
         'include(1)', the system concludes that traffic from this particular
         source is no longer desired on the attached network, and deletes this
         entry.

         If the value of sapMldSnpgGrpSrcExpiryTime is non-zero and the
         filter-mode for the group is 'exclude(2)', it means that at least one
         system desires to receive multicast traffic from this source.

         If the value of sapMldSnpgGrpSrcExpiryTime is zero and the filter-mode
         for the group is 'exclude(2)', it means that no system desires to
         receive multicast traffic from this source."
    ::= { sapMldSnpgGrpSrcEntry 5 }

sapMldSnpgGrpSrcFwdOrBlk         OBJECT-TYPE
    SYNTAX      INTEGER {
        forward (1),
        block   (2)
    }
    MAX-ACCESS  read-only
    STATUS      current
    DESCRIPTION
        "sapMldSnpgGrpSrcFwdOrBlk indicates whether this entry is on the
         forward list or block list."
    ::= { sapMldSnpgGrpSrcEntry 6 }

sapMldSnpgStaticGrpSrcTableLstCh OBJECT-TYPE
    SYNTAX      TimeStamp
    MAX-ACCESS  read-only
    STATUS      current
    DESCRIPTION
        "The value of the object sapMldSnpgStaticGrpSrcTableLstCh indicates the
         value of sysUpTime at the time of the last modification of an entry in
         the sapMldSnpgStaticGrpSrcTable."
    ::= { tmnxMldSnoopingSapObjs 5 }

sapMldSnpgStaticGrpSrcTable      OBJECT-TYPE
    SYNTAX      SEQUENCE OF SapMldSnpgStaticGrpSrcEntry
    MAX-ACCESS  not-accessible
    STATUS      current
    DESCRIPTION
        "The table sapMldSnpgStaticGrpSrcTable contains statically configured
         (S,G) entries for each SAP."
    ::= { tmnxMldSnoopingSapObjs 6 }

sapMldSnpgStaticGrpSrcEntry      OBJECT-TYPE
    SYNTAX      SapMldSnpgStaticGrpSrcEntry
    MAX-ACCESS  not-accessible
    STATUS      current
    DESCRIPTION
        "An entry in the sapMldSnpgStaticGrpSrcTable. Entries can be created or
         deleted by an SNMP SET request to sapMldSnpgStaticRowstatus."
    INDEX       {
        svcId,
        sapPortId,
        sapEncapValue,
        sapMldSnpgStaticGroupAddrType,
        sapMldSnpgStaticGroupAddr,
        sapMldSnpgStaticSourceAddrType,
        sapMldSnpgStaticSourceAddr
    }
    ::= { sapMldSnpgStaticGrpSrcTable 1 }

SapMldSnpgStaticGrpSrcEntry      ::= SEQUENCE
{
    sapMldSnpgStaticGroupAddrType    InetAddressType,
    sapMldSnpgStaticGroupAddr        InetAddress,
    sapMldSnpgStaticSourceAddrType   InetAddressType,
    sapMldSnpgStaticSourceAddr       InetAddress,
    sapMldSnpgStaticRowstatus        RowStatus,
    sapMldSnpgStaticLastChangeTime   TimeStamp
}

sapMldSnpgStaticGroupAddrType    OBJECT-TYPE
    SYNTAX      InetAddressType
    MAX-ACCESS  not-accessible
    STATUS      current
    DESCRIPTION
        "The value of the object sapMldSnpgStaticGroupAddrType specifies the
         type of sapMldSnpgStaticGroupAddr."
    ::= { sapMldSnpgStaticGrpSrcEntry 1 }

sapMldSnpgStaticGroupAddr        OBJECT-TYPE
    SYNTAX      InetAddress (SIZE (4|16))
    MAX-ACCESS  not-accessible
    STATUS      current
    DESCRIPTION
        "The value of the object sapMldSnpgStaticGroupAddr specifies the group
         multicast address for this statically configured (S,G) entry for this
         SAP."
    ::= { sapMldSnpgStaticGrpSrcEntry 2 }

sapMldSnpgStaticSourceAddrType   OBJECT-TYPE
    SYNTAX      InetAddressType
    MAX-ACCESS  not-accessible
    STATUS      current
    DESCRIPTION
        "The value of the object sapMldSnpgStaticSourceAddrType specifies the
         type of sapMldSnpgStaticSourceAddr."
    ::= { sapMldSnpgStaticGrpSrcEntry 3 }

sapMldSnpgStaticSourceAddr       OBJECT-TYPE
    SYNTAX      InetAddress (SIZE (4|16))
    MAX-ACCESS  not-accessible
    STATUS      current
    DESCRIPTION
        "The value of the object sapMldSnpgStaticSourceAddr specifies the
         source IP address for this statically configured (S,G) entry for this
         SAP.

         For a (*,G) entry, this object must be set to all zeros."
    ::= { sapMldSnpgStaticGrpSrcEntry 4 }

sapMldSnpgStaticRowstatus        OBJECT-TYPE
    SYNTAX      RowStatus
    MAX-ACCESS  read-create
    STATUS      current
    DESCRIPTION
        "The value of the object sapMldSnpgStaticRowstatus specifies the row
         status used for creation or deletion of sapMldSnpgStaticGrpSrcTable
         entries."
    ::= { sapMldSnpgStaticGrpSrcEntry 5 }

sapMldSnpgStaticLastChangeTime   OBJECT-TYPE
    SYNTAX      TimeStamp
    MAX-ACCESS  read-only
    STATUS      current
    DESCRIPTION
        "The value of the object sapMldSnpgStaticLastChangeTime indicates the
         sysUpTime at the time of the last modification of this entry."
    ::= { sapMldSnpgStaticGrpSrcEntry 6 }

sapMldSnpgStatsTable             OBJECT-TYPE
    SYNTAX      SEQUENCE OF SapMldSnpgStatsEntry
    MAX-ACCESS  not-accessible
    STATUS      current
    DESCRIPTION
        "sapMldSnpgStatsTable contains statistics on MLD snooping per SAP.

         Conceptual rows in this table are created and deleted automatically by
         the system when MLD snooping is enabled and disabled in the interface
         containing the SAP."
    ::= { tmnxMldSnoopingSapObjs 7 }

sapMldSnpgStatsEntry             OBJECT-TYPE
    SYNTAX      SapMldSnpgStatsEntry
    MAX-ACCESS  not-accessible
    STATUS      current
    DESCRIPTION
        "sapMldSnpgStatsEntry is an entry in the sapMldSnpgStatsTable. Each
         entry contains MLD snooping statics for a SAP in a Tls."
    INDEX       {
        svcId,
        sapPortId,
        sapEncapValue
    }
    ::= { sapMldSnpgStatsTable 1 }

SapMldSnpgStatsEntry             ::= SEQUENCE
{
    sapMldSnpgTxGenQueries           Counter32,
    sapMldSnpgTxGrpSpecQueries       Counter32,
    sapMldSnpgTxSrcSpecQueries       Counter32,
    sapMldSnpgTxV1Reports            Counter32,
    sapMldSnpgTxV2Reports            Counter32,
    sapMldSnpgTxV1Leaves             Counter32,
    sapMldSnpgRxGenQueries           Counter32,
    sapMldSnpgRxGrpSpecQueries       Counter32,
    sapMldSnpgRxSrcSpecQueries       Counter32,
    sapMldSnpgRxV1Reports            Counter32,
    sapMldSnpgRxV2Reports            Counter32,
    sapMldSnpgRxV1Leaves             Counter32,
    sapMldSnpgRxUnknownType          Counter32,
    sapMldSnpgFwdGenQueries          Counter32,
    sapMldSnpgFwdGrpSpecQueries      Counter32,
    sapMldSnpgFwdSrcSpecQueries      Counter32,
    sapMldSnpgFwdV1Reports           Counter32,
    sapMldSnpgFwdV2Reports           Counter32,
    sapMldSnpgFwdV1Leaves            Counter32,
    sapMldSnpgFwdUnknownType         Counter32,
    sapMldSnpgRxBadLenPkts           Counter32,
    sapMldSnpgRxBadMldChksmPkts      Counter32,
    sapMldSnpgRxBadEncodedPkts       Counter32,
    sapMldSnpgRxNoRtrAlertPkts       Counter32,
    sapMldSnpgRxZeroSrcAdrPkts       Counter32,
    sapMldSnpgSendQueryCfgDrops      Counter32,
    sapMldSnpgImportPolicyDrops      Counter32,
    sapMldSnpgMaxNumGroupsDrops      Counter32,
    sapMldSnpgMvrFromVplsCfgDrops    Counter32,
    sapMldSnpgMvrToSapCfgDrops       Counter32,
    sapMldSnpgRxWrongVersionPkts     Counter32,
    sapMldSnpgMcsFailures            Counter32,
    sapMldSnpgRxLocalScopePkts       Counter32,
    sapMldSnpgRxRsvdScopePkts        Counter32,
    sapMldSnpgMcacPolicyDrops        Counter32,
    sapMldSnpgRxJoinSyncRtes         Unsigned32,
    sapMldSnpgDropJoinSyncRtes       Unsigned32,
    sapMldSnpgTxJoinSyncRtes         Unsigned32,
    sapMldSnpgRxLeaveSyncRtes        Unsigned32,
    sapMldSnpgDropLeaveSyncRtes      Unsigned32,
    sapMldSnpgTxLeaveSyncRtes        Unsigned32
}

sapMldSnpgTxGenQueries           OBJECT-TYPE
    SYNTAX      Counter32
    MAX-ACCESS  read-only
    STATUS      current
    DESCRIPTION
        "The value of the object sapMldSnpgTxGenQueries indicates the number of
         MLD General Queries transmitted on this SAP."
    ::= { sapMldSnpgStatsEntry 1 }

sapMldSnpgTxGrpSpecQueries       OBJECT-TYPE
    SYNTAX      Counter32
    MAX-ACCESS  read-only
    STATUS      current
    DESCRIPTION
        "The value of the object sapMldSnpgTxGrpSpecQueries indicates the
         number of MLD Group-Specific Queries transmitted on this SAP."
    ::= { sapMldSnpgStatsEntry 2 }

sapMldSnpgTxSrcSpecQueries       OBJECT-TYPE
    SYNTAX      Counter32
    MAX-ACCESS  read-only
    STATUS      current
    DESCRIPTION
        "The value of the object sapMldSnpgTxSrcSpecQueries indicates the
         number of MLD Group-And-Source-Specific Queries transmitted on this
         SAP."
    ::= { sapMldSnpgStatsEntry 3 }

sapMldSnpgTxV1Reports            OBJECT-TYPE
    SYNTAX      Counter32
    MAX-ACCESS  read-only
    STATUS      current
    DESCRIPTION
        "The value of the object sapMldSnpgTxV1Reports indicates the number of
         MLDv1 Reports transmitted on this SAP."
    ::= { sapMldSnpgStatsEntry 4 }

sapMldSnpgTxV2Reports            OBJECT-TYPE
    SYNTAX      Counter32
    MAX-ACCESS  read-only
    STATUS      current
    DESCRIPTION
        "The value of the object sapMldSnpgTxV2Reports indicates the number of
         MLDv2 Reports transmitted on this SAP."
    ::= { sapMldSnpgStatsEntry 5 }

sapMldSnpgTxV1Leaves             OBJECT-TYPE
    SYNTAX      Counter32
    MAX-ACCESS  read-only
    STATUS      current
    DESCRIPTION
        "The value of the object sapMldSnpgTxV1Leaves indicates the number of
         MLDv1 Leaves transmitted on this SAP."
    ::= { sapMldSnpgStatsEntry 6 }

sapMldSnpgRxGenQueries           OBJECT-TYPE
    SYNTAX      Counter32
    MAX-ACCESS  read-only
    STATUS      current
    DESCRIPTION
        "The value of the object sapMldSnpgRxGenQueries indicates the number of
         MLD General Queries received on this SAP."
    ::= { sapMldSnpgStatsEntry 7 }

sapMldSnpgRxGrpSpecQueries       OBJECT-TYPE
    SYNTAX      Counter32
    MAX-ACCESS  read-only
    STATUS      current
    DESCRIPTION
        "The value of the object sapMldSnpgRxGrpSpecQueries indicates the
         number of MLD Group-Specific Queries received on this SAP."
    ::= { sapMldSnpgStatsEntry 8 }

sapMldSnpgRxSrcSpecQueries       OBJECT-TYPE
    SYNTAX      Counter32
    MAX-ACCESS  read-only
    STATUS      current
    DESCRIPTION
        "The value of the object sapMldSnpgRxSrcSpecQueries indicates the
         number of MLD Group-And-Source-Specific Queries received on this SAP."
    ::= { sapMldSnpgStatsEntry 9 }

sapMldSnpgRxV1Reports            OBJECT-TYPE
    SYNTAX      Counter32
    MAX-ACCESS  read-only
    STATUS      current
    DESCRIPTION
        "The value of the object sapMldSnpgRxV1Reports indicates the number of
         MLDv1 Reports received on this SAP."
    ::= { sapMldSnpgStatsEntry 10 }

sapMldSnpgRxV2Reports            OBJECT-TYPE
    SYNTAX      Counter32
    MAX-ACCESS  read-only
    STATUS      current
    DESCRIPTION
        "The value of the object sapMldSnpgRxV2Reports indicates the number of
         MLDv2 Reports received on this SAP."
    ::= { sapMldSnpgStatsEntry 11 }

sapMldSnpgRxV1Leaves             OBJECT-TYPE
    SYNTAX      Counter32
    MAX-ACCESS  read-only
    STATUS      current
    DESCRIPTION
        "The value of the object sapMldSnpgRxV1Leaves indicates the number of
         MLDv1 Leaves received on this SAP."
    ::= { sapMldSnpgStatsEntry 12 }

sapMldSnpgRxUnknownType          OBJECT-TYPE
    SYNTAX      Counter32
    MAX-ACCESS  read-only
    STATUS      current
    DESCRIPTION
        "The value of the object sapMldSnpgRxUnknownType indicates the number
         of MLD unknown type packets received on this SAP."
    ::= { sapMldSnpgStatsEntry 13 }

sapMldSnpgFwdGenQueries          OBJECT-TYPE
    SYNTAX      Counter32
    MAX-ACCESS  read-only
    STATUS      current
    DESCRIPTION
        "The value of the object sapMldSnpgFwdGenQueries indicates the number
         of MLD General Queries forwarded on this SAP."
    ::= { sapMldSnpgStatsEntry 14 }

sapMldSnpgFwdGrpSpecQueries      OBJECT-TYPE
    SYNTAX      Counter32
    MAX-ACCESS  read-only
    STATUS      current
    DESCRIPTION
        "The value of the object sapMldSnpgFwdGrpSpecQueries indicates the
         number of MLD Group-Specific Queries forwarded on this SAP."
    ::= { sapMldSnpgStatsEntry 15 }

sapMldSnpgFwdSrcSpecQueries      OBJECT-TYPE
    SYNTAX      Counter32
    MAX-ACCESS  read-only
    STATUS      current
    DESCRIPTION
        "The value of the object sapMldSnpgFwdSrcSpecQueries indicates the
         number of MLD Group-And-Source-Specific Queries forwarded on this SAP."
    ::= { sapMldSnpgStatsEntry 16 }

sapMldSnpgFwdV1Reports           OBJECT-TYPE
    SYNTAX      Counter32
    MAX-ACCESS  read-only
    STATUS      current
    DESCRIPTION
        "The value of the object sapMldSnpgFwdV1Reports indicates the number of
         MLDv1 Reports forwarded on this SAP."
    ::= { sapMldSnpgStatsEntry 17 }

sapMldSnpgFwdV2Reports           OBJECT-TYPE
    SYNTAX      Counter32
    MAX-ACCESS  read-only
    STATUS      current
    DESCRIPTION
        "The value of the object sapMldSnpgFwdV2Reports indicates the number of
         MLDv2 Reports forwarded on this SAP."
    ::= { sapMldSnpgStatsEntry 18 }

sapMldSnpgFwdV1Leaves            OBJECT-TYPE
    SYNTAX      Counter32
    MAX-ACCESS  read-only
    STATUS      current
    DESCRIPTION
        "The value of the object sapMldSnpgFwdV1Leaves indicates the number of
         MLDv1 Leaves forwarded on this SAP."
    ::= { sapMldSnpgStatsEntry 19 }

sapMldSnpgFwdUnknownType         OBJECT-TYPE
    SYNTAX      Counter32
    MAX-ACCESS  read-only
    STATUS      current
    DESCRIPTION
        "The value of the object sapMldSnpgFwdUnknownType indicates the number
         of MLD unknown type packets forwarded on this SAP."
    ::= { sapMldSnpgStatsEntry 20 }

sapMldSnpgRxBadLenPkts           OBJECT-TYPE
    SYNTAX      Counter32
    MAX-ACCESS  read-only
    STATUS      current
    DESCRIPTION
        "The value of the object sapMldSnpgRxBadLenPkts indicates the number of
         MLD packets dropped on this SAP because of a bad length."
    ::= { sapMldSnpgStatsEntry 21 }

sapMldSnpgRxBadMldChksmPkts      OBJECT-TYPE
    SYNTAX      Counter32
    MAX-ACCESS  read-only
    STATUS      current
    DESCRIPTION
        "The value of the object sapMldSnpgRxBadMldChksmPkts indicates the
         number of dropped MLD packets on this SAP because of a bad MLD header
         checksum."
    ::= { sapMldSnpgStatsEntry 22 }

sapMldSnpgRxBadEncodedPkts       OBJECT-TYPE
    SYNTAX      Counter32
    MAX-ACCESS  read-only
    STATUS      current
    DESCRIPTION
        "The value of the object sapMldSnpgRxBadEncodedPkts indicates the
         number of MLD packets dropped on this SAP because of a bad encoding."
    ::= { sapMldSnpgStatsEntry 23 }

sapMldSnpgRxNoRtrAlertPkts       OBJECT-TYPE
    SYNTAX      Counter32
    MAX-ACCESS  read-only
    STATUS      current
    DESCRIPTION
        "The value of the object sapMldSnpgRxNoRtrAlertPkts indicates the
         number of MLD packets dropped on this SAP because the Router Alert
         Option in the IP packet is not set."
    ::= { sapMldSnpgStatsEntry 24 }

sapMldSnpgRxZeroSrcAdrPkts       OBJECT-TYPE
    SYNTAX      Counter32
    MAX-ACCESS  read-only
    STATUS      current
    DESCRIPTION
        "The value of the object sapMldSnpgRxZeroSrcAdrPkts indicates the
         number of MLD packets dropped on this SAP because they contain a zero
         source IPv6 address."
    ::= { sapMldSnpgStatsEntry 25 }

sapMldSnpgSendQueryCfgDrops      OBJECT-TYPE
    SYNTAX      Counter32
    MAX-ACCESS  read-only
    STATUS      current
    DESCRIPTION
        "The value of the object sapMldSnpgSendQueryCfgDrops indicates the
         number of times an MLD Query is dropped because the object
         sapMldSnpgCfgSendQueries for this SAP is set to 'inService(2)'."
    ::= { sapMldSnpgStatsEntry 26 }

sapMldSnpgImportPolicyDrops      OBJECT-TYPE
    SYNTAX      Counter32
    MAX-ACCESS  read-only
    STATUS      current
    DESCRIPTION
        "The value of the object sapMldSnpgImportPolicyDrops indicates the
         number of times an MLD group or source is dropped because of applying
         an import policy on this SAP."
    ::= { sapMldSnpgStatsEntry 27 }

sapMldSnpgMaxNumGroupsDrops      OBJECT-TYPE
    SYNTAX      Counter32
    MAX-ACCESS  read-only
    STATUS      current
    DESCRIPTION
        "The value of the object sapMldSnpgMaxNumGroupsDrops indicates the
         number of times an MLD group is dropped because of exceeding the
         configured maximum number of groups on this SAP."
    ::= { sapMldSnpgStatsEntry 28 }

sapMldSnpgMvrFromVplsCfgDrops    OBJECT-TYPE
    SYNTAX      Counter32
    MAX-ACCESS  read-only
    STATUS      current
    DESCRIPTION
        "The value of the object sapMldSnpgMvrFromVplsCfgDrops indicates the
         number of times an MLD group or Query is dropped because of applying
         the sapMldSnpgCfgMvrFromVplsId configuration on this SAP."
    ::= { sapMldSnpgStatsEntry 29 }

sapMldSnpgMvrToSapCfgDrops       OBJECT-TYPE
    SYNTAX      Counter32
    MAX-ACCESS  read-only
    STATUS      current
    DESCRIPTION
        "The value of the object sapMldSnpgMvrToSapCfgDrops indicates the
         number times an MLD Report or Query is dropped because of applying the
         sapMldSnpgCfgMvrToSapPortId and sapMldSnpgCfgMvrToSapEncapVal
         configuration on this SAP."
    ::= { sapMldSnpgStatsEntry 30 }

sapMldSnpgRxWrongVersionPkts     OBJECT-TYPE
    SYNTAX      Counter32
    MAX-ACCESS  read-only
    STATUS      current
    DESCRIPTION
        "The value of the object sapMldSnpgRxWrongVersionPkts indicates the
         total number of MLD packets with a wrong version received on this SAP."
    ::= { sapMldSnpgStatsEntry 31 }

sapMldSnpgMcsFailures            OBJECT-TYPE
    SYNTAX      Counter32
    MAX-ACCESS  read-only
    STATUS      current
    DESCRIPTION
        "The value of the object sapMldSnpgMcsFailures indicates the number of
         times an MLD group on this SAP could not be synced to the MCS
         (multi-chassis synchronization) database."
    ::= { sapMldSnpgStatsEntry 32 }

sapMldSnpgRxLocalScopePkts       OBJECT-TYPE
    SYNTAX      Counter32
    MAX-ACCESS  read-only
    STATUS      current
    DESCRIPTION
        "The value of the object sapMldSnpgRxLocalScopePkts indicates the
         number of MLD packets received on the link-local scope IPv6 multicast
         address."
    ::= { sapMldSnpgStatsEntry 33 }

sapMldSnpgRxRsvdScopePkts        OBJECT-TYPE
    SYNTAX      Counter32
    MAX-ACCESS  read-only
    STATUS      current
    DESCRIPTION
        "The value of the object sapMldSnpgRxRsvdScopePkts indicates the number
         of MLD packets received on the reserved scope IPv6 multicast address."
    ::= { sapMldSnpgStatsEntry 34 }

sapMldSnpgMcacPolicyDrops        OBJECT-TYPE
    SYNTAX      Counter32
    MAX-ACCESS  read-only
    STATUS      current
    DESCRIPTION
        "The value of the object sapMldSnpgMcacPolicyDrops indicates the number
         of times an MLD Group is dropped because of applying a multicast CAC
         policy on this SAP."
    ::= { sapMldSnpgStatsEntry 35 }

sapMldSnpgRxJoinSyncRtes         OBJECT-TYPE
    SYNTAX      Unsigned32
    MAX-ACCESS  read-only
    STATUS      current
    DESCRIPTION
        "sapMldSnpgRxJoinSyncRtes is the number of received Bgp Multicast Join
         Sync routes fort this SAP."
    ::= { sapMldSnpgStatsEntry 36 }

sapMldSnpgDropJoinSyncRtes       OBJECT-TYPE
    SYNTAX      Unsigned32
    MAX-ACCESS  read-only
    STATUS      current
    DESCRIPTION
        "sapMldSnpgDropJoinSyncRtes is the number of dropped Bgp Multicast Join
         Sync routes for this SAP."
    ::= { sapMldSnpgStatsEntry 37 }

sapMldSnpgTxJoinSyncRtes         OBJECT-TYPE
    SYNTAX      Unsigned32
    MAX-ACCESS  read-only
    STATUS      current
    DESCRIPTION
        "sapMldSnpgTxJoinSyncRtes is the number of transmitted Smet Bgp
         Multicast Join Sync from this SAP."
    ::= { sapMldSnpgStatsEntry 38 }

sapMldSnpgRxLeaveSyncRtes        OBJECT-TYPE
    SYNTAX      Unsigned32
    MAX-ACCESS  read-only
    STATUS      current
    DESCRIPTION
        "sapMldSnpgRxLeaveSyncRtes is the number of received Bgp Multicast
         Leave Sync routes for this SAP."
    ::= { sapMldSnpgStatsEntry 39 }

sapMldSnpgDropLeaveSyncRtes      OBJECT-TYPE
    SYNTAX      Unsigned32
    MAX-ACCESS  read-only
    STATUS      current
    DESCRIPTION
        "sapMldSnpgDropLeaveSyncRtes is the number of dropped Bgp Multicast
         Leave Sync routes for this SAP."
    ::= { sapMldSnpgStatsEntry 40 }

sapMldSnpgTxLeaveSyncRtes        OBJECT-TYPE
    SYNTAX      Unsigned32
    MAX-ACCESS  read-only
    STATUS      current
    DESCRIPTION
        "sapMldSnpgTxLeaveSyncRtes is the number of transmitted Smet Bgp
         Multicast Leave Sync from this SAP."
    ::= { sapMldSnpgStatsEntry 41 }

sapMldSnpgMcacLevelTable         OBJECT-TYPE
    SYNTAX      SEQUENCE OF SapMldSnpgMcacLevelEntry
    MAX-ACCESS  not-accessible
    STATUS      current
    DESCRIPTION
        "The sapMldSnpgMcacLevelTable has an entry for each multicast CAC
         policy constraint level configured on this system."
    ::= { tmnxMldSnoopingSapObjs 8 }

sapMldSnpgMcacLevelEntry         OBJECT-TYPE
    SYNTAX      SapMldSnpgMcacLevelEntry
    MAX-ACCESS  not-accessible
    STATUS      current
    DESCRIPTION
        "Each row entry represents a particular multicast CAC policy bundle
         level constraints. Entries are created/deleted by the user."
    INDEX       {
        svcId,
        sapPortId,
        sapEncapValue,
        tmnxMcacLevelId
    }
    ::= { sapMldSnpgMcacLevelTable 1 }

SapMldSnpgMcacLevelEntry         ::= SEQUENCE
{
    sapMldSnpgCfgMcacLevelRowStat    RowStatus,
    sapMldSnpgCfgMcacLevelBW         Unsigned32,
    sapMldSnpgCfgMcacLevelLastChngT  TimeStamp
}

sapMldSnpgCfgMcacLevelRowStat    OBJECT-TYPE
    SYNTAX      RowStatus
    MAX-ACCESS  read-create
    STATUS      current
    DESCRIPTION
        "The value of sapMldSnpgCfgMcacLevelRowStat is used for
         creation/deletion of level constraint in a CAC policy."
    ::= { sapMldSnpgMcacLevelEntry 1 }

sapMldSnpgCfgMcacLevelBW         OBJECT-TYPE
    SYNTAX      Unsigned32 (0..2147483647)
    UNITS       "kilobps"
    MAX-ACCESS  read-create
    STATUS      current
    DESCRIPTION
        "The value of sapMldSnpgCfgMcacLevelBW specifies the bandwidth in
         kilobits per second (kbps) for the level."
    DEFVAL      { 1 }
    ::= { sapMldSnpgMcacLevelEntry 2 }

sapMldSnpgCfgMcacLevelLastChngT  OBJECT-TYPE
    SYNTAX      TimeStamp
    MAX-ACCESS  read-only
    STATUS      current
    DESCRIPTION
        "The value of the object sapMldSnpgCfgMcacLevelLastChngT indicates the
         sysUpTime at the time of the last modification of this entry."
    ::= { sapMldSnpgMcacLevelEntry 3 }

sapMldSnpgMcacLagTable           OBJECT-TYPE
    SYNTAX      SEQUENCE OF SapMldSnpgMcacLagEntry
    MAX-ACCESS  not-accessible
    STATUS      current
    DESCRIPTION
        "The sapMldSnpgMcacLagTable has an entry for each lag port configured
         for a multicast CAC policy bundle on this system."
    ::= { tmnxMldSnoopingSapObjs 9 }

sapMldSnpgMcacLagEntry           OBJECT-TYPE
    SYNTAX      SapMldSnpgMcacLagEntry
    MAX-ACCESS  not-accessible
    STATUS      current
    DESCRIPTION
        "Each row entry represents a particular multicast CAC lag port
         constraints. Entries are created/deleted by the user."
    INDEX       {
        svcId,
        sapPortId,
        sapEncapValue,
        tmnxMcacLagPortsDown
    }
    ::= { sapMldSnpgMcacLagTable 1 }

SapMldSnpgMcacLagEntry           ::= SEQUENCE
{
    sapMldSnpgCfgMcacLagRowStat      RowStatus,
    sapMldSnpgCfgMcacLagLevel        Unsigned32,
    sapMldSnpgCfgMcacLagLastChangeT  TimeStamp
}

sapMldSnpgCfgMcacLagRowStat      OBJECT-TYPE
    SYNTAX      RowStatus
    MAX-ACCESS  read-create
    STATUS      current
    DESCRIPTION
        "The value of sapMldSnpgCfgMcacLagRowStat is used for creation/deletion
         of lag constraint in a CAC policy."
    ::= { sapMldSnpgMcacLagEntry 1 }

sapMldSnpgCfgMcacLagLevel        OBJECT-TYPE
    SYNTAX      Unsigned32 (1..8)
    MAX-ACCESS  read-create
    STATUS      current
    DESCRIPTION
        "The value of sapMldSnpgCfgMcacLagLevel specifies the level id to use
         when the value of tmnxMcacLagPortsDown matches the actual number of
         ports down in a lag.

         Using the value of sapMldSnpgCfgMcacLagLevel as an index, the
         operational SAP unconstrained bandwidth will be set to
         sapMldSnpgCfgMcacLevelBW.

         By default, for all lag constraints the link level will be set to 1 at
         row creation."
    DEFVAL      { 1 }
    ::= { sapMldSnpgMcacLagEntry 2 }

sapMldSnpgCfgMcacLagLastChangeT  OBJECT-TYPE
    SYNTAX      TimeStamp
    MAX-ACCESS  read-only
    STATUS      current
    DESCRIPTION
        "The value of the object sapMldSnpgCfgMcacLagLastChangeT indicates the
         sysUpTime at the time of the last modification of this entry."
    ::= { sapMldSnpgMcacLagEntry 3 }

tmnxMldSnoopingSdpBindObjs       OBJECT IDENTIFIER ::= { tmnxMldSnoopingObjs 3 }

sdpBindMldSnpgConfigTableLastCh  OBJECT-TYPE
    SYNTAX      TimeStamp
    MAX-ACCESS  read-only
    STATUS      current
    DESCRIPTION
        "The value of the object sdpBindMldSnpgConfigTableLastCh indicates the
         value of sysUpTime at the time of the last modification of an entry in
         the sdpBindMldSnpgConfigTable."
    ::= { tmnxMldSnoopingSdpBindObjs 1 }

sdpBindMldSnpgConfigTable        OBJECT-TYPE
    SYNTAX      SEQUENCE OF SdpBindMldSnpgConfigEntry
    MAX-ACCESS  not-accessible
    STATUS      current
    DESCRIPTION
        "The table sdpBindMldSnpgConfigTable contains objects to configure the
         MLD snooping feature on an SDP Bind within a Tls."
    ::= { tmnxMldSnoopingSdpBindObjs 2 }

sdpBindMldSnpgConfigEntry        OBJECT-TYPE
    SYNTAX      SdpBindMldSnpgConfigEntry
    MAX-ACCESS  not-accessible
    STATUS      current
    DESCRIPTION
        "Each row contains MLD snooping configuration parameters for an SDP
         bind within a Tls.

         Entries in this table cannot be created or deleted via SNMP
         operations. An entry in this table will be created by the agent upon
         creation of a new SDP Bind (sdpBindTlsEntry). The entry is destroyed
         when the SDP or Tls service is removed."
    INDEX       {
        svcId,
        sdpBindId
    }
    ::= { sdpBindMldSnpgConfigTable 1 }

SdpBindMldSnpgConfigEntry        ::= SEQUENCE
{
    sdpBndMldSnpgCfgLastChangeTime   TimeStamp,
    sdpBndMldSnpgCfgImportPlcy       TPolicyStatementNameOrEmpty,
    sdpBndMldSnpgCfgFastLeave        TmnxAdminState,
    sdpBndMldSnpgCfgMRouter          TruthValue,
    sdpBndMldSnpgCfgSendQueries      TmnxAdminState,
    sdpBndMldSnpgCfgGenQueryIntvl    Unsigned32,
    sdpBndMldSnpgCfgQueryRespIntvl   Unsigned32,
    sdpBndMldSnpgCfgRobustCount      Unsigned32,
    sdpBndMldSnpgCfgLastMembIntvl    Unsigned32,
    sdpBndMldSnpgCfgMaxNbrGrps       Integer32,
    sdpBndMldSnpgCfgVersion          TmnxMldVersion,
    sdpBndMldSnpgCfgDisRtrAlertChk   TruthValue,
    sdpBndMldSnpgCfgMcacPolicyName   TPolicyStatementNameOrEmpty,
    sdpBndMldSnpgCfgMcacUnconstBW    Integer32,
    sdpBndMldSnpgCfgMcacPrRsvMndBW   Integer32,
    sdpBndMldSnpgCfgMcacinUseMndBw   Unsigned32,
    sdpBndMldSnpgCfgMcacinUseOplBw   Unsigned32,
    sdpBndMldSnpgCfgMcacAvailMndBw   Unsigned32,
    sdpBndMldSnpgCfgMcacAvailOplBw   Unsigned32,
    sdpBndMldSnpgCfgMcacValInTrans   TruthValue,
    sdpBndMldSnpgCfgMcacIfPlcyName   TPolicyStatementNameOrEmpty
}

sdpBndMldSnpgCfgLastChangeTime   OBJECT-TYPE
    SYNTAX      TimeStamp
    MAX-ACCESS  read-only
    STATUS      current
    DESCRIPTION
        "The value of the object sdpBndMldSnpgCfgLastChangeTime indicates the
         sysUpTime at the time of the last modification of this entry."
    ::= { sdpBindMldSnpgConfigEntry 1 }

sdpBndMldSnpgCfgImportPlcy       OBJECT-TYPE
    SYNTAX      TPolicyStatementNameOrEmpty
    MAX-ACCESS  read-write
    STATUS      current
    DESCRIPTION
        "The value of the object sdpBndMldSnpgCfgImportPlcy specifies a policy
         statement that must be applied to all incoming MLD messages on this
         SDP Bind."
    DEFVAL      { "" }
    ::= { sdpBindMldSnpgConfigEntry 2 }

sdpBndMldSnpgCfgFastLeave        OBJECT-TYPE
    SYNTAX      TmnxAdminState
    MAX-ACCESS  read-write
    STATUS      current
    DESCRIPTION
        "The value of the object sdpBndMldSnpgCfgFastLeave specifies whether or
         not fastleave is allowed on this SDP bind.

         If set to 'inService(2)', the system prunes the port on which a MLD
         'leave' message has been received without waiting for the Group
         Specific Query to timeout."
    DEFVAL      { outOfService }
    ::= { sdpBindMldSnpgConfigEntry 3 }

sdpBndMldSnpgCfgMRouter          OBJECT-TYPE
    SYNTAX      TruthValue
    MAX-ACCESS  read-write
    STATUS      current
    DESCRIPTION
        "The value of the object sdpBndMldSnpgCfgMRouter specifies whether a
         multicast router is attached behind this SDP.

         If sdpBndMldSnpgCfgSendQueries is set to 'inService(2)', the system
         acts as if this object was set to 'false(2)'."
    DEFVAL      { false }
    ::= { sdpBindMldSnpgConfigEntry 4 }

sdpBndMldSnpgCfgSendQueries      OBJECT-TYPE
    SYNTAX      TmnxAdminState
    MAX-ACCESS  read-write
    STATUS      current
    DESCRIPTION
        "The value of the object sdpBndMldSnpgCfgSendQueries specifies whether
         the system generates General Queries by itself on this SDP."
    DEFVAL      { outOfService }
    ::= { sdpBindMldSnpgConfigEntry 5 }

sdpBndMldSnpgCfgGenQueryIntvl    OBJECT-TYPE
    SYNTAX      Unsigned32 (2..1024)
    UNITS       "seconds"
    MAX-ACCESS  read-write
    STATUS      current
    DESCRIPTION
        "The value of the object sdpBndMldSnpgCfgGenQueryIntvl specifies the
         interval (in seconds) between two consecutive general queries sent by
         the system on this SDP.

         The value of this object is only meaningful when the value of
         sdpBndMldSnpgCfgSendQueries is 'inService(2)'."
    DEFVAL      { 125 }
    ::= { sdpBindMldSnpgConfigEntry 6 }

sdpBndMldSnpgCfgQueryRespIntvl   OBJECT-TYPE
    SYNTAX      Unsigned32 (1..1023)
    UNITS       "seconds"
    MAX-ACCESS  read-write
    STATUS      current
    DESCRIPTION
        "The value of the object sdpBndMldSnpgCfgQueryRespIntvl specifies the
         maximum response time (in seconds) advertised in MLD queries.

         The value of this object is only meaningful when the value of
         sdpBndMldSnpgCfgSendQueries is 'inService(2)'."
    DEFVAL      { 10 }
    ::= { sdpBindMldSnpgConfigEntry 7 }

sdpBndMldSnpgCfgRobustCount      OBJECT-TYPE
    SYNTAX      Unsigned32 (2..7)
    MAX-ACCESS  read-write
    STATUS      current
    DESCRIPTION
        "The value of the object sdpBndMldSnpgCfgRobustCount specifies the
         value of the Robust count.

         This object allows tuning for the expected packet loss on this SDP. If
         a SDP is expected to be lossy, the Robustness Variable may be
         increased. MLD snooping is robust to (Robustness Variable-1) packet
         losses.

         The value of this object is only meaningful when the value of
         sdpBndMldSnpgCfgSendQueries is 'inService(2)'."
    DEFVAL      { 2 }
    ::= { sdpBindMldSnpgConfigEntry 8 }

sdpBndMldSnpgCfgLastMembIntvl    OBJECT-TYPE
    SYNTAX      Unsigned32 (1..50)
    UNITS       "deciseconds"
    MAX-ACCESS  read-write
    STATUS      current
    DESCRIPTION
        "The value of the object sdpBndMldSnpgCfgLastMembIntvl specifies the
         Max Response Time (in deciseconds) used in Group-Specific and
         Group-Source-Specific Queries sent in response to 'leave' messages.
         This is also the amount of time between Group-Specific Query messages.

         This value may be tuned to modify the leave latency of the network. A
         reduced value results in reduced time to detect the loss of the last
         member of a group."
    DEFVAL      { 10 }
    ::= { sdpBindMldSnpgConfigEntry 9 }

sdpBndMldSnpgCfgMaxNbrGrps       OBJECT-TYPE
    SYNTAX      Integer32 (0..16000)
    MAX-ACCESS  read-write
    STATUS      current
    DESCRIPTION
        "The value of the object sdpBndMldSnpgCfgMaxNbrGrps specifies how many
         group addresses are allowed for this SDP bind.

         The value 0 means that no limit is imposed."
    DEFVAL      { 0 }
    ::= { sdpBindMldSnpgConfigEntry 10 }

sdpBndMldSnpgCfgVersion          OBJECT-TYPE
    SYNTAX      TmnxMldVersion
    MAX-ACCESS  read-write
    STATUS      current
    DESCRIPTION
        "The value of the object sdpBndMldSnpgCfgVersion specifies the version
         of MLD running on this SDP bind."
    DEFVAL      { version2 }
    ::= { sdpBindMldSnpgConfigEntry 11 }

sdpBndMldSnpgCfgDisRtrAlertChk   OBJECT-TYPE
    SYNTAX      TruthValue
    MAX-ACCESS  read-write
    STATUS      current
    DESCRIPTION
        "sdpBndMldSnpgCfgDisRtrAlertChk is used to enable/disable router alert
         checking for IGMP messages received on this sdp.

         If this flag is set to 'true', checking is disabled."
    DEFVAL      { false }
    ::= { sdpBindMldSnpgConfigEntry 12 }

sdpBndMldSnpgCfgMcacPolicyName   OBJECT-TYPE
    SYNTAX      TPolicyStatementNameOrEmpty
    MAX-ACCESS  read-write
    STATUS      current
    DESCRIPTION
        "The value of sdpBndMldSnpgCfgMcacPolicyName specifies the name of the
         multicast CAC policy."
    DEFVAL      { "" }
    ::= { sdpBindMldSnpgConfigEntry 13 }

sdpBndMldSnpgCfgMcacUnconstBW    OBJECT-TYPE
    SYNTAX      Integer32 (-1 | 0..2147483647)
    UNITS       "kilobps"
    MAX-ACCESS  read-write
    STATUS      current
    DESCRIPTION
        "The value of sdpBndMldSnpgCfgMcacUnconstBW specifies the bandwidth
         assigned for interface's multicast CAC policy traffic in kilobits per
         second(kbps).

         If the default value of '-1' is set, there is no constraint on
         bandwidth allocated at the interface.

         If the value of sdpBndIgmpSnpgCfgMcacUnconstBW is set to '0' and if a
         multicast CAC policy is assigned on the interface, then no group
         (channel) from that policy is allowed on that interface."
    DEFVAL      { -1 }
    ::= { sdpBindMldSnpgConfigEntry 14 }

sdpBndMldSnpgCfgMcacPrRsvMndBW   OBJECT-TYPE
    SYNTAX      Integer32 (-1 | 0..2147483647)
    UNITS       "kilobps"
    MAX-ACCESS  read-write
    STATUS      current
    DESCRIPTION
        "The value of sdpBndMldSnpgCfgMcacPrRsvMndBW specifies the bandwidth
         pre-reserved for all the mandatory channels on a given interface in
         kilobits per second(kbps).

         If the value of sdpBndMldSnpgCfgMcacUnconstBW is '0', no mandatory
         channels are allowed. If the value of sdpBndMldSnpgCfgMcacUnconstBW is
         '-1', then all mandatory and optional channels are allowed.

         If the value of sdpBndMldSnpgCfgMcacPrRsvMndBW is equal to the value
         of sdpBndMldSnpgCfgMcacUnconstBW, then all the unconstrained bandwidth
         on a given interface is allocated to mandatory channels configured
         through multicast CAC policy on that interface and no optional groups
         (channels) are allowed.

         The value of sdpBndMldSnpgCfgMcacPrRsvMndBW should always be less than
         or equal to that of sdpBndMldSnpgCfgMcacUnconstBW. An attempt to set
         the value of sdpBndMldSnpgCfgMcacPrRsvMndBW greater than that of
         sdpBndMldSnpgCfgMcacUnconstBW will result in inconsistent value error."
    DEFVAL      { -1 }
    ::= { sdpBindMldSnpgConfigEntry 15 }

sdpBndMldSnpgCfgMcacinUseMndBw   OBJECT-TYPE
    SYNTAX      Unsigned32
    UNITS       "kilobps"
    MAX-ACCESS  read-only
    STATUS      current
    DESCRIPTION
        "The value of sdpBndMldSnpgCfgMcacinUseMndBw indicates the in-use
         bandwidth in kilobits per second(kbps) for the mandatory channels for
         this protocol interface instance."
    ::= { sdpBindMldSnpgConfigEntry 16 }

sdpBndMldSnpgCfgMcacinUseOplBw   OBJECT-TYPE
    SYNTAX      Unsigned32
    UNITS       "kilobps"
    MAX-ACCESS  read-only
    STATUS      current
    DESCRIPTION
        "The value of sdpBndMldSnpgCfgMcacinUseOplBw indicates the in-use
         bandwidth in kilobits per second(kbps) for the optional channels for
         this protocol interface instance."
    ::= { sdpBindMldSnpgConfigEntry 17 }

sdpBndMldSnpgCfgMcacAvailMndBw   OBJECT-TYPE
    SYNTAX      Unsigned32
    UNITS       "kilobps"
    MAX-ACCESS  read-only
    STATUS      current
    DESCRIPTION
        "The value of sdpBndMldSnpgCfgMcacAvailMndBw indicates the pre-reserved
         bandwidth in kilobits per second(kbps) for the mandatory channels for
         this interface instance."
    ::= { sdpBindMldSnpgConfigEntry 18 }

sdpBndMldSnpgCfgMcacAvailOplBw   OBJECT-TYPE
    SYNTAX      Unsigned32
    UNITS       "kilobps"
    MAX-ACCESS  read-only
    STATUS      current
    DESCRIPTION
        "The value of sdpBndMldSnpgCfgMcacAvailOplBw indicates the available
         bandwidth in kilobits per second(kbps) for this interface instance."
    ::= { sdpBindMldSnpgConfigEntry 19 }

sdpBndMldSnpgCfgMcacValInTrans   OBJECT-TYPE
    SYNTAX      TruthValue
    MAX-ACCESS  read-only
    STATUS      current
    DESCRIPTION
        "The value of sdpBndMldSnpgCfgMcacValInTrans indicates that the
         operational (available and in-use mandatory/optional) value for the
         following objects are in transition due to configuration change:

         sdpBndMldSnpgCfgMcacinUseMndBw sdpBndMldSnpgCfgMcacinUseOplBw
         sdpBndMldSnpgCfgMcacAvailMndBw sdpBndMldSnpgCfgMcacAvailOplBw

         When multicast CAC Policy is applied on the interface for the join of
         the next channel, the operational values will be recalculated and
         applied to the above objects and the value for
         sdpBndMldSnpgCfgMcacValInTrans will be set to 'false(2)'.

         If the value of sdpBndMldSnpgCfgMcacValInTrans is 'true(1)' then the
         values are in transition."
    ::= { sdpBindMldSnpgConfigEntry 20 }

sdpBndMldSnpgCfgMcacIfPlcyName   OBJECT-TYPE
    SYNTAX      TPolicyStatementNameOrEmpty
    MAX-ACCESS  read-write
    STATUS      current
    DESCRIPTION
        "The value of sdpBndMldSnpgCfgMcacIfPlcyName specifies the name of the
         multicast CAC interface policy."
    DEFVAL      { "" }
    ::= { sdpBindMldSnpgConfigEntry 21 }

sdpBindMldSnpgGroupTable         OBJECT-TYPE
    SYNTAX      SEQUENCE OF SdpBindMldSnpgGroupEntry
    MAX-ACCESS  not-accessible
    STATUS      current
    DESCRIPTION
        "sdpBindMldSnpgGroupTable contains, together with the table
         sdpBindMldSnpgGrpSrcTable, multicast group address information
         collected by MLD snooping for each SDP Bind."
    ::= { tmnxMldSnoopingSdpBindObjs 3 }

sdpBindMldSnpgGroupEntry         OBJECT-TYPE
    SYNTAX      SdpBindMldSnpgGroupEntry
    MAX-ACCESS  not-accessible
    STATUS      current
    DESCRIPTION
        "Each entry in this table indicates a multicast group address learned
         by MLD snooping on this SDP Bind.

         If a source list is present, it is described in the corresponding
         entries of the sdpBindMldSnpgGrpSrcTable table."
    INDEX       {
        svcId,
        sdpBindId,
        sdpBndMldSnpgGrpAddressType,
        sdpBndMldSnpgGrpAddress
    }
    ::= { sdpBindMldSnpgGroupTable 1 }

SdpBindMldSnpgGroupEntry         ::= SEQUENCE
{
    sdpBndMldSnpgGrpAddressType      InetAddressType,
    sdpBndMldSnpgGrpAddress          InetAddress,
    sdpBndMldSnpgGrpType             TmnxMldGroupType,
    sdpBndMldSnpgGrpFilterMode       TmnxMldGroupFilterMode,
    sdpBndMldSnpgGrpUpTime           TimeTicks,
    sdpBndMldSnpgGrpExpiryTime       Unsigned32,
    sdpBndMldSnpgGrpCompatMode       Unsigned32,
    sdpBndMldSnpgGrpV1HostExpTime    Unsigned32
}

sdpBndMldSnpgGrpAddressType      OBJECT-TYPE
    SYNTAX      InetAddressType
    MAX-ACCESS  not-accessible
    STATUS      current
    DESCRIPTION
        "The value of the object sdpBndMldSnpgGrpAddressType indicates the type
         of sdpBndMldSnpgGrpAddress."
    ::= { sdpBindMldSnpgGroupEntry 1 }

sdpBndMldSnpgGrpAddress          OBJECT-TYPE
    SYNTAX      InetAddress (SIZE (4|16))
    MAX-ACCESS  not-accessible
    STATUS      current
    DESCRIPTION
        "The value of the object sdpBndMldSnpgGrpAddress indicates the IPv6
         multicast group address for which this entry contains information."
    ::= { sdpBindMldSnpgGroupEntry 2 }

sdpBndMldSnpgGrpType             OBJECT-TYPE
    SYNTAX      TmnxMldGroupType
    MAX-ACCESS  read-only
    STATUS      current
    DESCRIPTION
        "The value of the object sdpBndMldSnpgGrpType indicates whether this
         entry was learned dynamically or was statically configured."
    ::= { sdpBindMldSnpgGroupEntry 3 }

sdpBndMldSnpgGrpFilterMode       OBJECT-TYPE
    SYNTAX      TmnxMldGroupFilterMode
    MAX-ACCESS  read-only
    STATUS      current
    DESCRIPTION
        "The value of the object sdpBndMldSnpgGrpFilterMode indicates the
         filter-mode for this group."
    ::= { sdpBindMldSnpgGroupEntry 4 }

sdpBndMldSnpgGrpUpTime           OBJECT-TYPE
    SYNTAX      TimeTicks
    MAX-ACCESS  read-only
    STATUS      current
    DESCRIPTION
        "The value of the object sdpBndMldSnpgGrpUpTime indicates how long (in
         centiseconds) that the group address already exists in the database
         for this SDP Bind."
    ::= { sdpBindMldSnpgGroupEntry 5 }

sdpBndMldSnpgGrpExpiryTime       OBJECT-TYPE
    SYNTAX      Unsigned32
    UNITS       "seconds"
    MAX-ACCESS  read-only
    STATUS      current
    DESCRIPTION
        "The value of the object sdpBndMldSnpgGrpExpiryTime indicates the
         amount of time remaining before this entry will be aged out."
    ::= { sdpBindMldSnpgGroupEntry 6 }

sdpBndMldSnpgGrpCompatMode       OBJECT-TYPE
    SYNTAX      Unsigned32
    MAX-ACCESS  read-only
    STATUS      current
    DESCRIPTION
        "The value of the object sdpBndMldSnpgGrpCompatMode indicates the MLD
         version applicable on this SDP Bind for this multicast group address.
         This corresponds to the lowest version seen for this group address on
         this SDP Bind."
    ::= { sdpBindMldSnpgGroupEntry 7 }

sdpBndMldSnpgGrpV1HostExpTime    OBJECT-TYPE
    SYNTAX      Unsigned32
    UNITS       "seconds"
    MAX-ACCESS  read-only
    STATUS      current
    DESCRIPTION
        "The value of the object sdpBndMldSnpgGrpV1HostExpTime indicates the
         time remaining until the system will assume that there are no longer
         any MLDv1 members on this SDP Bind.

         Upon hearing any MLDv1 Membership Report, this value is reset to the
         group membership interval. While this time remaining is non-zero, the
         system ignores any MLDv2 'leave' messages for this group that it
         receives on this SDP Bind."
    ::= { sdpBindMldSnpgGroupEntry 8 }

sdpBindMldSnpgGrpSrcTable        OBJECT-TYPE
    SYNTAX      SEQUENCE OF SdpBindMldSnpgGrpSrcEntry
    MAX-ACCESS  not-accessible
    STATUS      current
    DESCRIPTION
        "sdpBindMldSnpgGrpSrcTable lists the IPv6 multicast sources
         corresponding to the IPv6 multicast groups listed in the
         sdpBindMldSnpgGroupTable."
    ::= { tmnxMldSnoopingSdpBindObjs 4 }

sdpBindMldSnpgGrpSrcEntry        OBJECT-TYPE
    SYNTAX      SdpBindMldSnpgGrpSrcEntry
    MAX-ACCESS  not-accessible
    STATUS      current
    DESCRIPTION
        "An entry in the sdpBindMldSnpgGrpSrcTable. Each entry represents a
         source address from which receivers are interested/not interested in
         receiving multicast traffic from."
    INDEX       {
        svcId,
        sdpBindId,
        sdpBndMldSnpgGrpAddressType,
        sdpBndMldSnpgGrpAddress,
        sdpBndMldSnpgGrpSrcAddrType,
        sdpBndMldSnpgGrpSrcAddr
    }
    ::= { sdpBindMldSnpgGrpSrcTable 1 }

SdpBindMldSnpgGrpSrcEntry        ::= SEQUENCE
{
    sdpBndMldSnpgGrpSrcAddrType      InetAddressType,
    sdpBndMldSnpgGrpSrcAddr          InetAddress,
    sdpBndMldSnpgGrpSrcType          TmnxMldGroupType,
    sdpBndMldSnpgGrpSrcUpTime        TimeTicks,
    sdpBndMldSnpgGrpSrcExpiryTime    Unsigned32,
    sdpBndMldSnpgGrpSrcFwdOrBlk      INTEGER
}

sdpBndMldSnpgGrpSrcAddrType      OBJECT-TYPE
    SYNTAX      InetAddressType
    MAX-ACCESS  not-accessible
    STATUS      current
    DESCRIPTION
        "The value of the object sdpBndMldSnpgGrpSrcAddrType indicates the type
         of sdpBndMldSnpgGrpSrcAddr."
    ::= { sdpBindMldSnpgGrpSrcEntry 1 }

sdpBndMldSnpgGrpSrcAddr          OBJECT-TYPE
    SYNTAX      InetAddress (SIZE (4|16))
    MAX-ACCESS  not-accessible
    STATUS      current
    DESCRIPTION
        "The value of the object sdpBndMldSnpgGrpSrcAddr indicates the address
         of the source sending multicast traffic to the group identified by
         sdpBndMldSnpgGrpAddress.

         If the value of sdpBndMldSnpgGrpFilterMode corresponding to this entry
         is 'include(1)', the receivers are interested in receiving traffic
         from this source.

         If the value of sdpBndMldSnpgGrpFilterMode corresponding to this entry
         is 'exclude(2)' the receivers, are not interested in receiving traffic
         from this source."
    ::= { sdpBindMldSnpgGrpSrcEntry 2 }

sdpBndMldSnpgGrpSrcType          OBJECT-TYPE
    SYNTAX      TmnxMldGroupType
    MAX-ACCESS  read-only
    STATUS      current
    DESCRIPTION
        "The value of the object sdpBndMldSnpgGrpSrcType indicates how this
         source entry was learned.

         If this source entry was learned, this object is set to 'dynamic(2)'.
         For statically configured sources, this object is set to 'static(1)'."
    ::= { sdpBindMldSnpgGrpSrcEntry 3 }

sdpBndMldSnpgGrpSrcUpTime        OBJECT-TYPE
    SYNTAX      TimeTicks
    MAX-ACCESS  read-only
    STATUS      current
    DESCRIPTION
        "The value of the object sdpBndMldSnpgGrpSrcUpTime indicates how long
         (in centiseconds) that the source address already exists in the
         database for this SDP Bind."
    ::= { sdpBindMldSnpgGrpSrcEntry 4 }

sdpBndMldSnpgGrpSrcExpiryTime    OBJECT-TYPE
    SYNTAX      Unsigned32
    UNITS       "seconds"
    MAX-ACCESS  read-only
    STATUS      current
    DESCRIPTION
        "The value of the object sdpBndMldSnpgGrpSrcExpiryTime indicates the
         minimum amount of time remaining before this entry will be aged out.

         If the value of sdpBndMldSnpgGrpSrcExpiryTime is non-zero and the
         value of sdpBndMldSnpgGrpFilterMode corresponding to this entry is
         'include(1)', it means that there are currently one or more systems
         which desire to receive multicast traffic for this source.

         If this timer expires and the value of sdpBndMldSnpgGrpFilterMode is
         'include(1)', the system concludes that traffic from this particular
         source is no longer desired on the attached network, and deletes this
         entry.

         If  the value of sdpBndMldSnpgGrpSrcExpiryTime is non-zero and the
         filter-mode for the group is 'exclude(2)', it means that at least one
         system desires to receive multicast traffic from this source.

         If the value of sdpBndMldSnpgGrpSrcExpiryTime is zero and the
         filter-mode for the group is 'exclude(2)', it means that no system
         desires to receive multicast traffic from this source."
    ::= { sdpBindMldSnpgGrpSrcEntry 5 }

sdpBndMldSnpgGrpSrcFwdOrBlk      OBJECT-TYPE
    SYNTAX      INTEGER {
        forward (1),
        block   (2)
    }
    MAX-ACCESS  read-only
    STATUS      current
    DESCRIPTION
        "sdpBndMldSnpgGrpSrcFwdOrBlk indicates whether this entry is on the
         forward list or block list."
    ::= { sdpBindMldSnpgGrpSrcEntry 6 }

sdpBindMldSnpgStatGrpSrcTblLstCh OBJECT-TYPE
    SYNTAX      TimeStamp
    MAX-ACCESS  read-only
    STATUS      current
    DESCRIPTION
        "The value of the object sdpBindMldSnpgStatGrpSrcTblLstCh indicates the
         value of sysUpTime at the time of the last modification of an entry in
         the sdpBindMldSnpgStatGrpSrcTable."
    ::= { tmnxMldSnoopingSdpBindObjs 5 }

sdpBindMldSnpgStatGrpSrcTable    OBJECT-TYPE
    SYNTAX      SEQUENCE OF SdpBindMldSnpgStatGrpSrcEntry
    MAX-ACCESS  not-accessible
    STATUS      current
    DESCRIPTION
        "The table sdpBindMldSnpgStatGrpSrcTable contains statically configured
         (S,G) entries for each SDP Bind."
    ::= { tmnxMldSnoopingSdpBindObjs 6 }

sdpBindMldSnpgStatGrpSrcEntry    OBJECT-TYPE
    SYNTAX      SdpBindMldSnpgStatGrpSrcEntry
    MAX-ACCESS  not-accessible
    STATUS      current
    DESCRIPTION
        "An entry in the sdpBindMldSnpgStatGrpSrcTable. Entries can be created
         or deleted by an SNMP SET request to sdpBndMldSnpgStaticRowstatus."
    INDEX       {
        svcId,
        sdpBindId,
        sdpBndMldSnpgStaticGroupAddrType,
        sdpBndMldSnpgStaticGroupAddr,
        sdpBndMldSnpgStaticSourceAddrTp,
        sdpBndMldSnpgStaticSourceAddr
    }
    ::= { sdpBindMldSnpgStatGrpSrcTable 1 }

SdpBindMldSnpgStatGrpSrcEntry    ::= SEQUENCE
{
    sdpBndMldSnpgStaticGroupAddrType InetAddressType,
    sdpBndMldSnpgStaticGroupAddr     InetAddress,
    sdpBndMldSnpgStaticSourceAddrTp  InetAddressType,
    sdpBndMldSnpgStaticSourceAddr    InetAddress,
    sdpBndMldSnpgStaticRowstatus     RowStatus,
    sdpBndMldSnpgStaticLastChange    TimeStamp
}

sdpBndMldSnpgStaticGroupAddrType OBJECT-TYPE
    SYNTAX      InetAddressType
    MAX-ACCESS  not-accessible
    STATUS      current
    DESCRIPTION
        "The value of the object sdpBndMldSnpgStaticGroupAddrType specifies the
         type of sdpBndMldSnpgStaticGroupAddr."
    ::= { sdpBindMldSnpgStatGrpSrcEntry 1 }

sdpBndMldSnpgStaticGroupAddr     OBJECT-TYPE
    SYNTAX      InetAddress (SIZE (4|16))
    MAX-ACCESS  not-accessible
    STATUS      current
    DESCRIPTION
        "The value of the object sdpBndMldSnpgStaticGroupAddr specifies the
         group multicast address for this statically configured (S,G) entry for
         this SDP Bind."
    ::= { sdpBindMldSnpgStatGrpSrcEntry 2 }

sdpBndMldSnpgStaticSourceAddrTp  OBJECT-TYPE
    SYNTAX      InetAddressType
    MAX-ACCESS  not-accessible
    STATUS      current
    DESCRIPTION
        "The value of the object sdpBndMldSnpgStaticSourceAddrTp specifies the
         type of sdpBndMldSnpgStaticSourceAddr."
    ::= { sdpBindMldSnpgStatGrpSrcEntry 3 }

sdpBndMldSnpgStaticSourceAddr    OBJECT-TYPE
    SYNTAX      InetAddress (SIZE (4|16))
    MAX-ACCESS  not-accessible
    STATUS      current
    DESCRIPTION
        "The value of the object sdpBndMldSnpgStaticSourceAddr specifies the
         source IP address for this statically configured (S,G) entry for this
         SDP Bind. For a (*,G) entry this object must be set to all zeros."
    ::= { sdpBindMldSnpgStatGrpSrcEntry 4 }

sdpBndMldSnpgStaticRowstatus     OBJECT-TYPE
    SYNTAX      RowStatus
    MAX-ACCESS  read-create
    STATUS      current
    DESCRIPTION
        "The value of the object sdpBndMldSnpgStaticRowstatus specifies the row
         status used for creation or deletion of sdpBindMldSnpgStatGrpSrcTable
         entries."
    ::= { sdpBindMldSnpgStatGrpSrcEntry 5 }

sdpBndMldSnpgStaticLastChange    OBJECT-TYPE
    SYNTAX      TimeStamp
    MAX-ACCESS  read-only
    STATUS      current
    DESCRIPTION
        "The value of the object sdpBndMldSnpgStaticLastChange indicates the
         sysUpTime at the time of the last modification of this entry."
    ::= { sdpBindMldSnpgStatGrpSrcEntry 6 }

sdpBindMldSnpgStatsTable         OBJECT-TYPE
    SYNTAX      SEQUENCE OF SdpBindMldSnpgStatsEntry
    MAX-ACCESS  not-accessible
    STATUS      current
    DESCRIPTION
        "sdpBindMldSnpgStatsTable contains statistics on MLD snooping per SDP
         Bind.

         Conceptual rows in this table are created and deleted automatically by
         the system when MLD snooping is enabled and disabled in the interface
         containing the SDP bind."
    ::= { tmnxMldSnoopingSdpBindObjs 7 }

sdpBindMldSnpgStatsEntry         OBJECT-TYPE
    SYNTAX      SdpBindMldSnpgStatsEntry
    MAX-ACCESS  not-accessible
    STATUS      current
    DESCRIPTION
        "sdpBindMldSnpgStatsEntry is an entry in the sdpBindMldSnpgStatsTable.
         Each entry contains MLD snooping statics for a SDP Bind in a Tls."
    INDEX       {
        svcId,
        sdpBindId
    }
    ::= { sdpBindMldSnpgStatsTable 1 }

SdpBindMldSnpgStatsEntry         ::= SEQUENCE
{
    sdpBndMldSnpgTxGenQueries        Counter32,
    sdpBndMldSnpgTxGrpSpecQueries    Counter32,
    sdpBndMldSnpgTxSrcSpecQueries    Counter32,
    sdpBndMldSnpgTxV1Reports         Counter32,
    sdpBndMldSnpgTxV2Reports         Counter32,
    sdpBndMldSnpgTxV1Leaves          Counter32,
    sdpBndMldSnpgRxGenQueries        Counter32,
    sdpBndMldSnpgRxGrpSpecQueries    Counter32,
    sdpBndMldSnpgRxSrcSpecQueries    Counter32,
    sdpBndMldSnpgRxV1Reports         Counter32,
    sdpBndMldSnpgRxV2Reports         Counter32,
    sdpBndMldSnpgRxV1Leaves          Counter32,
    sdpBndMldSnpgRxUnknownType       Counter32,
    sdpBndMldSnpgFwdGenQueries       Counter32,
    sdpBndMldSnpgFwdGrpSpecQueries   Counter32,
    sdpBndMldSnpgFwdSrcSpecQueries   Counter32,
    sdpBndMldSnpgFwdV1Reports        Counter32,
    sdpBndMldSnpgFwdV2Reports        Counter32,
    sdpBndMldSnpgFwdV1Leaves         Counter32,
    sdpBndMldSnpgFwdUnknownType      Counter32,
    sdpBndMldSnpgRxBadLenPkts        Counter32,
    sdpBndMldSnpgRxBadMldChksmPkts   Counter32,
    sdpBndMldSnpgRxBadEncodedPkts    Counter32,
    sdpBndMldSnpgRxNoRtrAlertPkts    Counter32,
    sdpBndMldSnpgRxZeroSrcAdrPkts    Counter32,
    sdpBndMldSnpgSendQueryCfgDrops   Counter32,
    sdpBndMldSnpgImportPolicyDrops   Counter32,
    sdpBndMldSnpgMaxNumGroupsDrops   Counter32,
    sdpBndMldSnpgRxWrongVersionPkts  Counter32,
    sdpBndMldSnpgRxLocalScopePkts    Counter32,
    sdpBndMldSnpgRxRsvdScopePkts     Counter32,
    sdpBndMldSnpgMcacPolicyDrops     Counter32,
    sdpBndMldSnpgRxJoinSyncRtes      Unsigned32,
    sdpBndMldSnpgDropJoinSyncRtes    Unsigned32,
    sdpBndMldSnpgTxJoinSyncRtes      Unsigned32,
    sdpBndMldSnpgRxLeaveSyncRtes     Unsigned32,
    sdpBndMldSnpgDropLeaveSyncRtes   Unsigned32,
    sdpBndMldSnpgTxLeaveSyncRtes     Unsigned32
}

sdpBndMldSnpgTxGenQueries        OBJECT-TYPE
    SYNTAX      Counter32
    MAX-ACCESS  read-only
    STATUS      current
    DESCRIPTION
        "The value of the object sdpBndMldSnpgTxGenQueries indicates the number
         of MLD General Queries transmitted on this SDP Bind."
    ::= { sdpBindMldSnpgStatsEntry 1 }

sdpBndMldSnpgTxGrpSpecQueries    OBJECT-TYPE
    SYNTAX      Counter32
    MAX-ACCESS  read-only
    STATUS      current
    DESCRIPTION
        "The value of the object sdpBndMldSnpgTxGrpSpecQueries indicates the
         number of MLD Group-Specific Queries transmitted on this SDP Bind."
    ::= { sdpBindMldSnpgStatsEntry 2 }

sdpBndMldSnpgTxSrcSpecQueries    OBJECT-TYPE
    SYNTAX      Counter32
    MAX-ACCESS  read-only
    STATUS      current
    DESCRIPTION
        "The value of the object sdpBndMldSnpgTxSrcSpecQueries indicates the
         number of MLD Group-And-Source-Specific Queries transmitted on this
         SDP Bind."
    ::= { sdpBindMldSnpgStatsEntry 3 }

sdpBndMldSnpgTxV1Reports         OBJECT-TYPE
    SYNTAX      Counter32
    MAX-ACCESS  read-only
    STATUS      current
    DESCRIPTION
        "The value of the object sdpBndMldSnpgTxV1Reports indicates the number
         of MLDv1 Reports transmitted on this SDP Bind."
    ::= { sdpBindMldSnpgStatsEntry 4 }

sdpBndMldSnpgTxV2Reports         OBJECT-TYPE
    SYNTAX      Counter32
    MAX-ACCESS  read-only
    STATUS      current
    DESCRIPTION
        "The value of the object sdpBndMldSnpgTxV2Reports indicates the number
         of MLDv2 Reports transmitted on this SDP Bind."
    ::= { sdpBindMldSnpgStatsEntry 5 }

sdpBndMldSnpgTxV1Leaves          OBJECT-TYPE
    SYNTAX      Counter32
    MAX-ACCESS  read-only
    STATUS      current
    DESCRIPTION
        "The value of the object sdpBndMldSnpgTxV1Leaves indicates the number
         of MLDv1 Leaves transmitted on this SDP Bind."
    ::= { sdpBindMldSnpgStatsEntry 6 }

sdpBndMldSnpgRxGenQueries        OBJECT-TYPE
    SYNTAX      Counter32
    MAX-ACCESS  read-only
    STATUS      current
    DESCRIPTION
        "The value of the object sdpBndMldSnpgRxGenQueries indicates the number
         of MLD General Queries received on this SDP Bind."
    ::= { sdpBindMldSnpgStatsEntry 7 }

sdpBndMldSnpgRxGrpSpecQueries    OBJECT-TYPE
    SYNTAX      Counter32
    MAX-ACCESS  read-only
    STATUS      current
    DESCRIPTION
        "The value of the object sdpBndMldSnpgRxGrpSpecQueries indicates the
         number of MLD Group-Specific Queries received on this SDP Bind."
    ::= { sdpBindMldSnpgStatsEntry 8 }

sdpBndMldSnpgRxSrcSpecQueries    OBJECT-TYPE
    SYNTAX      Counter32
    MAX-ACCESS  read-only
    STATUS      current
    DESCRIPTION
        "The value of the object sdpBndMldSnpgRxSrcSpecQueries indicates the
         number of MLD Group-And-Source-Specific Queries received on this SDP
         Bind."
    ::= { sdpBindMldSnpgStatsEntry 9 }

sdpBndMldSnpgRxV1Reports         OBJECT-TYPE
    SYNTAX      Counter32
    MAX-ACCESS  read-only
    STATUS      current
    DESCRIPTION
        "The value of the object sdpBndMldSnpgRxV1Reports indicates the number
         of MLDv1 Reports received on this SDP Bind."
    ::= { sdpBindMldSnpgStatsEntry 10 }

sdpBndMldSnpgRxV2Reports         OBJECT-TYPE
    SYNTAX      Counter32
    MAX-ACCESS  read-only
    STATUS      current
    DESCRIPTION
        "The value of the object sdpBndMldSnpgRxV2Reports indicates the number
         of MLDv2 Reports received on this SDP Bind."
    ::= { sdpBindMldSnpgStatsEntry 11 }

sdpBndMldSnpgRxV1Leaves          OBJECT-TYPE
    SYNTAX      Counter32
    MAX-ACCESS  read-only
    STATUS      current
    DESCRIPTION
        "The value of the object sdpBndMldSnpgRxV1Leaves indicates the number
         of MLDv1 Leaves received on this SDP Bind."
    ::= { sdpBindMldSnpgStatsEntry 12 }

sdpBndMldSnpgRxUnknownType       OBJECT-TYPE
    SYNTAX      Counter32
    MAX-ACCESS  read-only
    STATUS      current
    DESCRIPTION
        "The value of the object sdpBndMldSnpgRxUnknownType indicates the
         number of MLD unknown type packets received on this SDP Bind."
    ::= { sdpBindMldSnpgStatsEntry 13 }

sdpBndMldSnpgFwdGenQueries       OBJECT-TYPE
    SYNTAX      Counter32
    MAX-ACCESS  read-only
    STATUS      current
    DESCRIPTION
        "The value of the object sdpBndMldSnpgFwdGenQueries indicates the
         number of MLD General Queries forwarded on this SDP Bind."
    ::= { sdpBindMldSnpgStatsEntry 14 }

sdpBndMldSnpgFwdGrpSpecQueries   OBJECT-TYPE
    SYNTAX      Counter32
    MAX-ACCESS  read-only
    STATUS      current
    DESCRIPTION
        "The value of the object sdpBndMldSnpgFwdGrpSpecQueries indicates the
         number of MLD Group-Specific Queries forwarded on this SDP Bind."
    ::= { sdpBindMldSnpgStatsEntry 15 }

sdpBndMldSnpgFwdSrcSpecQueries   OBJECT-TYPE
    SYNTAX      Counter32
    MAX-ACCESS  read-only
    STATUS      current
    DESCRIPTION
        "The value of the object sdpBndMldSnpgFwdSrcSpecQueries indicates the
         number of MLD Group-And-Source-Specific Queries forwarded on this SDP
         Bind."
    ::= { sdpBindMldSnpgStatsEntry 16 }

sdpBndMldSnpgFwdV1Reports        OBJECT-TYPE
    SYNTAX      Counter32
    MAX-ACCESS  read-only
    STATUS      current
    DESCRIPTION
        "The value of the object sdpBndMldSnpgFwdV1Reports indicates the number
         of MLDv1 Reports forwarded on this SDP Bind."
    ::= { sdpBindMldSnpgStatsEntry 17 }

sdpBndMldSnpgFwdV2Reports        OBJECT-TYPE
    SYNTAX      Counter32
    MAX-ACCESS  read-only
    STATUS      current
    DESCRIPTION
        "The value of the object sdpBndMldSnpgFwdV2Reports indicates
         the  number of MLDv2 Reports forwarded on this SDP Bind."
    ::= { sdpBindMldSnpgStatsEntry 18 }

sdpBndMldSnpgFwdV1Leaves         OBJECT-TYPE
    SYNTAX      Counter32
    MAX-ACCESS  read-only
    STATUS      current
    DESCRIPTION
        "The value of the object sdpBndMldSnpgFwdV1Leaves indicates the number
         of MLDv1 Leaves forwarded on this SDP Bind."
    ::= { sdpBindMldSnpgStatsEntry 19 }

sdpBndMldSnpgFwdUnknownType      OBJECT-TYPE
    SYNTAX      Counter32
    MAX-ACCESS  read-only
    STATUS      current
    DESCRIPTION
        "The value of the object sdpBndMldSnpgFwdUnknownType indicates the
         number of MLD unknown type packets forwarded on this SDP Bind."
    ::= { sdpBindMldSnpgStatsEntry 20 }

sdpBndMldSnpgRxBadLenPkts        OBJECT-TYPE
    SYNTAX      Counter32
    MAX-ACCESS  read-only
    STATUS      current
    DESCRIPTION
        "The value of the object sdpBndMldSnpgRxBadLenPkts indicates the number
         of MLD packets dropped on this SDP Bind because of a bad length."
    ::= { sdpBindMldSnpgStatsEntry 21 }

sdpBndMldSnpgRxBadMldChksmPkts   OBJECT-TYPE
    SYNTAX      Counter32
    MAX-ACCESS  read-only
    STATUS      current
    DESCRIPTION
        "The value of the object sdpBndMldSnpgRxBadMldChksmPkts indicates
         the number of  dropped  MLD packets on this SDP Bind because of a
         bad MLD header checksum."
    ::= { sdpBindMldSnpgStatsEntry 22 }

sdpBndMldSnpgRxBadEncodedPkts    OBJECT-TYPE
    SYNTAX      Counter32
    MAX-ACCESS  read-only
    STATUS      current
    DESCRIPTION
        "The value of the object sdpBndMldSnpgRxBadEncodedPkts indicates the
         number of MLD packets dropped on this SDP Bind because of a bad
         encoding."
    ::= { sdpBindMldSnpgStatsEntry 23 }

sdpBndMldSnpgRxNoRtrAlertPkts    OBJECT-TYPE
    SYNTAX      Counter32
    MAX-ACCESS  read-only
    STATUS      current
    DESCRIPTION
        "The value of the object sdpBndMldSnpgRxNoRtrAlertPkts indicates the
         number of MLD packets dropped on this SDP Bind because the Router
         Alert Option in the IP packet is not set."
    ::= { sdpBindMldSnpgStatsEntry 24 }

sdpBndMldSnpgRxZeroSrcAdrPkts    OBJECT-TYPE
    SYNTAX      Counter32
    MAX-ACCESS  read-only
    STATUS      current
    DESCRIPTION
        "The value of the object sdpBndMldSnpgRxZeroSrcAdrPkts indicates the
         number of MLD packets dropped on this SDP Bind because they contain a
         zero source IPv6 address."
    ::= { sdpBindMldSnpgStatsEntry 25 }

sdpBndMldSnpgSendQueryCfgDrops   OBJECT-TYPE
    SYNTAX      Counter32
    MAX-ACCESS  read-only
    STATUS      current
    DESCRIPTION
        "The  value of the object sdpBndMldSnpgSendQueryCfgDrops indicates
         the number of times an MLD Query is dropped because the
         object sdpBndMldSnpgCfgSendQueries for this SDP Bind is set to
         'inService(2)'."
    ::= { sdpBindMldSnpgStatsEntry 26 }

sdpBndMldSnpgImportPolicyDrops   OBJECT-TYPE
    SYNTAX      Counter32
    MAX-ACCESS  read-only
    STATUS      current
    DESCRIPTION
        "The  value of the object sdpBndMldSnpgImportPolicyDrops indicates
         the number of times an MLD group or source is dropped
         because of applying an import policy on this SDP Bind."
    ::= { sdpBindMldSnpgStatsEntry 27 }

sdpBndMldSnpgMaxNumGroupsDrops   OBJECT-TYPE
    SYNTAX      Counter32
    MAX-ACCESS  read-only
    STATUS      current
    DESCRIPTION
        "The  value of the object sdpBndMldSnpgMaxNumGroupsDrops indicates
         the number of times an MLD group is dropped because of exceeding the
         configured maximum number of groups on this SDP Bind."
    ::= { sdpBindMldSnpgStatsEntry 28 }

sdpBndMldSnpgRxWrongVersionPkts  OBJECT-TYPE
    SYNTAX      Counter32
    MAX-ACCESS  read-only
    STATUS      current
    DESCRIPTION
        "The value of the object sdpBndMldSnpgRxWrongVersionPkts indicates the
         total number of MLD packets with a wrong version received on this SDP
         Bind."
    ::= { sdpBindMldSnpgStatsEntry 29 }

sdpBndMldSnpgRxLocalScopePkts    OBJECT-TYPE
    SYNTAX      Counter32
    MAX-ACCESS  read-only
    STATUS      current
    DESCRIPTION
        "The value of the object sdpBndMldSnpgRxLocalScopePkts indicates the
         number of MLD packets received on the link-local scope IPv6 multicast
         address."
    ::= { sdpBindMldSnpgStatsEntry 30 }

sdpBndMldSnpgRxRsvdScopePkts     OBJECT-TYPE
    SYNTAX      Counter32
    MAX-ACCESS  read-only
    STATUS      current
    DESCRIPTION
        "The value of the object sdpBndMldSnpgRxRsvdScopePkts indicates the
         number of MLD packets received on the reserved scope IPv6 multicast
         address."
    ::= { sdpBindMldSnpgStatsEntry 31 }

sdpBndMldSnpgMcacPolicyDrops     OBJECT-TYPE
    SYNTAX      Counter32
    MAX-ACCESS  read-only
    STATUS      current
    DESCRIPTION
        "The value of the object sdpBndMldSnpgMcacPolicyDrops indicates the
         number of times an MLD Group is dropped because of applying a
         multicast CAC policy on this SDP Bind."
    ::= { sdpBindMldSnpgStatsEntry 32 }

sdpBndMldSnpgRxJoinSyncRtes      OBJECT-TYPE
    SYNTAX      Unsigned32
    MAX-ACCESS  read-only
    STATUS      current
    DESCRIPTION
        "sdpBndMldSnpgRxJoinSyncRtes is the number of received Bgp Multicast
         Join Sync routes fort this SDP Bind."
    ::= { sdpBindMldSnpgStatsEntry 33 }

sdpBndMldSnpgDropJoinSyncRtes    OBJECT-TYPE
    SYNTAX      Unsigned32
    MAX-ACCESS  read-only
    STATUS      current
    DESCRIPTION
        "sdpBndMldSnpgDropJoinSyncRtes is the number of dropped Bgp Multicast
         Join Sync routes for this SDP Bind."
    ::= { sdpBindMldSnpgStatsEntry 34 }

sdpBndMldSnpgTxJoinSyncRtes      OBJECT-TYPE
    SYNTAX      Unsigned32
    MAX-ACCESS  read-only
    STATUS      current
    DESCRIPTION
        "sdpBndMldSnpgTxJoinSyncRtes is the number of transmitted Smet Bgp
         Multicast Join Sync from this SDP Bind."
    ::= { sdpBindMldSnpgStatsEntry 35 }

sdpBndMldSnpgRxLeaveSyncRtes     OBJECT-TYPE
    SYNTAX      Unsigned32
    MAX-ACCESS  read-only
    STATUS      current
    DESCRIPTION
        "sdpBndMldSnpgRxLeaveSyncRtes is the number of received Bgp Multicast
         Leave Sync routes for this SDP Bind."
    ::= { sdpBindMldSnpgStatsEntry 36 }

sdpBndMldSnpgDropLeaveSyncRtes   OBJECT-TYPE
    SYNTAX      Unsigned32
    MAX-ACCESS  read-only
    STATUS      current
    DESCRIPTION
        "sdpBndMldSnpgDropLeaveSyncRtes is the number of dropped Bgp Multicast
         Leave Sync routes for this SDP Bind."
    ::= { sdpBindMldSnpgStatsEntry 37 }

sdpBndMldSnpgTxLeaveSyncRtes     OBJECT-TYPE
    SYNTAX      Unsigned32
    MAX-ACCESS  read-only
    STATUS      current
    DESCRIPTION
        "sdpBndMldSnpgTxLeaveSyncRtes is the number of transmitted Smet Bgp
         Multicast Leave Sync from this SDP Bind."
    ::= { sdpBindMldSnpgStatsEntry 38 }

tmnxMldSnoopingNotificationObjs  OBJECT IDENTIFIER ::= { tmnxMldSnoopingObjs 4 }

tmnxMldSnpgGroupAddressType      OBJECT-TYPE
    SYNTAX      InetAddressType
    MAX-ACCESS  accessible-for-notify
    STATUS      current
    DESCRIPTION
        "The value of the object tmnxMldSnpgGroupAddressType indicates the type
         of tmnxMldSnpgGroupAddress."
    ::= { tmnxMldSnoopingNotificationObjs 1 }

tmnxMldSnpgGroupAddress          OBJECT-TYPE
    SYNTAX      InetAddress (SIZE (4|16))
    MAX-ACCESS  accessible-for-notify
    STATUS      current
    DESCRIPTION
        "The value of the object tmnxMldSnpgGroupAddress indicates an IP
         multicast group address."
    ::= { tmnxMldSnoopingNotificationObjs 2 }

tmnxMldSnpgMcsFailureReason      OBJECT-TYPE
    SYNTAX      DisplayString
    MAX-ACCESS  accessible-for-notify
    STATUS      current
    DESCRIPTION
        "The value of the object tmnxMldSnpgMcsFailureReason indicates the
         reason why the sapMldSnpgMcsFailure notification is sent."
    ::= { tmnxMldSnoopingNotificationObjs 3 }

tmnxMldSnoopingVxlanObjs         OBJECT IDENTIFIER ::= { tmnxMldSnoopingObjs 5 }

vxlanMldSnpgGroupTable           OBJECT-TYPE
    SYNTAX      SEQUENCE OF VxlanMldSnpgGroupEntry
    MAX-ACCESS  not-accessible
    STATUS      current
    DESCRIPTION
        "vxlanMldSnpgGroupTable together with the table vxlanMldSnpgGrpSrcTable
         contains multicast group address information collected by MLD snooping
         for each VXLAN.

         Support for this table will be discontinued. Please use
         eVxlanMldSnpgGroupTable instead."
    ::= { tmnxMldSnoopingVxlanObjs 1 }

vxlanMldSnpgGroupEntry           OBJECT-TYPE
    SYNTAX      VxlanMldSnpgGroupEntry
    MAX-ACCESS  not-accessible
    STATUS      current
    DESCRIPTION
        "Each entry in this table indicates a multicast group address learned
         by MLD snooping on this VXLAN. If a Source list is present it is
         described in the corresponding entries of the vxlanMldSnpgGrpSrcTable
         table.

         Support for this entry will be discontinued. Please use
         eVxlanMldSnpgGroupEntry instead."
    INDEX       {
        svcId,
        vxlanVTEPAddr,
        vxlanVNI,
        vxlanMldSnpgGrpAddressType,
        vxlanMldSnpgGrpAddress
    }
    ::= { vxlanMldSnpgGroupTable 1 }

VxlanMldSnpgGroupEntry           ::= SEQUENCE
{
    vxlanMldSnpgGrpAddressType       InetAddressType,
    vxlanMldSnpgGrpAddress           InetAddress,
    vxlanMldSnpgGrpType              TmnxIgmpSnpgGroupType,
    vxlanMldSnpgGrpFilterMode        TmnxMldGroupFilterMode,
    vxlanMldSnpgGrpUpTime            TimeTicks,
    vxlanMldSnpgGrpExpiryTime        Unsigned32,
    vxlanMldSnpgGrpCompatMode        Unsigned32,
    vxlanMldSnpgGrpV1HostExpTime     Unsigned32
}

vxlanMldSnpgGrpAddressType       OBJECT-TYPE
    SYNTAX      InetAddressType
    MAX-ACCESS  not-accessible
    STATUS      current
    DESCRIPTION
        "The value of the object vxlanMldSnpgGrpAddressType indicates the type
         of vxlanMldSnpgGrpAddress."
    ::= { vxlanMldSnpgGroupEntry 1 }

vxlanMldSnpgGrpAddress           OBJECT-TYPE
    SYNTAX      InetAddress (SIZE (4|16))
    MAX-ACCESS  not-accessible
    STATUS      current
    DESCRIPTION
        "The value of the object vxlanMldSnpgGrpAddress indicates the IPv6
         multicast group address for which this entry contains information."
    ::= { vxlanMldSnpgGroupEntry 2 }

vxlanMldSnpgGrpType              OBJECT-TYPE
    SYNTAX      TmnxIgmpSnpgGroupType
    MAX-ACCESS  read-only
    STATUS      current
    DESCRIPTION
        "The value of the object vxlanMldSnpgGrpType indicates whether this
         entry was learned dynamically or was statically configured."
    ::= { vxlanMldSnpgGroupEntry 3 }

vxlanMldSnpgGrpFilterMode        OBJECT-TYPE
    SYNTAX      TmnxMldGroupFilterMode
    MAX-ACCESS  read-only
    STATUS      current
    DESCRIPTION
        "The value of the object vxlanMldSnpgGrpFilterMode indicates the
         filter-mode for this group."
    ::= { vxlanMldSnpgGroupEntry 5 }

vxlanMldSnpgGrpUpTime            OBJECT-TYPE
    SYNTAX      TimeTicks
    MAX-ACCESS  read-only
    STATUS      current
    DESCRIPTION
        "The value of the object vxlanMldSnpgGrpUpTime indicates how long (in
         centiseconds) that the group address already exists in the database
         for this VXLAN."
    ::= { vxlanMldSnpgGroupEntry 6 }

vxlanMldSnpgGrpExpiryTime        OBJECT-TYPE
    SYNTAX      Unsigned32
    UNITS       "seconds"
    MAX-ACCESS  read-only
    STATUS      current
    DESCRIPTION
        "The value of the object vxlanMldSnpgGrpExpiryTime indicates the amount
         of time remaining before this entry will be aged out."
    ::= { vxlanMldSnpgGroupEntry 7 }

vxlanMldSnpgGrpCompatMode        OBJECT-TYPE
    SYNTAX      Unsigned32
    MAX-ACCESS  read-only
    STATUS      current
    DESCRIPTION
        "The value of the object vxlanMldSnpgGrpCompatMode indicates the MLD
         version applicable on this VXLAN for this multicast group address.
         This corresponds to the lowest version seen for this group address on
         this VXLAN."
    ::= { vxlanMldSnpgGroupEntry 8 }

vxlanMldSnpgGrpV1HostExpTime     OBJECT-TYPE
    SYNTAX      Unsigned32
    UNITS       "seconds"
    MAX-ACCESS  read-only
    STATUS      current
    DESCRIPTION
        "The value of the object vxlanMldSnpgGrpV1HostExpTime indicates the
         time remaining until the system will assume that there are no longer
         any MLDv1 members on this SAP.

         Upon hearing any MLDv1 Membership Report, this value is reset to the
         group membership interval. While this time remaining is non-zero, the
         system ignores any MLDv2 'leave' messages for this group that it
         receives on this VXLAN."
    ::= { vxlanMldSnpgGroupEntry 9 }

vxlanMldSnpgGrpSrcTable          OBJECT-TYPE
    SYNTAX      SEQUENCE OF VxlanMldSnpgGrpSrcEntry
    MAX-ACCESS  not-accessible
    STATUS      current
    DESCRIPTION
        "vxlanMldSnpgGrpSrcTable lists the IPv4 multicast Sources corresponding
         to the IPv4 multicast groups listed in the vxlanMldSnpgGroupTable.

         Support for this table will be discontinued. Please use
         eVxlanMldSnpgGrpSrcTable instead."
    ::= { tmnxMldSnoopingVxlanObjs 2 }

vxlanMldSnpgGrpSrcEntry          OBJECT-TYPE
    SYNTAX      VxlanMldSnpgGrpSrcEntry
    MAX-ACCESS  not-accessible
    STATUS      current
    DESCRIPTION
        "An entry in the vxlanMldSnpgGrpSrcTable. Each entry represents a
         Source address from which receivers are interested/not interested in
         receiving multicast traffic from.

         Support for this entry will be discontinued. Please use
         eVxlanMldSnpgGrpSrcEntry instead."
    INDEX       {
        svcId,
        vxlanVTEPAddr,
        vxlanVNI,
        vxlanMldSnpgGrpAddressType,
        vxlanMldSnpgGrpAddress,
        vxlanMldSnpgGrpSrcAddrType,
        vxlanMldSnpgGrpSrcAddr
    }
    ::= { vxlanMldSnpgGrpSrcTable 1 }

VxlanMldSnpgGrpSrcEntry          ::= SEQUENCE
{
    vxlanMldSnpgGrpSrcAddrType       InetAddressType,
    vxlanMldSnpgGrpSrcAddr           InetAddress,
    vxlanMldSnpgGrpSrcType           TmnxIgmpSnpgGroupType,
    vxlanMldSnpgGrpSrcUpTime         TimeTicks,
    vxlanMldSnpgGrpSrcExpiryTime     Unsigned32,
    vxlanMldSnpgGrpSrcFwdOrBlk       INTEGER
}

vxlanMldSnpgGrpSrcAddrType       OBJECT-TYPE
    SYNTAX      InetAddressType
    MAX-ACCESS  not-accessible
    STATUS      current
    DESCRIPTION
        "The value of the object vxlanMldSnpgGrpSrcAddrType indicates the type
         of vxlanMldSnpgGrpSrcAddr."
    ::= { vxlanMldSnpgGrpSrcEntry 1 }

vxlanMldSnpgGrpSrcAddr           OBJECT-TYPE
    SYNTAX      InetAddress (SIZE (4|16))
    MAX-ACCESS  not-accessible
    STATUS      current
    DESCRIPTION
        "The value of the object vxlanMldSnpgGrpSrcAddr indicates the address
         of the source sending multicast traffic to the group identified by
         vxlanMldSnpgGrpAddress.

         If the value of vxlanMldSnpgGrpFilterMode corresponding to this entry
         is 'include(1)', the receivers are interested in receiving traffic
         from this source.

         If the value of vxlanMldSnpgGrpFilterMode corresponding to this entry
         is 'exclude(2)' the receivers, are not interested in receiving traffic
         from this source."
    ::= { vxlanMldSnpgGrpSrcEntry 2 }

vxlanMldSnpgGrpSrcType           OBJECT-TYPE
    SYNTAX      TmnxIgmpSnpgGroupType
    MAX-ACCESS  read-only
    STATUS      current
    DESCRIPTION
        "The value of the object vxlanMldSnpgGrpSrcType indicates how this
         source entry was learned.

         If this source entry was learned, this object is set to 'dynamic(2)'.
         For statically configured sources, this object is set to 'static(1)'."
    ::= { vxlanMldSnpgGrpSrcEntry 3 }

vxlanMldSnpgGrpSrcUpTime         OBJECT-TYPE
    SYNTAX      TimeTicks
    MAX-ACCESS  read-only
    STATUS      current
    DESCRIPTION
        "The value of the object vxlanMldSnpgGrpSrcUpTime indicates how long
         (in centiseconds) that the Source address already exists in the
         database for this VXLAN."
    ::= { vxlanMldSnpgGrpSrcEntry 4 }

vxlanMldSnpgGrpSrcExpiryTime     OBJECT-TYPE
    SYNTAX      Unsigned32
    UNITS       "seconds"
    MAX-ACCESS  read-only
    STATUS      current
    DESCRIPTION
        "The value of the object vxlanMldSnpgGrpSrcExpiryTime indicates the
         minimum amount of time remaining before this entry will be aged out.

         If the value of vxlanMldSnpgGrpSrcExpiryTime is non-zero and the value
         of vxlanMldSnpgGrpFilterMode corresponding to this entry is
         'include(1)', it means that there are currently one or more systems
         which desire to receive multicast traffic for this Source.

         If this timer expires and the value of vxlanMldSnpgGrpFilterMode is
         'include(1)', the system concludes that traffic from this particular
         Source is no longer desired on the attached network, and deletes this
         entry.

         If the value of vxlanMldSnpgGrpSrcExpiryTime is non-zero and the
         filter-mode for the group is 'exclude(2)', it means that at least one
         system desires to receive multicast traffic from this source.

         If the value of vxlanMldSnpgGrpSrcExpiryTime is zero and the
         filter-mode for the group is 'exclude(2)', it means that no system
         desires to receive multicast traffic from this Source."
    ::= { vxlanMldSnpgGrpSrcEntry 5 }

vxlanMldSnpgGrpSrcFwdOrBlk       OBJECT-TYPE
    SYNTAX      INTEGER {
        forward (1),
        block   (2)
    }
    MAX-ACCESS  read-only
    STATUS      current
    DESCRIPTION
        "vxlanMldSnpgGrpSrcFwdOrBlk indicates whether this entry is on the
         forward list or block list."
    ::= { vxlanMldSnpgGrpSrcEntry 6 }

vxlanMldSnpgStatsTable           OBJECT-TYPE
    SYNTAX      SEQUENCE OF VxlanMldSnpgStatsEntry
    MAX-ACCESS  not-accessible
    STATUS      current
    DESCRIPTION
        "vxlanMldSnpgStatsTable contains statistics on MLD snooping per VXLAN.

         Support for this table will be discontinued. Please use
         eVxlanMldSnpgStatsTable instead."
    ::= { tmnxMldSnoopingVxlanObjs 3 }

vxlanMldSnpgStatsEntry           OBJECT-TYPE
    SYNTAX      VxlanMldSnpgStatsEntry
    MAX-ACCESS  not-accessible
    STATUS      current
    DESCRIPTION
        "vxlanMldSnpgStatsEntry is an entry in the vxlanMldSnpgStatsTable. Each
         entry contains MLD snooping statics for a VXLAN in a Tls.

         Support for this entry will be discontinued. Please use
         eVxlanMldSnpgStatsEntry instead."
    INDEX       {
        svcId,
        vxlanVTEPAddr,
        vxlanVNI
    }
    ::= { vxlanMldSnpgStatsTable 1 }

VxlanMldSnpgStatsEntry           ::= SEQUENCE
{
    vxlanMldSnpgTxGenQueries         Counter32,
    vxlanMldSnpgTxGrpSpecQueries     Counter32,
    vxlanMldSnpgTxSrcSpecQueries     Counter32,
    vxlanMldSnpgTxV1Reports          Counter32,
    vxlanMldSnpgTxV2Reports          Counter32,
    vxlanMldSnpgTxV1Leaves           Counter32,
    vxlanMldSnpgRxGenQueries         Counter32,
    vxlanMldSnpgRxGrpSpecQueries     Counter32,
    vxlanMldSnpgRxSrcSpecQueries     Counter32,
    vxlanMldSnpgRxV1Reports          Counter32,
    vxlanMldSnpgRxV2Reports          Counter32,
    vxlanMldSnpgRxV1Leaves           Counter32,
    vxlanMldSnpgRxUnknownType        Counter32,
    vxlanMldSnpgFwdGenQueries        Counter32,
    vxlanMldSnpgFwdGrpSpecQueries    Counter32,
    vxlanMldSnpgFwdSrcSpecQueries    Counter32,
    vxlanMldSnpgFwdV1Reports         Counter32,
    vxlanMldSnpgFwdV2Reports         Counter32,
    vxlanMldSnpgFwdV1Leaves          Counter32,
    vxlanMldSnpgFwdUnknownType       Counter32,
    vxlanMldSnpgRxBadLenPkts         Counter32,
    vxlanMldSnpgRxBadMldChksmPkts    Counter32,
    vxlanMldSnpgRxBadEncodedPkts     Counter32,
    vxlanMldSnpgRxNoRtrAlertPkts     Counter32,
    vxlanMldSnpgRxZeroSrcAdrPkts     Counter32,
    vxlanMldSnpgSendQueryCfgDrops    Counter32,
    vxlanMldSnpgImportPolicyDrops    Counter32,
    vxlanMldSnpgMaxNumGroupsDrops    Counter32,
    vxlanMldSnpgRxWrongVersionPkts   Counter32,
    vxlanMldSnpgRxLocalScopePkts     Counter32,
    vxlanMldSnpgRxRsvdScopePkts      Counter32,
    vxlanMldSnpgMcacPolicyDrops      Counter32
}

vxlanMldSnpgTxGenQueries         OBJECT-TYPE
    SYNTAX      Counter32
    MAX-ACCESS  read-only
    STATUS      current
    DESCRIPTION
        "The value of the object vxlanMldSnpgTxGenQueries indicates the number
         of MLD General Queries transmitted on this VXLAN."
    ::= { vxlanMldSnpgStatsEntry 1 }

vxlanMldSnpgTxGrpSpecQueries     OBJECT-TYPE
    SYNTAX      Counter32
    MAX-ACCESS  read-only
    STATUS      current
    DESCRIPTION
        "The value of the object vxlanMldSnpgTxGrpSpecQueries indicates the
         number of MLD Group-Specific Queries transmitted on this VXLAN."
    ::= { vxlanMldSnpgStatsEntry 2 }

vxlanMldSnpgTxSrcSpecQueries     OBJECT-TYPE
    SYNTAX      Counter32
    MAX-ACCESS  read-only
    STATUS      current
    DESCRIPTION
        "The value of the object vxlanMldSnpgTxSrcSpecQueries indicates the
         number of MLD Group-And-Source-Specific Queries transmitted on this
         VXLAN."
    ::= { vxlanMldSnpgStatsEntry 3 }

vxlanMldSnpgTxV1Reports          OBJECT-TYPE
    SYNTAX      Counter32
    MAX-ACCESS  read-only
    STATUS      current
    DESCRIPTION
        "The value of the object vxlanMldSnpgTxV1Reports indicates the number
         of MLDv1 Reports transmitted on this VXLAN."
    ::= { vxlanMldSnpgStatsEntry 4 }

vxlanMldSnpgTxV2Reports          OBJECT-TYPE
    SYNTAX      Counter32
    MAX-ACCESS  read-only
    STATUS      current
    DESCRIPTION
        "The value of the object vxlanMldSnpgTxV2Reports indicates the number
         of MLDv2 Reports transmitted on this VXLAN."
    ::= { vxlanMldSnpgStatsEntry 5 }

vxlanMldSnpgTxV1Leaves           OBJECT-TYPE
    SYNTAX      Counter32
    MAX-ACCESS  read-only
    STATUS      current
    DESCRIPTION
        "The value of the object vxlanMldSnpgTxV1Leaves indicates the number of
         MLDv1 Leaves transmitted on this VXLAN."
    ::= { vxlanMldSnpgStatsEntry 6 }

vxlanMldSnpgRxGenQueries         OBJECT-TYPE
    SYNTAX      Counter32
    MAX-ACCESS  read-only
    STATUS      current
    DESCRIPTION
        "The value of the object vxlanMldSnpgRxGenQueries indicates the number
         of MLD General Queries received on this VXLAN."
    ::= { vxlanMldSnpgStatsEntry 7 }

vxlanMldSnpgRxGrpSpecQueries     OBJECT-TYPE
    SYNTAX      Counter32
    MAX-ACCESS  read-only
    STATUS      current
    DESCRIPTION
        "The value of the object vxlanMldSnpgRxGrpSpecQueries indicates the
         number of MLD Group-Specific Queries received on this VXLAN."
    ::= { vxlanMldSnpgStatsEntry 8 }

vxlanMldSnpgRxSrcSpecQueries     OBJECT-TYPE
    SYNTAX      Counter32
    MAX-ACCESS  read-only
    STATUS      current
    DESCRIPTION
        "The value of the object vxlanMldSnpgRxSrcSpecQueries indicates the
         number of MLD Group-And-Source-Specific Queries received on this
         VXLAN."
    ::= { vxlanMldSnpgStatsEntry 9 }

vxlanMldSnpgRxV1Reports          OBJECT-TYPE
    SYNTAX      Counter32
    MAX-ACCESS  read-only
    STATUS      current
    DESCRIPTION
        "The value of the object vxlanMldSnpgRxV1Reports indicates the number
         of MLDv1 Reports received on this VXLAN."
    ::= { vxlanMldSnpgStatsEntry 10 }

vxlanMldSnpgRxV2Reports          OBJECT-TYPE
    SYNTAX      Counter32
    MAX-ACCESS  read-only
    STATUS      current
    DESCRIPTION
        "The value of the object vxlanMldSnpgRxV2Reports indicates the number
         of MLDv2 Reports received on this VXLAN."
    ::= { vxlanMldSnpgStatsEntry 11 }

vxlanMldSnpgRxV1Leaves           OBJECT-TYPE
    SYNTAX      Counter32
    MAX-ACCESS  read-only
    STATUS      current
    DESCRIPTION
        "The value of the object vxlanMldSnpgRxV1Leaves indicates the number of
         MLDv1 Leaves received on this VXLAN."
    ::= { vxlanMldSnpgStatsEntry 12 }

vxlanMldSnpgRxUnknownType        OBJECT-TYPE
    SYNTAX      Counter32
    MAX-ACCESS  read-only
    STATUS      current
    DESCRIPTION
        "The value of the object vxlanMldSnpgRxUnknownType indicates the number
         of MLD unknown type packets received on this VXLAN."
    ::= { vxlanMldSnpgStatsEntry 13 }

vxlanMldSnpgFwdGenQueries        OBJECT-TYPE
    SYNTAX      Counter32
    MAX-ACCESS  read-only
    STATUS      current
    DESCRIPTION
        "The value of the object vxlanMldSnpgFwdGenQueries indicates the number
         of MLD General Queries forwarded on this VXLAN."
    ::= { vxlanMldSnpgStatsEntry 14 }

vxlanMldSnpgFwdGrpSpecQueries    OBJECT-TYPE
    SYNTAX      Counter32
    MAX-ACCESS  read-only
    STATUS      current
    DESCRIPTION
        "The value of the object vxlanMldSnpgFwdGrpSpecQueries indicates the
         number of MLD Group-Specific Queries forwarded on this VXLAN."
    ::= { vxlanMldSnpgStatsEntry 15 }

vxlanMldSnpgFwdSrcSpecQueries    OBJECT-TYPE
    SYNTAX      Counter32
    MAX-ACCESS  read-only
    STATUS      current
    DESCRIPTION
        "The value of the object vxlanMldSnpgFwdSrcSpecQueries indicates the
         number of MLD Group-And-Source-Specific Queries forwarded on this
         VXLAN."
    ::= { vxlanMldSnpgStatsEntry 16 }

vxlanMldSnpgFwdV1Reports         OBJECT-TYPE
    SYNTAX      Counter32
    MAX-ACCESS  read-only
    STATUS      current
    DESCRIPTION
        "The value of the object vxlanMldSnpgFwdV1Reports indicates the number
         of MLDv1 Reports forwarded on this VXLAN."
    ::= { vxlanMldSnpgStatsEntry 17 }

vxlanMldSnpgFwdV2Reports         OBJECT-TYPE
    SYNTAX      Counter32
    MAX-ACCESS  read-only
    STATUS      current
    DESCRIPTION
        "The value of the object vxlanMldSnpgFwdV2Reports indicates the number
         of MLDv2 Reports forwarded on this VXLAN."
    ::= { vxlanMldSnpgStatsEntry 18 }

vxlanMldSnpgFwdV1Leaves          OBJECT-TYPE
    SYNTAX      Counter32
    MAX-ACCESS  read-only
    STATUS      current
    DESCRIPTION
        "The value of the object vxlanMldSnpgFwdV1Leaves indicates the number
         of MLDv1 Leaves forwarded on this VXLAN."
    ::= { vxlanMldSnpgStatsEntry 19 }

vxlanMldSnpgFwdUnknownType       OBJECT-TYPE
    SYNTAX      Counter32
    MAX-ACCESS  read-only
    STATUS      current
    DESCRIPTION
        "The value of the object vxlanMldSnpgFwdUnknownType indicates the
         number of MLD unknown type packets forwarded on this VXLAN."
    ::= { vxlanMldSnpgStatsEntry 20 }

vxlanMldSnpgRxBadLenPkts         OBJECT-TYPE
    SYNTAX      Counter32
    MAX-ACCESS  read-only
    STATUS      current
    DESCRIPTION
        "The value of the object vxlanMldSnpgRxBadLenPkts indicates the number
         of MLD packets dropped on this VXLAN because of a bad length."
    ::= { vxlanMldSnpgStatsEntry 21 }

vxlanMldSnpgRxBadMldChksmPkts    OBJECT-TYPE
    SYNTAX      Counter32
    MAX-ACCESS  read-only
    STATUS      current
    DESCRIPTION
        "The value of the object vxlanMldSnpgRxBadMldChksmPkts indicates the
         number of dropped MLD packets on this VXLAN because of a bad MLD
         header checksum."
    ::= { vxlanMldSnpgStatsEntry 22 }

vxlanMldSnpgRxBadEncodedPkts     OBJECT-TYPE
    SYNTAX      Counter32
    MAX-ACCESS  read-only
    STATUS      current
    DESCRIPTION
        "The value of the object vxlanMldSnpgRxBadEncodedPkts indicates the
         number of MLD packets dropped on this VXLAN because of a bad encoding."
    ::= { vxlanMldSnpgStatsEntry 23 }

vxlanMldSnpgRxNoRtrAlertPkts     OBJECT-TYPE
    SYNTAX      Counter32
    MAX-ACCESS  read-only
    STATUS      current
    DESCRIPTION
        "The value of the object vxlanMldSnpgRxNoRtrAlertPkts indicates the
         number of MLD packets dropped on this VXLAN because the Router Alert
         Option in the IP packet is not set."
    ::= { vxlanMldSnpgStatsEntry 24 }

vxlanMldSnpgRxZeroSrcAdrPkts     OBJECT-TYPE
    SYNTAX      Counter32
    MAX-ACCESS  read-only
    STATUS      current
    DESCRIPTION
        "The value of the object vxlanMldSnpgRxZeroSrcAdrPkts indicates the
         number of MLD packets dropped on this VXLAN because they contain a
         zero source IPv6 address."
    ::= { vxlanMldSnpgStatsEntry 25 }

vxlanMldSnpgSendQueryCfgDrops    OBJECT-TYPE
    SYNTAX      Counter32
    MAX-ACCESS  read-only
    STATUS      current
    DESCRIPTION
        "The value of the object vxlanMldSnpgSendQueryCfgDrops indicates the
         number of times an MLD Query is dropped because the object
         sapMldSnpgCfgSendQueries for this VXLAN is set to 'enabled(1)'."
    ::= { vxlanMldSnpgStatsEntry 26 }

vxlanMldSnpgImportPolicyDrops    OBJECT-TYPE
    SYNTAX      Counter32
    MAX-ACCESS  read-only
    STATUS      current
    DESCRIPTION
        "The value of the object vxlanMldSnpgImportPolicyDrops indicates the
         number of times an MLD Group or Source is dropped because of applying
         an import policy on this VXLAN."
    ::= { vxlanMldSnpgStatsEntry 27 }

vxlanMldSnpgMaxNumGroupsDrops    OBJECT-TYPE
    SYNTAX      Counter32
    MAX-ACCESS  read-only
    STATUS      current
    DESCRIPTION
        "The value of the object vxlanMldSnpgMaxNumGroupsDrops indicates the
         number of times an MLD Group is dropped because of exceeding the
         configured maximum number of groups on this VXLAN."
    ::= { vxlanMldSnpgStatsEntry 28 }

vxlanMldSnpgRxWrongVersionPkts   OBJECT-TYPE
    SYNTAX      Counter32
    MAX-ACCESS  read-only
    STATUS      current
    DESCRIPTION
        "The value of the object vxlanMldSnpgRxWrongVersionPkts indicates the
         total number of MLD packets with a wrong version received on this
         VXLAN."
    ::= { vxlanMldSnpgStatsEntry 29 }

vxlanMldSnpgRxLocalScopePkts     OBJECT-TYPE
    SYNTAX      Counter32
    MAX-ACCESS  read-only
    STATUS      current
    DESCRIPTION
        "The value of the object vxlanMldSnpgRxLocalScopePkts indicates the
         number of MLD packets received on the link-local scope IPv6 multicast
         address."
    ::= { vxlanMldSnpgStatsEntry 30 }

vxlanMldSnpgRxRsvdScopePkts      OBJECT-TYPE
    SYNTAX      Counter32
    MAX-ACCESS  read-only
    STATUS      current
    DESCRIPTION
        "The value of the object vxlanMldSnpgRxRsvdScopePkts indicates the
         number of MLD packets received on the reserved scope IPv6 multicast
         address."
    ::= { vxlanMldSnpgStatsEntry 31 }

vxlanMldSnpgMcacPolicyDrops      OBJECT-TYPE
    SYNTAX      Counter32
    MAX-ACCESS  read-only
    STATUS      current
    DESCRIPTION
        "The value of the object vxlanMldSnpgMcacPolicyDrops indicates the
         number of times an MLD Group is dropped because of applying a
         multicast CAC policy on this VXLAN."
    ::= { vxlanMldSnpgStatsEntry 32 }

vxlanMldSnpgStateTable           OBJECT-TYPE
    SYNTAX      SEQUENCE OF VxlanMldSnpgStateEntry
    MAX-ACCESS  not-accessible
    STATUS      current
    DESCRIPTION
        "vxlanMldSnpgStatsTable contains states on MLD snooping per VXLAN."
    ::= { tmnxMldSnoopingVxlanObjs 4 }

vxlanMldSnpgStateEntry           OBJECT-TYPE
    SYNTAX      VxlanMldSnpgStateEntry
    MAX-ACCESS  not-accessible
    STATUS      current
    DESCRIPTION
        ""
    INDEX       {
        svcId,
        vxlanVTEPAddrType,
        vxlanVTEPAddress,
        vxlanVNI
    }
    ::= { vxlanMldSnpgStateTable 1 }

VxlanMldSnpgStateEntry           ::= SEQUENCE
{
    vxlanMldSnpgOperState            TmnxOperState,
    vxlanMldSnpgGroupCount           Unsigned32,
    vxlanMldIsSbd                    TruthValue,
    vxlanMldRxSmetRoutes             Unsigned32,
    vxlanMldDroppedSmetRoutes        Unsigned32,
    vxlanMldOrigAddrType             InetAddressType,
    vxlanMldOrigAddress              InetAddress,
    vxlanMldEvpnProxySupport         TruthValue
}

vxlanMldSnpgOperState            OBJECT-TYPE
    SYNTAX      TmnxOperState
    MAX-ACCESS  read-only
    STATUS      current
    DESCRIPTION
        "The value of the object vxlanMldSnpgOperState indicates the current
         operating state of this VXLAN."
    ::= { vxlanMldSnpgStateEntry 1 }

vxlanMldSnpgGroupCount           OBJECT-TYPE
    SYNTAX      Unsigned32
    MAX-ACCESS  read-only
    STATUS      current
    DESCRIPTION
        "vxlanMldSnpgGroupCount is the number of multicast groups which have
         been learned on this VXLAN."
    ::= { vxlanMldSnpgStateEntry 2 }

vxlanMldIsSbd                    OBJECT-TYPE
    SYNTAX      TruthValue
    MAX-ACCESS  read-only
    STATUS      current
    DESCRIPTION
        "vxlanMldIsSbd indicates whether this VXLAN is from a  supplementary
         broadcast domain."
    ::= { vxlanMldSnpgStateEntry 3 }

vxlanMldRxSmetRoutes             OBJECT-TYPE
    SYNTAX      Unsigned32
    MAX-ACCESS  read-only
    STATUS      current
    DESCRIPTION
        "vxlanMldRxSmetRoutes is the number of received Smet routes on this
         VXLAN."
    ::= { vxlanMldSnpgStateEntry 4 }

vxlanMldDroppedSmetRoutes        OBJECT-TYPE
    SYNTAX      Unsigned32
    MAX-ACCESS  read-only
    STATUS      current
    DESCRIPTION
        "vxlanMldDroppedSmetRoutes is the number of dropped Smet routes on this
         VXLAN."
    ::= { vxlanMldSnpgStateEntry 5 }

vxlanMldOrigAddrType             OBJECT-TYPE
    SYNTAX      InetAddressType
    MAX-ACCESS  read-only
    STATUS      current
    DESCRIPTION
        ""
    ::= { vxlanMldSnpgStateEntry 6 }

vxlanMldOrigAddress              OBJECT-TYPE
    SYNTAX      InetAddress (SIZE (4|16))
    MAX-ACCESS  read-only
    STATUS      current
    DESCRIPTION
        ""
    ::= { vxlanMldSnpgStateEntry 7 }

vxlanMldEvpnProxySupport         OBJECT-TYPE
    SYNTAX      TruthValue
    MAX-ACCESS  read-only
    STATUS      current
    DESCRIPTION
        "vxlanMldEvpnProxySupport indicates whether Mld Proxy  is supported on
         this VXLAN."
    ::= { vxlanMldSnpgStateEntry 8 }

eVxlanMldSnpgGroupTable          OBJECT-TYPE
    SYNTAX      SEQUENCE OF EVxlanMldSnpgGroupEntry
    MAX-ACCESS  not-accessible
    STATUS      current
    DESCRIPTION
        "eVxlanMldSnpgGroupTable together with the table
         eVxlanMldSnpgGrpSrcTable contains multicast group address information
         collected by MLD snooping for each VXLAN."
    ::= { tmnxMldSnoopingVxlanObjs 5 }

eVxlanMldSnpgGroupEntry          OBJECT-TYPE
    SYNTAX      EVxlanMldSnpgGroupEntry
    MAX-ACCESS  not-accessible
    STATUS      current
    DESCRIPTION
        "Each entry in this table indicates a multicast group address learned
         by MLD snooping on this VXLAN. If a Source list is present it is
         described in the corresponding entries of the eVxlanMldSnpgGrpSrcTable
         table."
    INDEX       {
        svcId,
        eVxlanVTEPAddrType,
        eVxlanVTEPAddr,
        eVxlanVNI,
        eVxlanMldSnpgGrpAddressType,
        eVxlanMldSnpgGrpAddress
    }
    ::= { eVxlanMldSnpgGroupTable 1 }

EVxlanMldSnpgGroupEntry          ::= SEQUENCE
{
    eVxlanMldSnpgGrpAddressType      InetAddressType,
    eVxlanMldSnpgGrpAddress          InetAddress,
    eVxlanMldSnpgGrpType             TmnxIgmpSnpgGroupType,
    eVxlanMldSnpgGrpFilterMode       TmnxMldGroupFilterMode,
    eVxlanMldSnpgGrpUpTime           TimeTicks,
    eVxlanMldSnpgGrpExpiryTime       Unsigned32,
    eVxlanMldSnpgGrpCompatMode       Unsigned32,
    eVxlanMldSnpgGrpV1HostExpTime    Unsigned32
}

eVxlanMldSnpgGrpAddressType      OBJECT-TYPE
    SYNTAX      InetAddressType
    MAX-ACCESS  not-accessible
    STATUS      current
    DESCRIPTION
        "The value of the object eVxlanMldSnpgGrpAddressType indicates the type
         of eVxlanMldSnpgGrpAddress."
    ::= { eVxlanMldSnpgGroupEntry 1 }

eVxlanMldSnpgGrpAddress          OBJECT-TYPE
    SYNTAX      InetAddress (SIZE (4|16))
    MAX-ACCESS  not-accessible
    STATUS      current
    DESCRIPTION
        "The value of the object eVxlanMldSnpgGrpAddress indicates the IPv6
         multicast group address for which this entry contains information."
    ::= { eVxlanMldSnpgGroupEntry 2 }

eVxlanMldSnpgGrpType             OBJECT-TYPE
    SYNTAX      TmnxIgmpSnpgGroupType
    MAX-ACCESS  read-only
    STATUS      current
    DESCRIPTION
        "The value of the object eVxlanMldSnpgGrpType indicates whether this
         entry was learned dynamically or was statically configured."
    ::= { eVxlanMldSnpgGroupEntry 3 }

eVxlanMldSnpgGrpFilterMode       OBJECT-TYPE
    SYNTAX      TmnxMldGroupFilterMode
    MAX-ACCESS  read-only
    STATUS      current
    DESCRIPTION
        "The value of the object eVxlanMldSnpgGrpFilterMode indicates the
         filter-mode for this group."
    ::= { eVxlanMldSnpgGroupEntry 5 }

eVxlanMldSnpgGrpUpTime           OBJECT-TYPE
    SYNTAX      TimeTicks
    MAX-ACCESS  read-only
    STATUS      current
    DESCRIPTION
        "The value of the object eVxlanMldSnpgGrpUpTime indicates how long (in
         centiseconds) that the group address already exists in the database
         for this VXLAN."
    ::= { eVxlanMldSnpgGroupEntry 6 }

eVxlanMldSnpgGrpExpiryTime       OBJECT-TYPE
    SYNTAX      Unsigned32
    UNITS       "seconds"
    MAX-ACCESS  read-only
    STATUS      current
    DESCRIPTION
        "The value of the object eVxlanMldSnpgGrpExpiryTime indicates the
         amount of time remaining before this entry will be aged out."
    ::= { eVxlanMldSnpgGroupEntry 7 }

eVxlanMldSnpgGrpCompatMode       OBJECT-TYPE
    SYNTAX      Unsigned32
    MAX-ACCESS  read-only
    STATUS      current
    DESCRIPTION
        "The value of the object eVxlanMldSnpgGrpCompatMode indicates the MLD
         version applicable on this VXLAN for this multicast group address.
         This corresponds to the lowest version seen for this group address on
         this VXLAN."
    ::= { eVxlanMldSnpgGroupEntry 8 }

eVxlanMldSnpgGrpV1HostExpTime    OBJECT-TYPE
    SYNTAX      Unsigned32
    UNITS       "seconds"
    MAX-ACCESS  read-only
    STATUS      current
    DESCRIPTION
        "The value of the object eVxlanMldSnpgGrpV1HostExpTime indicates the
         time remaining until the system will assume that there are no longer
         any MLDv1 members on this SAP.

         Upon hearing any MLDv1 Membership Report, this value is reset to the
         group membership interval. While this time remaining is non-zero, the
         system ignores any MLDv2 'leave' messages for this group that it
         receives on this VXLAN."
    ::= { eVxlanMldSnpgGroupEntry 9 }

eVxlanMldSnpgGrpSrcTable         OBJECT-TYPE
    SYNTAX      SEQUENCE OF EVxlanMldSnpgGrpSrcEntry
    MAX-ACCESS  not-accessible
    STATUS      current
    DESCRIPTION
        "eVxlanMldSnpgGrpSrcTable lists the IPv4 multicast Sources
         corresponding to the IPv4 multicast groups listed in the
         eVxlanMldSnpgGroupTable."
    ::= { tmnxMldSnoopingVxlanObjs 6 }

eVxlanMldSnpgGrpSrcEntry         OBJECT-TYPE
    SYNTAX      EVxlanMldSnpgGrpSrcEntry
    MAX-ACCESS  not-accessible
    STATUS      current
    DESCRIPTION
        "An entry in the eVxlanMldSnpgGrpSrcTable. Each entry represents a
         Source address from which receivers are interested/not interested in
         receiving multicast traffic from."
    INDEX       {
        svcId,
        eVxlanVTEPAddrType,
        eVxlanVTEPAddr,
        eVxlanVNI,
        eVxlanMldSnpgGrpAddressType,
        eVxlanMldSnpgGrpAddress,
        eVxlanMldSnpgGrpSrcAddrType,
        eVxlanMldSnpgGrpSrcAddr
    }
    ::= { eVxlanMldSnpgGrpSrcTable 1 }

EVxlanMldSnpgGrpSrcEntry         ::= SEQUENCE
{
    eVxlanMldSnpgGrpSrcAddrType      InetAddressType,
    eVxlanMldSnpgGrpSrcAddr          InetAddress,
    eVxlanMldSnpgGrpSrcType          TmnxIgmpSnpgGroupType,
    eVxlanMldSnpgGrpSrcUpTime        TimeTicks,
    eVxlanMldSnpgGrpSrcExpiryTime    Unsigned32,
    eVxlanMldSnpgGrpSrcFwdOrBlk      INTEGER
}

eVxlanMldSnpgGrpSrcAddrType      OBJECT-TYPE
    SYNTAX      InetAddressType
    MAX-ACCESS  not-accessible
    STATUS      current
    DESCRIPTION
        "The value of the object eVxlanMldSnpgGrpSrcAddrType indicates the type
         of eVxlanMldSnpgGrpSrcAddr."
    ::= { eVxlanMldSnpgGrpSrcEntry 1 }

eVxlanMldSnpgGrpSrcAddr          OBJECT-TYPE
    SYNTAX      InetAddress (SIZE (4|16))
    MAX-ACCESS  not-accessible
    STATUS      current
    DESCRIPTION
        "The value of the object eVxlanMldSnpgGrpSrcAddr indicates the address
         of the source sending multicast traffic to the group identified by
         eVxlanMldSnpgGrpAddress.

         If the value of eVxlanMldSnpgGrpFilterMode corresponding to this entry
         is 'include(1)', the receivers are interested in receiving traffic
         from this source.

         If the value of eVxlanMldSnpgGrpFilterMode corresponding to this entry
         is 'exclude(2)' the receivers, are not interested in receiving traffic
         from this source."
    ::= { eVxlanMldSnpgGrpSrcEntry 2 }

eVxlanMldSnpgGrpSrcType          OBJECT-TYPE
    SYNTAX      TmnxIgmpSnpgGroupType
    MAX-ACCESS  read-only
    STATUS      current
    DESCRIPTION
        "The value of the object eVxlanMldSnpgGrpSrcType indicates how this
         source entry was learned.

         If this source entry was learned, this object is set to 'dynamic(2)'.
         For statically configured sources, this object is set to 'static(1)'."
    ::= { eVxlanMldSnpgGrpSrcEntry 3 }

eVxlanMldSnpgGrpSrcUpTime        OBJECT-TYPE
    SYNTAX      TimeTicks
    MAX-ACCESS  read-only
    STATUS      current
    DESCRIPTION
        "The value of the object eVxlanMldSnpgGrpSrcUpTime indicates how long
         (in centiseconds) that the Source address already exists in the
         database for this VXLAN."
    ::= { eVxlanMldSnpgGrpSrcEntry 4 }

eVxlanMldSnpgGrpSrcExpiryTime    OBJECT-TYPE
    SYNTAX      Unsigned32
    UNITS       "seconds"
    MAX-ACCESS  read-only
    STATUS      current
    DESCRIPTION
        "The value of the object eVxlanMldSnpgGrpSrcExpiryTime indicates the
         minimum amount of time remaining before this entry will be aged out.

         If the value of eVxlanMldSnpgGrpSrcExpiryTime is non-zero and the
         value of eVxlanMldSnpgGrpFilterMode corresponding to this entry is
         'include(1)', it means that there are currently one or more systems
         which desire to receive multicast traffic for this Source.

         If this timer expires and the value of eVxlanMldSnpgGrpFilterMode is
         'include(1)', the system concludes that traffic from this particular
         Source is no longer desired on the attached network, and deletes this
         entry.

         If the value of eVxlanMldSnpgGrpSrcExpiryTime is non-zero and the
         filter-mode for the group is 'exclude(2)', it means that at least one
         system desires to receive multicast traffic from this source.

         If the value of eVxlanMldSnpgGrpSrcExpiryTime is zero and the
         filter-mode for the group is 'exclude(2)', it means that no system
         desires to receive multicast traffic from this Source."
    ::= { eVxlanMldSnpgGrpSrcEntry 5 }

eVxlanMldSnpgGrpSrcFwdOrBlk      OBJECT-TYPE
    SYNTAX      INTEGER {
        forward (1),
        block   (2)
    }
    MAX-ACCESS  read-only
    STATUS      current
    DESCRIPTION
        "eVxlanMldSnpgGrpSrcFwdOrBlk indicates whether this entry is on the
         forward list or block list."
    ::= { eVxlanMldSnpgGrpSrcEntry 6 }

eVxlanMldSnpgStatsTable          OBJECT-TYPE
    SYNTAX      SEQUENCE OF EVxlanMldSnpgStatsEntry
    MAX-ACCESS  not-accessible
    STATUS      current
    DESCRIPTION
        "eVxlanMldSnpgStatsTable contains statistics on MLD snooping per VXLAN."
    ::= { tmnxMldSnoopingVxlanObjs 7 }

eVxlanMldSnpgStatsEntry          OBJECT-TYPE
    SYNTAX      EVxlanMldSnpgStatsEntry
    MAX-ACCESS  not-accessible
    STATUS      current
    DESCRIPTION
        "eVxlanMldSnpgStatsEntry is an entry in the eVxlanMldSnpgStatsTable.
         Each entry contains MLD snooping statics for a VXLAN in a Tls."
    INDEX       {
        svcId,
        eVxlanVTEPAddrType,
        eVxlanVTEPAddr,
        eVxlanVNI
    }
    ::= { eVxlanMldSnpgStatsTable 1 }

EVxlanMldSnpgStatsEntry          ::= SEQUENCE
{
    eVxlanMldSnpgTxGenQueries        Counter32,
    eVxlanMldSnpgTxGrpSpecQueries    Counter32,
    eVxlanMldSnpgTxSrcSpecQueries    Counter32,
    eVxlanMldSnpgTxV1Reports         Counter32,
    eVxlanMldSnpgTxV2Reports         Counter32,
    eVxlanMldSnpgTxV1Leaves          Counter32,
    eVxlanMldSnpgRxGenQueries        Counter32,
    eVxlanMldSnpgRxGrpSpecQueries    Counter32,
    eVxlanMldSnpgRxSrcSpecQueries    Counter32,
    eVxlanMldSnpgRxV1Reports         Counter32,
    eVxlanMldSnpgRxV2Reports         Counter32,
    eVxlanMldSnpgRxV1Leaves          Counter32,
    eVxlanMldSnpgRxUnknownType       Counter32,
    eVxlanMldSnpgFwdGenQueries       Counter32,
    eVxlanMldSnpgFwdGrpSpecQueries   Counter32,
    eVxlanMldSnpgFwdSrcSpecQueries   Counter32,
    eVxlanMldSnpgFwdV1Reports        Counter32,
    eVxlanMldSnpgFwdV2Reports        Counter32,
    eVxlanMldSnpgFwdV1Leaves         Counter32,
    eVxlanMldSnpgFwdUnknownType      Counter32,
    eVxlanMldSnpgRxBadLenPkts        Counter32,
    eVxlanMldSnpgRxBadMldChksmPkts   Counter32,
    eVxlanMldSnpgRxBadEncodedPkts    Counter32,
    eVxlanMldSnpgRxNoRtrAlertPkts    Counter32,
    eVxlanMldSnpgRxZeroSrcAdrPkts    Counter32,
    eVxlanMldSnpgSendQueryCfgDrops   Counter32,
    eVxlanMldSnpgImportPolicyDrops   Counter32,
    eVxlanMldSnpgMaxNumGroupsDrops   Counter32,
    eVxlanMldSnpgRxWrongVersionPkts  Counter32,
    eVxlanMldSnpgRxLocalScopePkts    Counter32,
    eVxlanMldSnpgRxRsvdScopePkts     Counter32,
    eVxlanMldSnpgMcacPolicyDrops     Counter32
}

eVxlanMldSnpgTxGenQueries        OBJECT-TYPE
    SYNTAX      Counter32
    MAX-ACCESS  read-only
    STATUS      current
    DESCRIPTION
        "The value of the object eVxlanMldSnpgTxGenQueries indicates the number
         of MLD General Queries transmitted on this VXLAN."
    ::= { eVxlanMldSnpgStatsEntry 1 }

eVxlanMldSnpgTxGrpSpecQueries    OBJECT-TYPE
    SYNTAX      Counter32
    MAX-ACCESS  read-only
    STATUS      current
    DESCRIPTION
        "The value of the object eVxlanMldSnpgTxGrpSpecQueries indicates the
         number of MLD Group-Specific Queries transmitted on this VXLAN."
    ::= { eVxlanMldSnpgStatsEntry 2 }

eVxlanMldSnpgTxSrcSpecQueries    OBJECT-TYPE
    SYNTAX      Counter32
    MAX-ACCESS  read-only
    STATUS      current
    DESCRIPTION
        "The value of the object eVxlanMldSnpgTxSrcSpecQueries indicates the
         number of MLD Group-And-Source-Specific Queries transmitted on this
         VXLAN."
    ::= { eVxlanMldSnpgStatsEntry 3 }

eVxlanMldSnpgTxV1Reports         OBJECT-TYPE
    SYNTAX      Counter32
    MAX-ACCESS  read-only
    STATUS      current
    DESCRIPTION
        "The value of the object eVxlanMldSnpgTxV1Reports indicates the number
         of MLDv1 Reports transmitted on this VXLAN."
    ::= { eVxlanMldSnpgStatsEntry 4 }

eVxlanMldSnpgTxV2Reports         OBJECT-TYPE
    SYNTAX      Counter32
    MAX-ACCESS  read-only
    STATUS      current
    DESCRIPTION
        "The value of the object eVxlanMldSnpgTxV2Reports indicates the number
         of MLDv2 Reports transmitted on this VXLAN."
    ::= { eVxlanMldSnpgStatsEntry 5 }

eVxlanMldSnpgTxV1Leaves          OBJECT-TYPE
    SYNTAX      Counter32
    MAX-ACCESS  read-only
    STATUS      current
    DESCRIPTION
        "The value of the object eVxlanMldSnpgTxV1Leaves indicates the number
         of MLDv1 Leaves transmitted on this VXLAN."
    ::= { eVxlanMldSnpgStatsEntry 6 }

eVxlanMldSnpgRxGenQueries        OBJECT-TYPE
    SYNTAX      Counter32
    MAX-ACCESS  read-only
    STATUS      current
    DESCRIPTION
        "The value of the object eVxlanMldSnpgRxGenQueries indicates the number
         of MLD General Queries received on this VXLAN."
    ::= { eVxlanMldSnpgStatsEntry 7 }

eVxlanMldSnpgRxGrpSpecQueries    OBJECT-TYPE
    SYNTAX      Counter32
    MAX-ACCESS  read-only
    STATUS      current
    DESCRIPTION
        "The value of the object eVxlanMldSnpgRxGrpSpecQueries indicates the
         number of MLD Group-Specific Queries received on this VXLAN."
    ::= { eVxlanMldSnpgStatsEntry 8 }

eVxlanMldSnpgRxSrcSpecQueries    OBJECT-TYPE
    SYNTAX      Counter32
    MAX-ACCESS  read-only
    STATUS      current
    DESCRIPTION
        "The value of the object eVxlanMldSnpgRxSrcSpecQueries indicates the
         number of MLD Group-And-Source-Specific Queries received on this
         VXLAN."
    ::= { eVxlanMldSnpgStatsEntry 9 }

eVxlanMldSnpgRxV1Reports         OBJECT-TYPE
    SYNTAX      Counter32
    MAX-ACCESS  read-only
    STATUS      current
    DESCRIPTION
        "The value of the object eVxlanMldSnpgRxV1Reports indicates the number
         of MLDv1 Reports received on this VXLAN."
    ::= { eVxlanMldSnpgStatsEntry 10 }

eVxlanMldSnpgRxV2Reports         OBJECT-TYPE
    SYNTAX      Counter32
    MAX-ACCESS  read-only
    STATUS      current
    DESCRIPTION
        "The value of the object eVxlanMldSnpgRxV2Reports indicates the number
         of MLDv2 Reports received on this VXLAN."
    ::= { eVxlanMldSnpgStatsEntry 11 }

eVxlanMldSnpgRxV1Leaves          OBJECT-TYPE
    SYNTAX      Counter32
    MAX-ACCESS  read-only
    STATUS      current
    DESCRIPTION
        "The value of the object eVxlanMldSnpgRxV1Leaves indicates the number
         of MLDv1 Leaves received on this VXLAN."
    ::= { eVxlanMldSnpgStatsEntry 12 }

eVxlanMldSnpgRxUnknownType       OBJECT-TYPE
    SYNTAX      Counter32
    MAX-ACCESS  read-only
    STATUS      current
    DESCRIPTION
        "The value of the object eVxlanMldSnpgRxUnknownType indicates the
         number of MLD unknown type packets received on this VXLAN."
    ::= { eVxlanMldSnpgStatsEntry 13 }

eVxlanMldSnpgFwdGenQueries       OBJECT-TYPE
    SYNTAX      Counter32
    MAX-ACCESS  read-only
    STATUS      current
    DESCRIPTION
        "The value of the object eVxlanMldSnpgFwdGenQueries indicates the
         number of MLD General Queries forwarded on this VXLAN."
    ::= { eVxlanMldSnpgStatsEntry 14 }

eVxlanMldSnpgFwdGrpSpecQueries   OBJECT-TYPE
    SYNTAX      Counter32
    MAX-ACCESS  read-only
    STATUS      current
    DESCRIPTION
        "The value of the object eVxlanMldSnpgFwdGrpSpecQueries indicates the
         number of MLD Group-Specific Queries forwarded on this VXLAN."
    ::= { eVxlanMldSnpgStatsEntry 15 }

eVxlanMldSnpgFwdSrcSpecQueries   OBJECT-TYPE
    SYNTAX      Counter32
    MAX-ACCESS  read-only
    STATUS      current
    DESCRIPTION
        "The value of the object eVxlanMldSnpgFwdSrcSpecQueries indicates the
         number of MLD Group-And-Source-Specific Queries forwarded on this
         VXLAN."
    ::= { eVxlanMldSnpgStatsEntry 16 }

eVxlanMldSnpgFwdV1Reports        OBJECT-TYPE
    SYNTAX      Counter32
    MAX-ACCESS  read-only
    STATUS      current
    DESCRIPTION
        "The value of the object eVxlanMldSnpgFwdV1Reports indicates the number
         of MLDv1 Reports forwarded on this VXLAN."
    ::= { eVxlanMldSnpgStatsEntry 17 }

eVxlanMldSnpgFwdV2Reports        OBJECT-TYPE
    SYNTAX      Counter32
    MAX-ACCESS  read-only
    STATUS      current
    DESCRIPTION
        "The value of the object eVxlanMldSnpgFwdV2Reports indicates the number
         of MLDv2 Reports forwarded on this VXLAN."
    ::= { eVxlanMldSnpgStatsEntry 18 }

eVxlanMldSnpgFwdV1Leaves         OBJECT-TYPE
    SYNTAX      Counter32
    MAX-ACCESS  read-only
    STATUS      current
    DESCRIPTION
        "The value of the object eVxlanMldSnpgFwdV1Leaves indicates the number
         of MLDv1 Leaves forwarded on this VXLAN."
    ::= { eVxlanMldSnpgStatsEntry 19 }

eVxlanMldSnpgFwdUnknownType      OBJECT-TYPE
    SYNTAX      Counter32
    MAX-ACCESS  read-only
    STATUS      current
    DESCRIPTION
        "The value of the object eVxlanMldSnpgFwdUnknownType indicates the
         number of MLD unknown type packets forwarded on this VXLAN."
    ::= { eVxlanMldSnpgStatsEntry 20 }

eVxlanMldSnpgRxBadLenPkts        OBJECT-TYPE
    SYNTAX      Counter32
    MAX-ACCESS  read-only
    STATUS      current
    DESCRIPTION
        "The value of the object eVxlanMldSnpgRxBadLenPkts indicates the number
         of MLD packets dropped on this VXLAN because of a bad length."
    ::= { eVxlanMldSnpgStatsEntry 21 }

eVxlanMldSnpgRxBadMldChksmPkts   OBJECT-TYPE
    SYNTAX      Counter32
    MAX-ACCESS  read-only
    STATUS      current
    DESCRIPTION
        "The value of the object eVxlanMldSnpgRxBadMldChksmPkts indicates the
         number of dropped MLD packets on this VXLAN because of a bad MLD
         header checksum."
    ::= { eVxlanMldSnpgStatsEntry 22 }

eVxlanMldSnpgRxBadEncodedPkts    OBJECT-TYPE
    SYNTAX      Counter32
    MAX-ACCESS  read-only
    STATUS      current
    DESCRIPTION
        "The value of the object eVxlanMldSnpgRxBadEncodedPkts indicates the
         number of MLD packets dropped on this VXLAN because of a bad encoding."
    ::= { eVxlanMldSnpgStatsEntry 23 }

eVxlanMldSnpgRxNoRtrAlertPkts    OBJECT-TYPE
    SYNTAX      Counter32
    MAX-ACCESS  read-only
    STATUS      current
    DESCRIPTION
        "The value of the object eVxlanMldSnpgRxNoRtrAlertPkts indicates the
         number of MLD packets dropped on this VXLAN because the Router Alert
         Option in the IP packet is not set."
    ::= { eVxlanMldSnpgStatsEntry 24 }

eVxlanMldSnpgRxZeroSrcAdrPkts    OBJECT-TYPE
    SYNTAX      Counter32
    MAX-ACCESS  read-only
    STATUS      current
    DESCRIPTION
        "The value of the object eVxlanMldSnpgRxZeroSrcAdrPkts indicates the
         number of MLD packets dropped on this VXLAN because they contain a
         zero source IPv6 address."
    ::= { eVxlanMldSnpgStatsEntry 25 }

eVxlanMldSnpgSendQueryCfgDrops   OBJECT-TYPE
    SYNTAX      Counter32
    MAX-ACCESS  read-only
    STATUS      current
    DESCRIPTION
        "The value of the object eVxlanMldSnpgSendQueryCfgDrops indicates the
         number of times an MLD Query is dropped because the object
         sapMldSnpgCfgSendQueries for this VXLAN is set to 'enabled(1)'."
    ::= { eVxlanMldSnpgStatsEntry 26 }

eVxlanMldSnpgImportPolicyDrops   OBJECT-TYPE
    SYNTAX      Counter32
    MAX-ACCESS  read-only
    STATUS      current
    DESCRIPTION
        "The value of the object eVxlanMldSnpgImportPolicyDrops indicates the
         number of times an MLD Group or Source is dropped because of applying
         an import policy on this VXLAN."
    ::= { eVxlanMldSnpgStatsEntry 27 }

eVxlanMldSnpgMaxNumGroupsDrops   OBJECT-TYPE
    SYNTAX      Counter32
    MAX-ACCESS  read-only
    STATUS      current
    DESCRIPTION
        "The value of the object eVxlanMldSnpgMaxNumGroupsDrops indicates the
         number of times an MLD Group is dropped because of exceeding the
         configured maximum number of groups on this VXLAN."
    ::= { eVxlanMldSnpgStatsEntry 28 }

eVxlanMldSnpgRxWrongVersionPkts  OBJECT-TYPE
    SYNTAX      Counter32
    MAX-ACCESS  read-only
    STATUS      current
    DESCRIPTION
        "The value of the object eVxlanMldSnpgRxWrongVersionPkts indicates the
         total number of MLD packets with a wrong version received on this
         VXLAN."
    ::= { eVxlanMldSnpgStatsEntry 29 }

eVxlanMldSnpgRxLocalScopePkts    OBJECT-TYPE
    SYNTAX      Counter32
    MAX-ACCESS  read-only
    STATUS      current
    DESCRIPTION
        "The value of the object eVxlanMldSnpgRxLocalScopePkts indicates the
         number of MLD packets received on the link-local scope IPv6 multicast
         address."
    ::= { eVxlanMldSnpgStatsEntry 30 }

eVxlanMldSnpgRxRsvdScopePkts     OBJECT-TYPE
    SYNTAX      Counter32
    MAX-ACCESS  read-only
    STATUS      current
    DESCRIPTION
        "The value of the object eVxlanMldSnpgRxRsvdScopePkts indicates the
         number of MLD packets received on the reserved scope IPv6 multicast
         address."
    ::= { eVxlanMldSnpgStatsEntry 31 }

eVxlanMldSnpgMcacPolicyDrops     OBJECT-TYPE
    SYNTAX      Counter32
    MAX-ACCESS  read-only
    STATUS      current
    DESCRIPTION
        "The value of the object eVxlanMldSnpgMcacPolicyDrops indicates the
         number of times an MLD Group is dropped because of applying a
         multicast CAC policy on this VXLAN."
    ::= { eVxlanMldSnpgStatsEntry 32 }

tmnxMldSnoopingEMplsObjs         OBJECT IDENTIFIER ::= { tmnxMldSnoopingObjs 6 }

eMplsMldSnpgStatsTable           OBJECT-TYPE
    SYNTAX      SEQUENCE OF EMplsMldSnpgStatsEntry
    MAX-ACCESS  not-accessible
    STATUS      current
    DESCRIPTION
        "eMplsMldSnpgStatsTable contains statistics on MLD snooping per
         evpn-mpls."
    ::= { tmnxMldSnoopingEMplsObjs 3 }

eMplsMldSnpgStatsEntry           OBJECT-TYPE
    SYNTAX      EMplsMldSnpgStatsEntry
    MAX-ACCESS  not-accessible
    STATUS      current
    DESCRIPTION
        "eMplsMldSnpgStatsEntry is an entry in the eMplsMldSnpgStatsTable. Each
         entry contains MLD snooping statics for an evpn-mpls in a Tls."
    INDEX       { svcId }
    ::= { eMplsMldSnpgStatsTable 1 }

EMplsMldSnpgStatsEntry           ::= SEQUENCE
{
    eMplsMldSnpgTxGenQueries         Counter32,
    eMplsMldSnpgTxGrpSpecQueries     Counter32,
    eMplsMldSnpgTxSrcSpecQueries     Counter32,
    eMplsMldSnpgTxV1Reports          Counter32,
    eMplsMldSnpgTxV2Reports          Counter32,
    eMplsMldSnpgTxV1Leaves           Counter32,
    eMplsMldSnpgRxGenQueries         Counter32,
    eMplsMldSnpgRxGrpSpecQueries     Counter32,
    eMplsMldSnpgRxSrcSpecQueries     Counter32,
    eMplsMldSnpgRxV1Reports          Counter32,
    eMplsMldSnpgRxV2Reports          Counter32,
    eMplsMldSnpgRxV1Leaves           Counter32,
    eMplsMldSnpgRxUnknownType        Counter32,
    eMplsMldSnpgFwdGenQueries        Counter32,
    eMplsMldSnpgFwdGrpSpecQueries    Counter32,
    eMplsMldSnpgFwdSrcSpecQueries    Counter32,
    eMplsMldSnpgFwdV1Reports         Counter32,
    eMplsMldSnpgFwdV2Reports         Counter32,
    eMplsMldSnpgFwdV1Leaves          Counter32,
    eMplsMldSnpgFwdUnknownType       Counter32,
    eMplsMldSnpgRxBadLenPkts         Counter32,
    eMplsMldSnpgRxBadMldChksmPkts    Counter32,
    eMplsMldSnpgRxBadEncodedPkts     Counter32,
    eMplsMldSnpgRxNoRtrAlertPkts     Counter32,
    eMplsMldSnpgRxZeroSrcAdrPkts     Counter32,
    eMplsMldSnpgSendQueryCfgDrops    Counter32,
    eMplsMldSnpgImportPolicyDrops    Counter32,
    eMplsMldSnpgMaxNumGroupsDrops    Counter32,
    eMplsMldSnpgRxWrongVersionPkts   Counter32,
    eMplsMldSnpgRxLocalScopePkts     Counter32,
    eMplsMldSnpgRxRsvdScopePkts      Counter32,
    eMplsMldSnpgMcacPolicyDrops      Counter32
}

eMplsMldSnpgTxGenQueries         OBJECT-TYPE
    SYNTAX      Counter32
    MAX-ACCESS  read-only
    STATUS      current
    DESCRIPTION
        "The value of the object eMplsMldSnpgTxGenQueries indicates the number
         of MLD General Queries transmitted on this evpn-mpls."
    ::= { eMplsMldSnpgStatsEntry 1 }

eMplsMldSnpgTxGrpSpecQueries     OBJECT-TYPE
    SYNTAX      Counter32
    MAX-ACCESS  read-only
    STATUS      current
    DESCRIPTION
        "The value of the object eMplsMldSnpgTxGrpSpecQueries indicates the
         number of MLD Group-Specific Queries transmitted on this evpn-mpls."
    ::= { eMplsMldSnpgStatsEntry 2 }

eMplsMldSnpgTxSrcSpecQueries     OBJECT-TYPE
    SYNTAX      Counter32
    MAX-ACCESS  read-only
    STATUS      current
    DESCRIPTION
        "The value of the object eMplsMldSnpgTxSrcSpecQueries indicates the
         number of MLD Group-And-Source-Specific Queries transmitted on this
         evpn-mpls."
    ::= { eMplsMldSnpgStatsEntry 3 }

eMplsMldSnpgTxV1Reports          OBJECT-TYPE
    SYNTAX      Counter32
    MAX-ACCESS  read-only
    STATUS      current
    DESCRIPTION
        "The value of the object eMplsMldSnpgTxV1Reports indicates the number
         of MLDv1 Reports transmitted on this evpn-mpls."
    ::= { eMplsMldSnpgStatsEntry 4 }

eMplsMldSnpgTxV2Reports          OBJECT-TYPE
    SYNTAX      Counter32
    MAX-ACCESS  read-only
    STATUS      current
    DESCRIPTION
        "The value of the object eMplsMldSnpgTxV2Reports indicates the number
         of MLDv2 Reports transmitted on this evpn-mpls."
    ::= { eMplsMldSnpgStatsEntry 5 }

eMplsMldSnpgTxV1Leaves           OBJECT-TYPE
    SYNTAX      Counter32
    MAX-ACCESS  read-only
    STATUS      current
    DESCRIPTION
        "The value of the object eMplsMldSnpgTxV1Leaves indicates the number of
         MLDv1 Leaves transmitted on this evpn-mpls."
    ::= { eMplsMldSnpgStatsEntry 6 }

eMplsMldSnpgRxGenQueries         OBJECT-TYPE
    SYNTAX      Counter32
    MAX-ACCESS  read-only
    STATUS      current
    DESCRIPTION
        "The value of the object eMplsMldSnpgRxGenQueries indicates the number
         of MLD General Queries received on this evpn-mpls."
    ::= { eMplsMldSnpgStatsEntry 7 }

eMplsMldSnpgRxGrpSpecQueries     OBJECT-TYPE
    SYNTAX      Counter32
    MAX-ACCESS  read-only
    STATUS      current
    DESCRIPTION
        "The value of the object eMplsMldSnpgRxGrpSpecQueries indicates the
         number of MLD Group-Specific Queries received on this evpn-mpls."
    ::= { eMplsMldSnpgStatsEntry 8 }

eMplsMldSnpgRxSrcSpecQueries     OBJECT-TYPE
    SYNTAX      Counter32
    MAX-ACCESS  read-only
    STATUS      current
    DESCRIPTION
        "The value of the object eMplsMldSnpgRxSrcSpecQueries indicates the
         number of MLD Group-And-Source-Specific Queries received on this
         evpn-mpls."
    ::= { eMplsMldSnpgStatsEntry 9 }

eMplsMldSnpgRxV1Reports          OBJECT-TYPE
    SYNTAX      Counter32
    MAX-ACCESS  read-only
    STATUS      current
    DESCRIPTION
        "The value of the object eMplsMldSnpgRxV1Reports indicates the number
         of MLDv1 Reports received on this evpn-mpls."
    ::= { eMplsMldSnpgStatsEntry 10 }

eMplsMldSnpgRxV2Reports          OBJECT-TYPE
    SYNTAX      Counter32
    MAX-ACCESS  read-only
    STATUS      current
    DESCRIPTION
        "The value of the object eMplsMldSnpgRxV2Reports indicates the number
         of MLDv2 Reports received on this evpn-mpls."
    ::= { eMplsMldSnpgStatsEntry 11 }

eMplsMldSnpgRxV1Leaves           OBJECT-TYPE
    SYNTAX      Counter32
    MAX-ACCESS  read-only
    STATUS      current
    DESCRIPTION
        "The value of the object eMplsMldSnpgRxV1Leaves indicates the number of
         MLDv1 Leaves received on this evpn-mpls."
    ::= { eMplsMldSnpgStatsEntry 12 }

eMplsMldSnpgRxUnknownType        OBJECT-TYPE
    SYNTAX      Counter32
    MAX-ACCESS  read-only
    STATUS      current
    DESCRIPTION
        "The value of the object eMplsMldSnpgRxUnknownType indicates the number
         of MLD unknown type packets received on this evpn-mpls."
    ::= { eMplsMldSnpgStatsEntry 13 }

eMplsMldSnpgFwdGenQueries        OBJECT-TYPE
    SYNTAX      Counter32
    MAX-ACCESS  read-only
    STATUS      current
    DESCRIPTION
        "The value of the object eMplsMldSnpgFwdGenQueries indicates the number
         of MLD General Queries forwarded on this evpn-mpls."
    ::= { eMplsMldSnpgStatsEntry 14 }

eMplsMldSnpgFwdGrpSpecQueries    OBJECT-TYPE
    SYNTAX      Counter32
    MAX-ACCESS  read-only
    STATUS      current
    DESCRIPTION
        "The value of the object eMplsMldSnpgFwdGrpSpecQueries indicates the
         number of MLD Group-Specific Queries forwarded on this evpn-mpls."
    ::= { eMplsMldSnpgStatsEntry 15 }

eMplsMldSnpgFwdSrcSpecQueries    OBJECT-TYPE
    SYNTAX      Counter32
    MAX-ACCESS  read-only
    STATUS      current
    DESCRIPTION
        "The value of the object eMplsMldSnpgFwdSrcSpecQueries indicates the
         number of MLD Group-And-Source-Specific Queries forwarded on this
         evpn-mpls."
    ::= { eMplsMldSnpgStatsEntry 16 }

eMplsMldSnpgFwdV1Reports         OBJECT-TYPE
    SYNTAX      Counter32
    MAX-ACCESS  read-only
    STATUS      current
    DESCRIPTION
        "The value of the object eMplsMldSnpgFwdV1Reports indicates the number
         of MLDv1 Reports forwarded on this evpn-mpls."
    ::= { eMplsMldSnpgStatsEntry 17 }

eMplsMldSnpgFwdV2Reports         OBJECT-TYPE
    SYNTAX      Counter32
    MAX-ACCESS  read-only
    STATUS      current
    DESCRIPTION
        "The value of the object eMplsMldSnpgFwdV2Reports indicates the number
         of MLDv2 Reports forwarded on this evpn-mpls."
    ::= { eMplsMldSnpgStatsEntry 18 }

eMplsMldSnpgFwdV1Leaves          OBJECT-TYPE
    SYNTAX      Counter32
    MAX-ACCESS  read-only
    STATUS      current
    DESCRIPTION
        "The value of the object eMplsMldSnpgFwdV1Leaves indicates the number
         of MLDv1 Leaves forwarded on this evpn-mpls."
    ::= { eMplsMldSnpgStatsEntry 19 }

eMplsMldSnpgFwdUnknownType       OBJECT-TYPE
    SYNTAX      Counter32
    MAX-ACCESS  read-only
    STATUS      current
    DESCRIPTION
        "The value of the object eMplsMldSnpgFwdUnknownType indicates the
         number of MLD unknown type packets forwarded on this evpn-mpls."
    ::= { eMplsMldSnpgStatsEntry 20 }

eMplsMldSnpgRxBadLenPkts         OBJECT-TYPE
    SYNTAX      Counter32
    MAX-ACCESS  read-only
    STATUS      current
    DESCRIPTION
        "The value of the object eMplsMldSnpgRxBadLenPkts indicates the number
         of MLD packets dropped on this evpn-mpls because of a bad length."
    ::= { eMplsMldSnpgStatsEntry 21 }

eMplsMldSnpgRxBadMldChksmPkts    OBJECT-TYPE
    SYNTAX      Counter32
    MAX-ACCESS  read-only
    STATUS      current
    DESCRIPTION
        "The value of the object eMplsMldSnpgRxBadMldChksmPkts indicates the
         number of dropped MLD packets on this evpn-mpls because of a bad MLD
         header checksum."
    ::= { eMplsMldSnpgStatsEntry 22 }

eMplsMldSnpgRxBadEncodedPkts     OBJECT-TYPE
    SYNTAX      Counter32
    MAX-ACCESS  read-only
    STATUS      current
    DESCRIPTION
        "The value of the object eMplsMldSnpgRxBadEncodedPkts indicates the
         number of MLD packets dropped on this evpn-mpls because of a bad
         encoding."
    ::= { eMplsMldSnpgStatsEntry 23 }

eMplsMldSnpgRxNoRtrAlertPkts     OBJECT-TYPE
    SYNTAX      Counter32
    MAX-ACCESS  read-only
    STATUS      current
    DESCRIPTION
        "The value of the object eMplsMldSnpgRxNoRtrAlertPkts indicates the
         number of MLD packets dropped on this evpn-mpls because the Router
         Alert Option in the IP packet is not set."
    ::= { eMplsMldSnpgStatsEntry 24 }

eMplsMldSnpgRxZeroSrcAdrPkts     OBJECT-TYPE
    SYNTAX      Counter32
    MAX-ACCESS  read-only
    STATUS      current
    DESCRIPTION
        "The value of the object eMplsMldSnpgRxZeroSrcAdrPkts indicates the
         number of MLD packets dropped on this evpn-mpls because they contain a
         zero source IPv6 address."
    ::= { eMplsMldSnpgStatsEntry 25 }

eMplsMldSnpgSendQueryCfgDrops    OBJECT-TYPE
    SYNTAX      Counter32
    MAX-ACCESS  read-only
    STATUS      current
    DESCRIPTION
        "The value of the object eMplsMldSnpgSendQueryCfgDrops indicates the
         number of times an MLD Query is dropped because the object
         sapMldSnpgCfgSendQueries for this evpn-mpls is set to 'enabled(1)'."
    ::= { eMplsMldSnpgStatsEntry 26 }

eMplsMldSnpgImportPolicyDrops    OBJECT-TYPE
    SYNTAX      Counter32
    MAX-ACCESS  read-only
    STATUS      current
    DESCRIPTION
        "The value of the object eMplsMldSnpgImportPolicyDrops indicates the
         number of times an MLD Group or Source is dropped because of applying
         an import policy on this evpn-mpls."
    ::= { eMplsMldSnpgStatsEntry 27 }

eMplsMldSnpgMaxNumGroupsDrops    OBJECT-TYPE
    SYNTAX      Counter32
    MAX-ACCESS  read-only
    STATUS      current
    DESCRIPTION
        "The value of the object eMplsMldSnpgMaxNumGroupsDrops indicates the
         number of times an MLD Group is dropped because of exceeding the
         configured maximum number of groups on this evpn-mpls."
    ::= { eMplsMldSnpgStatsEntry 28 }

eMplsMldSnpgRxWrongVersionPkts   OBJECT-TYPE
    SYNTAX      Counter32
    MAX-ACCESS  read-only
    STATUS      current
    DESCRIPTION
        "The value of the object eMplsMldSnpgRxWrongVersionPkts indicates the
         total number of MLD packets with a wrong version received on this
         evpn-mpls."
    ::= { eMplsMldSnpgStatsEntry 29 }

eMplsMldSnpgRxLocalScopePkts     OBJECT-TYPE
    SYNTAX      Counter32
    MAX-ACCESS  read-only
    STATUS      current
    DESCRIPTION
        "The value of the object eMplsMldSnpgRxLocalScopePkts indicates the
         number of MLD packets received on the link-local scope IPv6 multicast
         address."
    ::= { eMplsMldSnpgStatsEntry 30 }

eMplsMldSnpgRxRsvdScopePkts      OBJECT-TYPE
    SYNTAX      Counter32
    MAX-ACCESS  read-only
    STATUS      current
    DESCRIPTION
        "The value of the object eMplsMldSnpgRxRsvdScopePkts indicates the
         number of MLD packets received on the reserved scope IPv6 multicast
         address."
    ::= { eMplsMldSnpgStatsEntry 31 }

eMplsMldSnpgMcacPolicyDrops      OBJECT-TYPE
    SYNTAX      Counter32
    MAX-ACCESS  read-only
    STATUS      current
    DESCRIPTION
        "The value of the object eMplsMldSnpgMcacPolicyDrops indicates the
         number of times an MLD Group is dropped because of applying a
         multicast CAC policy on this evpn-mpls."
    ::= { eMplsMldSnpgStatsEntry 32 }

eMplsTEPLblMldSnpgGroupTable     OBJECT-TYPE
    SYNTAX      SEQUENCE OF EMplsTEPLblMldSnpgGroupEntry
    MAX-ACCESS  not-accessible
    STATUS      current
    DESCRIPTION
        "eMplsTEPLblMldSnpgGroupTable together with the table
         eMplsTEPLblMldSnpgGrpSrcTable contains multicast group address
         information collected by MLD snooping for each BGP EVPN-MPLS TEP and
         egress label pair."
    ::= { tmnxMldSnoopingEMplsObjs 4 }

eMplsTEPLblMldSnpgGroupEntry     OBJECT-TYPE
    SYNTAX      EMplsTEPLblMldSnpgGroupEntry
    MAX-ACCESS  not-accessible
    STATUS      current
    DESCRIPTION
        "Each entry in this table indicates a multicast group address learned
         by MLD snooping on this BGP EVPN-MPLS TEP and egress label pair. If a
         Source list is present it is described in the corresponding entries of
         the eMplsTEPLblMldSnpgGrpSrcTable table."
    INDEX       {
        svcId,
        eMplsTEPLblTEPAddrType,
        eMplsTEPLblTEPAddress,
        eMplsTEPLblTEPLabel,
        eMplsTEPLblMldSnpgGrpAddressType,
        eMplsTEPLblMldSnpgGrpAddress
    }
    ::= { eMplsTEPLblMldSnpgGroupTable 1 }

EMplsTEPLblMldSnpgGroupEntry     ::= SEQUENCE
{
    eMplsTEPLblMldSnpgGrpAddressType InetAddressType,
    eMplsTEPLblMldSnpgGrpAddress     InetAddress,
    eMplsTEPLblMldSnpgGrpType        TmnxIgmpSnpgGroupType,
    eMplsTEPLblMldSnpgGrpFilterMode  TmnxIgmpGroupFilterMode,
    eMplsTEPLblMldSnpgGrpUpTime      TimeTicks,
    eMplsTEPLblMldSnpgGrpExpiryTime  Unsigned32,
    eMplsTEPLblMldSnpgGrpCompatMode  Unsigned32,
    eMplsTEPLblMldSnpgGrpV1ExpTime   Unsigned32
}

eMplsTEPLblMldSnpgGrpAddressType OBJECT-TYPE
    SYNTAX      InetAddressType
    MAX-ACCESS  not-accessible
    STATUS      current
    DESCRIPTION
        "The value of the object eMplsTEPLblMldSnpgGrpAddressType indicates the
         type of eMplsTEPLblMldSnpgGrpAddress."
    ::= { eMplsTEPLblMldSnpgGroupEntry 1 }

eMplsTEPLblMldSnpgGrpAddress     OBJECT-TYPE
    SYNTAX      InetAddress (SIZE (4|16))
    MAX-ACCESS  not-accessible
    STATUS      current
    DESCRIPTION
        "The value of the object eMplsTEPLblMldSnpgGrpAddress indicates the
         IPv6 multicast group address for which this entry contains
         information."
    ::= { eMplsTEPLblMldSnpgGroupEntry 2 }

eMplsTEPLblMldSnpgGrpType        OBJECT-TYPE
    SYNTAX      TmnxIgmpSnpgGroupType
    MAX-ACCESS  read-only
    STATUS      current
    DESCRIPTION
        "The value of the object eMplsTEPLblMldSnpgGrpType indicates whether
         this entry was learned dynamically or was statically configured."
    ::= { eMplsTEPLblMldSnpgGroupEntry 3 }

eMplsTEPLblMldSnpgGrpFilterMode  OBJECT-TYPE
    SYNTAX      TmnxIgmpGroupFilterMode
    MAX-ACCESS  read-only
    STATUS      current
    DESCRIPTION
        "The value of the object eMplsTEPLblMldSnpgGrpFilterMode indicates the
         filter-mode for this group."
    ::= { eMplsTEPLblMldSnpgGroupEntry 4 }

eMplsTEPLblMldSnpgGrpUpTime      OBJECT-TYPE
    SYNTAX      TimeTicks
    MAX-ACCESS  read-only
    STATUS      current
    DESCRIPTION
        "The value of the object eMplsTEPLblMldSnpgGrpUpTime indicates how long
         (in centiseconds) that the group address already exists in the
         database for this BGP EVPN-MPLS TEP and egress label pair."
    ::= { eMplsTEPLblMldSnpgGroupEntry 5 }

eMplsTEPLblMldSnpgGrpExpiryTime  OBJECT-TYPE
    SYNTAX      Unsigned32
    UNITS       "seconds"
    MAX-ACCESS  read-only
    STATUS      current
    DESCRIPTION
        "The value of the object eMplsTEPLblMldSnpgGrpExpiryTime indicates the
         amount of time remaining before this entry will be aged out."
    ::= { eMplsTEPLblMldSnpgGroupEntry 6 }

eMplsTEPLblMldSnpgGrpCompatMode  OBJECT-TYPE
    SYNTAX      Unsigned32
    MAX-ACCESS  read-only
    STATUS      current
    DESCRIPTION
        "The value of the object eMplsTEPLblMldSnpgGrpCompatMode indicates the
         MLD version applicable on this BGP EVPN-MPLS TEP and egress label pair
         for this multicast group address. This corresponds to the lowest
         version seen for this group address on this BGP EVPN-MPLS TEP and
         egress label pair."
    ::= { eMplsTEPLblMldSnpgGroupEntry 7 }

eMplsTEPLblMldSnpgGrpV1ExpTime   OBJECT-TYPE
    SYNTAX      Unsigned32
    UNITS       "seconds"
    MAX-ACCESS  read-only
    STATUS      current
    DESCRIPTION
        "The value of the object eMplsTEPLblMldSnpgGrpV1ExpTime indicates the
         time remaining until the system will assume that there are no longer
         any MLDv1 members on this BGP EVPN-MPLS TEP and egress label pair.

         Upon hearing any MLDv1 Membership Report, this value is reset to the
         group membership interval. While this time remaining is non-zero, the
         system ignores any MLDv2 'leave' messages for this group that it
         receives on this BGP EVPN-MPLS TEP and egress label pair."
    ::= { eMplsTEPLblMldSnpgGroupEntry 8 }

eMplsTEPLblMldSnpgGrpSrcTable    OBJECT-TYPE
    SYNTAX      SEQUENCE OF EMplsTEPLblMldSnpgGrpSrcEntry
    MAX-ACCESS  not-accessible
    STATUS      current
    DESCRIPTION
        "eMplsTEPLblMldSnpgGrpSrcTable lists the IPv4 multicast Sources
         corresponding to the IPv4 multicast groups listed in the
         eMplsTEPLblMldSnpgGroupTable."
    ::= { tmnxMldSnoopingEMplsObjs 5 }

eMplsTEPLblMldSnpgGrpSrcEntry    OBJECT-TYPE
    SYNTAX      EMplsTEPLblMldSnpgGrpSrcEntry
    MAX-ACCESS  not-accessible
    STATUS      current
    DESCRIPTION
        "An entry in the eMplsTEPLblMldSnpgGrpSrcTable. Each entry represents a
         Source address from which receivers are interested/not interested in
         receiving multicast traffic from."
    INDEX       {
        svcId,
        eMplsTEPLblTEPAddrType,
        eMplsTEPLblTEPAddress,
        eMplsTEPLblTEPLabel,
        eMplsTEPLblMldSnpgGrpAddressType,
        eMplsTEPLblMldSnpgGrpAddress,
        eMplsTEPLblMldSnpgGrpSrcAddrType,
        eMplsTEPLblMldSnpgGrpSrcAddr
    }
    ::= { eMplsTEPLblMldSnpgGrpSrcTable 1 }

EMplsTEPLblMldSnpgGrpSrcEntry    ::= SEQUENCE
{
    eMplsTEPLblMldSnpgGrpSrcAddrType InetAddressType,
    eMplsTEPLblMldSnpgGrpSrcAddr     InetAddress,
    eMplsTEPLblMldSnpgGrpSrcType     TmnxIgmpSnpgGroupType,
    eMplsTEPLblMldSnpgGrpSrcUpTime   TimeTicks,
    eMplsTEPLblMldSnpgGrpSrcExpTime  Unsigned32,
    eMplsTEPLblMldSnpgGrpSrcFwdOrBlk INTEGER
}

eMplsTEPLblMldSnpgGrpSrcAddrType OBJECT-TYPE
    SYNTAX      InetAddressType
    MAX-ACCESS  not-accessible
    STATUS      current
    DESCRIPTION
        "The value of the object eMplsTEPLblMldSnpgGrpSrcAddrType indicates the
         type of eMplsTEPLblMldSnpgGrpSrcAddr."
    ::= { eMplsTEPLblMldSnpgGrpSrcEntry 1 }

eMplsTEPLblMldSnpgGrpSrcAddr     OBJECT-TYPE
    SYNTAX      InetAddress (SIZE (4|16))
    MAX-ACCESS  not-accessible
    STATUS      current
    DESCRIPTION
        "The value of the object eMplsTEPLblMldSnpgGrpSrcAddr indicates the
         address of the Source sending multicast traffic to the group
         identified by eMplsTEPLblMldSnpgGrpAddress.

         If the value of eMplsTEPLblMldSnpgGrpFilterMode corresponding to this
         entry is 'include(1)', the receivers are interested in receiving
         traffic from this Source.

         If the value of eMplsTEPLblMldSnpgGrpFilterMode corresponding to this
         entry is 'exclude(2)', the receivers are not interested in receiving
         traffic from this Source."
    ::= { eMplsTEPLblMldSnpgGrpSrcEntry 2 }

eMplsTEPLblMldSnpgGrpSrcType     OBJECT-TYPE
    SYNTAX      TmnxIgmpSnpgGroupType
    MAX-ACCESS  read-only
    STATUS      current
    DESCRIPTION
        "The value of the object eMplsTEPLblMldSnpgGrpSrcType indicates how
         this entry was learned."
    ::= { eMplsTEPLblMldSnpgGrpSrcEntry 3 }

eMplsTEPLblMldSnpgGrpSrcUpTime   OBJECT-TYPE
    SYNTAX      TimeTicks
    MAX-ACCESS  read-only
    STATUS      current
    DESCRIPTION
        "The value of the object eMplsTEPLblMldSnpgGrpSrcUpTime indicates how
         long (in centiseconds) that the Source address already exists in the
         database for this SAP."
    ::= { eMplsTEPLblMldSnpgGrpSrcEntry 4 }

eMplsTEPLblMldSnpgGrpSrcExpTime  OBJECT-TYPE
    SYNTAX      Unsigned32
    UNITS       "seconds"
    MAX-ACCESS  read-only
    STATUS      current
    DESCRIPTION
        "The value of the object eMplsTEPLblMldSnpgGrpSrcExpTime indicates the
         minimum amount of time remaining before this entry will be aged out.

         If the value of eMplsTEPLblMldSnpgGrpSrcExpTime is non-zero and the
         value of eMplsTEPLblMldSnpgGrpFilterMode corresponding to this entry
         is 'include(1)', it means that there are currently one or more systems
         which desire to receive multicast traffic for this Source.

         If this timer expires and the value of eMplsTEPLblMldSnpgGrpFilterMode
         is 'include(1)', the system concludes that traffic from this
         particular Source is no longer desired on the attached network, and
         deletes this entry.

         If the value of eMplsTEPLblMldSnpgGrpSrcExpTime is non-zero and the
         filter-mode for the group is 'exclude(2)', it means that at least one
         system desires to receive multicast traffic from this source.

         If the value of eMplsTEPLblMldSnpgGrpSrcExpTime is zero and the
         filter-mode for the group is 'exclude(2)', it means that no system
         desires to receive multicast traffic from this Source."
    ::= { eMplsTEPLblMldSnpgGrpSrcEntry 5 }

eMplsTEPLblMldSnpgGrpSrcFwdOrBlk OBJECT-TYPE
    SYNTAX      INTEGER {
        forward (1),
        block   (2)
    }
    MAX-ACCESS  read-only
    STATUS      current
    DESCRIPTION
        "eMplsTEPLblMldSnpgGrpSrcFwdOrBlk indicates whether this entry is on
         the forward list or block list."
    ::= { eMplsTEPLblMldSnpgGrpSrcEntry 6 }

eMplsTEPLblMldSnpgStateTable     OBJECT-TYPE
    SYNTAX      SEQUENCE OF EMplsTEPLblMldSnpgStateEntry
    MAX-ACCESS  not-accessible
    STATUS      current
    DESCRIPTION
        "eMplsTEPLblMldSnpgStateTable contains statistics on MLD snooping for
         each BGP EVPN-MPLS TEP and egress label pair."
    ::= { tmnxMldSnoopingEMplsObjs 6 }

eMplsTEPLblMldSnpgStateEntry     OBJECT-TYPE
    SYNTAX      EMplsTEPLblMldSnpgStateEntry
    MAX-ACCESS  not-accessible
    STATUS      current
    DESCRIPTION
        "eMplsTEPLblMldSnpgStateEntry is an entry in the
         eMplsTEPLblMldSnpgStateTable. Each entry contains MLD snooping statics
         for a  BGP EVPN-MPLS TEP and egress label pair in a Tls."
    INDEX       {
        svcId,
        eMplsTEPLblTEPAddrType,
        eMplsTEPLblTEPAddress,
        eMplsTEPLblTEPLabel
    }
    ::= { eMplsTEPLblMldSnpgStateTable 1 }

EMplsTEPLblMldSnpgStateEntry     ::= SEQUENCE
{
    eMplsTEPLblMldSnpgOperState      TmnxOperState,
    eMplsTEPLblMldSnpgGroupCount     Unsigned32,
    eMplsTEPLblMldIsSbd              TruthValue,
    eMplsTEPLblMldRxSmetRoutes       Unsigned32,
    eMplsTEPLblMldDroppedSmetRoutes  Unsigned32,
    eMplsTEPLblMldOrigAddrType       InetAddressType,
    eMplsTEPLblMldOrigAddress        InetAddress,
    eMplsTEPLblMldEvpnProxySupport   TruthValue
}

eMplsTEPLblMldSnpgOperState      OBJECT-TYPE
    SYNTAX      TmnxOperState
    MAX-ACCESS  read-only
    STATUS      current
    DESCRIPTION
        "The value of the object eMplsTEPLblMldSnpgOperState indicates the
         current operating state of this BGP EVPN-MPLS TEP and egress label
         pair."
    ::= { eMplsTEPLblMldSnpgStateEntry 1 }

eMplsTEPLblMldSnpgGroupCount     OBJECT-TYPE
    SYNTAX      Unsigned32
    MAX-ACCESS  read-only
    STATUS      current
    DESCRIPTION
        "eMplsTEPLblMldSnpgGroupCount is the number of multicast groups which
         have been learned on this BGP EVPN-MPLS TEP and egress label pair."
    ::= { eMplsTEPLblMldSnpgStateEntry 2 }

eMplsTEPLblMldIsSbd              OBJECT-TYPE
    SYNTAX      TruthValue
    MAX-ACCESS  read-only
    STATUS      current
    DESCRIPTION
        "eMplsTEPLblMldIsSbd indicates whether this BGP EVPN-MPLS TEP and
         egress label pair is from a  supplementary broadcast domain."
    ::= { eMplsTEPLblMldSnpgStateEntry 3 }

eMplsTEPLblMldRxSmetRoutes       OBJECT-TYPE
    SYNTAX      Unsigned32
    MAX-ACCESS  read-only
    STATUS      current
    DESCRIPTION
        "eMplsTEPLblMldRxSmetRoutes is the number of received Smet routes on
         this BGP EVPN-MPLS TEP and egress label pair."
    ::= { eMplsTEPLblMldSnpgStateEntry 4 }

eMplsTEPLblMldDroppedSmetRoutes  OBJECT-TYPE
    SYNTAX      Unsigned32
    MAX-ACCESS  read-only
    STATUS      current
    DESCRIPTION
        "eMplsTEPLblMldDroppedSmetRoutes is the number of received Smet routes
         on this BGP EVPN-MPLS TEP and egress label pair."
    ::= { eMplsTEPLblMldSnpgStateEntry 5 }

eMplsTEPLblMldOrigAddrType       OBJECT-TYPE
    SYNTAX      InetAddressType
    MAX-ACCESS  read-only
    STATUS      current
    DESCRIPTION
        ""
    ::= { eMplsTEPLblMldSnpgStateEntry 6 }

eMplsTEPLblMldOrigAddress        OBJECT-TYPE
    SYNTAX      InetAddress (SIZE (4|16))
    MAX-ACCESS  read-only
    STATUS      current
    DESCRIPTION
        ""
    ::= { eMplsTEPLblMldSnpgStateEntry 7 }

eMplsTEPLblMldEvpnProxySupport   OBJECT-TYPE
    SYNTAX      TruthValue
    MAX-ACCESS  read-only
    STATUS      current
    DESCRIPTION
        "eMplsTEPLblMldEvpnProxySupport indicates whether Mld Proxy  is
         supported on this BGP EVPN-MPLS TEP and egress label pair."
    ::= { eMplsTEPLblMldSnpgStateEntry 8 }

tmnxMldSnoopingConformance       OBJECT IDENTIFIER ::= { tmnxSRConfs 45 }

tmnxMldSnoopingCompliances       OBJECT IDENTIFIER ::= { tmnxMldSnoopingConformance 1 }

tmnxMldSnoopingCompliance        MODULE-COMPLIANCE
    STATUS      current
    DESCRIPTION
        "The compliance statement for management of MLD Snooping on Nokia 7xxx
         SR series systems."
    MODULE
        MANDATORY-GROUPS {
            tmnxMldSnpgConfigGroup,
            tmnxMldSnpgQuerierGroup,
            tmnxMldSnpgProxyGroup,
            tmnxMldSnpgMRouterGroup,
            tmnxMldMvrGroup,
            tmnxMldSnpgGroup,
            tmnxMldSnpgStaticGroup,
            tmnxMldSnpgStatsGroup,
            tmnxMldSnpgNotifyGroup
        }
    ::= { tmnxMldSnoopingCompliances 1 }

tmnxMldSnoopingV8v0Compliance    MODULE-COMPLIANCE
    STATUS      obsolete
    DESCRIPTION
        "The compliance statement for management of MLD Snooping on Nokia 7xxx
         SR series systems."
    MODULE
        MANDATORY-GROUPS {
            tmnxMldSnpgConfigGroup,
            tmnxMldSnpgConfigV8v0Group,
            tmnxMldSnpgQuerierGroup,
            tmnxMldSnpgProxyGroup,
            tmnxMldSnpgMRouterGroup,
            tmnxMldMvrGroup,
            tmnxMldSnpgGroup,
            tmnxMldSnpgStaticGroup,
            tmnxMldSnpgStatsGroup,
            tmnxMldSnpgNotifyGroup
        }
    ::= { tmnxMldSnoopingCompliances 2 }

tmnxMldSnoopingV12v0Compliance   MODULE-COMPLIANCE
    STATUS      current
    DESCRIPTION
        "The compliance statement for management of MLD Snooping on Nokia 7xxx
         SR series systems."
    MODULE
        MANDATORY-GROUPS {
            tmnxMldSnpgConfigGroup,
            tmnxMldSnpgConfigV8v0Group,
            tmnxMldSnpgConfigV12v0Group,
            tmnxMldSnpgQuerierGroup,
            tmnxMldSnpgProxyGroup,
            tmnxMldSnpgMRouterGroup,
            tmnxMldMvrGroup,
            tmnxMldSnpgGroup,
            tmnxMldSnpgStaticGroup,
            tmnxMldSnpgStatsGroup,
            tmnxMldSnpgStatsV12v0Group,
            tmnxMldSnpgNotifyGroup
        }
    ::= { tmnxMldSnoopingCompliances 3 }

tmnxMldSnoopingV14v0Compliance   MODULE-COMPLIANCE
    STATUS      obsolete
    DESCRIPTION
        "The compliance statement for management of MLD Snooping on Nokia 7xxx
         SR release 14.0 series systems."
    MODULE
        MANDATORY-GROUPS {
            tmnxMldSnpgConfigGroup,
            tmnxMldSnpgConfigV8v0Group,
            tmnxMldSnpgConfigV12v0Group,
            tmnxMldSnpgConfigV14v0Group,
            tmnxMldSnpgQuerierGroup,
            tmnxMldSnpgProxyGroup,
            tmnxMldSnpgMRouterGroup,
            tmnxMldMvrGroup,
            tmnxMldSnpgGroup,
            tmnxMldSnpgStaticGroup,
            tmnxMldSnpgStatsGroup,
            tmnxMldSnpgStatsV12v0Group,
            tmnxMldSnpgNotifyGroup
        }
    ::= { tmnxMldSnoopingCompliances 4 }

tmnxMldSnoopingV16v0Compliance   MODULE-COMPLIANCE
    STATUS      current
    DESCRIPTION
        "The compliance statement for management of MLD Snooping on Nokia 7xxx
         SR release 16.0 series systems."
    MODULE
        MANDATORY-GROUPS {
            tmnxMldSnpgConfigGroup,
            tmnxMldSnpgConfigV8v0Group,
            tmnxMldSnpgConfigV12v0Group,
            tmnxMldSnpgConfigV14v0Group,
            tmnxMldSnpgConfigV16v0Group,
            tmnxMldSnpgQuerierGroup,
            tmnxMldSnpgProxyGroup,
            tmnxMldSnpgMRouterGroup,
            tmnxMldMvrGroup,
            tmnxMldSnpgGroup,
            tmnxMldSnpgV16v0Group,
            tmnxMldSnpgStaticGroup,
            tmnxMldSnpgStatsGroup,
            tmnxMldSnpgStatsV12v0Group,
            tmnxMldSnpgStatsV16v0Group,
            tmnxMldSnpgNotifyGroup
        }
    ::= { tmnxMldSnoopingCompliances 5 }

tmnxMldSnpgEMplsV19v0Compliance  MODULE-COMPLIANCE
    STATUS      current
    DESCRIPTION
        "The compliance statement for management of MLD Snooping on evpn-mpls
         on Nokia 7x50 SR series release 19.0 systems."
    MODULE
        MANDATORY-GROUPS {
            tmnxEMplsMldSnpgStatsV19v0Grp
        }
    ::= { tmnxMldSnoopingCompliances 6 }

tmnxMldSnoopingV19v0Compliance   MODULE-COMPLIANCE
    STATUS      current
    DESCRIPTION
        "The compliance statement for management of MLD Snooping on Nokia 7xxx
         SR release 19.0 series systems."
    MODULE
        MANDATORY-GROUPS {
            tmnxMldSnpgConfigGroup,
            tmnxMldSnpgConfigV8v0Group,
            tmnxMldSnpgConfigV12v0Group,
            tmnxMldSnpgConfigV14v0Group,
            tmnxMldSnpgConfigV16v0Group,
            tmnxMldSnpgQuerierGroup,
            tmnxMldSnpgProxyGroup,
            tmnxMldSnpgMRouterGroup,
            tmnxMldMvrGroup,
            tmnxMldSnpgGroup,
            tmnxMldSnpgV16v0Group,
            tmnxMldSnpgStaticGroup,
            tmnxMldSnpgStatsGroup,
            tmnxMldSnpgStatsV12v0Group,
            tmnxMldSnpgStatsV16v0Group,
            tmnxMldSnpgNotifyGroup,
            tmnxTlsMldSnpgConfigV19v0Group
        }
    ::= { tmnxMldSnoopingCompliances 7 }

tmnxMldSnoopingV20v0Compliance   MODULE-COMPLIANCE
    STATUS      current
    DESCRIPTION
        "The compliance statement for management of MLD Snooping on Nokia 7xxx
         SR release 20.0 series systems."
    MODULE
        MANDATORY-GROUPS {
            tmnxVxlanMldSnpgStateV20v0Grp,
            tmnxMldSnpgStatsV20v0Group,
            tmnxTlsMldSnpgConfigV20v0Group,
            tmnxEMplsMldSnpgStatsV20v0Grp,
            tmnxMldSnpgProxyV20v0Group,
            tmnxVxlanMldSnpgGroupV20v0Grp,
            tmnxVxlanMldSnpgStatsV20v0Grp
        }
    ::= { tmnxMldSnoopingCompliances 8 }

tmnxMldSnoopingGroups            OBJECT IDENTIFIER ::= { tmnxMldSnoopingConformance 2 }

tmnxMldSnpgConfigGroup           OBJECT-GROUP
    OBJECTS     {
        tlsMldSnpgConfigTableLastChange,
        tlsMldSnpgCfgLastChangeTime,
        tlsMldSnpgCfgAdminState,
        tlsMldSnpgCfgGenQueryIntvl,
        tlsMldSnpgCfgRobustCount,
        tlsMldSnpgCfgReportSrcAddrType,
        tlsMldSnpgCfgReportSrcAddr,
        tlsMldSnpgCfgQuerySrcAddrType,
        tlsMldSnpgCfgQuerySrcAddr,
        sapMldSnpgConfigTableLastChange,
        sapMldSnpgCfgLastChangeTime,
        sapMldSnpgCfgImportPlcy,
        sapMldSnpgCfgFastLeave,
        sapMldSnpgCfgMRouter,
        sapMldSnpgCfgSendQueries,
        sapMldSnpgCfgGenQueryIntvl,
        sapMldSnpgCfgQueryRespIntvl,
        sapMldSnpgCfgRobustCount,
        sapMldSnpgCfgLastMembIntvl,
        sapMldSnpgCfgMaxNbrGrps,
        sapMldSnpgCfgVersion,
        sdpBindMldSnpgConfigTableLastCh,
        sdpBndMldSnpgCfgLastChangeTime,
        sdpBndMldSnpgCfgImportPlcy,
        sdpBndMldSnpgCfgFastLeave,
        sdpBndMldSnpgCfgMRouter,
        sdpBndMldSnpgCfgSendQueries,
        sdpBndMldSnpgCfgGenQueryIntvl,
        sdpBndMldSnpgCfgQueryRespIntvl,
        sdpBndMldSnpgCfgRobustCount,
        sdpBndMldSnpgCfgLastMembIntvl,
        sdpBndMldSnpgCfgMaxNbrGrps,
        sdpBndMldSnpgCfgVersion
    }
    STATUS      current
    DESCRIPTION
        "The group of objects supporting management of MLD snooping on Nokia
         7xxx SR series systems."
    ::= { tmnxMldSnoopingGroups 1 }

tmnxMldSnpgQuerierGroup          OBJECT-GROUP
    OBJECTS     {
        tlsMldSnpgQuerierVersion,
        tlsMldSnpgQuerierAddressType,
        tlsMldSnpgQuerierAddress,
        tlsMldSnpgQuerierLocale,
        tlsMldSnpgQuerierPortId,
        tlsMldSnpgQuerierEncapValue,
        tlsMldSnpgQuerierSdpId,
        tlsMldSnpgQuerierVcId,
        tlsMldSnpgQuerierUpTime,
        tlsMldSnpgQuerierExpiryTime,
        tlsMldSnpgQuerierGenQueryIntvl,
        tlsMldSnpgQuerierGenRespIntvl,
        tlsMldSnpgQuerierRobustCount
    }
    STATUS      current
    DESCRIPTION
        "The group of objects that allow to monitor the MLD querier in the Tls
         service by the MLD snooping device on Nokia 7xxx SR series systems."
    ::= { tmnxMldSnoopingGroups 2 }

tmnxMldSnpgProxyGroup            OBJECT-GROUP
    OBJECTS     {
        tlsMldSnpgProxyGroupFilterMode,
        tlsMldSnpgProxyGroupUpTime,
        tlsMldSnpgProxyGrpSrcUpTime
    }
    STATUS      current
    DESCRIPTION
        "The group of objects that allow to monitor the MLD snooping
         information used to proxy report to the MRouter on Nokia 7xxx SR
         series systems."
    ::= { tmnxMldSnoopingGroups 3 }

tmnxMldSnpgMRouterGroup          OBJECT-GROUP
    OBJECTS     {
        tlsMldSnpgMRouterLocale,
        tlsMldSnpgMRouterPortId,
        tlsMldSnpgMRouterEncapValue,
        tlsMldSnpgMRouterSdpId,
        tlsMldSnpgMRouterVcId,
        tlsMldSnpgMRouterVersion,
        tlsMldSnpgMRouterExpiryTime,
        tlsMldSnpgMRouterUpTime,
        tlsMldSnpgMRouterGenQueryIntvl,
        tlsMldSnpgMRouterGenRespIntvl,
        tlsMldSnpgMRouterRobustCount
    }
    STATUS      current
    DESCRIPTION
        "The group of objects that allow to monitor the MLD multicast routers
         in the Tls service by the MLD snooping device on Nokia 7xxx SR series
         systems."
    ::= { tmnxMldSnoopingGroups 4 }

tmnxMldMvrGroup                  OBJECT-GROUP
    OBJECTS     {
        tlsMldSnpgCfgMvrAdminState,
        tlsMldSnpgCfgMvrDescription,
        tlsMldSnpgCfgMvrPolicy,
        sapMldSnpgCfgMvrFromVplsId,
        sapMldSnpgCfgMvrToSapPortId,
        sapMldSnpgCfgMvrToSapEncapVal,
        sapMldSnpgGrpMvrFromVplsId,
        sapMldSnpgGrpMvrToSapPortId,
        sapMldSnpgGrpMvrToSapEncapVal,
        sapMldSnpgMvrFromVplsCfgDrops,
        sapMldSnpgMvrToSapCfgDrops
    }
    STATUS      current
    DESCRIPTION
        "The group of objects supporting MVR on Nokia 7xxx SR series systems."
    ::= { tmnxMldSnoopingGroups 5 }

tmnxMldSnpgGroup                 OBJECT-GROUP
    OBJECTS     {
        sapMldSnpgGrpType,
        sapMldSnpgGrpFilterMode,
        sapMldSnpgGrpUpTime,
        sapMldSnpgGrpExpiryTime,
        sapMldSnpgGrpCompatMode,
        sapMldSnpgGrpV1HostExpTime,
        sapMldSnpgGrpSrcType,
        sapMldSnpgGrpSrcUpTime,
        sapMldSnpgGrpSrcExpiryTime,
        sdpBndMldSnpgGrpType,
        sdpBndMldSnpgGrpFilterMode,
        sdpBndMldSnpgGrpUpTime,
        sdpBndMldSnpgGrpExpiryTime,
        sdpBndMldSnpgGrpCompatMode,
        sdpBndMldSnpgGrpV1HostExpTime,
        sdpBndMldSnpgGrpSrcType,
        sdpBndMldSnpgGrpSrcUpTime,
        sdpBndMldSnpgGrpSrcExpiryTime
    }
    STATUS      current
    DESCRIPTION
        "The group of objects that allow to monitor the MLD snooping
         information on Nokia 7xxx SR series systems."
    ::= { tmnxMldSnoopingGroups 6 }

tmnxMldSnpgStaticGroup           OBJECT-GROUP
    OBJECTS     {
        sapMldSnpgStaticGrpSrcTableLstCh,
        sapMldSnpgStaticRowstatus,
        sapMldSnpgStaticLastChangeTime,
        sdpBindMldSnpgStatGrpSrcTblLstCh,
        sdpBndMldSnpgStaticRowstatus,
        sdpBndMldSnpgStaticLastChange
    }
    STATUS      current
    DESCRIPTION
        "The group of objects that allow to statically configure (S,G)
         memberships on a SAP on Nokia 7xxx SR series systems."
    ::= { tmnxMldSnoopingGroups 7 }

tmnxMldSnpgStatsGroup            OBJECT-GROUP
    OBJECTS     {
        sapMldSnpgTxGenQueries,
        sapMldSnpgTxGrpSpecQueries,
        sapMldSnpgTxSrcSpecQueries,
        sapMldSnpgTxV1Reports,
        sapMldSnpgTxV2Reports,
        sapMldSnpgTxV1Leaves,
        sapMldSnpgRxGenQueries,
        sapMldSnpgRxGrpSpecQueries,
        sapMldSnpgRxSrcSpecQueries,
        sapMldSnpgRxV1Reports,
        sapMldSnpgRxV2Reports,
        sapMldSnpgRxV1Leaves,
        sapMldSnpgRxUnknownType,
        sapMldSnpgFwdGenQueries,
        sapMldSnpgFwdGrpSpecQueries,
        sapMldSnpgFwdSrcSpecQueries,
        sapMldSnpgFwdV1Reports,
        sapMldSnpgFwdV2Reports,
        sapMldSnpgFwdV1Leaves,
        sapMldSnpgFwdUnknownType,
        sapMldSnpgRxBadLenPkts,
        sapMldSnpgRxBadMldChksmPkts,
        sapMldSnpgRxBadEncodedPkts,
        sapMldSnpgRxNoRtrAlertPkts,
        sapMldSnpgRxZeroSrcAdrPkts,
        sapMldSnpgSendQueryCfgDrops,
        sapMldSnpgImportPolicyDrops,
        sapMldSnpgMaxNumGroupsDrops,
        sapMldSnpgRxWrongVersionPkts,
        sapMldSnpgMcsFailures,
        sapMldSnpgRxLocalScopePkts,
        sapMldSnpgRxRsvdScopePkts,
        sdpBndMldSnpgTxGenQueries,
        sdpBndMldSnpgTxGrpSpecQueries,
        sdpBndMldSnpgTxSrcSpecQueries,
        sdpBndMldSnpgTxV1Reports,
        sdpBndMldSnpgTxV2Reports,
        sdpBndMldSnpgTxV1Leaves,
        sdpBndMldSnpgRxGenQueries,
        sdpBndMldSnpgRxGrpSpecQueries,
        sdpBndMldSnpgRxSrcSpecQueries,
        sdpBndMldSnpgRxV1Reports,
        sdpBndMldSnpgRxV2Reports,
        sdpBndMldSnpgRxV1Leaves,
        sdpBndMldSnpgRxUnknownType,
        sdpBndMldSnpgFwdGenQueries,
        sdpBndMldSnpgFwdGrpSpecQueries,
        sdpBndMldSnpgFwdSrcSpecQueries,
        sdpBndMldSnpgFwdV1Reports,
        sdpBndMldSnpgFwdV2Reports,
        sdpBndMldSnpgFwdV1Leaves,
        sdpBndMldSnpgFwdUnknownType,
        sdpBndMldSnpgRxBadLenPkts,
        sdpBndMldSnpgRxBadMldChksmPkts,
        sdpBndMldSnpgRxBadEncodedPkts,
        sdpBndMldSnpgRxNoRtrAlertPkts,
        sdpBndMldSnpgRxZeroSrcAdrPkts,
        sdpBndMldSnpgSendQueryCfgDrops,
        sdpBndMldSnpgImportPolicyDrops,
        sdpBndMldSnpgMaxNumGroupsDrops,
        sdpBndMldSnpgRxWrongVersionPkts,
        sdpBndMldSnpgRxLocalScopePkts,
        sdpBndMldSnpgRxRsvdScopePkts
    }
    STATUS      current
    DESCRIPTION
        "The group of objects that allow to view statistics for MLD snooping on
         Nokia 7xxx SR series systems."
    ::= { tmnxMldSnoopingGroups 8 }

tmnxMldSnpgNotifyObjsGroup       OBJECT-GROUP
    OBJECTS     {
        tmnxMldSnpgGroupAddressType,
        tmnxMldSnpgGroupAddress,
        tmnxMldSnpgMcsFailureReason
    }
    STATUS      current
    DESCRIPTION
        "The group of notification objects supporting MLD snooping on Nokia
         7xxx SR series systems."
    ::= { tmnxMldSnoopingGroups 9 }

tmnxMldSnpgNotifyGroup           NOTIFICATION-GROUP
    NOTIFICATIONS {
        sapMldSnpgGrpLimitExceeded,
        sapMldSnpgMcsFailure,
        sdpBndMldSnpgGrpLimitExceeded
    }
    STATUS      current
    DESCRIPTION
        "The group of notifications supporting MLD snooping on Nokia 7xxx SR
         series systems."
    ::= { tmnxMldSnoopingGroups 10 }

tmnxMldSnpgConfigV8v0Group       OBJECT-GROUP
    OBJECTS     {
        sdpBndMldSnpgCfgDisRtrAlertChk,
        sapMldSnpgCfgDisRtrAlertChk
    }
    STATUS      current
    DESCRIPTION
        "The group of objects supporting management of MLD snooping on release
         8.0 Nokia 7xxx SR series systems."
    ::= { tmnxMldSnoopingGroups 11 }

tmnxMldSnpgConfigV12v0Group      OBJECT-GROUP
    OBJECTS     {
        sdpBndMldSnpgCfgMcacPolicyName,
        sdpBndMldSnpgCfgMcacUnconstBW,
        sdpBndMldSnpgCfgMcacPrRsvMndBW,
        sdpBndMldSnpgCfgMcacinUseMndBw,
        sdpBndMldSnpgCfgMcacinUseOplBw,
        sdpBndMldSnpgCfgMcacAvailMndBw,
        sdpBndMldSnpgCfgMcacAvailOplBw,
        sdpBndMldSnpgCfgMcacValInTrans,
        sapMldSnpgCfgMcacPolicyName,
        sapMldSnpgCfgMcacUnconstBW,
        sapMldSnpgCfgMcacPrRsvMndBW,
        sapMldSnpgCfgMcacConstAdmSt,
        sapMldSnpgCfgMcacinUseMandBw,
        sapMldSnpgCfgMcacinUseOpnlBw,
        sapMldSnpgCfgMcacAvailMandBw,
        sapMldSnpgCfgMcacAvailOpnlBw,
        sapMldSnpgCfgMcacValInTrans,
        sapMldSnpgCfgMcacUseLagPortWt,
        sapMldSnpgCfgMcacLevelRowStat,
        sapMldSnpgCfgMcacLevelBW,
        sapMldSnpgCfgMcacLevelLastChngT,
        sapMldSnpgCfgMcacLagRowStat,
        sapMldSnpgCfgMcacLagLevel,
        sapMldSnpgCfgMcacLagLastChangeT
    }
    STATUS      current
    DESCRIPTION
        "The group of objects supporting management of MLD snooping on release
         12.0 Nokia 7xxx SR series systems."
    ::= { tmnxMldSnoopingGroups 12 }

tmnxMldSnpgStatsV12v0Group       OBJECT-GROUP
    OBJECTS     {
        sdpBndMldSnpgMcacPolicyDrops,
        sapMldSnpgMcacPolicyDrops
    }
    STATUS      current
    DESCRIPTION
        "The group of objects that allow to view statistics for MLD snooping on
         release 12.0 Nokia 7xxx SR series systems."
    ::= { tmnxMldSnoopingGroups 13 }

tmnxMldSnpgConfigV14v0Group      OBJECT-GROUP
    OBJECTS     {
        sapMldSnpgCfgMcacIfPolicyName,
        sdpBndMldSnpgCfgMcacIfPlcyName,
        tlsMldSnpgCfgFwdIpv6McastToInt,
        tlsMldSnpgCfgRvplsMrouter,
        tlsMldSnpgQuerierVRtrId,
        tlsMldSnpgQuerierIfIndex,
        tlsMldSnpgMRouterVRtrId,
        tlsMldSnpgMRouterIfIndex
    }
    STATUS      current
    DESCRIPTION
        "The group of objects supporting management of MLD snooping on release
         14.0 Nokia 7xxx SR series systems."
    ::= { tmnxMldSnoopingGroups 14 }

tmnxMldSnpgConfigV16v0Group      OBJECT-GROUP
    OBJECTS     {
        tlsMldSnpgQuerierVTEPAddr,
        tlsMldSnpgQuerierVNI,
        tlsMldSnpgMRouterVTEPAddr,
        tlsMldSnpgMRouterVNI
    }
    STATUS      current
    DESCRIPTION
        "The group of objects supporting management of MLD snooping on release
         16.0 Nokia 7xxx SR series systems."
    ::= { tmnxMldSnoopingGroups 15 }

tmnxMldSnpgV16v0Group            OBJECT-GROUP
    OBJECTS     {
        vxlanMldSnpgGrpType,
        vxlanMldSnpgGrpFilterMode,
        vxlanMldSnpgGrpUpTime,
        vxlanMldSnpgGrpExpiryTime,
        vxlanMldSnpgGrpCompatMode,
        vxlanMldSnpgGrpV1HostExpTime,
        vxlanMldSnpgGrpSrcType,
        vxlanMldSnpgGrpSrcUpTime,
        vxlanMldSnpgGrpSrcExpiryTime
    }
    STATUS      current
    DESCRIPTION
        "The group of objects that allow to monitor the MLD snooping on release
         16.0 Nokia 7xxx SR series systems."
    ::= { tmnxMldSnoopingGroups 16 }

tmnxMldSnpgStatsV16v0Group       OBJECT-GROUP
    OBJECTS     {
        vxlanMldSnpgTxGenQueries,
        vxlanMldSnpgTxGrpSpecQueries,
        vxlanMldSnpgTxSrcSpecQueries,
        vxlanMldSnpgTxV1Reports,
        vxlanMldSnpgTxV2Reports,
        vxlanMldSnpgTxV1Leaves,
        vxlanMldSnpgRxGenQueries,
        vxlanMldSnpgRxGrpSpecQueries,
        vxlanMldSnpgRxSrcSpecQueries,
        vxlanMldSnpgRxV1Reports,
        vxlanMldSnpgRxV2Reports,
        vxlanMldSnpgRxV1Leaves,
        vxlanMldSnpgRxUnknownType,
        vxlanMldSnpgFwdGenQueries,
        vxlanMldSnpgFwdGrpSpecQueries,
        vxlanMldSnpgFwdSrcSpecQueries,
        vxlanMldSnpgFwdV1Reports,
        vxlanMldSnpgFwdV2Reports,
        vxlanMldSnpgFwdV1Leaves,
        vxlanMldSnpgFwdUnknownType,
        vxlanMldSnpgRxBadLenPkts,
        vxlanMldSnpgRxBadMldChksmPkts,
        vxlanMldSnpgRxBadEncodedPkts,
        vxlanMldSnpgRxNoRtrAlertPkts,
        vxlanMldSnpgRxZeroSrcAdrPkts,
        vxlanMldSnpgSendQueryCfgDrops,
        vxlanMldSnpgImportPolicyDrops,
        vxlanMldSnpgMaxNumGroupsDrops,
        vxlanMldSnpgRxWrongVersionPkts,
        vxlanMldSnpgRxLocalScopePkts,
        vxlanMldSnpgRxRsvdScopePkts,
        vxlanMldSnpgMcacPolicyDrops,
        eMplsMldSnpgTxGenQueries,
        eMplsMldSnpgTxGrpSpecQueries,
        eMplsMldSnpgTxSrcSpecQueries,
        eMplsMldSnpgTxV1Reports,
        eMplsMldSnpgTxV2Reports,
        eMplsMldSnpgTxV1Leaves,
        eMplsMldSnpgRxGenQueries,
        eMplsMldSnpgRxGrpSpecQueries,
        eMplsMldSnpgRxSrcSpecQueries,
        eMplsMldSnpgRxV1Reports,
        eMplsMldSnpgRxV2Reports,
        eMplsMldSnpgRxV1Leaves,
        eMplsMldSnpgRxUnknownType,
        eMplsMldSnpgFwdGenQueries,
        eMplsMldSnpgFwdGrpSpecQueries,
        eMplsMldSnpgFwdSrcSpecQueries,
        eMplsMldSnpgFwdV1Reports,
        eMplsMldSnpgFwdV2Reports,
        eMplsMldSnpgFwdV1Leaves,
        eMplsMldSnpgFwdUnknownType,
        eMplsMldSnpgRxBadLenPkts,
        eMplsMldSnpgRxBadMldChksmPkts,
        eMplsMldSnpgRxBadEncodedPkts,
        eMplsMldSnpgRxNoRtrAlertPkts,
        eMplsMldSnpgRxZeroSrcAdrPkts,
        eMplsMldSnpgSendQueryCfgDrops,
        eMplsMldSnpgImportPolicyDrops,
        eMplsMldSnpgMaxNumGroupsDrops,
        eMplsMldSnpgRxWrongVersionPkts,
        eMplsMldSnpgRxLocalScopePkts,
        eMplsMldSnpgRxRsvdScopePkts,
        eMplsMldSnpgMcacPolicyDrops
    }
    STATUS      current
    DESCRIPTION
        "The group of objects that allow to view statistics for MLD snooping on
         release 16.0 Nokia 7xxx SR series systems."
    ::= { tmnxMldSnoopingGroups 17 }

tmnxEMplsMldSnpgStatsV19v0Grp    OBJECT-GROUP
    OBJECTS     {
        eMplsTEPLblMldSnpgGrpSrcType,
        eMplsTEPLblMldSnpgGrpSrcUpTime,
        eMplsTEPLblMldSnpgGrpType,
        eMplsTEPLblMldSnpgGrpUpTime,
        eMplsTEPLblMldSnpgGrpV1ExpTime,
        eMplsTEPLblMldSnpgGrpCompatMode,
        eMplsTEPLblMldSnpgGrpExpiryTime,
        eMplsTEPLblMldSnpgGrpFilterMode,
        eMplsTEPLblMldSnpgGrpSrcExpTime,
        eMplsTEPLblMldSnpgOperState,
        eMplsTEPLblMldSnpgGroupCount,
        eMplsTEPLblMldIsSbd,
        eMplsTEPLblMldRxSmetRoutes,
        eMplsTEPLblMldDroppedSmetRoutes,
        eMplsTEPLblMldOrigAddrType,
        eMplsTEPLblMldOrigAddress
    }
    STATUS      current
    DESCRIPTION
        "The group of objects that allow to view statistics for MLD snooping on
         an evpn-mpls on Nokia 7x50 SR series release 19.0 systems."
    ::= { tmnxMldSnoopingGroups 18 }

tmnxTlsMldSnpgConfigV19v0Group   OBJECT-GROUP
    OBJECTS     {
        tlsMldSnpgCfgTxSmetRoutes
    }
    STATUS      current
    DESCRIPTION
        "The group of objects supporting management of MLF-Snooping on TLS
         level on Nokia 7x50 SR release 19.0 series systems."
    ::= { tmnxMldSnoopingGroups 19 }

tmnxVxlanMldSnpgStateV20v0Grp    OBJECT-GROUP
    OBJECTS     {
        vxlanMldDroppedSmetRoutes,
        vxlanMldIsSbd,
        vxlanMldRxSmetRoutes,
        vxlanMldSnpgGroupCount,
        vxlanMldSnpgOperState,
        vxlanMldOrigAddrType,
        vxlanMldOrigAddress,
        vxlanMldEvpnProxySupport,
        vxlanMldSnpgGrpSrcFwdOrBlk
    }
    STATUS      current
    DESCRIPTION
        "The group of objects that allow to view statistics for MLD snooping on
         a VXLAN on Nokia 7x50 SR series release 20.0 systems."
    ::= { tmnxMldSnoopingGroups 20 }

tmnxMldSnpgStatsV20v0Group       OBJECT-GROUP
    OBJECTS     {
        sapMldSnpgRxJoinSyncRtes,
        sapMldSnpgDropJoinSyncRtes,
        sapMldSnpgTxJoinSyncRtes,
        sapMldSnpgRxLeaveSyncRtes,
        sapMldSnpgDropLeaveSyncRtes,
        sapMldSnpgTxLeaveSyncRtes,
        sapMldSnpgGrpSrcFwdOrBlk,
        sdpBndMldSnpgRxJoinSyncRtes,
        sdpBndMldSnpgDropJoinSyncRtes,
        sdpBndMldSnpgTxJoinSyncRtes,
        sdpBndMldSnpgRxLeaveSyncRtes,
        sdpBndMldSnpgDropLeaveSyncRtes,
        sdpBndMldSnpgTxLeaveSyncRtes,
        sdpBndMldSnpgGrpSrcFwdOrBlk
    }
    STATUS      current
    DESCRIPTION
        "The group of objects that allow to view statistics for MLD snooping on
         release 20.0 Nokia 7xxx SR series systems."
    ::= { tmnxMldSnoopingGroups 21 }

tmnxTlsMldSnpgConfigV20v0Group   OBJECT-GROUP
    OBJECTS     {
        tlsMldSnpgCfgEvpnProxy
    }
    STATUS      current
    DESCRIPTION
        "The group of objects supporting management of MLD-Snooping on TLS
         level on Nokia 7x50 SR release 20.0 series systems."
    ::= { tmnxMldSnoopingGroups 22 }

tmnxEMplsMldSnpgStatsV20v0Grp    OBJECT-GROUP
    OBJECTS     {
        eMplsTEPLblMldEvpnProxySupport,
        eMplsTEPLblMldSnpgGrpSrcFwdOrBlk
    }
    STATUS      current
    DESCRIPTION
        "The group of objects that allow to view statistics for MLD snooping on
         an evpn-mpls on Nokia 7x50 SR series release 20.0 systems."
    ::= { tmnxMldSnoopingGroups 23 }

tmnxMldSnpgProxyV20v0Group       OBJECT-GROUP
    OBJECTS     {
        tlsMldSnpgEvpnProxyGrpFilterMode,
        tlsMldSnpgEvpnProxyGrpUpTime,
        tlsMldSnpgEvpnProxyGrpSrcUpTime,
        tlsMldSnpgEvpnProxyGrpV1Support,
        tlsMldSnpgEvpnProxyGrpV2Support
    }
    STATUS      current
    DESCRIPTION
        "The group of objects that allow to monitor the MLD snooping
         information used to proxy report to Bgp IMET destinations on Nokia
         7xxx SR series systems."
    ::= { tmnxMldSnoopingGroups 24 }

tmnxVxlanMldSnpgGroupV20v0Grp    OBJECT-GROUP
    OBJECTS     {
        eVxlanMldSnpgGrpType,
        eVxlanMldSnpgGrpFilterMode,
        eVxlanMldSnpgGrpUpTime,
        eVxlanMldSnpgGrpExpiryTime,
        eVxlanMldSnpgGrpCompatMode,
        eVxlanMldSnpgGrpV1HostExpTime,
        eVxlanMldSnpgGrpSrcType,
        eVxlanMldSnpgGrpSrcUpTime,
        eVxlanMldSnpgGrpSrcExpiryTime,
        eVxlanMldSnpgGrpSrcFwdOrBlk
    }
    STATUS      current
    DESCRIPTION
        "The group of objects that allow to monitor the MLD snooping
         information that is collected for a given VXLAN on Nokia 7x50 SR
         series release 20.0 systems."
    ::= { tmnxMldSnoopingGroups 25 }

tmnxVxlanMldSnpgStatsV20v0Grp    OBJECT-GROUP
    OBJECTS     {
        eVxlanMldSnpgTxGenQueries,
        eVxlanMldSnpgTxGrpSpecQueries,
        eVxlanMldSnpgTxSrcSpecQueries,
        eVxlanMldSnpgTxV1Reports,
        eVxlanMldSnpgTxV2Reports,
        eVxlanMldSnpgTxV1Leaves,
        eVxlanMldSnpgRxGenQueries,
        eVxlanMldSnpgRxGrpSpecQueries,
        eVxlanMldSnpgRxSrcSpecQueries,
        eVxlanMldSnpgRxV1Reports,
        eVxlanMldSnpgRxV2Reports,
        eVxlanMldSnpgRxV1Leaves,
        eVxlanMldSnpgRxUnknownType,
        eVxlanMldSnpgFwdGenQueries,
        eVxlanMldSnpgFwdGrpSpecQueries,
        eVxlanMldSnpgFwdSrcSpecQueries,
        eVxlanMldSnpgFwdV1Reports,
        eVxlanMldSnpgFwdV2Reports,
        eVxlanMldSnpgFwdV1Leaves,
        eVxlanMldSnpgFwdUnknownType,
        eVxlanMldSnpgRxBadLenPkts,
        eVxlanMldSnpgRxBadMldChksmPkts,
        eVxlanMldSnpgRxBadEncodedPkts,
        eVxlanMldSnpgRxNoRtrAlertPkts,
        eVxlanMldSnpgRxZeroSrcAdrPkts,
        eVxlanMldSnpgSendQueryCfgDrops,
        eVxlanMldSnpgImportPolicyDrops,
        eVxlanMldSnpgMaxNumGroupsDrops,
        eVxlanMldSnpgRxWrongVersionPkts,
        eVxlanMldSnpgRxLocalScopePkts,
        eVxlanMldSnpgRxRsvdScopePkts,
        eVxlanMldSnpgMcacPolicyDrops
    }
    STATUS      current
    DESCRIPTION
        "The group of objects that allow to view statistics for MLD snooping on
         a VXLAN on Nokia 7x50 SR series release 20.0 systems."
    ::= { tmnxMldSnoopingGroups 26 }

tmnxMldSnoopingNotifyPrefix      OBJECT IDENTIFIER ::= { tmnxSRNotifyPrefix 45 }

tmnxMldSnoopingSapPrefix         OBJECT IDENTIFIER ::= { tmnxMldSnoopingNotifyPrefix 1 }

tmnxMldSnpgSapNotifications      OBJECT IDENTIFIER ::= { tmnxMldSnoopingSapPrefix 0 }

sapMldSnpgGrpLimitExceeded       NOTIFICATION-TYPE
    OBJECTS     {
        svcId,
        sapPortId,
        sapEncapValue,
        sapMldSnpgCfgMaxNbrGrps,
        tmnxMldSnpgGroupAddressType,
        tmnxMldSnpgGroupAddress
    }
    STATUS      current
    DESCRIPTION
        "The sapMldSnpgGrpLimitExceeded notification is generated when an MLD
         group is dropped on a given SAP because a user configurable upper
         limit, given by sapMldSnpgCfgMaxNbrGrps, is reached."
    ::= { tmnxMldSnpgSapNotifications 1 }

sapMldSnpgMcsFailure             NOTIFICATION-TYPE
    OBJECTS     {
        svcId,
        sapPortId,
        sapEncapValue,
        tmnxMldSnpgGroupAddressType,
        tmnxMldSnpgGroupAddress,
        tmnxMldSnpgMcsFailureReason
    }
    STATUS      current
    DESCRIPTION
        "The sapMldSnpgMcsFailure notification is generated when an MLD group
         on a given SAP could not be synced to the MCS (multi-chassis
         synchronization) database."
    ::= { tmnxMldSnpgSapNotifications 2 }

tmnxMldSnoopingSdpBndPrefix      OBJECT IDENTIFIER ::= { tmnxMldSnoopingNotifyPrefix 2 }

tmnxMldSnpgSdpBndNotifications   OBJECT IDENTIFIER ::= { tmnxMldSnoopingSdpBndPrefix 0 }

sdpBndMldSnpgGrpLimitExceeded    NOTIFICATION-TYPE
    OBJECTS     {
        svcId,
        sdpBindId,
        sdpBndMldSnpgCfgMaxNbrGrps,
        tmnxMldSnpgGroupAddressType,
        tmnxMldSnpgGroupAddress
    }
    STATUS      current
    DESCRIPTION
        "The sdpBndMldSnpgGrpLimitExceeded notification is generated when an
         MLD group is dropped on a given SDP bind because a user configurable
         upper limit, given by sdpBndMldSnpgCfgMaxNbrGrps, is reached."
    ::= { tmnxMldSnpgSdpBndNotifications 1 }

END
