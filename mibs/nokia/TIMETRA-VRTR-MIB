TIMETRA-VRTR-MIB DEFINITIONS ::= BEGIN

IMPORTS
    IANAipRouteProtocol
                                                         FROM IANA-RTPROTO-MIB
    InterfaceIndex, InterfaceIndexOrZero
                                                         FROM IF-MIB
    InetAddress, InetAddressIPv4,
    InetAddressIPv6, InetAddressIPv6z,
    InetAddressPrefixLength,
    InetAddressType,
    InetAutonomousSystemNumber
                                                         FROM INET-ADDRESS-MIB
    inetCidrRouteDest,
    inetCidrRouteDestType,
    inetCidrRouteEntry,
    inetCidrRouteNextHop,
    inetCidrRouteNextHopType,
    inetCidrRoutePfxLen,
    inetCidrRoutePolicy, inetCidrRouteProto,
    ipCidrRouteEntry
                                                         FROM IP-FORWARD-MIB
    ipNetToMediaEntry, ipNetToPhysicalEntry,
    ipv6RouterAdvertEntry
                                                         FROM IP-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    TimeTicks, Unsigned32
                                                         FROM SNMPv2-SMI
    DisplayString, MacAddress, RowStatus,
    TEXTUAL-CONVENTION, TestAndIncr,
    TimeInterval, TimeStamp, TruthValue
                                                         FROM SNMPv2-TC
    TmnxSlotNum, tmnxCardSlotNum,
    tmnxChassisIndex, tmnxFPNum
                                                         FROM TIMETRA-CHASSIS-MIB
    TDHCPFilterID, TFilterID,
    TIPvXFilterType
                                                         FROM TIMETRA-FILTER-MIB
    timetraSRMIBModules, tmnxSRConfs,
    tmnxSRNotifyPrefix, tmnxSRObjs
                                                         FROM TIMETRA-GLOBAL-MIB
    tmnxPortNotifyPortId, tmnxPortType
                                                         FROM TIMETRA-PORT-MIB
    sapEncapValue, sapPortId
                                                         FROM TIMETRA-SAP-MIB
    svcDhcpClientLease,
    svcDhcpLseStateNewChAddr,
    svcDhcpLseStateNewCiAddr
                                                         FROM TIMETRA-SERV-MIB
    ClassIndex, ClassIndexOrNone,
    DateAndTimeOrEmpty, Dot1PPriority,
    IpAddressPrefixLength, SdpBindId,
    TBgpSrv6UpaTriggerNextHop,
    TBgpUntaggedRouteType, TCIRRate,
    TCpmProtPolicyID, TDSCPValue,
    TDSCPValueOrNone, TFCNameOrEmpty,
    TFCType, TItemDescription,
    TItemLongDescription,
    TLNamedItemOrEmpty,
    TLPolicyNameOrExpOrEmpty, TNamedItem,
    TNamedItemOrEmpty, TNetworkPolicyID,
    TPIRRate, TPlcrBurstSizeBytes,
    TPlcyAcctPolicerId,
    TPolicyStatementNameOrEmpty,
    TPriorityOrUndefined,
    TQosQGrpInstanceIDorZero, TRateType,
    TResolveStatus, TSrv6RouteResolution,
    TXLPolicyNameOrExpOrEmpty,
    TmnxAddressAndPrefixAddress,
    TmnxAddressAndPrefixPrefix,
    TmnxAddressAndPrefixType,
    TmnxAdminState, TmnxAlgorithmId,
    TmnxAttrSetImport, TmnxBfdSessOperFlags,
    TmnxBfdSessProtocolState,
    TmnxBfdSessionProtocols,
    TmnxBfdTermination,
    TmnxBgpAutonomousSystem, TmnxCBFClasses,
    TmnxCreateOrigin, TmnxCustId,
    TmnxDHCP6MsgType, TmnxDPathDomainId,
    TmnxDataFormat, TmnxDhcpClientState,
    TmnxDhcpOptionType,
    TmnxDhcpServerDUIDTypeCode,
    TmnxDistCpuProtActionDuration,
    TmnxDistCpuProtProtocolId,
    TmnxDistCpuProtState,
    TmnxEnabledDisabled, TmnxEncapVal,
    TmnxFPNumber, TmnxFlexAlgoIdOrZero,
    TmnxIpv6AddressAndPrefixAddress,
    TmnxIpv6AddressAndPrefixPrefix,
    TmnxIsaBbGrpId, TmnxLagPerLinkHashClass,
    TmnxLagPerLinkHashWeight,
    TmnxLinkMapProfileIdOrZero,
    TmnxMplsLabelOrZero, TmnxMplsTpGlobalID,
    TmnxMplsTpNodeID, TmnxOperState,
    TmnxPortID, TmnxPwGlobalIdOrZero,
    TmnxQosRateHigh32, TmnxQosRateLow32,
    TmnxReasContextVal, TmnxRouteDistType,
    TmnxServId, TmnxStatus,
    TmnxTunnelGroupIdOrZero, TmnxTunnelID,
    TmnxTunnelType, TmnxTunnelTypeExt,
    TmnxUrpfCheckMode,
    TmnxVPNRouteDistinguisher, TmnxVRtrID,
    TmnxVRtrIDOrZero, TmnxVpnIpBackupFamily
                                                         FROM TIMETRA-TC-MIB
    ;

timetraVRtrMIBModule             MODULE-IDENTITY
    LAST-UPDATED "202502010000Z"
    ORGANIZATION "Nokia"
    CONTACT-INFO
        "Nokia SROS Support
         Web: http://www.nokia.com"
    DESCRIPTION
        "This document  is the SNMP MIB  module to manage and provision
         the  Nokia SROS device transport and virtual routers,
         their interfaces, and other related features.

         Copyright 2003-2025 Nokia. All rights reserved.
         Reproduction of  this document is authorized  on the condition
         that the foregoing copyright notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "202502010000Z"
    DESCRIPTION
        "Rev 25.0               01 Feb 2025 00:00
         25.0 release of the TIMETRA-VRTR-MIB."

    REVISION    "202402010000Z"
    DESCRIPTION
        "Rev 24.0               01 Feb 2024 00:00
         24.0 release of the TIMETRA-VRTR-MIB."

    REVISION    "202302010000Z"
    DESCRIPTION
        "Rev 23.0               01 Feb 2023 00:00
         23.0 release of the TIMETRA-VRTR-MIB."

    REVISION    "202202010000Z"
    DESCRIPTION
        "Rev 22.0               01 Feb 2022 00:00
         22.0 release of the TIMETRA-VRTR-MIB."

    REVISION    "202102010000Z"
    DESCRIPTION
        "Rev 21.0               01 Feb 2021 00:00
         21.0 release of the TIMETRA-VRTR-MIB."

    REVISION    "202002010000Z"
    DESCRIPTION
        "Rev 20.0               01 Feb 2020 00:00
         20.0 release of the TIMETRA-VRTR-MIB."

    REVISION    "201903010000Z"
    DESCRIPTION
        "Rev 19.0               01 Mar 2019 00:00
         19.0 release of the TIMETRA-VRTR-MIB."

    REVISION    "201703010000Z"
    DESCRIPTION
        "Rev 15.0               01 Mar 2017 00:00
         15.0 release of the TIMETRA-VRTR-MIB."

    REVISION    "201601010000Z"
    DESCRIPTION
        "Rev 14.0               01 Jan 2016 00:00
         14.0 release of the TIMETRA-VRTR-MIB."

    REVISION    "201501010000Z"
    DESCRIPTION
        "Rev 13.0               01 Jan 2015 00:00
         13.0 release of the TIMETRA-VRTR-MIB."

    REVISION    "201401010000Z"
    DESCRIPTION
        "Rev 12.0               01 Jan 2014 00:00
         12.0 release of the TIMETRA-VRTR-MIB."

    REVISION    "201102010000Z"
    DESCRIPTION
        "Rev 9.0                1 Feb 2011 00:00
         9.0 release of the TIMETRA-VRTR-MIB."

    REVISION    "200902280000Z"
    DESCRIPTION
        "Rev 7.0                28 Feb 2009 00:00
         7.0 release of the TIMETRA-VRTR-MIB."

    REVISION    "200807010000Z"
    DESCRIPTION
        "Rev 6.1                01 Jul 2008 00:00
         6.1 release of the TIMETRA-VRTR-MIB."

    REVISION    "200801010000Z"
    DESCRIPTION
        "Rev 6.0                01 Jan 2008 00:00
         6.0 release of the TIMETRA-VRTR-MIB."

    REVISION    "200701010000Z"
    DESCRIPTION
        "Rev 5.0                01 Jan 2007 00:00
         5.0 release of the TIMETRA-VRTR-MIB."

    REVISION    "200602280000Z"
    DESCRIPTION
        "Rev 4.0                28 Feb 2006 00:00
         4.0 release of the TIMETRA-VRTR-MIB."

    REVISION    "200508310000Z"
    DESCRIPTION
        "Rev 3.0                31 Aug 2005 00:00
         3.0 release of the TIMETRA-VRTR-MIB."

    REVISION    "200501240000Z"
    DESCRIPTION
        "Rev 2.1                24 Jan 2005 00:00
         2.1 release of the TIMETRA-VRTR-MIB."

    REVISION    "200401150000Z"
    DESCRIPTION
        "Rev 2.0                15 Jan 2004 00:00
         2.0 release of the TIMETRA-VRTR-MIB."

    REVISION    "200308150000Z"
    DESCRIPTION
        "Rev 1.2                15 Aug 2003 00:00
         1.2 release of the TIMETRA-VRTR-MIB."

    REVISION    "200301200000Z"
    DESCRIPTION
        "Rev 1.0                20 Jan 2003 00:00
         1.0 Release of the TIMETRA-VRTR-MIB."

    REVISION    "200008140000Z"
    DESCRIPTION
        "Rev 0.1                14 Aug 2000 00:00
         Initial version of the TIMETRA-VRTR-MIB."

    ::= { timetraSRMIBModules 3 }

TmnxVPNId                        ::= TEXTUAL-CONVENTION
    STATUS      current
    DESCRIPTION
        "The purpose of a VPN-ID is to identify a VPN.
         The global VPN Identifier format is:
            3-octet VPN Authority, organizationally unique ID followed by a
            4-octet VPN index identifying the VPN according to OUI."
    REFERENCE
        "RFC 2685, Fox & Gleeson, 'Virtual Private Networks Identifier',
         September 1999."
    SYNTAX      OCTET STRING (SIZE (0..7))

TmnxInetAddrState                ::= TEXTUAL-CONVENTION
    STATUS      current
    DESCRIPTION
        "The TmnxInetAddrState is the state of an ipv6 address."
    SYNTAX      INTEGER {
        unknown      (0),
        tentative    (1),
        duplicated   (2),
        inaccessible (3),
        deprecated   (4),
        preferred    (5)
    }

TDSCPAppId                       ::= TEXTUAL-CONVENTION
    STATUS      current
    DESCRIPTION
        "DSCP Application identifiers for protocols that generate control
         traffic on the the Nokia SROS router."
    SYNTAX      INTEGER {
        bgp               (1),
        cflowd            (2),
        dhcp              (3),
        dns               (4),
        ftp               (5),
        icmp              (6),
        igmp              (7),
        l2tp              (8),
        ldp               (9),
        mld               (10),
        msdp              (11),
        ndis              (12),
        ntp               (13),
        ospf              (14),
        pim               (15),
        radius            (16),
        rip               (17),
        rsvp              (18),
        snmp              (19),
        snmp-notification (20),
        srrp              (21),
        ssh               (22),
        syslog            (23),
        tacplus           (24),
        telnet            (25),
        tftp              (26),
        traceroute        (27),
        vrrp              (28),
        ptp               (29),
        igmp-reporter     (30),
        gtp               (31),
        sflow             (34),
        diameter          (35),
        pcep              (36),
        call-trace        (37),
        bmp               (38),
        grpc              (39),
        mtrace2           (40),
        http              (41),
        mpls-udp-return   (42),
        pfcp              (43),
        ibcp              (44),
        bfd               (45)
    }

TDot1pAppId                      ::= TEXTUAL-CONVENTION
    STATUS      current
    DESCRIPTION
        "IEEE 802.1p priority (Dot1p) Application identifiers for Layer-2
         protocols that generate control traffic on the the Nokia SROS router."
    SYNTAX      INTEGER {
        arp   (1),
        isis  (2),
        pppoe (3)
    }

TmnxVrtrSingleSfmOverloadState   ::= TEXTUAL-CONVENTION
    STATUS      current
    DESCRIPTION
        "The TmnxVrtrSingleSfmOverloadState data type is an enumerated integer
         that describes the values used to identify the IGP single-SFM-overload
         state (SFM:Switch-Fabric/Control Processor Module).
                 notApplicable   : the IGP overload reaction to the single-SFM
                                   condition is disabled;
                 normal          : the full system multicast capacity of a
                                   dual-SFM chassis is available;
                 overload        : only reduced system multicast capacity is
                                   available, and IGP protocols are in overload."
    SYNTAX      INTEGER {
        notApplicable (0),
        normal        (1),
        overload      (2)
    }

TmnxInetCidrNextHopType          ::= TEXTUAL-CONVENTION
    STATUS      current
    DESCRIPTION
        "The TmnxInetCidrNextHopType is the type of next hop for a route.
         regular     :  Next hop is an IPv4 destination address for an
                       IPv4 prefix or and IPv6 destination address for
                       and IPv6 prefix.
         tunneled    : Next hop refers to a IPv4 LDP/RSVP/GRE tunnel.
         sixOverMPLS : Next hop is a MPLS tunnel for IPv6 prefix.
         sixOverFour : Next hop is a IPv4 destination for IPv6 prefix.
         tunneledIpv6: Next hop refers to a IPv6 LDP tunnel."
    SYNTAX      INTEGER {
        regular      (1),
        tunneled     (2),
        sixOverMPLS  (3),
        sixOverFour  (4),
        tunneledIpv6 (5)
    }

TmnxInetCidrNextHopOwner         ::= TEXTUAL-CONVENTION
    STATUS      current
    DESCRIPTION
        "The TmnxInetCidrNextHopOwner is the owner of the next hop for a route.
         unknown       :  Next hop owner is unknown.
         rsvp          :  Next hop owner is RSVP.
         ldp           :  Next hop owner is LDP.
         ldpOverRsvp   :  Next hop owner is LDP over RSVP.
         bgp           :  Next hop owner is BGP.
         srOspf        :  Next hop owner is SR-OSPF.
         srIsis        :  Next hop owner is SR-ISIS.
         srTe          :  Next hop owner is SR-TE.
         udp           :  Next hop owner is UDP.
         srBgp         :  Next hop owner is BGP-SR TE.
         mplsFwdPolicy :  Next hop owner is MPLS-Fwd-Policy.
         srPolicy      :  Next hop owner is SR-POLICY.
         ribApi        :  Next hop owner is RIB-API.
         srv6          :  Next hop owner is SRV6.
         srv6Isis      :  Next hop owner is SRV6-ISIS.
         srv6Policy    :  Next hop owner is SRV6-POLICY.
         video         :  Next hop owner is VIDEO.
         esmbcast      :  Next hop owner is ESMBCAST.
         vxlan         :  Next hop owner is VXLAN."
    SYNTAX      INTEGER {
        unknown       (0),
        rsvp          (1),
        ldp           (2),
        ldpOverRsvp   (3),
        bgp           (4),
        srOspf        (5),
        srIsis        (6),
        srTe          (7),
        udp           (8),
        srBgp         (9),
        srOspfV3      (10),
        mplsFwdPolicy (11),
        srPolicy      (12),
        ribApi        (13),
        srv6          (14),
        srv6Isis      (15),
        srv6Policy    (16),
        video         (17),
        esmbcast      (18),
        vxlan         (19),
        reserved20    (20)
    }

TmnxL3RouteOwner                 ::= TEXTUAL-CONVENTION
    STATUS      current
    DESCRIPTION
        "The TmnxL3RouteOwner is the owner of the next hop for a Layer 3 route."
    SYNTAX      INTEGER {
        unknown (0),
        local   (1),
        host    (2),
        static  (5),
        bgp     (16)
    }

TmnxRouteOperFlags               ::= TEXTUAL-CONVENTION
    STATUS      current
    DESCRIPTION
        "The value of TmnxRouteOperFlags specifies the different properties on
         the route."
    SYNTAX      BITS {
        stickyFlag (0)
    }

VRtrVprnTTLPropagateType         ::= TEXTUAL-CONVENTION
    STATUS      current
    DESCRIPTION
        "The value of VRtrVprnTTLPropagateType specifies whether or not to
         enable the propagation of time to live (TTL) at Ingress LER from the
         header of IP packet into all labels in the stack.

         When the value is set to 'none' the IP TTL propagation is disabled
         from the IP header to all labels in the stack including the VC label.

         When the value is set to 'all' the IP TTL is propagated from the
         header of IP packet into all labels in the stack.

         When the value is set to 'vcOnly' the IP TTL is propagated from the IP
         header into the VC label but not the transport labels in the stack.

         When the value is set to 'inherit', the VPRN instance inherits the
         base router instance configuration."
    SYNTAX      INTEGER {
        none    (0),
        all     (1),
        vcOnly  (2),
        inherit (3)
    }

VRtrTTLPropagateType             ::= TEXTUAL-CONVENTION
    STATUS      current
    DESCRIPTION
        "The value of VRtrTTLPropagateType specifies whether or not to enable
         the propagation of time to live (TTL) from the header of IP packet
         into all labels in the stack.

         When the value is set to 'none' the IP TTL propagation is disabled
         from the IP header to all labels in the stack.

         When the value is set to 'all' the IP TTL is propagated from the
         header of IP packet into all labels in the stack."
    SYNTAX      INTEGER {
        none (0),
        all  (1)
    }

TmnxSendCgaModifier              ::= TEXTUAL-CONVENTION
    DISPLAY-HINT "1x:"
    STATUS      current
    DESCRIPTION
        "The TmnxSendCgaModifier textual convention represents a 16-octets
         string used as modifier while generating Cryptographically Generated
         Addresses (CGA)."
    SYNTAX      OCTET STRING (SIZE (16))

TmnxEmbFlowspecFltrMaxSize       ::= TEXTUAL-CONVENTION
    STATUS      current
    DESCRIPTION
        "The value of TmnxEmbFlowspecFltrMaxSize specifies the maximum number
         of entries reserved for an auto-created IP or IPv6 embedded filter for
         flowspec rules on a given virtual router."
    SYNTAX      Unsigned32 (0..262143)

TmnxInetAddrTypeWithMcast        ::= TEXTUAL-CONVENTION
    STATUS      current
    DESCRIPTION
        "The TmnxInetAddrTypeWithMcast represents a type of Internet address.

         It extends the standard InetAddressType with the values of 'ipv4Mcast
         (128)' and 'ipv6Mcast (129)' that indicate IPv4/IPv6 addresses used
         for multicast extensions."
    SYNTAX      INTEGER {
        unknown   (0),
        ipv4      (1),
        ipv6      (2),
        ipv4z     (3),
        ipv6z     (4),
        dns       (16),
        ipv4Mcast (128),
        ipv6Mcast (129)
    }

TmnxVrtrNeid                     ::= TEXTUAL-CONVENTION
    DISPLAY-HINT "1x:"
    STATUS      current
    DESCRIPTION
        "The textual convention TmnxVrtrNeid represents the  Network Element
         Identifier."
    SYNTAX      OCTET STRING (SIZE (4))

VrtrMplsTunnelMode               ::= TEXTUAL-CONVENTION
    STATUS      current
    DESCRIPTION
        "The value of VrtrMplsTunnelMode specifies MPLS tunnel mode."
    SYNTAX      INTEGER {
        uniform (0),
        pipe    (1)
    }

VrtrIpTunnelOperState            ::= TEXTUAL-CONVENTION
    STATUS      current
    DESCRIPTION
        "The VrtrIpTunnelOperState data type is an enumerated integer that
         describes the values used to identify the current operational state of
         IP Tunnel functional modules."
    SYNTAX      INTEGER {
        unknown      (1),
        inService    (2),
        outOfService (3)
    }

tmnxVRtrObjs                     OBJECT IDENTIFIER ::= { tmnxSRObjs 3 }

vRtrConfTable                    OBJECT-TYPE
    SYNTAX      SEQUENCE OF VRtrConfEntry
    MAX-ACCESS  not-accessible
    STATUS      current
    DESCRIPTION
        "The vRtrConfTable has an entry for each virtual router configured in
         the system."
    ::= { tmnxVRtrObjs 1 }

vRtrConfEntry                    OBJECT-TYPE
    SYNTAX      VRtrConfEntry
    MAX-ACCESS  not-accessible
    STATUS      current
    DESCRIPTION
        "Each row entry represents a virtual router in the system. Entries can
         be created and deleted via SNMP SET operations.  Creation requires a
         SET request containing vRtrRowStatus, vRtrName and vRtrType.
         Note that rows in this table are usually created by the agent itself
         as a side affect of some other configuration; for example, when a
         service vprn is created by setting the appropriate objects in the
         TIMETRA-SERV-MIB.

         There will always be at least two row entries in this table, one of
         these entries represents the base or transport router and the other
         represents the management router.  These entries are created when the
         system is initialized and can never be deleted."
    INDEX       { vRtrID }
    ::= { vRtrConfTable 1 }

VRtrConfEntry                    ::= SEQUENCE
{
    vRtrID                           TmnxVRtrID,
    vRtrRowStatus                    RowStatus,
    vRtrAdminState                   TmnxAdminState,
    vRtrName                         TNamedItemOrEmpty,
    vRtrMaxNumRoutes                 Integer32,
    vRtrBgpStatus                    TmnxStatus,
    vRtrMplsStatus                   TmnxStatus,
    vRtrOspfStatus                   TmnxStatus,
    vRtrRipStatus                    TmnxStatus,
    vRtrRsvpStatus                   TmnxStatus,
    vRtrEcmpMaxRoutes                Unsigned32,
    vRtrAS                           TmnxBgpAutonomousSystem,
    vRtrNewIfIndex                   TestAndIncr,
    vRtrLdpStatus                    TmnxStatus,
    vRtrIsIsStatus                   TmnxStatus,
    vRtrRouterId                     IpAddress,
    vRtrTriggeredPolicy              TruthValue,
    vRtrConfederationAS              TmnxBgpAutonomousSystem,
    vRtrRouteDistinguisher           TmnxVPNRouteDistinguisher,
    vRtrMidRouteThreshold            Unsigned32,
    vRtrHighRouteThreshold           Unsigned32,
    vRtrIllegalLabelThreshold        Unsigned32,
    vRtrVpnId                        TmnxVPNId,
    vRtrDescription                  TItemDescription,
    vRtrGracefulRestart              TruthValue,
    vRtrGracefulRestartType          INTEGER,
    vRtrType                         INTEGER,
    vRtrServiceId                    TmnxServId,
    vRtrCustId                       TmnxCustId,
    vRtrIgmpStatus                   TmnxStatus,
    vRtrMaxNumRoutesLogOnly          TruthValue,
    vRtrVrfTarget                    TNamedItemOrEmpty,
    vRtrVrfExportTarget              TNamedItemOrEmpty,
    vRtrVrfImportTarget              TNamedItemOrEmpty,
    vRtrPimStatus                    TmnxStatus,
    vRtrMaxMcastNumRoutes            Integer32,
    vRtrMaxMcastNumRoutesLogOnly     TruthValue,
    vRtrMcastMidRouteThreshold       Unsigned32,
    vRtrIgnoreIcmpRedirect           TruthValue,
    vRtrOspfv3Status                 TmnxStatus,
    vRtrMsdpStatus                   TmnxStatus,
    vRtrVprnType                     INTEGER,
    vRtrSecondaryVrfId               TmnxVRtrIDOrZero,
    vRtrMldStatus                    TmnxStatus,
    vRtrIPv6MaxNumRoutes             Integer32,
    vRtrIPv6MidRouteThreshold        Unsigned32,
    vRtrIPv6HighRouteThreshold       Unsigned32,
    vRtrIPv6MaxNumRoutesLogOnly      TruthValue,
    vRtrIPv6IgnoreIcmpRedirect       TruthValue,
    vRtrMcPathMgmtPlcyName           TNamedItem,
    vRtrIgnoreNextHopMetric          TruthValue,
    vRtrMvpnVrfTarget                TNamedItemOrEmpty,
    vRtrMvpnVrfExportTarget          TNamedItemOrEmpty,
    vRtrMvpnVrfImportTarget          TNamedItemOrEmpty,
    vRtrMvpnVrfTargetUnicast         TruthValue,
    vRtrMvpnVrfExportTargetUnicast   TruthValue,
    vRtrMvpnVrfImportTargetUnicast   TruthValue,
    vRtrAS4Byte                      InetAutonomousSystemNumber,
    vRtrConfederationAS4Byte         InetAutonomousSystemNumber,
    vRtrMvpnCMcastImportRT           TNamedItemOrEmpty,
    vRtrInterASMvpn                  TruthValue,
    vRtrRipNgStatus                  TmnxStatus
}

vRtrID                           OBJECT-TYPE
    SYNTAX      TmnxVRtrID
    MAX-ACCESS  accessible-for-notify
    STATUS      current
    DESCRIPTION
        "The  unique value which identifies this virtual router in the Tmnx
         system.  The  vRtrID  value  for  each  virtual router must remain
         constant  at least   from  one  re-initialization  of  the  system
         management  processor  (CPM)  to the next. There will always be at
         least  one  router  entry defined by the agent with vRtrID=1 which
         represents the transport router."
    ::= { vRtrConfEntry 1 }

vRtrRowStatus                    OBJECT-TYPE
    SYNTAX      RowStatus
    MAX-ACCESS  read-create
    STATUS      current
    DESCRIPTION
        "The row status. The creation or deletion of a virtual router entry
         causes creation or deletion of corresponding entries in other Tmnx MIB
         tables with the same vRtrID value. Note that it is not allowed to
         'destroy' the row entry for vRtrID = 1.

         In  order  for  row  creation  to succeed, values for vRtrName and
         vRtrType   must   be   included  in  the  same  SNMP  SET  PDU  as
         vRtrRowStatus."
    ::= { vRtrConfEntry 2 }

vRtrAdminState                   OBJECT-TYPE
    SYNTAX      TmnxAdminState
    MAX-ACCESS  read-create
    STATUS      current
    DESCRIPTION
        "The desired administrative state for this virtual router. Note that it
         is not allowed to set vRtrAdminState to 'outOfService for the row
         entry with vRtrID = 1."
    DEFVAL      { outOfService }
    ::= { vRtrConfEntry 3 }

vRtrName                         OBJECT-TYPE
    SYNTAX      TNamedItemOrEmpty
    MAX-ACCESS  read-create
    STATUS      current
    DESCRIPTION
        "The administrative name for this virtual router. The router name must
         be unique among all virtual routers in the system.

         For row creation to succeed a value must be specified for vRtrName.

         When a row is created in the vRtrConfTable for a service vprn (i.e.
         when vRtrType is set to 'vprn'), the agent automatically assigns the
         name 'vprn<service-id>'."
    ::= { vRtrConfEntry 4 }

vRtrMaxNumRoutes                 OBJECT-TYPE
    SYNTAX      Integer32 (-1 | 1..2147483647)
    MAX-ACCESS  read-create
    STATUS      current
    DESCRIPTION
        "The maximum number of routes that can be configured on
         this virtual router.  If the value is -1, then there
         is no limit."
    DEFVAL      { -1 }
    ::= { vRtrConfEntry 5 }

vRtrBgpStatus                    OBJECT-TYPE
    SYNTAX      TmnxStatus
    MAX-ACCESS  read-create
    STATUS      current
    DESCRIPTION
        "The desired state for BGP on this virtual router.  An attempt
         to set vRtrBgpStatus to 'delete' will fail if the BGP protocol
         is not in the administrative outOfService state."
    DEFVAL      { delete }
    ::= { vRtrConfEntry 6 }

vRtrMplsStatus                   OBJECT-TYPE
    SYNTAX      TmnxStatus
    MAX-ACCESS  read-create
    STATUS      current
    DESCRIPTION
        "The desired state for MPLS on this virtual router.  An attempt
         to set vRtrMplsStatus to 'delete' will fail if the MPLS
         protocol is not in the administrative outOfService state,
         i.e. TIMETRA-MPLS-MIB::vRtrMplsGeneralAdminState must be
         set to 'outOfService'."
    DEFVAL      { delete }
    ::= { vRtrConfEntry 7 }

vRtrOspfStatus                   OBJECT-TYPE
    SYNTAX      TmnxStatus
    MAX-ACCESS  read-create
    STATUS      obsolete
    DESCRIPTION
        "The desired state for OSPFv2 on this virtual router.  An attempt
         to set vRtrOspfStatus to 'delete' will fail if the OSPFv2
         protocol is not in the administrative outOfService state,
         i.e. TIMETRA-OSPF-NG-MIB::tmnxOspfAdminState must be set
         to 'disabled'.

         This object was obsoleted in release 5.0."
    DEFVAL      { delete }
    ::= { vRtrConfEntry 8 }

vRtrRipStatus                    OBJECT-TYPE
    SYNTAX      TmnxStatus
    MAX-ACCESS  read-create
    STATUS      current
    DESCRIPTION
        "The desired state for RIP on this virtual router.  An attempt
         to set vRtrRipStatus to 'delete' will fail if the RIP
         protocol is not in the administrative outOfService state."
    DEFVAL      { delete }
    ::= { vRtrConfEntry 9 }

vRtrRsvpStatus                   OBJECT-TYPE
    SYNTAX      TmnxStatus
    MAX-ACCESS  read-create
    STATUS      current
    DESCRIPTION
        "The desired state for RSVP on this virtual router.  An attempt
         to set vRtrRsvpStatus to 'delete' will fail if the RSVP
         protocol is not in the administrative outOfService state,
         i.e. TIMETRA-RSVP-MIB::vRtrRsvpGeneralAdminState must be set
         to 'outOfService'."
    DEFVAL      { delete }
    ::= { vRtrConfEntry 10 }

vRtrEcmpMaxRoutes                OBJECT-TYPE
    SYNTAX      Unsigned32 (1..128)
    MAX-ACCESS  read-create
    STATUS      current
    DESCRIPTION
        "The value of vRtrEcmpMaxRoutes specifies the maximum number of equal
         cost routes allowed on this routing table instance. When the number
         ecmp routes available at the best preference value exceed the number
         of vRtrEcmpMaxRoutes allowed, then the lowest next-hop IP address
         algorithm is used to select the ecmp routes used.

         When vRtrEcmpMaxRoutes is set to one (1), and multiple routes are
         available with the same best preference value and equal cost values,
         then the route with the lowest next-hop IP address is used."
    DEFVAL      { 1 }
    ::= { vRtrConfEntry 11 }

vRtrAS                           OBJECT-TYPE
    SYNTAX      TmnxBgpAutonomousSystem
    MAX-ACCESS  read-create
    STATUS      obsolete
    DESCRIPTION
        "The value of vRtrAS specifies the autonomous system number to be
         advertised to this peer.  This object is MUST be set before BGP
         can be activated.

         This object was obsoleted in release 7.0.  It is replaced with the
         4-byte AS number defined by vRtrAS4Byte."
    DEFVAL      { 0 }
    ::= { vRtrConfEntry 12 }

vRtrNewIfIndex                   OBJECT-TYPE
    SYNTAX      TestAndIncr
    MAX-ACCESS  read-create
    STATUS      current
    DESCRIPTION
        "This object is used to assign values to vRtrIfIndex as
         described in 'Textual Conventions for SNMPv2'.  The network
         manager reads the object, and then writes the value back
         in the SET request that creates a new instance of vRtrIfEntry.
         If the SET fails with the code 'inconsistentValue', then
         the process must be repeated.  If the the SET succeeds, then
         the object is incremented and the new instance is created
         according to the manager's directions."
    ::= { vRtrConfEntry 13 }

vRtrLdpStatus                    OBJECT-TYPE
    SYNTAX      TmnxStatus
    MAX-ACCESS  read-create
    STATUS      current
    DESCRIPTION
        "The desired state for LDP on this virtual router.  An attempt
         to set vRtrLdpStatus to 'delete' will fail if the LDP
         protocol is not in the administrative outOfService state,
         i.e. TIMETRA-LDP-MIB::vRtrLdpGenAdminState must be set
         to 'outOfService'."
    DEFVAL      { delete }
    ::= { vRtrConfEntry 14 }

vRtrIsIsStatus                   OBJECT-TYPE
    SYNTAX      TmnxStatus
    MAX-ACCESS  read-create
    STATUS      obsolete
    DESCRIPTION
        "The desired state for ISIS on this virtual router.  An attempt
         to set vRtrIsIsStatus to 'delete' will fail if the ISIS
         protocol is not in the administrative outOfService state."
    DEFVAL      { delete }
    ::= { vRtrConfEntry 15 }

vRtrRouterId                     OBJECT-TYPE
    SYNTAX      IpAddress
    MAX-ACCESS  read-create
    STATUS      current
    DESCRIPTION
        "The value of vRtrRouterId specifies an IPv4 IP address, uniquely
         identifying the router in the Autonomous System (AS).

         By convention, if the value of the vRtrRouterId is the default value,
         the router's IP interface address will be used as the operational
         router-id for the system."
    DEFVAL      { '00000000'H }
    ::= { vRtrConfEntry 16 }

vRtrTriggeredPolicy              OBJECT-TYPE
    SYNTAX      TruthValue
    MAX-ACCESS  read-create
    STATUS      current
    DESCRIPTION
        "If the value of vRtrTriggeredPolicy is 'false', all routing protocols
         automatically reevaluate their routes when the route policies are
         changed. If this value is 'true', then the user must trigger the
         recalculation of routes when the route policies are changed."
    DEFVAL      { false }
    ::= { vRtrConfEntry 17 }

vRtrConfederationAS              OBJECT-TYPE
    SYNTAX      TmnxBgpAutonomousSystem
    MAX-ACCESS  read-create
    STATUS      obsolete
    DESCRIPTION
        "The value of vRtrConfederationAS specifies the confederation AS number
         for the virtual router. A value of 0 means no confederation AS.

         This object was obsoleted in release 7.0.  It is replaced with the
         4-byte AS number defined by vRtrConfederationAS4Byte."
    DEFVAL      { 0 }
    ::= { vRtrConfEntry 18 }

vRtrRouteDistinguisher           OBJECT-TYPE
    SYNTAX      TmnxVPNRouteDistinguisher
    MAX-ACCESS  read-create
    STATUS      current
    DESCRIPTION
        "The value of vRtrRouteDistinguisher is an identifier attached to
         routes that distinguishes to which VPN it belongs.  The VPRN
         cannot be operationally 'inService' until a route distinguisher
         has been assigned.

         SNMP set of vRtrRouteDistinguisher to a non-default value will
         automatically set vRtrBgpAutoRD to 'false'."
    DEFVAL      { '0000000000000000'H }
    ::= { vRtrConfEntry 19 }

vRtrMidRouteThreshold            OBJECT-TYPE
    SYNTAX      Unsigned32 (0..100)
    UNITS       "percent"
    MAX-ACCESS  read-create
    STATUS      current
    DESCRIPTION
        "The value of vRtrMidRouteThreshold specifies the mid-level water
         marker for the number of routes which this VRF may hold. When this
         limit is exceeded a tmnxVRtrMidRouteTCA notification is generated.

         A value of 0 (zero) for this object indicates that the threshold is
         infinite, and the notification will never be sent."
    DEFVAL      { 0 }
    ::= { vRtrConfEntry 20 }

vRtrHighRouteThreshold           OBJECT-TYPE
    SYNTAX      Unsigned32 (0..100)
    UNITS       "percent"
    MAX-ACCESS  read-only
    STATUS      current
    DESCRIPTION
        "The value of vRtrHighRouteThreshold specifies the high-level water
         marker for the number of routes which this VRF may hold. When this
         limit is exceeded a tmnxVRtrHighRouteTCA notification is generated.

         A value of 0 (zero) for this object indicates that the threshold is
         infinite, and the notification will never be sent."
    ::= { vRtrConfEntry 21 }

vRtrIllegalLabelThreshold        OBJECT-TYPE
    SYNTAX      Unsigned32
    MAX-ACCESS  read-create
    STATUS      obsolete
    DESCRIPTION
        "The value of vRtrIllegalLabelThreshold specifies the allowed limit for
         illegal label violations on this VRF. When this limit is exceeded a
         tmnxVRtrIllegalLabelTCA notification is generated.

         A value of 0 (zero) for this object indicates that the threshold is
         infinite, and the notification will never be sent.

         This object is made obsolete in release 14.0."
    DEFVAL      { 0 }
    ::= { vRtrConfEntry 22 }

vRtrVpnId                        OBJECT-TYPE
    SYNTAX      TmnxVPNId
    MAX-ACCESS  read-create
    STATUS      current
    DESCRIPTION
        "The value of vRtrVpnId is the Virtual Private Network Identifier of
         this virtual router."
    DEFVAL      { ''H }
    ::= { vRtrConfEntry 23 }

vRtrDescription                  OBJECT-TYPE
    SYNTAX      TItemDescription
    MAX-ACCESS  read-create
    STATUS      current
    DESCRIPTION
        "The value of vRtrDescription is a user provided description
         string for this virtual router.  It can consist of any printable,
         seven-bit ASCII characters up to 80 characters in length."
    DEFVAL      { ''H }
    ::= { vRtrConfEntry 25 }

vRtrGracefulRestart              OBJECT-TYPE
    SYNTAX      TruthValue
    MAX-ACCESS  read-create
    STATUS      current
    DESCRIPTION
        "The value of vRtrGracefulRestart specifies whether or not
         graceful restart capabilities are enabled on this virtual
         router.  In order for any protocol to perform graceful
         restart vRtrGracefulRestart must have a value of 'true'.
         Graceful restart capabilities can then be enabled or disabled
         on an individual protocol basis."
    DEFVAL      { false }
    ::= { vRtrConfEntry 26 }

vRtrGracefulRestartType          OBJECT-TYPE
    SYNTAX      INTEGER {
        never     (0),
        manual    (1),
        automatic (2)
    }
    MAX-ACCESS  read-create
    STATUS      current
    DESCRIPTION
        "The value of vRtrGracefulRestartType specifies when to include
         grace restart of routing protocols as a result of a switchover
         from primary CPM in a redundant system.
            'never'     - always switch without graceful restart
            'manual'    - perform graceful restart only on a forced switchover
            'automatic' - perform graceful restart on either a switchover
                          caused by an error or a forced switchover"
    DEFVAL      { never }
    ::= { vRtrConfEntry 27 }

vRtrType                         OBJECT-TYPE
    SYNTAX      INTEGER {
        baseRouter (1),
        vprn       (2),
        vr         (3)
    }
    MAX-ACCESS  read-create
    STATUS      current
    DESCRIPTION
        "The value of vRtrType specifies the type of virtual router
         represented by this row entry.  When a row is created in this
         table using 'createAndGo', vRtrType must be specified or the
         row creation will fail.

         Only the value of 'vr (3)' can be set with a SNMP SET request. The
         other values are used for row entries created internally by the agent.

         The value of vRtrType cannot be modified if vRtrRowStatus has a value
         of 'active'."
    ::= { vRtrConfEntry 28 }

vRtrServiceId                    OBJECT-TYPE
    SYNTAX      TmnxServId
    MAX-ACCESS  read-only
    STATUS      current
    DESCRIPTION
        "When vRtrType has a value of 'vprn', the value of vRtrServiceId
         indicates the service-id of the associated service that created this
         row entry."
    ::= { vRtrConfEntry 29 }

vRtrCustId                       OBJECT-TYPE
    SYNTAX      TmnxCustId
    MAX-ACCESS  read-only
    STATUS      current
    DESCRIPTION
        "When vRtrType has a value of 'vprn', the value of vRtrCustId indicates
         the customer-id of the associated service that created this row entry."
    ::= { vRtrConfEntry 30 }

vRtrIgmpStatus                   OBJECT-TYPE
    SYNTAX      TmnxStatus
    MAX-ACCESS  read-create
    STATUS      current
    DESCRIPTION
        "The desired state for IGMP on this virtual router.  An attempt
         to set vRtrIgmpStatus to 'delete' will fail if the IGMP
         protocol is not in the administrative outOfService state,
         i.e. TIMETRA-IGMP-MIB::vRtrIgmpGenAdminState must be set to
         'outOfService'."
    DEFVAL      { delete }
    ::= { vRtrConfEntry 31 }

vRtrMaxNumRoutesLogOnly          OBJECT-TYPE
    SYNTAX      TruthValue
    MAX-ACCESS  read-create
    STATUS      current
    DESCRIPTION
        "The value of vRtrMaxNumRoutesLogOnly specifies the action to
         be taken when the maximum number of routes that can be held
         within a given VRF context is reached.  If the value is 'true'
         the event is logged (a trap is sent) and the learning of
         new routes is not disabled.  If the value is 'false' the event
         is logged and the learning of new routes is disabled."
    DEFVAL      { false }
    ::= { vRtrConfEntry 32 }

vRtrVrfTarget                    OBJECT-TYPE
    SYNTAX      TNamedItemOrEmpty
    MAX-ACCESS  read-create
    STATUS      current
    DESCRIPTION
        "The value of vRtrVrfTarget specifies the extended community name for
         the default vrf-import or vrf-export policy to use for the vRtrID if
         no entries are configured in the vRtrPolicyTable for this vRtrID
         instance.

         This object can not be set if either vRtrVrfExportTarget or
         vRtrVrfImportTarget has been set."
    ::= { vRtrConfEntry 33 }

vRtrVrfExportTarget              OBJECT-TYPE
    SYNTAX      TNamedItemOrEmpty
    MAX-ACCESS  read-create
    STATUS      current
    DESCRIPTION
        "The value of vRtrVrfExportTarget specifies the extended community name
         for the default vrf-export policy to use for the vRtrID if no entries
         are configured in the vRtrPolicyTable for this vRtrID instance.

         This object can not be set if vRtrVrfTarget has been set."
    ::= { vRtrConfEntry 34 }

vRtrVrfImportTarget              OBJECT-TYPE
    SYNTAX      TNamedItemOrEmpty
    MAX-ACCESS  read-create
    STATUS      current
    DESCRIPTION
        "The value of vRtrVrfImportTarget specifies the extended community name
         for the default vrf-import policy to use for the vRtrID if no entries
         are configured in the vRtrPolicyTable for this vRtrID instance.

         This object can not be set if vRtrVrfTarget has been set."
    ::= { vRtrConfEntry 35 }

vRtrPimStatus                    OBJECT-TYPE
    SYNTAX      TmnxStatus
    MAX-ACCESS  read-create
    STATUS      current
    DESCRIPTION
        "The desired state for PIM on this virtual router. When the object is
         set to 'create', PIM protocol instance is enabled on the virtual
         router. Setting the value to 'delete' disables PIM on the virtual
         router."
    DEFVAL      { delete }
    ::= { vRtrConfEntry 36 }

vRtrMaxMcastNumRoutes            OBJECT-TYPE
    SYNTAX      Integer32 (-1 | 1..2147483647)
    MAX-ACCESS  read-create
    STATUS      current
    DESCRIPTION
        "The maximum number of multicast routes that can be configured on
         this virtual router.  If the value is -1, then there
         is no limit."
    DEFVAL      { -1 }
    ::= { vRtrConfEntry 37 }

vRtrMaxMcastNumRoutesLogOnly     OBJECT-TYPE
    SYNTAX      TruthValue
    MAX-ACCESS  read-create
    STATUS      current
    DESCRIPTION
        "The value of vRtrMaxMcastNumRoutesLogOnly specifies the action to
         be taken when the maximum number of multicast routes that can be held
         within a given VRF context is reached.  If the value is 'true'
         the event is logged (a trap is sent) and the learning of
         new multicast routes is not disabled.  If the value is 'false' the
         event is logged and the learning of new routes is disabled."
    DEFVAL      { false }
    ::= { vRtrConfEntry 38 }

vRtrMcastMidRouteThreshold       OBJECT-TYPE
    SYNTAX      Unsigned32 (0..100)
    UNITS       "percent"
    MAX-ACCESS  read-create
    STATUS      current
    DESCRIPTION
        "The value of vRtrMcastMidRouteThreshold specifies the mid-level water
         marker for the number of multicast routes which this VRF may hold.
         When this limit is exceeded a tmnxVRtrMcastMidRouteTCA notification is
         generated.

         A value of 0 (zero) for this object indicates that the threshold is
         infinite, and the notification will never be sent."
    DEFVAL      { 0 }
    ::= { vRtrConfEntry 39 }

vRtrIgnoreIcmpRedirect           OBJECT-TYPE
    SYNTAX      TruthValue
    MAX-ACCESS  read-create
    STATUS      current
    DESCRIPTION
        "If the value of vRtrIgnoreIcmpRedirect is 'true', the virtual router
         will drop all ICMP Redirects received on the management interface. If
         the value of vRtrIgnoreIcmpRedirect is 'false' and an ICMP Redirect is
         received on the management interface, a /32 route will be created in
         the route table.

         If the value of vRtrName is not 'management', an SNMP set request to
         vRtrIgnoreIcmpRedirect will fail with an 'inconsistentValue' error."
    DEFVAL      { true }
    ::= { vRtrConfEntry 40 }

vRtrOspfv3Status                 OBJECT-TYPE
    SYNTAX      TmnxStatus
    MAX-ACCESS  read-create
    STATUS      obsolete
    DESCRIPTION
        "The desired state for OSPFv3 on this virtual router.  An attempt
         to set vRtrOspfv3Status to 'delete' will fail if the OSPFv3
         protocol is not in the administrative outOfService state,
         i.e. TIMETRA-OSPF-NG-MIB::tmnxOspfAdminState must be set
         to 'disabled'.

         This object was obsoleted in release 5.0."
    DEFVAL      { delete }
    ::= { vRtrConfEntry 41 }

vRtrMsdpStatus                   OBJECT-TYPE
    SYNTAX      TmnxStatus
    MAX-ACCESS  read-create
    STATUS      current
    DESCRIPTION
        "The desired state for Msdp on this virtual router.  An attempt
         to set vRtrMsdpStatus to 'delete' will fail if the Msdp
         protocol is not in the administrative outOfService state,
         i.e. TIMETRA-MSDP-NG-MIB::tmnxMsdpNgAdminState must be
         set to 'outOfService'."
    DEFVAL      { delete }
    ::= { vRtrConfEntry 42 }

vRtrVprnType                     OBJECT-TYPE
    SYNTAX      INTEGER {
        regular                (1),
        hub                    (2),
        spoke                  (3),
        subscriberSplitHorizon (4)
    }
    MAX-ACCESS  read-create
    STATUS      current
    DESCRIPTION
        "The value of vRtrVprnType specifies how traffic is routed.

         regular (1)                - All traffic is routed to all
                                      destinations.

         hub (2)                    - Network traffic is routed only to
                                      the access side. Access traffic is
                                      routed to all destinations.

         spoke (3)                  - Networks traffic is routed to all
                                      destinations. Access traffic is
                                      routed only to the network side.

         subscriberSplitHorizon (4) - Subscriber interface traffic is
                                      routed only to the network side.
                                      All other traffic is routed to
                                      all destinations.

         This object cannot be modified if vRtrType is not 'vprn'."
    DEFVAL      { regular }
    ::= { vRtrConfEntry 43 }

vRtrSecondaryVrfId               OBJECT-TYPE
    SYNTAX      TmnxVRtrIDOrZero
    MAX-ACCESS  read-only
    STATUS      current
    DESCRIPTION
        "The unique value of vRtrSecondaryVrfId indicates the secondary vrf-id
         for hub and spoke vprn.

         Non-zero value of vRtrSecondaryVrfId indicates that two route tables
         exist for hub and spoke vprn system one each for hub and spoke. One of
         which is indexed by vRtrSecondaryVrfId.

         If the value of  vRtrSecondaryVrfId  is zero, it indicates that
         there is only one route table for hub and spoke vprn system."
    ::= { vRtrConfEntry 44 }

vRtrMldStatus                    OBJECT-TYPE
    SYNTAX      TmnxStatus
    MAX-ACCESS  read-create
    STATUS      current
    DESCRIPTION
        "The desired state for Multicast Listener Discovery (MLD) Protocol
         on this virtual router.  An attempt to set vRtrMldStatus to 'delete'
         will fail if the MLD protocol is not in the administrative
         outOfService state, i.e. TIMETRA-MLD-MIB::vRtrMldGenAdminState
         must be set to 'outOfService'."
    DEFVAL      { delete }
    ::= { vRtrConfEntry 45 }

vRtrIPv6MaxNumRoutes             OBJECT-TYPE
    SYNTAX      Integer32 (-1 | 1..2147483647)
    MAX-ACCESS  read-create
    STATUS      current
    DESCRIPTION
        "The maximum number of IPv6 routes that can be configured on
         this virtual router.  If the value is -1, then there
         is no limit.

         This object is not supported on SR-1, where the value of
         TIMETRA-CHASSIS-MIB::tmnxChassisType is '5'."
    DEFVAL      { -1 }
    ::= { vRtrConfEntry 46 }

vRtrIPv6MidRouteThreshold        OBJECT-TYPE
    SYNTAX      Unsigned32 (0..100)
    UNITS       "percent"
    MAX-ACCESS  read-create
    STATUS      current
    DESCRIPTION
        "The value of vRtrIPv6MidRouteThreshold specifies the mid-level water
         marker for the number of IPv6 routes which this VRF may hold. When
         this limit is exceeded a tmnxVRtrIPv6MidRouteTCA notification is
         generated.

         A value of 0 (zero) for this object indicates that the threshold is
         infinite, and the notification will never be sent."
    DEFVAL      { 0 }
    ::= { vRtrConfEntry 47 }

vRtrIPv6HighRouteThreshold       OBJECT-TYPE
    SYNTAX      Unsigned32 (0..100)
    UNITS       "percent"
    MAX-ACCESS  read-only
    STATUS      current
    DESCRIPTION
        "The value of vRtrIPv6HighRouteThreshold specifies the high-level water
         marker for the number of IPv6 routes which this VRF may hold. When
         this limit is exceeded a tmnxVRtrIPv6HighRouteTCA notification is
         generated.

         A value of 0 (zero) for this object indicates that the threshold is
         infinite, and the notification will never be sent."
    ::= { vRtrConfEntry 48 }

vRtrIPv6MaxNumRoutesLogOnly      OBJECT-TYPE
    SYNTAX      TruthValue
    MAX-ACCESS  read-create
    STATUS      current
    DESCRIPTION
        "The value of vRtrIPv6MaxNumRoutesLogOnly specifies the action to
         be taken when the maximum number of IPv6 routes that can be held
         within a given VRF context is reached.  If the value is 'true'
         the event is logged (a trap is sent) and the learning of
         new routes is not disabled.  If the value is 'false' the event
         is logged and the learning of new routes is disabled."
    DEFVAL      { false }
    ::= { vRtrConfEntry 49 }

vRtrIPv6IgnoreIcmpRedirect       OBJECT-TYPE
    SYNTAX      TruthValue
    MAX-ACCESS  read-create
    STATUS      current
    DESCRIPTION
        "If the value of vRtrIPv6IgnoreIcmpRedirect is 'true', the virtual
         router will drop all IPv6 ICMP Redirects received on the management
         interface. If the value of vRtrIPv6IgnoreIcmpRedirect is 'false' and
         an IPv6 ICMP Redirect is received on the management interface, a /128
         route will be created in the route table.

         If the value of vRtrName is not 'management', an SNMP set request to
         vRtrIPv6IgnoreIcmpRedirect will fail with an 'inconsistentValue'
         error."
    DEFVAL      { true }
    ::= { vRtrConfEntry 50 }

vRtrMcPathMgmtPlcyName           OBJECT-TYPE
    SYNTAX      TNamedItem
    MAX-ACCESS  read-create
    STATUS      current
    DESCRIPTION
        "The value of vRtrMcPathMgmtPlcyName specifies the multicast policy
         name configured on this virtual router."
    DEFVAL      { "default" }
    ::= { vRtrConfEntry 51 }

vRtrIgnoreNextHopMetric          OBJECT-TYPE
    SYNTAX      TruthValue
    MAX-ACCESS  read-create
    STATUS      current
    DESCRIPTION
        "The value of vRtrIgnoreNextHopMetric specifies whether next-hop metric
         should be ignored when computing ECMP paths for VPRN routes."
    DEFVAL      { false }
    ::= { vRtrConfEntry 52 }

vRtrMvpnVrfTarget                OBJECT-TYPE
    SYNTAX      TNamedItemOrEmpty
    MAX-ACCESS  read-create
    STATUS      current
    DESCRIPTION
        "The value of vRtrMvpnVrfTarget specifies the extended community name
         for the Multicast VPN (MVPN) vrf-import or vrf-export policy to use
         for the vRtrID if no entries are configured in the vRtrPolicyTable for
         this vRtrID instance.

         This object can not be set if either vRtrMvpnVrfExportTarget or
         vRtrMvpnVrfImportTarget has been set."
    DEFVAL      { ''H }
    ::= { vRtrConfEntry 53 }

vRtrMvpnVrfExportTarget          OBJECT-TYPE
    SYNTAX      TNamedItemOrEmpty
    MAX-ACCESS  read-create
    STATUS      current
    DESCRIPTION
        "The value of vRtrMvpnVrfExportTarget specifies the extended community
         name for the Multicast VPN (MVPN) vrf-export policy to use for the
         vRtrID if no entries are configured in the vRtrPolicyTable for this
         vRtrID instance.

         This object can not be set if vRtrMvpnVrfTarget has been set."
    DEFVAL      { ''H }
    ::= { vRtrConfEntry 54 }

vRtrMvpnVrfImportTarget          OBJECT-TYPE
    SYNTAX      TNamedItemOrEmpty
    MAX-ACCESS  read-create
    STATUS      current
    DESCRIPTION
        "The value of vRtrMvpnVrfImportTarget specifies the extended community
         name for the Multicast VPN (MVPN) vrf-import policy to use for the
         vRtrID if no  entries are configured in the vRtrPolicyTable for
         this vRtrID instance.

         This object can not be set if vRtrMvpnVrfTarget has been set."
    DEFVAL      { ''H }
    ::= { vRtrConfEntry 55 }

vRtrMvpnVrfTargetUnicast         OBJECT-TYPE
    SYNTAX      TruthValue
    MAX-ACCESS  read-create
    STATUS      current
    DESCRIPTION
        "The value of vRtrMvpnVrfTargetUnicast specifies whether unicast
         vrf-target extended community is used for the Multicast VPN (MVPN) as
         well.

         If the value is 'true', vRtrVrfTarget extended community is used for
         MVPN.

         If the value is 'false', vRtrMvpnVrfTarget extended community is used
         for MVPN."
    DEFVAL      { false }
    ::= { vRtrConfEntry 56 }

vRtrMvpnVrfExportTargetUnicast   OBJECT-TYPE
    SYNTAX      TruthValue
    MAX-ACCESS  read-create
    STATUS      current
    DESCRIPTION
        "The value of vRtrMvpnVrfExportTargetUnicast specifies whether unicast
         vrf-target import extended community is used for the Multicast VPN
         (MVPN) as well.

         If the value is 'true', vRtrVrfExportTarget extended community is used
         for MVPN.

         If the value is 'false', vRtrMvpnVrfExportTarget extended community is
         used for MVPN."
    DEFVAL      { false }
    ::= { vRtrConfEntry 57 }

vRtrMvpnVrfImportTargetUnicast   OBJECT-TYPE
    SYNTAX      TruthValue
    MAX-ACCESS  read-create
    STATUS      current
    DESCRIPTION
        "The value of vRtrMvpnVrfImportTargetUnicast specifies whether unicast
         vrf-target export extended community is used for the Multicast VPN
         (MVPN) as well.

         If the value is 'true', vRtrVrfImportTarget extended community is used
         for MVPN.

         If the value is 'false', vRtrMvpnVrfImportTarget extended community is
         used for MVPN."
    DEFVAL      { false }
    ::= { vRtrConfEntry 58 }

vRtrAS4Byte                      OBJECT-TYPE
    SYNTAX      InetAutonomousSystemNumber
    MAX-ACCESS  read-create
    STATUS      current
    DESCRIPTION
        "The value of vRtrAS4Byte specifies the autonomous system number to be
         advertised to this peer.  This object MUST be set before BGP
         can be activated."
    DEFVAL      { 0 }
    ::= { vRtrConfEntry 59 }

vRtrConfederationAS4Byte         OBJECT-TYPE
    SYNTAX      InetAutonomousSystemNumber
    MAX-ACCESS  read-create
    STATUS      current
    DESCRIPTION
        "The value of vRtrConfederationAS4Byte specifies the confederation AS
         number for the virtual router. A value of 0 means no confederation AS."
    DEFVAL      { 0 }
    ::= { vRtrConfEntry 60 }

vRtrMvpnCMcastImportRT           OBJECT-TYPE
    SYNTAX      TNamedItemOrEmpty
    MAX-ACCESS  read-only
    STATUS      current
    DESCRIPTION
        "The value of vRtrMvpnCMcastImportRT indicates C-multicast Import Route
         that uniquely identifies a VRF.

         vRtrMvpnCMcastImportRT controls imports of C-multicast routes into a
         particular VRF. A PE that has sites of a given MVPN connected to it
         needs to communicate the value of the C-multicast Import RT associated
         with the VRF of that MVPN on the PE to all other PEs that have sites
         of that MVPN. A PE that originates a (unicast) route to VPN-IP
         addresses must include in the BGP Update message the value of the
         C-multicast Import RT of the VRF associated with the route."
    DEFVAL      { ''H }
    ::= { vRtrConfEntry 61 }

vRtrInterASMvpn                  OBJECT-TYPE
    SYNTAX      TruthValue
    MAX-ACCESS  read-only
    STATUS      current
    DESCRIPTION
        "When the object vRtrType has a value of 'vprn', the value of
         vRtrInterASMvpn indicates whether the VPRN service is used for
         inter-AS MVPN or not.

         If the value of the object is 'true', it indicates that the vprn
         service is used for inter-AS MVPN only. If the value of the object is
         'false', it indicates that the vprn service is not used for inter-AS
         MVPN."
    ::= { vRtrConfEntry 64 }

vRtrRipNgStatus                  OBJECT-TYPE
    SYNTAX      TmnxStatus
    MAX-ACCESS  read-create
    STATUS      current
    DESCRIPTION
        "The desired state for RIP-NG on this virtual router.  An attempt
         to set vRtrRipNgStatus to 'delete' will fail if the RIP-NG
         protocol is not in the administrative outOfService state."
    DEFVAL      { delete }
    ::= { vRtrConfEntry 65 }

vRtrStatTable                    OBJECT-TYPE
    SYNTAX      SEQUENCE OF VRtrStatEntry
    MAX-ACCESS  not-accessible
    STATUS      current
    DESCRIPTION
        "The vRtrStatTable has an entry for each virtual router configured in
         the system."
    ::= { tmnxVRtrObjs 2 }

vRtrStatEntry                    OBJECT-TYPE
    SYNTAX      VRtrStatEntry
    MAX-ACCESS  not-accessible
    STATUS      current
    DESCRIPTION
        "Each row entry represents a collection of statistics for a virtual
         router in the system.

         Entries cannot be created and deleted via SNMP SET operations."
    AUGMENTS    { vRtrConfEntry }
    ::= { vRtrStatTable 1 }

VRtrStatEntry                    ::= SEQUENCE
{
    vRtrOperState                    TmnxOperState,
    vRtrDirectRoutes                 Gauge32,
    vRtrDirectActiveRoutes           Gauge32,
    vRtrStaticRoutes                 Gauge32,
    vRtrStaticActiveRoutes           Gauge32,
    vRtrOSPFRoutes                   Gauge32,
    vRtrOSPFActiveRoutes             Gauge32,
    vRtrBGPRoutes                    Gauge32,
    vRtrBGPActiveRoutes              Gauge32,
    vRtrISISRoutes                   Gauge32,
    vRtrISISActiveRoutes             Gauge32,
    vRtrRIPRoutes                    Gauge32,
    vRtrRIPActiveRoutes              Gauge32,
    vRtrAggregateRoutes              Gauge32,
    vRtrAggregateActiveRoutes        Gauge32,
    vRtrStatConfiguredIfs            Gauge32,
    vRtrStatActiveIfs                Gauge32,
    vRtrStatIllegalLabels            Counter32,
    vRtrStatCurrNumRoutes            Gauge32,
    vRtrStatBGPVpnRoutes             Gauge32,
    vRtrStatBGPVpnActiveRoutes       Gauge32,
    vRtrStatTotalLdpTunnels          Gauge32,
    vRtrStatTotalSdpTunnels          Gauge32,
    vRtrStatActiveLdpTunnels         Gauge32,
    vRtrStatActiveSdpTunnels         Gauge32,
    vRtrMulticastRoutes              Gauge32,
    vRtrStatActiveARPEntries         Gauge32,
    vRtrStatTotalARPEntries          Gauge32,
    vRtrV6DirectRoutes               Gauge32,
    vRtrV6DirectActiveRoutes         Gauge32,
    vRtrV6StaticRoutes               Gauge32,
    vRtrV6StaticActiveRoutes         Gauge32,
    vRtrV6OSPFRoutes                 Gauge32,
    vRtrV6OSPFActiveRoutes           Gauge32,
    vRtrV6BGPRoutes                  Gauge32,
    vRtrV6BGPActiveRoutes            Gauge32,
    vRtrV6ISISRoutes                 Gauge32,
    vRtrV6ISISActiveRoutes           Gauge32,
    vRtrV6RIPRoutes                  Gauge32,
    vRtrV6RIPActiveRoutes            Gauge32,
    vRtrV6AggregateRoutes            Gauge32,
    vRtrV6AggregateActiveRoutes      Gauge32,
    vRtrV6StatConfiguredIfs          Gauge32,
    vRtrV6StatActiveIfs              Gauge32,
    vRtrV6StatIllegalLabels          Counter32,
    vRtrV6StatCurrNumRoutes          Gauge32,
    vRtrV6StatBGPVpnRoutes           Gauge32,
    vRtrV6StatBGPVpnActiveRoutes     Gauge32,
    vRtrV6StatTotalLdpTunnels        Gauge32,
    vRtrV6StatTotalSdpTunnels        Gauge32,
    vRtrV6StatActiveLdpTunnels       Gauge32,
    vRtrV6StatActiveSdpTunnels       Gauge32,
    vRtrV6MulticastRoutes            Gauge32,
    vRtrV6StatActiveNbrEntries       Gauge32,
    vRtrV6StatTotalNbrEntries        Gauge32,
    vRtrSubMgmtRoutes                Gauge32,
    vRtrSubMgmtActiveRoutes          Gauge32,
    vRtrStatTotalRsvpTunnels         Gauge32,
    vRtrStatActiveRsvpTunnels        Gauge32,
    vRtrV6StatTotalRsvpTunnels       Gauge32,
    vRtrV6StatActiveRsvpTunnels      Gauge32,
    vRtrHostRoutes                   Gauge32,
    vRtrHostActiveRoutes             Gauge32,
    vRtrV6HostRoutes                 Gauge32,
    vRtrV6HostActiveRoutes           Gauge32,
    vRtrStatLocalARPEntries          Gauge32,
    vRtrStatStaticARPEntries         Gauge32,
    vRtrStatDynamicARPEntries        Gauge32,
    vRtrStatManagedARPEntries        Gauge32,
    vRtrStatInternalARPEntries       Gauge32,
    vRtrManagedRoutes                Gauge32,
    vRtrManagedActiveRoutes          Gauge32,
    vRtrLDPRoutes                    Gauge32,
    vRtrLDPActiveRoutes              Gauge32,
    vRtrVPNLeakRoutes                Gauge32,
    vRtrVPNLeakActiveRoutes          Gauge32,
    vRtrV6VPNLeakRoutes              Gauge32,
    vRtrV6VPNLeakActiveRoutes        Gauge32,
    vRtrV6SubMgmtRoutes              Gauge32,
    vRtrV6SubMgmtActiveRoutes        Gauge32,
    vRtrMobileHostRoutes             Gauge32,
    vRtrMobileHostActiveRoutes       Gauge32,
    vRtrV6MobileHostRoutes           Gauge32,
    vRtrV6MobileHostActiveRoutes     Gauge32,
    vRtrStatTotalBgpTunnels          Gauge32,
    vRtrStatActiveBgpTunnels         Gauge32,
    vRtrNatRoutes                    Gauge32,
    vRtrNatActiveRoutes              Gauge32,
    vRtrV6NatRoutes                  Gauge32,
    vRtrV6NatActiveRoutes            Gauge32,
    vRtrPeriodicRoutes               Gauge32,
    vRtrPeriodicActiveRoutes         Gauge32,
    vRtrV6PeriodicRoutes             Gauge32,
    vRtrV6PeriodicActiveRoutes       Gauge32,
    vRtrV6ManagedRoutes              Gauge32,
    vRtrV6ManagedActiveRoutes        Gauge32,
    vRtrStatTotalMplsTpTunnels       Gauge32,
    vRtrStatActiveMplsTpTunnels      Gauge32,
    vRtrV6Dhcpv6PdRoutes             Gauge32,
    vRtrV6Dhcpv6PdActiveRoutes       Gauge32,
    vRtrV6Dhcpv6NaRoutes             Gauge32,
    vRtrV6Dhcpv6NaActiveRoutes       Gauge32,
    vRtrV6Dhcpv6TaRoutes             Gauge32,
    vRtrV6Dhcpv6TaActiveRoutes       Gauge32,
    vRtrV6Dhcpv6PdExclRoutes         Gauge32,
    vRtrV6Dhcpv6PdExclActiveRoutes   Gauge32,
    vRtrIPsecRoutes                  Gauge32,
    vRtrIPsecActiveRoutes            Gauge32,
    vRtrStatBGPEVPNARPEntries        Gauge32,
    vRtrStatBGPEvpnRoutes            Gauge32,
    vRtrStatBGPEvpnActiveRoutes      Gauge32,
    vRtrV6StatBGPEvpnRoutes          Gauge32,
    vRtrV6StatBGPEvpnActiveRoutes    Gauge32,
    vRtrMcastIpv4StatBGPEvpnRoutes   Gauge32,
    vRtrMcastIpv4StatBGPEvpnActvRts  Gauge32,
    vRtrMcastIpv6StatBGPEvpnRoutes   Gauge32,
    vRtrMcastIpv6StatBGPEvpnActvRts  Gauge32,
    vRtrV6IPsecRoutes                Gauge32,
    vRtrV6IPsecActiveRoutes          Gauge32,
    vRtrStatBGPLabelV4Routes         Gauge32,
    vRtrStatBGPLabelV4ActiveRoutes   Gauge32,
    vRtrStatBGPLabelV6Routes         Gauge32,
    vRtrStatBGPLabelV6ActiveRoutes   Gauge32,
    vRtrStatTotalBgpEpeTunnels       Gauge32,
    vRtrStatActiveBgpEpeTunnels      Gauge32,
    vRtrStatTotalBgpEpeV6Tunnels     Gauge32,
    vRtrStatActiveBgpEpeV6Tunnels    Gauge32,
    vRtrStatTotalBgpV6Tunnels        Gauge32,
    vRtrStatActiveBgpV6Tunnels       Gauge32
}

vRtrOperState                    OBJECT-TYPE
    SYNTAX      TmnxOperState
    MAX-ACCESS  read-only
    STATUS      current
    DESCRIPTION
        "vRtrOperState indicates current operational status of this virtual
         router."
    ::= { vRtrStatEntry 1 }

vRtrDirectRoutes                 OBJECT-TYPE
    SYNTAX      Gauge32
    MAX-ACCESS  read-only
    STATUS      current
    DESCRIPTION
        "vRtrDirectRoutes indicates the current number of direct routes for
         this instance of the route table."
    ::= { vRtrStatEntry 2 }

vRtrDirectActiveRoutes           OBJECT-TYPE
    SYNTAX      Gauge32
    MAX-ACCESS  read-only
    STATUS      current
    DESCRIPTION
        "vRtrDirectActiveRoutes indicates the current number of active direct
         routes for this instance of the route table."
    ::= { vRtrStatEntry 3 }

vRtrStaticRoutes                 OBJECT-TYPE
    SYNTAX      Gauge32
    MAX-ACCESS  read-only
    STATUS      current
    DESCRIPTION
        "vRtrStaticRoutes indicates the current number of static routes for
         this instance of the route table."
    ::= { vRtrStatEntry 4 }

vRtrStaticActiveRoutes           OBJECT-TYPE
    SYNTAX      Gauge32
    MAX-ACCESS  read-only
    STATUS      current
    DESCRIPTION
        "vRtrStaticActiveRoutes indicates the current number of active static
         routes for this instance of the route table."
    ::= { vRtrStatEntry 5 }

vRtrOSPFRoutes                   OBJECT-TYPE
    SYNTAX      Gauge32
    MAX-ACCESS  read-only
    STATUS      current
    DESCRIPTION
        "vRtrOSPFRoutes indicates the current number of ospf routes for this
         instance of the route table."
    ::= { vRtrStatEntry 6 }

vRtrOSPFActiveRoutes             OBJECT-TYPE
    SYNTAX      Gauge32
    MAX-ACCESS  read-only
    STATUS      current
    DESCRIPTION
        "vRtrOSPFActiveRoutes indicates the current number of active ospf
         routes for this instance of the route table."
    ::= { vRtrStatEntry 7 }

vRtrBGPRoutes                    OBJECT-TYPE
    SYNTAX      Gauge32
    MAX-ACCESS  read-only
    STATUS      current
    DESCRIPTION
        "vRtrBGPRoutes indicates the current number of bgp routes for this
         instance of the route table."
    ::= { vRtrStatEntry 8 }

vRtrBGPActiveRoutes              OBJECT-TYPE
    SYNTAX      Gauge32
    MAX-ACCESS  read-only
    STATUS      current
    DESCRIPTION
        "vRtrBGPActiveRoutes indicates the current number of active bgp routes
         for this instance of the route table."
    ::= { vRtrStatEntry 9 }

vRtrISISRoutes                   OBJECT-TYPE
    SYNTAX      Gauge32
    MAX-ACCESS  read-only
    STATUS      current
    DESCRIPTION
        "vRtrISISRoutes indicates the current number of isis routes for this
         instance of the route table."
    ::= { vRtrStatEntry 10 }

vRtrISISActiveRoutes             OBJECT-TYPE
    SYNTAX      Gauge32
    MAX-ACCESS  read-only
    STATUS      current
    DESCRIPTION
        "vRtrISISActiveRoutes indicates the current number of active isis
         routes for this instance of the route table."
    ::= { vRtrStatEntry 11 }

vRtrRIPRoutes                    OBJECT-TYPE
    SYNTAX      Gauge32
    MAX-ACCESS  read-only
    STATUS      current
    DESCRIPTION
        "vRtrRIPRoutes indicates the current number of rip routes for this
         instance of the route table."
    ::= { vRtrStatEntry 12 }

vRtrRIPActiveRoutes              OBJECT-TYPE
    SYNTAX      Gauge32
    MAX-ACCESS  read-only
    STATUS      current
    DESCRIPTION
        "vRtrRIPActiveRoutes indicates the current number of active rip routes
         for this instance of the route table."
    ::= { vRtrStatEntry 13 }

vRtrAggregateRoutes              OBJECT-TYPE
    SYNTAX      Gauge32
    MAX-ACCESS  read-only
    STATUS      current
    DESCRIPTION
        "vRtrAggregateRoutes indicates the current number of aggregate routes
         for this instance of the route table."
    ::= { vRtrStatEntry 14 }

vRtrAggregateActiveRoutes        OBJECT-TYPE
    SYNTAX      Gauge32
    MAX-ACCESS  read-only
    STATUS      current
    DESCRIPTION
        "vRtrAggregateActiveRoutes indicates the current number of active
         aggregate routes for this instance of the route table."
    ::= { vRtrStatEntry 15 }

vRtrStatConfiguredIfs            OBJECT-TYPE
    SYNTAX      Gauge32
    MAX-ACCESS  read-only
    STATUS      current
    DESCRIPTION
        "vRtrStatConfiguredIfs indicates the current number of router
         interfaces configured on this virtual router."
    ::= { vRtrStatEntry 16 }

vRtrStatActiveIfs                OBJECT-TYPE
    SYNTAX      Gauge32
    MAX-ACCESS  read-only
    STATUS      current
    DESCRIPTION
        "vRtrStatActiveIfs indicates the current number of router interfaces
         with vRtrIfAdminState equal 'inService' on this virtual router."
    ::= { vRtrStatEntry 17 }

vRtrStatIllegalLabels            OBJECT-TYPE
    SYNTAX      Counter32
    MAX-ACCESS  read-only
    STATUS      current
    DESCRIPTION
        "vRtrStatIllegalLabels indicates the number of illegally received
         labels on this virtual router."
    ::= { vRtrStatEntry 18 }

vRtrStatCurrNumRoutes            OBJECT-TYPE
    SYNTAX      Gauge32
    MAX-ACCESS  read-only
    STATUS      current
    DESCRIPTION
        "vRtrStatCurrNumRoutes indicates the current number of routes in the
         VRF for this virtual router."
    ::= { vRtrStatEntry 19 }

vRtrStatBGPVpnRoutes             OBJECT-TYPE
    SYNTAX      Gauge32
    MAX-ACCESS  read-only
    STATUS      current
    DESCRIPTION
        "vRtrStatBGPVpnRoutes indicates the current number of VPN-IPV4 routes
         learned by MP-BGP for this virtual router."
    ::= { vRtrStatEntry 20 }

vRtrStatBGPVpnActiveRoutes       OBJECT-TYPE
    SYNTAX      Gauge32
    MAX-ACCESS  read-only
    STATUS      current
    DESCRIPTION
        "vRtrStatBGPVpnActiveRoutes indicates the current number of active
         VPN-IPV4 routes learned by MP-BGP for this virtual router."
    ::= { vRtrStatEntry 21 }

vRtrStatTotalLdpTunnels          OBJECT-TYPE
    SYNTAX      Gauge32
    MAX-ACCESS  read-only
    STATUS      current
    DESCRIPTION
        "vRtrStatTotalLdpTunnels indicates the current number of both active
         and inactive LDP tunnels."
    ::= { vRtrStatEntry 22 }

vRtrStatTotalSdpTunnels          OBJECT-TYPE
    SYNTAX      Gauge32
    MAX-ACCESS  read-only
    STATUS      current
    DESCRIPTION
        "vRtrStatTotalSdpTunnels indicates the current number of both active
         and inactive SDP tunnels."
    ::= { vRtrStatEntry 23 }

vRtrStatActiveLdpTunnels         OBJECT-TYPE
    SYNTAX      Gauge32
    MAX-ACCESS  read-only
    STATUS      current
    DESCRIPTION
        "vRtrStatActiveLdpTunnels indicates the current number of rows in the
         vRtrInetTunnelTable where vRtrInetTunnelType has a value of 'ldp'."
    ::= { vRtrStatEntry 24 }

vRtrStatActiveSdpTunnels         OBJECT-TYPE
    SYNTAX      Gauge32
    MAX-ACCESS  read-only
    STATUS      current
    DESCRIPTION
        "vRtrStatActiveSdpTunnels indicates the current number of rows in the
         vRtrInetTunnelTable where vRtrInetTunnelType has a value of 'sdp'."
    ::= { vRtrStatEntry 25 }

vRtrMulticastRoutes              OBJECT-TYPE
    SYNTAX      Gauge32
    MAX-ACCESS  read-only
    STATUS      current
    DESCRIPTION
        "vRtrMulticastRoutes indicates the current number of rows in the
         vRtrPimNgGrpSrcTable."
    ::= { vRtrStatEntry 26 }

vRtrStatActiveARPEntries         OBJECT-TYPE
    SYNTAX      Gauge32
    MAX-ACCESS  read-only
    STATUS      current
    DESCRIPTION
        "vRtrStatActiveARPEntries indicates the number of active ARP entries
         for the specified virtual router in the system."
    ::= { vRtrStatEntry 27 }

vRtrStatTotalARPEntries          OBJECT-TYPE
    SYNTAX      Gauge32
    MAX-ACCESS  read-only
    STATUS      current
    DESCRIPTION
        "vRtrStatTotalARPEntries indicates the total number of active and
         inactive ARP entries for the specified virtual router in the system."
    ::= { vRtrStatEntry 28 }

vRtrV6DirectRoutes               OBJECT-TYPE
    SYNTAX      Gauge32
    MAX-ACCESS  read-only
    STATUS      current
    DESCRIPTION
        "vRtrV6DirectRoutes indicates the current number of v6 direct routes
         for this instance of the route table."
    ::= { vRtrStatEntry 29 }

vRtrV6DirectActiveRoutes         OBJECT-TYPE
    SYNTAX      Gauge32
    MAX-ACCESS  read-only
    STATUS      current
    DESCRIPTION
        "vRtrV6DirectActiveRoutes indicates the current number of v6 active
         direct routes for this instance of the route table."
    ::= { vRtrStatEntry 30 }

vRtrV6StaticRoutes               OBJECT-TYPE
    SYNTAX      Gauge32
    MAX-ACCESS  read-only
    STATUS      current
    DESCRIPTION
        "vRtrV6StaticRoutes indicates the current number of v6 static routes
         for this instance of the route table."
    ::= { vRtrStatEntry 31 }

vRtrV6StaticActiveRoutes         OBJECT-TYPE
    SYNTAX      Gauge32
    MAX-ACCESS  read-only
    STATUS      current
    DESCRIPTION
        "vRtrV6StaticActiveRoutes indicates the current number of v6 active
         static routes for this instance of the route table."
    ::= { vRtrStatEntry 32 }

vRtrV6OSPFRoutes                 OBJECT-TYPE
    SYNTAX      Gauge32
    MAX-ACCESS  read-only
    STATUS      current
    DESCRIPTION
        "vRtrV6OSPFRoutes indicates the current number of v6 ospf routes for
         this instance of the route table."
    ::= { vRtrStatEntry 33 }

vRtrV6OSPFActiveRoutes           OBJECT-TYPE
    SYNTAX      Gauge32
    MAX-ACCESS  read-only
    STATUS      current
    DESCRIPTION
        "vRtrV6OSPFActiveRoutes indicates the current number of v6 active ospf
         routes for this instance of the route table."
    ::= { vRtrStatEntry 34 }

vRtrV6BGPRoutes                  OBJECT-TYPE
    SYNTAX      Gauge32
    MAX-ACCESS  read-only
    STATUS      current
    DESCRIPTION
        "vRtrV6BGPRoutes indicates the current number of v6 bgp routes for this
         instance of the route table."
    ::= { vRtrStatEntry 35 }

vRtrV6BGPActiveRoutes            OBJECT-TYPE
    SYNTAX      Gauge32
    MAX-ACCESS  read-only
    STATUS      current
    DESCRIPTION
        "vRtrV6BGPActiveRoutes indicates the current number of v6 active bgp
         routes for this instance of the route table."
    ::= { vRtrStatEntry 36 }

vRtrV6ISISRoutes                 OBJECT-TYPE
    SYNTAX      Gauge32
    MAX-ACCESS  read-only
    STATUS      current
    DESCRIPTION
        "vRtrV6ISISRoutes indicates the current number of v6 isis routes for
         this instance of the route table."
    ::= { vRtrStatEntry 37 }

vRtrV6ISISActiveRoutes           OBJECT-TYPE
    SYNTAX      Gauge32
    MAX-ACCESS  read-only
    STATUS      current
    DESCRIPTION
        "vRtrV6ISISActiveRoutes indicates the current number of v6 active isis
         routes for this instance of the route table."
    ::= { vRtrStatEntry 38 }

vRtrV6RIPRoutes                  OBJECT-TYPE
    SYNTAX      Gauge32
    MAX-ACCESS  read-only
    STATUS      current
    DESCRIPTION
        "vRtrV6RIPRoutes indicates the current number of v6 rip routes for this
         instance of the route table."
    ::= { vRtrStatEntry 39 }

vRtrV6RIPActiveRoutes            OBJECT-TYPE
    SYNTAX      Gauge32
    MAX-ACCESS  read-only
    STATUS      current
    DESCRIPTION
        "vRtrV6RIPActiveRoutes indicates the current number of active v6 rip
         routes for this instance of the route table."
    ::= { vRtrStatEntry 40 }

vRtrV6AggregateRoutes            OBJECT-TYPE
    SYNTAX      Gauge32
    MAX-ACCESS  read-only
    STATUS      current
    DESCRIPTION
        "vRtrV6AggregateRoutes indicates the current number of v6 aggregate
         routes for this instance of the route table."
    ::= { vRtrStatEntry 41 }

vRtrV6AggregateActiveRoutes      OBJECT-TYPE
    SYNTAX      Gauge32
    MAX-ACCESS  read-only
    STATUS      current
    DESCRIPTION
        "vRtrV6AggregateActiveRoutes indicates the current number of active v6
         aggregate routes for this instance of the route table."
    ::= { vRtrStatEntry 42 }

vRtrV6StatConfiguredIfs          OBJECT-TYPE
    SYNTAX      Gauge32
    MAX-ACCESS  read-only
    STATUS      current
    DESCRIPTION
        "vRtrV6StatConfiguredIfs indicates the current number of v6 router
         interfaces configured on this virtual router."
    ::= { vRtrStatEntry 43 }

vRtrV6StatActiveIfs              OBJECT-TYPE
    SYNTAX      Gauge32
    MAX-ACCESS  read-only
    STATUS      current
    DESCRIPTION
        "vRtrV6StatActiveIfs indicates the current number of v6 router
         interfaces with vRtrIfAdminState equal 'inService' on this virtual
         router."
    ::= { vRtrStatEntry 44 }

vRtrV6StatIllegalLabels          OBJECT-TYPE
    SYNTAX      Counter32
    MAX-ACCESS  read-only
    STATUS      current
    DESCRIPTION
        "vRtrV6StatIllegalLabels indicates the number of illegally received v6
         labels on this virtual router."
    ::= { vRtrStatEntry 45 }

vRtrV6StatCurrNumRoutes          OBJECT-TYPE
    SYNTAX      Gauge32
    MAX-ACCESS  read-only
    STATUS      current
    DESCRIPTION
        "vRtrV6StatCurrNumRoutes indicates the current number of v6 routes in
         the VRF for this virtual router."
    ::= { vRtrStatEntry 46 }

vRtrV6StatBGPVpnRoutes           OBJECT-TYPE
    SYNTAX      Gauge32
    MAX-ACCESS  read-only
    STATUS      current
    DESCRIPTION
        "vRtrV6StatBGPVpnRoutes indicates the current number of VPN-IPV6 routes
         learned by MP-BGP for this virtual router."
    ::= { vRtrStatEntry 47 }

vRtrV6StatBGPVpnActiveRoutes     OBJECT-TYPE
    SYNTAX      Gauge32
    MAX-ACCESS  read-only
    STATUS      current
    DESCRIPTION
        "vRtrV6StatBGPVpnActiveRoutes indicates the current number of active
         VPN-IPV6 routes learned by MP-BGP for this virtual router."
    ::= { vRtrStatEntry 48 }

vRtrV6StatTotalLdpTunnels        OBJECT-TYPE
    SYNTAX      Gauge32
    MAX-ACCESS  read-only
    STATUS      current
    DESCRIPTION
        "vRtrV6StatTotalLdpTunnels indicates the current number of both active
         and inactive v6 LDP tunnels."
    ::= { vRtrStatEntry 49 }

vRtrV6StatTotalSdpTunnels        OBJECT-TYPE
    SYNTAX      Gauge32
    MAX-ACCESS  read-only
    STATUS      current
    DESCRIPTION
        "vRtrV6StatTotalSdpTunnels indicates the current number of both active
         and inactive v6 SDP tunnels."
    ::= { vRtrStatEntry 50 }

vRtrV6StatActiveLdpTunnels       OBJECT-TYPE
    SYNTAX      Gauge32
    MAX-ACCESS  read-only
    STATUS      current
    DESCRIPTION
        "vRtrV6StatActiveLdpTunnels indicates the current number of v6 rows in
         the vRtrInetTunnelTable where vRtrInetTunnelType has a value of 'ldp'."
    ::= { vRtrStatEntry 51 }

vRtrV6StatActiveSdpTunnels       OBJECT-TYPE
    SYNTAX      Gauge32
    MAX-ACCESS  read-only
    STATUS      current
    DESCRIPTION
        "vRtrV6StatActiveSdpTunnels indicates the current number of v6 rows in
         the vRtrInetTunnelTable where vRtrInetTunnelType has a value of 'sdp'."
    ::= { vRtrStatEntry 52 }

vRtrV6MulticastRoutes            OBJECT-TYPE
    SYNTAX      Gauge32
    MAX-ACCESS  read-only
    STATUS      current
    DESCRIPTION
        "vRtrV6MulticastRoutes indicates the current number of v6 rows in the
         vRtrPimNgGrpSrcTable."
    ::= { vRtrStatEntry 53 }

vRtrV6StatActiveNbrEntries       OBJECT-TYPE
    SYNTAX      Gauge32
    MAX-ACCESS  read-only
    STATUS      current
    DESCRIPTION
        "vRtrV6StatActiveNbrEntries indicates the number of active V6 neighbor
         discovery entries for the specified virtual router in the system."
    ::= { vRtrStatEntry 54 }

vRtrV6StatTotalNbrEntries        OBJECT-TYPE
    SYNTAX      Gauge32
    MAX-ACCESS  read-only
    STATUS      current
    DESCRIPTION
        "vRtrV6StatTotalNbrEntries indicates the total number of active
         and inactive v6 neighbor discovery entries for the specified
          virtual router in the system."
    ::= { vRtrStatEntry 55 }

vRtrSubMgmtRoutes                OBJECT-TYPE
    SYNTAX      Gauge32
    MAX-ACCESS  read-only
    STATUS      current
    DESCRIPTION
        "The value of vRtrSubMgmtRoutes  indicates the total number of
         subscriber management routes in the route Table."
    ::= { vRtrStatEntry 56 }

vRtrSubMgmtActiveRoutes          OBJECT-TYPE
    SYNTAX      Gauge32
    MAX-ACCESS  read-only
    STATUS      current
    DESCRIPTION
        "The value of vRtrSubMgmtActiveRoutes indicates the number of active
         subscriber management routes."
    ::= { vRtrStatEntry 57 }

vRtrStatTotalRsvpTunnels         OBJECT-TYPE
    SYNTAX      Gauge32
    MAX-ACCESS  read-only
    STATUS      current
    DESCRIPTION
        "The value of vRtrStatTotalRsvpTunnels indicates the current number of
         both active and inactive RSVP tunnels."
    ::= { vRtrStatEntry 58 }

vRtrStatActiveRsvpTunnels        OBJECT-TYPE
    SYNTAX      Gauge32
    MAX-ACCESS  read-only
    STATUS      current
    DESCRIPTION
        "The value of vRtrStatActiveRsvpTunnels indicates the current number of
         rows in the vRtrInetTunnelTable where vRtrInetTunnelType has a value
         of 'rsvp'."
    ::= { vRtrStatEntry 59 }

vRtrV6StatTotalRsvpTunnels       OBJECT-TYPE
    SYNTAX      Gauge32
    MAX-ACCESS  read-only
    STATUS      current
    DESCRIPTION
        "The value of vRtrV6StatTotalRsvpTunnels indicates the current number
         of both active and inactive IPv6 RSVP tunnels."
    ::= { vRtrStatEntry 60 }

vRtrV6StatActiveRsvpTunnels      OBJECT-TYPE
    SYNTAX      Gauge32
    MAX-ACCESS  read-only
    STATUS      current
    DESCRIPTION
        "The value of vRtrV6StatActiveRsvpTunnels indicates the current number
         of IPv6 rows in the vRtrInetTunnelTable where vRtrInetTunnelType has a
         value of 'rsvp'."
    ::= { vRtrStatEntry 61 }

vRtrHostRoutes                   OBJECT-TYPE
    SYNTAX      Gauge32
    MAX-ACCESS  read-only
    STATUS      current
    DESCRIPTION
        "The value of vRtrHostRoutes indicates the current number of direct
         routes with prefix value 32 for this instance of the route table."
    ::= { vRtrStatEntry 62 }

vRtrHostActiveRoutes             OBJECT-TYPE
    SYNTAX      Gauge32
    MAX-ACCESS  read-only
    STATUS      current
    DESCRIPTION
        "The value of vRtrHostActiveRoutes indicates the current number of
         active direct routes with prefix value 32 for this instance of the
         route table."
    ::= { vRtrStatEntry 63 }

vRtrV6HostRoutes                 OBJECT-TYPE
    SYNTAX      Gauge32
    MAX-ACCESS  read-only
    STATUS      current
    DESCRIPTION
        "The value of vRtrV6HostRoutes indicates the current number of v6
         direct routes with prefix value 128 for this instance of the route
         table."
    ::= { vRtrStatEntry 64 }

vRtrV6HostActiveRoutes           OBJECT-TYPE
    SYNTAX      Gauge32
    MAX-ACCESS  read-only
    STATUS      current
    DESCRIPTION
        "The value of vRtrV6HostActiveRoutes indicates the current number of v6
         active direct routes with prefix value 128 for this instance of the
         route table."
    ::= { vRtrStatEntry 65 }

vRtrStatLocalARPEntries          OBJECT-TYPE
    SYNTAX      Gauge32
    MAX-ACCESS  read-only
    STATUS      current
    DESCRIPTION
        "The value of vRtrStatLocalARPEntries indicates the total number of
         active and inactive local ARP entries for the specified virtual router
         in the system."
    ::= { vRtrStatEntry 66 }

vRtrStatStaticARPEntries         OBJECT-TYPE
    SYNTAX      Gauge32
    MAX-ACCESS  read-only
    STATUS      current
    DESCRIPTION
        "The value of vRtrStatStaticARPEntries indicates the total number of
         active and inactive static ARP entries for the specified virtual
         router in the system."
    ::= { vRtrStatEntry 67 }

vRtrStatDynamicARPEntries        OBJECT-TYPE
    SYNTAX      Gauge32
    MAX-ACCESS  read-only
    STATUS      current
    DESCRIPTION
        "The value of vRtrStatDynamicARPEntries indicates the total number of
         active and inactive dynamic ARP entries for the specified virtual
         router in the system."
    ::= { vRtrStatEntry 68 }

vRtrStatManagedARPEntries        OBJECT-TYPE
    SYNTAX      Gauge32
    MAX-ACCESS  read-only
    STATUS      current
    DESCRIPTION
        "The value of vRtrStatManagedARPEntries indicates the total number of
         active and inactive managed ARP entries for the specified virtual
         router in the system."
    ::= { vRtrStatEntry 69 }

vRtrStatInternalARPEntries       OBJECT-TYPE
    SYNTAX      Gauge32
    MAX-ACCESS  read-only
    STATUS      current
    DESCRIPTION
        "The value of vRtrStatInternalARPEntries indicates the total number of
         active and inactive internal ARP entries for the specified virtual
         router in the system."
    ::= { vRtrStatEntry 70 }

vRtrManagedRoutes                OBJECT-TYPE
    SYNTAX      Gauge32
    MAX-ACCESS  read-only
    STATUS      current
    DESCRIPTION
        "The value of vRtrManagedRoutes indicates the total number of active
         and inactive managed routes for the specified virtual router in the
         system."
    ::= { vRtrStatEntry 71 }

vRtrManagedActiveRoutes          OBJECT-TYPE
    SYNTAX      Gauge32
    MAX-ACCESS  read-only
    STATUS      current
    DESCRIPTION
        "The value of vRtrManagedActiveRoutes indicates the total number of
         active managed routes for the specified virtual router in the system."
    ::= { vRtrStatEntry 72 }

vRtrLDPRoutes                    OBJECT-TYPE
    SYNTAX      Gauge32
    MAX-ACCESS  read-only
    STATUS      current
    DESCRIPTION
        "vRtrLDPRoutes indicates the current number of ldp routes for this
         instance of the route table."
    ::= { vRtrStatEntry 73 }

vRtrLDPActiveRoutes              OBJECT-TYPE
    SYNTAX      Gauge32
    MAX-ACCESS  read-only
    STATUS      current
    DESCRIPTION
        "vRtrLDPActiveRoutes indicates the current number of active ldp routes
         for this instance of the route table."
    ::= { vRtrStatEntry 74 }

vRtrVPNLeakRoutes                OBJECT-TYPE
    SYNTAX      Gauge32
    MAX-ACCESS  read-only
    STATUS      current
    DESCRIPTION
        "vRtrVPNLeakRoutes indicates the current number of VPN Leak routes for
         this instance of the route table."
    ::= { vRtrStatEntry 75 }

vRtrVPNLeakActiveRoutes          OBJECT-TYPE
    SYNTAX      Gauge32
    MAX-ACCESS  read-only
    STATUS      current
    DESCRIPTION
        "vRtrVPNLeakActiveRoutes indicates the current number of active VPN
         Leak routes for this instance of the route table."
    ::= { vRtrStatEntry 76 }

vRtrV6VPNLeakRoutes              OBJECT-TYPE
    SYNTAX      Gauge32
    MAX-ACCESS  read-only
    STATUS      current
    DESCRIPTION
        "vRtrV6VPNLeakRoutes indicates the current number of v6 VPN Leak routes
         for this instance of the route table."
    ::= { vRtrStatEntry 77 }

vRtrV6VPNLeakActiveRoutes        OBJECT-TYPE
    SYNTAX      Gauge32
    MAX-ACCESS  read-only
    STATUS      current
    DESCRIPTION
        "vRtrV6VPNLeakActiveRoutes indicates the current number of v6 active
         VPN Leak routes for this instance of the route table."
    ::= { vRtrStatEntry 78 }

vRtrV6SubMgmtRoutes              OBJECT-TYPE
    SYNTAX      Gauge32
    MAX-ACCESS  read-only
    STATUS      current
    DESCRIPTION
        "vRtrV6SubMgmtRoutes indicates the current number of v6 subscriber
         management routes for this instance of the route table."
    ::= { vRtrStatEntry 79 }

vRtrV6SubMgmtActiveRoutes        OBJECT-TYPE
    SYNTAX      Gauge32
    MAX-ACCESS  read-only
    STATUS      current
    DESCRIPTION
        "vRtrV6SubMgmtActiveRoutes indicates the current number of v6 active
         subscriber management routes for this instance of the route table."
    ::= { vRtrStatEntry 80 }

vRtrMobileHostRoutes             OBJECT-TYPE
    SYNTAX      Gauge32
    MAX-ACCESS  read-only
    STATUS      current
    DESCRIPTION
        "The value of vRtrMobileHostRoutes indicates the current number of IPv4
         Mobile Host routes for this instance of the route table."
    ::= { vRtrStatEntry 81 }

vRtrMobileHostActiveRoutes       OBJECT-TYPE
    SYNTAX      Gauge32
    MAX-ACCESS  read-only
    STATUS      current
    DESCRIPTION
        "The value of vRtrMobileHostActiveRoutes indicates the current number
         of IPv4 active Mobile Host routes for this instance of the route
         table."
    ::= { vRtrStatEntry 82 }

vRtrV6MobileHostRoutes           OBJECT-TYPE
    SYNTAX      Gauge32
    MAX-ACCESS  read-only
    STATUS      current
    DESCRIPTION
        "The value of vRtrV6MobileHostRoutes indicates the current number of
         IPv6 Mobile Host routes for this instance of the route table."
    ::= { vRtrStatEntry 83 }

vRtrV6MobileHostActiveRoutes     OBJECT-TYPE
    SYNTAX      Gauge32
    MAX-ACCESS  read-only
    STATUS      current
    DESCRIPTION
        "The value of vRtrV6MobileHostActiveRoutes indicates the current number
         of IPv6 active Mobile Host routes for this instance of the route
         table."
    ::= { vRtrStatEntry 84 }

vRtrStatTotalBgpTunnels          OBJECT-TYPE
    SYNTAX      Gauge32
    MAX-ACCESS  read-only
    STATUS      current
    DESCRIPTION
        "vRtrStatTotalBgpTunnels indicates the current number of both active
         and inactive BGP tunnels."
    ::= { vRtrStatEntry 85 }

vRtrStatActiveBgpTunnels         OBJECT-TYPE
    SYNTAX      Gauge32
    MAX-ACCESS  read-only
    STATUS      current
    DESCRIPTION
        "vRtrStatActiveBgpTunnels indicates the current number of rows in the
         vRtrInetTunnelTable where vRtrInetTunnelType has a value of 'bgp'."
    ::= { vRtrStatEntry 86 }

vRtrNatRoutes                    OBJECT-TYPE
    SYNTAX      Gauge32
    MAX-ACCESS  read-only
    STATUS      current
    DESCRIPTION
        "The value of vRtrNatRoutes indicates the current number of IPv4 NAT
         (Network Address Translation) routes for this instance of the route
         table."
    ::= { vRtrStatEntry 87 }

vRtrNatActiveRoutes              OBJECT-TYPE
    SYNTAX      Gauge32
    MAX-ACCESS  read-only
    STATUS      current
    DESCRIPTION
        "The value of vRtrNatActiveRoutes indicates the current number of IPv4
         NAT routes for this instance of the route table."
    ::= { vRtrStatEntry 88 }

vRtrV6NatRoutes                  OBJECT-TYPE
    SYNTAX      Gauge32
    MAX-ACCESS  read-only
    STATUS      current
    DESCRIPTION
        "The value of vRtrV6NatRoutes indicates the current number of IPv6 NAT
         routes for this instance of the route table."
    ::= { vRtrStatEntry 89 }

vRtrV6NatActiveRoutes            OBJECT-TYPE
    SYNTAX      Gauge32
    MAX-ACCESS  read-only
    STATUS      current
    DESCRIPTION
        "The value of vRtrV6NatActiveRoutes indicates the current number of
         IPv6 active NAT routes for this instance of the route table."
    ::= { vRtrStatEntry 90 }

vRtrPeriodicRoutes               OBJECT-TYPE
    SYNTAX      Gauge32
    MAX-ACCESS  read-only
    STATUS      current
    DESCRIPTION
        "The value of vRtrPeriodicRoutes indicates the current number of
         periodic routes for this instance of the route table."
    ::= { vRtrStatEntry 91 }

vRtrPeriodicActiveRoutes         OBJECT-TYPE
    SYNTAX      Gauge32
    MAX-ACCESS  read-only
    STATUS      current
    DESCRIPTION
        "The value of vRtrPeriodicActiveRoutes indicates the current number of
         active periodic routes for this instance of the route table."
    ::= { vRtrStatEntry 92 }

vRtrV6PeriodicRoutes             OBJECT-TYPE
    SYNTAX      Gauge32
    MAX-ACCESS  read-only
    STATUS      current
    DESCRIPTION
        "The value of vRtrV6PeriodicRoutes indicates the current number of IPv6
         periodic routes for this instance of the route table."
    ::= { vRtrStatEntry 93 }

vRtrV6PeriodicActiveRoutes       OBJECT-TYPE
    SYNTAX      Gauge32
    MAX-ACCESS  read-only
    STATUS      current
    DESCRIPTION
        "The value of vRtrV6PeriodicActiveRoutes indicates the current number
         of active IPv6 periodic routes for this instance of the route table."
    ::= { vRtrStatEntry 94 }

vRtrV6ManagedRoutes              OBJECT-TYPE
    SYNTAX      Gauge32
    MAX-ACCESS  read-only
    STATUS      current
    DESCRIPTION
        "The value of vRtrV6ManagedRoutes indicates the total number of active
         and inactive IPv6 managed routes for the specified virtual router."
    ::= { vRtrStatEntry 95 }

vRtrV6ManagedActiveRoutes        OBJECT-TYPE
    SYNTAX      Gauge32
    MAX-ACCESS  read-only
    STATUS      current
    DESCRIPTION
        "The value of vRtrV6ManagedActiveRoutes indicates the total number of
         active IPv6 managed routes for the specified virtual router."
    ::= { vRtrStatEntry 96 }

vRtrStatTotalMplsTpTunnels       OBJECT-TYPE
    SYNTAX      Gauge32
    MAX-ACCESS  read-only
    STATUS      current
    DESCRIPTION
        "vRtrStatTotalMplsTpTunnels indicates the current number of both active
         and inactive MPLS-TP tunnels."
    ::= { vRtrStatEntry 97 }

vRtrStatActiveMplsTpTunnels      OBJECT-TYPE
    SYNTAX      Gauge32
    MAX-ACCESS  read-only
    STATUS      current
    DESCRIPTION
        "vRtrStatActiveMplsTpTunnels indicates the current number of active
         MPLS-TP tunnels."
    ::= { vRtrStatEntry 98 }

vRtrV6Dhcpv6PdRoutes             OBJECT-TYPE
    SYNTAX      Gauge32
    MAX-ACCESS  read-only
    STATUS      current
    DESCRIPTION
        "The value of vRtrV6Dhcpv6PdRoutes indicates the current number of IPv6
         DHCPv6 delegated prefix routes for this instance of the route table."
    ::= { vRtrStatEntry 99 }

vRtrV6Dhcpv6PdActiveRoutes       OBJECT-TYPE
    SYNTAX      Gauge32
    MAX-ACCESS  read-only
    STATUS      current
    DESCRIPTION
        "The value of vRtrV6Dhcpv6PdActiveRoutes indicates the current number
         of active IPv6 DHCPv6 delegated prefix routes for this instance of the
         route table."
    ::= { vRtrStatEntry 100 }

vRtrV6Dhcpv6NaRoutes             OBJECT-TYPE
    SYNTAX      Gauge32
    MAX-ACCESS  read-only
    STATUS      current
    DESCRIPTION
        "The value of vRtrV6Dhcpv6NaRoutes indicates the current number of IPv6
         DHCPv6 non-temporary address routes for this instance of the route
         table."
    ::= { vRtrStatEntry 101 }

vRtrV6Dhcpv6NaActiveRoutes       OBJECT-TYPE
    SYNTAX      Gauge32
    MAX-ACCESS  read-only
    STATUS      current
    DESCRIPTION
        "The value of vRtrV6Dhcpv6NaActiveRoutes indicates the current number
         of active IPv6 DHCPv6 non-temporary address routes for this instance
         of the route table."
    ::= { vRtrStatEntry 102 }

vRtrV6Dhcpv6TaRoutes             OBJECT-TYPE
    SYNTAX      Gauge32
    MAX-ACCESS  read-only
    STATUS      current
    DESCRIPTION
        "The value of vRtrV6Dhcpv6TaRoutes indicates the current number of IPv6
         DHCPv6 temporary address routes for this instance of the route table."
    ::= { vRtrStatEntry 103 }

vRtrV6Dhcpv6TaActiveRoutes       OBJECT-TYPE
    SYNTAX      Gauge32
    MAX-ACCESS  read-only
    STATUS      current
    DESCRIPTION
        "The value of vRtrV6Dhcpv6TaActiveRoutes indicates the current number
         of active IPv6 DHCPv6 temporary address routes for this instance of
         the route table."
    ::= { vRtrStatEntry 104 }

vRtrV6Dhcpv6PdExclRoutes         OBJECT-TYPE
    SYNTAX      Gauge32
    MAX-ACCESS  read-only
    STATUS      current
    DESCRIPTION
        "The value of vRtrV6Dhcpv6PdExclRoutes indicates the current number of
         IPv6 DHCPv6 delegated prefix exclude routes for this instance of the
         route table."
    ::= { vRtrStatEntry 105 }

vRtrV6Dhcpv6PdExclActiveRoutes   OBJECT-TYPE
    SYNTAX      Gauge32
    MAX-ACCESS  read-only
    STATUS      current
    DESCRIPTION
        "The value of vRtrV6Dhcpv6PdExclActiveRoutes indicates the current
         number of active IPv6 DHCPv6 delegated prefix exclude routes for this
         instance of the route table."
    ::= { vRtrStatEntry 106 }

vRtrIPsecRoutes                  OBJECT-TYPE
    SYNTAX      Gauge32
    MAX-ACCESS  read-only
    STATUS      current
    DESCRIPTION
        "The value of the object vRtrIPsecRoutes indicates the current number
         of IPsec routes for this instance of the route table."
    ::= { vRtrStatEntry 107 }

vRtrIPsecActiveRoutes            OBJECT-TYPE
    SYNTAX      Gauge32
    MAX-ACCESS  read-only
    STATUS      current
    DESCRIPTION
        "The value of the object vRtrIPsecActiveRoutes indicates the current
         number of active IPsec routes for this instance of the route table."
    ::= { vRtrStatEntry 108 }

vRtrStatBGPEVPNARPEntries        OBJECT-TYPE
    SYNTAX      Gauge32
    MAX-ACCESS  read-only
    STATUS      current
    DESCRIPTION
        "The value of vRtrStatBGPEVPNARPEntries indicates the total number of
         BGP EVPN ARP entries for the specified virtual router in the system."
    ::= { vRtrStatEntry 109 }

vRtrStatBGPEvpnRoutes            OBJECT-TYPE
    SYNTAX      Gauge32
    MAX-ACCESS  read-only
    STATUS      obsolete
    DESCRIPTION
        "The value of vRtrStatBGPEvpnRoutes indicates the total number of IPv4
         BGP EVPN route entries for the specified virtual router in the system.

         This object is replaced by vRtrBgpEvpnIffRoutes in SR release 20.10.R1
         and obsoleted in 21.2.R1."
    ::= { vRtrStatEntry 110 }

vRtrStatBGPEvpnActiveRoutes      OBJECT-TYPE
    SYNTAX      Gauge32
    MAX-ACCESS  read-only
    STATUS      obsolete
    DESCRIPTION
        "The value of vRtrStatBGPEvpnActiveRoutes indicates the total number of
         active IPv4 BGP EVPN route entries for the specified virtual router in
         the system.

         This object is replaced by vRtrBgpEvpnIffActRoutes in SR release
         20.10.R1 and obsoleted in 21.2.R1."
    ::= { vRtrStatEntry 111 }

vRtrV6StatBGPEvpnRoutes          OBJECT-TYPE
    SYNTAX      Gauge32
    MAX-ACCESS  read-only
    STATUS      obsolete
    DESCRIPTION
        "The value of vRtrV6StatBGPEvpnRoutes indicates the total number of
         IPv6 BGP EVPN route entries for the specified virtual router in the
         system.

         This object is replaced by vRtrV6BgpEvpnIffRoutes in SR release
         20.10.R1 and obsoleted in 21.2.R1."
    ::= { vRtrStatEntry 112 }

vRtrV6StatBGPEvpnActiveRoutes    OBJECT-TYPE
    SYNTAX      Gauge32
    MAX-ACCESS  read-only
    STATUS      obsolete
    DESCRIPTION
        "The value of vRtrV6StatBGPEvpnActiveRoutes indicates the total number
         of active IPv6 BGP EVPN route entries for the specified virtual router
         in the system.

         This object is replaced by vRtrV6BgpEvpnIffActRoutes in SR release
         20.10.R1 and obsoleted in 21.2.R1."
    ::= { vRtrStatEntry 113 }

vRtrMcastIpv4StatBGPEvpnRoutes   OBJECT-TYPE
    SYNTAX      Gauge32
    MAX-ACCESS  read-only
    STATUS      obsolete
    DESCRIPTION
        "The value of vRtrMcastIpv4StatBGPEvpnRoutes indicates the total number
         of IPv4 Multicast BGP EVPN route entries for the specified virtual
         router in the system."
    ::= { vRtrStatEntry 114 }

vRtrMcastIpv4StatBGPEvpnActvRts  OBJECT-TYPE
    SYNTAX      Gauge32
    MAX-ACCESS  read-only
    STATUS      obsolete
    DESCRIPTION
        "The value of vRtrMcastIpv4StatBGPEvpnActvRts indicates the total
         number of active IPv4 Multicast BGP EVPN route entries for the
         specified virtual router in the system."
    ::= { vRtrStatEntry 115 }

vRtrMcastIpv6StatBGPEvpnRoutes   OBJECT-TYPE
    SYNTAX      Gauge32
    MAX-ACCESS  read-only
    STATUS      obsolete
    DESCRIPTION
        "The value of vRtrMcastIpv6StatBGPEvpnRoutes indicates the total number
         of IPv6 Multicast BGP EVPN route entries for the specified virtual
         router in the system."
    ::= { vRtrStatEntry 116 }

vRtrMcastIpv6StatBGPEvpnActvRts  OBJECT-TYPE
    SYNTAX      Gauge32
    MAX-ACCESS  read-only
    STATUS      obsolete
    DESCRIPTION
        "The value of vRtrMcastIpv6StatBGPEvpnActvRts indicates the total
         number of active IPv6 Multicast BGP EVPN route entries for the
         specified virtual router in the system."
    ::= { vRtrStatEntry 117 }

vRtrV6IPsecRoutes                OBJECT-TYPE
    SYNTAX      Gauge32
    MAX-ACCESS  read-only
    STATUS      current
    DESCRIPTION
        "The value of the object vRtrV6IPsecRoutes indicates the current number
         of IPv6 IPsec routes for this instance of the route table."
    ::= { vRtrStatEntry 118 }

vRtrV6IPsecActiveRoutes          OBJECT-TYPE
    SYNTAX      Gauge32
    MAX-ACCESS  read-only
    STATUS      current
    DESCRIPTION
        "The value of the object vRtrV6IPsecActiveRoutes indicates the current
         number of active IPv6 IPsec routes for this instance of the route
         table."
    ::= { vRtrStatEntry 119 }

vRtrStatBGPLabelV4Routes         OBJECT-TYPE
    SYNTAX      Gauge32
    MAX-ACCESS  read-only
    STATUS      current
    DESCRIPTION
        "The value of vRtrStatBGPLabelV4Routes indicates the total number of
         labeled IPv4 BGP route entries for the specified virtual router in the
         system."
    ::= { vRtrStatEntry 120 }

vRtrStatBGPLabelV4ActiveRoutes   OBJECT-TYPE
    SYNTAX      Gauge32
    MAX-ACCESS  read-only
    STATUS      current
    DESCRIPTION
        "The value of vRtrStatBGPLabelV4ActiveRoutes indicates the total number
         of active labeled IPv4 BGP route entries for the specified virtual
         router in the system."
    ::= { vRtrStatEntry 121 }

vRtrStatBGPLabelV6Routes         OBJECT-TYPE
    SYNTAX      Gauge32
    MAX-ACCESS  read-only
    STATUS      current
    DESCRIPTION
        "The value of vRtrStatBGPLabelV6Routes indicates the total number of
         labeled IPv6 BGP route entries for the specified virtual router in the
         system."
    ::= { vRtrStatEntry 122 }

vRtrStatBGPLabelV6ActiveRoutes   OBJECT-TYPE
    SYNTAX      Gauge32
    MAX-ACCESS  read-only
    STATUS      current
    DESCRIPTION
        "The value of vRtrStatBGPLabelV6ActiveRoutes indicates the total number
         of active labeled IPv6 BGP route entries for the specified virtual
         router in the system."
    ::= { vRtrStatEntry 123 }

vRtrStatTotalBgpEpeTunnels       OBJECT-TYPE
    SYNTAX      Gauge32
    MAX-ACCESS  read-only
    STATUS      current
    DESCRIPTION
        "vRtrStatTotalBgpEpeTunnels indicates the current number of both active
         and inactive BGP EPE tunnels."
    ::= { vRtrStatEntry 124 }

vRtrStatActiveBgpEpeTunnels      OBJECT-TYPE
    SYNTAX      Gauge32
    MAX-ACCESS  read-only
    STATUS      current
    DESCRIPTION
        "vRtrStatActiveBgpEpeTunnels indicates the current number of active BGP
         EPE tunnels."
    ::= { vRtrStatEntry 125 }

vRtrStatTotalBgpEpeV6Tunnels     OBJECT-TYPE
    SYNTAX      Gauge32
    MAX-ACCESS  read-only
    STATUS      current
    DESCRIPTION
        "vRtrStatTotalBgpEpeV6Tunnels indicates the current number of both
         active and inactive BGP EPE tunnels for IPv6."
    ::= { vRtrStatEntry 126 }

vRtrStatActiveBgpEpeV6Tunnels    OBJECT-TYPE
    SYNTAX      Gauge32
    MAX-ACCESS  read-only
    STATUS      current
    DESCRIPTION
        "vRtrStatActiveBgpEpeV6Tunnels indicates the current number of active
         BGP EPE tunnels for IPv6."
    ::= { vRtrStatEntry 127 }

vRtrStatTotalBgpV6Tunnels        OBJECT-TYPE
    SYNTAX      Gauge32
    MAX-ACCESS  read-only
    STATUS      current
    DESCRIPTION
        "vRtrStatTotalBgpV6Tunnels indicates the current number of both active
         and inactive BGP tunnels for IPv6."
    ::= { vRtrStatEntry 128 }

vRtrStatActiveBgpV6Tunnels       OBJECT-TYPE
    SYNTAX      Gauge32
    MAX-ACCESS  read-only
    STATUS      current
    DESCRIPTION
        "vRtrStatActiveBgpV6Tunnels indicates the current number of active BGP
         tunnels for IPv6."
    ::= { vRtrStatEntry 129 }

vRtrIfTotalNumber                OBJECT-TYPE
    SYNTAX      Integer32 (0..65535)
    MAX-ACCESS  read-only
    STATUS      current
    DESCRIPTION
        "The number of router interfaces configured in this system."
    ::= { tmnxVRtrObjs 3 }

vRtrIfTable                      OBJECT-TYPE
    SYNTAX      SEQUENCE OF VRtrIfEntry
    MAX-ACCESS  not-accessible
    STATUS      current
    DESCRIPTION
        "The vRtrIfTable has an entry for each router interface configured in
         the system."
    ::= { tmnxVRtrObjs 4 }

vRtrIfEntry                      OBJECT-TYPE
    SYNTAX      VRtrIfEntry
    MAX-ACCESS  not-accessible
    STATUS      current
    DESCRIPTION
        "Each row entry represents a virtual router interface in the system.
         Entries can be created and deleted via SNMP SET operations using the
         vRtrIfRowStatus variable."
    INDEX       {
        vRtrID,
        vRtrIfIndex
    }
    ::= { vRtrIfTable 1 }

VRtrIfEntry                      ::= SEQUENCE
{
    vRtrIfIndex                      InterfaceIndex,
    vRtrIfRowStatus                  RowStatus,
    vRtrIfType                       INTEGER,
    vRtrIfName                       TNamedItem,
    vRtrIfPortID                     TmnxPortID,
    vRtrIfChannelID                  Unsigned32,
    vRtrIfEncapValue                 TmnxEncapVal,
    vRtrIfAdminState                 TmnxAdminState,
    vRtrIfOperState                  TmnxOperState,
    vRtrIfAlias                      DisplayString,
    vRtrIfPhysicalAddress            MacAddress,
    vRtrIfArpTimeout                 Unsigned32,
    vRtrIfIcmpMaskReply              TruthValue,
    vRtrIfIcmpRedirects              TruthValue,
    vRtrIfIcmpNumRedirects           Unsigned32,
    vRtrIfIcmpRedirectsTime          Unsigned32,
    vRtrIfIcmpUnreachables           TruthValue,
    vRtrIfIcmpNumUnreachables        Unsigned32,
    vRtrIfIcmpUnreachablesTime       Unsigned32,
    vRtrIfIcmpTtlExpired             TruthValue,
    vRtrIfIcmpNumTtlExpired          Unsigned32,
    vRtrIfIcmpTtlExpiredTime         Unsigned32,
    vRtrIfNtpBroadcast               TruthValue,
    vRtrIfUnnumbered                 IpAddress,
    vRtrIfMtu                        Unsigned32,
    vRtrIfQosPolicyId                TNetworkPolicyID,
    vRtrIfIngressFilterId            TFilterID,
    vRtrIfEgressFilterId             TFilterID,
    vRtrIfDirectedBroadcast          TruthValue,
    vRtrIfMplsStatus                 TmnxStatus,
    vRtrIfUnnumberedIf               DisplayString,
    vRtrIfCflowd                     INTEGER,
    vRtrIfVPNClass                   INTEGER,
    vRtrIfDescription                TItemLongDescription,
    vRtrIfProtocol                   BITS,
    vRtrIfTosMarkingTrusted          TruthValue,
    vRtrIfServiceId                  TmnxServId,
    vRtrIfArpPopulate                INTEGER,
    vRtrIfIPv6ConfigAllowed          TruthValue,
    vRtrIfIPv6OperState              TmnxOperState,
    vRtrIfIPv6IngressFilterId        TFilterID,
    vRtrIfIPv6EgressFilterId         TFilterID,
    vRtrIfIcmpV6Redirects            TruthValue,
    vRtrIfIcmpV6NumRedirects         Unsigned32,
    vRtrIfIcmpV6RedirectsTime        Unsigned32,
    vRtrIfIcmpV6Unreachables         TruthValue,
    vRtrIfIcmpV6NumUnreachables      Unsigned32,
    vRtrIfIcmpV6UnreachablesTime     Unsigned32,
    vRtrIfIcmpV6TimeExceeded         TruthValue,
    vRtrIfIcmpV6NumTimeExceeded      Unsigned32,
    vRtrIfIcmpV6TimeExceededTime     Unsigned32,
    vRtrIfIcmpV6PktTooBig            TruthValue,
    vRtrIfIcmpV6NumPktTooBig         Unsigned32,
    vRtrIfIcmpV6PktTooBigTime        Unsigned32,
    vRtrIfIcmpV6ParamProblem         TruthValue,
    vRtrIfIcmpV6NumParamProblem      Unsigned32,
    vRtrIfIcmpV6ParamProblemTime     Unsigned32,
    vRtrIfLinkLocalAddressType       InetAddressType,
    vRtrIfLinkLocalAddress           InetAddress,
    vRtrIfLinkLocalAddressState      TmnxInetAddrState,
    vRtrIfLastOperStateChange        TimeStamp,
    vRtrIfOperMtu                    Unsigned32,
    vRtrIfGlobalIndex                Unsigned32,
    vRtrIfDelaySeconds               Unsigned32,
    vRtrIfDelayUpTimer               Integer32,
    vRtrIfLocalDhcpServerName        TNamedItemOrEmpty,
    vRtrIfInitDelayEnable            TruthValue,
    vRtrIfCpmProtPolicyId            TCpmProtPolicyID,
    vRtrIfCpmProtUncfgdProtoDropCnt  Gauge32,
    vRtrIfLdpSyncTimer               Unsigned32,
    vRtrIfStripLabel                 TruthValue,
    vRtrIfuRPFCheckState             TmnxEnabledDisabled,
    vRtrIfuRPFCheckMode              TmnxUrpfCheckMode,
    vRtrIfQosQGrp                    TNamedItemOrEmpty,
    vRtrIfAdminLinkLocalAddrType     InetAddressType,
    vRtrIfAdminLinkLocalAddr         InetAddress,
    vRtrIfAdmLnkLclAddrPreferred     TruthValue,
    vRtrIfOperDownReason             BITS
}

vRtrIfIndex                      OBJECT-TYPE
    SYNTAX      InterfaceIndex
    MAX-ACCESS  accessible-for-notify
    STATUS      current
    DESCRIPTION
        "The unique value which identifies this interface of this virtual
         router in the Tmnx system. This field provides an identifier for
         virtual router interfaces similar to the ifIndex values used in the
         mib-2 interfaces table for physical interfaces. The vRtrIfIndex values
         can be reused for different virtual routers, but are unique within
         those entries with the same vRtrID.

         The vRtrIfIndex value for each virtual interface must remain constant
         at least from one re-initialization of the system management processor
         to the next."
    ::= { vRtrIfEntry 1 }

vRtrIfRowStatus                  OBJECT-TYPE
    SYNTAX      RowStatus
    MAX-ACCESS  read-create
    STATUS      current
    DESCRIPTION
        "The row status.  The creation or deletion of a router interface entry
         causes creation or deletion of corresponding entries in other Tmnx MIB
         tables with the same vRtrID and vRtrIfIndex values, such as the
         vRtrIpAddrTable.  The router interface is associated to a physical port
         interface through the vRtrIfPortID and vRtrIfEncapValue variables. The
         RowStatus cannot be SET to 'active' unless vRtrIfName has been
         initialized."
    ::= { vRtrIfEntry 2 }

vRtrIfType                       OBJECT-TYPE
    SYNTAX      INTEGER {
        network               (1),
        service               (2),
        serviceIes            (3),
        serviceRtdVpls        (4),
        serviceVprn           (5),
        serviceIesSubscriber  (6),
        serviceIesGroup       (7),
        serviceVprnSubscriber (8),
        serviceVprnGroup      (9),
        serviceIesRedundant   (10),
        serviceVprnRedundant  (11),
        serviceVpls           (12),
        serviceIesCem         (13),
        serviceVprnCem        (14),
        serviceVprnIPsec      (15),
        serviceVprnIPMirror   (16),
        serviceVideo          (17),
        serviceVplsVideo      (18),
        multiHomingPrimary    (19),
        multiHomingSecondary  (20),
        serviceIesTunnel      (21),
        serviceIpReas         (22),
        networkIpReas         (23),
        networkVprn           (24),
        reserved25            (25),
        serviceIesAarp        (26),
        serviceVprnAarp       (27),
        serviceIesAa          (28),
        serviceVprnAa         (29),
        unnumMplsTp           (30),
        gmplsLoopback         (31),
        controlTunnel         (32),
        pdn                   (33),
        serviceIesDms         (34),
        serviceVprnDms        (35),
        serviceIesIpTunnel    (36),
        serviceVprnIpTunnel   (37)
    }
    MAX-ACCESS  read-create
    STATUS      current
    DESCRIPTION
        "The value of vRtrIfType specifies the type of this interface.
         Different virtual router interface types are defined as follows:

         network               - defined on a network port.
         service               - used internally.
         serviceIes            - defined on a SAP or Spoke SDP.
         serviceRtdVpls        - obsoleted.
         serviceVprn           - defined on a SAP or Spoke SDP.
         serviceIesSubscriber  - used internally.
         serviceIesGroup       - defined on a SAP
         serviceVprnSubscriber - used internally.
         serviceVprnGroup      - defined on a SAP.
         serviceIesRedundant   - defined on a Spoke SDP.
         serviceVprnRedundant  - defined on a Spoke SDP.
         serviceVpls           - defined on an IP endpoint for VPLS.
         serviceIesCem         - defined on a SAP. --not supported
         serviceVprnCem        - defined on a SAP. --not supported
         serviceVprnIPsec      - defined on a SAP.
         serviceVprnIPMirror   - defined on a Mirror.
         serviceVideo          - defined on a video SAP.
         serviceVplsVideo      - defined on an IP endpoint for video interface
                                 for VPLS.
         multiHomingPrimary    - obsoleted.
         multiHomingSecondary  - obsoleted.
         serviceIesTunnel      - defined on a SAP.
         serviceIpReas         - defined on a network port.
         networkIpReas         - defined on a network port.
         networkVprn           - network interface defined in a VPRN.
         reserved25            - threat management service interface.
         serviceIesAarp        - defined on an AARP (Asymmetry Removal) Spoke SDP.
         serviceVprnAarp       - defined on an AARP Spoke SDP.
         serviceIesAa          - defined on an AA (Application Assurance) SAP.
         serviceVprnAa         - defined on an AA SAP.
         unnumMplsTp           - defined for an unnumbered mpls tp interface.
         gmplsLoopback         - obsoleted.
         controlTunnel         - obsoleted.
         pdn                   - defined for a packet data network interface.
         serviceIesDms         - defined on a DMS (Defender Mitigation System) SAP.
         serviceVprnDms        - defined on a DMS SAP.
         serviceIesIpTunnel    - defined for an IP-GRE tunnel interface.
         serviceVprnIpTunnel   - defined for an IP-GRE tunnel interface."
    ::= { vRtrIfEntry 3 }

vRtrIfName                       OBJECT-TYPE
    SYNTAX      TNamedItem
    MAX-ACCESS  read-create
    STATUS      current
    DESCRIPTION
        "The administrative name assigned this router interface. The interface
         name must be unique among entries with the same vRtrID value. In order
         for row creation to succeed, a value must also be assigned to
         vRtrIfName."
    ::= { vRtrIfEntry 4 }

vRtrIfPortID                     OBJECT-TYPE
    SYNTAX      TmnxPortID
    MAX-ACCESS  read-create
    STATUS      current
    DESCRIPTION
        "The physical port to which this interface is bound. If vRtrIfPortID is
         zero (0), then there is no binding between this virtual router
         interface and a physical port. Once an interface has been bound to a
         port, several steps are required to change the binding to some other
         TmnxPortID value. vRtrIfAdminState must be 'outOfService';
         vRtrIfPortID must be set to zero (0) to disassociate the interface
         from the original port binding; finally, set vRtrIfPortID to the value
         for the new port binding.

         Setting vRtrIfPortID to 0x20000001 indicates that this interface is
         the system interface for the device."
    DEFVAL      { 0 }
    ::= { vRtrIfEntry 5 }

vRtrIfChannelID                  OBJECT-TYPE
    SYNTAX      Unsigned32 (0..64)
    MAX-ACCESS  read-create
    STATUS      obsolete
    DESCRIPTION
        "When the physical port, vRtrIfPortID, is a SONET port, vRtrIfChannelID
         is the STSx channel number used by this interface. If vRtrIfPortID is
         not a SONET port or the interface has not yet been bound to a physical
         port, vRtrIfChannelID will be zero (0).

         This object was obsoleted in release 5.0."
    DEFVAL      { 0 }
    ::= { vRtrIfEntry 6 }

vRtrIfEncapValue                 OBJECT-TYPE
    SYNTAX      TmnxEncapVal
    MAX-ACCESS  read-create
    STATUS      current
    DESCRIPTION
        "The value of the label used along with vRtrIfPortID to identify a SAP
         on the specified access port."
    DEFVAL      { 0 }
    ::= { vRtrIfEntry 7 }

vRtrIfAdminState                 OBJECT-TYPE
    SYNTAX      TmnxAdminState
    MAX-ACCESS  read-create
    STATUS      current
    DESCRIPTION
        "The desired administrative state for this router interface."
    DEFVAL      { inService }
    ::= { vRtrIfEntry 8 }

vRtrIfOperState                  OBJECT-TYPE
    SYNTAX      TmnxOperState
    MAX-ACCESS  read-only
    STATUS      current
    DESCRIPTION
        "The current operational status of this router interface."
    ::= { vRtrIfEntry 9 }

vRtrIfAlias                      OBJECT-TYPE
    SYNTAX      DisplayString (SIZE (0..32))
    MAX-ACCESS  read-create
    STATUS      obsolete
    DESCRIPTION
        "An alternative administrative name assigned to this router interface."
    DEFVAL      { ''H }
    ::= { vRtrIfEntry 10 }

vRtrIfPhysicalAddress            OBJECT-TYPE
    SYNTAX      MacAddress
    MAX-ACCESS  read-create
    STATUS      current
    DESCRIPTION
        "The interface's address at its protocol sub-layer. For example, for an
         802.x interface, this object normally contains a MAC address. The
         interface's media-specific MIB must define the bit and byte ordering
         and the format of the value of this object."
    DEFVAL      { '000000000000'H }
    ::= { vRtrIfEntry 11 }

vRtrIfArpTimeout                 OBJECT-TYPE
    SYNTAX      Unsigned32 (0..65535)
    UNITS       "seconds"
    MAX-ACCESS  read-create
    STATUS      current
    DESCRIPTION
        "The value of vRtrIfArpTimeout determines how long an ARP entry
         associated with this interface remains in the ARP cache. When
         vRtrIfArpTimeout has a value of zero, '0', the entry will never be
         cleared from the cache."
    DEFVAL      { 14400 }
    ::= { vRtrIfEntry 12 }

vRtrIfIcmpMaskReply              OBJECT-TYPE
    SYNTAX      TruthValue
    MAX-ACCESS  read-create
    STATUS      current
    DESCRIPTION
        "When vRtrIfIcmpMaskReply is set to 'true', a reply will be
         issued when this node is requested for the network mask for this
         subnet.  The requesting node must be attached to the local
         network.  When vRtrIfIcmpMaskReply is set to 'false', no reply
         is  issued if an ICMP mask request is received."
    DEFVAL      { true }
    ::= { vRtrIfEntry 13 }

vRtrIfIcmpRedirects              OBJECT-TYPE
    SYNTAX      TruthValue
    MAX-ACCESS  read-create
    STATUS      current
    DESCRIPTION
        "When vRtrIfIcmpRedirects is set to 'true', ICMP redirects are
         generated when routes are not optimal on this router and another
         router on the same subnetwork has a better route in order to
         alert that node that a better route is available.  When
         vRtrIfIcmpRedirects is set to 'false', ICMP redirects are not
         generated."
    DEFVAL      { true }
    ::= { vRtrIfEntry 14 }

vRtrIfIcmpNumRedirects           OBJECT-TYPE
    SYNTAX      Unsigned32 (10..1000)
    MAX-ACCESS  read-create
    STATUS      current
    DESCRIPTION
        "The value of vRtrIfIcmpNumRedirects limits the number of redirects
         issued per the time frame specified in vRtrIfIcmpRedirectsTime."
    DEFVAL      { 100 }
    ::= { vRtrIfEntry 15 }

vRtrIfIcmpRedirectsTime          OBJECT-TYPE
    SYNTAX      Unsigned32 (1..60)
    UNITS       "seconds"
    MAX-ACCESS  read-create
    STATUS      current
    DESCRIPTION
        "The value of vRtrIfIcmpRedirectsTime determines the time frame in
         seconds that is used to limit the number of redirects issued per time
         frame."
    DEFVAL      { 10 }
    ::= { vRtrIfEntry 16 }

vRtrIfIcmpUnreachables           OBJECT-TYPE
    SYNTAX      TruthValue
    MAX-ACCESS  read-create
    STATUS      current
    DESCRIPTION
        "When vRtrIfIcmpUnreachables is set to 'true', ICMP host and network
         unreachable messages are generated by this interface. When
         vRtrIfIcmpUnreachables is set to 'false', ICMP host and network
         unreachable messages are not sent."
    DEFVAL      { true }
    ::= { vRtrIfEntry 17 }

vRtrIfIcmpNumUnreachables        OBJECT-TYPE
    SYNTAX      Unsigned32 (10..2000)
    MAX-ACCESS  read-create
    STATUS      current
    DESCRIPTION
        "The value of vRtrIfIcmpNumUnreachables determines how many destination
         unreachable messages are issued in the time frame specified by
         vRtrIfIcmpUnreachablesTime."
    DEFVAL      { 100 }
    ::= { vRtrIfEntry 18 }

vRtrIfIcmpUnreachablesTime       OBJECT-TYPE
    SYNTAX      Unsigned32 (1..60)
    UNITS       "seconds"
    MAX-ACCESS  read-create
    STATUS      current
    DESCRIPTION
        "The value of vRtrIfIcmpUnreachablesTime sets the time frame in seconds
         that is used to limit the number of destination unreachable messages
         issued per time frame."
    DEFVAL      { 10 }
    ::= { vRtrIfEntry 19 }

vRtrIfIcmpTtlExpired             OBJECT-TYPE
    SYNTAX      TruthValue
    MAX-ACCESS  read-create
    STATUS      current
    DESCRIPTION
        "When vRtrIfIcmpTtlExpired is set to 'true', the rate that ttl-expired
         messages by this interface is throttled based on the values of
         vRtrIfIcmpNumTtlExpired and vRtrIfIcmpTtlExpiredTime. When
         vRtrIfIcmpTtlExpired is set to 'false', unlimited ttl-expired messages
         are sent."
    DEFVAL      { true }
    ::= { vRtrIfEntry 20 }

vRtrIfIcmpNumTtlExpired          OBJECT-TYPE
    SYNTAX      Unsigned32 (10..2000)
    MAX-ACCESS  read-create
    STATUS      current
    DESCRIPTION
        "The value of vRtrIfIcmpNumTtlExpired defines how many ttl-expired
         messages will be issued in the time frame specified by
         vRtrIfIcmpTtlExpiredTime."
    DEFVAL      { 100 }
    ::= { vRtrIfEntry 21 }

vRtrIfIcmpTtlExpiredTime         OBJECT-TYPE
    SYNTAX      Unsigned32 (1..60)
    UNITS       "seconds"
    MAX-ACCESS  read-create
    STATUS      current
    DESCRIPTION
        "The value of vRtrIfIcmpTtlExpiredTime sets the time frame in seconds
         that is used to limit the number of ttl-expired messages issued by
         this interface with the specified time frame."
    DEFVAL      { 10 }
    ::= { vRtrIfEntry 22 }

vRtrIfNtpBroadcast               OBJECT-TYPE
    SYNTAX      TruthValue
    MAX-ACCESS  read-create
    STATUS      obsolete
    DESCRIPTION
        "When vRtrIfNtpBroadcast is set to 'true', NTP/SNTP broadcasts will be
         received on this interface."
    DEFVAL      { false }
    ::= { vRtrIfEntry 23 }

vRtrIfUnnumbered                 OBJECT-TYPE
    SYNTAX      IpAddress
    MAX-ACCESS  read-create
    STATUS      current
    DESCRIPTION
        "The IP address to be used when generating packets on this interface.
         This variable is complemented by vRtrIfUnnumbered. If
         vRtrIfUnnumberedIf is a null string and vRtrIfUnnumbered is '0.0.0.0'
         it implies that no unnumbered interface is configured. At any instant
         only one of the two members can be non-null.

         A value of '255.255.255.255' implies the use of system-ip. It is
         strongly suggested to use the node's system IP address as it is not
         associated with a particular physical interface and is therefore
         always reachable."
    DEFVAL      { '00000000'H }
    ::= { vRtrIfEntry 24 }

vRtrIfMtu                        OBJECT-TYPE
    SYNTAX      Unsigned32 (0 | 512..9786)
    UNITS       "bytes"
    MAX-ACCESS  read-create
    STATUS      current
    DESCRIPTION
        "The value of vRtrIfMtu is used to reflect the MTU size of this
         interface in the header of an ICMP MTU exceeded message when a packet
         is too large to be transmitted on this interface. The default size is
         calculated by subtracting the DLC header size from the physical MTU
         size of the interface.

         When a SNMP SET request is received with a value of zero (0), the
         agent actually sets vRtrIfMtu to the calculated default size."
    DEFVAL      { 0 }
    ::= { vRtrIfEntry 25 }

vRtrIfQosPolicyId                OBJECT-TYPE
    SYNTAX      TNetworkPolicyID
    MAX-ACCESS  read-create
    STATUS      obsolete
    DESCRIPTION
        "The value of vRtrIfQosPolicyId associates a pre-existing
         network-policy-id to a network interface. Packets are marked using qos
         policies on edge switches; invoking a qos policy on a network port
         allows for the packets that match the policy criteria to be remarked.

         If this entry indicates a service virtual router interface or the
         special out-of-band management interface, this object is meaningless
         and is not applied to the interface.

         This object is obsoleted in release 10.0 and replaced with object
         vRtrIfQosNetworkPolicyId."
    DEFVAL      { 1 }
    ::= { vRtrIfEntry 26 }

vRtrIfIngressFilterId            OBJECT-TYPE
    SYNTAX      TFilterID
    MAX-ACCESS  read-create
    STATUS      current
    DESCRIPTION
        "The value of vRtrIfIngressFilterId associates an ip-filter-id
         with an ingress interface. Filters control the forwarding and
         dropping of packets based on IP criteria.  A value of zero (0)
         indicates that there is no ip-filter-id associated with this
         interface.

         If this entry indicates a service virtual router interface or the
         special out-of-band management interface, this object is meaningless
         and is not applied to the interface."
    DEFVAL      { 0 }
    ::= { vRtrIfEntry 27 }

vRtrIfEgressFilterId             OBJECT-TYPE
    SYNTAX      TFilterID
    MAX-ACCESS  read-create
    STATUS      current
    DESCRIPTION
        "The value of vRtrIfEgressFilterId associates an ip-filter-id
         with an egress interface. Filters control the forwarding and
         dropping of packets based on IP criteria.  A value of zero (0)
         indicates that there is no ip-filter-id associated with this
         interface.

         If this entry indicates a service virtual router interface or the
         special out-of-band management interface, this object is meaningless
         and is not applied to the interface."
    DEFVAL      { 0 }
    ::= { vRtrIfEntry 28 }

vRtrIfDirectedBroadcast          OBJECT-TYPE
    SYNTAX      TruthValue
    MAX-ACCESS  read-create
    STATUS      current
    DESCRIPTION
        "When vRtrIfDirectedBroadcast is set to 'true', allows broadcasts
         directed to this interface to be accepted.  When 'false',
         directed broadcasts are dropped.  This is of particular use
         when preventing denial of service attacks."
    DEFVAL      { false }
    ::= { vRtrIfEntry 29 }

vRtrIfMplsStatus                 OBJECT-TYPE
    SYNTAX      TmnxStatus
    MAX-ACCESS  read-create
    STATUS      current
    DESCRIPTION
        "Setting this variable to 'create' causes this interface to be
         used with MPLS.  It also causes a row to be created in the
         vRtrMplsIfTable.  Setting it to 'delete' removes the interface
         from MPLS and causes the corresponding row in the vRtrMplsIfTable
         to be removed.  However, an attempt to set vRtrIfMplsStatus to
         'delete' will fail if MPLS activity on this interface is not
         administratively in the outOfService state, i.e. vRtrMplsIfAdminState
         of the vRtrMplsIfTable must be set to 'outOfService'."
    DEFVAL      { delete }
    ::= { vRtrIfEntry 30 }

vRtrIfUnnumberedIf               OBJECT-TYPE
    SYNTAX      DisplayString (SIZE (0..32))
    MAX-ACCESS  read-create
    STATUS      current
    DESCRIPTION
        "The name of the interface to which this unnumbered interface will
         refer to. This variable is complemented by vRtrIfUnnumbered. If
         vRtrIfUnnumberedIf is a null string and vRtrIfUnnumbered is '0' it
         implies that no unnumbered interface is configured. At any instant
         only one of the two members can be non-null."
    DEFVAL      { ''H }
    ::= { vRtrIfEntry 31 }

vRtrIfCflowd                     OBJECT-TYPE
    SYNTAX      INTEGER {
        none                   (1),
        aclIngressOnly         (2),
        interfaceIngressOnly   (3),
        aclEgressOnly          (4),
        interfaceEgressOnly    (5),
        aclIngressEgress       (6),
        interfaceIngressEgress (7)
    }
    MAX-ACCESS  read-create
    STATUS      obsolete
    DESCRIPTION
        "The value of vRtrIfCflowd specifies the type and direction of Cflowd
         analysis applied to this interface. A Cflowd profile controls the
         sampling and analysis of data flows through the router.  A value of
         'none (1)' indicates that there is no Cflowd analysis associated with
         this interface."
    DEFVAL      { none }
    ::= { vRtrIfEntry 32 }

vRtrIfVPNClass                   OBJECT-TYPE
    SYNTAX      INTEGER {
        unknown          (0),
        carrierOfCarrier (1),
        enterprise       (2),
        interProvider    (3)
    }
    MAX-ACCESS  read-only
    STATUS      current
    DESCRIPTION
        "The value of vRtrIfVPNClass indicates the type of VPN scenario
         supported on this virtual router interface."
    ::= { vRtrIfEntry 33 }

vRtrIfDescription                OBJECT-TYPE
    SYNTAX      TItemLongDescription
    MAX-ACCESS  read-create
    STATUS      current
    DESCRIPTION
        "The value of vRtrIfDescription is a user provided description
         string for this virtual router interface.  It can consist of
         printable, seven-bit ASCII characters."
    DEFVAL      { ''H }
    ::= { vRtrIfEntry 34 }

vRtrIfProtocol                   OBJECT-TYPE
    SYNTAX      BITS {
        ospfv2 (0),
        rip    (1),
        isis   (2),
        bgp    (3),
        mpls   (4),
        rsvp   (5),
        ldp    (6),
        igmp   (7),
        pim    (8),
        ospf3  (9),
        mld    (10),
        ripng  (11)
    }
    MAX-ACCESS  read-only
    STATUS      current
    DESCRIPTION
        "The value of vRtrIfProtocol indicates which protocols are running on
         this virtual router interface. If the bit corresponding to a protocol
         is set, then the protocol is enabled on this interface."
    ::= { vRtrIfEntry 35 }

vRtrIfTosMarkingTrusted          OBJECT-TYPE
    SYNTAX      TruthValue
    MAX-ACCESS  read-create
    STATUS      current
    DESCRIPTION
        "The value of vRtrIfTosMarkingTrusted specifies whether the TOS bits on
         the packets ingressing on the interface should be trusted by the
         system or not. If the value is set to 'true', the TOS bits should be
         trusted.

         If the system does not trust these packets, it will remark the packets
         upon egress as indicated by the value of the egress remark flag,
         TIMETRA-QOS-MIB:: tNetworkPolicyEgressRemark. The egress remark flag
         is part of the QoS policy applied to the network interface.

         The interfaces belonging to the IES service have the egress remark
         flag set to not trusted, 'false', by default. For all other interface
         types, the TOS bits are trusted by default."
    DEFVAL      { true }
    ::= { vRtrIfEntry 36 }

vRtrIfServiceId                  OBJECT-TYPE
    SYNTAX      TmnxServId
    MAX-ACCESS  read-create
    STATUS      current
    DESCRIPTION
        "The value of vRtrIfServiceId specifies the service id for this
         interface. This object must always be set at row creation when the
         vRtrIfType is not network(1). This object cannot be modified once the
         row is created."
    DEFVAL      { 0 }
    ::= { vRtrIfEntry 37 }

vRtrIfArpPopulate                OBJECT-TYPE
    SYNTAX      INTEGER {
        disabled (1),
        enabled  (2)
    }
    MAX-ACCESS  read-create
    STATUS      current
    DESCRIPTION
        "The value of the object vRtrIfArpPopulate specifies the ARP populate
         action. The value disabled means that the normal ARP protocol is
         active. The value enabled means that the system will not originate ARP
         requests on this interface. The ARP cache is only populated with MAC
         addresses learned via the DHCP protocol. If the value of vRtrIfType is
         network, this object can only be set to disabled."
    DEFVAL      { disabled }
    ::= { vRtrIfEntry 38 }

vRtrIfIPv6ConfigAllowed          OBJECT-TYPE
    SYNTAX      TruthValue
    MAX-ACCESS  read-create
    STATUS      current
    DESCRIPTION
        "The value of vRtrIfIPv6ConfigAllowed specifies whether IPv6 can be
         configured on this router interface. When the value is 'true', IPv6
         can be configured on this interface. When it is 'false', IPv6 cannot
         be configured.

         Object iesIfIPv6ConfigAllowed should be set if vRtrIfType is
         'subscriber' or 'group'."
    DEFVAL      { false }
    ::= { vRtrIfEntry 39 }

vRtrIfIPv6OperState              OBJECT-TYPE
    SYNTAX      TmnxOperState
    MAX-ACCESS  read-only
    STATUS      current
    DESCRIPTION
        "The current operational status for IPv6 on this router interface."
    ::= { vRtrIfEntry 40 }

vRtrIfIPv6IngressFilterId        OBJECT-TYPE
    SYNTAX      TFilterID
    MAX-ACCESS  read-create
    STATUS      current
    DESCRIPTION
        "The value of vRtrIfIPv6IngressFilterId associates an ip-filter-id
         with an ingress v6 interface. Filters control the forwarding and
         dropping of packets based on IP criteria.  A value of zero (0)
         indicates that there is no ip-filter-id associated with this
         interface.

         If this entry indicates a service virtual router interface or the
         special out-of-band management interface, this object is meaningless
         and is not applied to the interface."
    DEFVAL      { 0 }
    ::= { vRtrIfEntry 41 }

vRtrIfIPv6EgressFilterId         OBJECT-TYPE
    SYNTAX      TFilterID
    MAX-ACCESS  read-create
    STATUS      current
    DESCRIPTION
        "The value of vRtrIfIPv6EgressFilterId associates an ip-filter-id
         with an egress v6 interface. Filters control the forwarding and
         dropping of packets based on IP criteria.  A value of zero (0)
         indicates that there is no ip-filter-id associated with this
         interface.

         If this entry indicates a service virtual router interface or the
         special out-of-band management interface, this object is meaningless
         and is not applied to the interface."
    DEFVAL      { 0 }
    ::= { vRtrIfEntry 42 }

vRtrIfIcmpV6Redirects            OBJECT-TYPE
    SYNTAX      TruthValue
    MAX-ACCESS  read-create
    STATUS      current
    DESCRIPTION
        "When vRtrIfIcmpV6Redirects is set to 'true', ICMPv6 redirects are
         generated when routes are not optimal on this router and another
         router on the same subnetwork has a better route in order to
         alert that node that a better route is available.  When
         vRtrIfIcmpV6Redirects is set to 'false', ICMPv6 redirects are not
         generated."
    DEFVAL      { true }
    ::= { vRtrIfEntry 43 }

vRtrIfIcmpV6NumRedirects         OBJECT-TYPE
    SYNTAX      Unsigned32 (10..1000)
    MAX-ACCESS  read-create
    STATUS      current
    DESCRIPTION
        "The value of vRtrIfIcmpV6NumRedirects limits the number of v6
         redirects issued per the time frame specified in
         vRtrIfIcmpV6RedirectsTime."
    DEFVAL      { 100 }
    ::= { vRtrIfEntry 44 }

vRtrIfIcmpV6RedirectsTime        OBJECT-TYPE
    SYNTAX      Unsigned32 (1..60)
    UNITS       "seconds"
    MAX-ACCESS  read-create
    STATUS      current
    DESCRIPTION
        "The value of vRtrIfIcmpV6RedirectsTime determines the time frame in
         seconds that is used to limit the number of v6 redirects issued per
         time frame."
    DEFVAL      { 10 }
    ::= { vRtrIfEntry 45 }

vRtrIfIcmpV6Unreachables         OBJECT-TYPE
    SYNTAX      TruthValue
    MAX-ACCESS  read-create
    STATUS      current
    DESCRIPTION
        "When vRtrIfIcmpV6Unreachables is set to 'true', ICMPv6 host and
         network unreachable messages are generated by this interface. When
         vRtrIfIcmpV6Unreachables is set to 'false', ICMPv6 host and network
         unreachable messages are not sent."
    DEFVAL      { true }
    ::= { vRtrIfEntry 46 }

vRtrIfIcmpV6NumUnreachables      OBJECT-TYPE
    SYNTAX      Unsigned32 (10..2000)
    MAX-ACCESS  read-create
    STATUS      current
    DESCRIPTION
        "The value of vRtrIfIcmpV6NumUnreachables determines how many
         destination unreachable ICMPv6 messages are issued in the time frame
         specified by vRtrIfIcmpV6UnreachablesTime."
    DEFVAL      { 100 }
    ::= { vRtrIfEntry 47 }

vRtrIfIcmpV6UnreachablesTime     OBJECT-TYPE
    SYNTAX      Unsigned32 (1..60)
    UNITS       "seconds"
    MAX-ACCESS  read-create
    STATUS      current
    DESCRIPTION
        "The value of vRtrIfIcmpV6UnreachablesTime sets the time frame in
         seconds that is used to limit the number of destination unreachable
         ICMPv6 messages issued per time frame."
    DEFVAL      { 10 }
    ::= { vRtrIfEntry 48 }

vRtrIfIcmpV6TimeExceeded         OBJECT-TYPE
    SYNTAX      TruthValue
    MAX-ACCESS  read-create
    STATUS      current
    DESCRIPTION
        "The value of vRtrIfIcmpV6TimeExceeded specifies whether time-exceeded
         ICMP messages should be sent. When it is set to 'true', ICMPv6
         time-exceeded messages are generated by this interface. When
         vRtrIfIcmpV6TimeExceeded is set to 'false', ICMPv6 time-exceeded
         messages are not sent."
    DEFVAL      { true }
    ::= { vRtrIfEntry 49 }

vRtrIfIcmpV6NumTimeExceeded      OBJECT-TYPE
    SYNTAX      Unsigned32 (10..2000)
    MAX-ACCESS  read-create
    STATUS      current
    DESCRIPTION
        "The value of vRtrIfIcmpV6NumTimeExceeded specifies how many
         time-exceeded ICMPv6 messages are issued in the time frame specified
         by vRtrIfIcmpV6TimeExceededTime."
    DEFVAL      { 100 }
    ::= { vRtrIfEntry 50 }

vRtrIfIcmpV6TimeExceededTime     OBJECT-TYPE
    SYNTAX      Unsigned32 (1..60)
    UNITS       "seconds"
    MAX-ACCESS  read-create
    STATUS      current
    DESCRIPTION
        "The value of vRtrIfIcmpV6TimeExceededTime specifies the time frame in
         seconds that is used to limit the number of time-exceeded ICMPv6
         messages issued per time frame."
    DEFVAL      { 10 }
    ::= { vRtrIfEntry 51 }

vRtrIfIcmpV6PktTooBig            OBJECT-TYPE
    SYNTAX      TruthValue
    MAX-ACCESS  read-create
    STATUS      current
    DESCRIPTION
        "The value of vRtrIfIcmpV6PktTooBig specifies whether packet-too-big
         ICMP messages should be sent. When it is set to 'true', ICMPv6
         packet-too-big messages are generated by this interface. When
         vRtrIfIcmpV6PktTooBig is set to 'false', ICMPv6 packet-too-big
         messages are not sent."
    DEFVAL      { true }
    ::= { vRtrIfEntry 52 }

vRtrIfIcmpV6NumPktTooBig         OBJECT-TYPE
    SYNTAX      Unsigned32 (10..1000)
    MAX-ACCESS  read-create
    STATUS      current
    DESCRIPTION
        "The value of vRtrIfIcmpV6NumPktTooBig specifies how many
         packet-too-big ICMPv6 messages are issued in the time frame specified
         by vRtrIfIcmpV6PktTooBigTime."
    DEFVAL      { 100 }
    ::= { vRtrIfEntry 53 }

vRtrIfIcmpV6PktTooBigTime        OBJECT-TYPE
    SYNTAX      Unsigned32 (1..60)
    UNITS       "seconds"
    MAX-ACCESS  read-create
    STATUS      current
    DESCRIPTION
        "The value of vRtrIfIcmpV6PktTooBigTime specifies the time frame in
         seconds that is used to limit the number of packet-too-big ICMPv6
         messages issued per time frame."
    DEFVAL      { 10 }
    ::= { vRtrIfEntry 54 }

vRtrIfIcmpV6ParamProblem         OBJECT-TYPE
    SYNTAX      TruthValue
    MAX-ACCESS  read-create
    STATUS      current
    DESCRIPTION
        "The value of vRtrIfIcmpV6ParamProblem specifies whether
         parameter-problem ICMP messages should be sent. When it is set to
         'true', ICMPv6 parameter-problem messages are generated by this
         interface. When vRtrIfIcmpV6ParamProblem is set to 'false', ICMPv6
         parameter-problem messages are not sent."
    DEFVAL      { true }
    ::= { vRtrIfEntry 55 }

vRtrIfIcmpV6NumParamProblem      OBJECT-TYPE
    SYNTAX      Unsigned32 (10..1000)
    MAX-ACCESS  read-create
    STATUS      current
    DESCRIPTION
        "The value of vRtrIfIcmpV6NumParamProblem specifies how many
         parameter-problem ICMPv6 messages are issued in the time frame
         specified by vRtrIfIcmpV6ParamProblemTime."
    DEFVAL      { 100 }
    ::= { vRtrIfEntry 56 }

vRtrIfIcmpV6ParamProblemTime     OBJECT-TYPE
    SYNTAX      Unsigned32 (1..60)
    UNITS       "seconds"
    MAX-ACCESS  read-create
    STATUS      current
    DESCRIPTION
        "The value of vRtrIfIcmpV6ParamProblemTime specifies the time frame in
         seconds that is used to limit the number of parameter-problem ICMPv6
         messages issued per time frame."
    DEFVAL      { 10 }
    ::= { vRtrIfEntry 57 }

vRtrIfLinkLocalAddressType       OBJECT-TYPE
    SYNTAX      InetAddressType
    MAX-ACCESS  read-only
    STATUS      current
    DESCRIPTION
        "The value of vRtrIfLinkLocalAddressType indicates the IP address type
         of the link local address of this virtual router interface. When the
         value of vRtrIfIPv6OperState is 'inService', this object will have a
         value of 'ipv6z', and 'unknown' otherwise."
    ::= { vRtrIfEntry 58 }

vRtrIfLinkLocalAddress           OBJECT-TYPE
    SYNTAX      InetAddress (SIZE (0|20))
    MAX-ACCESS  read-only
    STATUS      current
    DESCRIPTION
        "The value of vRtrIfLinkLocalAddress indicates the link local IP
         address of this virtual router interface. This address valid when the
         value of vRtrIfIPv6OperState is 'inService'."
    ::= { vRtrIfEntry 59 }

vRtrIfLinkLocalAddressState      OBJECT-TYPE
    SYNTAX      TmnxInetAddrState
    MAX-ACCESS  read-only
    STATUS      current
    DESCRIPTION
        "The value of vRtrIfLinkLocalAddressState indicates the address state
         of vRtrIfLinkLocalAddress. When vRtrIfIPv6OperState is 'outOfService',
         the value of this object is 'unknown'."
    ::= { vRtrIfEntry 60 }

vRtrIfLastOperStateChange        OBJECT-TYPE
    SYNTAX      TimeStamp
    MAX-ACCESS  read-only
    STATUS      current
    DESCRIPTION
        "The value of vRtrIfLastOperStateChange indicates the sysUpTime when
         the operational state of this interface last changed."
    ::= { vRtrIfEntry 61 }

vRtrIfOperMtu                    OBJECT-TYPE
    SYNTAX      Unsigned32
    UNITS       "bytes"
    MAX-ACCESS  read-only
    STATUS      current
    DESCRIPTION
        "The value of vRtrIfOperMtu indicates the operational value of the IP
         MTU on this interface. It is the minimum of the vRtrIfMtu and the MTU
         of the physical port this interface is bound to."
    ::= { vRtrIfEntry 62 }

vRtrIfGlobalIndex                OBJECT-TYPE
    SYNTAX      Unsigned32 (0..262144)
    MAX-ACCESS  read-only
    STATUS      current
    DESCRIPTION
        "The value of vRtrIfGlobalIndex uniquely identifies this interface in
         the tmnx system. This field provides an identifier for router
         interfaces similar to the vRtrIfIndex value, except that vRtrIfIndex
         is unique within each virtual router. The vRtrIfGlobalIndex is unique
         system wide regardless of the vRtrID.

         The vRtrIfGlobalIndex value for each virtual interface must remain
         constant at least from one re-initialization of the system management
         processor to the next."
    ::= { vRtrIfEntry 63 }

vRtrIfDelaySeconds               OBJECT-TYPE
    SYNTAX      Unsigned32 (0..65535)
    UNITS       "seconds"
    MAX-ACCESS  read-create
    STATUS      obsolete
    DESCRIPTION
        "The value of vRtrIfDelaySeconds specifies the time in seconds that is
         used to bring up the interface.

         When interface comes up, it will not become operational until after
         the specified delay.

         When used to configure delayed-enable for a router interface, the
         values specified for vRtrIfDelaySeconds  can be in the range of
         0..1200. When used to configure hold-time of a Multi-homing secondary
         interface, the values specified can be in the range of 0..65535.

         The default value of vRtrIfDelaySeconds is also based on the router
         interface type. When used for a regular interface its default value is
         0. When used for a Multi-homing secondary interface, its default value
         is 30."
    ::= { vRtrIfEntry 64 }

vRtrIfDelayUpTimer               OBJECT-TYPE
    SYNTAX      Integer32
    UNITS       "seconds"
    MAX-ACCESS  read-only
    STATUS      obsolete
    DESCRIPTION
        "The value of vRtrIfDelayUpTimer indicates the time left before the
         interface comes up when vRtrIfDelaySeconds is configured to a non-zero
         value.

         When the interface is down, this object will return the value -1. It's
         value can be in the range 0 to vRtrIfDelaySeconds's value if the
         interface is 'about to come up'.

         If the interface is up, the value of vRtrIfDelayUpTimer will be 0."
    ::= { vRtrIfEntry 65 }

vRtrIfLocalDhcpServerName        OBJECT-TYPE
    SYNTAX      TNamedItemOrEmpty
    MAX-ACCESS  read-create
    STATUS      current
    DESCRIPTION
        "The value of vRtrIfLocalDhcpServerName specifies the local DHCP server
         that can be reached via this interface.

         The server itself is configured on virtual router level in object
         TIMETRA-DHCP-SERVER-MIB::tmnxDhcpServerCfgServerName. Assigning an IP
         address to it is done here by linking it to an interface. A server can
         be linked to several interfaces on the same virtual router."
    DEFVAL      { ''H }
    ::= { vRtrIfEntry 66 }

vRtrIfInitDelayEnable            OBJECT-TYPE
    SYNTAX      TruthValue
    MAX-ACCESS  read-create
    STATUS      obsolete
    DESCRIPTION
        "The value of vRtrIfInitDelayEnable specifies whether
         vRtrIfDelaySeconds is used only the next time or everytime the system
         attempts to bring the interface operationally up.

         The value of vRtrIfInitDelayEnable is ignored if the value of
         vRtrIfDelaySeconds is set to 0.

         The value of vRtrIfInitDelayEnable is only set when interface is of
         type subscriber interface.

         When the value vRtrIfInitDelayEnable is set to 'false', everytime the
         system attempts to bring the interface operationally up, it will be
         delayed by the value of vRtrIfDelaySeconds.

         When the value vRtrIfInitDelayEnable is set to 'true', only the next
         time the system attempts to bring the interface operationally up, it
         will be delayed by the value of vRtrIfDelaySeconds."
    DEFVAL      { false }
    ::= { vRtrIfEntry 67 }

vRtrIfCpmProtPolicyId            OBJECT-TYPE
    SYNTAX      TCpmProtPolicyID
    MAX-ACCESS  read-create
    STATUS      current
    DESCRIPTION
        "The value of vRtrIfCpmProtPolicyId associates a CPM Protection policy
         with an interface.

         A value of zero (0) specifies that no CPM Protection policy is
         associated with this interface.

         If no value for vRtrIfCpmProtPolicyId is specified when the
         vRtrIfEntry is created, the system assigns a default value, derived
         from the value of the object vRtrIfType, as follows:

         vRtrIfType              vRtrIfCpmProtPolicyId
         ---------------------------------------------------------------------
         network                 255
         service                 used internally.
         serviceIes              254
         serviceRtdVpls          obsoleted.
         serviceVprn             254
         serviceIesSubscriber    0
         serviceIesGroup         0
         serviceVprnSubscriber   used internally.
         serviceVprnGroup        0
         serviceIesRedundant     0
         serviceVprnRedundant    0
         serviceVpls             0
         serviceIesCem           defined on a SAP. --not supported
         serviceVprnCem          defined on a SAP. --not supported
         serviceVprnIPsec        254
         serviceVprnIPMirror     0
         serviceVideo            0
         serviceVplsVideo        0
         multiHomingPrimary      0
         multiHomingSecondary    0
         serviceIesTunnel        254
         serviceIpReas           0
         networkIpReas           0
         networkVprn             255
         tmsService              255
         serviceIesAarp          0
         serviceVprnAarp         0
         serviceIesAa            0
         serviceVprnAa           0
         unnumMplsTp             255
         gmplsLoopback           255

         If an interface would get a default value of 'zero', it is not allowed
         to modify the value of vRtrIfCpmProtPolicyId.

         This object is not supported on SR-1 and ESS-1, where the value of
         TIMETRA-CHASSIS-MIB::tmnxChassisType is '5', and 7710, where the value
         of TIMETRA-CHASSIS-MIB::tmnxChassisType is '7' or '9'."
    ::= { vRtrIfEntry 68 }

vRtrIfCpmProtUncfgdProtoDropCnt  OBJECT-TYPE
    SYNTAX      Gauge32
    MAX-ACCESS  read-only
    STATUS      current
    DESCRIPTION
        "The value of vRtrIfCpmProtUncfgdProtoDropCnt indicates the number of
         network control protocol messages dropped due to the operation of the
         protocol protection facility.

         The protocol protection facility can be enabled and disabled by means
         of the object TIMETRA-SECURITY-MIB::tmnxCpmProtDropUncfgdProtocolMsg.

         When the protocol protection facility is enabled, network control
         protocol traffic received on this virtual router interface is dropped
         if the protocol is not configured on this virtual router interface.

         The value of vRtrIfProtocol indicates which protocols are configured
         on this virtual router interface.

         This object is not supported on SR-1 and ESS-1, where the value of
         TIMETRA-CHASSIS-MIB::tmnxChassisType is '5', and 7710, where the value
         of TIMETRA-CHASSIS-MIB::tmnxChassisType is '7' or '9'."
    ::= { vRtrIfEntry 69 }

vRtrIfLdpSyncTimer               OBJECT-TYPE
    SYNTAX      Unsigned32 (0..1800)
    UNITS       "seconds"
    MAX-ACCESS  read-create
    STATUS      current
    DESCRIPTION
        "The value of vRtrIfLdpSyncTimer specifies a time interval used for
         IGP-LDP synchronization. The timer is started from the time the LDP
         session to the neighbor is up over the interface. This is to allow for
         the label FEC bindings to be exchanged.

         When the timer expires, the link cost is restored and is
         re-advertised. IGP will announce a new best next-hop and LDP will use
         it if the label binding for the neighbor's FEC is available."
    DEFVAL      { 0 }
    ::= { vRtrIfEntry 70 }

vRtrIfStripLabel                 OBJECT-TYPE
    SYNTAX      TruthValue
    MAX-ACCESS  read-create
    STATUS      current
    DESCRIPTION
        "The value of vRtrIfStripLabel specifies whether a packet received on
         the interface will have it's MPLS labels stripped from the packet
         (true) or not (false)."
    DEFVAL      { false }
    ::= { vRtrIfEntry 71 }

vRtrIfuRPFCheckState             OBJECT-TYPE
    SYNTAX      TmnxEnabledDisabled
    MAX-ACCESS  read-create
    STATUS      current
    DESCRIPTION
        "The value of vRtrIfuRPFCheckState specifies whether unicast RPF (uRPF)
         Check is enabled on this interface."
    DEFVAL      { disabled }
    ::= { vRtrIfEntry 72 }

vRtrIfuRPFCheckMode              OBJECT-TYPE
    SYNTAX      TmnxUrpfCheckMode
    MAX-ACCESS  read-create
    STATUS      current
    DESCRIPTION
        "The value of vRtrIfuRPFCheckMode specifies the mode of unicast RPF
         check.

         In 'strict' mode, uRPF checks whether incoming packet has a source
         address that matches a prefix in the routing table, and whether the
         interface expects to receive a packet with this source address prefix.

         In 'loose' mode, uRPF checks whether incoming packet has source
         address with a corresponding prefix in the routing table, however
         'loose' mode does not check whether the interface expects to receive a
         packet with a specific source address prefix.

         In 'strictNoEcmp' mode, when a packet is received on an interface and
         the source address matches an ECMP route the packet is dropped by
         uRPF. If source address does not match an ECMP route, the behavior is
         same as 'strict' mode.

         This object is valid only when value of vRtrIfuRPFCheckState is set to
         'enabled'."
    DEFVAL      { strict }
    ::= { vRtrIfEntry 73 }

vRtrIfQosQGrp                    OBJECT-TYPE
    SYNTAX      TNamedItemOrEmpty
    MAX-ACCESS  read-create
    STATUS      obsolete
    DESCRIPTION
        "The value of vRtrIfQosQGrp specifies the name of the QoS queue-group
         (TIMETRA-QOS-MIB::tQosEgrQGroupName) used with this interface.

         An 'inconsistentValue' error is returned if this object is set to a
         non-default value and an entry corresponding to vRtrIfPortID does not
         exist in TIMETRA-PORT-MIB::tPortNetEgrQGrpTable.

         This object is obsoleted in release 10.0 and replaced with object
         vRtrIfQosEgrPortRedirectQGrp."
    DEFVAL      { ''H }
    ::= { vRtrIfEntry 74 }

vRtrIfAdminLinkLocalAddrType     OBJECT-TYPE
    SYNTAX      InetAddressType
    MAX-ACCESS  read-create
    STATUS      current
    DESCRIPTION
        "The value of vRtrIfAdminLinkLocalAddrType specifies the IP address
         type of the link local address of this virtual router interface."
    DEFVAL      { unknown }
    ::= { vRtrIfEntry 75 }

vRtrIfAdminLinkLocalAddr         OBJECT-TYPE
    SYNTAX      InetAddress (SIZE (0|20))
    MAX-ACCESS  read-create
    STATUS      current
    DESCRIPTION
        "The value of vRtrIfAdminLinkLocalAddr specifies the link local IP
         address of this virtual router interface.

         Last four bytes of the address ('zone') refers to router interface
         identifier (vRtrIfIndex).

         This object will return default value of empty string when
         vRtrIfAdminLinkLocalAddrType is set to 'unknown'."
    DEFVAL      { ''H }
    ::= { vRtrIfEntry 76 }

vRtrIfAdmLnkLclAddrPreferred     OBJECT-TYPE
    SYNTAX      TruthValue
    MAX-ACCESS  read-create
    STATUS      current
    DESCRIPTION
        "The value of vRtrIfAdmLnkLclAddrPreferred specifies whether
         vRtrIfAdminLinkLocalAddr specified for this interface should be
         treated as preferred and disable duplicate address detection (DAD)."
    DEFVAL      { false }
    ::= { vRtrIfEntry 77 }

vRtrIfOperDownReason             OBJECT-TYPE
    SYNTAX      BITS {
        ifAdminDown             (0),
        svcAdminDown            (1),
        portOperDown            (2),
        addrOrIfNotReady        (3),
        assocObjNotReady        (4),
        rvplsDown               (5),
        operGrpDown             (6),
        ifAdminDestroy          (7),
        noIfAddress             (8),
        noIfInfo                (9),
        delayedStartEnabled     (10),
        ifProtoOperDown         (11),
        invalidPortCfg          (12),
        unknown                 (13),
        noRouteDistinguisher    (14),
        wlanGwRedundancyStandby (15),
        wlanGwGroupDegraded     (16)
    }
    MAX-ACCESS  read-only
    STATUS      obsolete
    DESCRIPTION
        "The value of vRtrIfOperDownReason indicates the reason why the
         interface is operationally down.

         The bit values are:
         'ifAdminDown (0)'              - Interface is administratively down
         'svcAdminDown (1)'             - Service is administratively down
         'portOperDown (2)'             - SAP port is operationally down
         'addrOrIfNotReady (3)'         - Address or Parent interface is not
                                          ready
         'assocObjNotReady (4)'         - Associated object is not ready
         'rvplsDown (5)'                - R-VPLS service is down
         'operGrpDown (6)'              - Associated Operational Group is down
         'ifAdminDestroy (7)'           - Interface is being deleted
         'noIfAddress (8)'              - Interface address is not configured
         'noIfInfo (9)'                 - Interface info not present
         'delayedStartEnabled (10)'     - Delayed start timer is enabled on
                                          the interface
         'ifProtoOperDown (11)'         - Protocols on interface are
                                          operationally down
         'invalidPortCfg (12)'          - Port configuration is not valid
         'unknown (13)'                 - Reason is unknown
         'noRouteDistinguisher (14)'    - Route Distinguisher not configured in VPRN
         'wlanGwRedundancyStandby (15)  - Interface is in standby state for
                                          WLAN-GW redundancy
         'wlanGwGroupDegraded (16)      - The associated WLAN-GW group is in a
                                          degraded state"
    ::= { vRtrIfEntry 78 }

vRtrIfNameTable                  OBJECT-TYPE
    SYNTAX      SEQUENCE OF VRtrIfNameEntry
    MAX-ACCESS  not-accessible
    STATUS      current
    DESCRIPTION
        "This is a read-only table, each row of which represents a one to one
         equivalence between a router interface name (vRtrIfName) and its
         corresponding index in the vRtrIfTable (vRtrIfIndex)."
    ::= { tmnxVRtrObjs 5 }

vRtrIfNameEntry                  OBJECT-TYPE
    SYNTAX      VRtrIfNameEntry
    MAX-ACCESS  not-accessible
    STATUS      current
    DESCRIPTION
        "Each row entry in the vRtrIfNameTable corresponds to a row in the
         vRtrIfTable. When an entry is created or deleted in the vRtrIfTable, a
         corresponding entry is created or deleted in this table."
    INDEX       {
        vRtrID,
        IMPLIED vRtrIfName
    }
    ::= { vRtrIfNameTable 1 }

VRtrIfNameEntry                  ::= SEQUENCE
{ vRtrIfNameIndex                  InterfaceIndex }

vRtrIfNameIndex                  OBJECT-TYPE
    SYNTAX      InterfaceIndex
    MAX-ACCESS  read-only
    STATUS      current
    DESCRIPTION
        "The value of vRtrIfNameIndex gives the value of vRtrIfIndex for a row
         in the vRtrIfTable. This row corresponds to the virtual router
         interface which has interface name as vRtrIfName. Every vRtrIfName is
         unique within a specific instance of vRtrID."
    ::= { vRtrIfNameEntry 1 }

vRtrIpAddrTable                  OBJECT-TYPE
    SYNTAX      SEQUENCE OF VRtrIpAddrEntry
    MAX-ACCESS  not-accessible
    STATUS      current
    DESCRIPTION
        "The vRtrIpAddrTable has an entry for each IP address configured
         for a virtual router in the system.  An interface on the
         virtual router may have more than one IP address assigned to
         it."
    ::= { tmnxVRtrObjs 6 }

vRtrIpAddrEntry                  OBJECT-TYPE
    SYNTAX      VRtrIpAddrEntry
    MAX-ACCESS  not-accessible
    STATUS      current
    DESCRIPTION
        "Each row entry represents an IP address assigned a virtual
         router interface.  Entries can be created and deleted via
         SNMP SET operations.  Setting RowStatus to 'active' requires
         a values for all column variables to have been assigned."
    INDEX       {
        vRtrID,
        vRtrIfIndex,
        vRiaIndex
    }
    ::= { vRtrIpAddrTable 1 }

VRtrIpAddrEntry                  ::= SEQUENCE
{
    vRiaIndex                        Integer32,
    vRiaRowStatus                    RowStatus,
    vRiaIpAddress                    IpAddress,
    vRiaNetMask                      IpAddress,
    vRiaBcastAddrFormat              INTEGER,
    vRiaReasmMaxSize                 Integer32,
    vRiaIgpInhibit                   TruthValue,
    vRiaInetAddressType              TmnxAddressAndPrefixType,
    vRiaInetAddress                  TmnxAddressAndPrefixAddress,
    vRiaInetPrefixLen                TmnxAddressAndPrefixPrefix,
    vRiaInetAddrState                TmnxInetAddrState,
    vRiaInetEui64                    TruthValue,
    vRiaInetOperAddress              InetAddress,
    vRiaInetGwAddressType            InetAddressType,
    vRiaInetGwAddress                InetAddress,
    vRiaInetRemoteIpType             InetAddressType,
    vRiaInetRemoteIp                 InetAddress,
    vRiaInetAddrPreferred            TruthValue,
    vRiaSubscrPrefix                 TruthValue,
    vRiaSubscrPrefixType             BITS,
    vRiaSubscrHostRoutePopulate      TruthValue,
    vRiaTrackSrrpInstance            Unsigned32,
    vRiaHoldUpTime                   Unsigned32,
    vRiaCreationOrigin               TmnxCreateOrigin,
    vRiaInetAddressSendCgaModifier   TmnxSendCgaModifier,
    vRiaInetAddressPrimaryPreference Unsigned32,
    vRiaInetAddressPrimaryPreferred  TruthValue,
    vRiaInetAddressGreTermination    TruthValue
}

vRiaIndex                        OBJECT-TYPE
    SYNTAX      Integer32 (1..2048)
    MAX-ACCESS  not-accessible
    STATUS      current
    DESCRIPTION
        "The unique value which identifies this IP address entry for
         this interface of this virtual router in the Tmnx system.
         Those row entries with vRiaIndex = 1 represent the primary
         IP address for the interface identified by the vRtrID and
         vRtrIfIndex pair.  Row entries with other values for vRiaIndex
         are secondary IP addresses.  The values greater than 256 are
         reserved for internal interfaces only and cannot be used to
         create an IP address entry."
    ::= { vRtrIpAddrEntry 1 }

vRiaRowStatus                    OBJECT-TYPE
    SYNTAX      RowStatus
    MAX-ACCESS  read-create
    STATUS      current
    DESCRIPTION
        "The row status used for creation, deletion, or control
         of vRtrIpAddrTable entries.  All the other row variables
         must have been assigned values before the row can be
         place into the 'active' state."
    ::= { vRtrIpAddrEntry 2 }

vRiaIpAddress                    OBJECT-TYPE
    SYNTAX      IpAddress
    MAX-ACCESS  read-create
    STATUS      current
    DESCRIPTION
        "The IP address assigned to a router's interface."
    ::= { vRtrIpAddrEntry 3 }

vRiaNetMask                      OBJECT-TYPE
    SYNTAX      IpAddress
    MAX-ACCESS  read-create
    STATUS      current
    DESCRIPTION
        "The subnet mask associated with the IP address of this
         entry.  The value of the mask is an IP address with all
         the network bits set to 1 and all the host bits set to
         0."
    DEFVAL      { 'ffffff00'H }
    ::= { vRtrIpAddrEntry 4 }

vRiaBcastAddrFormat              OBJECT-TYPE
    SYNTAX      INTEGER {
        allOnes  (1),
        hostOnes (2)
    }
    MAX-ACCESS  read-create
    STATUS      current
    DESCRIPTION
        "When vRiaBcastAddrFormat is set to 'allOnes', the 255.255.255.255
         address is used for local broadcast. When vRiaBcastAddrFormat is set
         to 'hostOnes', the <prefix>-1 address is used for the local broadcast.
         For example for subnet 10.10.16.0/20 the <prefix>-1 address is
         10.10.31.255."
    DEFVAL      { hostOnes }
    ::= { vRtrIpAddrEntry 5 }

vRiaReasmMaxSize                 OBJECT-TYPE
    SYNTAX      Integer32 (0..65535)
    MAX-ACCESS  read-create
    STATUS      current
    DESCRIPTION
        "The size of the largest IP datagram which this entry can reassemble
         from incoming IP fragmented datagrams received on this interface."
    ::= { vRtrIpAddrEntry 6 }

vRiaIgpInhibit                   OBJECT-TYPE
    SYNTAX      TruthValue
    MAX-ACCESS  read-create
    STATUS      current
    DESCRIPTION
        "This variable should only be associated with secondary
         ip addresses, i.e., when the value of vRiaIndex is other
         than 1. When vRiaIgpInhibit has a value of 'true',
         it indicates that the given secondary IP address should
         not be recognized as a local interface by the running IGP.
         For OSPF and IS-IS, this means that the given secondary
         IP addresses will not be injected as passive interfaces
         and will not be advertised as internal IP interfaces into
         the IGP's link state database.  For RIP this means these
         secondary IP interfaces will not source RIP updates."
    ::= { vRtrIpAddrEntry 7 }

vRiaInetAddressType              OBJECT-TYPE
    SYNTAX      TmnxAddressAndPrefixType
    MAX-ACCESS  read-create
    STATUS      current
    DESCRIPTION
        "vRiaInetAddressType specifies the type of the vRiaInetAddress address
         assigned to a router's interface."
    ::= { vRtrIpAddrEntry 8 }

vRiaInetAddress                  OBJECT-TYPE
    SYNTAX      TmnxAddressAndPrefixAddress (SIZE (0|4|16))
    MAX-ACCESS  read-create
    STATUS      current
    DESCRIPTION
        "The type of this address is determined by the value of the
         vRiaInetAddressType object.

         vRiaInetAddress indicates the IPv4/IPv6 address assigned to a router's
         interface."
    ::= { vRtrIpAddrEntry 9 }

vRiaInetPrefixLen                OBJECT-TYPE
    SYNTAX      TmnxAddressAndPrefixPrefix
    MAX-ACCESS  read-create
    STATUS      current
    DESCRIPTION
        "The value of vRiaInetPrefixLen specifies the length of the IP netmask
         for this interface address."
    ::= { vRtrIpAddrEntry 10 }

vRiaInetAddrState                OBJECT-TYPE
    SYNTAX      TmnxInetAddrState
    MAX-ACCESS  read-only
    STATUS      current
    DESCRIPTION
        "The value of vRiaInetAddrState indicates the address state of the IPv6
         address of the interface."
    ::= { vRtrIpAddrEntry 11 }

vRiaInetEui64                    OBJECT-TYPE
    SYNTAX      TruthValue
    MAX-ACCESS  read-create
    STATUS      current
    DESCRIPTION
        "The value of vRiaInetEui64 specifies whether the
         vRiaInetOperAddress is an eui64 address.  This object
         can only be set at creation time.

         When vRiaInetEui64 is 'true', then the vRiaInetOperAddress
         is derived from the vRiaInetAddress and the physical address
         of the interface this address is attached to.  vRiaInetAddress
         has to have all zeros the least significant 8 bytes. Also,
         vRiaInetPrefixLen cannot be longer than 64.

         When vRiaInetEui64 is 'false', then the vRiaInetOperAddress
         is a copy of vRiaInetAddress.  The value is always 'false' when
         vRiaInetAddressType is not 'ipv6'."
    DEFVAL      { false }
    ::= { vRtrIpAddrEntry 12 }

vRiaInetOperAddress              OBJECT-TYPE
    SYNTAX      InetAddress (SIZE (0|4|16|20))
    MAX-ACCESS  read-only
    STATUS      current
    DESCRIPTION
        "The value of vRiaInetOperAddress indicates the operational
         address of this entry.  The type of this address is determined
         by the value of the vRiaInetAddressType object."
    ::= { vRtrIpAddrEntry 13 }

vRiaInetGwAddressType            OBJECT-TYPE
    SYNTAX      InetAddressType
    MAX-ACCESS  read-create
    STATUS      current
    DESCRIPTION
        "The value of vRiaInetGwAddressType specifies the address type of
         vRiaInetGwAddress."
    DEFVAL      { unknown }
    ::= { vRtrIpAddrEntry 14 }

vRiaInetGwAddress                OBJECT-TYPE
    SYNTAX      InetAddress (SIZE (0|4|16))
    MAX-ACCESS  read-create
    STATUS      current
    DESCRIPTION
        "The value of vRiaInetGwAddress specifies the gateway address for the
         subnet specified by vRiaInetAddress and vRiaInetPrefixLen. The address
         type is defined by vRiaInetGwAddressType. This field is only valid
         when the address is configured on a subscriber interface."
    DEFVAL      { ''H }
    ::= { vRtrIpAddrEntry 15 }

vRiaInetRemoteIpType             OBJECT-TYPE
    SYNTAX      InetAddressType
    MAX-ACCESS  read-create
    STATUS      current
    DESCRIPTION
        "The value of vRiaInetRemoteIpType specifies the address type of
         vRiaInetRemoteIp."
    DEFVAL      { unknown }
    ::= { vRtrIpAddrEntry 16 }

vRiaInetRemoteIp                 OBJECT-TYPE
    SYNTAX      InetAddress (SIZE (0|4|16))
    MAX-ACCESS  read-create
    STATUS      current
    DESCRIPTION
        "The value of vRiaInetRemoteIp specifies the IP address of the remote
         redundant interface. This field is only valid when the address is
         configured on a redundant interface."
    DEFVAL      { ''H }
    ::= { vRtrIpAddrEntry 17 }

vRiaInetAddrPreferred            OBJECT-TYPE
    SYNTAX      TruthValue
    MAX-ACCESS  read-create
    STATUS      current
    DESCRIPTION
        "The value of vRiaInetAddrPreferred specifies whether vRiaInetAddress
         specified for this interface should be treated as preferred and
         disable duplicate address detection (DAD)."
    DEFVAL      { false }
    ::= { vRtrIpAddrEntry 18 }

vRiaSubscrPrefix                 OBJECT-TYPE
    SYNTAX      TruthValue
    MAX-ACCESS  read-create
    STATUS      current
    DESCRIPTION
        "The value of vRiaSubscrPrefix specifies whether the vRiaIpAddress
         specified for this interface should be treated as a subscriber prefix.
         This object cannot be modified once the row is created."
    DEFVAL      { false }
    ::= { vRtrIpAddrEntry 19 }

vRiaSubscrPrefixType             OBJECT-TYPE
    SYNTAX      BITS {
        pd       (0),
        wan-host (1)
    }
    MAX-ACCESS  read-create
    STATUS      current
    DESCRIPTION
        "The value of vRiaSubscrPrefixType specifies the type of subscriber
         prefix contained in vRiaIpAddress if vRiaSubscrPrefix is TRUE. This
         object cannot be modified once the row is created."
    DEFVAL      { {pd} }
    ::= { vRtrIpAddrEntry 20 }

vRiaSubscrHostRoutePopulate      OBJECT-TYPE
    SYNTAX      TruthValue
    MAX-ACCESS  read-create
    STATUS      current
    DESCRIPTION
        "The value of vRiaSubscrHostRoutePopulate specifies if subscriber host
         routes are populated in the FIB (Forwarding Information Base).

         This object can only be set to 'true' if the address is configured on
         a subscriber interface."
    DEFVAL      { false }
    ::= { vRtrIpAddrEntry 21 }

vRiaTrackSrrpInstance            OBJECT-TYPE
    SYNTAX      Unsigned32
    MAX-ACCESS  read-create
    STATUS      current
    DESCRIPTION
        "The value of vRiaTrackSrrpInstance specifies the SRRP instance whose
         state is tracked on this IP address."
    DEFVAL      { 0 }
    ::= { vRtrIpAddrEntry 22 }

vRiaHoldUpTime                   OBJECT-TYPE
    SYNTAX      Unsigned32 (0 | 100..5000)
    UNITS       "milliseconds"
    MAX-ACCESS  read-create
    STATUS      current
    DESCRIPTION
        "The value of vRiaHoldUpTime specifies the time to wait for the route
         to accept new state of the SRRP instance which is being tracked with
         this address.

         An 'inconsistentValue' error is returned if vRiaHoldUpTime is set to
         non-default value when vRiaTrackSrrpInstance is set to its default
         value."
    DEFVAL      { 0 }
    ::= { vRtrIpAddrEntry 23 }

vRiaCreationOrigin               OBJECT-TYPE
    SYNTAX      TmnxCreateOrigin
    MAX-ACCESS  read-only
    STATUS      current
    DESCRIPTION
        "The value of vRiaCreationOrigin indicates the mechanism used to create
         this entry."
    DEFVAL      { manual }
    ::= { vRtrIpAddrEntry 24 }

vRiaInetAddressSendCgaModifier   OBJECT-TYPE
    SYNTAX      TmnxSendCgaModifier
    MAX-ACCESS  read-create
    STATUS      current
    DESCRIPTION
        "The value of vRiaInetAddressSendCgaModifier specifies the modifier
         used during CGA generation.

         The value of vRiaInetAddressSendCgaModifier must have been generated
         with the RSA key pair and security parameter that is associated with
         this interface.

         The value all zeroes means that no modifier is specified; however,
         setting the value to all zeroes in an existing row while Secure
         Neighbor Discovery is enabled on its interface, causes the generation
         of a new CGA and a new modifier; Secure Neighbor Discovery is enabled
         on its interface by means of the object vRtrIfSendAdminState."
    REFERENCE
        "RFC 3972 Cryptographically Generated Addresses
         section 3 CGA Parameters"
    DEFVAL      { '00000000000000000000000000000000'H }
    ::= { vRtrIpAddrEntry 25 }

vRiaInetAddressPrimaryPreference OBJECT-TYPE
    SYNTAX      Unsigned32 (0 | 1..4294967295)
    MAX-ACCESS  read-create
    STATUS      current
    DESCRIPTION
        "The value of vRiaInetAddressPrimaryPreference specifies the order in
         which the address is used by control plane protocols and applications
         which require a fixed address of the interface.

         These include LDP and Segment Routing. When originating packets from
         this interface, the source IPv6 address follows the selection rules in
         RFC 6724 except for the specific cases where a fixed address is
         required. In the latter case, the IPv6 address with the lowest
         primary-preference index is selected. If the selected address is
         removed, the system selects the IPv6 address with the next lowest
         primary-preference index. The address index space is unique across all
         addresses of a given interface."
    DEFVAL      { 0 }
    ::= { vRtrIpAddrEntry 26 }

vRiaInetAddressPrimaryPreferred  OBJECT-TYPE
    SYNTAX      TruthValue
    MAX-ACCESS  read-only
    STATUS      current
    DESCRIPTION
        "The value of vRiaInetAddressPrimaryPreferred indicates that this IP
         address is selected as the interface primary preferred IP address.
         Only one IP address per address family will be selected as primary
         preferred."
    ::= { vRtrIpAddrEntry 27 }

vRiaInetAddressGreTermination    OBJECT-TYPE
    SYNTAX      TruthValue
    MAX-ACCESS  read-create
    STATUS      current
    DESCRIPTION
        "The value of vRiaInetAddressGreTermination indicates that GRE-MPLS
         packets with the destination IP specified by vRiaInetAddress and
         vRiaInetPrefixLen can be  terminated on this router interface."
    DEFVAL      { false }
    ::= { vRtrIpAddrEntry 28 }

vRtrIpCidrRouteTable             OBJECT-TYPE
    SYNTAX      SEQUENCE OF VRtrIpCidrRouteEntry
    MAX-ACCESS  not-accessible
    STATUS      current
    DESCRIPTION
        "The vRtrIpCidrRouteTable provides an extension of the ipCidrRouteTable
         in the IP-FORWARD-MIB."
    ::= { tmnxVRtrObjs 7 }

vRtrIpCidrRouteEntry             OBJECT-TYPE
    SYNTAX      VRtrIpCidrRouteEntry
    MAX-ACCESS  not-accessible
    STATUS      current
    DESCRIPTION
        "Each row entry in the vRtrIpCidrRouteTable represents additional
         columns for attributes specific to the Nokia SROS series
         implementation for the IP route table."
    AUGMENTS    { ipCidrRouteEntry }
    ::= { vRtrIpCidrRouteTable 1 }

VRtrIpCidrRouteEntry             ::= SEQUENCE
{
    vRtrIpCidrRouteLastEnabledTime   TimeStamp,
    vRtrIpCidrRoutePreference        Unsigned32,
    vRtrIpCidrRouteMetric            Unsigned32
}

vRtrIpCidrRouteLastEnabledTime   OBJECT-TYPE
    SYNTAX      TimeStamp
    MAX-ACCESS  read-only
    STATUS      current
    DESCRIPTION
        "The vRtrIpCidrRouteLastEnabledTime variable contains the sysUpTime
         value when ipCidrRouteStatus was last set to active (1) to allow IP
         forwarding on this route entry."
    ::= { vRtrIpCidrRouteEntry 1 }

vRtrIpCidrRoutePreference        OBJECT-TYPE
    SYNTAX      Unsigned32 (0..255)
    MAX-ACCESS  read-create
    STATUS      current
    DESCRIPTION
        "When ipCidrRouteProto has a value of 'netmgmt' to indicate that this
         entry is a static route, the value of vRtrIpCidrRoutePreference
         determines the priority of this static route versus the routes from
         different sources such as BGP or OSPF etc.

         Different protocols should not be configured with the same preference,
         if this occurs the tiebreaker is determined per the default preference
         value as defined in the table below.

         If multiple routes are learned with an identical preference using the
         same protocol, the lowest cost is used. If multiple routes are learned
         with an identical preference using the same protocol and the costs
         (metrics) are equal, then the decision as to what route to use is
         determined by the configuration of the ecmp command.

         Default preferences:

         Route Type             Preference      Configurable
         ----------             ----------      ------------
         Direct attached                 0                no
         Static route                    5               yes
         MPLS (post FCS)                 7
         OSPF Internal routes           10                no
         OSPF External                 150               yes
         BGP                           170               yes"
    DEFVAL      { 5 }
    ::= { vRtrIpCidrRouteEntry 2 }

vRtrIpCidrRouteMetric            OBJECT-TYPE
    SYNTAX      Unsigned32
    MAX-ACCESS  read-only
    STATUS      current
    DESCRIPTION
        "The primary routing metric  for this route. The semantics
         of this metric are determined by the routing-protocol specified
         in the route's ipCidrRouteProto value."
    ::= { vRtrIpCidrRouteEntry 3 }

vRtrStaticRouteNumber            OBJECT-TYPE
    SYNTAX      Unsigned32
    MAX-ACCESS  read-only
    STATUS      current
    DESCRIPTION
        "The number of current vRtrInetStaticRouteTable entries that are
         'active'."
    ::= { tmnxVRtrObjs 8 }

vRtrStaticRouteTable             OBJECT-TYPE
    SYNTAX      SEQUENCE OF VRtrStaticRouteEntry
    MAX-ACCESS  not-accessible
    STATUS      obsolete
    DESCRIPTION
        "This entity's Static Routing table.

         This object was made obsolete in the 15.0 release."
    ::= { tmnxVRtrObjs 9 }

vRtrStaticRouteEntry             OBJECT-TYPE
    SYNTAX      VRtrStaticRouteEntry
    MAX-ACCESS  not-accessible
    STATUS      obsolete
    DESCRIPTION
        "A particular route to  a  particular  destination, through a
         particular next hop.

         This object was made obsolete in the 15.0 release."
    INDEX       {
        vRtrID,
        vRtrStaticRouteDest,
        vRtrStaticRouteMask,
        vRtrStaticRouteIndex
    }
    ::= { vRtrStaticRouteTable 1 }

VRtrStaticRouteEntry             ::= SEQUENCE
{
    vRtrStaticRouteDest              IpAddress,
    vRtrStaticRouteMask              IpAddress,
    vRtrStaticRouteIndex             Integer32,
    vRtrStaticRouteRowStatus         RowStatus,
    vRtrStaticRouteLastEnabledTime   TimeStamp,
    vRtrStaticRouteStatus            INTEGER,
    vRtrStaticRouteStaticType        INTEGER,
    vRtrStaticRoutePreference        Unsigned32,
    vRtrStaticRouteMetric            Unsigned32,
    vRtrStaticRouteEgressIfIndex     InterfaceIndexOrZero,
    vRtrStaticRouteNextHop           IpAddress,
    vRtrStaticRouteNextHopUnnumberedIf DisplayString,
    vRtrStaticRouteAdminState        TmnxAdminState,
    vRtrStaticRouteIgpShortcut       BITS,
    vRtrStaticRouteDisallowIgp       TruthValue,
    vRtrStaticRouteTag               Unsigned32
}

vRtrStaticRouteDest              OBJECT-TYPE
    SYNTAX      IpAddress
    MAX-ACCESS  read-only
    STATUS      obsolete
    DESCRIPTION
        "The destination IP address of this route.
         This object may not take a Multicast (Class  D) address value.

         Any assignment (implicit or  otherwise) of an instance of this object to
         a value x must be rejected if the bitwise logical-AND of x with the
         value of the corresponding instance of the vRtrStaticRouteMask object
         is not equal to x.

         This object was made obsolete in the 15.0 release."
    ::= { vRtrStaticRouteEntry 1 }

vRtrStaticRouteMask              OBJECT-TYPE
    SYNTAX      IpAddress
    MAX-ACCESS  read-only
    STATUS      obsolete
    DESCRIPTION
        "Indicate the mask to be logical-ANDed  with  the  destination  address
         before  being compared to the value  in  the  vRtrStaticRouteDest field.
         For those  systems  that  do  not support arbitrary subnet masks, an
         agent constructs the value  of the  vRtrStaticRouteMask  by  reference
         to the IP Address Class.

         Any assignment (implicit or  otherwise)  of  an instance of this object
         to a value x must be rejected if the bitwise logical-AND of x with the
         value of the corresponding instance of the vRtrStaticRouteDest object is
         not equal to vRtrStaticRouteDest.

         This object was made obsolete in the 15.0 release."
    ::= { vRtrStaticRouteEntry 2 }

vRtrStaticRouteIndex             OBJECT-TYPE
    SYNTAX      Integer32 (1..2147483647)
    MAX-ACCESS  read-only
    STATUS      obsolete
    DESCRIPTION
        "The quaternary index for the vRtrStaticRouteTable.

         This object was made obsolete in the 15.0 release."
    ::= { vRtrStaticRouteEntry 3 }

vRtrStaticRouteRowStatus         OBJECT-TYPE
    SYNTAX      RowStatus
    MAX-ACCESS  read-create
    STATUS      obsolete
    DESCRIPTION
        "The row status variable, used according to row installation and
         removal conventions.

         This object was made obsolete in the 15.0 release."
    ::= { vRtrStaticRouteEntry 4 }

vRtrStaticRouteLastEnabledTime   OBJECT-TYPE
    SYNTAX      TimeStamp
    MAX-ACCESS  read-only
    STATUS      obsolete
    DESCRIPTION
        "The vRtrStaticRouteLastEnabledTime variable contains the sysUpTime
         value when vRtrStaticRouteStatus was last set to active (1) to allow
         IP forwarding on this static route entry.

         This object was made obsolete in the 15.0 release."
    ::= { vRtrStaticRouteEntry 5 }

vRtrStaticRouteStatus            OBJECT-TYPE
    SYNTAX      INTEGER {
        active   (1),
        inactive (2)
    }
    MAX-ACCESS  read-only
    STATUS      obsolete
    DESCRIPTION
        "The value of vRtrStaticRouteStatus indicates whether or not this
         route entry is active in the system.  When an interface
         transitions to the down state, any associated route entries
         are marked as 'inactive' and are usually not displayed in a
         standard route table listing.  When the interface transitions
         to the up state, the agent marks the associated routes as
         'active'.

         This object was made obsolete in the 15.0 release."
    ::= { vRtrStaticRouteEntry 6 }

vRtrStaticRouteStaticType        OBJECT-TYPE
    SYNTAX      INTEGER {
        unknown   (0),
        nextHop   (1),
        indirect  (2),
        blackHole (3),
        grt       (4)
    }
    MAX-ACCESS  read-create
    STATUS      obsolete
    DESCRIPTION
        "The value of vRtrStaticRouteStaticType specifies the type of static
         route represented by this row entry.

         This object was made obsolete in the 15.0 release."
    DEFVAL      { unknown }
    ::= { vRtrStaticRouteEntry 7 }

vRtrStaticRoutePreference        OBJECT-TYPE
    SYNTAX      Unsigned32 (1..255)
    MAX-ACCESS  read-create
    STATUS      obsolete
    DESCRIPTION
        "The value of vRtrStaticRoutePreference determines the priority of this
         static route versus the routes from different sources such as BGP or
         OSPF etc.

         Different protocols should not be configured with the same preference,
         if this occurs the tiebreaker is determined per the default preference
         value as defined in the table below.

         If multiple routes are learned with an identical preference using the
         same protocol, the lowest cost is used. If multiple routes are learned
         with an identical preference using the same protocol and the costs
         (metrics) are equal, then the decision as to what route to use is
         determined by the configuration of the ecmp command.

         Default preferences.


         Route Type             Preference      Configurable
         ----------             ----------      ------------
         Direct attached                 0                no
         Static route                    5               yes
         MPLS (post FCS)                 7
         OSPF Internal routes           10                no
         OSPF External                 150               yes
         BGP                           170               yes

         This object was made obsolete in the 15.0 release."
    DEFVAL      { 5 }
    ::= { vRtrStaticRouteEntry 8 }

vRtrStaticRouteMetric            OBJECT-TYPE
    SYNTAX      Unsigned32 (0..65535)
    MAX-ACCESS  read-create
    STATUS      obsolete
    DESCRIPTION
        "When ipCidrRouteProto has a value of 'netmgmt' to indicate that
         this entry is a static route, the value of vRtrStaticRouteMetric
         associates a metric value with the route. This value is used
         when importing this static route into other protocols such as
         OSPF.  When the metric is configured as zero then the metric
         configured in OSPF, default-import-metric, applies.  This value
         is also used to determine which static route to install in the
         forwarding table:

         If there are multiple static routes with the same preference but
         unequal metric then the lower cost (metric) route will be installed.

         If there are multiple static routes with equal preference and metrics
         then ecmp rules apply.

         If there are multiple routes with unequal preference then the lower
         preference route will be installed.

         This object was made obsolete in the 15.0 release."
    DEFVAL      { 1 }
    ::= { vRtrStaticRouteEntry 9 }

vRtrStaticRouteEgressIfIndex     OBJECT-TYPE
    SYNTAX      InterfaceIndexOrZero
    MAX-ACCESS  read-only
    STATUS      obsolete
    DESCRIPTION
        "The outgoing ifIndex for this route as computed by the static route
         module. This variable will have a value of 0 if vRtrStaticRouteStatus
         is 'inactive' or if this static route is configured as a black hole.

         This object was made obsolete in the 15.0 release."
    ::= { vRtrStaticRouteEntry 11 }

vRtrStaticRouteNextHop           OBJECT-TYPE
    SYNTAX      IpAddress
    MAX-ACCESS  read-create
    STATUS      obsolete
    DESCRIPTION
        "In case of remote routes, the address of the next system en route.
         This member is complemented by vRtrStaticRouteNextHopUnnumberedIf. At
         most only one of them can be non-null. If vRtrStaticRouteNextHop is
         '0.0.0.0' and vRtrStaticRouteNextHopUnnumberedIf is a null string then
         this static route is configured as a black hole.

         This object was made obsolete in the 15.0 release."
    ::= { vRtrStaticRouteEntry 12 }

vRtrStaticRouteNextHopUnnumberedIf OBJECT-TYPE
    SYNTAX      DisplayString (SIZE (0..32))
    MAX-ACCESS  read-create
    STATUS      obsolete
    DESCRIPTION
        "The name of the unnumbered Interface which will be the nexthop for
         this route. This member is complemented by vRtrStaticRouteNextHop.

         At most only one of them can be non-null. If vRtrStaticRouteNextHop is
         '0.0.0.0' and vRtrStaticRouteNextHopUnnumberedIf is a null string then
         this static route is configured as a black hole.

         This object was made obsolete in the 15.0 release."
    ::= { vRtrStaticRouteEntry 13 }

vRtrStaticRouteAdminState        OBJECT-TYPE
    SYNTAX      TmnxAdminState
    MAX-ACCESS  read-create
    STATUS      obsolete
    DESCRIPTION
        "The desired administrative state for this virtual router static route.

         This object was made obsolete in the 15.0 release."
    DEFVAL      { outOfService }
    ::= { vRtrStaticRouteEntry 14 }

vRtrStaticRouteIgpShortcut       OBJECT-TYPE
    SYNTAX      BITS {
        te  (0),
        ldp (1),
        ip  (2)
    }
    MAX-ACCESS  read-create
    STATUS      obsolete
    DESCRIPTION
        "The value of vRtrStaticRouteIgpShortcut is valid only for indirect
         static routes (i.e. vRtrStaticRouteStaticType is 'indirect'). The bits
         of vRtrStaticRouteIgpShortcut identify Layer 2 tunneling mechanisms
         used for IGP shortcuts. If a bit is set, IGP shortcuts associated with
         that tunneling mechanism will be used to resolve next-hop for the
         static route. If no bits are set, IGP shortcuts will not be used to
         resolve next-hop for the static routes.

         The tunneling mechanisms represented by each bit are:
           te(0)  - RSVP Traffic Engineering
           ldp(1) - LDP /32 Route Forwarding Equivalence Class (FEC)
           ip(2)  - IP (IP-in-IP or GRE)

         Evaluation of tunnel preference is based on the following order, in
         descending priority:
           1. Traffic Engineered Shortcut (RSVP-TE)
           2. LDP /32 Route FEC Shortcut
           3. IP Shortcut (IP-in-IP or GRE)
           4. Actual IGP Next-Hop.

         This object was replaced by vRtrInetSRIndirectTunnelLdp and
         vRtrInetSRIndirectTunnelRsvpTe objects in 13.0."
    DEFVAL      { {} }
    ::= { vRtrStaticRouteEntry 15 }

vRtrStaticRouteDisallowIgp       OBJECT-TYPE
    SYNTAX      TruthValue
    MAX-ACCESS  read-create
    STATUS      obsolete
    DESCRIPTION
        "The value of vRtrStaticRouteDisallowIgp is valid only for indirect
         static routes (i.e. vRtrStaticRouteStaticType is 'indirect'). If the
         value of vRtrStaticRouteDisallowIgp is set to 'true', and if none of
         the defined tunneling mechanisms (RSVP-TE, LDP or IP) qualify as a
         next-hop, the normal IGP next-hop to the indirect next-hop address
         will not be used. If the value is set to 'false', IGP next-hop to the
         indirect next-hop address can be used as the next-hop of the last
         resort.

         This object was replaced by vRtrInetSRIndirectTunnelDisalIgp object in
         13.0."
    DEFVAL      { false }
    ::= { vRtrStaticRouteEntry 16 }

vRtrStaticRouteTag               OBJECT-TYPE
    SYNTAX      Unsigned32 (0..4294967295)
    MAX-ACCESS  read-create
    STATUS      obsolete
    DESCRIPTION
        "The value of vRtrStaticRouteTag is used to add a 32-bit integer tag to
         the static route. This tag could then be used in route policies to
         control distribution of the route into other protocols. A value of 0
         indicates that the tag has not been set.

         This object was made obsolete in the 15.0 release."
    DEFVAL      { 0 }
    ::= { vRtrStaticRouteEntry 17 }

vRtrSvcIpRangeTable              OBJECT-TYPE
    SYNTAX      SEQUENCE OF VRtrSvcIpRangeEntry
    MAX-ACCESS  not-accessible
    STATUS      obsolete
    DESCRIPTION
        "The vRtrSvcIpRangeTable has an entry for each IP address
         range configured for a virtual interface in a virtual router
         in the system.  An interface on the virtual router may have
         more than one Service IP address ranges assigned to it.

         This table is obsoleted in release 22.2 and later."
    ::= { tmnxVRtrObjs 10 }

vRtrSvcIpRangeEntry              OBJECT-TYPE
    SYNTAX      VRtrSvcIpRangeEntry
    MAX-ACCESS  not-accessible
    STATUS      obsolete
    DESCRIPTION
        "Each row entry represents an IP address range assigned a
         virtual router service interface.  Entries can be created
         and deleted via SNMP SET operations.  Setting RowStatus to
         'active' requires values for all column variables to have
         been assigned."
    INDEX       {
        vRtrID,
        vRtrSvcIpRangeAddress,
        vRtrSvcIpRangeMask
    }
    ::= { vRtrSvcIpRangeTable 1 }

VRtrSvcIpRangeEntry              ::= SEQUENCE
{
    vRtrSvcIpRangeAddress            IpAddress,
    vRtrSvcIpRangeMask               Unsigned32,
    vRtrSvcIpRangeRowStatus          RowStatus,
    vRtrSvcIpRangeExclusive          TruthValue
}

vRtrSvcIpRangeAddress            OBJECT-TYPE
    SYNTAX      IpAddress
    MAX-ACCESS  read-create
    STATUS      obsolete
    DESCRIPTION
        "The IP address prefix range assigned to a router's service interface."
    ::= { vRtrSvcIpRangeEntry 1 }

vRtrSvcIpRangeMask               OBJECT-TYPE
    SYNTAX      Unsigned32 (0..32)
    MAX-ACCESS  read-create
    STATUS      obsolete
    DESCRIPTION
        "The subnet mask associated with the Service IP address of this
         entry.  The value of the mask is an 32-bit integer with all
         the network bits set to 1 and all the host bits set to 0."
    ::= { vRtrSvcIpRangeEntry 2 }

vRtrSvcIpRangeRowStatus          OBJECT-TYPE
    SYNTAX      RowStatus
    MAX-ACCESS  read-create
    STATUS      obsolete
    DESCRIPTION
        "The row status used for creation, deletion, or control of
         vRtrSvcIpRangeTable entries."
    ::= { vRtrSvcIpRangeEntry 3 }

vRtrSvcIpRangeExclusive          OBJECT-TYPE
    SYNTAX      TruthValue
    MAX-ACCESS  read-create
    STATUS      obsolete
    DESCRIPTION
        "When vRtrSvcIpRangeExclusive has a value of 'true', this
         set of addresses is reserved for services only and cannot be
         assigned to network ports.  When it has a value of 'false',
         it could be used for services as well as network ports."
    DEFVAL      { false }
    ::= { vRtrSvcIpRangeEntry 4 }

vRtrIpNetToMediaTable            OBJECT-TYPE
    SYNTAX      SEQUENCE OF VRtrIpNetToMediaEntry
    MAX-ACCESS  not-accessible
    STATUS      current
    DESCRIPTION
        "The vRtrIpNetToMediaTable provides an extension of the
         ipNetToMediaTable in the IP-MIB."
    ::= { tmnxVRtrObjs 11 }

vRtrIpNetToMediaEntry            OBJECT-TYPE
    SYNTAX      VRtrIpNetToMediaEntry
    MAX-ACCESS  not-accessible
    STATUS      current
    DESCRIPTION
        "Each row entry in the vRtrIpNetToMediaTable represents additional
         columns for attributes specific to the Nokia SROS series
         implementation for the vRtrIpNetToMediaTable."
    AUGMENTS    { ipNetToMediaEntry }
    ::= { vRtrIpNetToMediaTable 1 }

VRtrIpNetToMediaEntry            ::= SEQUENCE
{
    vRtrIpNetToMediaTimer            Unsigned32,
    vRtrIpNetToMediaOperState        TmnxOperState
}

vRtrIpNetToMediaTimer            OBJECT-TYPE
    SYNTAX      Unsigned32 (0..65535)
    UNITS       "seconds"
    MAX-ACCESS  read-only
    STATUS      current
    DESCRIPTION
        "The value of vRtrIpNetToMediaTimer determines how much longer an ARP
         entry associated with an vRtrIpNetToMediaTable entry remains in the
         ARP cache. It is initially set to vRtrIfArpTimeout. When
         vRtrIpNetToMediaTimer has a value of zero, '0', the entry is cleared
         from the cache."
    ::= { vRtrIpNetToMediaEntry 1 }

vRtrIpNetToMediaOperState        OBJECT-TYPE
    SYNTAX      TmnxOperState
    MAX-ACCESS  read-only
    STATUS      current
    DESCRIPTION
        "The value of vRtrIpNetToMediaOperState indicates if the ARP entry is
         being used actively in the ARP Table. When ipNetToMediaType has a
         value 'dynamic', vRtrIpNetToMediaOperState will never have a value of
         'outOfService'."
    ::= { vRtrIpNetToMediaEntry 2 }

vRtrInstanceAggregationTableLastChanged OBJECT-TYPE
    SYNTAX      TimeStamp
    MAX-ACCESS  read-only
    STATUS      obsolete
    DESCRIPTION
        "Timestamp of the last change to the vRtrInstanceAggregationTable
         either from adding a row or removing a row."
    ::= { tmnxVRtrObjs 12 }

vRtrInstanceAggregationTable     OBJECT-TYPE
    SYNTAX      SEQUENCE OF VRtrInstanceAggregationEntry
    MAX-ACCESS  not-accessible
    STATUS      obsolete
    DESCRIPTION
        "The vRtrInstanceAggregationTable is the list of configured VRtr
         aggregations and their operational status information.

         Specifies the route aggregates that should be generated into the
         virtual router if at least one contributing route (more specific) is
         learned.

         A route could match multiple aggregate statements. For instance, with
         the following entries: aggregate 10.0.0.0/8 aggregate 10.1.0.0/16

         If the route 10.1.1.0/24 is learned, both aggregates would be
         generated.

         This table was obsoleted in release 7.0.  It is replaced with the
         vRtrInetInstAggrTable to support ipv6 addresses."
    ::= { tmnxVRtrObjs 13 }

vRtrInstanceAggregationEntry     OBJECT-TYPE
    SYNTAX      VRtrInstanceAggregationEntry
    MAX-ACCESS  not-accessible
    STATUS      obsolete
    DESCRIPTION
        "An entry (conceptual row) in the vRtrInstanceAggregationTable. Entries
         are created by user. Entries are destroyed by user."
    INDEX       {
        vRtrID,
        vRtrAggregationIpPrefix,
        vRtrAggregationIpPrefixMask
    }
    ::= { vRtrInstanceAggregationTable 1 }

VRtrInstanceAggregationEntry     ::= SEQUENCE
{
    vRtrAggregationIpPrefix          IpAddress,
    vRtrAggregationIpPrefixMask      IpAddressPrefixLength,
    vRtrAggregationRowStatus         RowStatus,
    vRtrAggregationLastChanged       TimeStamp,
    vRtrAggregationSummaryOnly       TruthValue,
    vRtrAggregationASSet             TruthValue,
    vRtrAggregationAggregatorAS      TmnxBgpAutonomousSystem,
    vRtrAggregationAggregatorIPAddr  IpAddress,
    vRtrAggregationOperState         TmnxOperState
}

vRtrAggregationIpPrefix          OBJECT-TYPE
    SYNTAX      IpAddress
    MAX-ACCESS  not-accessible
    STATUS      obsolete
    DESCRIPTION
        "IP address prefix to match for the aggregation."
    ::= { vRtrInstanceAggregationEntry 1 }

vRtrAggregationIpPrefixMask      OBJECT-TYPE
    SYNTAX      IpAddressPrefixLength
    MAX-ACCESS  not-accessible
    STATUS      obsolete
    DESCRIPTION
        "Mask length for vRtrAggregationIpPrefix, to match for the aggregation."
    ::= { vRtrInstanceAggregationEntry 2 }

vRtrAggregationRowStatus         OBJECT-TYPE
    SYNTAX      RowStatus
    MAX-ACCESS  read-create
    STATUS      obsolete
    DESCRIPTION
        "Row status for this entry."
    ::= { vRtrInstanceAggregationEntry 3 }

vRtrAggregationLastChanged       OBJECT-TYPE
    SYNTAX      TimeStamp
    MAX-ACCESS  read-create
    STATUS      obsolete
    DESCRIPTION
        "Time stamp of last change of any object for this entry."
    ::= { vRtrInstanceAggregationEntry 4 }

vRtrAggregationSummaryOnly       OBJECT-TYPE
    SYNTAX      TruthValue
    MAX-ACCESS  read-create
    STATUS      obsolete
    DESCRIPTION
        "When true(1), only the aggregate is advertised, the more specific
         routes that make up the aggregate are not.

         When false(2), both the aggregate and more specific components are
         advertised."
    DEFVAL      { false }
    ::= { vRtrInstanceAggregationEntry 5 }

vRtrAggregationASSet             OBJECT-TYPE
    SYNTAX      TruthValue
    MAX-ACCESS  read-create
    STATUS      obsolete
    DESCRIPTION
        "When true(1), the AS-Path of the resulting aggregate will contain an
         AS-SET containing all AS numbers from the contributing routes.

         When false(2), the AS-Path will contain no AS-SET and will be
         originated by the ESR."
    DEFVAL      { false }
    ::= { vRtrInstanceAggregationEntry 6 }

vRtrAggregationAggregatorAS      OBJECT-TYPE
    SYNTAX      TmnxBgpAutonomousSystem
    MAX-ACCESS  read-create
    STATUS      obsolete
    DESCRIPTION
        "When vRtrAggregationAggregatorAS is set to non zero, and
         vRtrAggregationAggregatorIPAddr is set to non-zero, the supplied ASN
         and IP address will be used for the aggregator path attributes.

         When omitted, automatically uses its own ASN & Router-ID."
    DEFVAL      { 0 }
    ::= { vRtrInstanceAggregationEntry 7 }

vRtrAggregationAggregatorIPAddr  OBJECT-TYPE
    SYNTAX      IpAddress
    MAX-ACCESS  read-create
    STATUS      obsolete
    DESCRIPTION
        "When vRtrAggregationAggregatorAS is set to non zero, and
         vRtrAggregationAggregatorIPAddr is set to non-zero, the supplied ASN
         and IP address will be used for the aggregator path attributes.

         When omitted, automatically uses its own ASN & Router-ID."
    DEFVAL      { '00000000'H }
    ::= { vRtrInstanceAggregationEntry 8 }

vRtrAggregationOperState         OBJECT-TYPE
    SYNTAX      TmnxOperState
    MAX-ACCESS  read-only
    STATUS      obsolete
    DESCRIPTION
        "vRtrAggregationOperState indicates the current operational status of
         the aggregation entry."
    ::= { vRtrInstanceAggregationEntry 9 }

vRtrStaticRouteIndexTable        OBJECT-TYPE
    SYNTAX      SEQUENCE OF VRtrStaticRouteIndexEntry
    MAX-ACCESS  not-accessible
    STATUS      obsolete
    DESCRIPTION
        "This entity's Static Route Index Table.

         This object was made obsolete in the 15.0 release."
    ::= { tmnxVRtrObjs 14 }

vRtrStaticRouteIndexEntry        OBJECT-TYPE
    SYNTAX      VRtrStaticRouteIndexEntry
    MAX-ACCESS  not-accessible
    STATUS      obsolete
    DESCRIPTION
        "The available index for the vRtrStaticRouteTable for every destination
         per virtual router.

         This object was made obsolete in the 15.0 release."
    INDEX       {
        vRtrID,
        vRtrStaticRouteIndexDest,
        vRtrStaticRouteIndexMask
    }
    ::= { vRtrStaticRouteIndexTable 1 }

VRtrStaticRouteIndexEntry        ::= SEQUENCE
{
    vRtrStaticRouteIndexDest         IpAddress,
    vRtrStaticRouteIndexMask         IpAddress,
    vRtrStaticRouteAvailableIndex    TestAndIncr
}

vRtrStaticRouteIndexDest         OBJECT-TYPE
    SYNTAX      IpAddress
    MAX-ACCESS  read-only
    STATUS      obsolete
    DESCRIPTION
        "The destination IP address of this index entry.
         This object may not take a Multicast (Class  D) address value.

         Any  assignment  (implicit  or  otherwise)  of an instance of this
         object to a value x must be rejected if the bitwise logical-AND of
         x   with   the   value   of  the  corresponding  instance  of  the
         vRtrStaticRouteMask object is not equal to x.

         This object was made obsolete in the 15.0 release."
    ::= { vRtrStaticRouteIndexEntry 1 }

vRtrStaticRouteIndexMask         OBJECT-TYPE
    SYNTAX      IpAddress
    MAX-ACCESS  read-only
    STATUS      obsolete
    DESCRIPTION
        "Indicate the mask to be logical-ANDed with the destination address
         before  being  compared  to  the  value in the vRtrStaticRouteDest
         field.  For  those  systems  that  do not support arbitrary subnet
         masks, an agent constructs the value of the vRtrStaticRouteMask by
         reference  to  the  IP  Address Class. Any assignment (implicit or
         otherwise)  of  an  instance  of  this object to a value x must be
         rejected  if  the  bitwise  logical-AND of x with the value of the
         corresponding  instance  of  the vRtrStaticRouteDest object is not
         equal to vRtrStaticRouteDest.

         This object was made obsolete in the 15.0 release."
    ::= { vRtrStaticRouteIndexEntry 2 }

vRtrStaticRouteAvailableIndex    OBJECT-TYPE
    SYNTAX      TestAndIncr (1..2147483647)
    MAX-ACCESS  read-only
    STATUS      obsolete
    DESCRIPTION
        "The available quaternary index for the vRtrStaticRouteTable.

         This object was made obsolete in the 15.0 release."
    ::= { vRtrStaticRouteIndexEntry 3 }

tmnxVRtrGlobalObjs               OBJECT IDENTIFIER ::= { tmnxVRtrObjs 15 }

vRtrNextVRtrID                   OBJECT-TYPE
    SYNTAX      TestAndIncr
    MAX-ACCESS  read-write
    STATUS      current
    DESCRIPTION
        "The vRtrNextVRtrID object is used to assign values to vRtrID
         to be used to create a new row in the vRtrConfTable as described
         in 'Textual Conventions for SNMPv2'.  The network manager reads
         the object, and then writes the value back in the SET request
         that creates a new instance of vRtrConfEntry.  If the SET fails
         with the code 'inconsistentValue', then the process must be
         repeated.  If the the SET succeeds, then the object is
         incremented and the new instance is created according to the
         manager's directions."
    ::= { tmnxVRtrGlobalObjs 1 }

vRtrConfiguredVRtrs              OBJECT-TYPE
    SYNTAX      Gauge32
    MAX-ACCESS  read-only
    STATUS      current
    DESCRIPTION
        "The value of vRtrConfiguredVRtrs indicates the current number of
         virtual routers configured in the system and represented as rows in
         the vRtrConfTable."
    ::= { tmnxVRtrGlobalObjs 2 }

vRtrActiveVRtrs                  OBJECT-TYPE
    SYNTAX      Gauge32
    MAX-ACCESS  read-only
    STATUS      current
    DESCRIPTION
        "The value of vRtrActiveVRtrs indicates the current number of virtual
         routers in the system with vRtrAdminState equal 'inService'."
    ::= { tmnxVRtrGlobalObjs 3 }

vRtrRouteThresholdSoakTime       OBJECT-TYPE
    SYNTAX      Unsigned32
    UNITS       "seconds"
    MAX-ACCESS  read-write
    STATUS      current
    DESCRIPTION
        "Following the generation of a tmnxVRtrHighRouteTCA notification, the
         value of vRtrRouteThresholdSoakTime indicates the soak interval in
         seconds before another tmnxVRtrHighRouteTCA notification will be
         re-issued.  Imposing this soak period prevents continuous generation of
         notifications by the agent in the event that routes are continually
         added to a VRF after it has reached its maximum capacity.  When this
         object has a value of 0, it indicates that the agent should issue a
         single notification at the time that the value of
         vRtrHighRouteThreshold is exceeded and another notification should not
         be sent until the number of routes has fallen below the value
         configured in vRtrMidRouteThreshold."
    DEFVAL      { 600 }
    ::= { tmnxVRtrGlobalObjs 4 }

vRtrMaxARPEntries                OBJECT-TYPE
    SYNTAX      Unsigned32
    MAX-ACCESS  read-only
    STATUS      current
    DESCRIPTION
        "vRtrMaxARPEntries indicates the maximum number of active and inactive
         ARP entries supported across all virtual routers in the system."
    ::= { tmnxVRtrGlobalObjs 5 }

vRtrIPv6RouteThresholdSoakTime   OBJECT-TYPE
    SYNTAX      Unsigned32
    UNITS       "seconds"
    MAX-ACCESS  read-write
    STATUS      current
    DESCRIPTION
        "The value of object vRtrIPv6RouteThresholdSoakTime specifies the soak
         interval in seconds before another tmnxVRtrIPv6HighRouteTCA
         notification will be re-issued, after the generation of a
         tmnxVRtrIPv6HighRouteTCA notification.

         Imposing this soak period prevents continuous generation of
         notifications by the agent, in the event that routes are continually
         added to a VRF after it has reached its maximum capacity.

         When this object has a value of 0, it indicates that the agent should
         issue a single notification at the time that the value of
         vRtrIPv6HighRouteThreshold is exceeded and another notification should
         not be sent until the number of routes has fallen below the value
         configured in vRtrIPv6MidRouteThreshold."
    DEFVAL      { 600 }
    ::= { tmnxVRtrGlobalObjs 6 }

vRtrSendKeyRollover              OBJECT-TYPE
    SYNTAX      TruthValue
    MAX-ACCESS  read-only
    STATUS      current
    DESCRIPTION
        "The value of the object vRtrSendKeyRollover indicates if this system
         is currently performing a Secure Neighbor Discovery (Send) RSA (public
         key crypto-system) key pair rollover.

         During a Secure Neighbor Discovery key pair rollover, the key pair in
         use is replaced with another one; during the process,
         Cryptographically Generated Addresses (CGA) are refreshed."
    REFERENCE
        "RFC 3971 SEcure Neighbor Discovery (SEND)
         RFC 3972 Cryptographically Generated Addresses (CGA)"
    ::= { tmnxVRtrGlobalObjs 7 }

vRtrPolicyTable                  OBJECT-TYPE
    SYNTAX      SEQUENCE OF VRtrPolicyEntry
    MAX-ACCESS  not-accessible
    STATUS      current
    DESCRIPTION
        "The vRtrPolicyTable has an entry for each virtual router configured in
         the system."
    ::= { tmnxVRtrObjs 16 }

vRtrPolicyEntry                  OBJECT-TYPE
    SYNTAX      VRtrPolicyEntry
    MAX-ACCESS  not-accessible
    STATUS      current
    DESCRIPTION
        "Each row entry represents a collection of statistics for a virtual
         router in the system. Entries cannot be created and deleted via SNMP
         SET operations."
    AUGMENTS    { vRtrConfEntry }
    ::= { vRtrPolicyTable 1 }

VRtrPolicyEntry                  ::= SEQUENCE
{
    vRtrImportPolicy1                TPolicyStatementNameOrEmpty,
    vRtrImportPolicy2                TPolicyStatementNameOrEmpty,
    vRtrImportPolicy3                TPolicyStatementNameOrEmpty,
    vRtrImportPolicy4                TPolicyStatementNameOrEmpty,
    vRtrImportPolicy5                TPolicyStatementNameOrEmpty,
    vRtrExportPolicy1                TPolicyStatementNameOrEmpty,
    vRtrExportPolicy2                TPolicyStatementNameOrEmpty,
    vRtrExportPolicy3                TPolicyStatementNameOrEmpty,
    vRtrExportPolicy4                TPolicyStatementNameOrEmpty,
    vRtrExportPolicy5                TPolicyStatementNameOrEmpty,
    vRtrMvpnImportPolicy1            TPolicyStatementNameOrEmpty,
    vRtrMvpnImportPolicy2            TPolicyStatementNameOrEmpty,
    vRtrMvpnImportPolicy3            TPolicyStatementNameOrEmpty,
    vRtrMvpnImportPolicy4            TPolicyStatementNameOrEmpty,
    vRtrMvpnImportPolicy5            TPolicyStatementNameOrEmpty,
    vRtrMvpnExportPolicy1            TPolicyStatementNameOrEmpty,
    vRtrMvpnExportPolicy2            TPolicyStatementNameOrEmpty,
    vRtrMvpnExportPolicy3            TPolicyStatementNameOrEmpty,
    vRtrMvpnExportPolicy4            TPolicyStatementNameOrEmpty,
    vRtrMvpnExportPolicy5            TPolicyStatementNameOrEmpty,
    vRtrMvpnImportPolicyUnicast      TruthValue,
    vRtrMvpnExportPolicyUnicast      TruthValue,
    vRtrGrtMaxExportRoutes           Unsigned32,
    vRtrGrtExportPolicy1             TXLPolicyNameOrExpOrEmpty,
    vRtrGrtExportPolicy2             TLPolicyNameOrExpOrEmpty,
    vRtrGrtExportPolicy3             TLPolicyNameOrExpOrEmpty,
    vRtrGrtExportPolicy4             TLPolicyNameOrExpOrEmpty,
    vRtrGrtExportPolicy5             TLPolicyNameOrExpOrEmpty,
    vRtrGrtMaxIpv6ExportRoutes       Unsigned32,
    vRtrGrtImportPolicy1             TXLPolicyNameOrExpOrEmpty,
    vRtrGrtImportPolicy2             TLPolicyNameOrExpOrEmpty,
    vRtrGrtImportPolicy3             TLPolicyNameOrExpOrEmpty,
    vRtrGrtImportPolicy4             TLPolicyNameOrExpOrEmpty,
    vRtrGrtImportPolicy5             TLPolicyNameOrExpOrEmpty
}

vRtrImportPolicy1                OBJECT-TYPE
    SYNTAX      TPolicyStatementNameOrEmpty
    MAX-ACCESS  read-create
    STATUS      obsolete
    DESCRIPTION
        "The value of vRtrImportPolicy1 is the name of the first
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfImportPolicy1."
    DEFVAL      { ''H }
    ::= { vRtrPolicyEntry 1 }

vRtrImportPolicy2                OBJECT-TYPE
    SYNTAX      TPolicyStatementNameOrEmpty
    MAX-ACCESS  read-create
    STATUS      obsolete
    DESCRIPTION
        "The value of vRtrImportPolicy2 is the name of the second
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfImportPolicy2."
    DEFVAL      { ''H }
    ::= { vRtrPolicyEntry 2 }

vRtrImportPolicy3                OBJECT-TYPE
    SYNTAX      TPolicyStatementNameOrEmpty
    MAX-ACCESS  read-create
    STATUS      obsolete
    DESCRIPTION
        "The value of vRtrImportPolicy3 is the name of the third
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfImportPolicy3."
    DEFVAL      { ''H }
    ::= { vRtrPolicyEntry 3 }

vRtrImportPolicy4                OBJECT-TYPE
    SYNTAX      TPolicyStatementNameOrEmpty
    MAX-ACCESS  read-create
    STATUS      obsolete
    DESCRIPTION
        "The value of vRtrImportPolicy4 is the name of the fourth
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfImportPolicy4."
    DEFVAL      { ''H }
    ::= { vRtrPolicyEntry 4 }

vRtrImportPolicy5                OBJECT-TYPE
    SYNTAX      TPolicyStatementNameOrEmpty
    MAX-ACCESS  read-create
    STATUS      obsolete
    DESCRIPTION
        "The value of vRtrImportPolicy5 is the name of the fifth
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfImportPolicy5."
    DEFVAL      { ''H }
    ::= { vRtrPolicyEntry 5 }

vRtrExportPolicy1                OBJECT-TYPE
    SYNTAX      TPolicyStatementNameOrEmpty
    MAX-ACCESS  read-create
    STATUS      obsolete
    DESCRIPTION
        "The value of vRtrExportPolicy1 is the name of the first
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfExportPolicy1."
    DEFVAL      { ''H }
    ::= { vRtrPolicyEntry 6 }

vRtrExportPolicy2                OBJECT-TYPE
    SYNTAX      TPolicyStatementNameOrEmpty
    MAX-ACCESS  read-create
    STATUS      obsolete
    DESCRIPTION
        "The value of vRtrExportPolicy2 is the name of the second
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfExportPolicy2."
    DEFVAL      { ''H }
    ::= { vRtrPolicyEntry 7 }

vRtrExportPolicy3                OBJECT-TYPE
    SYNTAX      TPolicyStatementNameOrEmpty
    MAX-ACCESS  read-create
    STATUS      obsolete
    DESCRIPTION
        "The value of vRtrExportPolicy3 is the name of the third
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfExportPolicy3."
    DEFVAL      { ''H }
    ::= { vRtrPolicyEntry 8 }

vRtrExportPolicy4                OBJECT-TYPE
    SYNTAX      TPolicyStatementNameOrEmpty
    MAX-ACCESS  read-create
    STATUS      obsolete
    DESCRIPTION
        "The value of vRtrExportPolicy4 is the name of the fourth
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfExportPolicy4."
    DEFVAL      { ''H }
    ::= { vRtrPolicyEntry 9 }

vRtrExportPolicy5                OBJECT-TYPE
    SYNTAX      TPolicyStatementNameOrEmpty
    MAX-ACCESS  read-create
    STATUS      obsolete
    DESCRIPTION
        "The value of vRtrExportPolicy5 is the name of the fifth
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrVrfExportPolicy5."
    DEFVAL      { ''H }
    ::= { vRtrPolicyEntry 10 }

vRtrMvpnImportPolicy1            OBJECT-TYPE
    SYNTAX      TPolicyStatementNameOrEmpty
    MAX-ACCESS  read-create
    STATUS      obsolete
    DESCRIPTION
        "The value of vRtrMvpnImportPolicy1 is the name of the first
         policy to be used for determining which multicast routes are imported
         into the VRF for this virtual router.  If no import policy
         is defined, no routes are accepted into the VRF.

         If multiple policy names are specified, the policies are evaluated
         in the order they are specified.  The first policy that matches
         is applied.

         The import policy name list, vRtrMvpnImportPolicy1 through
         vRtrMvpnImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfImportPolicy1."
    DEFVAL      { ''H }
    ::= { vRtrPolicyEntry 11 }

vRtrMvpnImportPolicy2            OBJECT-TYPE
    SYNTAX      TPolicyStatementNameOrEmpty
    MAX-ACCESS  read-create
    STATUS      obsolete
    DESCRIPTION
        "The value of vRtrMvpnImportPolicy2 is the name of the second
         policy to be used for determining which multicast routes are imported
         into the VRF for this virtual router.  If no import policy
         is defined, no routes are accepted into the VRF.

         If multiple policy names are specified, the policies are evaluated
         in the order they are specified.  The first policy that matches
         is applied.

         The import policy name list, vRtrMvpnImportPolicy1 through
         vRtrMvpnImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfImportPolicy2."
    DEFVAL      { ''H }
    ::= { vRtrPolicyEntry 12 }

vRtrMvpnImportPolicy3            OBJECT-TYPE
    SYNTAX      TPolicyStatementNameOrEmpty
    MAX-ACCESS  read-create
    STATUS      obsolete
    DESCRIPTION
        "The value of vRtrMvpnImportPolicy3 is the name of the third
         policy to be used for determining which multicast routes are imported
         into the VRF for this virtual router.  If no import policy
         is defined, no routes are accepted into the VRF.

         If multiple policy names are specified, the policies are evaluated
         in the order they are specified.  The first policy that matches
         is applied.

         The import policy name list, vRtrMvpnImportPolicy1 through
         vRtrMvpnImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfImportPolicy3."
    DEFVAL      { ''H }
    ::= { vRtrPolicyEntry 13 }

vRtrMvpnImportPolicy4            OBJECT-TYPE
    SYNTAX      TPolicyStatementNameOrEmpty
    MAX-ACCESS  read-create
    STATUS      obsolete
    DESCRIPTION
        "The value of vRtrMvpnImportPolicy4 is the name of the fourth
         policy to be used for determining which multicast routes are imported
         into the VRF for this virtual router.  If no import policy
         is defined, no routes are accepted into the VRF.

         If multiple policy names are specified, the policies are evaluated
         in the order they are specified.  The first policy that matches
         is applied.

         The import policy name list, vRtrMvpnImportPolicy1 through
         vRtrMvpnImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfImportPolicy4."
    DEFVAL      { ''H }
    ::= { vRtrPolicyEntry 14 }

vRtrMvpnImportPolicy5            OBJECT-TYPE
    SYNTAX      TPolicyStatementNameOrEmpty
    MAX-ACCESS  read-create
    STATUS      obsolete
    DESCRIPTION
        "The value of vRtrMvpnImportPolicy5 is the name of the fifth
         policy to be used for determining which multicast routes are imported
         into the VRF for this virtual router.  If no import policy
         is defined, no routes are accepted into the VRF.

         If multiple policy names are specified, the policies are evaluated
         in the order they are specified.  The first policy that matches
         is applied.

         The import policy name list, vRtrMvpnImportPolicy1 through
         vRtrMvpnImportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfImportPolicy5."
    DEFVAL      { ''H }
    ::= { vRtrPolicyEntry 15 }

vRtrMvpnExportPolicy1            OBJECT-TYPE
    SYNTAX      TPolicyStatementNameOrEmpty
    MAX-ACCESS  read-create
    STATUS      obsolete
    DESCRIPTION
        "The value of vRtrMvpnExportPolicy1 is the name of the first
         policy to be used for determining which multicast routes are exported
         from the VRF for this virtual router.  If no export policy
         is defined, no routes are exported from the VRF.

         If multiple policy names are specified, the policies are evaluated
         in the order they are specified.  The first policy that matches
         is applied.

         The export policy name list, vRtrMvpnExportPolicy1 through
         vRtrMvpnExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfExportPolicy1."
    DEFVAL      { ''H }
    ::= { vRtrPolicyEntry 16 }

vRtrMvpnExportPolicy2            OBJECT-TYPE
    SYNTAX      TPolicyStatementNameOrEmpty
    MAX-ACCESS  read-create
    STATUS      obsolete
    DESCRIPTION
        "The value of vRtrMvpnExportPolicy2 is the name of the second
         policy to be used for determining which multicast routes are exported
         from the VRF for this virtual router.  If no export policy
         is defined, no routes are exported from the VRF.

         If multiple policy names are specified, the policies are evaluated
         in the order they are specified.  The first policy that matches
         is applied.

         The export policy name list, vRtrMvpnExportPolicy1 through
         vRtrMvpnExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfExportPolicy2."
    DEFVAL      { ''H }
    ::= { vRtrPolicyEntry 17 }

vRtrMvpnExportPolicy3            OBJECT-TYPE
    SYNTAX      TPolicyStatementNameOrEmpty
    MAX-ACCESS  read-create
    STATUS      obsolete
    DESCRIPTION
        "The value of vRtrMvpnExportPolicy3 is the name of the third
         policy to be used for determining which multicast routes are exported
         from the VRF for this virtual router.  If no export policy
         is defined, no routes are exported from the VRF.

         If multiple policy names are specified, the policies are evaluated
         in the order they are specified.  The first policy that matches
         is applied.

         The export policy name list, vRtrMvpnExportPolicy1 through
         vRtrMvpnExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfExportPolicy3."
    DEFVAL      { ''H }
    ::= { vRtrPolicyEntry 18 }

vRtrMvpnExportPolicy4            OBJECT-TYPE
    SYNTAX      TPolicyStatementNameOrEmpty
    MAX-ACCESS  read-create
    STATUS      obsolete
    DESCRIPTION
        "The value of vRtrMvpnExportPolicy4 is the name of the fourth
         policy to be used for determining which multicast routes are exported
         from the VRF for this virtual router.  If no export policy
         is defined, no routes are exported from the VRF.

         If multiple policy names are specified, the policies are evaluated
         in the order they are specified.  The first policy that matches
         is applied.

         The export policy name list, vRtrMvpnExportPolicy1 through
         vRtrMvpnExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfExportPolicy4."
    DEFVAL      { ''H }
    ::= { vRtrPolicyEntry 19 }

vRtrMvpnExportPolicy5            OBJECT-TYPE
    SYNTAX      TPolicyStatementNameOrEmpty
    MAX-ACCESS  read-create
    STATUS      obsolete
    DESCRIPTION
        "The value of vRtrMvpnExportPolicy5 is the name of the fifth
         policy to be used for determining which multicast routes are exported
         from the VRF for this virtual router.  If no export policy
         is defined, no routes are exported from the VRF.

         If multiple policy names are specified, the policies are evaluated
         in the order they are specified.  The first policy that matches
         is applied.

         The export policy name list, vRtrMvpnExportPolicy1 through
         vRtrMvpnExportPolicy5, is handled by the SNMP agent as a single
         entity.  When an SNMP SET request is received to modify one or
         more of the policy names, all the policy variables are first
         set to the empty string, ''H, and then the new names are set
         into the specified policy variables within a single SNMP SET PDU.

         This object was obsoleted in release 10.0. It is replaced by object
         vRtrMvpnVrfExportPolicy5."
    DEFVAL      { ''H }
    ::= { vRtrPolicyEntry 20 }

vRtrMvpnImportPolicyUnicast      OBJECT-TYPE
    SYNTAX      TruthValue
    MAX-ACCESS  read-create
    STATUS      current
    DESCRIPTION
        "The value of vRtrMvpnImportPolicyUnicast specifies whether unicast
         vrf-import policy is used for the Multicast VPN (MVPN) as well.

         If the value is 'true', vRtrImportPolicy1 through vRtrImportPolicy5
         are used for MVPN.

         If the value is 'false', vRtrMvpnImportPolicy1 through
         vRtrMvpnImportPolicy5 are used for MVPN."
    DEFVAL      { false }
    ::= { vRtrPolicyEntry 21 }

vRtrMvpnExportPolicyUnicast      OBJECT-TYPE
    SYNTAX      TruthValue
    MAX-ACCESS  read-create
    STATUS      current
    DESCRIPTION
        "The value of vRtrMvpnExportPolicyUnicast specifies whether unicast
         vrf-export policy is used for the Multicast VPN (MVPN) as well.

         If the value is 'true', vRtrExportPolicy1 through vRtrExportPolicy5 is
         used for MVPN.

         If the value is 'false', vRtrMvpnExportPolicy1 through
         vRtrMvpnExportPolicy5 is used for MVPN."
    DEFVAL      { false }
    ::= { vRtrPolicyEntry 22 }

vRtrGrtMaxExportRoutes           OBJECT-TYPE
    SYNTAX      Unsigned32 (0..1000)
    MAX-ACCESS  read-create
    STATUS      current
    DESCRIPTION
        "The value of vRtrGrtMaxExportRoutes specifies the maximum number of
         routes that can be exported from the VRF to the GRT."
    DEFVAL      { 5 }
    ::= { vRtrPolicyEntry 23 }

vRtrGrtExportPolicy1             OBJECT-TYPE
    SYNTAX      TXLPolicyNameOrExpOrEmpty
    MAX-ACCESS  read-create
    STATUS      current
    DESCRIPTION
        "The value of vRtrGrtExportPolicy1 specifies the name of the first
         policy to be used for determining which routes are exported from the
         VRF to the GRT. These entries will be marked as BGP-VPN routes in the
         GRT. If no export policy is defined, no routes are exported from the
         VRF.

         If multiple policy names are specified, the policies are evaluated
         in the order they are specified.  The first policy that matches
         is applied.

         The export policy name list, vRtrGrtExportPolicy1 through
         vRtrGrtExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrPolicyEntry 24 }

vRtrGrtExportPolicy2             OBJECT-TYPE
    SYNTAX      TLPolicyNameOrExpOrEmpty
    MAX-ACCESS  read-create
    STATUS      current
    DESCRIPTION
        "The value of vRtrGrtExportPolicy2 specifies the name of the second
         policy to be used for determining which routes are exported from the
         VRF to the GRT. These entries will be marked as BGP-VPN routes in the
         GRT. If no export policy is defined, no routes are exported from the
         VRF.

         If multiple policy names are specified, the policies are evaluated
         in the order they are specified.  The first policy that matches
         is applied.

         The export policy name list, vRtrGrtExportPolicy1 through
         vRtrGrtExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrPolicyEntry 25 }

vRtrGrtExportPolicy3             OBJECT-TYPE
    SYNTAX      TLPolicyNameOrExpOrEmpty
    MAX-ACCESS  read-create
    STATUS      current
    DESCRIPTION
        "The value of vRtrGrtExportPolicy3 specifies the name of the third
         policy to be used for determining which routes are exported from the
         VRF to the GRT. These entries will be marked as BGP-VPN routes in the
         GRT. If no export policy is defined, no routes are exported from the
         VRF.

         If multiple policy names are specified, the policies are evaluated
         in the order they are specified.  The first policy that matches
         is applied.

         The export policy name list, vRtrGrtExportPolicy1 through
         vRtrGrtExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrPolicyEntry 26 }

vRtrGrtExportPolicy4             OBJECT-TYPE
    SYNTAX      TLPolicyNameOrExpOrEmpty
    MAX-ACCESS  read-create
    STATUS      current
    DESCRIPTION
        "The value of vRtrGrtExportPolicy4 specifies the name of the fourth
         policy to be used for determining which routes are exported from the
         VRF to the GRT. These entries will be marked as BGP-VPN routes in the
         GRT. If no export policy is defined, no routes are exported from the
         VRF.

         If multiple policy names are specified, the policies are evaluated
         in the order they are specified.  The first policy that matches
         is applied.

         The export policy name list, vRtrGrtExportPolicy1 through
         vRtrGrtExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrPolicyEntry 27 }

vRtrGrtExportPolicy5             OBJECT-TYPE
    SYNTAX      TLPolicyNameOrExpOrEmpty
    MAX-ACCESS  read-create
    STATUS      current
    DESCRIPTION
        "The value of vRtrGrtExportPolicy5 specifies the name of the fifth
         policy to be used for determining which routes are exported from the
         VRF to the GRT. These entries will be marked as BGP-VPN routes in the
         GRT. If no export policy is defined, no routes are exported from the
         VRF.

         If multiple policy names are specified, the policies are evaluated
         in the order they are specified.  The first policy that matches
         is applied.

         The export policy name list, vRtrGrtExportPolicy1 through
         vRtrGrtExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrPolicyEntry 28 }

vRtrGrtMaxIpv6ExportRoutes       OBJECT-TYPE
    SYNTAX      Unsigned32 (0..1000)
    MAX-ACCESS  read-create
    STATUS      current
    DESCRIPTION
        "The value of vRtrGrtMaxIpv6ExportRoutes specifies the maximum number
         of IPv6 routes that can be exported from the VRF to the GRT. When the
         value of this object is set to '0', there is no limit on the number of
         routes exported from the VRF to the GRT."
    DEFVAL      { 5 }
    ::= { vRtrPolicyEntry 29 }

vRtrGrtImportPolicy1             OBJECT-TYPE
    SYNTAX      TXLPolicyNameOrExpOrEmpty
    MAX-ACCESS  read-create
    STATUS      current
    DESCRIPTION
        "The value of vRtrGrtImportPolicy1 specifies the name of the first
         policy to be used for determining which routes are imported from the
         GRT to the VRF. If no import policy is defined, no routes are imported
         from the GRT.

         If multiple policy names are specified, the policies are evaluated
         in the order they are specified.  The first policy that matches
         is applied.

         The import policy name list, vRtrGrtImportPolicy1 through
         vRtrGrtImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrPolicyEntry 30 }

vRtrGrtImportPolicy2             OBJECT-TYPE
    SYNTAX      TLPolicyNameOrExpOrEmpty
    MAX-ACCESS  read-create
    STATUS      current
    DESCRIPTION
        "The value of vRtrGrtImportPolicy2 specifies the name of the second
         policy to be used for determining which routes are imported from the
         GRT to the VRF.If no import policy is defined, no routes are imported
         from the GRT.

         If multiple policy names are specified, the policies are evaluated
         in the order they are specified.  The first policy that matches
         is applied.

         The import policy name list, vRtrGrtImportPolicy1 through
         vRtrGrtImportPolicy5, is handled by the SNMP agent as a single
         entity.  When an SNMP SET request is received to modify one or
         more of the policy names, all the policy variables are first
         set to the empty string, ''H, and then the new names are set
         into the specified policy variables within a single SNMP SET PDU.

         It is required to configure vRtrGrtImportPolicy1 before configuring
         vRtrGrtImportPolicy2."
    DEFVAL      { ''H }
    ::= { vRtrPolicyEntry 31 }

vRtrGrtImportPolicy3             OBJECT-TYPE
    SYNTAX      TLPolicyNameOrExpOrEmpty
    MAX-ACCESS  read-create
    STATUS      current
    DESCRIPTION
        "The value of vRtrGrtImportPolicy3 specifies the name of the third
         policy to be used for determining which routes are imported from the
         GRT to the VRF. If no import policy is defined, no routes are imported
         from the GRT.

         If multiple policy names are specified, the policies are evaluated
         in the order they are specified.  The first policy that matches
         is applied.

         The import policy name list, vRtrGrtImportPolicy1 through
         vRtrGrtImportPolicy5, is handled by the SNMP agent as a single
         entity.  When an SNMP SET request is received to modify one or
         more of the policy names, all the policy variables are first
         set to the empty string, ''H, and then the new names are set
         into the specified policy variables within a single SNMP SET PDU.

         It is required to configure vRtrGrtImportPolicy2 before configuring
         vRtrGrtImportPolicy3."
    DEFVAL      { ''H }
    ::= { vRtrPolicyEntry 32 }

vRtrGrtImportPolicy4             OBJECT-TYPE
    SYNTAX      TLPolicyNameOrExpOrEmpty
    MAX-ACCESS  read-create
    STATUS      current
    DESCRIPTION
        "The value of vRtrGrtImportPolicy4 specifies the name of the fourth
         policy to be used for determining which routes are imported from the
         GRT to the VRF. If no import policy is defined, no routes are imported
         from the GRT.

         If multiple policy names are specified, the policies are evaluated
         in the order they are specified.  The first policy that matches
         is applied.

         The import policy name list, vRtrGrtImportPolicy1 through
         vRtrGrtImportPolicy5, is handled by the SNMP agent as a single
         entity.  When an SNMP SET request is received to modify one or
         more of the policy names, all the policy variables are first
         set to the empty string, ''H, and then the new names are set
         into the specified policy variables within a single SNMP SET PDU.

         It is required to configure vRtrGrtImportPolicy3 before configuring
         vRtrGrtImportPolicy4."
    DEFVAL      { ''H }
    ::= { vRtrPolicyEntry 33 }

vRtrGrtImportPolicy5             OBJECT-TYPE
    SYNTAX      TLPolicyNameOrExpOrEmpty
    MAX-ACCESS  read-create
    STATUS      current
    DESCRIPTION
        "The value of vRtrGrtImportPolicy5 specifies the name of the fifth
         policy to be used for determining which routes are imported from the
         GRT to the VRF. If no import policy is defined, no routes are imported
         from the GRT.

         If multiple policy names are specified, the policies are evaluated
         in the order they are specified.  The first policy that matches
         is applied.

         The import policy name list, vRtrGrtImportPolicy1 through
         vRtrGrtImportPolicy5, is handled by the SNMP agent as a single
         entity.  When an SNMP SET request is received to modify one or
         more of the policy names, all the policy variables are first
         set to the empty string, ''H, and then the new names are set
         into the specified policy variables within a single SNMP SET PDU.

         It is required to configure vRtrGrtImportPolicy4 before configuring
         vRtrGrtImportPolicy5."
    DEFVAL      { ''H }
    ::= { vRtrPolicyEntry 34 }

vRtrTunnelTable                  OBJECT-TYPE
    SYNTAX      SEQUENCE OF VRtrTunnelEntry
    MAX-ACCESS  not-accessible
    STATUS      obsolete
    DESCRIPTION
        "vRtrTunnelTable maintains a list of tunnels for the specific router
         instance.

         This table has been replaced by vRtrInetTunnelTable in 13.0."
    ::= { tmnxVRtrObjs 17 }

vRtrTunnelEntry                  OBJECT-TYPE
    SYNTAX      VRtrTunnelEntry
    MAX-ACCESS  not-accessible
    STATUS      obsolete
    DESCRIPTION
        "vRtrTunnelEntry defines a tunnel to a particular destination in a
         specific router context. A tunnel to a specific destination could
         established using GRE, LDP, RSVP or could be a static LSP."
    INDEX       {
        vRtrID,
        vRtrTunnelDest,
        vRtrTunnelMask,
        vRtrTunnelPreference,
        vRtrTunnelType,
        vRtrTunnelID,
        vRtrTunnelNexthop
    }
    ::= { vRtrTunnelTable 1 }

VRtrTunnelEntry                  ::= SEQUENCE
{
    vRtrTunnelDest                   IpAddress,
    vRtrTunnelMask                   IpAddress,
    vRtrTunnelPreference             Unsigned32,
    vRtrTunnelType                   TmnxTunnelType,
    vRtrTunnelID                     TmnxTunnelID,
    vRtrTunnelNexthop                IpAddress,
    vRtrTunnelMetric                 Unsigned32,
    vRtrTunnelAge                    Integer32,
    vRtrTunnelNextHopFlags           INTEGER
}

vRtrTunnelDest                   OBJECT-TYPE
    SYNTAX      IpAddress
    MAX-ACCESS  not-accessible
    STATUS      obsolete
    DESCRIPTION
        "vRtrTunnelDest maintains the destination IP address of this tunnel.
         This object may not take a Multicast (Class  D) address value.

         Any assignment (implicit or otherwise) of an instance of this object
         to a value x must be rejected if the bitwise logical-AND of x with the
         value of the corresponding instance of the vRtrTunnelMask object is
         not equal to x."
    ::= { vRtrTunnelEntry 1 }

vRtrTunnelMask                   OBJECT-TYPE
    SYNTAX      IpAddress
    MAX-ACCESS  not-accessible
    STATUS      obsolete
    DESCRIPTION
        "vRtrTunnelMask indicates the mask to be logical-ANDed with the
         destination address before being compared to the value in the
         vRtrTunnelDest field. For those systems that do not support arbitrary
         subnet masks, an agent constructs the value of the vRtrTunnelMask by
         reference to the IP Address Class.

         Any assignment (implicit or otherwise) of an instance of this object
         to a value x must be rejected if the bitwise logical-AND of x with the
         value of the corresponding instance of the ipCidrRouteDest object is
         not equal to ipCidrRouteDest."
    ::= { vRtrTunnelEntry 2 }

vRtrTunnelPreference             OBJECT-TYPE
    SYNTAX      Unsigned32 (1..255)
    MAX-ACCESS  not-accessible
    STATUS      obsolete
    DESCRIPTION
        "The value of vRtrTunnelPreference determines the priority of this
         tunnel versus the other tunnels from different sources such as LDP,
         RSVP, GRE etc. This is an absolute number used internally by the
         system to specify preferences for the tunnel.

         Lowest number signifies the most preferred entry in the table."
    ::= { vRtrTunnelEntry 3 }

vRtrTunnelType                   OBJECT-TYPE
    SYNTAX      TmnxTunnelType
    MAX-ACCESS  not-accessible
    STATUS      obsolete
    DESCRIPTION
        "The type of this tunnel entity."
    ::= { vRtrTunnelEntry 4 }

vRtrTunnelID                     OBJECT-TYPE
    SYNTAX      TmnxTunnelID
    MAX-ACCESS  not-accessible
    STATUS      obsolete
    DESCRIPTION
        "Additional index provided to distinguish between multiple tunnels to
         same destination having same characteristics.

         There could be multiple tunnels for the type 'sdp'. In such cases the
         vRtrTunnelID will hold the SDP Id.

         There could be multiple tunnels for the type 'ldp'. In such cases the
         vRtrTunnelID will hold the LSPId of the LSP in use.

         For other vRtrTunnelType values this field will always be 0 as only a
         single tunnel is established using other tunnel types."
    ::= { vRtrTunnelEntry 5 }

vRtrTunnelNexthop                OBJECT-TYPE
    SYNTAX      IpAddress
    MAX-ACCESS  not-accessible
    STATUS      obsolete
    DESCRIPTION
        "The address of the next system en route; Otherwise, 0.0.0.0."
    ::= { vRtrTunnelEntry 6 }

vRtrTunnelMetric                 OBJECT-TYPE
    SYNTAX      Unsigned32
    MAX-ACCESS  read-only
    STATUS      obsolete
    DESCRIPTION
        "vRtrTunnelMetric maintains the metric of the tunnel. This is used in
         addition to the preference for this tunnel."
    ::= { vRtrTunnelEntry 7 }

vRtrTunnelAge                    OBJECT-TYPE
    SYNTAX      Integer32
    MAX-ACCESS  read-only
    STATUS      obsolete
    DESCRIPTION
        "The number of seconds  since this tunnel entry was last
         updated or otherwise determined to be correct. No semantics
         of  `too  old' can  be implied except through knowledge of
         owner of the tunnel."
    ::= { vRtrTunnelEntry 8 }

vRtrTunnelNextHopFlags           OBJECT-TYPE
    SYNTAX      INTEGER {
        none          (0),
        hasLfa        (1),
        hasBackup     (2),
        isBackup      (3),
        isBgpInactive (4)
    }
    MAX-ACCESS  read-only
    STATUS      obsolete
    DESCRIPTION
        "The value of vRtrTunnelNextHopFlags indicates the properties of the
         tunnel next hop.

         A value of 'none' indicates that no next-hop is present.

         A value of 'hasLfa' indicates that an LFA next-hop is present in
         addition to the regular next-hop.

         A value of 'hasBackup' indicates that this route has a backup route.

         A value of 'isBackup' indicates that this route is a backup route to
         another route with the same prefix.

         A value of 'isBgpInactive' indicates that this route is an inactive
         best-external route exported from BGP."
    ::= { vRtrTunnelEntry 9 }

vRtrIfProxyArpTable              OBJECT-TYPE
    SYNTAX      SEQUENCE OF VRtrIfProxyArpEntry
    MAX-ACCESS  not-accessible
    STATUS      current
    DESCRIPTION
        "The vRtrIfProxyArpTable provides an extension to the vRtrIfTable. It
         has an entry for each virtual router interface configured in the
         system."
    ::= { tmnxVRtrObjs 18 }

vRtrIfProxyArpEntry              OBJECT-TYPE
    SYNTAX      VRtrIfProxyArpEntry
    MAX-ACCESS  not-accessible
    STATUS      current
    DESCRIPTION
        "Each row entry represents information related to Proxy ARP for a
         virtual router interface in the system.

         Entries cannot be created and deleted via SNMP SET operations."
    AUGMENTS    { vRtrIfEntry }
    ::= { vRtrIfProxyArpTable 1 }

VRtrIfProxyArpEntry              ::= SEQUENCE
{
    vRtrIfProxyArp                   TruthValue,
    vRtrIfProxyArpLocal              TruthValue,
    vRtrIfProxyArpPolicy1            TPolicyStatementNameOrEmpty,
    vRtrIfProxyArpPolicy2            TPolicyStatementNameOrEmpty,
    vRtrIfProxyArpPolicy3            TPolicyStatementNameOrEmpty,
    vRtrIfProxyArpPolicy4            TPolicyStatementNameOrEmpty,
    vRtrIfProxyArpPolicy5            TPolicyStatementNameOrEmpty
}

vRtrIfProxyArp                   OBJECT-TYPE
    SYNTAX      TruthValue
    MAX-ACCESS  read-create
    STATUS      current
    DESCRIPTION
        "If the value of vRtrIfProxyArp is set to 'true', proxy ARP is enabled
         on this interface. If this value is 'false', proxy ARP is disabled on
         the interface."
    DEFVAL      { false }
    ::= { vRtrIfProxyArpEntry 1 }

vRtrIfProxyArpLocal              OBJECT-TYPE
    SYNTAX      TruthValue
    MAX-ACCESS  read-create
    STATUS      current
    DESCRIPTION
        "If the value of vRtrIfProxyArpLocal is set to 'true', local proxy ARP
         is enabled, that is, the interface will reply to ARP requests even if
         both the hosts are on the same subnet. In this case ICMP redirects
         will be disabled. If the value of vRtrIfProxyArpLocal is set to
         'false', the interface will not reply to ARP requests if both the
         hosts are on the same subnet."
    DEFVAL      { false }
    ::= { vRtrIfProxyArpEntry 2 }

vRtrIfProxyArpPolicy1            OBJECT-TYPE
    SYNTAX      TPolicyStatementNameOrEmpty
    MAX-ACCESS  read-create
    STATUS      current
    DESCRIPTION
        "The value of vRtrIfProxyArpPolicy1 is used to specify the first proxy
         ARP policy for this interface. This policy determines networks and
         sources for which proxy ARP will be attempted. If this value is set to
         an empty string, ''H, the interface does not have a proxy ARP policy
         associated with it.

         The value of vRtrIfProxyArpPolicy1 has no effect if vRtrIfProxyArp is
         set to 'false'."
    DEFVAL      { ''H }
    ::= { vRtrIfProxyArpEntry 3 }

vRtrIfProxyArpPolicy2            OBJECT-TYPE
    SYNTAX      TPolicyStatementNameOrEmpty
    MAX-ACCESS  read-create
    STATUS      current
    DESCRIPTION
        "The value of vRtrIfProxyArpPolicy2 is used to specify the second proxy
         ARP policy for this interface. This policy determines networks and
         sources for which proxy ARP will be attempted. If this value is set to
         an empty string, ''H, the interface does not have a proxy ARP policy
         associated with it.

         The value of vRtrIfProxyArpPolicy2 has no effect if vRtrIfProxyArp is
         set to 'false'."
    DEFVAL      { ''H }
    ::= { vRtrIfProxyArpEntry 4 }

vRtrIfProxyArpPolicy3            OBJECT-TYPE
    SYNTAX      TPolicyStatementNameOrEmpty
    MAX-ACCESS  read-create
    STATUS      current
    DESCRIPTION
        "The value of vRtrIfProxyArpPolicy3 is used to specify the third proxy
         ARP policy for this interface. This policy determines networks and
         sources for which proxy ARP will be attempted. If this value is set to
         an empty string, ''H, the interface does not have a proxy ARP policy
         associated with it.

         The value of vRtrIfProxyArpPolicy3 has no effect if vRtrIfProxyArp is
         set to 'false'."
    DEFVAL      { ''H }
    ::= { vRtrIfProxyArpEntry 5 }

vRtrIfProxyArpPolicy4            OBJECT-TYPE
    SYNTAX      TPolicyStatementNameOrEmpty
    MAX-ACCESS  read-create
    STATUS      current
    DESCRIPTION
        "The value of vRtrIfProxyArpPolicy4 is used to specify the fourth proxy
         ARP policy for this interface. This policy determines networks and
         sources for which proxy ARP will be attempted. If this value is set to
         an empty string, ''H, the interface does not have a proxy ARP policy
         associated with it.

         The value of vRtrIfProxyArpPolicy4 has no effect if vRtrIfProxyArp is
         set to 'false'."
    DEFVAL      { ''H }
    ::= { vRtrIfProxyArpEntry 6 }

vRtrIfProxyArpPolicy5            OBJECT-TYPE
    SYNTAX      TPolicyStatementNameOrEmpty
    MAX-ACCESS  read-create
    STATUS      current
    DESCRIPTION
        "The value of vRtrIfProxyArpPolicy5 is used to specify the fifth proxy
         ARP policy for this interface. This policy determines networks and
         sources for which proxy ARP will be attempted. If this value is set to
         an empty string, ''H, the interface does not have a proxy ARP policy
         associated with it.

         The value of vRtrIfProxyArpPolicy5 has no effect if vRtrIfProxyArp is
         set to 'false'."
    DEFVAL      { ''H }
    ::= { vRtrIfProxyArpEntry 7 }

vRtrIfDHCPTable                  OBJECT-TYPE
    SYNTAX      SEQUENCE OF VRtrIfDHCPEntry
    MAX-ACCESS  not-accessible
    STATUS      current
    DESCRIPTION
        "The vRtrIfDHCPTable is used to configure the interface parameters for
         the DHCP Relay agent."
    ::= { tmnxVRtrObjs 19 }

vRtrIfDHCPEntry                  OBJECT-TYPE
    SYNTAX      VRtrIfDHCPEntry
    MAX-ACCESS  not-accessible
    STATUS      current
    DESCRIPTION
        "Each row entry represents information related to DHCP Relay for a
         virtual router interface in the system.

         Entries cannot be created and deleted via SNMP SET operations."
    AUGMENTS    { vRtrIfEntry }
    ::= { vRtrIfDHCPTable 1 }

VRtrIfDHCPEntry                  ::= SEQUENCE
{
    vRtrIfDHCPRelayInfoOption        TruthValue,
    vRtrIfDHCPRelayInfoAction        INTEGER,
    vRtrIfDHCPRelayCircuitId         INTEGER,
    vRtrIfDHCPRelayRemoteId          INTEGER,
    vRtrIfDHCPAutoFilter             Unsigned32,
    vRtrIfDHCPRelayServer1           IpAddress,
    vRtrIfDHCPRelayServer2           IpAddress,
    vRtrIfDHCPRelayServer3           IpAddress,
    vRtrIfDHCPRelayServer4           IpAddress,
    vRtrIfDHCPRelayServer5           IpAddress,
    vRtrIfDHCPRelayServer6           IpAddress,
    vRtrIfDHCPRelayServer7           IpAddress,
    vRtrIfDHCPRelayServer8           IpAddress,
    vRtrIfDHCPRelayTrusted           TruthValue,
    vRtrIfDHCPAdminState             TmnxAdminState,
    vRtrIfDHCPSnooping               INTEGER,
    vRtrIfDHCPDescription            TItemDescription,
    vRtrIfDHCPAutoFilterId           TFilterID,
    vRtrIfDHCPOperAutoFilter         Unsigned32,
    vRtrIfDHCPAuthPolicy             TPolicyStatementNameOrEmpty,
    vRtrIfDHCPLeasePopulate          Unsigned32,
    vRtrIfDHCPOperLeasePopulate      Unsigned32,
    vRtrIfDHCPGiAddressType          InetAddressType,
    vRtrIfDHCPGiAddress              InetAddress,
    vRtrIfDHCPGiAddressAsSrc         TruthValue,
    vRtrIfDHCPMatchOption82          TruthValue,
    vRtrIfDHCPRelayRemoteIdStr       DisplayString,
    vRtrIfDHCPProxyAdminState        TmnxAdminState,
    vRtrIfDHCPProxyServerAddr        IpAddress,
    vRtrIfDHCPProxyLeaseTime         Unsigned32,
    vRtrIfDHCPProxyLTRadiusOverride  TruthValue,
    vRtrIfDHCPVendorIncludeOptions   BITS,
    vRtrIfDHCPVendorOptionString     DisplayString,
    vRtrIfDHCPLayer2Header           TruthValue,
    vRtrIfDHCPAntiSpoofMacAddr       MacAddress,
    vRtrIfDHCPClientApplications     BITS,
    vRtrIfDHCPRelayPlainBootp        INTEGER,
    vRtrIfDHCPUserDb                 TNamedItemOrEmpty,
    vRtrIfDHCPUseArpForReply         TruthValue,
    vRtrIfDHCPFilterId               TDHCPFilterID,
    vRtrIfDHCPRelayUnicastMsg        INTEGER,
    vRtrIfDHCPPythonPolicy           TNamedItemOrEmpty,
    vRtrIfDHCPVirtualSubnet          TmnxEnabledDisabled,
    vRtrIfDHCPRelaySiaddrOvrAddrType InetAddressType,
    vRtrIfDHCPRelaySiaddrOvrAddr     InetAddress,
    vRtrIfDHCPOSelDiscoDly           Integer32,
    vRtrIfDHCPOSelClntMac            INTEGER,
    vRtrIfDHCPOSelClntMacDiscoDly    Integer32,
    vRtrIfDHCPReleaseIncludeGiaddr   TruthValue,
    vRtrIfDHCPRelayForceRenewWoLease TruthValue
}

vRtrIfDHCPRelayInfoOption        OBJECT-TYPE
    SYNTAX      TruthValue
    MAX-ACCESS  read-create
    STATUS      obsolete
    DESCRIPTION
        "vRtrIfDHCPRelayInfoOption is used to enable/disable DHCP Option 82. If
         the value of this object is set to 'false', DHCP Relay is disabled."
    DEFVAL      { false }
    ::= { vRtrIfDHCPEntry 1 }

vRtrIfDHCPRelayInfoAction        OBJECT-TYPE
    SYNTAX      INTEGER {
        replace (1),
        drop    (2),
        keep    (3)
    }
    MAX-ACCESS  read-create
    STATUS      current
    DESCRIPTION
        "vRtrIfDHCPRelayInfoAction is used to configure the DHCP Relay
         reforwarding policy.

         replace(1) - replace existing information with
                      DHCP relay information
         drop(2)    - discard messages with existing relay information if
                      the option 82 information is also present.
         keep(3)    - retain the existing relay information."
    DEFVAL      { keep }
    ::= { vRtrIfDHCPEntry 2 }

vRtrIfDHCPRelayCircuitId         OBJECT-TYPE
    SYNTAX      INTEGER {
        none           (0),
        ifIndex        (1),
        asciiTuple     (2),
        sapId          (3),
        vlanAsciiTuple (4),
        portId         (5),
        ifName         (6)
    }
    MAX-ACCESS  read-create
    STATUS      current
    DESCRIPTION
        "The value of the object vRtrIfDHCPRelayCircuitId specifies whether or
         not the circuit-id suboption is present, and if it is present what
         information goes in it.
         If the value of this object is set to 'none', the circuit-id suboption
         will not be part of the information option (option 82).
         If the value of this object is set to 'ifIndex', the value of the
         interface index is used.
         If the value of this object is set to 'asciiTuple', the ASCII-encoded
         concatenated tuple consisting of the
         - access-node-identifier
         - service-id
         - interface name
         - SAP-id (only if the value of vRtrIfType is 'serviceIesGroup')
         is used.
         If the value of this object is set to 'sapId', the ASCII-encoded
         SAP-id is used.
         If the value of this object is set to 'vlanAsciiTuple' - the format
         will include VLAN-id and dot1p bits in addition to what is included in
         ascii-tuple already.  The format is supported on dot1q and qinq
         encapsulated ports only.  Thus, when the option 82 bits are
         stripped, dot1p bits will be copied to the Ethernet header of an
         outgoing packet.

         The value  'sapId(3)' can only be used if the interface is a service
         interface.
         The values 'portId(5)' and 'ifName(6)' can only be used if the
         interface is a network interface."
    DEFVAL      { asciiTuple }
    ::= { vRtrIfDHCPEntry 3 }

vRtrIfDHCPRelayRemoteId          OBJECT-TYPE
    SYNTAX      INTEGER {
        mac       (1),
        none      (2),
        remote-id (3)
    }
    MAX-ACCESS  read-create
    STATUS      current
    DESCRIPTION
        "The value of vRtrIfDHCPRelayRemoteId specifies what information goes
         into the remote-id suboption in the DHCP Relay packet.  If the
         value of this object is set to 'none', the remote-id suboption is
         left blank. If the value of this object is set to 'mac',
         the MAC address of the remote end is encoded in the suboption.  If the
         value of the object is set to 'remote-id', vRtrIfDHCPRelayRemoteIdStr
         will be the remote-id."
    DEFVAL      { none }
    ::= { vRtrIfDHCPEntry 4 }

vRtrIfDHCPAutoFilter             OBJECT-TYPE
    SYNTAX      Unsigned32 (0..2000)
    MAX-ACCESS  read-create
    STATUS      obsolete
    DESCRIPTION
        "vRtrIfDHCPAutoFilter allows the router to automatically build
         anti-spoofing filter lists. When this object is set to a non-zero
         value, auto-filtering is enabled and a filter allowing only PPPoE or
         DHCP traffic is established on the interface. The non-zero value
         indicates the maximum number of entries that the auto-filter can have.
         These entries are created by the agent upon snooping a valid DHCP
         Reply packet and are used to allow traffic sourced by the given
         DHCP-assigned IP address."
    DEFVAL      { 0 }
    ::= { vRtrIfDHCPEntry 5 }

vRtrIfDHCPRelayServer1           OBJECT-TYPE
    SYNTAX      IpAddress
    MAX-ACCESS  read-create
    STATUS      current
    DESCRIPTION
        "vRtrIfDHCPRelayServer1 is used to configure the first DHCP server
         where the requests will be forwarded."
    DEFVAL      { '00000000'H }
    ::= { vRtrIfDHCPEntry 6 }

vRtrIfDHCPRelayServer2           OBJECT-TYPE
    SYNTAX      IpAddress
    MAX-ACCESS  read-create
    STATUS      current
    DESCRIPTION
        "vRtrIfDHCPRelayServer2 is used to configure the second DHCP server
         where the requests will be forwarded."
    DEFVAL      { '00000000'H }
    ::= { vRtrIfDHCPEntry 7 }

vRtrIfDHCPRelayServer3           OBJECT-TYPE
    SYNTAX      IpAddress
    MAX-ACCESS  read-create
    STATUS      current
    DESCRIPTION
        "vRtrIfDHCPRelayServer3 is used to configure the third DHCP server
         where the requests will be forwarded."
    DEFVAL      { '00000000'H }
    ::= { vRtrIfDHCPEntry 8 }

vRtrIfDHCPRelayServer4           OBJECT-TYPE
    SYNTAX      IpAddress
    MAX-ACCESS  read-create
    STATUS      current
    DESCRIPTION
        "vRtrIfDHCPRelayServer4 is used to configure the fourth DHCP server
         where the requests will be forwarded."
    DEFVAL      { '00000000'H }
    ::= { vRtrIfDHCPEntry 9 }

vRtrIfDHCPRelayServer5           OBJECT-TYPE
    SYNTAX      IpAddress
    MAX-ACCESS  read-create
    STATUS      current
    DESCRIPTION
        "vRtrIfDHCPRelayServer5 is used to configure the fifth DHCP server
         where the requests will be forwarded."
    DEFVAL      { '00000000'H }
    ::= { vRtrIfDHCPEntry 10 }

vRtrIfDHCPRelayServer6           OBJECT-TYPE
    SYNTAX      IpAddress
    MAX-ACCESS  read-create
    STATUS      current
    DESCRIPTION
        "vRtrIfDHCPRelayServer6 is used to configure the sixth DHCP server
         where the requests will be forwarded."
    DEFVAL      { '00000000'H }
    ::= { vRtrIfDHCPEntry 11 }

vRtrIfDHCPRelayServer7           OBJECT-TYPE
    SYNTAX      IpAddress
    MAX-ACCESS  read-create
    STATUS      current
    DESCRIPTION
        "vRtrIfDHCPRelayServer7 is used to configure the seventh DHCP server
         where the requests will be forwarded."
    DEFVAL      { '00000000'H }
    ::= { vRtrIfDHCPEntry 12 }

vRtrIfDHCPRelayServer8           OBJECT-TYPE
    SYNTAX      IpAddress
    MAX-ACCESS  read-create
    STATUS      current
    DESCRIPTION
        "vRtrIfDHCPRelayServer8 is used to configure the eighth DHCP server
         where the requests will be forwarded."
    DEFVAL      { '00000000'H }
    ::= { vRtrIfDHCPEntry 13 }

vRtrIfDHCPRelayTrusted           OBJECT-TYPE
    SYNTAX      TruthValue
    MAX-ACCESS  read-create
    STATUS      current
    DESCRIPTION
        "When the value of vRtrIfDHCPRelayTrusted is set to 'true(1)', the
         router will relay requests where the DHCP giaddr is zero."
    DEFVAL      { false }
    ::= { vRtrIfDHCPEntry 14 }

vRtrIfDHCPAdminState             OBJECT-TYPE
    SYNTAX      TmnxAdminState
    MAX-ACCESS  read-create
    STATUS      current
    DESCRIPTION
        "vRtrIfDHCPAdminState is used to configure the desired administrative
         state of DHCP on this interface. If the value of vRtrIfType is network
         this object can only be set to 'outOfService'."
    DEFVAL      { outOfService }
    ::= { vRtrIfDHCPEntry 15 }

vRtrIfDHCPSnooping               OBJECT-TYPE
    SYNTAX      INTEGER {
        enabled  (1),
        disabled (2)
    }
    MAX-ACCESS  read-create
    STATUS      obsolete
    DESCRIPTION
        "vRtrIfDHCPSnooping is used to enable/disable snooping of DHCP packets
         received on interface."
    DEFVAL      { disabled }
    ::= { vRtrIfDHCPEntry 16 }

vRtrIfDHCPDescription            OBJECT-TYPE
    SYNTAX      TItemDescription
    MAX-ACCESS  read-create
    STATUS      current
    DESCRIPTION
        "The value of vRtrIfDHCPDescription is a user provided description
         string for DHCP on this virtual router interface.  It can consist of
         any printable, seven-bit ASCII characters up to 80 characters in
         length."
    DEFVAL      { ''H }
    ::= { vRtrIfDHCPEntry 17 }

vRtrIfDHCPAutoFilterId           OBJECT-TYPE
    SYNTAX      TFilterID
    MAX-ACCESS  read-only
    STATUS      obsolete
    DESCRIPTION
        "vRtrIfDHCPAutoFilterId maintains the auto-filter identifier being used
         for this interface."
    ::= { vRtrIfDHCPEntry 18 }

vRtrIfDHCPOperAutoFilter         OBJECT-TYPE
    SYNTAX      Unsigned32 (0..2000)
    MAX-ACCESS  read-only
    STATUS      obsolete
    DESCRIPTION
        "The value of vRtrIfDHCPOperAutoFilter indicates the number of active
         auto-filter entries per interface. These entries are created in the
         TIMETRA-FILTER-MIB::tIPFilterTable by the agent by snooping valid
         'DHCP ACK' messages."
    DEFVAL      { 0 }
    ::= { vRtrIfDHCPEntry 19 }

vRtrIfDHCPAuthPolicy             OBJECT-TYPE
    SYNTAX      TPolicyStatementNameOrEmpty
    MAX-ACCESS  read-create
    STATUS      current
    DESCRIPTION
        "Defines which subscriber authentication policy must be applied when a
         subscriber message (e.g. DHCP, PPPoE, ...) is received on the
         interface. The authentication policy must be defined in
         tmnxSubAuthPlcyTable."
    DEFVAL      { ''H }
    ::= { vRtrIfDHCPEntry 20 }

vRtrIfDHCPLeasePopulate          OBJECT-TYPE
    SYNTAX      Unsigned32 (0..511999)
    MAX-ACCESS  read-create
    STATUS      current
    DESCRIPTION
        "The value of the object vRtrIfDHCPLeasePopulate specifies the
         maximum number of DHCPv4 lease states allowed
         - on this interface, if it is a retailer interface, or
         - per Service Access Point (SAP) or Managed SAP (MSAP)
           associated with this interface, in all other cases."
    DEFVAL      { 0 }
    ::= { vRtrIfDHCPEntry 21 }

vRtrIfDHCPOperLeasePopulate      OBJECT-TYPE
    SYNTAX      Unsigned32 (0..511999)
    MAX-ACCESS  read-only
    STATUS      current
    DESCRIPTION
        "The value of the object vRtrIfDHCPOperLeasePopulate indicates the
         maximum number of DHCP lease states allocated on this interface."
    ::= { vRtrIfDHCPEntry 22 }

vRtrIfDHCPGiAddressType          OBJECT-TYPE
    SYNTAX      InetAddressType
    MAX-ACCESS  read-create
    STATUS      current
    DESCRIPTION
        "The value of vRtrIfDHCPGiAddressType specifies the type of
         vRtrIfDHCPGiAddress, the gateway interface address."
    DEFVAL      { ipv4 }
    ::= { vRtrIfDHCPEntry 23 }

vRtrIfDHCPGiAddress              OBJECT-TYPE
    SYNTAX      InetAddress (SIZE (0|4))
    MAX-ACCESS  read-create
    STATUS      current
    DESCRIPTION
        "The value of vRtrIfDHCPGiAddress specifies the gateway interface
         address. The type of this address is specified by the value of
         vRtrIfDHCPGiAddressType."
    DEFVAL      { '00000000'H }
    ::= { vRtrIfDHCPEntry 24 }

vRtrIfDHCPGiAddressAsSrc         OBJECT-TYPE
    SYNTAX      TruthValue
    MAX-ACCESS  read-create
    STATUS      current
    DESCRIPTION
        "The value of vRtrIfDHCPGiAddressAsSrc specifies whether the DHCP relay
         should use the gateway interface address as the source IP address when
         communicating with the DHCP server. When it is set to 'true(1)', the
         source IP address used to communicate with the DHCP server is the
         gateway interface address. When it is 'false', the source IP is the IP
         of the egress interface the IP packet goes out on."
    DEFVAL      { false }
    ::= { vRtrIfDHCPEntry 25 }

vRtrIfDHCPMatchOption82          OBJECT-TYPE
    SYNTAX      TruthValue
    MAX-ACCESS  read-create
    STATUS      current
    DESCRIPTION
        "The value of vRtrIfDHCPMatchOption82 specifies whether the DHCP relay
         should use the circuit ID in the option 82 field in DHCP packets to
         match DHCP messages. When it is set to 'true(1)', the option 82
         circuit ID is used in addition to the MAC address and transaction ID.
         When it is set to 'false', only the MAC address and transaction ID are
         used."
    DEFVAL      { false }
    ::= { vRtrIfDHCPEntry 26 }

vRtrIfDHCPRelayRemoteIdStr       OBJECT-TYPE
    SYNTAX      DisplayString (SIZE (0..32))
    MAX-ACCESS  read-create
    STATUS      current
    DESCRIPTION
        "The value of vRtrIfDHCPRelayRemoteIdStr specifies the remote-id in the
         DHCP Relay packet if value of vRtrIfDHCPRelayRemoteId is set to
         'remote-id'."
    DEFVAL      { "" }
    ::= { vRtrIfDHCPEntry 27 }

vRtrIfDHCPProxyAdminState        OBJECT-TYPE
    SYNTAX      TmnxAdminState
    MAX-ACCESS  read-create
    STATUS      current
    DESCRIPTION
        "The value of vRtrIfDHCPProxyAdminState specifies the desired
         administrative state of the proxy server on this interface.

         When it is set to 'inService', the proxy server is enabled only if
         vRtrIfDHCPAdminState is also set to 'inService'."
    DEFVAL      { outOfService }
    ::= { vRtrIfDHCPEntry 28 }

vRtrIfDHCPProxyServerAddr        OBJECT-TYPE
    SYNTAX      IpAddress
    MAX-ACCESS  read-create
    STATUS      current
    DESCRIPTION
        "The value of vRtrIfDHCPProxyServerAddr specifies the IP address which
         will be used as the source address of the emulated DHCP server.

         If this IP address is not configured, the value of vRiaIpAddress will
         be used as the source address of the emulated DHCP server."
    DEFVAL      { '00000000'H }
    ::= { vRtrIfDHCPEntry 29 }

vRtrIfDHCPProxyLeaseTime         OBJECT-TYPE
    SYNTAX      Unsigned32 (0 | 300..315446399)
    UNITS       "seconds"
    MAX-ACCESS  read-create
    STATUS      current
    DESCRIPTION
        "The value of vRtrIfDHCPProxyLeaseTime specifies in seconds how long a
         DHCP client is allowed to use the offered IP address.

         Value 0 means the lease time provided by a RADIUS or an upstream DHCP
         server will not be overridden. A lease time of 7 days is used when
         RADIUS does not provide a lease time."
    DEFVAL      { 0 }
    ::= { vRtrIfDHCPEntry 30 }

vRtrIfDHCPProxyLTRadiusOverride  OBJECT-TYPE
    SYNTAX      TruthValue
    MAX-ACCESS  read-create
    STATUS      current
    DESCRIPTION
        "The value of vRtrIfDHCPProxyLTRadiusOverride specifies whether or not
         the lease time provided by the RADIUS server or local user database is
         presented to the DHCP client.

         By default the proxy server will always make use of
         vRtrIfDHCPProxyLeaseTime, regardless of what lease time information is
         provided from the RADIUS server or local user database. When
         vRtrIfDHCPProxyLTRadiusOverride is set to 'true(1)', the proxy server
         will use the lease time information provided by the RADIUS server or
         local user database, regardless of the configured one."
    DEFVAL      { false }
    ::= { vRtrIfDHCPEntry 31 }

vRtrIfDHCPVendorIncludeOptions   OBJECT-TYPE
    SYNTAX      BITS {
        systemId  (0),
        clientMac (1),
        serviceId (2),
        sapId     (3),
        poolName  (4),
        portId    (5)
    }
    MAX-ACCESS  read-create
    STATUS      current
    DESCRIPTION
        "The value of vRtrIfDHCPVendorIncludeOptions specifies what is encoded
         in the Nokia vendor specific sub-option of option 82.

         The values 'serviceId(2)' and 'sapId(3)' can only be used if the
         interface is a service interface. The value 'portId(5)' can only be
         used if the interface is a network interface.

         The value of this object is only used when vRtrIfDHCPRelayInfoAction
         is 'replace(1)'."
    DEFVAL      { {} }
    ::= { vRtrIfDHCPEntry 32 }

vRtrIfDHCPVendorOptionString     OBJECT-TYPE
    SYNTAX      DisplayString (SIZE (0..32))
    MAX-ACCESS  read-create
    STATUS      current
    DESCRIPTION
        "The value of vRtrIfDHCPVendorOptionString specifies the string that
         goes into the Nokia vendor specific sub-option of option 82.

         This string is only used when vRtrIfDHCPRelayInfoAction is set to
         'replace(1)'."
    DEFVAL      { "" }
    ::= { vRtrIfDHCPEntry 33 }

vRtrIfDHCPLayer2Header           OBJECT-TYPE
    SYNTAX      TruthValue
    MAX-ACCESS  read-create
    STATUS      current
    DESCRIPTION
        "The value of vRtrIfDHCPLayer2Header specifies, together with the value
         of object vRtrIfDHCPAntiSpoofMacAddr, the MAC address that is used in
         anti-spoof entries for the lease states on this interface.

         When it is set to 'false (2)', the client hardware address from the
         DHCP payload, stored in TIMETRA-SERV-MIB::svcDhcpLseStateChAddr, is
         used.

         When it is set to 'true (1)', the behavior depends on the value of
         vRtrIfDHCPAntiSpoofMacAddr. If vRtrIfDHCPAntiSpoofMacAddr is set to
         all zeros, the source MAC address in the L2 header of the DHCP packet
         is used. If vRtrIfDHCPAntiSpoofMacAddr is configured, then its value
         is used.

         Only if the corresponding row in the vRtrIfTable has the value of the
         object vRtrIfType equal to 'serviceIesGroup', it is allowed to set the
         value of vRtrIfDHCPLayer2Header to 'true'."
    DEFVAL      { false }
    ::= { vRtrIfDHCPEntry 34 }

vRtrIfDHCPAntiSpoofMacAddr       OBJECT-TYPE
    SYNTAX      MacAddress
    MAX-ACCESS  read-create
    STATUS      current
    DESCRIPTION
        "The value of vRtrIfDHCPAntiSpoofMacAddr specifies, together with the
         value of object vRtrIfDHCPLayer2Header, the MAC address that is used
         in anti-spoof entries for the lease states on this interface.

         When vRtrIfDHCPLayer2Header is 'false (2)', the client hardware
         address from the DHCP payload, stored in
         TIMETRA-SERV-MIB::svcDhcpLseStateChAddr, is used.

         When vRtrIfDHCPLayer2Header is 'true (1)' and the value of this object
         is all zeros, the source MAC address in the L2 header of the DHCP
         packet is used.

         When vRtrIfDHCPLayer2Header is 'true (1)' and the value of this object
         is not all zeros, then this value is used.

         This object can only be configured if the value of object
         vRtrIfDHCPLayer2Header is set to 'true (1)'."
    DEFVAL      { '000000000000'H }
    ::= { vRtrIfDHCPEntry 35 }

vRtrIfDHCPClientApplications     OBJECT-TYPE
    SYNTAX      BITS {
        dhcp (0),
        ppp  (1)
    }
    MAX-ACCESS  read-create
    STATUS      current
    DESCRIPTION
        "The value of vRtrIfDHCPClientApplications specifies the set of client
         applications that can make use of the DHCP relay functionality on this
         interface."
    DEFVAL      { {dhcp} }
    ::= { vRtrIfDHCPEntry 36 }

vRtrIfDHCPRelayPlainBootp        OBJECT-TYPE
    SYNTAX      INTEGER {
        enabled  (1),
        disabled (2)
    }
    MAX-ACCESS  read-create
    STATUS      current
    DESCRIPTION
        "The value of vRtrIfDHCPRelayPlainBootp specifies whether plain bootp
         messages will be relayed. If set to 'disabled', the system will
         consider plain bootp packets as malformed DHCP packets and hence will
         not relay these messages."
    DEFVAL      { disabled }
    ::= { vRtrIfDHCPEntry 37 }

vRtrIfDHCPUserDb                 OBJECT-TYPE
    SYNTAX      TNamedItemOrEmpty
    MAX-ACCESS  read-create
    STATUS      current
    DESCRIPTION
        "The value of vRtrIfDHCPUserDb specifies the local user database to
         authenticate against.

         If no authentication with the local user database is required, the
         value of this object must be set to the empty string."
    DEFVAL      { "" }
    ::= { vRtrIfDHCPEntry 38 }

vRtrIfDHCPUseArpForReply         OBJECT-TYPE
    SYNTAX      TruthValue
    MAX-ACCESS  read-create
    STATUS      current
    DESCRIPTION
        "The value of vRtrIfDHCPUseArpForReply specifies, how the
         system  determines the Hw address for outgoing IP packets.

         If set to 'false', the DHCP CHADDR (Client Hardware Address) is used.
         If set to 'true' the CHADDR is ignored, and ARP is used to determine
         the Hw address.

         Is set to TRUE, the system will accept all DHCP messages with CHADDR
         set to 00:00:00:00:00:00.

         This option only has effect on ethernet interfaces."
    DEFVAL      { false }
    ::= { vRtrIfDHCPEntry 39 }

vRtrIfDHCPFilterId               OBJECT-TYPE
    SYNTAX      TDHCPFilterID
    MAX-ACCESS  read-create
    STATUS      current
    DESCRIPTION
        "The value of vRtrIfDHCPFilterId specifies the DHCP filter to apply.

         If no filtering is required, the value of this object must be set to
         0."
    DEFVAL      { 0 }
    ::= { vRtrIfDHCPEntry 40 }

vRtrIfDHCPRelayUnicastMsg        OBJECT-TYPE
    SYNTAX      INTEGER {
        none            (0),
        renew           (1),
        releaseUpdSrcIp (2)
    }
    MAX-ACCESS  read-create
    STATUS      current
    DESCRIPTION
        "The value of vRtrIfDHCPRelayUnicastMsg specifies whether unicast
         messages will be relayed.

         If set to 'none', the system will not relay any messages. If set to
         'renew', the system will only relay renew messages. If set to
         'releaseUpdSrcIp', the system will relay renew and release messages."
    DEFVAL      { none }
    ::= { vRtrIfDHCPEntry 41 }

vRtrIfDHCPPythonPolicy           OBJECT-TYPE
    SYNTAX      TNamedItemOrEmpty
    MAX-ACCESS  read-create
    STATUS      current
    DESCRIPTION
        "The value of vRtrIfDHCPPythonPolicy specifies the Python policy used
         for processing DHCP messages on this interface.

         The specified Python policy needs to exists in the
         TIMETRA-PYTHON-MIB::tmnxPythonPolicyTable."
    DEFVAL      { "" }
    ::= { vRtrIfDHCPEntry 42 }

vRtrIfDHCPVirtualSubnet          OBJECT-TYPE
    SYNTAX      TmnxEnabledDisabled
    MAX-ACCESS  read-create
    STATUS      current
    DESCRIPTION
        "The value of vRtrIfDHCPVirtualSubnet specifies if virtual subnetting
         is enabled for DHCPv4 hosts on this interface.

         The value 'enabled' is only supported while the value of the object
         vRtrIfType is equal to 'serviceIesSubscriber' or
         'serviceVprnSubscriber'."
    DEFVAL      { disabled }
    ::= { vRtrIfDHCPEntry 44 }

vRtrIfDHCPRelaySiaddrOvrAddrType OBJECT-TYPE
    SYNTAX      InetAddressType
    MAX-ACCESS  read-create
    STATUS      current
    DESCRIPTION
        "The value of vRtrIfDHCPRelaySiaddrOvrAddrType specifies the type of
         vRtrIfDHCPRelaySiaddrOvrAddr."
    DEFVAL      { unknown }
    ::= { vRtrIfDHCPEntry 45 }

vRtrIfDHCPRelaySiaddrOvrAddr     OBJECT-TYPE
    SYNTAX      InetAddress (SIZE (0|4))
    MAX-ACCESS  read-create
    STATUS      current
    DESCRIPTION
        "The value of vRtrIfDHCPRelaySiaddrOvrAddr specifies the IP address to
         use instead of the 'siaddr', while the value of
         vRtrIfDHCPRelayUnicastMsg is not 'none'."
    DEFVAL      { ''H }
    ::= { vRtrIfDHCPEntry 46 }

vRtrIfDHCPOSelDiscoDly           OBJECT-TYPE
    SYNTAX      Integer32 (0..100)
    UNITS       "deci-seconds"
    MAX-ACCESS  read-create
    STATUS      current
    DESCRIPTION
        "The value of vRtrIfDHCPOSelDiscoDly specifies the default  amount of
         time to delay DHCP Discovery messages to any server.

         This can be overruled by more specific settings per server address or
         client subset."
    DEFVAL      { 0 }
    ::= { vRtrIfDHCPEntry 47 }

vRtrIfDHCPOSelClntMac            OBJECT-TYPE
    SYNTAX      INTEGER {
        none (0),
        odd  (1),
        even (2)
    }
    MAX-ACCESS  read-create
    STATUS      current
    DESCRIPTION
        "The value of vRtrIfDHCPOSelClntMac specifies the MAC filter for a
         client subset which require a specific setting for DHCP Offer
         selection."
    DEFVAL      { none }
    ::= { vRtrIfDHCPEntry 48 }

vRtrIfDHCPOSelClntMacDiscoDly    OBJECT-TYPE
    SYNTAX      Integer32 (0..100)
    UNITS       "deci-seconds"
    MAX-ACCESS  read-create
    STATUS      current
    DESCRIPTION
        "The value of vRtrIfDHCPOSelClntMacDiscoDly specifies the  amount of
         time to delay DHCP Discovery messages relayed to any server."
    DEFVAL      { 0 }
    ::= { vRtrIfDHCPEntry 49 }

vRtrIfDHCPReleaseIncludeGiaddr   OBJECT-TYPE
    SYNTAX      TruthValue
    MAX-ACCESS  read-create
    STATUS      current
    DESCRIPTION
        "The value of vRtrIfDHCPReleaseIncludeGiaddr specifies if this system
         inserts the Gateway IP Address (giaddr) in DHCPRELEASE messages."
    DEFVAL      { false }
    ::= { vRtrIfDHCPEntry 50 }

vRtrIfDHCPRelayForceRenewWoLease OBJECT-TYPE
    SYNTAX      TruthValue
    MAX-ACCESS  read-create
    STATUS      current
    DESCRIPTION
        "The value of vRtrIfDHCPRelayForceRenewWoLease specifies if FORCERENEW
         messages without lease are allowed, while the value of
         vRtrIfDHCPRelayUnicastMsg is not 'none'."
    DEFVAL      { false }
    ::= { vRtrIfDHCPEntry 51 }

vRtrIfDHCPRelayStatsTable        OBJECT-TYPE
    SYNTAX      SEQUENCE OF VRtrIfDHCPRelayStatsEntry
    MAX-ACCESS  not-accessible
    STATUS      current
    DESCRIPTION
        "The vRtrIfDHCPRelayStatsTable contains the statistics for the DHCP
         Relay agent."
    ::= { tmnxVRtrObjs 20 }

vRtrIfDHCPRelayStatsEntry        OBJECT-TYPE
    SYNTAX      VRtrIfDHCPRelayStatsEntry
    MAX-ACCESS  not-accessible
    STATUS      current
    DESCRIPTION
        "Each row entry represents information related to DHCP Relay statistics
         for a virtual router interface in the system.

         Entries cannot be created and deleted via SNMP SET operations."
    AUGMENTS    { vRtrIfEntry }
    ::= { vRtrIfDHCPRelayStatsTable 1 }

VRtrIfDHCPRelayStatsEntry        ::= SEQUENCE
{
    vRtrIfDHCPRelayRxPkts            Counter32,
    vRtrIfDHCPRelayTxPkts            Counter32,
    vRtrIfDHCPRelayRxMalformedPkts   Counter32,
    vRtrIfDHCPRelayRxUntrustedPkts   Counter32,
    vRtrIfDHCPRelayClientPktsDiscarded Counter32,
    vRtrIfDHCPRelayClientPktsRelayed Counter32,
    vRtrIfDHCPRelayServerPktsDiscarded Counter32,
    vRtrIfDHCPRelayServerPktsRelayed Counter32,
    vRtrIfDHCPRelayAuthPktsDiscarded Counter32,
    vRtrIfDHCPRelayAuthPktsSuccess   Counter32,
    vRtrIfDHCPRelayClientPktsSnooped Counter32,
    vRtrIfDHCPRelayServerPktsSnooped Counter32,
    vRtrIfDHCPRelayClientPktsProxRad Counter32,
    vRtrIfDHCPRelayClientPktsProxLS  Counter32,
    vRtrIfDHCPRelayPktsGenRelease    Counter32,
    vRtrIfDHCPRelayPktsGenForceRenew Counter32,
    vRtrIfDHCPRelayClientPktsProxUDB Counter32,
    vRtrIfDHCPRelayClientPktsProxNq  Counter32,
    vRtrIfDHCPRelayClientPktsStream  Counter32
}

vRtrIfDHCPRelayRxPkts            OBJECT-TYPE
    SYNTAX      Counter32
    MAX-ACCESS  read-only
    STATUS      current
    DESCRIPTION
        "vRtrIfDHCPRelayRxPkts indicates the total number of packets received
         by the DHCP relay agent."
    ::= { vRtrIfDHCPRelayStatsEntry 1 }

vRtrIfDHCPRelayTxPkts            OBJECT-TYPE
    SYNTAX      Counter32
    MAX-ACCESS  read-only
    STATUS      current
    DESCRIPTION
        "vRtrIfDHCPRelayTxPkts indicates the total number of packets
         transmitted by the DHCP relay agent."
    ::= { vRtrIfDHCPRelayStatsEntry 2 }

vRtrIfDHCPRelayRxMalformedPkts   OBJECT-TYPE
    SYNTAX      Counter32
    MAX-ACCESS  read-only
    STATUS      current
    DESCRIPTION
        "vRtrIfDHCPRelayRxMalformedPkts indicates the total number of malformed
         packets received by the DHCP relay agent."
    ::= { vRtrIfDHCPRelayStatsEntry 3 }

vRtrIfDHCPRelayRxUntrustedPkts   OBJECT-TYPE
    SYNTAX      Counter32
    MAX-ACCESS  read-only
    STATUS      current
    DESCRIPTION
        "vRtrIfDHCPRelayRxUntrustedPkts indicates the total number of untrusted
         packets received by the DHCP relay agent."
    ::= { vRtrIfDHCPRelayStatsEntry 4 }

vRtrIfDHCPRelayClientPktsDiscarded OBJECT-TYPE
    SYNTAX      Counter32
    MAX-ACCESS  read-only
    STATUS      current
    DESCRIPTION
        "vRtrIfDHCPRelayClientPktsDiscarded indicates the total number of
         client packets discarded by the DHCP relay agent."
    ::= { vRtrIfDHCPRelayStatsEntry 5 }

vRtrIfDHCPRelayClientPktsRelayed OBJECT-TYPE
    SYNTAX      Counter32
    MAX-ACCESS  read-only
    STATUS      current
    DESCRIPTION
        "vRtrIfDHCPRelayClientPktsRelayed indicates the total number of client
         packets relayed by the DHCP relay agent."
    ::= { vRtrIfDHCPRelayStatsEntry 6 }

vRtrIfDHCPRelayServerPktsDiscarded OBJECT-TYPE
    SYNTAX      Counter32
    MAX-ACCESS  read-only
    STATUS      current
    DESCRIPTION
        "vRtrIfDHCPRelayServerPktsDiscarded indicates the total number of
         server packets discarded by the DHCP relay agent."
    ::= { vRtrIfDHCPRelayStatsEntry 7 }

vRtrIfDHCPRelayServerPktsRelayed OBJECT-TYPE
    SYNTAX      Counter32
    MAX-ACCESS  read-only
    STATUS      current
    DESCRIPTION
        "vRtrIfDHCPRelayServerPktsRelayed indicates the total number of server
         packets relayed by the DHCP relay agent."
    ::= { vRtrIfDHCPRelayStatsEntry 8 }

vRtrIfDHCPRelayAuthPktsDiscarded OBJECT-TYPE
    SYNTAX      Counter32
    MAX-ACCESS  read-only
    STATUS      current
    DESCRIPTION
        "vRtrIfDHCPRelayAuthPktsDiscarded indicates the total number of packets
         discarded because authentication was not successful."
    ::= { vRtrIfDHCPRelayStatsEntry 9 }

vRtrIfDHCPRelayAuthPktsSuccess   OBJECT-TYPE
    SYNTAX      Counter32
    MAX-ACCESS  read-only
    STATUS      current
    DESCRIPTION
        "vRtrIfDHCPRelayAuthPktsSuccess indicates the total number of packets
         for which authentication was successful."
    ::= { vRtrIfDHCPRelayStatsEntry 10 }

vRtrIfDHCPRelayClientPktsSnooped OBJECT-TYPE
    SYNTAX      Counter32
    MAX-ACCESS  read-only
    STATUS      current
    DESCRIPTION
        "vRtrIfDHCPRelayClientPktsSnooped indicates the total number of client
         packets snooped by the DHCP relay agent."
    ::= { vRtrIfDHCPRelayStatsEntry 11 }

vRtrIfDHCPRelayServerPktsSnooped OBJECT-TYPE
    SYNTAX      Counter32
    MAX-ACCESS  read-only
    STATUS      current
    DESCRIPTION
        "vRtrIfDHCPRelayServerPktsSnooped indicates the total number of server
         packets snooped by the DHCP relay agent."
    ::= { vRtrIfDHCPRelayStatsEntry 12 }

vRtrIfDHCPRelayClientPktsProxRad OBJECT-TYPE
    SYNTAX      Counter32
    MAX-ACCESS  read-only
    STATUS      current
    DESCRIPTION
        "vRtrIfDHCPRelayClientPktsProxRad indicates the total number of client
         packets proxied by the DHCP relay agent based on data received from a
         RADIUS server."
    ::= { vRtrIfDHCPRelayStatsEntry 13 }

vRtrIfDHCPRelayClientPktsProxLS  OBJECT-TYPE
    SYNTAX      Counter32
    MAX-ACCESS  read-only
    STATUS      current
    DESCRIPTION
        "vRtrIfDHCPRelayClientPktsProxLS indicates the total number of client
         packets proxied by the DHCP relay agent based on a lease state. The
         lease itself can have been obtained from a DHCP or RADIUS server. This
         is the so called lease split functionality."
    ::= { vRtrIfDHCPRelayStatsEntry 14 }

vRtrIfDHCPRelayPktsGenRelease    OBJECT-TYPE
    SYNTAX      Counter32
    MAX-ACCESS  read-only
    STATUS      current
    DESCRIPTION
        "vRtrIfDHCPRelayPktsGenRelease indicates the total number of DHCP
         RELEASE messages spoofed by the DHCP relay agent to the DHCP server."
    ::= { vRtrIfDHCPRelayStatsEntry 15 }

vRtrIfDHCPRelayPktsGenForceRenew OBJECT-TYPE
    SYNTAX      Counter32
    MAX-ACCESS  read-only
    STATUS      current
    DESCRIPTION
        "vRtrIfDHCPRelayPktsGenForceRenew indicates the total number of DHCP
         FORCERENEW messages spoofed by the DHCP relay agent to the DHCP
         clients."
    ::= { vRtrIfDHCPRelayStatsEntry 16 }

vRtrIfDHCPRelayClientPktsProxUDB OBJECT-TYPE
    SYNTAX      Counter32
    MAX-ACCESS  read-only
    STATUS      current
    DESCRIPTION
        "vRtrIfDHCPRelayClientPktsProxUDB indicates the total number of client
         packets proxied by the DHCP relay agent based on the local user
         database."
    ::= { vRtrIfDHCPRelayStatsEntry 17 }

vRtrIfDHCPRelayClientPktsProxNq  OBJECT-TYPE
    SYNTAX      Counter32
    MAX-ACCESS  read-only
    STATUS      current
    DESCRIPTION
        "The value of the object vRtrIfDHCPRelayClientPktsProxNq indicates
         the total number of  client packets proxied by the DHCP relay agent
         based on data received from a Diameter NASREQ server."
    ::= { vRtrIfDHCPRelayStatsEntry 18 }

vRtrIfDHCPRelayClientPktsStream  OBJECT-TYPE
    SYNTAX      Counter32
    MAX-ACCESS  read-only
    STATUS      current
    DESCRIPTION
        "The value of the object vRtrIfDHCPRelayClientPktsStream indicates the
         total number of received client packets scheduled for streaming to an
         external server, by the DHCP proxy function."
    ::= { vRtrIfDHCPRelayStatsEntry 19 }

tmnxVRtrNotificationObjects      OBJECT IDENTIFIER ::= { tmnxVRtrObjs 21 }

vRtrAutoFilterDHCPClientAddress  OBJECT-TYPE
    SYNTAX      IpAddress
    MAX-ACCESS  accessible-for-notify
    STATUS      obsolete
    DESCRIPTION
        "The Client IP address from the PDU causing the trap. Used by
         tmnxVRtrDHCPAFEntriesExceeded to report the client's IP address."
    ::= { tmnxVRtrNotificationObjects 1 }

vRtrAutoFilterDHCPClientLease    OBJECT-TYPE
    SYNTAX      Unsigned32
    MAX-ACCESS  accessible-for-notify
    STATUS      obsolete
    DESCRIPTION
        "The lease time specified in the PDU causing the trap. Used by
         tmnxVRtrDHCPAFEntriesExceeded to report the lease time."
    ::= { tmnxVRtrNotificationObjects 2 }

vRtrDHCPClientLease              OBJECT-TYPE
    SYNTAX      Integer32
    MAX-ACCESS  accessible-for-notify
    STATUS      obsolete
    DESCRIPTION
        "The value of the object vRtrDHCPClientLease indicates the lease time
         specified in the PDU causing the trap."
    ::= { tmnxVRtrNotificationObjects 3 }

vRtrDhcpLseStateOldCiAddr        OBJECT-TYPE
    SYNTAX      IpAddress
    MAX-ACCESS  accessible-for-notify
    STATUS      obsolete
    DESCRIPTION
        "The value of the object vRtrDhcpLseStateOldCiAddr indicates the Client
         IP address that was formerly assigned to this Least state."
    ::= { tmnxVRtrNotificationObjects 4 }

vRtrDhcpLseStateOldChAddr        OBJECT-TYPE
    SYNTAX      MacAddress
    MAX-ACCESS  accessible-for-notify
    STATUS      obsolete
    DESCRIPTION
        "The value of the object vRtrDhcpLseStateOldChAddr indicates the Client
         MAC address that was formerly assigned to this Least state."
    ::= { tmnxVRtrNotificationObjects 5 }

vRtrDhcpLseStateNewCiAddr        OBJECT-TYPE
    SYNTAX      IpAddress
    MAX-ACCESS  accessible-for-notify
    STATUS      obsolete
    DESCRIPTION
        "The value of the object vRtrDhcpLseStateNewCiAddr indicates the Client
         IP address specified in the PDU causing the trap."
    ::= { tmnxVRtrNotificationObjects 6 }

vRtrDhcpLseStateNewChAddr        OBJECT-TYPE
    SYNTAX      MacAddress
    MAX-ACCESS  accessible-for-notify
    STATUS      obsolete
    DESCRIPTION
        "The value of the object vRtrDhcpLseStateNewChAddr indicates the Client
         MAC address specified in the PDU causing the trap."
    ::= { tmnxVRtrNotificationObjects 7 }

vRtrDhcpRestoreLseStateCiAddr    OBJECT-TYPE
    SYNTAX      IpAddress
    MAX-ACCESS  accessible-for-notify
    STATUS      obsolete
    DESCRIPTION
        "The value of the object vRtrDhcpRestoreLseStateCiAddr indicates the IP
         address specified in the persistency record causing the trap."
    ::= { tmnxVRtrNotificationObjects 8 }

vRtrDhcpRestoreLseStateVRtrId    OBJECT-TYPE
    SYNTAX      TmnxVRtrID
    MAX-ACCESS  accessible-for-notify
    STATUS      obsolete
    DESCRIPTION
        "The value of the object vRtrDhcpRestoreLseStateVRtrId indicates the
         serviceId specified in the persistency record causing the trap."
    ::= { tmnxVRtrNotificationObjects 9 }

vRtrDhcpRestoreLseStateIfIndex   OBJECT-TYPE
    SYNTAX      InterfaceIndex
    MAX-ACCESS  accessible-for-notify
    STATUS      obsolete
    DESCRIPTION
        "The value of the object vRtrDhcpRestoreLseStateIfIndex indicates the
         Port ID specified in the persistency record causing the trap."
    ::= { tmnxVRtrNotificationObjects 10 }

vRtrDhcpRestoreLseStateProblem   OBJECT-TYPE
    SYNTAX      DisplayString
    MAX-ACCESS  accessible-for-notify
    STATUS      obsolete
    DESCRIPTION
        "The value of the object vRtrDhcpRestoreLseStateProblem indicates why
         the persistency record cannot be restored."
    ::= { tmnxVRtrNotificationObjects 11 }

vRtrDhcpPacketProblem            OBJECT-TYPE
    SYNTAX      DisplayString
    MAX-ACCESS  accessible-for-notify
    STATUS      current
    DESCRIPTION
        "The value of the object vRtrDhcpPacketProblem indicates information on
         a received DHCP packet is considered suspicious by the system."
    ::= { tmnxVRtrNotificationObjects 12 }

vRtrDhcpLseStatePopulateError    OBJECT-TYPE
    SYNTAX      DisplayString
    MAX-ACCESS  accessible-for-notify
    STATUS      obsolete
    DESCRIPTION
        "The value of the object vRtrDhcpLseStatePopulateError indicates the
         reason why the system was unable to update the Lease state table with
         the information contained in the received DHCP ACK message."
    ::= { tmnxVRtrNotificationObjects 13 }

vRtrBfdSlotNumber                OBJECT-TYPE
    SYNTAX      TmnxSlotNum
    MAX-ACCESS  accessible-for-notify
    STATUS      current
    DESCRIPTION
        "The value of vRtrBfdSlotNumber indicates the IOM slot number where the
         number of supported BFD sessions has reached the maximum value. This
         object is reported when the tmnxVRtrBfdMaxSessionOnSlot notification
         is generated."
    ::= { tmnxVRtrNotificationObjects 14 }

vRtrNumberOfBfdSessionsOnSlot    OBJECT-TYPE
    SYNTAX      Unsigned32
    MAX-ACCESS  accessible-for-notify
    STATUS      current
    DESCRIPTION
        "The value of vRtrNumberOfBfdSessionsOnSlot indicates the current
         number of BFD sessions on the slot indicated by vRtrBfdSlotNumber.
         This object is reported when the tmnxVRtrBfdMaxSessionOnSlot
         notification is generated."
    ::= { tmnxVRtrNotificationObjects 15 }

vRtrBfdMaxSessionReason          OBJECT-TYPE
    SYNTAX      BITS {
        maxSessionsPerSlot  (0),
        maxTxPacketRate     (1),
        maxRxPacketRate     (2),
        noSupportConfTimers (3),
        maxTableEntries     (4)
    }
    MAX-ACCESS  accessible-for-notify
    STATUS      current
    DESCRIPTION
        "The value of vRtrBfdMaxSessionReason indicates the reason the maximum
         numbers of sessions on this IOM slot was reached. This object is
         reported when the tmnxVRtrBfdMaxSessionOnSlot notification is
         generated."
    ::= { tmnxVRtrNotificationObjects 16 }

vRtrDHCP6ServerNetAddrType       OBJECT-TYPE
    SYNTAX      InetAddressType
    MAX-ACCESS  accessible-for-notify
    STATUS      current
    DESCRIPTION
        "The value of the object vRtrDHCP6ServerNetAddrType indicates the
         address type of vRtrDHCP6ServerNetAddr."
    ::= { tmnxVRtrNotificationObjects 17 }

vRtrDHCP6ServerNetAddr           OBJECT-TYPE
    SYNTAX      InetAddress
    MAX-ACCESS  accessible-for-notify
    STATUS      current
    DESCRIPTION
        "The value of the object vRtrDHCP6ServerNetAddr indicates the IP
         address of the DHCP server."
    ::= { tmnxVRtrNotificationObjects 18 }

vRtrDHCP6ClientNetAddrType       OBJECT-TYPE
    SYNTAX      InetAddressType
    MAX-ACCESS  accessible-for-notify
    STATUS      current
    DESCRIPTION
        "The value of the object vRtrDHCP6ClientNetAddrType indicates the
         address type of vRtrDHCP6ClientNetAddr."
    ::= { tmnxVRtrNotificationObjects 19 }

vRtrDHCP6ClientNetAddr           OBJECT-TYPE
    SYNTAX      InetAddress
    MAX-ACCESS  accessible-for-notify
    STATUS      current
    DESCRIPTION
        "The value of the object vRtrDHCP6ClientNetAddr indicates the IP
         address of the DHCP client."
    ::= { tmnxVRtrNotificationObjects 20 }

vRtrDHCP6AssignedNetAddrType     OBJECT-TYPE
    SYNTAX      InetAddressType
    MAX-ACCESS  accessible-for-notify
    STATUS      current
    DESCRIPTION
        "The value of the object vRtrDHCP6AssignedNetAddrType indicates the
         address type of vRtrDHCP6AssignedNetAddr."
    ::= { tmnxVRtrNotificationObjects 21 }

vRtrDHCP6AssignedNetAddr         OBJECT-TYPE
    SYNTAX      InetAddress
    MAX-ACCESS  accessible-for-notify
    STATUS      current
    DESCRIPTION
        "The value of the object vRtrDHCP6AssignedNetAddr indicates the IP
         address assigned to the DHCP client."
    ::= { tmnxVRtrNotificationObjects 22 }

vRtrDHCP6AssignedPrefixLen       OBJECT-TYPE
    SYNTAX      InetAddressPrefixLength
    MAX-ACCESS  accessible-for-notify
    STATUS      current
    DESCRIPTION
        "The value of vRtrDHCP6AssignedPrefixLen specifies the length of the IP
         netmask for vRtrDHCP6AssignedNetAddr."
    ::= { tmnxVRtrNotificationObjects 23 }

vRtrDHCP6OldAssignedNetAddrType  OBJECT-TYPE
    SYNTAX      InetAddressType
    MAX-ACCESS  accessible-for-notify
    STATUS      current
    DESCRIPTION
        "The value of the object vRtrDHCP6OldAssignedNetAddrType indicates the
         address type of vRtrDHCP6OldAssignedNetAddr."
    ::= { tmnxVRtrNotificationObjects 24 }

vRtrDHCP6OldAssignedNetAddr      OBJECT-TYPE
    SYNTAX      InetAddress
    MAX-ACCESS  accessible-for-notify
    STATUS      current
    DESCRIPTION
        "The value of the object vRtrDHCP6OldAssignedNetAddr indicates the IP
         address formerly assigned to the DHCP client."
    ::= { tmnxVRtrNotificationObjects 25 }

vRtrDHCP6OldAssignedPrefixLen    OBJECT-TYPE
    SYNTAX      InetAddressPrefixLength
    MAX-ACCESS  accessible-for-notify
    STATUS      current
    DESCRIPTION
        "The value of vRtrDHCP6OldAssignedPrefixLen specifies the length of the
         IP netmask for vRtrDHCP6OldAssignedNetAddr."
    ::= { tmnxVRtrNotificationObjects 26 }

vRtrDHCP6NewClientId             OBJECT-TYPE
    SYNTAX      OCTET STRING (SIZE (0..255))
    MAX-ACCESS  accessible-for-notify
    STATUS      current
    DESCRIPTION
        "The value of vRtrDHCP6NewClientId indicates the new DHCP6 clients
         unique identifier (DUID)."
    ::= { tmnxVRtrNotificationObjects 27 }

vRtrDHCP6OldClientId             OBJECT-TYPE
    SYNTAX      OCTET STRING (SIZE (0..255))
    MAX-ACCESS  accessible-for-notify
    STATUS      current
    DESCRIPTION
        "The value of vRtrDHCP6OldClientId indicates the old DHCP6 clients
         unique identifier (DUID)."
    ::= { tmnxVRtrNotificationObjects 28 }

vRtrDHCP6LeaseOverrideResult     OBJECT-TYPE
    SYNTAX      DisplayString
    MAX-ACCESS  accessible-for-notify
    STATUS      current
    DESCRIPTION
        "The value of the object vRtrDHCP6LeaseOverrideResult indicates whether
         or not the lease state has been overridden."
    ::= { tmnxVRtrNotificationObjects 29 }

vRtrInetStatRteCpeNotifyAddrType OBJECT-TYPE
    SYNTAX      InetAddressType
    MAX-ACCESS  accessible-for-notify
    STATUS      current
    DESCRIPTION
        "The value of the object vRtrInetStatRteCpeNotifyAddrType indicates the
         address type of vRtrInetStatRteCpeNotifyAddr."
    ::= { tmnxVRtrNotificationObjects 30 }

vRtrInetStatRteCpeNotifyAddr     OBJECT-TYPE
    SYNTAX      InetAddress
    MAX-ACCESS  accessible-for-notify
    STATUS      current
    DESCRIPTION
        "The value of the object vRtrInetStatRteCpeNotifyAddr indicates the IP
         address of the CPE."
    ::= { tmnxVRtrNotificationObjects 31 }

vRtrInetStaticRouteCpeStatus     OBJECT-TYPE
    SYNTAX      INTEGER {
        reachable   (0),
        unreachable (1)
    }
    MAX-ACCESS  accessible-for-notify
    STATUS      current
    DESCRIPTION
        "The value of the object vRtrInetStaticRouteCpeStatus indicates whether
         or not the CPE associated with a static route is 'reachable' or
         'unreachable'."
    ::= { tmnxVRtrNotificationObjects 32 }

vRtrManagedRouteInetAddrType     OBJECT-TYPE
    SYNTAX      InetAddressType
    MAX-ACCESS  accessible-for-notify
    STATUS      current
    DESCRIPTION
        "The value of vRtrManagedRouteInetAddrType indicates the address type
         of vRtrManagedRouteInetAddr."
    ::= { tmnxVRtrNotificationObjects 33 }

vRtrManagedRouteInetAddr         OBJECT-TYPE
    SYNTAX      InetAddress (SIZE (0|4|16))
    MAX-ACCESS  accessible-for-notify
    STATUS      current
    DESCRIPTION
        "The value of vRtrManagedRouteInetAddr indicates the IP address of the
         managed route."
    ::= { tmnxVRtrNotificationObjects 34 }

vRtrManagedRoutePrefixLen        OBJECT-TYPE
    SYNTAX      InetAddressPrefixLength
    MAX-ACCESS  accessible-for-notify
    STATUS      current
    DESCRIPTION
        "The value of vRtrManagedRoutePrefixLen indicates the prefix length of
         the subnet associated with vRtrManagedRouteInetAddr."
    ::= { tmnxVRtrNotificationObjects 35 }

vRtrFailureDescription           OBJECT-TYPE
    SYNTAX      DisplayString
    MAX-ACCESS  accessible-for-notify
    STATUS      current
    DESCRIPTION
        "The value of the object vRtrFailureDescription is a printable
         character string which contains information about the reason why the
         notification is sent."
    ::= { tmnxVRtrNotificationObjects 36 }

vRtrMaxRoutesType                OBJECT-TYPE
    SYNTAX      INTEGER {
        ipv4 (0),
        ipv6 (1)
    }
    MAX-ACCESS  accessible-for-notify
    STATUS      current
    DESCRIPTION
        "The value of the object vRtrMaxRoutesType indicates the type of the
         maximum number of routes indicated by vRtrMaxNumRoutes"
    ::= { tmnxVRtrNotificationObjects 37 }

vRtrSlotOrCpmFlag                OBJECT-TYPE
    SYNTAX      INTEGER {
        slot      (0),
        cpm       (1),
        reserved2 (2)
    }
    MAX-ACCESS  accessible-for-notify
    STATUS      current
    DESCRIPTION
        "    The value of the object vRtrSlotOrCpmFlag
             indicates slot, when we have IOM based sessions and CPM
             when the sessions are centralized."
    ::= { tmnxVRtrNotificationObjects 38 }

vRtrNotifInetAddrType            OBJECT-TYPE
    SYNTAX      InetAddressType
    MAX-ACCESS  accessible-for-notify
    STATUS      current
    DESCRIPTION
        "The value of vRtrNotifInetAddrType indicates the address type of
         vRtrNotifInetAddr."
    ::= { tmnxVRtrNotificationObjects 39 }

vRtrNotifInetAddr                OBJECT-TYPE
    SYNTAX      InetAddress (SIZE (0|4|16))
    MAX-ACCESS  accessible-for-notify
    STATUS      current
    DESCRIPTION
        "The value of vRtrNotifInetAddr indicates an IP address."
    ::= { tmnxVRtrNotificationObjects 40 }

vRtrIfBfdSessChangedProtocol     OBJECT-TYPE
    SYNTAX      DisplayString
    MAX-ACCESS  accessible-for-notify
    STATUS      current
    DESCRIPTION
        "The value of the object vRtrIfBfdSessChangedProtocol indicates the
         protocol that changed the state in BFD."
    ::= { tmnxVRtrNotificationObjects 41 }

vRtrIfBfdSessProtoChngdState     OBJECT-TYPE
    SYNTAX      INTEGER {
        added   (0),
        cleared (1)
    }
    MAX-ACCESS  accessible-for-notify
    STATUS      current
    DESCRIPTION
        "The value of the object vRtrIfBfdSessProtoChngdState indicates the
         changed state of vRtrIfBfdSessChangedProtocol in BFD."
    ::= { tmnxVRtrNotificationObjects 42 }

vRtrIfDcpTimeEventOccured        OBJECT-TYPE
    SYNTAX      TimeStamp
    MAX-ACCESS  accessible-for-notify
    STATUS      current
    DESCRIPTION
        "The value of vRtrIfDcpTimeEventOccured indicates the actual time the
         event was detected in the system which may differ from the time the
         event was collected by the logging infrastructure."
    ::= { tmnxVRtrNotificationObjects 43 }

vRtrNotifTruthValue              OBJECT-TYPE
    SYNTAX      TruthValue
    MAX-ACCESS  accessible-for-notify
    STATUS      current
    DESCRIPTION
        "The value of vRtrNotifTruthValue indicates a boolean value."
    ::= { tmnxVRtrNotificationObjects 44 }

tmnxVRtrMaxNHRvplsARPEntries     OBJECT-TYPE
    SYNTAX      Unsigned32
    MAX-ACCESS  accessible-for-notify
    STATUS      current
    DESCRIPTION
        "The value of tmnxVRtrMaxNHRvplsARPEntries indicates the maximum number
         of Nexthop RVPLS ARP entries supported. This object is reported when
         the tmnxVRtrNHRvplsARPHighUsage, tmnxVRtrNHRvplsARPExhaust or
         tmnxVRtrNHRvplsARPHighUsageClr notification is generated."
    ::= { tmnxVRtrNotificationObjects 45 }

vRtrNotifIgnorePortState         OBJECT-TYPE
    SYNTAX      INTEGER {
        active  (1),
        pending (2)
    }
    MAX-ACCESS  accessible-for-notify
    STATUS      current
    DESCRIPTION
        "The value of vRtrNotifIgnorePortState indicates the system state to
         ignore non-operational port associated with the IP interface with the
         SAP."
    ::= { tmnxVRtrNotificationObjects 46 }

vRtrNotifyFpNum                  OBJECT-TYPE
    SYNTAX      TmnxFPNumber
    MAX-ACCESS  accessible-for-notify
    STATUS      current
    DESCRIPTION
        "The value of vRtrNotifyFpNum identifies the Forwarding Plane."
    ::= { tmnxVRtrNotificationObjects 51 }

vRtrNotifyBgpInstType            OBJECT-TYPE
    SYNTAX      INTEGER {
        ipVpnMpls (1),
        ipVpnSrv6 (2),
        evpnMpls  (3),
        evpnSrv6  (4)
    }
    MAX-ACCESS  accessible-for-notify
    STATUS      current
    DESCRIPTION
        "The vRtrNotifyBgpInstType specifies the BGP protocol family used with
         this service."
    ::= { tmnxVRtrNotificationObjects 52 }

vRtrNotifyBgpInstance            OBJECT-TYPE
    SYNTAX      Integer32 (0..1)
    MAX-ACCESS  accessible-for-notify
    STATUS      current
    DESCRIPTION
        "The vRtrNotifyBgpInstance specifies the BGP instance used with this
         service."
    ::= { tmnxVRtrNotificationObjects 53 }

vRtrIfDHCPLeaseStateTable        OBJECT-TYPE
    SYNTAX      SEQUENCE OF VRtrIfDHCPLeaseStateEntry
    MAX-ACCESS  not-accessible
    STATUS      obsolete
    DESCRIPTION
        "vRtrIfDHCPLeaseStateTable contains DHCP lease state info for a virtual
         router interface in the system. The content of this table is moved to
         the TIMETRA-SERV-MIB::svcDhcpLeaseStateTable."
    ::= { tmnxVRtrObjs 22 }

vRtrIfDHCPLeaseStateEntry        OBJECT-TYPE
    SYNTAX      VRtrIfDHCPLeaseStateEntry
    MAX-ACCESS  not-accessible
    STATUS      obsolete
    DESCRIPTION
        "DHCP lease state information for a virtual router interface."
    INDEX       {
        vRtrID,
        vRtrIfIndex,
        vRtrIfDHCPLseStateCiAddr
    }
    ::= { vRtrIfDHCPLeaseStateTable 1 }

VRtrIfDHCPLeaseStateEntry        ::= SEQUENCE
{
    vRtrIfDHCPLseStateCiAddr         IpAddress,
    vRtrIfDHCPLseStateChAddr         MacAddress,
    vRtrIfDHCPLseStateRemainLseTime  Unsigned32,
    vRtrIfDHCPLseStateOption82       OCTET STRING,
    vRtrIfDHCPLseStatePersistKey     Unsigned32
}

vRtrIfDHCPLseStateCiAddr         OBJECT-TYPE
    SYNTAX      IpAddress
    MAX-ACCESS  not-accessible
    STATUS      obsolete
    DESCRIPTION
        "The value of the object vRtrIfDHCPLseStateCiAddr indicates the IP
         address of the DHCP lease state."
    ::= { vRtrIfDHCPLeaseStateEntry 1 }

vRtrIfDHCPLseStateChAddr         OBJECT-TYPE
    SYNTAX      MacAddress
    MAX-ACCESS  read-only
    STATUS      obsolete
    DESCRIPTION
        "The value of the object vRtrIfDHCPLseStateChAddr indicates the MAC
         address of the DHCP lease state."
    ::= { vRtrIfDHCPLeaseStateEntry 2 }

vRtrIfDHCPLseStateRemainLseTime  OBJECT-TYPE
    SYNTAX      Unsigned32
    MAX-ACCESS  read-only
    STATUS      obsolete
    DESCRIPTION
        "The value of the object vRtrIfDHCPLseStateRemainLseTime indicates the
         remaining lease time of the IP address of the DHCP lease state."
    ::= { vRtrIfDHCPLeaseStateEntry 3 }

vRtrIfDHCPLseStateOption82       OBJECT-TYPE
    SYNTAX      OCTET STRING
    MAX-ACCESS  read-only
    STATUS      obsolete
    DESCRIPTION
        "vRtrIfDHCPLseStateOption82 indicates the content of the Option82 for
         this DHCP lease state."
    ::= { vRtrIfDHCPLeaseStateEntry 4 }

vRtrIfDHCPLseStatePersistKey     OBJECT-TYPE
    SYNTAX      Unsigned32
    MAX-ACCESS  read-only
    STATUS      obsolete
    DESCRIPTION
        "The value of the object vRtrIfDHCPLseStatePersistKey indicates a key
         value that can be used to track this lease state in the persistence
         file."
    ::= { vRtrIfDHCPLeaseStateEntry 5 }

vRtrAdvPrefixTable               OBJECT-TYPE
    SYNTAX      SEQUENCE OF VRtrAdvPrefixEntry
    MAX-ACCESS  not-accessible
    STATUS      current
    DESCRIPTION
        "This table allows the user to configure IPv6 prefixes for router
         advertisements on an interface"
    ::= { tmnxVRtrObjs 23 }

vRtrAdvPrefixEntry               OBJECT-TYPE
    SYNTAX      VRtrAdvPrefixEntry
    MAX-ACCESS  not-accessible
    STATUS      current
    DESCRIPTION
        "An entry in the vRtrAdvPrefixTable."
    INDEX       {
        vRtrID,
        vRtrAdvPrefixIfIndex,
        vRtrAdvPrefixPrefix,
        vRtrAdvPrefixLength
    }
    ::= { vRtrAdvPrefixTable 1 }

VRtrAdvPrefixEntry               ::= SEQUENCE
{
    vRtrAdvPrefixIfIndex             InterfaceIndex,
    vRtrAdvPrefixPrefix              InetAddress,
    vRtrAdvPrefixLength              InetAddressPrefixLength,
    vRtrAdvPrefixRowStatus           RowStatus,
    vRtrAdvPrefixOnLinkFlag          TruthValue,
    vRtrAdvPrefixAutonomousFlag      TruthValue,
    vRtrAdvPrefixPreferredLifetime   Unsigned32,
    vRtrAdvPrefixValidLifetime       Unsigned32
}

vRtrAdvPrefixIfIndex             OBJECT-TYPE
    SYNTAX      InterfaceIndex
    MAX-ACCESS  not-accessible
    STATUS      current
    DESCRIPTION
        "The index value which uniquely identifies the interface on
         which this prefix is configured.  The interface identified
         by a particular value of this index is the same interface as
         identified by the same value of the IF-MIB's ifIndex."
    ::= { vRtrAdvPrefixEntry 1 }

vRtrAdvPrefixPrefix              OBJECT-TYPE
    SYNTAX      InetAddress (SIZE (16))
    MAX-ACCESS  not-accessible
    STATUS      current
    DESCRIPTION
        "The ipv6 address prefix. The length of this object is the standard
         length (16 bytes ) for IPv6 prefixes."
    ::= { vRtrAdvPrefixEntry 2 }

vRtrAdvPrefixLength              OBJECT-TYPE
    SYNTAX      InetAddressPrefixLength (4..127)
    MAX-ACCESS  not-accessible
    STATUS      current
    DESCRIPTION
        "The prefix length associated with this prefix. The value 0 has no
         special meaning for this object."
    ::= { vRtrAdvPrefixEntry 3 }

vRtrAdvPrefixRowStatus           OBJECT-TYPE
    SYNTAX      RowStatus
    MAX-ACCESS  read-create
    STATUS      current
    DESCRIPTION
        "The row status used for creation and deletion of router advertisement
         prefix entries."
    ::= { vRtrAdvPrefixEntry 4 }

vRtrAdvPrefixOnLinkFlag          OBJECT-TYPE
    SYNTAX      TruthValue
    MAX-ACCESS  read-create
    STATUS      current
    DESCRIPTION
        "This object has the value 'true(1)', if this prefix can be
         used  for on-link determination and the value 'false(2)'
         otherwise."
    REFERENCE
        "For IPv6 RFC2461, especially sections 2 and 4.6.2 and
         RFC2462"
    DEFVAL      { true }
    ::= { vRtrAdvPrefixEntry 5 }

vRtrAdvPrefixAutonomousFlag      OBJECT-TYPE
    SYNTAX      TruthValue
    MAX-ACCESS  read-create
    STATUS      current
    DESCRIPTION
        "Autonomous address configuration flag. When true(1),
         indicates that this prefix can be used for autonomous
         address configuration (i.e. can be used to form a local
         interface address).  If false(2), it is not used to auto-
         configure a local interface address."
    REFERENCE
        "For IPv6 RFC2461, especially sections 2 and 4.6.2 and
         RFC2462"
    DEFVAL      { true }
    ::= { vRtrAdvPrefixEntry 6 }

vRtrAdvPrefixPreferredLifetime   OBJECT-TYPE
    SYNTAX      Unsigned32
    UNITS       "seconds"
    MAX-ACCESS  read-create
    STATUS      current
    DESCRIPTION
        "The remaining length of time in seconds that this prefix will continue
         to be preferred, i.e. time until deprecation. A value of 4,294,967,295
         represents infinity.

         The address generated from a deprecated prefix should no longer be
         used as a source address in new communications, but packets received
         on such an interface are processed as expected."
    REFERENCE
        "For IPv6 RFC2461, especially sections 2 and 4.6.2 and
         RFC2462"
    DEFVAL      { 604800 }
    ::= { vRtrAdvPrefixEntry 7 }

vRtrAdvPrefixValidLifetime       OBJECT-TYPE
    SYNTAX      Unsigned32
    UNITS       "seconds"
    MAX-ACCESS  read-create
    STATUS      current
    DESCRIPTION
        "The remaining length of time, in seconds, that this prefix
         will continue to be valid, i.e. time until invalidation.  A
         value of 4,294,967,295 represents infinity.

         The address generated from an invalidated prefix should not appear as
         the destination or source address of a packet."
    REFERENCE
        "For IPv6 RFC2461, especially sections 2 and 4.6.2 and
         RFC2462"
    DEFVAL      { 2592000 }
    ::= { vRtrAdvPrefixEntry 8 }

vRtrInetStaticRouteTable         OBJECT-TYPE
    SYNTAX      SEQUENCE OF VRtrInetStaticRouteEntry
    MAX-ACCESS  not-accessible
    STATUS      current
    DESCRIPTION
        "The table of addressing information relevant to this entity's Static
         Routing table."
    ::= { tmnxVRtrObjs 24 }

vRtrInetStaticRouteEntry         OBJECT-TYPE
    SYNTAX      VRtrInetStaticRouteEntry
    MAX-ACCESS  not-accessible
    STATUS      current
    DESCRIPTION
        "A particular route to a particular destination, through a particular
         next hop."
    INDEX       {
        vRtrID,
        vRtrInetStaticRouteDestType,
        vRtrInetStaticRouteDest,
        vRtrInetStaticRouteDestPfxLen,
        vRtrInetStaticRouteIndex
    }
    ::= { vRtrInetStaticRouteTable 1 }

VRtrInetStaticRouteEntry         ::= SEQUENCE
{
    vRtrInetStaticRouteDestType      TmnxInetAddrTypeWithMcast,
    vRtrInetStaticRouteDest          InetAddress,
    vRtrInetStaticRouteDestPfxLen    InetAddressPrefixLength,
    vRtrInetStaticRouteIndex         Integer32,
    vRtrInetStaticRouteRowStatus     RowStatus,
    vRtrInetStaticRouteLastEnabledTime TimeStamp,
    vRtrInetStaticRouteStatus        INTEGER,
    vRtrInetStaticRouteStaticType    INTEGER,
    vRtrInetStaticRoutePreference    Unsigned32,
    vRtrInetStaticRouteMetric        Unsigned32,
    vRtrInetStaticRouteEgressIfIndex InterfaceIndexOrZero,
    vRtrInetStaticRouteNextHopType   InetAddressType,
    vRtrInetStaticRouteNextHop       InetAddress,
    vRtrInetStaticRouteNextHopIf     DisplayString,
    vRtrInetStaticRouteAdminState    TmnxAdminState,
    vRtrInetStaticRouteIgpShortcut   BITS,
    vRtrInetStaticRouteDisallowIgp   TruthValue,
    vRtrInetStaticRouteTag           Unsigned32,
    vRtrInetStaticRouteEnableBfd     TruthValue,
    vRtrInetStaticRouteCpeAddrType   InetAddressType,
    vRtrInetStaticRouteCpeAddr       InetAddress,
    vRtrInetStaticRouteCpeInterval   Unsigned32,
    vRtrInetStaticRouteCpeDropCnt    Unsigned32,
    vRtrInetStaticRouteCpeEnableLog  TruthValue,
    vRtrInetStaticRouteNHTunnelName  TNamedItemOrEmpty,
    vRtrInetStaticRoutePrefixListName TNamedItemOrEmpty,
    vRtrInetStaticRoutePrefixListFlag INTEGER,
    vRtrInetStaticRouteLdpSync       TruthValue,
    vRtrInetStaticRouteFC            TNamedItemOrEmpty,
    vRtrInetStaticRouteFCPriority    TPriorityOrUndefined,
    vRtrInetStaticRouteCommunityVal  DisplayString,
    vRtrInetStaticRouteCreationOrig  TmnxCreateOrigin,
    vRtrInetStaticRouteDynamicBgp    TmnxEnabledDisabled,
    vRtrInetStaticRouteDescription   TItemDescription,
    vRtrInetStaticRoutePaddingSize   Unsigned32,
    vRtrInetStaticRouteDynBgpNHType  InetAddressType,
    vRtrInetStaticRouteDynBgpNH      InetAddress,
    vRtrInetStaticRouteGenerateIcmp  TruthValue,
    vRtrInetStaticRouteValidateNH    TruthValue,
    vRtrInetStaticRouteSrcClassIndex ClassIndexOrNone,
    vRtrInetStaticRouteDstClassIndex ClassIndexOrNone,
    vRtrInetStaticRouteHoldTimeLeft  Unsigned32,
    vRtrInetStaticRouteLoadBalWeight Unsigned32,
    vRtrInetStaticRouteBackupNHType  InetAddressType,
    vRtrInetStaticRouteBackupNHAddr  InetAddress,
    vRtrInetStaticRouteBackupStatus  INTEGER,
    vRtrInetStaticRoutePfxLstRtrInst TLNamedItemOrEmpty
}

vRtrInetStaticRouteDestType      OBJECT-TYPE
    SYNTAX      TmnxInetAddrTypeWithMcast
    MAX-ACCESS  not-accessible
    STATUS      current
    DESCRIPTION
        "The value of vRtrInetStaticRouteDestType indicates the address type of
         vRtrInetStaticRouteDest address."
    ::= { vRtrInetStaticRouteEntry 1 }

vRtrInetStaticRouteDest          OBJECT-TYPE
    SYNTAX      InetAddress (SIZE (4|16|20))
    MAX-ACCESS  not-accessible
    STATUS      current
    DESCRIPTION
        "The value of vRtrInetStaticRouteDest indicates the destination IP
         address of this static route."
    ::= { vRtrInetStaticRouteEntry 2 }

vRtrInetStaticRouteDestPfxLen    OBJECT-TYPE
    SYNTAX      InetAddressPrefixLength
    MAX-ACCESS  not-accessible
    STATUS      current
    DESCRIPTION
        "The value of vRtrInetStaticRouteDestPfxLen indicates the prefix length
         associated with the vRtrInetStaticRouteDest address."
    ::= { vRtrInetStaticRouteEntry 3 }

vRtrInetStaticRouteIndex         OBJECT-TYPE
    SYNTAX      Integer32 (1..2147483647)
    MAX-ACCESS  not-accessible
    STATUS      current
    DESCRIPTION
        "The value of vRtrInetStaticRouteIndex indicates the fifth index for
         the vRtrInetStaticRouteTable.

         The fifth index to vRtrInetStaticRouteTable identifies a specific
         next-hop route to distinguish it from other routes that share the same
         destination address."
    ::= { vRtrInetStaticRouteEntry 4 }

vRtrInetStaticRouteRowStatus     OBJECT-TYPE
    SYNTAX      RowStatus
    MAX-ACCESS  read-create
    STATUS      current
    DESCRIPTION
        "vRtrInetStaticRouteRowStatus controls the creation and deletion of
         rows in the table."
    ::= { vRtrInetStaticRouteEntry 5 }

vRtrInetStaticRouteLastEnabledTime OBJECT-TYPE
    SYNTAX      TimeStamp
    MAX-ACCESS  read-only
    STATUS      current
    DESCRIPTION
        "The value of vRtrInetStaticRouteLastEnabledTime indicates the
         sysUpTime value when vRtrInetStaticRouteStatus was last set to active
         (1) to allow IP forwarding on this static route entry."
    ::= { vRtrInetStaticRouteEntry 6 }

vRtrInetStaticRouteStatus        OBJECT-TYPE
    SYNTAX      INTEGER {
        active   (1),
        inactive (2)
    }
    MAX-ACCESS  read-only
    STATUS      current
    DESCRIPTION
        "The value of vRtrInetStaticRouteStatus indicates
         whether or not this route entry is active in the system.
         When an interface transitions to the down state, any
         associated route entries are marked as 'inactive'
         and are usually not displayed in a standard route
         table listing.  When the interface transitions
         to the up state, the agent marks the associated routes as
         'active'"
    ::= { vRtrInetStaticRouteEntry 7 }

vRtrInetStaticRouteStaticType    OBJECT-TYPE
    SYNTAX      INTEGER {
        unknown   (0),
        nextHop   (1),
        indirect  (2),
        blackHole (3),
        grt       (4),
        reserved5 (5)
    }
    MAX-ACCESS  read-create
    STATUS      current
    DESCRIPTION
        "The value of vRtrInetStaticRouteStaticType specifies the type of
         static route represented by this row entry. The values of
         vRtrInetStaticRouteNextHopType, vRtrInetStaticRouteNextHop,
         vRtrInetStaticRouteNextHopIf and vRtrInetStaticRouteNHTunnelName
         depends on the value of vRtrInetStaticRouteStaticType.

         For details please look at the following chart:

         vRtrInetStaticRouteStaticType  unknown nexthop indirect blackHole grt
         ---------------------------------------------------------------------
         vRtrInetStaticRouteNextHopType unknown valid   valid   unknown  unknown
         vRtrInetStaticRouteNextHop     null    valid   valid   null     null
         vRtrInetStaticRouteNextHopIf   null    valid   null    null     null
         vRtrInetStaticRouteNHTunnelName null  valid   null    null      null

         Though all the values of vRtrInetStaticRouteNextHop,
         vRtrInetStaticRouteNextHopIf and vRtrInetStaticRouteNHTunnelName can
         be valid when the value of vRtrInetStaticRouteStaticType is 'nexthop',
         please note that at most only one of them can have a non null string."
    DEFVAL      { unknown }
    ::= { vRtrInetStaticRouteEntry 8 }

vRtrInetStaticRoutePreference    OBJECT-TYPE
    SYNTAX      Unsigned32 (1..255)
    MAX-ACCESS  read-create
    STATUS      current
    DESCRIPTION
        "The value of vRtrInetStaticRoutePreference specifies the priority of
         this static route versus the routes from different sources such as BGP
         or OSPF etc.

         Different protocols should not be configured with the same preference,
         if this occurs the tiebreaker is determined per the default preference
         value as defined in the table below.

         If multiple routes are learned with an identical preference using the
         same protocol, the lowest cost is used. If multiple routes are learned
         with an identical preference using the same protocol and the costs
         (metrics) are equal, then the decision as to what route to use is
         determined by the configuration of the ecmp command.

         Default preferences.


         Route Type             Preference      Configurable
         ----------             ----------      ------------
         Direct attached                 0                no
         Static route                    5               yes
         MPLS (post FCS)                 7
         OSPF Internal routes           10                no
         OSPF External                 150               yes
         BGP                           170               yes"
    DEFVAL      { 5 }
    ::= { vRtrInetStaticRouteEntry 9 }

vRtrInetStaticRouteMetric        OBJECT-TYPE
    SYNTAX      Unsigned32 (0..65535)
    MAX-ACCESS  read-create
    STATUS      current
    DESCRIPTION
        "The value of vRtrInetStaticRouteMetric specifies the metric for the
         static route.

         When ipCidrRouteProto has a value of 'netmgmt' to specify that
         this entry is a static route, the value of vRtrInetStaticRouteMetric
         associates a metric value with the route. This value is used
         when importing this static route into other protocols such as
         OSPF.  When the metric is configured as zero then the metric
         configured in OSPF, default-import-metric, applies.  This value
         is also used to determine which static route to install in the
         forwarding table:

         If there are multiple static routes with the same preference but
         unequal metric then the lower cost (metric) route will be installed.

         If there are multiple static routes with equal preference and metrics
         then ecmp rules apply.

         If there are multiple routes with unequal preference then the lower
         preference route will be installed."
    DEFVAL      { 1 }
    ::= { vRtrInetStaticRouteEntry 10 }

vRtrInetStaticRouteEgressIfIndex OBJECT-TYPE
    SYNTAX      InterfaceIndexOrZero
    MAX-ACCESS  read-only
    STATUS      current
    DESCRIPTION
        "The value of vRtrInetStaticRouteEgressIfIndex indicates the outgoing
         ifIndex for this route as computed by the static route module. This
         variable will have a value of 0 if vRtrInetStaticRouteStatus is
         'inactive' or if this static route is configured as a black hole."
    ::= { vRtrInetStaticRouteEntry 11 }

vRtrInetStaticRouteNextHopType   OBJECT-TYPE
    SYNTAX      InetAddressType
    MAX-ACCESS  read-create
    STATUS      current
    DESCRIPTION
        "The value of vRtrInetStaticRouteNextHopType specifies the address type
         of vRtrInetStaticRouteNextHop address."
    DEFVAL      { unknown }
    ::= { vRtrInetStaticRouteEntry 12 }

vRtrInetStaticRouteNextHop       OBJECT-TYPE
    SYNTAX      InetAddress (SIZE (0|4|16|20))
    MAX-ACCESS  read-create
    STATUS      current
    DESCRIPTION
        "The value of vRtrInetStaticRouteNextHop specifies the ip address of
         the next hop for the static route and it depends on the value of
         vRtrInetStaticRouteStaticType.

         At most only one of the values of the three objects:
         vRtrInetStaticRouteNextHop, vRtrInetStaticRouteNextHopIf and
         vRtrInetStaticRouteNHTunnelName can be a non null string.

         If the value of vRtrInetStaticRouteStaticType is 'unknown' or
         'blackHole' then the value of vRtrInetStaticRouteNextHopType should be
         'unknown' and the values of vRtrInetStaticRouteNextHop,
         vRtrInetStaticRouteNextHopIf, vRtrInetStaticRouteNHTunnelName should
         be null strings."
    ::= { vRtrInetStaticRouteEntry 13 }

vRtrInetStaticRouteNextHopIf     OBJECT-TYPE
    SYNTAX      DisplayString (SIZE (0..32))
    MAX-ACCESS  read-create
    STATUS      current
    DESCRIPTION
        "The value of vRtrInetStaticRouteNextHopIf specifies the name of the
         interface to be used for the next hop of this static route and it
         depends on the value of vRtrInetStaticRouteStaticType.

         At most only one of the values of the three objects:
         vRtrInetStaticRouteNextHop, vRtrInetStaticRouteNextHopIf and
         vRtrInetStaticRouteNHTunnelName can be a non null string.

         If the value of vRtrInetStaticRouteStaticType is 'unknown' or
         'blackHole' then the value of vRtrInetStaticRouteNextHopType should be
         'unknown' and the values of vRtrInetStaticRouteNextHop,
         vRtrInetStaticRouteNextHopIf, vRtrInetStaticRouteNHTunnelName should
         be null strings."
    ::= { vRtrInetStaticRouteEntry 14 }

vRtrInetStaticRouteAdminState    OBJECT-TYPE
    SYNTAX      TmnxAdminState
    MAX-ACCESS  read-create
    STATUS      current
    DESCRIPTION
        "The value of vRtrInetStaticRouteAdminState specifies the desired
         administrative state for this virtual router static route"
    DEFVAL      { outOfService }
    ::= { vRtrInetStaticRouteEntry 15 }

vRtrInetStaticRouteIgpShortcut   OBJECT-TYPE
    SYNTAX      BITS {
        te  (0),
        ldp (1),
        ip  (2)
    }
    MAX-ACCESS  read-create
    STATUS      obsolete
    DESCRIPTION
        "The value of vRtrInetStaticRouteIgpShortcut specifies the Layer 2
         tunneling mechanism used for IGP shortcuts.

         The value of vRtrInetStaticRouteIgpShortcut is valid only for indirect
         static routes (i.e. vRtrInetStaticRouteStaticType is 'indirect'). The
         bits of vRtrInetStaticRouteIgpShortcut identify Layer 2 tunneling
         mechanisms used for IGP shortcuts. If a bit is set, IGP shortcuts
         associated with that tunneling mechanism will be used to resolve
         next-hop for the static route. If no bits are set, IGP shortcuts will
         not be used to resolve next-hop for the static routes.

         The tunneling mechanisms represented by each bit are:
           te(0)  - RSVP Traffic Engineering
           ldp(1) - LDP /32 Route Forwarding Equivalence Class (FEC)
           ip(2)  - IP (IP-in-IP or GRE)

         Evaluation of tunnel preference is based on the following order, in
         descending priority:
           1. Traffic Engineered Shortcut (RSVP-TE)
           2. LDP /32 Route FEC Shortcut
           3. IP Shortcut (IP-in-IP or GRE)
           4. Actual IGP Next-Hop.

         This object was replaced by vRtrInetSRIndirectTunnelLdp and
         vRtrInetSRIndirectTunnelRsvpTe objects in 13.0."
    DEFVAL      { {} }
    ::= { vRtrInetStaticRouteEntry 16 }

vRtrInetStaticRouteDisallowIgp   OBJECT-TYPE
    SYNTAX      TruthValue
    MAX-ACCESS  read-create
    STATUS      obsolete
    DESCRIPTION
        "The value of vRtrInetStaticRouteDisallowIgp specifies if IGP shortcuts
         are to be used or not.

         The value of vRtrInetStaticRouteDisallowIgp is valid only for indirect
         static routes (i.e. vRtrInetStaticRouteStaticType is 'indirect'). If
         the value of vRtrInetStaticRouteDisallowIgp is set to 'true', and if
         none of the defined tunneling mechanisms (RSVP-TE, LDP or IP) qualify
         as a next-hop, the normal IGP next-hop to the indirect next-hop
         address will not be used. If the value is set to 'false', IGP next-hop
         to the indirect next-hop address can be used as the next-hop of the
         last resort.

         This object was replaced by vRtrInetSRIndirectTunnelDisalIgp object in
         13.0."
    DEFVAL      { false }
    ::= { vRtrInetStaticRouteEntry 17 }

vRtrInetStaticRouteTag           OBJECT-TYPE
    SYNTAX      Unsigned32 (0..4294967295)
    MAX-ACCESS  read-create
    STATUS      current
    DESCRIPTION
        "The value of vRtrInetStaticRouteTag specifies a 32-bit integer tag
         that is used to add to the static route. This tag could then be used
         in route policies to control distribution of the route into other
         protocols. A value of 0 indicates that the tag has not been set."
    DEFVAL      { 0 }
    ::= { vRtrInetStaticRouteEntry 18 }

vRtrInetStaticRouteEnableBfd     OBJECT-TYPE
    SYNTAX      TruthValue
    MAX-ACCESS  read-create
    STATUS      current
    DESCRIPTION
        "The value of vRtrInetStaticRouteEnableBfd specifies whether or not
         Bi-directional Forwarding Detection is enabled on this static route.

         When the value is 'true', this static route can establish BFD sessions
         and use BFD as a signalling mechanism. When it is 'false', it cannot
         use BFD."
    DEFVAL      { false }
    ::= { vRtrInetStaticRouteEntry 19 }

vRtrInetStaticRouteCpeAddrType   OBJECT-TYPE
    SYNTAX      InetAddressType
    MAX-ACCESS  read-create
    STATUS      current
    DESCRIPTION
        "The value of vRtrInetStaticRouteCpeAddrType specifies the address type
         of vRtrInetStaticRouteCpeAddr address.

         When the value of vRtrInetStaticRouteCpeAddrType is not 'unknown',
         statistics for the Customer Provided Equipment (CPE) host checks for
         this static route entry will be found in the sparsely dependent table
         extension, vRtrInetStatRteCpeChkStatsTable."
    DEFVAL      { unknown }
    ::= { vRtrInetStaticRouteEntry 20 }

vRtrInetStaticRouteCpeAddr       OBJECT-TYPE
    SYNTAX      InetAddress (SIZE (0|4|16))
    MAX-ACCESS  read-create
    STATUS      current
    DESCRIPTION
        "The value of vRtrInetStaticRouteCpeAddr specifies the IP address of
         the target CPE device. When this object is configured, ICMP pings will
         be sent to this target IP address to determine CPE connectivity and
         whether this static route should be active.

         When the value of vRtrInetStaticRouteCpeAddr is non-empty, statistics
         for the CPE host checks for this static route entry will be found in
         the sparsely dependent table extension,
         vRtrInetStatRteCpeChkStatsTable."
    DEFVAL      { ''H }
    ::= { vRtrInetStaticRouteEntry 21 }

vRtrInetStaticRouteCpeInterval   OBJECT-TYPE
    SYNTAX      Unsigned32 (1..255)
    UNITS       "seconds"
    MAX-ACCESS  read-create
    STATUS      current
    DESCRIPTION
        "The value of vRtrInetStaticRouteCpeInterval specifies the interval, in
         seconds, between ICMP pings to the target CPE IP address,
         vRtrInetStaticRouteCpeAddr."
    DEFVAL      { 1 }
    ::= { vRtrInetStaticRouteEntry 22 }

vRtrInetStaticRouteCpeDropCnt    OBJECT-TYPE
    SYNTAX      Unsigned32 (1..255)
    MAX-ACCESS  read-create
    STATUS      current
    DESCRIPTION
        "The value of vRtrInetStaticRouteCpeDropCnt specifies the number of
         consecutive ping replies that must be missed before concluding the CPE
         is down. If the CPE is determined to be down, the associated static
         route will be deactivated."
    DEFVAL      { 3 }
    ::= { vRtrInetStaticRouteEntry 23 }

vRtrInetStaticRouteCpeEnableLog  OBJECT-TYPE
    SYNTAX      TruthValue
    MAX-ACCESS  read-create
    STATUS      current
    DESCRIPTION
        "The value of vRtrInetStaticRouteCpeEnableLog specifies whether to
         enable the logging of transitions between active and inactive based on
         the CPE connectivity check.

         A value of 'true (1)' indicates that logging should be enabled."
    DEFVAL      { false }
    ::= { vRtrInetStaticRouteEntry 24 }

vRtrInetStaticRouteNHTunnelName  OBJECT-TYPE
    SYNTAX      TNamedItemOrEmpty
    MAX-ACCESS  read-create
    STATUS      current
    DESCRIPTION
        "The value of vRtrInetStaticRouteNHTunnelName specifies the name of the
         IPsec tunnel to be used for the nexthop of this static route and it
         depends on the value of vRtrInetStaticRouteStaticType.

         The value of vRtrInetStaticRouteNHTunnelName is valid only for static
         routes configured for a vprn service. An 'inconsistentValue' error is
         returned if an attempt is made to set this object for the base
         instance which can be identified by vRtrID value of '1'.

         At most only one of the values of the three objects:
         vRtrInetStaticRouteNextHop, vRtrInetStaticRouteNextHopIf and
         vRtrInetStaticRouteNHTunnelName can be a non null string.

         If the value of vRtrInetStaticRouteStaticType is 'blackHole' then the
         value of vRtrInetStaticRouteNextHopType should be 'unknown' and the
         values of vRtrInetStaticRouteNextHop, vRtrInetStaticRouteNextHopIf,
         vRtrInetStaticRouteNHTunnelName should be null strings."
    ::= { vRtrInetStaticRouteEntry 25 }

vRtrInetStaticRoutePrefixListName OBJECT-TYPE
    SYNTAX      TNamedItemOrEmpty
    MAX-ACCESS  read-create
    STATUS      current
    DESCRIPTION
        "The value of vRtrInetStaticRoutePrefixListName specifies the name of a
         prefix list to match on. This value allows the existence of specified
         routes within the Route Table Manager (RTM) to trigger the addition of
         a static route in the RTM.

         If any of the routes specified in the
         vRtrInetStaticRoutePrefixListName exists in the RTM, then the
         associated static route should be added to the RTM."
    DEFVAL      { "" }
    ::= { vRtrInetStaticRouteEntry 26 }

vRtrInetStaticRoutePrefixListFlag OBJECT-TYPE
    SYNTAX      INTEGER {
        any  (0),
        all  (1),
        none (2)
    }
    MAX-ACCESS  read-create
    STATUS      current
    DESCRIPTION
        "The value of vRtrInetStaticRoutePrefixListFlag specifies the routes to
         match on from vRtrInetStaticRoutePrefixListName.

         If 'all (1)' is specified, all of the routes specified in the
         vRtrInetStaticRoutePrefixListName should exist in the Route Table
         Manager (RTM) for the associated static route to be added in the RTM.

         If 'none (2)' is specified, none of the routes specified in the
         vRtrInetStaticRoutePrefixListName should exist in the RTM for the
         associated static route to be added in the RTM.

         The value of vRtrInetStaticRoutePrefixListFlag will be reset to the
         default value when vRtrInetStaticRoutePrefixListName is set to the
         default value."
    DEFVAL      { any }
    ::= { vRtrInetStaticRouteEntry 27 }

vRtrInetStaticRouteLdpSync       OBJECT-TYPE
    SYNTAX      TruthValue
    MAX-ACCESS  read-create
    STATUS      current
    DESCRIPTION
        "The value of vRtrInetStaticRouteLdpSync specifies whether the the LDP
         synchronization timer for this route on an interface,
         vRtrIfLdpSyncTimer, is enabled or not.

         If the value of vRtrInetStaticRouteLdpSync is 'true (1)', this static
         route would not enable the preferred route immediately after the
         interface to the next-hop comes up but would wait for the LDP
         adjacency on the link to come up and start the ldp sync timer,
         vRtrIfLdpSyncTimer. On timer expiration, routing will enable the
         static route.

         If the value of vRtrInetStaticRouteLdpSync is 'false (2)',
         vRtrIfLdpSyncTimer would not be applied to this static route."
    DEFVAL      { false }
    ::= { vRtrInetStaticRouteEntry 28 }

vRtrInetStaticRouteFC            OBJECT-TYPE
    SYNTAX      TNamedItemOrEmpty
    MAX-ACCESS  read-create
    STATUS      current
    DESCRIPTION
        "The value of vRtrInetStaticRouteFC specifies the forwarding class
         associated with the static route.

         This object can take one of the following eight values - 'be', 'l2',
         'af', 'l1', 'h2', 'ef', 'h1' or 'nc'.

         An 'inconsistentValue' error is returned if an attempt is made to set
         this object to a non-default value when vRtrInetStaticRouteStaticType
         is not set to either 'indirect' or 'nexthop'."
    DEFVAL      { ''H }
    ::= { vRtrInetStaticRouteEntry 29 }

vRtrInetStaticRouteFCPriority    OBJECT-TYPE
    SYNTAX      TPriorityOrUndefined
    MAX-ACCESS  read-create
    STATUS      current
    DESCRIPTION
        "The value of vRtrInetStaticRouteFCPriority specifies the priority to
         be assigned to the static routes.

         An 'inconsistentValue' error is returned if an attempt is made to set
         this object to a non-default value when vRtrInetStaticRouteStaticType
         is not set to either 'indirect' or 'nexthop'."
    DEFVAL      { undefined }
    ::= { vRtrInetStaticRouteEntry 30 }

vRtrInetStaticRouteCommunityVal  OBJECT-TYPE
    SYNTAX      DisplayString (SIZE (0..72))
    MAX-ACCESS  read-create
    STATUS      current
    DESCRIPTION
        "The value of vRtrInetStaticRouteCommunityVal specifies the community
         name that is used to add to the static route. This value could then
         be used in route policies to control the distribution of the route
         into other protocols and by BGP to control the distribution of this
         route into other routers. A value of ''H  indicates that the
         vRtrInetStaticRouteCommunityVal has not been set."
    DEFVAL      { ''H }
    ::= { vRtrInetStaticRouteEntry 31 }

vRtrInetStaticRouteCreationOrig  OBJECT-TYPE
    SYNTAX      TmnxCreateOrigin
    MAX-ACCESS  read-only
    STATUS      current
    DESCRIPTION
        "The value of vRtrInetStaticRouteCreationOrig indicates the mechanism
         that created this static route."
    ::= { vRtrInetStaticRouteEntry 32 }

vRtrInetStaticRouteDynamicBgp    OBJECT-TYPE
    SYNTAX      TmnxEnabledDisabled
    MAX-ACCESS  read-create
    STATUS      current
    DESCRIPTION
        "The value of vRtrInetStaticRouteDynamicBgp specifies whether to enable
         a static route to dynamically derive its next-hop from the best BGP
         route for the exact same IP prefix.

         A value of 'enabled (1)' indicates that a static route is enabled to
         dynamically derive its next-hop from the best BGP route for the exact
         same prefix."
    DEFVAL      { disabled }
    ::= { vRtrInetStaticRouteEntry 33 }

vRtrInetStaticRouteDescription   OBJECT-TYPE
    SYNTAX      TItemDescription
    MAX-ACCESS  read-create
    STATUS      current
    DESCRIPTION
        "The value of vRtrInetStaticRouteDescription is a user provided
         description string for a static route.  It can consist of any
         printable, seven-bit ASCII characters up to 80 characters in
         length."
    DEFVAL      { ''H }
    ::= { vRtrInetStaticRouteEntry 34 }

vRtrInetStaticRoutePaddingSize   OBJECT-TYPE
    SYNTAX      Unsigned32 (0..16384)
    UNITS       "bytes"
    MAX-ACCESS  read-create
    STATUS      current
    DESCRIPTION
        "The value of vRtrInetStaticRoutePaddingSize specifies the padding size
         for the ICMP ping test packet of the cpe connectivity check.
         vRtrInetStaticRoutePaddingSize is valid if the value of
         vRtrInetStaticRouteCpeAddr is non-empty. This option applies to IPv4
          and IPv6 static routes."
    DEFVAL      { 56 }
    ::= { vRtrInetStaticRouteEntry 35 }

vRtrInetStaticRouteDynBgpNHType  OBJECT-TYPE
    SYNTAX      InetAddressType
    MAX-ACCESS  read-only
    STATUS      current
    DESCRIPTION
        "The value of vRtrInetStaticRouteDynBgpNHType indicates the address
         type of vRtrInetStaticRouteDynBgpNH address.

         The value of vRtrInetStaticRouteDynBgpNHType is valid only when
         vRtrInetStaticRouteStaticType is set to 'blackHole' and if
         vRtrInetStaticRouteDynamicBgp is set to 'enabled'."
    ::= { vRtrInetStaticRouteEntry 36 }

vRtrInetStaticRouteDynBgpNH      OBJECT-TYPE
    SYNTAX      InetAddress (SIZE (0|4|16|20))
    MAX-ACCESS  read-only
    STATUS      current
    DESCRIPTION
        "The value of vRtrInetStaticRouteDynBgpNH indicates the ip address of
         the next hop for the static route and it depends on the value of
         vRtrInetStaticRouteStaticType.

         When the value of vRtrInetStaticRouteStaticType is 'blackHole' and the
         value of vRtrInetStaticRouteDynamicBgp is 'enabled' then the value of
         vRtrInetStaticRouteDynBgpNH is valid and dynamically derived from the
         best BGP route for the exact same prefix."
    ::= { vRtrInetStaticRouteEntry 37 }

vRtrInetStaticRouteGenerateIcmp  OBJECT-TYPE
    SYNTAX      TruthValue
    MAX-ACCESS  read-create
    STATUS      current
    DESCRIPTION
        "The value of vRtrInetStaticRouteGenerateIcmp specifies if we should
         generate and send an ICMP message when a packet matches a static route
         with a black-hole next-hop.

         An 'inconsistentValue' error will be returned if an attempt is made to
         set vRtrInetStaticRouteGenerateIcmp when the value of
         vRtrInetStaticRouteStaticType is not set to 'blackHole(3)'."
    DEFVAL      { false }
    ::= { vRtrInetStaticRouteEntry 38 }

vRtrInetStaticRouteValidateNH    OBJECT-TYPE
    SYNTAX      TruthValue
    MAX-ACCESS  read-create
    STATUS      current
    DESCRIPTION
        "The value of vRtrInetStaticRouteValidateNH specifies whether or not to
         track the state of the next-hop in the IPV4 ARP Cache or the IPv6
         Neighbor Cache.

         When vRtrInetStaticRouteValidateNH is set to 'true', the next-hop is
         checked for reachability in the IPV4 ARP Cache or the IPV6 Neighbor
         Cache.

         The object vRtrInetStaticRouteValidateNH is only supported for
         directly connected next-hops."
    DEFVAL      { false }
    ::= { vRtrInetStaticRouteEntry 39 }

vRtrInetStaticRouteSrcClassIndex OBJECT-TYPE
    SYNTAX      ClassIndexOrNone
    MAX-ACCESS  read-create
    STATUS      current
    DESCRIPTION
        "The value of vRtrInetStaticRouteSrcClassIndex specifies the
         source-class for this static route.

         The value of 0 means no source-class."
    DEFVAL      { 0 }
    ::= { vRtrInetStaticRouteEntry 40 }

vRtrInetStaticRouteDstClassIndex OBJECT-TYPE
    SYNTAX      ClassIndexOrNone
    MAX-ACCESS  read-create
    STATUS      current
    DESCRIPTION
        "The value of vRtrInetStaticRouteDstClassIndex specifies the
         destination-class for this static route.

         The value of 0 means no destination-class."
    DEFVAL      { 0 }
    ::= { vRtrInetStaticRouteEntry 41 }

vRtrInetStaticRouteHoldTimeLeft  OBJECT-TYPE
    SYNTAX      Unsigned32
    MAX-ACCESS  read-only
    STATUS      current
    DESCRIPTION
        "The value of vRtrInetStaticRouteHoldTimeLeft indicates the remaining
         time in seconds for static route to become active/up, if static route
         is being held down. A non-zero value indicates static route is being
         held down for this many seconds."
    ::= { vRtrInetStaticRouteEntry 42 }

vRtrInetStaticRouteLoadBalWeight OBJECT-TYPE
    SYNTAX      Unsigned32 (0 | 1..4294967295)
    MAX-ACCESS  read-create
    STATUS      current
    DESCRIPTION
        "The value of vRtrInetStaticRouteLoadBalWeight specifies the
         load-balancing-weight for all of the ECMP next-hops.

         The value of 0 means no load-balancing-weight."
    DEFVAL      { 0 }
    ::= { vRtrInetStaticRouteEntry 43 }

vRtrInetStaticRouteBackupNHType  OBJECT-TYPE
    SYNTAX      InetAddressType
    MAX-ACCESS  read-create
    STATUS      current
    DESCRIPTION
        "The value of vRtrInetStaticRouteBackupNHType specifies the backup
         next-hop  address type of vRtrInetStaticRouteBackupNHAddr address."
    DEFVAL      { unknown }
    ::= { vRtrInetStaticRouteEntry 44 }

vRtrInetStaticRouteBackupNHAddr  OBJECT-TYPE
    SYNTAX      InetAddress (SIZE (0|4|16))
    MAX-ACCESS  read-create
    STATUS      current
    DESCRIPTION
        "The value of vRtrInetStaticRouteBackupNHAddr specifies the ip address
         of the backup next-hop for the static route."
    DEFVAL      { ''H }
    ::= { vRtrInetStaticRouteEntry 45 }

vRtrInetStaticRouteBackupStatus  OBJECT-TYPE
    SYNTAX      INTEGER {
        inactive        (1),
        activeAsBackup  (2),
        activeAsPrimary (3)
    }
    MAX-ACCESS  read-only
    STATUS      current
    DESCRIPTION
        "The value of vRtrInetStaticRouteBackupStatus indicates whether
         vRtrInetStaticRouteBackupNHAddr is in use or not.

         If vRtrInetStaticRouteBackupNHAddr is not in use, the
         vRtrInetStaticRouteBackupStatus is 'inactive'. If
         vRtrInetStaticRouteBackupNHAddr is in use as a backup to the primary
         hop represented by vRtrInetStaticRouteNextHop,
         vRtrInetStaticRouteBackupStatus is 'activeAsBackup'. If
         vRtrInetStaticRouteBackupNHAddr is in use as the primary hop,
         vRtrInetStaticRouteBackupStatus is 'activeAsPrimary'."
    ::= { vRtrInetStaticRouteEntry 46 }

vRtrInetStaticRoutePfxLstRtrInst OBJECT-TYPE
    SYNTAX      TLNamedItemOrEmpty
    MAX-ACCESS  read-create
    STATUS      current
    DESCRIPTION
        "The value of the vRtrInetStaticRoutePfxLstRtrInst specifies the name
         of the router instance to match routes on
         vRtrInetStaticRoutePrefixListName."
    DEFVAL      { ''H }
    ::= { vRtrInetStaticRouteEntry 49 }

vRtrInetStaticRouteIndexTable    OBJECT-TYPE
    SYNTAX      SEQUENCE OF VRtrInetStaticRouteIndexEntry
    MAX-ACCESS  not-accessible
    STATUS      current
    DESCRIPTION
        "This entity's Static Route Index Table."
    ::= { tmnxVRtrObjs 25 }

vRtrInetStaticRouteIndexEntry    OBJECT-TYPE
    SYNTAX      VRtrInetStaticRouteIndexEntry
    MAX-ACCESS  not-accessible
    STATUS      current
    DESCRIPTION
        "The available index for the vRtrInetStaticRouteTable for every
         destination per virtual router."
    INDEX       {
        vRtrID,
        vRtrInetStaticRouteDestType,
        vRtrInetStaticRouteDest,
        vRtrInetStaticRouteDestPfxLen
    }
    ::= { vRtrInetStaticRouteIndexTable 1 }

VRtrInetStaticRouteIndexEntry    ::= SEQUENCE
{ vRtrInetStaticRouteAvailIndex    TestAndIncr }

vRtrInetStaticRouteAvailIndex    OBJECT-TYPE
    SYNTAX      TestAndIncr (1..2147483647)
    MAX-ACCESS  read-only
    STATUS      current
    DESCRIPTION
        "The value of vRtrInetStaticRouteAvailIndex indicates the available
         fifth index for the vRtrInetStaticRouteTable.

         The fifth index to vRtrInetStaticRouteTable identifies a specific
         next-hop route to distinguish it from other routes that share the same
         destination address."
    ::= { vRtrInetStaticRouteIndexEntry 1 }

vRtrInetInstAggrTblLastChged     OBJECT-TYPE
    SYNTAX      TimeStamp
    MAX-ACCESS  read-only
    STATUS      current
    DESCRIPTION
        "Timestamp of the last change to the vRtrInetInstAggrTable either from
         adding a row or removing a row."
    ::= { tmnxVRtrObjs 26 }

vRtrInetInstAggrTable            OBJECT-TYPE
    SYNTAX      SEQUENCE OF VRtrInetInstAggrEntry
    MAX-ACCESS  not-accessible
    STATUS      current
    DESCRIPTION
        "The vRtrInetInstAggrTable is the list of configured virtual router
         aggregations and their operational status information.

         vRtrInetInstAggrTable specifies the route aggregates that should be
         generated into the virtual router if at least one contributing route
         (more specific) is learned.

         A route could match multiple aggregate statements. For instance, with
         the following entries: aggregate 10.0.0.0/8 aggregate 10.1.0.0/16

         If the route 10.1.1.0/24 is learned, both aggregates would be
         generated."
    ::= { tmnxVRtrObjs 27 }

vRtrInetInstAggrEntry            OBJECT-TYPE
    SYNTAX      VRtrInetInstAggrEntry
    MAX-ACCESS  not-accessible
    STATUS      current
    DESCRIPTION
        "vRtrInetInstAggrEntry indicates an entry (conceptual row) in the
         vRtrInetInstAggrTable. Entries are created and destroyed by user."
    INDEX       {
        vRtrID,
        vRtrInetAggrIpPrefixType,
        vRtrInetAggrIpPrefix,
        vRtrInetAggrIpPrefixLen
    }
    ::= { vRtrInetInstAggrTable 1 }

VRtrInetInstAggrEntry            ::= SEQUENCE
{
    vRtrInetAggrIpPrefixType         InetAddressType,
    vRtrInetAggrIpPrefix             InetAddress,
    vRtrInetAggrIpPrefixLen          InetAddressPrefixLength,
    vRtrInetAggrRowStatus            RowStatus,
    vRtrInetAggrLastChanged          TimeStamp,
    vRtrInetAggrSummaryOnly          TruthValue,
    vRtrInetAggrASSet                TruthValue,
    vRtrInetAggrAggregatorAS         TmnxBgpAutonomousSystem,
    vRtrInetAggrAggregatorIPAddr     IpAddress,
    vRtrInetAggrOperState            TmnxOperState,
    vRtrInetAggrAggregatorAS4Byte    InetAutonomousSystemNumber,
    vRtrInetAggrNextHopType          INTEGER,
    vRtrInetAggrCommunityVal         DisplayString,
    vRtrInetAggrIndirectAddrType     InetAddressType,
    vRtrInetAggrIndirectAddr         InetAddress,
    vRtrInetAggrGenerateIcmp         TruthValue,
    vRtrInetAggrDescription          TItemDescription,
    vRtrInetAggrCommunityVal2        DisplayString,
    vRtrInetAggrCommunityVal3        DisplayString,
    vRtrInetAggrCommunityVal4        DisplayString,
    vRtrInetAggrCommunityVal5        DisplayString,
    vRtrInetAggrCommunityVal6        DisplayString,
    vRtrInetAggrCommunityVal7        DisplayString,
    vRtrInetAggrCommunityVal8        DisplayString,
    vRtrInetAggrCommunityVal9        DisplayString,
    vRtrInetAggrCommunityVal10       DisplayString,
    vRtrInetAggrCommunityVal11       DisplayString,
    vRtrInetAggrCommunityVal12       DisplayString,
    vRtrInetAggrFlags                BITS,
    vRtrInetAggrLocalPreference      Unsigned32,
    vRtrInetAggrDiscardComponent     TruthValue,
    vRtrInetAggrTunnelGroup          TmnxTunnelGroupIdOrZero,
    vRtrInetAggrPolicy               TLNamedItemOrEmpty
}

vRtrInetAggrIpPrefixType         OBJECT-TYPE
    SYNTAX      InetAddressType
    MAX-ACCESS  not-accessible
    STATUS      current
    DESCRIPTION
        "The value of vRtrInetAggrIpPrefixType indicates the IP address type of
         vRtrInetAggrIpPrefix."
    ::= { vRtrInetInstAggrEntry 1 }

vRtrInetAggrIpPrefix             OBJECT-TYPE
    SYNTAX      InetAddress (SIZE (4|16))
    MAX-ACCESS  not-accessible
    STATUS      current
    DESCRIPTION
        "The value of vRtrInetAggrIpPrefixType indicates the IP address prefix
         to match for the aggregation."
    ::= { vRtrInetInstAggrEntry 2 }

vRtrInetAggrIpPrefixLen          OBJECT-TYPE
    SYNTAX      InetAddressPrefixLength
    MAX-ACCESS  not-accessible
    STATUS      current
    DESCRIPTION
        "The value of vRtrInetAggrIpPrefixLen indicates the prefix length for
         vRtrInetAggrIpPrefix, to match for the aggregation."
    ::= { vRtrInetInstAggrEntry 3 }

vRtrInetAggrRowStatus            OBJECT-TYPE
    SYNTAX      RowStatus
    MAX-ACCESS  read-create
    STATUS      current
    DESCRIPTION
        "vRtrInetAggrRowStatus controls the creation and deletion of rows in
         the table."
    ::= { vRtrInetInstAggrEntry 4 }

vRtrInetAggrLastChanged          OBJECT-TYPE
    SYNTAX      TimeStamp
    MAX-ACCESS  read-only
    STATUS      current
    DESCRIPTION
        "The value of vRtrInetAggrLastChanged indicates the time stamp of the
         last change to this row of vRtrInetInstAggrTable."
    ::= { vRtrInetInstAggrEntry 5 }

vRtrInetAggrSummaryOnly          OBJECT-TYPE
    SYNTAX      TruthValue
    MAX-ACCESS  read-create
    STATUS      current
    DESCRIPTION
        "The value of vRtrInetAggrSummaryOnly specifies if specific routes that
         make up aggregates are advertised or not.

         When vRtrInetAggrSummaryOnly has value of 'true(1)', only the
         aggregate is advertised, the more specific routes that make up the
         aggregate are not.

         When vRtrInetAggrSummaryOnly has value of 'false(2)', both the
         aggregate and more specific components are advertised."
    DEFVAL      { false }
    ::= { vRtrInetInstAggrEntry 6 }

vRtrInetAggrASSet                OBJECT-TYPE
    SYNTAX      TruthValue
    MAX-ACCESS  read-create
    STATUS      current
    DESCRIPTION
        "The value of vRtrInetAggrASSet specifies whether the aggregate route
         has AS-SET.

         When vRtrInetAggrASSet has value of 'true(1)', the AS-Path of the
         resulting aggregate will contain an AS-SET containing all AS numbers
         from the contributing routes.

         When vRtrInetAggrASSet has value of 'false(2)', the AS-Path will
         contain no AS-SET and will be originated by the ESR."
    DEFVAL      { false }
    ::= { vRtrInetInstAggrEntry 7 }

vRtrInetAggrAggregatorAS         OBJECT-TYPE
    SYNTAX      TmnxBgpAutonomousSystem
    MAX-ACCESS  read-create
    STATUS      obsolete
    DESCRIPTION
        "The value of vRtrInetAggrAggregatorAS specifies the aggregator's ASN.

         When vRtrInetAggrAggregatorAS is set to non zero, and
         vRtrInetAggrAggregatorIPAddr is set to non-zero, the supplied ASN and
         IP address will be used for the aggregator path attributes.

         When vRtrInetAggrAggregatorAS is not set, the aggregate routes ASN &
         Router-ID will be used for the aggregator path attributes.

         This object was obsoleted in release 7.0.  It is replaced with the
         4-byte AS number defined by vRtrInetAggrAggregatorAS4Byte."
    DEFVAL      { 0 }
    ::= { vRtrInetInstAggrEntry 8 }

vRtrInetAggrAggregatorIPAddr     OBJECT-TYPE
    SYNTAX      IpAddress
    MAX-ACCESS  read-create
    STATUS      current
    DESCRIPTION
        "The value of vRtrInetAggrAggregatorIPAddr specifies the aggregator's
         IP address.

         When vRtrInetAggrAggregatorAS is set to non zero, and
         vRtrInetAggrAggregatorIPAddr is set to non-zero, the supplied ASN and
         IP address will be used for the aggregator path attributes.

         When vRtrInetAggrAggregatorIPAddr is not set, the aggregate routes ASN
         & Router-ID will be used for the aggregator path attributes."
    DEFVAL      { '00000000'H }
    ::= { vRtrInetInstAggrEntry 9 }

vRtrInetAggrOperState            OBJECT-TYPE
    SYNTAX      TmnxOperState
    MAX-ACCESS  read-only
    STATUS      current
    DESCRIPTION
        "The value of vRtrInetAggrOperState indicates the current operational
         status of the aggregation entry."
    ::= { vRtrInetInstAggrEntry 10 }

vRtrInetAggrAggregatorAS4Byte    OBJECT-TYPE
    SYNTAX      InetAutonomousSystemNumber
    MAX-ACCESS  read-create
    STATUS      current
    DESCRIPTION
        "The value of vRtrInetAggrAggregatorAS4Byte specifies the aggregator's
         Autonomous System Number (ASN).

         When vRtrInetAggrAggregatorAS4Byte is set to non zero, and
         vRtrInetAggrAggregatorIPAddr is set to non-zero, the supplied ASN and
         IP address will be used for the aggregator path attributes.

         When vRtrInetAggrAggregatorAS4Byte is not set, the aggregate routes
         ASN and Router-ID will be used for the aggregator path attributes."
    DEFVAL      { 0 }
    ::= { vRtrInetInstAggrEntry 11 }

vRtrInetAggrNextHopType          OBJECT-TYPE
    SYNTAX      INTEGER {
        none      (0),
        blackHole (1),
        indirect  (2)
    }
    MAX-ACCESS  read-create
    STATUS      current
    DESCRIPTION
        "The value of vRtrInetAggrNextHopType specifies whether the aggregate
         route will be installed in the Forwarding Information Base (FIB) when
         the route is activated.

         When vRtrInetAggrNextHopType has a value of 'none', the aggregate
         route will not be installed in the FIB.

         When vRtrInetAggrNextHopType has a value of 'blackHole' and the
         aggregate route is active, it will be installed in the FIB with a
         black-hole next-hop and packets matching this route will be discarded.

         When vRtrInetAggrNextHopType has a value of 'indirect' and the
         aggregate route is active, it will be installed in the FIB with a
         indirect next-hop and packets matching this route will be forwarded to
         the resolved direct next-hop."
    DEFVAL      { none }
    ::= { vRtrInetInstAggrEntry 12 }

vRtrInetAggrCommunityVal         OBJECT-TYPE
    SYNTAX      DisplayString (SIZE (0..72))
    MAX-ACCESS  read-create
    STATUS      current
    DESCRIPTION
        "The value of vRtrInetAggrCommunityVal specifies the community name
         that is used to add to the aggregate route. This value could then be
         used in route policies to control the distribution of the route into
         other protocols and by BGP to control the distribution of the route
         into other routers. A value of ''H indicates that the
         vRtrInetAggrCommunityVal has not been set."
    DEFVAL      { ''H }
    ::= { vRtrInetInstAggrEntry 13 }

vRtrInetAggrIndirectAddrType     OBJECT-TYPE
    SYNTAX      InetAddressType
    MAX-ACCESS  read-create
    STATUS      current
    DESCRIPTION
        "The value of vRtrInetAggrIndirectAddrType specifies the address type
         of the indirect next-hop address."
    DEFVAL      { unknown }
    ::= { vRtrInetInstAggrEntry 14 }

vRtrInetAggrIndirectAddr         OBJECT-TYPE
    SYNTAX      InetAddress (SIZE (0|4|16))
    MAX-ACCESS  read-create
    STATUS      current
    DESCRIPTION
        "The value of vRtrInetAggrIndirectAddr specifies the address of the
         indirect next-hop address.

         An 'inconsistentValue' error will be returned if an attempt is made to
         set vRtrInetAggrIndirectAddr to ipv4 address when the value of
         vRtrInetAggrIpPrefix is not set to an ipv4 address or if an attempt is
         made to set vRtrInetAggrIndirectAddr to ipv6 address when the value of
         vRtrInetAggrIpPrefix is not set to an ipv6 address."
    DEFVAL      { ''H }
    ::= { vRtrInetInstAggrEntry 15 }

vRtrInetAggrGenerateIcmp         OBJECT-TYPE
    SYNTAX      TruthValue
    MAX-ACCESS  read-create
    STATUS      current
    DESCRIPTION
        "The value of vRtrInetAggrGenerateIcmp specifies if we should generate
         and send an ICMP message when a packet matches an aggregate route with
         a black-hole next-hop.

         An 'inconsistentValue' error will be returned if an attempt is made to
         set vRtrInetAggrGenerateIcmp when the value of vRtrInetAggrNextHopType
         is not set to 'blackHole(1)'."
    DEFVAL      { false }
    ::= { vRtrInetInstAggrEntry 16 }

vRtrInetAggrDescription          OBJECT-TYPE
    SYNTAX      TItemDescription
    MAX-ACCESS  read-create
    STATUS      current
    DESCRIPTION
        "The value of vRtrInetAggrDescription is a user provided
         description string for aggregate route.  It can consist of any
         printable, seven-bit ASCII characters up to 80 characters in
         length."
    DEFVAL      { ''H }
    ::= { vRtrInetInstAggrEntry 17 }

vRtrInetAggrCommunityVal2        OBJECT-TYPE
    SYNTAX      DisplayString (SIZE (0..72))
    MAX-ACCESS  read-create
    STATUS      current
    DESCRIPTION
        "The value of vRtrInetAggrCommunityVal2 specifies the 2nd community
         name that is used to add to the aggregate route. This value could then
         be used in route policies to control the distribution of the route
         into other protocols and by BGP to control the distribution of the
         route into other routers. A value of ''H indicates that the
         vRtrInetAggrCommunityVal2 has not been set.

         It is required to configure vRtrInetAggrCommunityVal before
         configuring vRtrInetAggrCommunityVal2."
    DEFVAL      { ''H }
    ::= { vRtrInetInstAggrEntry 18 }

vRtrInetAggrCommunityVal3        OBJECT-TYPE
    SYNTAX      DisplayString (SIZE (0..72))
    MAX-ACCESS  read-create
    STATUS      current
    DESCRIPTION
        "The value of vRtrInetAggrCommunityVal3 specifies the 3rd community
         name that is used to add to the aggregate route. This value could then
         be used in route policies to control the distribution of the route
         into other protocols and by BGP to control the distribution of the
         route into other routers. A value of ''H indicates that the
         vRtrInetAggrCommunityVal3 has not been set.

         It is required to configure vRtrInetAggrCommunityVal2 before
         configuring vRtrInetAggrCommunityVal3."
    DEFVAL      { ''H }
    ::= { vRtrInetInstAggrEntry 19 }

vRtrInetAggrCommunityVal4        OBJECT-TYPE
    SYNTAX      DisplayString (SIZE (0..72))
    MAX-ACCESS  read-create
    STATUS      current
    DESCRIPTION
        "The value of vRtrInetAggrCommunityVal4 specifies the 4th community
         name that is used to add to the aggregate route. This value could then
         be used in route policies to control the distribution of the route
         into other protocols and by BGP to control the distribution of the
         route into other routers. A value of ''H indicates that the
         vRtrInetAggrCommunityVal4 has not been set.

         It is required to configure vRtrInetAggrCommunityVal3 before
         configuring vRtrInetAggrCommunityVal4."
    DEFVAL      { ''H }
    ::= { vRtrInetInstAggrEntry 20 }

vRtrInetAggrCommunityVal5        OBJECT-TYPE
    SYNTAX      DisplayString (SIZE (0..72))
    MAX-ACCESS  read-create
    STATUS      current
    DESCRIPTION
        "The value of vRtrInetAggrCommunityVal5 specifies the 5th community
         name that is used to add to the aggregate route. This value could then
         be used in route policies to control the distribution of the route
         into other protocols and by BGP to control the distribution of the
         route into other routers. A value of ''H indicates that the
         vRtrInetAggrCommunityVal5 has not been set.

         It is required to configure vRtrInetAggrCommunityVal4 before
         configuring vRtrInetAggrCommunityVal5."
    DEFVAL      { ''H }
    ::= { vRtrInetInstAggrEntry 21 }

vRtrInetAggrCommunityVal6        OBJECT-TYPE
    SYNTAX      DisplayString (SIZE (0..72))
    MAX-ACCESS  read-create
    STATUS      current
    DESCRIPTION
        "The value of vRtrInetAggrCommunityVal6 specifies the 6th community
         name that is used to add to the aggregate route. This value could then
         be used in route policies to control the distribution of the route
         into other protocols and by BGP to control the distribution of the
         route into other routers. A value of ''H indicates that the
         vRtrInetAggrCommunityVal6 has not been set.

         It is required to configure vRtrInetAggrCommunityVal5 before
         configuring vRtrInetAggrCommunityVal6."
    DEFVAL      { ''H }
    ::= { vRtrInetInstAggrEntry 22 }

vRtrInetAggrCommunityVal7        OBJECT-TYPE
    SYNTAX      DisplayString (SIZE (0..72))
    MAX-ACCESS  read-create
    STATUS      current
    DESCRIPTION
        "The value of vRtrInetAggrCommunityVal7 specifies the 7th community
         name that is used to add to the aggregate route. This value could then
         be used in route policies to control the distribution of the route
         into other protocols and by BGP to control the distribution of the
         route into other routers. A value of ''H indicates that the
         vRtrInetAggrCommunityVal7 has not been set.

         It is required to configure vRtrInetAggrCommunityVal6 before
         configuring vRtrInetAggrCommunityVal7."
    DEFVAL      { ''H }
    ::= { vRtrInetInstAggrEntry 23 }

vRtrInetAggrCommunityVal8        OBJECT-TYPE
    SYNTAX      DisplayString (SIZE (0..72))
    MAX-ACCESS  read-create
    STATUS      current
    DESCRIPTION
        "The value of vRtrInetAggrCommunityVal8 specifies the 8th community
         name that is used to add to the aggregate route. This value could then
         be used in route policies to control the distribution of the route
         into other protocols and by BGP to control the distribution of the
         route into other routers. A value of ''H indicates that the
         vRtrInetAggrCommunityVal8 has not been set.

         It is required to configure vRtrInetAggrCommunityVal7 before
         configuring vRtrInetAggrCommunityVal8."
    DEFVAL      { ''H }
    ::= { vRtrInetInstAggrEntry 24 }

vRtrInetAggrCommunityVal9        OBJECT-TYPE
    SYNTAX      DisplayString (SIZE (0..72))
    MAX-ACCESS  read-create
    STATUS      current
    DESCRIPTION
        "The value of vRtrInetAggrCommunityVal9 specifies the 9th community
         name that is used to add to the aggregate route. This value could then
         be used in route policies to control the distribution of the route
         into other protocols and by BGP to control the distribution of the
         route into other routers. A value of ''H indicates that the
         vRtrInetAggrCommunityVal9 has not been set.

         It is required to configure vRtrInetAggrCommunityVal8 before
         configuring vRtrInetAggrCommunityVal9."
    DEFVAL      { ''H }
    ::= { vRtrInetInstAggrEntry 25 }

vRtrInetAggrCommunityVal10       OBJECT-TYPE
    SYNTAX      DisplayString (SIZE (0..72))
    MAX-ACCESS  read-create
    STATUS      current
    DESCRIPTION
        "The value of vRtrInetAggrCommunityVal10 specifies the 10th community
         name that is used to add to the aggregate route. This value could then
         be used in route policies to control the distribution of the route
         into other protocols and by BGP to control the distribution of the
         route into other routers. A value of ''H indicates that the
         vRtrInetAggrCommunityVal10 has not been set.

         It is required to configure vRtrInetAggrCommunityVal9 before
         configuring vRtrInetAggrCommunityVal10."
    DEFVAL      { ''H }
    ::= { vRtrInetInstAggrEntry 26 }

vRtrInetAggrCommunityVal11       OBJECT-TYPE
    SYNTAX      DisplayString (SIZE (0..72))
    MAX-ACCESS  read-create
    STATUS      current
    DESCRIPTION
        "The value of vRtrInetAggrCommunityVal11 specifies the 11th community
         name that is used to add to the aggregate route. This value could then
         be used in route policies to control the distribution of the route
         into other protocols and by BGP to control the distribution of the
         route into other routers. A value of ''H indicates that the
         vRtrInetAggrCommunityVal11 has not been set.

         It is required to configure vRtrInetAggrCommunityVal10 before
         configuring vRtrInetAggrCommunityVal11."
    DEFVAL      { ''H }
    ::= { vRtrInetInstAggrEntry 27 }

vRtrInetAggrCommunityVal12       OBJECT-TYPE
    SYNTAX      DisplayString (SIZE (0..72))
    MAX-ACCESS  read-create
    STATUS      current
    DESCRIPTION
        "The value of vRtrInetAggrCommunityVal12 specifies the 12th community
         name that is used to add to the aggregate route. This value could then
         be used in route policies to control the distribution of the route
         into other protocols and by BGP to control the distribution of the
         route into other routers. A value of ''H indicates that the
         vRtrInetAggrCommunityVal12 has not been set.

         It is required to configure vRtrInetAggrCommunityVal11 before
         configuring vRtrInetAggrCommunityVal12."
    DEFVAL      { ''H }
    ::= { vRtrInetInstAggrEntry 28 }

vRtrInetAggrFlags                OBJECT-TYPE
    SYNTAX      BITS {
        vRtrInetAggrValidLocalPref (0)
    }
    MAX-ACCESS  read-create
    STATUS      current
    DESCRIPTION
        "This object is a bit-mask, with the following bits:

         If the 'vRtrInetAggrValidLocalPref' bit is set, the value in the
         'vRtrInetAggrLocalPreference' object is valid to use."
    DEFVAL      { {} }
    ::= { vRtrInetInstAggrEntry 29 }

vRtrInetAggrLocalPreference      OBJECT-TYPE
    SYNTAX      Unsigned32 (0..4294967295)
    MAX-ACCESS  read-create
    STATUS      current
    DESCRIPTION
        "The value of vRtrInetAggrLocalPreference specifies the local
         preference value for this aggregate route.

         This value is valid to use only if the 'vRtrInetAggrValidLocalPref'
         bit is set in the 'vRtrInetAggrFlags' object."
    DEFVAL      { 0 }
    ::= { vRtrInetInstAggrEntry 30 }

vRtrInetAggrDiscardComponent     OBJECT-TYPE
    SYNTAX      TruthValue
    MAX-ACCESS  read-create
    STATUS      current
    DESCRIPTION
        "When this optional flag is configured, in both the VPRN and GRT instance,
         the aggregate is advertised with only the configured BGP community set.
         None of the communities from the component routes activating the aggregate are included.
         If no communities are configured as part of the aggregate commands then
         no new communities are added to the aggregate aggregate."
    DEFVAL      { false }
    ::= { vRtrInetInstAggrEntry 31 }

vRtrInetAggrTunnelGroup          OBJECT-TYPE
    SYNTAX      TmnxTunnelGroupIdOrZero
    MAX-ACCESS  read-create
    STATUS      current
    DESCRIPTION
        "The value of vRtrInetAggrTunnelGroup adds mc-ipsec state of specified
         tunnel-group to aggregate route."
    DEFVAL      { 0 }
    ::= { vRtrInetInstAggrEntry 32 }

vRtrInetAggrPolicy               OBJECT-TYPE
    SYNTAX      TLNamedItemOrEmpty
    MAX-ACCESS  read-create
    STATUS      current
    DESCRIPTION
        "When configured the policy to which this refers will determine which
         routes can contribute to the aggregate. This cannot be configured
         together with as-set or indirect nexthops."
    DEFVAL      { "" }
    ::= { vRtrInetInstAggrEntry 33 }

vRtrInetSvcIpRangeTable          OBJECT-TYPE
    SYNTAX      SEQUENCE OF VRtrInetSvcIpRangeEntry
    MAX-ACCESS  not-accessible
    STATUS      obsolete
    DESCRIPTION
        "The vRtrInetSvcIpRangeTable has an entry for each IP address
         range configured for a virtual interface in a virtual router
         in the system.  An interface on the virtual router may have
         more than one Service IP address range assigned to it.

         This table is obsoleted in release 22.2 and later."
    ::= { tmnxVRtrObjs 28 }

vRtrInetSvcIpRangeEntry          OBJECT-TYPE
    SYNTAX      VRtrInetSvcIpRangeEntry
    MAX-ACCESS  not-accessible
    STATUS      obsolete
    DESCRIPTION
        "Each row entry represents an IP address range assigned a virtual
         router service interface. Setting RowStatus to 'active' requires
         values for all column variables to have been assigned."
    INDEX       {
        vRtrID,
        vRtrInetSvcIpRangeAddrType,
        vRtrInetSvcIpRangeAddr,
        vRtrInetSvcIpRangePfxLen
    }
    ::= { vRtrInetSvcIpRangeTable 1 }

VRtrInetSvcIpRangeEntry          ::= SEQUENCE
{
    vRtrInetSvcIpRangeAddrType       InetAddressType,
    vRtrInetSvcIpRangeAddr           InetAddress,
    vRtrInetSvcIpRangePfxLen         InetAddressPrefixLength,
    vRtrInetSvcIpRangeRowStatus      RowStatus,
    vRtrInetSvcIpRangeExclusive      TruthValue
}

vRtrInetSvcIpRangeAddrType       OBJECT-TYPE
    SYNTAX      InetAddressType
    MAX-ACCESS  not-accessible
    STATUS      current
    DESCRIPTION
        "The value of vRtrInetSvcIpRangeAddrType indicates the IP address type
         of vRtrInetSvcIpRangeAddr."
    ::= { vRtrInetSvcIpRangeEntry 1 }

vRtrInetSvcIpRangeAddr           OBJECT-TYPE
    SYNTAX      InetAddress
    MAX-ACCESS  not-accessible
    STATUS      current
    DESCRIPTION
        "The value of vRtrInetSvcIpRangeAddr indicates the IP address service
         range assigned to a router's service interface. The address type of
         vRtrInetSvcIpRangeAddr is indicated by vRtrInetSvcIpRangeAddrType."
    ::= { vRtrInetSvcIpRangeEntry 2 }

vRtrInetSvcIpRangePfxLen         OBJECT-TYPE
    SYNTAX      InetAddressPrefixLength
    MAX-ACCESS  not-accessible
    STATUS      current
    DESCRIPTION
        "The value of vRtrInetSvcIpRangePfxLen specifies the prefix length to
         be used with vRtrInetSvcIpRangeAddr for determining the IP address
         range."
    ::= { vRtrInetSvcIpRangeEntry 3 }

vRtrInetSvcIpRangeRowStatus      OBJECT-TYPE
    SYNTAX      RowStatus
    MAX-ACCESS  read-create
    STATUS      obsolete
    DESCRIPTION
        "The value of vRtrInetSvcIpRangeRowStatus is used for creation and
         deletion of IP service prefix ranges."
    ::= { vRtrInetSvcIpRangeEntry 4 }

vRtrInetSvcIpRangeExclusive      OBJECT-TYPE
    SYNTAX      TruthValue
    MAX-ACCESS  read-create
    STATUS      obsolete
    DESCRIPTION
        "The value of vRtrInetSvcIpRangeExclusive specifies how the set
         of addresses specified by this entry are interpreted. When the
         value is 'true', they are reserved for services only and cannot be
         assigned to network ports.  When the value is 'false',
         it could be used for services as well as network ports."
    DEFVAL      { false }
    ::= { vRtrInetSvcIpRangeEntry 5 }

vRtrIpNetToPhysicalTable         OBJECT-TYPE
    SYNTAX      SEQUENCE OF VRtrIpNetToPhysicalEntry
    MAX-ACCESS  not-accessible
    STATUS      current
    DESCRIPTION
        "The vRtrIpNetToPhysicalTable provides an extension of the
         ipNetToPhysicalTable in the IP-MIB."
    ::= { tmnxVRtrObjs 29 }

vRtrIpNetToPhysicalEntry         OBJECT-TYPE
    SYNTAX      VRtrIpNetToPhysicalEntry
    MAX-ACCESS  not-accessible
    STATUS      current
    DESCRIPTION
        "Each row entry in the vRtrIpNetToPhysicalTable represents additional
         columns for attributes specific to the Nokia SROS series
         implementation for the vRtrIpNetToPhysicalTable."
    AUGMENTS    { ipNetToPhysicalEntry }
    ::= { vRtrIpNetToPhysicalTable 1 }

VRtrIpNetToPhysicalEntry         ::= SEQUENCE
{
    vRtrIpNetToPhysicalTimer         Unsigned32,
    vRtrIpNetToPhysicalOperState     TmnxOperState,
    vRtrIpNetToPhysicalIsRouter      TruthValue,
    vRtrIpNetToPhysicalMTU           Unsigned32,
    vRtrIpNetToPhysicalPort          TmnxPortID,
    vRtrIpNetToPhysicalEncap         TmnxEncapVal,
    vRtrIpNetToPhysicalSecureNd      INTEGER
}

vRtrIpNetToPhysicalTimer         OBJECT-TYPE
    SYNTAX      Unsigned32 (0..65535)
    UNITS       "seconds"
    MAX-ACCESS  read-only
    STATUS      current
    DESCRIPTION
        "The value of vRtrIpNetToPhysicalTimer indicates how much longer an ARP
         entry associated with an vRtrIpNetToPhysicalTable entry remains in the
         ARP cache. It is initially set to vRtrIfArpTimeout. When
         vRtrIpNetToPhysicalTimer has a value of zero, '0', the entry is
         cleared from the cache."
    ::= { vRtrIpNetToPhysicalEntry 1 }

vRtrIpNetToPhysicalOperState     OBJECT-TYPE
    SYNTAX      TmnxOperState
    MAX-ACCESS  read-only
    STATUS      current
    DESCRIPTION
        "The value of vRtrIpNetToPhysicalOperState indicates if the ARP entry
         is being used actively in the ARP Table. When ipNetToPhysicalType has
         a value 'dynamic', vRtrIpNetToPhysicalOperState will never have a
         value of 'outOfService'."
    ::= { vRtrIpNetToPhysicalEntry 2 }

vRtrIpNetToPhysicalIsRouter      OBJECT-TYPE
    SYNTAX      TruthValue
    MAX-ACCESS  read-only
    STATUS      current
    DESCRIPTION
        "The value of vRtrIpNetToPhysicalIsRouter indicates whether this
         ipNetToPhysicalEntry is a router."
    ::= { vRtrIpNetToPhysicalEntry 3 }

vRtrIpNetToPhysicalMTU           OBJECT-TYPE
    SYNTAX      Unsigned32
    MAX-ACCESS  read-only
    STATUS      current
    DESCRIPTION
        "The value of vRtrIpNetToPhysicalMTU indicates the MTU of the link
         attached to this ipNetToPhysicalEntry."
    ::= { vRtrIpNetToPhysicalEntry 4 }

vRtrIpNetToPhysicalPort          OBJECT-TYPE
    SYNTAX      TmnxPortID
    MAX-ACCESS  read-only
    STATUS      current
    DESCRIPTION
        "The value of vRtrIpNetToPhysicalPort indicates the ID of the port on
         which this entry was learned."
    ::= { vRtrIpNetToPhysicalEntry 5 }

vRtrIpNetToPhysicalEncap         OBJECT-TYPE
    SYNTAX      TmnxEncapVal
    MAX-ACCESS  read-only
    STATUS      current
    DESCRIPTION
        "The value of vRtrIpNetToPhysicalEncap indicates the encap value of the
         SAP this entry was learned on. If this entry was learned on a network
         port or null-encap SAP, the value of this object will be zero."
    ::= { vRtrIpNetToPhysicalEntry 6 }

vRtrIpNetToPhysicalSecureNd      OBJECT-TYPE
    SYNTAX      INTEGER {
        notApplicable (0),
        secure        (1),
        unsecure      (2)
    }
    MAX-ACCESS  read-only
    STATUS      current
    DESCRIPTION
        "The value of vRtrIpNetToPhysicalSecureNd indicates whether the
         physical address is received via Secured Neighbor Discovery messages."
    ::= { vRtrIpNetToPhysicalEntry 7 }

vRtrInetCidrRouteTable           OBJECT-TYPE
    SYNTAX      SEQUENCE OF VRtrInetCidrRouteEntry
    MAX-ACCESS  not-accessible
    STATUS      current
    DESCRIPTION
        "The vRtrInetCidrRouteTable provides an extension of the
         inetCidrRouteTable in the IP-FORWARD-MIB."
    ::= { tmnxVRtrObjs 30 }

vRtrInetCidrRouteEntry           OBJECT-TYPE
    SYNTAX      VRtrInetCidrRouteEntry
    MAX-ACCESS  not-accessible
    STATUS      current
    DESCRIPTION
        "Each row entry in the vRtrInetCidrRouteTable represents additional
         columns for attributes specific to the Nokia SROS series
         implementation for the IP route table."
    AUGMENTS    { inetCidrRouteEntry }
    ::= { vRtrInetCidrRouteTable 1 }

VRtrInetCidrRouteEntry           ::= SEQUENCE
{
    vRtrInetCidrRouteLastEnabledTime TimeStamp,
    vRtrInetCidrRoutePreference      Unsigned32,
    vRtrInetCidrRouteMetric          Unsigned32,
    vRtrInetCidrRouteIfVRtrId        TmnxVRtrIDOrZero,
    vRtrInetCidrRouteTunnEndpntInfo  OCTET STRING,
    vRtrInetCidrProtocolInstance     Unsigned32,
    vRtrInetCidrRouteNextHopType     TmnxInetCidrNextHopType,
    vRtrInetCidrRouteNextHopOwner    TmnxInetCidrNextHopOwner,
    vRtrInetCidrRouteNHOwnerAuxInfo  Unsigned32,
    vRtrInetCidrRouteNHFC            TFCNameOrEmpty,
    vRtrInetCidrRouteNHPriority      TPriorityOrUndefined,
    vRtrInetCidrRouteBkupFlags       INTEGER,
    vRtrInetCidrRouteBkupNextHopType InetAddressType,
    vRtrInetCidrRouteBkupNextHop     InetAddress,
    vRtrInetCidrRouteBkupMetric      Unsigned32,
    vRtrInetCidrRouteNextHopRepCount Unsigned32,
    vRtrInetCidrRouteBkupNHType      TmnxInetCidrNextHopType,
    vRtrInetCidrRouteBkupNHOwner     TmnxInetCidrNextHopOwner,
    vRtrInetCidrRouteBkupNHOwnAxInfo Unsigned32,
    vRtrInetCidrRouteSrcClassIndex   ClassIndexOrNone,
    vRtrInetCidrRouteDstClassIndex   ClassIndexOrNone,
    vRtrInetCidrRouteOperFlags       TmnxRouteOperFlags,
    vRtrInetCidrRouteNextHopWeight   Unsigned32,
    vRtrInetCidrRouteNextHopOwnInst  Unsigned32,
    vRtrInetCidrRouteBkupNHOwnInst   Unsigned32,
    vRtrInetCidrRouteNHIsFec         TruthValue,
    vRtrInetCidrRouteNHFecPfxLen     InetAddressPrefixLength,
    vRtrInetCidrRouteEgrVni          Unsigned32
}

vRtrInetCidrRouteLastEnabledTime OBJECT-TYPE
    SYNTAX      TimeStamp
    MAX-ACCESS  read-only
    STATUS      current
    DESCRIPTION
        "The vRtrInetCidrRouteLastEnabledTime variable indicates the sysUpTime
         value when ipCidrRouteStatus was last set to active (1) to allow IP
         forwarding on this route entry."
    ::= { vRtrInetCidrRouteEntry 1 }

vRtrInetCidrRoutePreference      OBJECT-TYPE
    SYNTAX      Unsigned32 (0..255)
    MAX-ACCESS  read-only
    STATUS      current
    DESCRIPTION
        "The value of vRtrInetCidrRoutePreference indicates the priority of
         this static route versus the routes from different sources such as BGP
         or OSPF etc, when ipCidrRouteProto has a value of 'netmgmt' to
         indicate that this entry is a static route.

         Different protocols should not be configured with the same preference,
         if this occurs the tiebreaker is determined per the default preference
         value as defined in the table below.

         If multiple routes are learned with an identical preference using the
         same protocol, the lowest cost is used. If multiple routes are learned
         with an identical preference using the same protocol and the costs
         (metrics) are equal, then the decision as to what route to use is
         determined by the configuration of the ecmp command.

         Default preferences:

         Route Type             Preference      Configurable
         ----------             ----------      ------------
         Direct attached                 0                no
         Static route                    5               yes
         MPLS (post FCS)                 7
         OSPF Internal routes           10                no
         OSPF External                 150               yes
         BGP                           170               yes"
    DEFVAL      { 5 }
    ::= { vRtrInetCidrRouteEntry 2 }

vRtrInetCidrRouteMetric          OBJECT-TYPE
    SYNTAX      Unsigned32
    MAX-ACCESS  read-only
    STATUS      current
    DESCRIPTION
        "The value of vRtrInetCidrRouteMetric indicates the primary routing
         metric  for this route. The semantics of this metric are determined
         by the routing-protocol specified in the route's ipCidrRouteProto
         value."
    ::= { vRtrInetCidrRouteEntry 3 }

vRtrInetCidrRouteIfVRtrId        OBJECT-TYPE
    SYNTAX      TmnxVRtrIDOrZero
    MAX-ACCESS  read-only
    STATUS      current
    DESCRIPTION
        "The value of vRtrInetCidrRouteIfVRtrId indicates the virtual router
         instance of the egress interface defined by inetCidrRouteIfIndex. This
         object is valid only for subscriber management routes. For all other
         route types, this object will have a value of zero."
    ::= { vRtrInetCidrRouteEntry 4 }

vRtrInetCidrRouteTunnEndpntInfo  OBJECT-TYPE
    SYNTAX      OCTET STRING (SIZE (0|12..136))
    MAX-ACCESS  read-only
    STATUS      current
    DESCRIPTION
        "The value of vRtrInetCidrRouteTunnEndpntInfo indicates tunnel endpoint
         information.  The first 4 bytes indicate number of tunnel end-points,
         the next 4 bytes indicate IGP cost to reach tunnel end-points and the
         next 64 bytes indicate up to 16 4-byte IPv4 addresses (the number of
         end-points represented by bytes 1-4 indicate how many addresses are
         present).  When no tunnel endpoints exist, the size of this object
         will be 0. When at least one tunnel endpoint exists, there would be
         12 bytes to represent the information related to one tunnel endpoint."
    ::= { vRtrInetCidrRouteEntry 5 }

vRtrInetCidrProtocolInstance     OBJECT-TYPE
    SYNTAX      Unsigned32 (0..31)
    MAX-ACCESS  read-only
    STATUS      current
    DESCRIPTION
        "The value of vRtrInetCidrProtocolInstance indicates the instance of
         the protocol through which this route was learned.

         A single instance protocol will always return an instance value 0."
    ::= { vRtrInetCidrRouteEntry 6 }

vRtrInetCidrRouteNextHopType     OBJECT-TYPE
    SYNTAX      TmnxInetCidrNextHopType
    MAX-ACCESS  read-only
    STATUS      current
    DESCRIPTION
        "The value of vRtrInetCidrRouteNextHopType indicates the type of next
         hop for this route."
    ::= { vRtrInetCidrRouteEntry 7 }

vRtrInetCidrRouteNextHopOwner    OBJECT-TYPE
    SYNTAX      TmnxInetCidrNextHopOwner
    MAX-ACCESS  read-only
    STATUS      current
    DESCRIPTION
        "The value of vRtrInetCidrRouteNextHopOwner indicates the owner of next
         hop for this route."
    ::= { vRtrInetCidrRouteEntry 8 }

vRtrInetCidrRouteNHOwnerAuxInfo  OBJECT-TYPE
    SYNTAX      Unsigned32
    MAX-ACCESS  read-only
    STATUS      current
    DESCRIPTION
        "The value of vRtrInetCidrRouteNHOwnerAuxInfo indicates the auxiliary
         information for next hop owner as indicated by
         vRtrInetCidrRouteNextHopOwner.

         The value of vRtrInetCidrRouteNHOwnerAuxInfo indicates the number of
         tunnel ids existing for this next hop type and owner."
    ::= { vRtrInetCidrRouteEntry 9 }

vRtrInetCidrRouteNHFC            OBJECT-TYPE
    SYNTAX      TFCNameOrEmpty
    MAX-ACCESS  read-only
    STATUS      current
    DESCRIPTION
        "The value of vRtrInetCidrRouteNHFC indicates the forwarding class or
         the sub forwarding class associated with the CIDR route.

         Specification of a sub forwarding class is also allowed. The format of
         a sub forwarding class is the concatenation of the base forwarding
         class and a sub class identifier in the form
         base-fc-name[.sub-fc-name]."
    ::= { vRtrInetCidrRouteEntry 10 }

vRtrInetCidrRouteNHPriority      OBJECT-TYPE
    SYNTAX      TPriorityOrUndefined
    MAX-ACCESS  read-only
    STATUS      current
    DESCRIPTION
        "The value of vRtrInetCidrRouteNHPriority indicates the priority to be
         assigned to the CIDR routes."
    ::= { vRtrInetCidrRouteEntry 11 }

vRtrInetCidrRouteBkupFlags       OBJECT-TYPE
    SYNTAX      INTEGER {
        none          (0),
        hasLfa        (1),
        hasBackup     (2),
        isBackup      (3),
        isBgpInactive (4)
    }
    MAX-ACCESS  read-only
    STATUS      current
    DESCRIPTION
        "The value of vRtrInetCidrRouteBkupFlags indicates the presence or
         absence of LFA next-hops and backup routes.

         'none' indicates that no next-hop is present. 'hasLfa' indicates that
         an LFA next-hop is present in addition to the regular next-hop.
         'hasBackup' indicates that this route has a backup route. 'isBackup'
         indicates that this route is a backup route to another route with the
         same prefix. 'isBgpInactive' indicates that this route is an inactive
         best-external route exported from BGP."
    ::= { vRtrInetCidrRouteEntry 12 }

vRtrInetCidrRouteBkupNextHopType OBJECT-TYPE
    SYNTAX      InetAddressType
    MAX-ACCESS  read-only
    STATUS      current
    DESCRIPTION
        "The value of vRtrInetCidrRouteBkupNextHopType indicates the IP address
         type of vRtrInetCidrRouteBkupNextHop. The value of
         vRtrInetCidrRouteBkupNextHopType is only valid when
         vRtrInetCidrRouteBkupFlags has a value of 'hasLfa'."
    ::= { vRtrInetCidrRouteEntry 13 }

vRtrInetCidrRouteBkupNextHop     OBJECT-TYPE
    SYNTAX      InetAddress
    MAX-ACCESS  read-only
    STATUS      current
    DESCRIPTION
        "The value of vRtrInetCidrRouteBkupNextHop indicates the IP address of
         a backup next-hop. The value of vRtrInetCidrRouteBkupNextHop is only
         valid when vRtrInetCidrRouteBkupFlags has a value of 'hasLfa'."
    ::= { vRtrInetCidrRouteEntry 14 }

vRtrInetCidrRouteBkupMetric      OBJECT-TYPE
    SYNTAX      Unsigned32
    MAX-ACCESS  read-only
    STATUS      current
    DESCRIPTION
        "The value of vRtrInetCidrRouteBkupMetric indicates the routing
         metric  for a backup route. The semantics of this metric are determined
         by the routing-protocol specified in the route's ipCidrRouteProto
         value. The value of vRtrInetCidrRouteBkupMetric is only
         valid when vRtrInetCidrRouteBkupFlags has a value of 'hasLfa'."
    ::= { vRtrInetCidrRouteEntry 15 }

vRtrInetCidrRouteNextHopRepCount OBJECT-TYPE
    SYNTAX      Unsigned32
    MAX-ACCESS  read-only
    STATUS      current
    DESCRIPTION
        "The value of vRtrInetCidrRouteNextHopRepCount indicates the number of
         times the next-hop repeats for a particular route."
    ::= { vRtrInetCidrRouteEntry 16 }

vRtrInetCidrRouteBkupNHType      OBJECT-TYPE
    SYNTAX      TmnxInetCidrNextHopType
    MAX-ACCESS  read-only
    STATUS      current
    DESCRIPTION
        "The value of vRtrInetCidrRouteBkupNHType indicates the type of next
         hop for this backup route."
    ::= { vRtrInetCidrRouteEntry 17 }

vRtrInetCidrRouteBkupNHOwner     OBJECT-TYPE
    SYNTAX      TmnxInetCidrNextHopOwner
    MAX-ACCESS  read-only
    STATUS      current
    DESCRIPTION
        "The value of vRtrInetCidrRouteBkupNHOwner indicates the owner of next
         hop for this backup route."
    ::= { vRtrInetCidrRouteEntry 18 }

vRtrInetCidrRouteBkupNHOwnAxInfo OBJECT-TYPE
    SYNTAX      Unsigned32
    MAX-ACCESS  read-only
    STATUS      current
    DESCRIPTION
        "The value of vRtrInetCidrRouteBkupNHOwnAxInfo indicates the auxiliary
         information for next hop owner as indicated by
         vRtrInetCidrRouteBkupNHOwner.

         The value of vRtrInetCidrRouteBkupNHOwnAxInfo indicates the tunnel id
         existing for this backup next hop type and owner."
    ::= { vRtrInetCidrRouteEntry 19 }

vRtrInetCidrRouteSrcClassIndex   OBJECT-TYPE
    SYNTAX      ClassIndexOrNone
    MAX-ACCESS  read-only
    STATUS      current
    DESCRIPTION
        "The value of vRtrInetCidrRouteSrcClassIndex indicates the source-class
         for this CIDR route."
    ::= { vRtrInetCidrRouteEntry 20 }

vRtrInetCidrRouteDstClassIndex   OBJECT-TYPE
    SYNTAX      ClassIndexOrNone
    MAX-ACCESS  read-only
    STATUS      current
    DESCRIPTION
        "The value of vRtrInetCidrRouteDstClassIndex indicates the
         destination-class for this CIDR route."
    ::= { vRtrInetCidrRouteEntry 21 }

vRtrInetCidrRouteOperFlags       OBJECT-TYPE
    SYNTAX      TmnxRouteOperFlags
    MAX-ACCESS  read-only
    STATUS      current
    DESCRIPTION
        "The value of vRtrInetCidrRouteOperFlags indicates the status of
         different properties of this route.

         If the 'stickyFlag' bit is set, then it indicates ECMP sticky flag is
         set on this route."
    ::= { vRtrInetCidrRouteEntry 22 }

vRtrInetCidrRouteNextHopWeight   OBJECT-TYPE
    SYNTAX      Unsigned32
    MAX-ACCESS  read-only
    STATUS      current
    DESCRIPTION
        "The value of vRtrInetCidrRouteNextHopWeight indicates the weight given
         to traffic this particular next-hop among the ECMP set of next-hops.

         The range of vRtrInetCidrRouteNextHopWeight is between 0 and maximum
         value of vRtrEcmpMaxRoutes. A value of 0 implies that weighted ECMP is
         not being used in the ECMP set of next-hops and this next-hop will be
         used equally with other next-hops for ECMP."
    ::= { vRtrInetCidrRouteEntry 23 }

vRtrInetCidrRouteNextHopOwnInst  OBJECT-TYPE
    SYNTAX      Unsigned32
    MAX-ACCESS  read-only
    STATUS      current
    DESCRIPTION
        "The value of vRtrInetCidrRouteNextHopOwnInst indicates the instance of
         the next hop owner as indicated by vRtrInetCidrRouteNextHopOwner."
    ::= { vRtrInetCidrRouteEntry 24 }

vRtrInetCidrRouteBkupNHOwnInst   OBJECT-TYPE
    SYNTAX      Unsigned32
    MAX-ACCESS  read-only
    STATUS      current
    DESCRIPTION
        "The value of vRtrInetCidrRouteBkupNHOwnInst indicates the instance of
         the back up next hop owner as indicated by
         vRtrInetCidrRouteBkupNHOwner."
    ::= { vRtrInetCidrRouteEntry 25 }

vRtrInetCidrRouteNHIsFec         OBJECT-TYPE
    SYNTAX      TruthValue
    MAX-ACCESS  read-only
    STATUS      current
    DESCRIPTION
        "When the value of vRtrInetCidrRouteNHIsFec is 'true', it indicates
         inetCidrRouteNextHop is a LDP FEC prefix. This is possible only with
         routes that resolve over LDP FECs. If 'true' then
         vRtrInetCidrRouteNHFecPfxLen has the prefix-length to be used with
         inetCidrRouteNextHop."
    ::= { vRtrInetCidrRouteEntry 26 }

vRtrInetCidrRouteNHFecPfxLen     OBJECT-TYPE
    SYNTAX      InetAddressPrefixLength
    MAX-ACCESS  read-only
    STATUS      current
    DESCRIPTION
        "The value of 'vRtrInetCidrRouteNHFecPfxLen' indicates the prefix
         length of the LDP FEC that resolves the route. This is valid only if
         vRtrInetCidrRouteNHIsFec is 'true', and when valid, this should be
         used in conjunction with inetCidrRouteNextHop to identify the LDP FEC
         that that resolves the route."
    ::= { vRtrInetCidrRouteEntry 27 }

vRtrInetCidrRouteEgrVni          OBJECT-TYPE
    SYNTAX      Unsigned32 (0 | 1..16777215)
    MAX-ACCESS  read-only
    STATUS      current
    DESCRIPTION
        "The value of vRtrInetCidrRouteEgrVni specifies the egress VNI of the
         VXLAN."
    ::= { vRtrInetCidrRouteEntry 28 }

vRtrIcmp6Table                   OBJECT-TYPE
    SYNTAX      SEQUENCE OF VRtrIcmp6Entry
    MAX-ACCESS  not-accessible
    STATUS      current
    DESCRIPTION
        "The vRtrIcmp6Table table contains statistics of ICMPv6 messages that
         are received and sourced by a router instance."
    ::= { tmnxVRtrObjs 31 }

vRtrIcmp6Entry                   OBJECT-TYPE
    SYNTAX      VRtrIcmp6Entry
    MAX-ACCESS  not-accessible
    STATUS      current
    DESCRIPTION
        "Each row entry represents the ICMP statistics of a virtual router
         instance. Entries are created and deleted when entries in the
         vRtrConfEntry are created and deleted."
    AUGMENTS    { vRtrConfEntry }
    ::= { vRtrIcmp6Table 1 }

VRtrIcmp6Entry                   ::= SEQUENCE
{
    vRtrIcmp6InMsgs                  Counter32,
    vRtrIcmp6InErrors                Counter32,
    vRtrIcmp6InDestUnreachs          Counter32,
    vRtrIcmp6InAdminProhibs          Counter32,
    vRtrIcmp6InTimeExcds             Counter32,
    vRtrIcmp6InParmProblems          Counter32,
    vRtrIcmp6InPktTooBigs            Counter32,
    vRtrIcmp6InEchos                 Counter32,
    vRtrIcmp6InEchoReplies           Counter32,
    vRtrIcmp6InRtrSolicits           Counter32,
    vRtrIcmp6InRtrAdvertisements     Counter32,
    vRtrIcmp6InNbrSolicits           Counter32,
    vRtrIcmp6InNbrAdvertisements     Counter32,
    vRtrIcmp6InRedirects             Counter32,
    vRtrIcmp6InGrpMembQueries        Counter32,
    vRtrIcmp6InGrpMembResponses      Counter32,
    vRtrIcmp6InGrpMembReductions     Counter32,
    vRtrIcmp6OutMsgs                 Counter32,
    vRtrIcmp6OutErrors               Counter32,
    vRtrIcmp6OutDestUnreachs         Counter32,
    vRtrIcmp6OutAdminProhibs         Counter32,
    vRtrIcmp6OutTimeExcds            Counter32,
    vRtrIcmp6OutParmProblems         Counter32,
    vRtrIcmp6OutPktTooBigs           Counter32,
    vRtrIcmp6OutEchos                Counter32,
    vRtrIcmp6OutEchoReplies          Counter32,
    vRtrIcmp6OutRtrSolicits          Counter32,
    vRtrIcmp6OutRtrAdvertisements    Counter32,
    vRtrIcmp6OutNbrSolicits          Counter32,
    vRtrIcmp6OutNbrAdvertisements    Counter32,
    vRtrIcmp6OutRedirects            Counter32,
    vRtrIcmp6OutGrpMembQueries       Counter32,
    vRtrIcmp6OutGrpMembResponses     Counter32,
    vRtrIcmp6OutGrpMembReductions    Counter32,
    vRtrIcmp6OutDiscards             Counter32
}

vRtrIcmp6InMsgs                  OBJECT-TYPE
    SYNTAX      Counter32
    MAX-ACCESS  read-only
    STATUS      current
    DESCRIPTION
        "The value of vRtrIcmp6InMsgs indicates the total number of ICMP
         messages received by this router instance which includes all those
         counted by vRtrIcmp6InErrors."
    ::= { vRtrIcmp6Entry 1 }

vRtrIcmp6InErrors                OBJECT-TYPE
    SYNTAX      Counter32
    MAX-ACCESS  read-only
    STATUS      current
    DESCRIPTION
        "The value of vRtrIcmp6InErrors indicates the number of ICMP messages
         which this router instance received but determined as having
         ICMP-specific errors (bad ICMP checksums, bad length , etc.)."
    ::= { vRtrIcmp6Entry 2 }

vRtrIcmp6InDestUnreachs          OBJECT-TYPE
    SYNTAX      Counter32
    MAX-ACCESS  read-only
    STATUS      current
    DESCRIPTION
        "The value of vRtrIcmp6InDestUnreachs indicates the number of ICMP
         Destination Unreachable messages received by this router instance."
    ::= { vRtrIcmp6Entry 3 }

vRtrIcmp6InAdminProhibs          OBJECT-TYPE
    SYNTAX      Counter32
    MAX-ACCESS  read-only
    STATUS      current
    DESCRIPTION
        "The value of vRtrIcmp6InAdminProhibs indicates the number of ICMP
         destination unreachable/communication administratively prohibited
         messages received by this router instance."
    ::= { vRtrIcmp6Entry 4 }

vRtrIcmp6InTimeExcds             OBJECT-TYPE
    SYNTAX      Counter32
    MAX-ACCESS  read-only
    STATUS      current
    DESCRIPTION
        "The value of vRtrIcmp6InTimeExcds indicates the number of ICMP Time
         Exceeded messages received by this router instance."
    ::= { vRtrIcmp6Entry 5 }

vRtrIcmp6InParmProblems          OBJECT-TYPE
    SYNTAX      Counter32
    MAX-ACCESS  read-only
    STATUS      current
    DESCRIPTION
        "The value of vRtrIcmp6InParmProblems indicates the number of ICMP
         Parameter Problem messages received by this router instance."
    ::= { vRtrIcmp6Entry 6 }

vRtrIcmp6InPktTooBigs            OBJECT-TYPE
    SYNTAX      Counter32
    MAX-ACCESS  read-only
    STATUS      current
    DESCRIPTION
        "The value of vRtrIcmp6InPktTooBigs indicates the number of ICMP Packet
         Too Big messages received by this router instance."
    ::= { vRtrIcmp6Entry 7 }

vRtrIcmp6InEchos                 OBJECT-TYPE
    SYNTAX      Counter32
    MAX-ACCESS  read-only
    STATUS      current
    DESCRIPTION
        "The value of vRtrIcmp6InEchos indicates the number of ICMP Echo
         (request) messages received by this router instance."
    ::= { vRtrIcmp6Entry 8 }

vRtrIcmp6InEchoReplies           OBJECT-TYPE
    SYNTAX      Counter32
    MAX-ACCESS  read-only
    STATUS      current
    DESCRIPTION
        "The value of vRtrIcmp6InEchoReplies indicates the number of ICMP Echo
         Reply messages received by this router instance."
    ::= { vRtrIcmp6Entry 9 }

vRtrIcmp6InRtrSolicits           OBJECT-TYPE
    SYNTAX      Counter32
    MAX-ACCESS  read-only
    STATUS      current
    DESCRIPTION
        "The value of vRtrIcmp6InRtrSolicits indicates the number of ICMP
         Router Solicit messages received by this router instance."
    ::= { vRtrIcmp6Entry 10 }

vRtrIcmp6InRtrAdvertisements     OBJECT-TYPE
    SYNTAX      Counter32
    MAX-ACCESS  read-only
    STATUS      current
    DESCRIPTION
        "The value of vRtrIcmp6InRtrAdvertisements indicates the number of ICMP
         Router Advertisement messages received by this router instance."
    ::= { vRtrIcmp6Entry 11 }

vRtrIcmp6InNbrSolicits           OBJECT-TYPE
    SYNTAX      Counter32
    MAX-ACCESS  read-only
    STATUS      current
    DESCRIPTION
        "The value of vRtrIcmp6InNbrSolicits indicates the number of ICMP
         Neighbor Solicit messages received by this router instance."
    ::= { vRtrIcmp6Entry 12 }

vRtrIcmp6InNbrAdvertisements     OBJECT-TYPE
    SYNTAX      Counter32
    MAX-ACCESS  read-only
    STATUS      current
    DESCRIPTION
        "The value of vRtrIcmp6InNbrAdvertisements indicates the number of ICMP
         Neighbor Advertisement messages received by this router instance."
    ::= { vRtrIcmp6Entry 13 }

vRtrIcmp6InRedirects             OBJECT-TYPE
    SYNTAX      Counter32
    MAX-ACCESS  read-only
    STATUS      current
    DESCRIPTION
        "The value of vRtrIcmp6InRedirects indicates number of ICMP Redirect
         messages received by this router instance."
    ::= { vRtrIcmp6Entry 14 }

vRtrIcmp6InGrpMembQueries        OBJECT-TYPE
    SYNTAX      Counter32
    MAX-ACCESS  read-only
    STATUS      current
    DESCRIPTION
        "The value of vRtrIcmp6InGrpMembQueries indicates the number of ICMP
         Group Membership Query messages received by this router instance."
    ::= { vRtrIcmp6Entry 15 }

vRtrIcmp6InGrpMembResponses      OBJECT-TYPE
    SYNTAX      Counter32
    MAX-ACCESS  read-only
    STATUS      current
    DESCRIPTION
        "The value of vRtrIcmp6InGrpMembResponses indicates the number of ICMP
         Group Membership Response messages received by this router instance."
    ::= { vRtrIcmp6Entry 16 }

vRtrIcmp6InGrpMembReductions     OBJECT-TYPE
    SYNTAX      Counter32
    MAX-ACCESS  read-only
    STATUS      current
    DESCRIPTION
        "The value of vRtrIcmp6InGrpMembReductions indicates the number of ICMP
         Group Membership Reduction messages received by this router instance."
    ::= { vRtrIcmp6Entry 17 }

vRtrIcmp6OutMsgs                 OBJECT-TYPE
    SYNTAX      Counter32
    MAX-ACCESS  read-only
    STATUS      current
    DESCRIPTION
        "The value of vRtrIcmp6OutMsgs indicates the total number of ICMP
         messages which this router instance attempted to send.  Note that
         this counter includes all those counted by icmpOutErrors."
    ::= { vRtrIcmp6Entry 18 }

vRtrIcmp6OutErrors               OBJECT-TYPE
    SYNTAX      Counter32
    MAX-ACCESS  read-only
    STATUS      current
    DESCRIPTION
        "The value of vRtrIcmp6OutErrors indicates the number of ICMP
         messages which this router instance did not send due to problems
         discovered within ICMP such as a lack of buffers.  This value
         should not include errors discovered outside the ICMP layer such
         as the inability of VRtr IPv6 to route the resultant datagram.  In
         some implementations there may be no types of error which contribute
         to this counter's value."
    ::= { vRtrIcmp6Entry 19 }

vRtrIcmp6OutDestUnreachs         OBJECT-TYPE
    SYNTAX      Counter32
    MAX-ACCESS  read-only
    STATUS      current
    DESCRIPTION
        "The value of vRtrIcmp6OutDestUnreachs indicates the number of ICMP
         Destination Unreachable messages sent by this router instance."
    ::= { vRtrIcmp6Entry 20 }

vRtrIcmp6OutAdminProhibs         OBJECT-TYPE
    SYNTAX      Counter32
    MAX-ACCESS  read-only
    STATUS      current
    DESCRIPTION
        "The value of vRtrIcmp6OutAdminProhibs indicates the number of ICMP
         destination unreachable/communication administratively prohibited
         messages sent by this router instance."
    ::= { vRtrIcmp6Entry 21 }

vRtrIcmp6OutTimeExcds            OBJECT-TYPE
    SYNTAX      Counter32
    MAX-ACCESS  read-only
    STATUS      current
    DESCRIPTION
        "The value of vRtrIcmp6OutTimeExcds indicates the number of ICMP Time
         Exceeded messages sent by this router instance."
    ::= { vRtrIcmp6Entry 22 }

vRtrIcmp6OutParmProblems         OBJECT-TYPE
    SYNTAX      Counter32
    MAX-ACCESS  read-only
    STATUS      current
    DESCRIPTION
        "The value of vRtrIcmp6OutParmProblems indicates the number of ICMP
         Parameter Problem messages sent by this router instance."
    ::= { vRtrIcmp6Entry 23 }

vRtrIcmp6OutPktTooBigs           OBJECT-TYPE
    SYNTAX      Counter32
    MAX-ACCESS  read-only
    STATUS      current
    DESCRIPTION
        "The value of vRtrIcmp6OutPktTooBigs indicates the number of ICMP
         Packet Too Big messages sent by this router instance."
    ::= { vRtrIcmp6Entry 24 }

vRtrIcmp6OutEchos                OBJECT-TYPE
    SYNTAX      Counter32
    MAX-ACCESS  read-only
    STATUS      current
    DESCRIPTION
        "The value of vRtrIcmp6OutEchos indicates the number of ICMP Echo
         Request messages sent by this router instance."
    ::= { vRtrIcmp6Entry 25 }

vRtrIcmp6OutEchoReplies          OBJECT-TYPE
    SYNTAX      Counter32
    MAX-ACCESS  read-only
    STATUS      current
    DESCRIPTION
        "The value of vRtrIcmp6OutEchoReplies indicates the number of ICMP Echo
         Reply messages sent by this router instance."
    ::= { vRtrIcmp6Entry 26 }

vRtrIcmp6OutRtrSolicits          OBJECT-TYPE
    SYNTAX      Counter32
    MAX-ACCESS  read-only
    STATUS      current
    DESCRIPTION
        "The value of vRtrIcmp6OutRtrSolicits indicates the number of ICMP
         Router Solicitation messages sent by this router instance."
    ::= { vRtrIcmp6Entry 27 }

vRtrIcmp6OutRtrAdvertisements    OBJECT-TYPE
    SYNTAX      Counter32
    MAX-ACCESS  read-only
    STATUS      current
    DESCRIPTION
        "The value of vRtrIcmp6OutRtrAdvertisements indicates the number of
         ICMP Router Advertisement messages sent by this router instance."
    ::= { vRtrIcmp6Entry 28 }

vRtrIcmp6OutNbrSolicits          OBJECT-TYPE
    SYNTAX      Counter32
    MAX-ACCESS  read-only
    STATUS      current
    DESCRIPTION
        "The value of vRtrIcmp6OutNbrSolicits indicates the number of ICMP
         Neighbor Solicitation messages sent by this router instance."
    ::= { vRtrIcmp6Entry 29 }

vRtrIcmp6OutNbrAdvertisements    OBJECT-TYPE
    SYNTAX      Counter32
    MAX-ACCESS  read-only
    STATUS      current
    DESCRIPTION
        "The value of vRtrIcmp6OutNbrAdvertisements indicates the number of
         ICMP Neighbor Advertisement messages sent by this router instance."
    ::= { vRtrIcmp6Entry 30 }

vRtrIcmp6OutRedirects            OBJECT-TYPE
    SYNTAX      Counter32
    MAX-ACCESS  read-only
    STATUS      current
    DESCRIPTION
        "The value of vRtrIcmp6OutRedirects indicates the number of ICMP
         Redirect messages sent by this router instance."
    ::= { vRtrIcmp6Entry 31 }

vRtrIcmp6OutGrpMembQueries       OBJECT-TYPE
    SYNTAX      Counter32
    MAX-ACCESS  read-only
    STATUS      current
    DESCRIPTION
        "The value of vRtrIcmp6OutGrpMembQueries indicates the number of ICMP
         Group Membership Query messages sent by this router instance."
    ::= { vRtrIcmp6Entry 32 }

vRtrIcmp6OutGrpMembResponses     OBJECT-TYPE
    SYNTAX      Counter32
    MAX-ACCESS  read-only
    STATUS      current
    DESCRIPTION
        "The value of vRtrIcmp6OutGrpMembResponses indicates the number of ICMP
         Group Membership Response messages sent by this router instance."
    ::= { vRtrIcmp6Entry 33 }

vRtrIcmp6OutGrpMembReductions    OBJECT-TYPE
    SYNTAX      Counter32
    MAX-ACCESS  read-only
    STATUS      current
    DESCRIPTION
        "The value of vRtrIcmp6OutGrpMembReductions indicates the number of
         ICMP Group Membership Reduction messages sent by this router instance."
    ::= { vRtrIcmp6Entry 34 }

vRtrIcmp6OutDiscards             OBJECT-TYPE
    SYNTAX      Counter32
    MAX-ACCESS  read-only
    STATUS      current
    DESCRIPTION
        "The value of vRtrIcmp6OutDiscards indicates the number of ICMP
         outgoing packets that were dropped by this router instance."
    ::= { vRtrIcmp6Entry 35 }

vRtrIfIcmp6Table                 OBJECT-TYPE
    SYNTAX      SEQUENCE OF VRtrIfIcmp6Entry
    MAX-ACCESS  not-accessible
    STATUS      current
    DESCRIPTION
        "The vRtrIfIcmp6Table table contains statistics of ICMPv6 messages that
         are received and sourced by a router interface."
    ::= { tmnxVRtrObjs 32 }

vRtrIfIcmp6Entry                 OBJECT-TYPE
    SYNTAX      VRtrIfIcmp6Entry
    MAX-ACCESS  not-accessible
    STATUS      current
    DESCRIPTION
        "Each row entry represents the ICMP statistics of a virtual router
         interface. Entries are created and deleted when entries in the
         vRtrIfTable are created and deleted."
    AUGMENTS    { vRtrIfEntry }
    ::= { vRtrIfIcmp6Table 1 }

VRtrIfIcmp6Entry                 ::= SEQUENCE
{
    vRtrIfIcmp6InMsgs                Counter32,
    vRtrIfIcmp6InErrors              Counter32,
    vRtrIfIcmp6InDestUnreachs        Counter32,
    vRtrIfIcmp6InAdminProhibs        Counter32,
    vRtrIfIcmp6InTimeExcds           Counter32,
    vRtrIfIcmp6InParmProblems        Counter32,
    vRtrIfIcmp6InPktTooBigs          Counter32,
    vRtrIfIcmp6InEchos               Counter32,
    vRtrIfIcmp6InEchoReplies         Counter32,
    vRtrIfIcmp6InRtrSolicits         Counter32,
    vRtrIfIcmp6InRtrAdvertisements   Counter32,
    vRtrIfIcmp6InNbrSolicits         Counter32,
    vRtrIfIcmp6InNbrAdvertisements   Counter32,
    vRtrIfIcmp6InRedirects           Counter32,
    vRtrIfIcmp6InGrpMembQueries      Counter32,
    vRtrIfIcmp6InGrpMembResponses    Counter32,
    vRtrIfIcmp6InGrpMembReductions   Counter32,
    vRtrIfIcmp6OutMsgs               Counter32,
    vRtrIfIcmp6OutErrors             Counter32,
    vRtrIfIcmp6OutDestUnreachs       Counter32,
    vRtrIfIcmp6OutAdminProhibs       Counter32,
    vRtrIfIcmp6OutTimeExcds          Counter32,
    vRtrIfIcmp6OutParmProblems       Counter32,
    vRtrIfIcmp6OutPktTooBigs         Counter32,
    vRtrIfIcmp6OutEchos              Counter32,
    vRtrIfIcmp6OutEchoReplies        Counter32,
    vRtrIfIcmp6OutRtrSolicits        Counter32,
    vRtrIfIcmp6OutRtrSolicitsTime    TimeStamp,
    vRtrIfIcmp6OutRtrAdvertisements  Counter32,
    vRtrIfIcmp6OutRtrAdvTime         TimeStamp,
    vRtrIfIcmp6OutNbrSolicits        Counter32,
    vRtrIfIcmp6OutNbrSolicitsTime    TimeStamp,
    vRtrIfIcmp6OutNbrAdvertisements  Counter32,
    vRtrIfIcmp6OutNbrAdvTime         TimeStamp,
    vRtrIfIcmp6OutRedirects          Counter32,
    vRtrIfIcmp6OutGrpMembQueries     Counter32,
    vRtrIfIcmp6OutGrpMembResponses   Counter32,
    vRtrIfIcmp6OutGrpMembReductions  Counter32,
    vRtrIfIcmp6OutDiscards           Counter32
}

vRtrIfIcmp6InMsgs                OBJECT-TYPE
    SYNTAX      Counter32
    MAX-ACCESS  read-only
    STATUS      current
    DESCRIPTION
        "The value of vRtrIfIcmp6InMsgs indicates the total number of ICMP
         messages received by this interface which includes all those counted
         by vRtrIfIcmp6InErrors. Note that this interface is the interface to
         which the ICMP messages were addressed which may not be necessarily
         the input interface for the messages."
    ::= { vRtrIfIcmp6Entry 1 }

vRtrIfIcmp6InErrors              OBJECT-TYPE
    SYNTAX      Counter32
    MAX-ACCESS  read-only
    STATUS      current
    DESCRIPTION
        "The value of vRtrIfIcmp6InErrors indicates the number of ICMP messages
         which this interface received but determined as having ICMP-specific
         errors (bad ICMP checksums, bad length , etc.)."
    ::= { vRtrIfIcmp6Entry 2 }

vRtrIfIcmp6InDestUnreachs        OBJECT-TYPE
    SYNTAX      Counter32
    MAX-ACCESS  read-only
    STATUS      current
    DESCRIPTION
        "The value of vRtrIfIcmp6InDestUnreachs indicates the number of ICMP
         Destination Unreachable messages received by this interface."
    ::= { vRtrIfIcmp6Entry 3 }

vRtrIfIcmp6InAdminProhibs        OBJECT-TYPE
    SYNTAX      Counter32
    MAX-ACCESS  read-only
    STATUS      current
    DESCRIPTION
        "The value of vRtrIfIcmp6InAdminProhibs indicates the number of ICMP
         destination unreachable/communication administratively prohibited
         messages received by this interface."
    ::= { vRtrIfIcmp6Entry 4 }

vRtrIfIcmp6InTimeExcds           OBJECT-TYPE
    SYNTAX      Counter32
    MAX-ACCESS  read-only
    STATUS      current
    DESCRIPTION
        "The value of vRtrIfIcmp6InTimeExcds indicates the number of ICMP Time
         Exceeded messages received by this interface."
    ::= { vRtrIfIcmp6Entry 5 }

vRtrIfIcmp6InParmProblems        OBJECT-TYPE
    SYNTAX      Counter32
    MAX-ACCESS  read-only
    STATUS      current
    DESCRIPTION
        "The value of vRtrIfIcmp6InParmProblems indicates the number of ICMP
         Parameter Problem messages received by this interface."
    ::= { vRtrIfIcmp6Entry 6 }

vRtrIfIcmp6InPktTooBigs          OBJECT-TYPE
    SYNTAX      Counter32
    MAX-ACCESS  read-only
    STATUS      current
    DESCRIPTION
        "The value of vRtrIfIcmp6InPktTooBigs indicates the number of ICMP
         Packet Too Big messages received by this interface."
    ::= { vRtrIfIcmp6Entry 7 }

vRtrIfIcmp6InEchos               OBJECT-TYPE
    SYNTAX      Counter32
    MAX-ACCESS  read-only
    STATUS      current
    DESCRIPTION
        "The value of vRtrIfIcmp6InEchos indicates the number of ICMP Echo
         (request) messages received by this interface."
    ::= { vRtrIfIcmp6Entry 8 }

vRtrIfIcmp6InEchoReplies         OBJECT-TYPE
    SYNTAX      Counter32
    MAX-ACCESS  read-only
    STATUS      current
    DESCRIPTION
        "The value of vRtrIfIcmp6InEchoReplies indicates the number of ICMP
         Echo Reply messages received by this interface."
    ::= { vRtrIfIcmp6Entry 9 }

vRtrIfIcmp6InRtrSolicits         OBJECT-TYPE
    SYNTAX      Counter32
    MAX-ACCESS  read-only
    STATUS      current
    DESCRIPTION
        "The value of vRtrIfIcmp6InRtrSolicits indicates the number of ICMP
         Router Solicit messages received by this interface."
    ::= { vRtrIfIcmp6Entry 10 }

vRtrIfIcmp6InRtrAdvertisements   OBJECT-TYPE
    SYNTAX      Counter32
    MAX-ACCESS  read-only
    STATUS      current
    DESCRIPTION
        "The value of vRtrIfIcmp6InRtrAdvertisements indicates the number of
         ICMP Router Advertisement messages received by this interface."
    ::= { vRtrIfIcmp6Entry 11 }

vRtrIfIcmp6InNbrSolicits         OBJECT-TYPE
    SYNTAX      Counter32
    MAX-ACCESS  read-only
    STATUS      current
    DESCRIPTION
        "The value of vRtrIfIcmp6InNbrSolicits indicates the number of ICMP
         Neighbor Solicit messages received by this interface."
    ::= { vRtrIfIcmp6Entry 12 }

vRtrIfIcmp6InNbrAdvertisements   OBJECT-TYPE
    SYNTAX      Counter32
    MAX-ACCESS  read-only
    STATUS      current
    DESCRIPTION
        "The value of vRtrIfIcmp6InNbrAdvertisements indicates the number of
         ICMP Neighbor Advertisement messages received by this interface."
    ::= { vRtrIfIcmp6Entry 13 }

vRtrIfIcmp6InRedirects           OBJECT-TYPE
    SYNTAX      Counter32
    MAX-ACCESS  read-only
    STATUS      current
    DESCRIPTION
        "The value of vRtrIfIcmp6InRedirects indicates number of ICMP Redirect
         messages received by this interface."
    ::= { vRtrIfIcmp6Entry 14 }

vRtrIfIcmp6InGrpMembQueries      OBJECT-TYPE
    SYNTAX      Counter32
    MAX-ACCESS  read-only
    STATUS      current
    DESCRIPTION
        "The value of vRtrIfIcmp6InGrpMembQueries indicates the number of ICMP
         Group Membership Query messages received by this interface."
    ::= { vRtrIfIcmp6Entry 15 }

vRtrIfIcmp6InGrpMembResponses    OBJECT-TYPE
    SYNTAX      Counter32
    MAX-ACCESS  read-only
    STATUS      current
    DESCRIPTION
        "The value of vRtrIfIcmp6InGrpMembResponses indicates the number of
         ICMP Group Membership Response messages received by this interface."
    ::= { vRtrIfIcmp6Entry 16 }

vRtrIfIcmp6InGrpMembReductions   OBJECT-TYPE
    SYNTAX      Counter32
    MAX-ACCESS  read-only
    STATUS      current
    DESCRIPTION
        "The value of vRtrIfIcmp6InGrpMembReductions indicates the number of
         ICMP Group Membership Reduction messages received by this interface."
    ::= { vRtrIfIcmp6Entry 17 }

vRtrIfIcmp6OutMsgs               OBJECT-TYPE
    SYNTAX      Counter32
    MAX-ACCESS  read-only
    STATUS      current
    DESCRIPTION
        "The value of vRtrIfIcmp6OutMsgs indicates the total number of ICMP
         messages which this interface attempted to send.  Note that this
         counter includes all those counted by icmpOutErrors."
    ::= { vRtrIfIcmp6Entry 18 }

vRtrIfIcmp6OutErrors             OBJECT-TYPE
    SYNTAX      Counter32
    MAX-ACCESS  read-only
    STATUS      current
    DESCRIPTION
        "The value of vRtrIfIcmp6OutErrors indicates the number of ICMP
         messages which this interface did not send due to problems discovered
         within ICMP such as a lack of buffers.  This value should not include
         errors discovered outside the ICMP layer such as the inability of
         VRtr IPv6 to route the resultant datagram.  In some implementations
         there may be no types of error which contribute to this counter's
         value."
    ::= { vRtrIfIcmp6Entry 19 }

vRtrIfIcmp6OutDestUnreachs       OBJECT-TYPE
    SYNTAX      Counter32
    MAX-ACCESS  read-only
    STATUS      current
    DESCRIPTION
        "The value of vRtrIfIcmp6OutDestUnreachs indicates the number of ICMP
         Destination Unreachable messages sent by this interface."
    ::= { vRtrIfIcmp6Entry 20 }

vRtrIfIcmp6OutAdminProhibs       OBJECT-TYPE
    SYNTAX      Counter32
    MAX-ACCESS  read-only
    STATUS      current
    DESCRIPTION
        "The value of vRtrIfIcmp6OutAdminProhibs indicates the number of ICMP
         destination unreachable/communication administratively prohibited
         messages sent by this interface."
    ::= { vRtrIfIcmp6Entry 21 }

vRtrIfIcmp6OutTimeExcds          OBJECT-TYPE
    SYNTAX      Counter32
    MAX-ACCESS  read-only
    STATUS      current
    DESCRIPTION
        "The value of vRtrIfIcmp6OutTimeExcds indicates the number of ICMP Time
         Exceeded messages sent by this interface."
    ::= { vRtrIfIcmp6Entry 22 }

vRtrIfIcmp6OutParmProblems       OBJECT-TYPE
    SYNTAX      Counter32
    MAX-ACCESS  read-only
    STATUS      current
    DESCRIPTION
        "The value of vRtrIfIcmp6OutParmProblems indicates the number of ICMP
         Parameter Problem messages sent by this interface."
    ::= { vRtrIfIcmp6Entry 23 }

vRtrIfIcmp6OutPktTooBigs         OBJECT-TYPE
    SYNTAX      Counter32
    MAX-ACCESS  read-only
    STATUS      current
    DESCRIPTION
        "The value of vRtrIfIcmp6OutPktTooBigs indicates the number of ICMP
         Packet Too Big messages sent by this interface."
    ::= { vRtrIfIcmp6Entry 24 }

vRtrIfIcmp6OutEchos              OBJECT-TYPE
    SYNTAX      Counter32
    MAX-ACCESS  read-only
    STATUS      current
    DESCRIPTION
        "The value of vRtrIfIcmp6OutEchos indicates the number of ICMP Echo
         Request messages sent by this interface."
    ::= { vRtrIfIcmp6Entry 25 }

vRtrIfIcmp6OutEchoReplies        OBJECT-TYPE
    SYNTAX      Counter32
    MAX-ACCESS  read-only
    STATUS      current
    DESCRIPTION
        "The value of vRtrIfIcmp6OutEchoReplies indicates the number of ICMP
         Echo Reply messages sent by this interface."
    ::= { vRtrIfIcmp6Entry 26 }

vRtrIfIcmp6OutRtrSolicits        OBJECT-TYPE
    SYNTAX      Counter32
    MAX-ACCESS  read-only
    STATUS      current
    DESCRIPTION
        "The value of vRtrIfIcmp6OutRtrSolicits indicates the number of ICMP
         Router Solicitation messages sent by this interface."
    ::= { vRtrIfIcmp6Entry 27 }

vRtrIfIcmp6OutRtrSolicitsTime    OBJECT-TYPE
    SYNTAX      TimeStamp
    MAX-ACCESS  read-only
    STATUS      current
    DESCRIPTION
        "The value of vRtrIfIcmp6OutRtrSolicitsTime indicates the system time
         when the last router solicitation message was sent by this interface."
    ::= { vRtrIfIcmp6Entry 28 }

vRtrIfIcmp6OutRtrAdvertisements  OBJECT-TYPE
    SYNTAX      Counter32
    MAX-ACCESS  read-only
    STATUS      current
    DESCRIPTION
        "The value of vRtrIfIcmp6OutRtrAdvertisements indicates the number of
         ICMP Router Advertisement messages sent by this interface."
    ::= { vRtrIfIcmp6Entry 29 }

vRtrIfIcmp6OutRtrAdvTime         OBJECT-TYPE
    SYNTAX      TimeStamp
    MAX-ACCESS  read-only
    STATUS      current
    DESCRIPTION
        "The value of vRtrIfIcmp6OutRtrAdvTime indicates the system time when
         the last router advertisement message was sent by this interface."
    ::= { vRtrIfIcmp6Entry 30 }

vRtrIfIcmp6OutNbrSolicits        OBJECT-TYPE
    SYNTAX      Counter32
    MAX-ACCESS  read-only
    STATUS      current
    DESCRIPTION
        "The value of vRtrIfIcmp6OutNbrSolicits indicates the number of ICMP
         Neighbor Solicitation messages sent by this interface."
    ::= { vRtrIfIcmp6Entry 31 }

vRtrIfIcmp6OutNbrSolicitsTime    OBJECT-TYPE
    SYNTAX      TimeStamp
    MAX-ACCESS  read-only
    STATUS      current
    DESCRIPTION
        "The value of vRtrIfIcmp6OutNbrSolicitsTime indicates the system time
         when the last neighbor solicitation message was sent by this
         interface."
    ::= { vRtrIfIcmp6Entry 32 }

vRtrIfIcmp6OutNbrAdvertisements  OBJECT-TYPE
    SYNTAX      Counter32
    MAX-ACCESS  read-only
    STATUS      current
    DESCRIPTION
        "The value of vRtrIfIcmp6OutNbrAdvertisements indicates the number of
         ICMP Neighbor Advertisement messages sent by this interface."
    ::= { vRtrIfIcmp6Entry 33 }

vRtrIfIcmp6OutNbrAdvTime         OBJECT-TYPE
    SYNTAX      TimeStamp
    MAX-ACCESS  read-only
    STATUS      current
    DESCRIPTION
        "The value of vRtrIfIcmp6OutNbrAdvTime indicates the system time when
         the last neighbor advertisement message was sent by this interface."
    ::= { vRtrIfIcmp6Entry 34 }

vRtrIfIcmp6OutRedirects          OBJECT-TYPE
    SYNTAX      Counter32
    MAX-ACCESS  read-only
    STATUS      current
    DESCRIPTION
        "The value of vRtrIfIcmp6OutRedirects indicates the number of ICMP
         Redirect messages sent by this interface."
    ::= { vRtrIfIcmp6Entry 35 }

vRtrIfIcmp6OutGrpMembQueries     OBJECT-TYPE
    SYNTAX      Counter32
    MAX-ACCESS  read-only
    STATUS      current
    DESCRIPTION
        "The value of vRtrIfIcmp6OutGrpMembQueries indicates the number of ICMP
         Group Membership Query messages sent by this interface."
    ::= { vRtrIfIcmp6Entry 36 }

vRtrIfIcmp6OutGrpMembResponses   OBJECT-TYPE
    SYNTAX      Counter32
    MAX-ACCESS  read-only
    STATUS      current
    DESCRIPTION
        "The value of vRtrIfIcmp6OutGrpMembResponses indicates the number of
         ICMP Group Membership Response messages sent by this interface."
    ::= { vRtrIfIcmp6Entry 37 }

vRtrIfIcmp6OutGrpMembReductions  OBJECT-TYPE
    SYNTAX      Counter32
    MAX-ACCESS  read-only
    STATUS      current
    DESCRIPTION
        "The value of vRtrIfIcmp6OutGrpMembReductions indicates the number of
         ICMP Group Membership Reduction messages sent by this interface."
    ::= { vRtrIfIcmp6Entry 38 }

vRtrIfIcmp6OutDiscards           OBJECT-TYPE
    SYNTAX      Counter32
    MAX-ACCESS  read-only
    STATUS      current
    DESCRIPTION
        "The value of vRtrIfIcmp6OutDiscards indicates the number of ICMP
         outgoing packets that were dropped on this interface."
    ::= { vRtrIfIcmp6Entry 39 }

vRtrIfBfdTable                   OBJECT-TYPE
    SYNTAX      SEQUENCE OF VRtrIfBfdEntry
    MAX-ACCESS  not-accessible
    STATUS      obsolete
    DESCRIPTION
        "The vRtrIfBfdTable table contains the configuration for Bi-directional
         Forwarding Detection (BFD) on the vRtrIfEntry with the same indices.

         The vRtrIfBfdTable is obsoleted and replaced with vRtrIfBfdExtTable in
         9.0 Release."
    ::= { tmnxVRtrObjs 33 }

vRtrIfBfdEntry                   OBJECT-TYPE
    SYNTAX      VRtrIfBfdEntry
    MAX-ACCESS  not-accessible
    STATUS      obsolete
    DESCRIPTION
        "Each row entry represents the BFD configuration for an interface.
         Entries are created and deleted when entries in the vRtrIfTable are
         created and deleted.

         The vRtrIfBfdEntry is obsoleted and replaced with vRtrIfBfdExtEntry in
         9.0 Release."
    AUGMENTS    { vRtrIfEntry }
    ::= { vRtrIfBfdTable 1 }

VRtrIfBfdEntry                   ::= SEQUENCE
{
    vRtrIfBfdAdminState              TmnxAdminState,
    vRtrIfBfdTransmitInterval        Unsigned32,
    vRtrIfBfdReceiveInterval         Unsigned32,
    vRtrIfBfdMultiplier              Unsigned32,
    vRtrIfBfdEchoInterval            Unsigned32,
    vRtrIfBfdType                    INTEGER
}

vRtrIfBfdAdminState              OBJECT-TYPE
    SYNTAX      TmnxAdminState
    MAX-ACCESS  read-write
    STATUS      obsolete
    DESCRIPTION
        "The value of vRtrIfBfdAdminState specifies the admin state of BFD on
         this interface. When it is 'inService', BFD sessions can be
         established on this interface. When it is 'outOfService', they cannot.

         The vRtrIfBfdAdminState object is obsoleted and replaced with
         vRtrIfBfdExtAdminState object in 9.0 Release."
    ::= { vRtrIfBfdEntry 1 }

vRtrIfBfdTransmitInterval        OBJECT-TYPE
    SYNTAX      Unsigned32 (10..100000)
    UNITS       "milliseconds"
    MAX-ACCESS  read-write
    STATUS      obsolete
    DESCRIPTION
        "The value of vRtrIfBfdTransmitInterval specifies the BFD transmit
         interval over this interface.  The minimum accepted value depends
         on the value of vRtrIfBfdType, as follows:
             'cpmNp(1)' :   10 milliseconds
             'auto(2)'  :  100 milliseconds.

         The vRtrIfBfdTransmitInterval object is obsoleted and replaced with
         vRtrIfBfdExtTransmitInterval object in 9.0 Release."
    DEFVAL      { 100 }
    ::= { vRtrIfBfdEntry 2 }

vRtrIfBfdReceiveInterval         OBJECT-TYPE
    SYNTAX      Unsigned32 (10..100000)
    UNITS       "milliseconds"
    MAX-ACCESS  read-write
    STATUS      obsolete
    DESCRIPTION
        "The value of vRtrIfBfdReceiveInterval specifies the BFD receive
         interval over this interface.  The minimum accepted value depends
         on the value of vRtrIfBfdType, as follows:
             'cpmNp(1)' :   10 milliseconds
             'auto(2)'  :  100 milliseconds.

         The vRtrIfBfdReceiveInterval object is obsoleted and replaced with
         vRtrIfBfdExtReceiveInterval object in 9.0 Release."
    DEFVAL      { 100 }
    ::= { vRtrIfBfdEntry 3 }

vRtrIfBfdMultiplier              OBJECT-TYPE
    SYNTAX      Unsigned32 (3..20)
    MAX-ACCESS  read-write
    STATUS      obsolete
    DESCRIPTION
        "The value of vRtrIfBfdMultiplier specifies the the number of
         consecutive BFD messages that must be missed from the peer before the
         BFD session state is changed to down and the upper level protocols
         (OSPF, IS-IS or PIM) are notified of the fault.

         The vRtrIfBfdMultiplier object is obsoleted and replaced with
         vRtrIfBfdExtMultiplier object in 9.0 Release."
    DEFVAL      { 3 }
    ::= { vRtrIfBfdEntry 4 }

vRtrIfBfdEchoInterval            OBJECT-TYPE
    SYNTAX      Unsigned32 (0 | 100..100000)
    UNITS       "milliseconds"
    MAX-ACCESS  read-write
    STATUS      obsolete
    DESCRIPTION
        "The value of vRtrIfBfdEchoInterval specifies the BFD echo interval
         over this interface.

         The vRtrIfBfdEchoInterval object is obsoleted and replaced with
         vRtrIfBfdExtEchoInterval object in 9.0 Release."
    DEFVAL      { 0 }
    ::= { vRtrIfBfdEntry 5 }

vRtrIfBfdType                    OBJECT-TYPE
    SYNTAX      INTEGER {
        cpmNp (1),
        auto  (2)
    }
    MAX-ACCESS  read-write
    STATUS      obsolete
    DESCRIPTION
        "The value of vRtrIfBfdType specifies the configured termination
         of a BFD session on this interface.  'cpmNp(1)' specifies
         termination on the CPM card's Network Processor.  'auto(2)'
         specifies a system-selected termination other than the CPM Network
         Processor.

         The vRtrIfBfdType object is obsoleted and replaced with
         vRtrIfBfdExtType object in 9.0 Release."
    DEFVAL      { auto }
    ::= { vRtrIfBfdEntry 6 }

vRtrIfBfdSessionTable            OBJECT-TYPE
    SYNTAX      SEQUENCE OF VRtrIfBfdSessionEntry
    MAX-ACCESS  not-accessible
    STATUS      obsolete
    DESCRIPTION
        "The vRtrIfBfdSessionTable table contains per BFD session statistics
         and operational settings."
    ::= { tmnxVRtrObjs 34 }

vRtrIfBfdSessionEntry            OBJECT-TYPE
    SYNTAX      VRtrIfBfdSessionEntry
    MAX-ACCESS  not-accessible
    STATUS      obsolete
    DESCRIPTION
        "Each row entry represents a BFD session. Entries are created
         automatically by the system, or when a static route is configured to
         use BFD."
    INDEX       {
        vRtrID,
        vRtrIfIndex,
        vRtrIfBfdSessionLclAddrType,
        vRtrIfBfdSessionLclAddr,
        vRtrIfBfdSessionRemAddrType,
        vRtrIfBfdSessionRemAddr
    }
    ::= { vRtrIfBfdSessionTable 1 }

VRtrIfBfdSessionEntry            ::= SEQUENCE
{
    vRtrIfBfdSessionLclAddrType      InetAddressType,
    vRtrIfBfdSessionLclAddr          InetAddress,
    vRtrIfBfdSessionRemAddrType      InetAddressType,
    vRtrIfBfdSessionRemAddr          InetAddress,
    vRtrIfBfdSessionOperState        TmnxOperState,
    vRtrIfBfdSessionState            INTEGER,
    vRtrIfBfdSessionOperFlags        BITS,
    vRtrIfBfdSessionMesgRecv         Counter32,
    vRtrIfBfdSessionMesgSent         Counter32,
    vRtrIfBfdSessionLastDownTime     TimeStamp,
    vRtrIfBfdSessionLastUpTime       TimeStamp,
    vRtrIfBfdSessionUpCount          Counter32,
    vRtrIfBfdSessionDownCount        Counter32,
    vRtrIfBfdSessionLclDisc          Unsigned32,
    vRtrIfBfdSessionRemDisc          Unsigned32,
    vRtrIfBfdSessionProtocols        BITS,
    vRtrIfBfdSessionTxInterval       Unsigned32,
    vRtrIfBfdSessionRxInterval       Unsigned32,
    vRtrIfBfdSessionType             INTEGER,
    vRtrIfBfdSessionVerMismatch      Counter32,
    vRtrIfBfdSessionTimeSinceLastRx  Unsigned32,
    vRtrIfBfdSessionTimeSinceLastTx  Unsigned32
}

vRtrIfBfdSessionLclAddrType      OBJECT-TYPE
    SYNTAX      InetAddressType
    MAX-ACCESS  not-accessible
    STATUS      obsolete
    DESCRIPTION
        "The value of vRtrIfBfdSessionLclAddrType indicates the address type in
         vRtrIfBfdSessionLclAddr."
    ::= { vRtrIfBfdSessionEntry 1 }

vRtrIfBfdSessionLclAddr          OBJECT-TYPE
    SYNTAX      InetAddress (SIZE (0|4|16|20))
    MAX-ACCESS  not-accessible
    STATUS      obsolete
    DESCRIPTION
        "The value of vRtrIfBfdSessionLclAddr indicates the address of the
         local endpoint of this BFD session. Its type is specified by
         vRtrIfBfdSessionLclAddrType."
    ::= { vRtrIfBfdSessionEntry 2 }

vRtrIfBfdSessionRemAddrType      OBJECT-TYPE
    SYNTAX      InetAddressType
    MAX-ACCESS  not-accessible
    STATUS      obsolete
    DESCRIPTION
        "The value of vRtrIfBfdSessionRemAddrType indicates the address type in
         vRtrIfBfdSessionRemAddr."
    ::= { vRtrIfBfdSessionEntry 3 }

vRtrIfBfdSessionRemAddr          OBJECT-TYPE
    SYNTAX      InetAddress (SIZE (0|4|16|20))
    MAX-ACCESS  not-accessible
    STATUS      obsolete
    DESCRIPTION
        "The value of vRtrIfBfdSessionRemAddr indicates the address of the
         local endpoint of this BFD session. Its type is specified by
         vRtrIfBfdSessionRemAddrType."
    ::= { vRtrIfBfdSessionEntry 4 }

vRtrIfBfdSessionOperState        OBJECT-TYPE
    SYNTAX      TmnxOperState
    MAX-ACCESS  read-only
    STATUS      obsolete
    DESCRIPTION
        "The value of vRtrIfBfdSessionOperState indicates the operational state
         of BFD on this interface."
    ::= { vRtrIfBfdSessionEntry 5 }

vRtrIfBfdSessionState            OBJECT-TYPE
    SYNTAX      INTEGER {
        adminDown (0),
        down      (1),
        init      (2),
        up        (3)
    }
    MAX-ACCESS  read-only
    STATUS      obsolete
    DESCRIPTION
        "The value of vRtrIfBfdSessionState indicates the state of the BFD
         protocol on this interface."
    ::= { vRtrIfBfdSessionEntry 6 }

vRtrIfBfdSessionOperFlags        OBJECT-TYPE
    SYNTAX      BITS {
        noProtocols   (0),
        noHeartBeat   (1),
        echoFailed    (2),
        nbrSignalDown (3),
        fwdPlaneReset (4),
        pathDown      (5),
        nbrAdminDown  (6),
        adminClear    (7)
    }
    MAX-ACCESS  read-only
    STATUS      obsolete
    DESCRIPTION
        "The value of vRtrIfBfdSessionOperFlags indicates the reasons why a BFD
         session is not up."
    ::= { vRtrIfBfdSessionEntry 7 }

vRtrIfBfdSessionMesgRecv         OBJECT-TYPE
    SYNTAX      Counter32
    MAX-ACCESS  read-only
    STATUS      obsolete
    DESCRIPTION
        "The value of vRtrIfBfdSessionMesgRecv indicates the number of messages
         received in this session.

         This object is applicable if vRtrIfBfdSessionType is 'iom(1)' or
         'cpm(2)'.  Otherwise, zero is returned."
    ::= { vRtrIfBfdSessionEntry 8 }

vRtrIfBfdSessionMesgSent         OBJECT-TYPE
    SYNTAX      Counter32
    MAX-ACCESS  read-only
    STATUS      obsolete
    DESCRIPTION
        "The value of vRtrIfBfdSessionMesgSent indicates the number of messages
         sent in this session.

         This object is applicable if vRtrIfBfdSessionType is 'iom(1)' or
         'cpm(2)'.  Otherwise, zero is returned."
    ::= { vRtrIfBfdSessionEntry 9 }

vRtrIfBfdSessionLastDownTime     OBJECT-TYPE
    SYNTAX      TimeStamp
    MAX-ACCESS  read-only
    STATUS      obsolete
    DESCRIPTION
        "The value of vRtrIfBfdSessionLastDownTime indicates the system time
         when this session last went down."
    ::= { vRtrIfBfdSessionEntry 10 }

vRtrIfBfdSessionLastUpTime       OBJECT-TYPE
    SYNTAX      TimeStamp
    MAX-ACCESS  read-only
    STATUS      obsolete
    DESCRIPTION
        "The value of vRtrIfBfdSessionLastUpTime indicates the system time when
         this session last came up."
    ::= { vRtrIfBfdSessionEntry 11 }

vRtrIfBfdSessionUpCount          OBJECT-TYPE
    SYNTAX      Counter32
    MAX-ACCESS  read-only
    STATUS      obsolete
    DESCRIPTION
        "The value of vRtrIfBfdSessionUpCount indicates the number of times
         vRtrIfBfdSessionOperState changed from 'outOfService' to 'inService'."
    ::= { vRtrIfBfdSessionEntry 12 }

vRtrIfBfdSessionDownCount        OBJECT-TYPE
    SYNTAX      Counter32
    MAX-ACCESS  read-only
    STATUS      obsolete
    DESCRIPTION
        "The value of vRtrIfBfdSessionDownCount indicates the number of times
         vRtrIfBfdSessionOperState changed from 'inService' to 'outOfService'."
    ::= { vRtrIfBfdSessionEntry 13 }

vRtrIfBfdSessionLclDisc          OBJECT-TYPE
    SYNTAX      Unsigned32
    MAX-ACCESS  read-only
    STATUS      obsolete
    DESCRIPTION
        "The value of vRtrIfBfdSessionLclDisc indicates the unique local
         discriminator for this session."
    ::= { vRtrIfBfdSessionEntry 14 }

vRtrIfBfdSessionRemDisc          OBJECT-TYPE
    SYNTAX      Unsigned32
    MAX-ACCESS  read-only
    STATUS      obsolete
    DESCRIPTION
        "The value of vRtrIfBfdSessionRemDisc indicates the remote
         discriminator for this session."
    ::= { vRtrIfBfdSessionEntry 15 }

vRtrIfBfdSessionProtocols        OBJECT-TYPE
    SYNTAX      BITS {
        ospfv2      (0),
        pim         (1),
        isis        (2),
        staticRoute (3),
        mcRing      (4),
        rsvp        (5),
        bgp         (6),
        vrrp        (7),
        srrp        (8),
        mcep        (9),
        ldp         (10),
        ipsecTunnel (11),
        ospfv3      (12),
        mcIpsec     (13),
        mcMobile    (14),
        mplsTp      (15),
        lag         (16)
    }
    MAX-ACCESS  read-only
    STATUS      obsolete
    DESCRIPTION
        "The value of vRtrIfBfdSessionProtocols indicates which protocols are
         using this BFD session."
    ::= { vRtrIfBfdSessionEntry 16 }

vRtrIfBfdSessionTxInterval       OBJECT-TYPE
    SYNTAX      Unsigned32
    UNITS       "milliseconds"
    MAX-ACCESS  read-only
    STATUS      obsolete
    DESCRIPTION
        "The value of vRtrIfBfdSessionTxInterval indicates the negotiated
         transmit interval. This value is the minimum of the local node's
         'vRtrIfBfdExtTransmitInterval' and the remote node's receive interval."
    ::= { vRtrIfBfdSessionEntry 17 }

vRtrIfBfdSessionRxInterval       OBJECT-TYPE
    SYNTAX      Unsigned32
    UNITS       "milliseconds"
    MAX-ACCESS  read-only
    STATUS      obsolete
    DESCRIPTION
        "The value of vRtrIfBfdSessionRxInterval indicates the negotiated
         receive interval. This value is the minimum of the local node's
         'vRtrIfBfdExtReceiveInterval' and the remote node's transmit interval."
    ::= { vRtrIfBfdSessionEntry 18 }

vRtrIfBfdSessionType             OBJECT-TYPE
    SYNTAX      INTEGER {
        iom   (1),
        cpm   (2),
        cpmNp (3)
    }
    MAX-ACCESS  read-only
    STATUS      obsolete
    DESCRIPTION
        "The value of vRtrIfBfdSessionType indicates the termination of the BFD
         session, as follows:
             'iom (1)'   - termination on the IOM card main processor,
             'cpm (2)'   - termination on the CPM card main processor,
             'cpmNp (3)' - termination on the CPM card Network Processor."
    ::= { vRtrIfBfdSessionEntry 19 }

vRtrIfBfdSessionVerMismatch      OBJECT-TYPE
    SYNTAX      Counter32
    MAX-ACCESS  read-only
    STATUS      obsolete
    DESCRIPTION
        "The value of vRtrIfBfdSessionVerMismatch indicates the number of
         version mismatch errors for the bfd session."
    ::= { vRtrIfBfdSessionEntry 20 }

vRtrIfBfdSessionTimeSinceLastRx  OBJECT-TYPE
    SYNTAX      Unsigned32
    UNITS       "milliseconds"
    MAX-ACCESS  read-only
    STATUS      obsolete
    DESCRIPTION
        "The value of vRtrIfBfdSessionTimeSinceLastRx indicates the number of
         milliseconds elapsed since the most recent message was received on the
         BFD session.  If the session is down, zero is returned.

         This object is applicable to sessions with vRtrIfBfdSessionType equal
         to 'cpmNp(3)'.  Otherwise, zero is returned."
    ::= { vRtrIfBfdSessionEntry 21 }

vRtrIfBfdSessionTimeSinceLastTx  OBJECT-TYPE
    SYNTAX      Unsigned32
    UNITS       "milliseconds"
    MAX-ACCESS  read-only
    STATUS      obsolete
    DESCRIPTION
        "The value of vRtrIfBfdSessionTimeSinceLastTx indicates the number of
         milliseconds elapsed since the most recent message was transmitted on
         the BFD session.  If the session is down, zero is returned.

         This object is applicable to sessions with vRtrIfBfdSessionType equal
         to 'cpmNp(3)'.  Otherwise, zero is returned."
    ::= { vRtrIfBfdSessionEntry 22 }

vRtrIfDHCP6TableLastChanged      OBJECT-TYPE
    SYNTAX      TimeStamp
    MAX-ACCESS  read-only
    STATUS      current
    DESCRIPTION
        "The value of the object vRtrIfDHCP6TableLastChanged indicates the time
         of the last change to any row of vRtrIfDHCP6Table"
    ::= { tmnxVRtrObjs 35 }

vRtrIfDHCP6Table                 OBJECT-TYPE
    SYNTAX      SEQUENCE OF VRtrIfDHCP6Entry
    MAX-ACCESS  not-accessible
    STATUS      current
    DESCRIPTION
        "The vRtrIfDHCP6Table is used to configure the interface parameters for
         DHCP6."
    ::= { tmnxVRtrObjs 36 }

vRtrIfDHCP6Entry                 OBJECT-TYPE
    SYNTAX      VRtrIfDHCP6Entry
    MAX-ACCESS  not-accessible
    STATUS      current
    DESCRIPTION
        "Each row entry represents information related to DHCP6 for a virtual
         router interface in the system.

         Entries cannot be created and deleted via SNMP SET operations."
    AUGMENTS    { vRtrIfEntry }
    ::= { vRtrIfDHCP6Table 1 }

VRtrIfDHCP6Entry                 ::= SEQUENCE
{
    vRtrIfDHCP6LastChanged           TimeStamp,
    vRtrIfDHCP6AdminState            TmnxAdminState,
    vRtrIfDHCP6OperState             INTEGER,
    vRtrIfDHCP6Description           TItemDescription,
    vRtrIfDHCP6RelayServer1          InetAddressIPv6z,
    vRtrIfDHCP6RelayServer2          InetAddressIPv6z,
    vRtrIfDHCP6RelayServer3          InetAddressIPv6z,
    vRtrIfDHCP6RelayServer4          InetAddressIPv6z,
    vRtrIfDHCP6RelayServer5          InetAddressIPv6z,
    vRtrIfDHCP6RelayServer6          InetAddressIPv6z,
    vRtrIfDHCP6RelayServer7          InetAddressIPv6z,
    vRtrIfDHCP6RelayServer8          InetAddressIPv6z,
    vRtrIfDHCP6RelayItfIdOption      INTEGER,
    vRtrIfDHCP6LeasePopulate         Unsigned32,
    vRtrIfDHCP6CurrLeasePopulate     Unsigned32,
    vRtrIfDHCP6SourceAddress         InetAddressIPv6,
    vRtrIfDHCP6EnableNgbrResolution  TruthValue,
    vRtrIfDHCP6RemoteIdOption        TruthValue,
    vRtrIfDHCP6PfxdAdminState        INTEGER,
    vRtrIfDHCP6ServerMaxLeaseStates  Unsigned32,
    vRtrIfDHCP6CurrServerLeaseStates Unsigned32,
    vRtrIfDHCP6ItfIdString           DisplayString,
    vRtrIfDHCP6ProxyAdminState       TmnxAdminState,
    vRtrIfDHCP6ProxyRenewTimer       Unsigned32,
    vRtrIfDHCP6ProxyRebindTimer      Unsigned32,
    vRtrIfDHCP6ProxyValidLifetime    Unsigned32,
    vRtrIfDHCP6ProxyPrefLifetime     Unsigned32,
    vRtrIfDHCP6ProxyApplications     BITS,
    vRtrIfDHCP6UserDb                TNamedItemOrEmpty,
    vRtrIfDHCP6LocalDhcpServerName   TNamedItemOrEmpty,
    vRtrIfDHCP6RelayApplications     BITS,
    vRtrIfDHCP6LinkAddress           InetAddressIPv6,
    vRtrIfDHCP6RoutePopulatePd       TruthValue,
    vRtrIfDHCP6RoutePopulateNa       TruthValue,
    vRtrIfDHCP6RoutePopulateTa       TruthValue,
    vRtrIfDHCP6RoutePopulateExcl     TruthValue,
    vRtrIfDHCP6PythonPolicy          TNamedItemOrEmpty,
    vRtrIfDHCP6FilterId              TDHCPFilterID,
    vRtrIfDHCP6SnpgAdminState        TmnxAdminState,
    vRtrIfDHCP6ASelSlctDly           Integer32,
    vRtrIfDHCP6ASelPref              Integer32,
    vRtrIfDHCP6ASelClntMac           INTEGER,
    vRtrIfDHCP6ASelClntMacSlctDly    Integer32,
    vRtrIfDHCP6ASelClntMacPref       Integer32,
    vRtrIfDHCP6LseSplitAdminState    TmnxAdminState,
    vRtrIfDHCP6LseSplitValidLifetime Unsigned32,
    vRtrIfDHCP6AllowClntIdChng       TruthValue,
    vRtrIfDHCP6RelayReconfigureWoLse TruthValue
}

vRtrIfDHCP6LastChanged           OBJECT-TYPE
    SYNTAX      TimeStamp
    MAX-ACCESS  read-only
    STATUS      current
    DESCRIPTION
        "The value of the object vRtrIfDHCP6LastChanged indicates the time of
         the last change to this row of VRtrIfDHCP6Entry."
    ::= { vRtrIfDHCP6Entry 1 }

vRtrIfDHCP6AdminState            OBJECT-TYPE
    SYNTAX      TmnxAdminState
    MAX-ACCESS  read-create
    STATUS      current
    DESCRIPTION
        "The value of the object vRtrIfDHCP6AdminState specifies the desired
         administrative status of the DHCP6 relay agent on this interface.

         The value can only be set to inService if the value of vRtrIfType is
         serviceIesGroup. The value noop(3) is never allowed."
    DEFVAL      { outOfService }
    ::= { vRtrIfDHCP6Entry 2 }

vRtrIfDHCP6OperState             OBJECT-TYPE
    SYNTAX      INTEGER {
        up                 (1),
        down               (2),
        noIPv6Pfx          (3),
        noServerConfigured (4),
        noValidSourceAddr  (5)
    }
    MAX-ACCESS  read-only
    STATUS      current
    DESCRIPTION
        "The value of the object vRtrIfDHCP6OperState indicates the current
         operational state of the DHCP6 relay agent on this interface.
         Following value are possible:
         up (1)           - the DHCP6 relay agent is running.

         down (2),        - the DHCP6 relay agent is administratively disabled.

         noIPv6Pfx (3),   - the DHCP6 relay agent cannot be operational as
                            no ipv6 prefix is assigned to this link.

         noServerConfigured(4) - the DHCP6 relay agent cannot be operational
                                 as no DHCP6 servers are configured.
         noValidSourceAddr(5)  - the DHCP6 relay agent cannot be operational
                                 because a source address has been configured
                                 and the address is not local to this node."
    ::= { vRtrIfDHCP6Entry 3 }

vRtrIfDHCP6Description           OBJECT-TYPE
    SYNTAX      TItemDescription
    MAX-ACCESS  read-create
    STATUS      current
    DESCRIPTION
        "The value of the object vRtrIfDHCP6Description specifies a user
         provided description string for DHCP6 relay agent on this virtual
         router interface. It can consist of any printable, seven-bit ASCII
         characters up to 80 characters in length."
    DEFVAL      { ''H }
    ::= { vRtrIfDHCP6Entry 4 }

vRtrIfDHCP6RelayServer1          OBJECT-TYPE
    SYNTAX      InetAddressIPv6z
    MAX-ACCESS  read-create
    STATUS      current
    DESCRIPTION
        "The value of the object vRtrIfDHCP6RelayServer1 specifies the first
         DHCP6 server where the DHCP6 requests will be forwarded to."
    DEFVAL      { '0000000000000000000000000000000000000000'H }
    ::= { vRtrIfDHCP6Entry 5 }

vRtrIfDHCP6RelayServer2          OBJECT-TYPE
    SYNTAX      InetAddressIPv6z
    MAX-ACCESS  read-create
    STATUS      current
    DESCRIPTION
        "The value of the object vRtrIfDHCP6RelayServer2 specifies the 2nd
         DHCP6 server where the DHCP6 requests will be forwarded to."
    DEFVAL      { '0000000000000000000000000000000000000000'H }
    ::= { vRtrIfDHCP6Entry 6 }

vRtrIfDHCP6RelayServer3          OBJECT-TYPE
    SYNTAX      InetAddressIPv6z
    MAX-ACCESS  read-create
    STATUS      current
    DESCRIPTION
        "The value of the object vRtrIfDHCP6RelayServer3 specifies the 3rd
         DHCP6 server where the DHCP6 requests will be forwarded to."
    DEFVAL      { '0000000000000000000000000000000000000000'H }
    ::= { vRtrIfDHCP6Entry 7 }

vRtrIfDHCP6RelayServer4          OBJECT-TYPE
    SYNTAX      InetAddressIPv6z
    MAX-ACCESS  read-create
    STATUS      current
    DESCRIPTION
        "The value of the object vRtrIfDHCP6RelayServer4 specifies the 4rd
         DHCP6 server where the DHCP6 requests will be forwarded to."
    DEFVAL      { '0000000000000000000000000000000000000000'H }
    ::= { vRtrIfDHCP6Entry 8 }

vRtrIfDHCP6RelayServer5          OBJECT-TYPE
    SYNTAX      InetAddressIPv6z
    MAX-ACCESS  read-create
    STATUS      current
    DESCRIPTION
        "The value of the object vRtrIfDHCP6RelayServer5 specifies the 5th
         DHCP6 server where the DHCP6 requests will be forwarded to."
    DEFVAL      { '0000000000000000000000000000000000000000'H }
    ::= { vRtrIfDHCP6Entry 9 }

vRtrIfDHCP6RelayServer6          OBJECT-TYPE
    SYNTAX      InetAddressIPv6z
    MAX-ACCESS  read-create
    STATUS      current
    DESCRIPTION
        "The value of the object vRtrIfDHCP6RelayServer6 specifies the 6th
         DHCP6 server where the DHCP6 requests will be forwarded to."
    DEFVAL      { '0000000000000000000000000000000000000000'H }
    ::= { vRtrIfDHCP6Entry 10 }

vRtrIfDHCP6RelayServer7          OBJECT-TYPE
    SYNTAX      InetAddressIPv6z
    MAX-ACCESS  read-create
    STATUS      current
    DESCRIPTION
        "The value of the object vRtrIfDHCP6RelayServer7 specifies the 7th
         DHCP6 server where the DHCP6 requests will be forwarded to."
    DEFVAL      { '0000000000000000000000000000000000000000'H }
    ::= { vRtrIfDHCP6Entry 11 }

vRtrIfDHCP6RelayServer8          OBJECT-TYPE
    SYNTAX      InetAddressIPv6z
    MAX-ACCESS  read-create
    STATUS      current
    DESCRIPTION
        "The value of the object vRtrIfDHCP6RelayServer8 specifies the 8th
         DHCP6 server where the DHCP6 requests will be forwarded to."
    DEFVAL      { '0000000000000000000000000000000000000000'H }
    ::= { vRtrIfDHCP6Entry 12 }

vRtrIfDHCP6RelayItfIdOption      OBJECT-TYPE
    SYNTAX      INTEGER {
        none       (0),
        ifIndex    (1),
        asciiTuple (2),
        sapId      (3),
        string     (4)
    }
    MAX-ACCESS  read-create
    STATUS      current
    DESCRIPTION
        "The value of the object vRtrIfDHCP6RelayItfIdOption specifies whether
         or not the interface-id option is added by the DHCP6 relay agent,
         and, if it is present, what information goes in it.
         If the value of this object is set to 'none', the option is not added
         by the relay agent. In all other cases the option is added to the relay
         message. The content of the option is defined as follows:
         - 'ifIndex'    - the value of the interface index is used.
         - 'asciiTuple' - the ASCII-encoded concatenated tuple consisting of the
             - access-node-identifier
             - service-id
             - interface name
             - SAP-id (only if the value of vRtrIfType is 'serviceIesGroup')
         - 'sapId'      - the ASCII-encoded SAP-id is used.
         - 'string'     - the value of the object vRtrIfDHCP6ItfIdString
                          is used.

         If the value of vRtrIfType, associated with this interface, has a
         value of 'serviceIesGroup(7)' or 'serviceVprnGroup(9)', the value of
         the object vRtrIfDHCP6RelayItfIdOption may also be included in the
         RADIUS authentication request sent by the DHCPv6 proxy server."
    DEFVAL      { none }
    ::= { vRtrIfDHCP6Entry 13 }

vRtrIfDHCP6LeasePopulate         OBJECT-TYPE
    SYNTAX      Unsigned32 (0..32767)
    MAX-ACCESS  read-create
    STATUS      current
    DESCRIPTION
        "The value of the object vRtrIfDHCP6LeasePopulate specifies the maximum
         number of lease states allocated by the DHCP6 relay function, allowed
         on this interface."
    DEFVAL      { 0 }
    ::= { vRtrIfDHCP6Entry 14 }

vRtrIfDHCP6CurrLeasePopulate     OBJECT-TYPE
    SYNTAX      Unsigned32 (0..32767)
    MAX-ACCESS  read-only
    STATUS      current
    DESCRIPTION
        "The value of the object vRtrIfDHCP6CurrLeasePopulate indicates the
         number of lease states currently allocated on this interface by the
         DHCP6 relay function."
    ::= { vRtrIfDHCP6Entry 15 }

vRtrIfDHCP6SourceAddress         OBJECT-TYPE
    SYNTAX      InetAddressIPv6
    MAX-ACCESS  read-create
    STATUS      current
    DESCRIPTION
        "The value of the object vRtrIfDHCP6SourceAddress specifies the IPv6
         address that will be used by the DHCP6 relay agent as source IP
         address in all messages sent to the DHCP6 servers.
         If set to ::, the system will use the IPv6 address assigned on the
         link on which the relay message is sent out, if such an address is
         defined. As a last resort the system IPv6 address is taken."
    DEFVAL      { '00000000000000000000000000000000'H }
    ::= { vRtrIfDHCP6Entry 16 }

vRtrIfDHCP6EnableNgbrResolution  OBJECT-TYPE
    SYNTAX      TruthValue
    MAX-ACCESS  read-create
    STATUS      current
    DESCRIPTION
        "The value of the object vRtrIfDHCP6EnableNgbrResolution specifies
         whether or not neighbor resolution via DHCP6 Relay must be enabled on
         this interface. This feature is similar to the arp-populate feature in
         ipv4."
    DEFVAL      { false }
    ::= { vRtrIfDHCP6Entry 17 }

vRtrIfDHCP6RemoteIdOption        OBJECT-TYPE
    SYNTAX      TruthValue
    MAX-ACCESS  read-create
    STATUS      current
    DESCRIPTION
        "The value of the object vRtrIfDHCP6RemoteIdOption specifies whether or
         not the remote Id option is sent to the DHCP6 server. The client DUID
         is used as remoteId.

         If the value of vRtrIfType, associated with this interface, has a
         value of 'serviceIesGroup(7)' or 'serviceVprnGroup(9)', the value of
         the object vRtrIfDHCP6RemoteIdOption may also be included in the
         RADIUS authentication request sent by the DHCPv6 proxy server."
    DEFVAL      { false }
    ::= { vRtrIfDHCP6Entry 18 }

vRtrIfDHCP6PfxdAdminState        OBJECT-TYPE
    SYNTAX      INTEGER {
        enabled  (1),
        disabled (2)
    }
    MAX-ACCESS  read-create
    STATUS      current
    DESCRIPTION
        "The value of the object vRtrIfDHCP6PfxdAdminState specifies the
         administrative state of the row. If set to enabled, this IPv6 prefix
         will be delegated by the system."
    DEFVAL      { disabled }
    ::= { vRtrIfDHCP6Entry 19 }

vRtrIfDHCP6ServerMaxLeaseStates  OBJECT-TYPE
    SYNTAX      Unsigned32 (0..8000)
    MAX-ACCESS  read-create
    STATUS      current
    DESCRIPTION
        "The value of the object vRtrIfDHCP6ServerMaxLeaseStates specifies the
         maximum number of lease states installed by the DHCP6 server function
         allowed on this interface."
    DEFVAL      { 8000 }
    ::= { vRtrIfDHCP6Entry 20 }

vRtrIfDHCP6CurrServerLeaseStates OBJECT-TYPE
    SYNTAX      Unsigned32 (0..8000)
    MAX-ACCESS  read-only
    STATUS      current
    DESCRIPTION
        "The value of the object vRtrIfDHCP6CurrServerLeaseStates indicates the
         number of lease states currently allocated on this interface by the
         DHCP6 server function."
    ::= { vRtrIfDHCP6Entry 21 }

vRtrIfDHCP6ItfIdString           OBJECT-TYPE
    SYNTAX      DisplayString (SIZE (0..80))
    MAX-ACCESS  read-create
    STATUS      current
    DESCRIPTION
        "The value of the object vRtrIfDHCP6ItfIdString specifies the string
         that will be put in the interface-id option added by the relay agent.
         This value is only meaningful if the object
         vRtrIfDHCP6RelayItfIdOption is set to string(4)."
    ::= { vRtrIfDHCP6Entry 22 }

vRtrIfDHCP6ProxyAdminState       OBJECT-TYPE
    SYNTAX      TmnxAdminState
    MAX-ACCESS  read-create
    STATUS      current
    DESCRIPTION
        "The value of vRtrIfDHCP6ProxyAdminState specifies the desired
         administrative state of the IPv6 Router Advertisements."
    DEFVAL      { outOfService }
    ::= { vRtrIfDHCP6Entry 23 }

vRtrIfDHCP6ProxyRenewTimer       OBJECT-TYPE
    SYNTAX      Unsigned32 (0..604800)
    UNITS       "seconds"
    MAX-ACCESS  read-create
    STATUS      current
    DESCRIPTION
        "The value of vRtrIfDHCP6ProxyRenewTimer specifies the renew-timer
         (T1).

         The time at which the client contacts the server from which the
         addresses in the IA_NA or IA_PD were obtained to extend the lifetimes
         of the addresses or prefixes assigned to the client."
    DEFVAL      { 1800 }
    ::= { vRtrIfDHCP6Entry 24 }

vRtrIfDHCP6ProxyRebindTimer      OBJECT-TYPE
    SYNTAX      Unsigned32 (0..1209600)
    UNITS       "seconds"
    MAX-ACCESS  read-create
    STATUS      current
    DESCRIPTION
        "The value of vRtrIfDHCP6ProxyRebindTimer specifies the rebind-timer
         (T2).

         The time at which the client contacts any available server to extend
         the lifetimes of the addresses or prefixes assigned to the client."
    DEFVAL      { 2880 }
    ::= { vRtrIfDHCP6Entry 25 }

vRtrIfDHCP6ProxyValidLifetime    OBJECT-TYPE
    SYNTAX      Unsigned32 (300..4294967295)
    UNITS       "seconds"
    MAX-ACCESS  read-create
    STATUS      current
    DESCRIPTION
        "The value of vRtrIfDHCP6ProxyValidLifetime specifies the valid
         lifetime for the IPv6 prefix or address in the option.

         A value of 0xFFFFFFFF represents infinity."
    DEFVAL      { 86400 }
    ::= { vRtrIfDHCP6Entry 26 }

vRtrIfDHCP6ProxyPrefLifetime     OBJECT-TYPE
    SYNTAX      Unsigned32 (300..4294967295)
    UNITS       "seconds"
    MAX-ACCESS  read-create
    STATUS      current
    DESCRIPTION
        "The value of vRtrIfDHCP6ProxyPrefLifetime specifies the preferred
         lifetime for the IPv6 prefix or address in the option. When preferred
         lifetime expires, then any derived addresses are deprecated.

         A value of 0xFFFFFFFF represents infinity."
    DEFVAL      { 3600 }
    ::= { vRtrIfDHCP6Entry 27 }

vRtrIfDHCP6ProxyApplications     OBJECT-TYPE
    SYNTAX      BITS {
        dhcp (0),
        ppp  (1)
    }
    MAX-ACCESS  read-create
    STATUS      current
    DESCRIPTION
        "The value of vRtrIfDHCP6ProxyApplications specifies the set of client
         applications that can make use of the DHCP proxy functionality on this
         interface."
    DEFVAL      { {dhcp} }
    ::= { vRtrIfDHCP6Entry 28 }

vRtrIfDHCP6UserDb                OBJECT-TYPE
    SYNTAX      TNamedItemOrEmpty
    MAX-ACCESS  read-create
    STATUS      current
    DESCRIPTION
        "The value of vRtrIfDHCP6UserDb specifies the local user database to
         authenticate against.

         If no authentication with the local user database is required, the
         value of this object must be set to the empty string."
    DEFVAL      { "" }
    ::= { vRtrIfDHCP6Entry 29 }

vRtrIfDHCP6LocalDhcpServerName   OBJECT-TYPE
    SYNTAX      TNamedItemOrEmpty
    MAX-ACCESS  read-create
    STATUS      current
    DESCRIPTION
        "The value of vRtrIfDHCP6LocalDhcpServerName specifies the local DHCP
         server that can be reached via this interface.

         The server itself is configured on virtual router level in object
         TIMETRA-DHCP-SERVER-MIB::tmnxDhcpServerCfgServerName. Assigning an
         ip-address to it is done here by linking it to an interface. A server
         can be linked to several interfaces on the same virtual router."
    DEFVAL      { ''H }
    ::= { vRtrIfDHCP6Entry 30 }

vRtrIfDHCP6RelayApplications     OBJECT-TYPE
    SYNTAX      BITS {
        dhcp (0),
        ppp  (1)
    }
    MAX-ACCESS  read-create
    STATUS      current
    DESCRIPTION
        "The value of vRtrIfDHCP6RelayApplications specifies the set of client
         applications that can make use of the DHCP relay functionality on this
         interface. This object can only be set when the value of vRtrIfType,
         associated with this interface, has a value of 'serviceIesGroup(7)'
         'serviceVprnGroup(9)', or for retailer subscriber interfaces. Unless
         on a subscriber interface, the object cannot be set to all zero, i.e.
         at least one application must be specified."
    DEFVAL      { {dhcp} }
    ::= { vRtrIfDHCP6Entry 31 }

vRtrIfDHCP6LinkAddress           OBJECT-TYPE
    SYNTAX      InetAddressIPv6
    MAX-ACCESS  read-create
    STATUS      current
    DESCRIPTION
        "The value of the object vRtrIfDHCP6LinkAddress specifies the ipv6
         address that will be used by the DHCP6 relay agent as link address in
         all messages sent to the DHCP6 servers.
         If set to ::, the system determines the link address
         based on the group interface configuration.

         This object can only be set when vRtrIfType is either
         'serviceIesGroup(7)' or 'serviceVprnGroup(9)'."
    DEFVAL      { '00000000000000000000000000000000'H }
    ::= { vRtrIfDHCP6Entry 32 }

vRtrIfDHCP6RoutePopulatePd       OBJECT-TYPE
    SYNTAX      TruthValue
    MAX-ACCESS  read-create
    STATUS      current
    DESCRIPTION
        "The value of the object vRtrIfDHCP6RoutePopulatePd specifies whether
         or not route-population PD via DHCP6 Relay must be enabled on this
         interface."
    DEFVAL      { false }
    ::= { vRtrIfDHCP6Entry 33 }

vRtrIfDHCP6RoutePopulateNa       OBJECT-TYPE
    SYNTAX      TruthValue
    MAX-ACCESS  read-create
    STATUS      current
    DESCRIPTION
        "The value of the object vRtrIfDHCP6RoutePopulateNa specifies whether
         or not route-population NA via DHCP6 Relay must be enabled on this
         interface."
    DEFVAL      { false }
    ::= { vRtrIfDHCP6Entry 34 }

vRtrIfDHCP6RoutePopulateTa       OBJECT-TYPE
    SYNTAX      TruthValue
    MAX-ACCESS  read-create
    STATUS      current
    DESCRIPTION
        "The value of the object vRtrIfDHCP6RoutePopulateTa specifies whether
         or not route-population TA via DHCP6 Relay must be enabled on this
         interface."
    DEFVAL      { false }
    ::= { vRtrIfDHCP6Entry 35 }

vRtrIfDHCP6RoutePopulateExcl     OBJECT-TYPE
    SYNTAX      TruthValue
    MAX-ACCESS  read-create
    STATUS      current
    DESCRIPTION
        "The value of the object vRtrIfDHCP6RoutePopulateExcl specifies whether
         or not black-hole routers should be populated based on the prefix
         exclude option (as per RFC 6603).

         Only applicable when vRtrIfDHCP6RoutePopulatePd is set to true (1)."
    DEFVAL      { false }
    ::= { vRtrIfDHCP6Entry 36 }

vRtrIfDHCP6PythonPolicy          OBJECT-TYPE
    SYNTAX      TNamedItemOrEmpty
    MAX-ACCESS  read-create
    STATUS      current
    DESCRIPTION
        "The value vRtrIfDHCP6PythonPolicy specifies the name of the Python
         policy used on this interface.

         The Python policy referenced here needs to exist in the
         TIMETRA-PYTHON-MIB::tmnxPythonPolicyTable."
    DEFVAL      { "" }
    ::= { vRtrIfDHCP6Entry 37 }

vRtrIfDHCP6FilterId              OBJECT-TYPE
    SYNTAX      TDHCPFilterID
    MAX-ACCESS  read-create
    STATUS      current
    DESCRIPTION
        "The value of vRtrIfDHCP6FilterId specifies the DHCP6 filter to apply.

         If no filtering is required, then a value of zero (0) must be set."
    DEFVAL      { 0 }
    ::= { vRtrIfDHCP6Entry 38 }

vRtrIfDHCP6SnpgAdminState        OBJECT-TYPE
    SYNTAX      TmnxAdminState
    MAX-ACCESS  read-create
    STATUS      current
    DESCRIPTION
        "The value of vRtrIfDHCP6SnpgAdminState specifies the desired
         administrative state of the DHCP6 Snooping."
    DEFVAL      { outOfService }
    ::= { vRtrIfDHCP6Entry 39 }

vRtrIfDHCP6ASelSlctDly           OBJECT-TYPE
    SYNTAX      Integer32 (0..100)
    UNITS       "deci-seconds"
    MAX-ACCESS  read-create
    STATUS      current
    DESCRIPTION
        "The value of vRtrIfDHCP6ASelSlctDly specifies the default  amount of
         time to delay DHCPv6 Solicit messages relayed  to any server.

         This can be overruled by more specific settings per server address or
         client subset."
    DEFVAL      { 0 }
    ::= { vRtrIfDHCP6Entry 40 }

vRtrIfDHCP6ASelPref              OBJECT-TYPE
    SYNTAX      Integer32 (-1..255)
    MAX-ACCESS  read-create
    STATUS      current
    DESCRIPTION
        "The value of vRtrIfDHCP6ASelPref specifies the default  value for the
         Preference option inserted when a DHCPv6 Reply message is relayed to
         clients.

         This can be overruled by more specific settings per server address or
         client subset."
    DEFVAL      { -1 }
    ::= { vRtrIfDHCP6Entry 41 }

vRtrIfDHCP6ASelClntMac           OBJECT-TYPE
    SYNTAX      INTEGER {
        none (0),
        odd  (1),
        even (2)
    }
    MAX-ACCESS  read-create
    STATUS      current
    DESCRIPTION
        "The value of vRtrIfDHCP6ASelClntMac specifies the MAC filter for a
         client subset which require a specific setting for  DHCPv6 Advertise
         selection."
    DEFVAL      { none }
    ::= { vRtrIfDHCP6Entry 42 }

vRtrIfDHCP6ASelClntMacSlctDly    OBJECT-TYPE
    SYNTAX      Integer32 (0..100)
    UNITS       "deci-seconds"
    MAX-ACCESS  read-create
    STATUS      current
    DESCRIPTION
        "The value of vRtrIfDHCP6ASelClntMacSlctDly specifies the amount of
         time to delay DHCPv6 Solicit messages relayed to any server."
    DEFVAL      { 0 }
    ::= { vRtrIfDHCP6Entry 43 }

vRtrIfDHCP6ASelClntMacPref       OBJECT-TYPE
    SYNTAX      Integer32 (-1..255)
    MAX-ACCESS  read-create
    STATUS      current
    DESCRIPTION
        "The value of vRtrIfDHCP6ASelClntMacPref specifies the value for the
         Preference option inserted when a DHCPv6 Reply message is  relayed to
         clients."
    DEFVAL      { -1 }
    ::= { vRtrIfDHCP6Entry 44 }

vRtrIfDHCP6LseSplitAdminState    OBJECT-TYPE
    SYNTAX      TmnxAdminState
    MAX-ACCESS  read-create
    STATUS      current
    DESCRIPTION
        "The value of vRtrIfDHCP6LseSplitAdminState specifies the desired
         administrative status of the DHCP6 relay lease split on this
         interface.

         The value noop(3) is never allowed."
    DEFVAL      { outOfService }
    ::= { vRtrIfDHCP6Entry 45 }

vRtrIfDHCP6LseSplitValidLifetime OBJECT-TYPE
    SYNTAX      Unsigned32 (300..315446399)
    UNITS       "seconds"
    MAX-ACCESS  read-create
    STATUS      current
    DESCRIPTION
        "The value of vRtrIfDHCP6LseSplitValidLifetime specifies the valid
         lifetime for the IPv6 lease split in the option."
    DEFVAL      { 3600 }
    ::= { vRtrIfDHCP6Entry 46 }

vRtrIfDHCP6AllowClntIdChng       OBJECT-TYPE
    SYNTAX      TruthValue
    MAX-ACCESS  read-create
    STATUS      current
    DESCRIPTION
        "The value of the object vRtrIfDHCP6AllowClntIdChng specifies whether
         or not it is allowed for the system to change the client ID."
    DEFVAL      { false }
    ::= { vRtrIfDHCP6Entry 47 }

vRtrIfDHCP6RelayReconfigureWoLse OBJECT-TYPE
    SYNTAX      TruthValue
    MAX-ACCESS  read-create
    STATUS      current
    DESCRIPTION
        "The value of vRtrIfDHCP6RelayReconfigureWoLse specifies whether it is
         allowed to relay Reconfigure messages  to DHCPv6 clients without lease
         state."
    DEFVAL      { false }
    ::= { vRtrIfDHCP6Entry 48 }

vRtrIfGlobalIndexTable           OBJECT-TYPE
    SYNTAX      SEQUENCE OF VRtrIfGlobalIndexEntry
    MAX-ACCESS  not-accessible
    STATUS      current
    DESCRIPTION
        "This is a read-only table, each row of which represents a one to one
         equivalence between a unique system wide router interface index
         (vRtrIfGlobalIndex) and its corresponding virtual router ID (vRtrID)
         and index in the vRtrIfTable (vRtrIfIndex)."
    ::= { tmnxVRtrObjs 37 }

vRtrIfGlobalIndexEntry           OBJECT-TYPE
    SYNTAX      VRtrIfGlobalIndexEntry
    MAX-ACCESS  not-accessible
    STATUS      current
    DESCRIPTION
        "Each row entry in the vRtrIfGlobalIndexTable corresponds to a row in
         the vRtrIfTable. When an entry is created or deleted in the
         vRtrIfTable, a corresponding entry is created or deleted in this
         table."
    INDEX       { vRtrIfGlobalIndex }
    ::= { vRtrIfGlobalIndexTable 1 }

VRtrIfGlobalIndexEntry           ::= SEQUENCE
{
    vRtrIfGlobalIndexvRtrID          TmnxVRtrID,
    vRtrIfGlobalIndexvRtrIfIndex     InterfaceIndex
}

vRtrIfGlobalIndexvRtrID          OBJECT-TYPE
    SYNTAX      TmnxVRtrID
    MAX-ACCESS  read-only
    STATUS      current
    DESCRIPTION
        "The value of vRtrIfGlobalIndexvRtrID indicates the vRtrID that maps to
         the vRtrIfGlobalIndex. The combination of a vRtrID and a vRtrIfIndex
         correspond to a system wide unique vRtrIfGlobalIndex. This value
         represents the specific instance of virtual router which the
         vRtrIfGlobalIndex belongs to."
    ::= { vRtrIfGlobalIndexEntry 1 }

vRtrIfGlobalIndexvRtrIfIndex     OBJECT-TYPE
    SYNTAX      InterfaceIndex
    MAX-ACCESS  read-only
    STATUS      current
    DESCRIPTION
        "The value of vRtrIfGlobalIndexvRtrIfIndex gives the value of
         vRtrIfIndex for a row in the vRtrIfTable. This row corresponds to the
         virtual router interface that maps to the vRtrIfGlobalIndex. The
         combination of a vRtrID and a vRtrIfIndex correspond to a system wide
         unique vRtrIfGlobalIndex."
    ::= { vRtrIfGlobalIndexEntry 2 }

vRtrIfProxyNDTable               OBJECT-TYPE
    SYNTAX      SEQUENCE OF VRtrIfProxyNDEntry
    MAX-ACCESS  not-accessible
    STATUS      current
    DESCRIPTION
        "The vRtrIfProxyNDTable provides an extension to the vRtrIfTable. It
         has an entry for each virtual router interface configured in the
         system."
    ::= { tmnxVRtrObjs 38 }

vRtrIfProxyNDEntry               OBJECT-TYPE
    SYNTAX      VRtrIfProxyNDEntry
    MAX-ACCESS  not-accessible
    STATUS      current
    DESCRIPTION
        "Each row entry represents information related to Proxy Neighbor
         Discovery for a virtual router interface in the system.

         Entries cannot be created and deleted via SNMP SET operations."
    AUGMENTS    { vRtrIfEntry }
    ::= { vRtrIfProxyNDTable 1 }

VRtrIfProxyNDEntry               ::= SEQUENCE
{
    vRtrIfProxyNDLocal               TruthValue,
    vRtrIfProxyNDPolicy1             TPolicyStatementNameOrEmpty,
    vRtrIfProxyNDPolicy2             TPolicyStatementNameOrEmpty,
    vRtrIfProxyNDPolicy3             TPolicyStatementNameOrEmpty,
    vRtrIfProxyNDPolicy4             TPolicyStatementNameOrEmpty,
    vRtrIfProxyNDPolicy5             TPolicyStatementNameOrEmpty
}

vRtrIfProxyNDLocal               OBJECT-TYPE
    SYNTAX      TruthValue
    MAX-ACCESS  read-create
    STATUS      current
    DESCRIPTION
        "If the value of vRtrIfProxyNDLocal is set to 'true', local proxy
         Neighbor Discovery is enabled, that is, the interface will reply to
         Neighbor Solicitation requests when both the hosts are on the same
         subnet. In this case ICMP redirects will be disabled. If the value of
         vRtrIfProxyNDLocal is set to 'false', the interface will not reply to
         Neighbor Solicitation requests if both the hosts are on the same
         subnet."
    DEFVAL      { false }
    ::= { vRtrIfProxyNDEntry 1 }

vRtrIfProxyNDPolicy1             OBJECT-TYPE
    SYNTAX      TPolicyStatementNameOrEmpty
    MAX-ACCESS  read-create
    STATUS      current
    DESCRIPTION
        "The value of vRtrIfProxyNDPolicy1 specifies the first proxy ND policy
         for this interface. This policy determines networks and sources for
         which proxy ND will be attempted, when local proxy ND is enabled."
    DEFVAL      { ''H }
    ::= { vRtrIfProxyNDEntry 2 }

vRtrIfProxyNDPolicy2             OBJECT-TYPE
    SYNTAX      TPolicyStatementNameOrEmpty
    MAX-ACCESS  read-create
    STATUS      current
    DESCRIPTION
        "The value of vRtrIfProxyNDPolicy2 specifies the second proxy ND policy
         for this interface. This policy determines networks and sources for
         which proxy ND will be attempted, when local proxy ND is enabled."
    DEFVAL      { ''H }
    ::= { vRtrIfProxyNDEntry 3 }

vRtrIfProxyNDPolicy3             OBJECT-TYPE
    SYNTAX      TPolicyStatementNameOrEmpty
    MAX-ACCESS  read-create
    STATUS      current
    DESCRIPTION
        "The value of vRtrIfProxyNDPolicy3 specifies the third proxy ND policy
         for this interface. This policy determines networks and sources for
         which proxy ND will be attempted, when local proxy ND is enabled."
    DEFVAL      { ''H }
    ::= { vRtrIfProxyNDEntry 4 }

vRtrIfProxyNDPolicy4             OBJECT-TYPE
    SYNTAX      TPolicyStatementNameOrEmpty
    MAX-ACCESS  read-create
    STATUS      current
    DESCRIPTION
        "The value of vRtrIfProxyNDPolicy4 specifies the fourth proxy ND policy
         for this interface. This policy determines networks and sources for
         which proxy ND will be attempted, when local proxy ND is enabled."
    DEFVAL      { ''H }
    ::= { vRtrIfProxyNDEntry 5 }

vRtrIfProxyNDPolicy5             OBJECT-TYPE
    SYNTAX      TPolicyStatementNameOrEmpty
    MAX-ACCESS  read-create
    STATUS      current
    DESCRIPTION
        "The value of vRtrIfProxyNDPolicy5 specifies the fifth proxy ND policy
         for this interface. This policy determines networks and sources for
         which proxy ND will be attempted, when local proxy ND is enabled."
    DEFVAL      { ''H }
    ::= { vRtrIfProxyNDEntry 6 }

vRtrIfDHCP6PfxDelegationLstChgd  OBJECT-TYPE
    SYNTAX      TimeStamp
    MAX-ACCESS  read-only
    STATUS      current
    DESCRIPTION
        "The value of the object vRtrIfDHCP6PfxDelegationLstChgd indicates the
         Timestamp of the last change to any row the
         vRtrIfDHCP6PfxDelegationTable"
    ::= { tmnxVRtrObjs 39 }

vRtrIfDHCP6PfxDelegationTable    OBJECT-TYPE
    SYNTAX      SEQUENCE OF VRtrIfDHCP6PfxDelegationEntry
    MAX-ACCESS  not-accessible
    STATUS      current
    DESCRIPTION
        "The table vRtrIfDHCP6PfxDelegationTable is used to configure the
         feature of automated delegation of IPv6 prefixes using DHCP6.

         This feature is intended for delegating a long-lived prefix from a
         delegating router to a requesting router, where the delegating router
         does not require knowledge about the topology of the links in the
         network to which the prefixes will be assigned."
    ::= { tmnxVRtrObjs 40 }

vRtrIfDHCP6PfxDelegationEntry    OBJECT-TYPE
    SYNTAX      VRtrIfDHCP6PfxDelegationEntry
    MAX-ACCESS  not-accessible
    STATUS      current
    DESCRIPTION
        "Each row entry represents a delegated IPv6 prefix. Entries can be
         created and deleted via SNMP SET operations. Creation requires a SET
         request containing the vRtrRowStatus."
    INDEX       {
        vRtrID,
        vRtrIfIndex,
        vRtrIfDHCP6PfxdPrefix,
        vRtrIfDHCP6PfxdPrefixLen
    }
    ::= { vRtrIfDHCP6PfxDelegationTable 1 }

VRtrIfDHCP6PfxDelegationEntry    ::= SEQUENCE
{
    vRtrIfDHCP6PfxdPrefix            TmnxIpv6AddressAndPrefixAddress,
    vRtrIfDHCP6PfxdPrefixLen         TmnxIpv6AddressAndPrefixPrefix,
    vRtrIfDHCP6PfxdRowStatus         RowStatus,
    vRtrIfDHCP6PfxdLastChanged       TimeStamp,
    vRtrIfDHCP6PfxdDUID              OCTET STRING,
    vRtrIfDHCP6PfxdIAID              Unsigned32,
    vRtrIfDHCP6PfxdPrefLifetime      Unsigned32,
    vRtrIfDHCP6PfxdValidLifetime     Unsigned32
}

vRtrIfDHCP6PfxdPrefix            OBJECT-TYPE
    SYNTAX      TmnxIpv6AddressAndPrefixAddress
    MAX-ACCESS  not-accessible
    STATUS      current
    DESCRIPTION
        "The value of the object vRtrIfDHCP6PfxdPrefix specifies, together with
         the object vRtrIfDHCP6PfxdPrefixLen the ipv6 prefix that will be
         delegated."
    ::= { vRtrIfDHCP6PfxDelegationEntry 1 }

vRtrIfDHCP6PfxdPrefixLen         OBJECT-TYPE
    SYNTAX      TmnxIpv6AddressAndPrefixPrefix
    MAX-ACCESS  not-accessible
    STATUS      current
    DESCRIPTION
        "The value of the object vRtrIfDHCP6PfxdPrefixLen specifies, together
         with the object vRtrIfDHCP6PfxdPrefix the ipv6 prefix that will be
         delegated by this system."
    ::= { vRtrIfDHCP6PfxDelegationEntry 2 }

vRtrIfDHCP6PfxdRowStatus         OBJECT-TYPE
    SYNTAX      RowStatus
    MAX-ACCESS  read-create
    STATUS      current
    DESCRIPTION
        "The value of the object vRtrIfDHCP6PfxdRowStatus specifies the Row
         status of this table row. This object is used to create or delete rows
         in this table.

         The only allowed values for this object are: active(1),
         createAndGo(4), and destroy(6)."
    ::= { vRtrIfDHCP6PfxDelegationEntry 3 }

vRtrIfDHCP6PfxdLastChanged       OBJECT-TYPE
    SYNTAX      TimeStamp
    MAX-ACCESS  read-only
    STATUS      current
    DESCRIPTION
        "The value of vRtrIfDHCP6PfxdLastChanged indicates the sysUpTime when
         any object of the row is last changed."
    ::= { vRtrIfDHCP6PfxDelegationEntry 4 }

vRtrIfDHCP6PfxdDUID              OBJECT-TYPE
    SYNTAX      OCTET STRING (SIZE (0..64))
    MAX-ACCESS  read-create
    STATUS      current
    DESCRIPTION
        "The value of the object vRtrIfDHCP6PfxdDUID specifies the ID of the
         requesting router. If set to a non zero value the prefix defined in
         this row will only be delegated to this router. If set to zero, the
         prefix will be delegated to any requesting router."
    DEFVAL      { ''H }
    ::= { vRtrIfDHCP6PfxDelegationEntry 6 }

vRtrIfDHCP6PfxdIAID              OBJECT-TYPE
    SYNTAX      Unsigned32
    MAX-ACCESS  read-create
    STATUS      current
    DESCRIPTION
        "The value of the object vRtrIfDHCP6PfxdIAID specifies the IAID from
         the requesting router that needs to match in order to delegate the
         prefix defined in this row.If set to 0 no match on the received IAID
         is done."
    DEFVAL      { 0 }
    ::= { vRtrIfDHCP6PfxDelegationEntry 7 }

vRtrIfDHCP6PfxdPrefLifetime      OBJECT-TYPE
    SYNTAX      Unsigned32 (0..4294967295)
    UNITS       "seconds"
    MAX-ACCESS  read-create
    STATUS      current
    DESCRIPTION
        "The value of the object vRtrIfDHCP6PfxdPrefLifetime specifies the time
         in seconds that this prefix remains preferred.

         The value of vRtrIfDHCP6PfxdPrefLifetime cannot be bigger then the
         value of vRtrIfDHCP6PfxdValidLifetime.

         The value 4294967295 is considered equal to infinity."
    DEFVAL      { 604800 }
    ::= { vRtrIfDHCP6PfxDelegationEntry 8 }

vRtrIfDHCP6PfxdValidLifetime     OBJECT-TYPE
    SYNTAX      Unsigned32 (0..4294967295)
    UNITS       "seconds"
    MAX-ACCESS  read-create
    STATUS      current
    DESCRIPTION
        "The value of the object vRtrIfDHCP6PfxdValidLifetime specifies the
         time in seconds that the prefix is valid. The value 4294967295 is
         considered equal to infinity."
    DEFVAL      { 2592000 }
    ::= { vRtrIfDHCP6PfxDelegationEntry 9 }

vRtrDHCP6DropStatTable           OBJECT-TYPE
    SYNTAX      SEQUENCE OF VRtrDHCP6DropStatEntry
    MAX-ACCESS  not-accessible
    STATUS      current
    DESCRIPTION
        "The vRtrDHCP6DropStatTable has an entry for each virtual router
         configured in the system."
    ::= { tmnxVRtrObjs 41 }

vRtrDHCP6DropStatEntry           OBJECT-TYPE
    SYNTAX      VRtrDHCP6DropStatEntry
    MAX-ACCESS  not-accessible
    STATUS      current
    DESCRIPTION
        "Each row entry represents a collection of DHCP6 drop reason statistics
         for a virtual router in the system.

         Entries cannot be created and deleted via SNMP SET operations."
    INDEX       {
        vRtrID,
        vRtrDHCP6DropStatReason
    }
    ::= { vRtrDHCP6DropStatTable 1 }

VRtrDHCP6DropStatEntry           ::= SEQUENCE
{
    vRtrDHCP6DropStatReason          INTEGER,
    vRtrDHCP6DropStatLastCleared     TimeStamp,
    vRtrDHCP6DropStatPktsDropped     Gauge32
}

vRtrDHCP6DropStatReason          OBJECT-TYPE
    SYNTAX      INTEGER {
        none                 (0),
        srcOperDown          (1),
        dstOperDown          (2),
        rlyReplyOnClientItf  (3),
        hopCount             (4),
        badRelayedMsg        (5),
        clientItfNotFound    (6),
        noMemory             (7),
        noGlobalPfx          (8),
        noSrcIp              (9),
        noRteToServer        (10),
        subMgmtUpdFail       (11),
        relayForw            (12),
        msgTooSmall          (13),
        msgNotForServer      (14),
        noServerId           (15),
        noClientId           (16),
        serverIdInClientMsg  (17),
        wrongServerId        (18),
        illegalUnicast       (19),
        illegalSrcIp         (20),
        pdMsgNotSupported    (21),
        nbrAddrsExceeded     (22),
        clientMacNotResolved (23),
        illegalAssignedAddr  (24),
        msgEncodingError     (25),
        rcoMsgNotSupported   (26),
        iaInInfoRequest      (27),
        noIaInClientMsg      (28),
        noAddrInConfirmMsg   (29),
        noRelayServers       (30),
        hostLockout          (31),
        noLinkAddress        (32),
        droppedByPython      (33),
        invalidForcedServer  (34),
        rcvOnSrrpBackupItf   (35),
        dhcpTransactNotFound (36),
        retailItfNotFound    (37),
        dropByDhcpFilter     (38),
        authenticationFailed (39),
        invalidForcedSrc     (40)
    }
    MAX-ACCESS  not-accessible
    STATUS      current
    DESCRIPTION
        "The object vRtrDHCP6DropStatReason indicates the drop reason for
         which the object vRtrDHCP6DropStatPktsDropped contains the counter.
         none
         srcOperDown            Dhcp6 oper state is not Up on src itf
         dstOperDown            Dhcp6 oper state is not Up on dst itf
         rlyReplyOnClientItf    Relay Reply Msg on Client Itf
         hopCount               Hop Count Limit reached
         badRelayedMsg          Missing Relay Msg option, or illegal msg type
         clientItfNotFound      Unable to determine destination client Itf
         noMemory               Out of Memory
         noGlobalPfx            No global Pfx on Client Itf
         noSrcIp                Unable to determine src Ip Addr
         noRteToServer          No route to server
         subMgmtUpdFail         Subscr. Mgmt. Update failed
         relayForw              Received Relay Forward Message
         msgTooSmall            Packet too small to contain valid dhcp6 msg
         msgNotForServer        Server cannot respond to this message
         noServerId             No Server Id option in msg from server
         noClientId             No Client Id option in msg from client
         serverIdInClientMsg    Server Id option in client msg
         wrongServerId          Server DUID in client msg does not match ours
         illegalUnicast         Client sent message to unicast while not
                                allowed
         illegalSrcIp           Client sent message with illegal src Ip
         pdMsgNotSupported      Client message type not supported in
                                pfx delegation
         nbrAddrsExceeded       Nbr of addrs or pfxs exceeds allowed
                                maximum in msg
         clientMacNotResolved   Unable to resolve client's mac address
         illegalAssignedAddr    The client was assigned an illegal address
         msgEncodingError       Illegal pfx length in a IA_PREFIX option
         rcoMsgNotSupported     Client message type not supported on rco
                                interfaces
         iaInInfoRequest        Info request holds IA options
         noIaInClientMsg        Client msg holds no IA options
         noAddrInConfirmMsg     No addresses in client confirm msg
         noRelayServers         No relay servers configured
         hostLockout            Blocked by host lockout
         noLinkAddress          No link address available
         droppedByPython        Either explicit or because of a Python
                                failure
         invalidForcedServer    The forced server configured in the
                                local user database is not configured on
                                the interface.
         rcvOnSrrpBackupItf     Packet ignored on SRRP backup interface
         dhcpTransactNotFound   A DHCP transaction is not found
         retailItfNotFound      Retail interface is not found
         dropByDhcpFilter       Packet dropped by DHCP filter
         authenticationFailed   The packet was rejected by authentication
         invalidForcedSrc       Forced source not configured on VRF"
    ::= { vRtrDHCP6DropStatEntry 1 }

vRtrDHCP6DropStatLastCleared     OBJECT-TYPE
    SYNTAX      TimeStamp
    MAX-ACCESS  read-only
    STATUS      current
    DESCRIPTION
        "The value of vRtrDHCP6DropStatLastCleared indicates the sysUpTime when
         the counters of this row were last reset. A value of zero for this
         object indicates that the counters have not been reset since the
         system has last been initialized."
    ::= { vRtrDHCP6DropStatEntry 2 }

vRtrDHCP6DropStatPktsDropped     OBJECT-TYPE
    SYNTAX      Gauge32
    MAX-ACCESS  read-only
    STATUS      current
    DESCRIPTION
        "The value of vRtrDHCP6DropStatPktsDropped indicates the number of
         DHCP6 packets were dropped for the reason described in
         vRtrDHCP6DropStatReason."
    ::= { vRtrDHCP6DropStatEntry 3 }

vRtrDHCP6MsgStatTable            OBJECT-TYPE
    SYNTAX      SEQUENCE OF VRtrDHCP6MsgStatEntry
    MAX-ACCESS  not-accessible
    STATUS      current
    DESCRIPTION
        "The vRtrDHCP6MsgStatTable has an entry for each virtual router
         configured in the system."
    ::= { tmnxVRtrObjs 42 }

vRtrDHCP6MsgStatEntry            OBJECT-TYPE
    SYNTAX      VRtrDHCP6MsgStatEntry
    MAX-ACCESS  not-accessible
    STATUS      current
    DESCRIPTION
        "Each row entry represents a collection of counters for each DHCP6
         message type for a virtual router in the system.

         Entries cannot be created and deleted via SNMP SET operations."
    INDEX       {
        vRtrID,
        vRtrDHCP6MsgStatsMsgType
    }
    ::= { vRtrDHCP6MsgStatTable 1 }

VRtrDHCP6MsgStatEntry            ::= SEQUENCE
{
    vRtrDHCP6MsgStatsMsgType         TmnxDHCP6MsgType,
    vRtrDHCP6MsgStatsLstClrd         TimeStamp,
    vRtrDHCP6MsgStatsRcvd            Gauge32,
    vRtrDHCP6MsgStatsSent            Gauge32,
    vRtrDHCP6MsgStatsDropped         Gauge32
}

vRtrDHCP6MsgStatsMsgType         OBJECT-TYPE
    SYNTAX      TmnxDHCP6MsgType
    MAX-ACCESS  not-accessible
    STATUS      current
    DESCRIPTION
        "The object vRtrDHCP6MsgStatsMsgType indicates the DHCP6 message type
         for which statistics are kept on a per vrtr basis."
    ::= { vRtrDHCP6MsgStatEntry 1 }

vRtrDHCP6MsgStatsLstClrd         OBJECT-TYPE
    SYNTAX      TimeStamp
    MAX-ACCESS  read-only
    STATUS      current
    DESCRIPTION
        "The value of vRtrDHCP6MsgStatsLstClrd indicates the sysUpTime when the
         counters of this row were last reset. A value of zero for this object
         indicates that the counters have not been reset since the system has
         last been initialized."
    ::= { vRtrDHCP6MsgStatEntry 2 }

vRtrDHCP6MsgStatsRcvd            OBJECT-TYPE
    SYNTAX      Gauge32
    MAX-ACCESS  read-only
    STATUS      current
    DESCRIPTION
        "The value of vRtrDHCP6MsgStatsRcvd indicates the number of DHCP6
         packets were received of the DHCP6 message type indicated by
         vRtrDHCP6MsgStatsMsgType."
    ::= { vRtrDHCP6MsgStatEntry 3 }

vRtrDHCP6MsgStatsSent            OBJECT-TYPE
    SYNTAX      Gauge32
    MAX-ACCESS  read-only
    STATUS      current
    DESCRIPTION
        "The value of vRtrDHCP6MsgStatsSent indicates the number of DHCP6
         packets were sent of the DHCP6 message type indicated by
         vRtrDHCP6MsgStatsMsgType."
    ::= { vRtrDHCP6MsgStatEntry 4 }

vRtrDHCP6MsgStatsDropped         OBJECT-TYPE
    SYNTAX      Gauge32
    MAX-ACCESS  read-only
    STATUS      current
    DESCRIPTION
        "The value of vRtrDHCP6MsgStatsDropped indicates the number of DHCP6
         packets were dropped of the DHCP6 message type indicated by
         vRtrDHCP6MsgStatsMsgType."
    ::= { vRtrDHCP6MsgStatEntry 5 }

vRtrIfIpcpTable                  OBJECT-TYPE
    SYNTAX      SEQUENCE OF VRtrIfIpcpEntry
    MAX-ACCESS  not-accessible
    STATUS      current
    DESCRIPTION
        "The vRtrIfIpcpTable table contains the configuration for IPCP
         interface configuration on the vRtrIfEntry with the same indices."
    ::= { tmnxVRtrObjs 43 }

vRtrIfIpcpEntry                  OBJECT-TYPE
    SYNTAX      VRtrIfIpcpEntry
    MAX-ACCESS  not-accessible
    STATUS      current
    DESCRIPTION
        "Each row entry represents the IPCP configuration for an interface.
         Entries are created and deleted when entries in the vRtrIfTable are
         created and deleted."
    AUGMENTS    { vRtrIfEntry }
    ::= { vRtrIfIpcpTable 1 }

VRtrIfIpcpEntry                  ::= SEQUENCE
{
    vRtrIfIpcpPeerAddrType           InetAddressType,
    vRtrIfIpcpPeerAddr               InetAddress,
    vRtrIfIpcpPriDnsAddrType         InetAddressType,
    vRtrIfIpcpPriDnsAddr             InetAddress,
    vRtrIfIpcpSecDnsAddrType         InetAddressType,
    vRtrIfIpcpSecDnsAddr             InetAddress
}

vRtrIfIpcpPeerAddrType           OBJECT-TYPE
    SYNTAX      InetAddressType
    MAX-ACCESS  read-create
    STATUS      current
    DESCRIPTION
        "The value of vRtrIfIpcpPeerAddrType specifies the type of
         vRtrIfIpcpPeerAddr, the remote peer's IP address.

         vRtrIfIpcpPeerAddrType can be set to non-default only when the
         following rules are met for objects in vRtrIfEntry with the same
         indices:
          - The value of vRtrIfType is set to serviceIes(3) or serviceVprn(5)
          - The value of tmnxPortEncapType in tmnxPortEntry indexed using
            the value of vRtrIfPortID is set to unknown (0) or nullEncap (1)
            or ipcpEncap (6)

         When the value of vRtrIfIpcpPeerAddrType is unknown, the value of
         vRtrIfIpcpPeerAddr is assumed to be of size 0."
    DEFVAL      { unknown }
    ::= { vRtrIfIpcpEntry 1 }

vRtrIfIpcpPeerAddr               OBJECT-TYPE
    SYNTAX      InetAddress (SIZE (0|4|16))
    MAX-ACCESS  read-create
    STATUS      current
    DESCRIPTION
        "The value of vRtrIfIpcpPeerAddr specifies the IP address that will be
         exchanged by IPCP, if applicable on a given interface, to configure
         the remote peer's IP address. The type of this address is specified by
         the value of vRtrIfIpcpPeerAddrType

         vRtrIfIpcpPeerAddr can be set to on-default only when the following
         rules are met for objects in vRtrIfEntry with the same indices:
          - The value of vRtrIfType is set to serviceIes(3) or serviceVprn(5)
          - The value of tmnxPortEncapType in tmnxPortEntry indexed using
            the value of vRtrIfPortID is set to unknown (0) or nullEncap (1)
            or ipcpEncap (6)"
    DEFVAL      { ''H }
    ::= { vRtrIfIpcpEntry 2 }

vRtrIfIpcpPriDnsAddrType         OBJECT-TYPE
    SYNTAX      InetAddressType
    MAX-ACCESS  read-create
    STATUS      current
    DESCRIPTION
        "The value of vRtrIfIpcpPriDnsAddrType specifies the type of
         vRtrIfIpcpPriDnsAddr, the IP address of the primary DNS to be used by
         the remote peer.

         vRtrIfIpcpPriDnsAddrType can be set to non-default only when the
         following rules are met for objects in vRtrIfEntry with the same
         indices:
          - The value of vRtrIfType is set to serviceIes(3) or serviceVprn(5)
          - The value of tmnxPortEncapType in tmnxPortEntry indexed using
            the value of vRtrIfPortID is set to unknown (0) or nullEncap (1)
            or ipcpEncap (6)

         When the value of vRtrIfIpcpPriDnsAddrType is unknown, the value of
         vRtrIfIpcpPriDnsAddr is assumed to be of size 0."
    DEFVAL      { unknown }
    ::= { vRtrIfIpcpEntry 3 }

vRtrIfIpcpPriDnsAddr             OBJECT-TYPE
    SYNTAX      InetAddress (SIZE (0|4|16))
    MAX-ACCESS  read-create
    STATUS      current
    DESCRIPTION
        "The value of vRtrIfIpcpPriDnsAddr specifies the IP address that will
         be exchanged by IPCP, if applicable on a given interface, to configure
         the primary DNS's IP address on the remote peer. The type of this
         address is specified by the value of vRtrIfIpcpPriDnsAddrType

         vRtrIfIpcpPriDnsAddr can be set to non-default only when the following
         rules are met for objects in vRtrIfEntry with the same indices:
          - The value of vRtrIfType is set to serviceIes(3) or serviceVprn(5)
          - The value of tmnxPortEncapType in tmnxPortEntry indexed using
            the value of vRtrIfPortID is set to unknown (0) or nullEncap (1)
            or ipcpEncap (6)"
    DEFVAL      { ''H }
    ::= { vRtrIfIpcpEntry 4 }

vRtrIfIpcpSecDnsAddrType         OBJECT-TYPE
    SYNTAX      InetAddressType
    MAX-ACCESS  read-create
    STATUS      current
    DESCRIPTION
        "The value of vRtrIfIpcpSecDnsAddrType specifies the type of
         vRtrIfIpcpSecDnsAddr, the IP address of the secondary DNS to be used
         by the remote peer.

         vRtrIfIpcpSecDnsAddrType can be set to non-default only when the
         following rules are met for objects in vRtrIfEntry with the same
         indices:
          - The value of vRtrIfType is set to serviceIes(3) or serviceVprn(5)
          - The value of tmnxPortEncapType in tmnxPortEntry indexed using
            the value of vRtrIfPortID is set to unknown (0) or nullEncap (1)
            or ipcpEncap (6)

         When the value of vRtrIfIpcpSecDnsAddrType is unknown, the value of
         vRtrIfIpcpSecDnsAddr is assumed to be of size 0."
    DEFVAL      { unknown }
    ::= { vRtrIfIpcpEntry 5 }

vRtrIfIpcpSecDnsAddr             OBJECT-TYPE
    SYNTAX      InetAddress (SIZE (0|4|16))
    MAX-ACCESS  read-create
    STATUS      current
    DESCRIPTION
        "The value of vRtrIfIpcpSecDnsAddr specifies the IP address that will
         be exchanged by IPCP, if applicable on a given interface, to configure
         the secondary DNS's IP address on the remote peer. The type of this
         address is specified by the value of vRtrIfIpcpSecDnsAddrType.

         vRtrIfIpcpSecDnsAddr can be set to non-default only when the following
         rules are met for objects in vRtrIfEntry with the same indices:
          - The value of vRtrIfType is set to serviceIes(3) or serviceVprn(5)
          - The value of tmnxPortEncapType in tmnxPortEntry indexed using
            the value of vRtrIfPortID is set to unknown (0) or nullEncap (1)
            or ipcpEncap (6)"
    DEFVAL      { ''H }
    ::= { vRtrIfIpcpEntry 6 }

vRtrInetStatRteCpeChkStatsTable  OBJECT-TYPE
    SYNTAX      SEQUENCE OF VRtrInetStatRteCpeChkStatsEntry
    MAX-ACCESS  not-accessible
    STATUS      current
    DESCRIPTION
        "The vRtrInetStatRteCpeChkStatsTable has an entry for each entry in the
         vRtrInetStaticRouteTable that has a non-default values set for the
         vRtrInetStaticRouteCpeAddrType and vRtrInetStaticRouteCpeAddr objects."
    ::= { tmnxVRtrObjs 44 }

vRtrInetStatRteCpeChkStatsEntry  OBJECT-TYPE
    SYNTAX      VRtrInetStatRteCpeChkStatsEntry
    MAX-ACCESS  not-accessible
    STATUS      current
    DESCRIPTION
        "Each row entry represents a collection of Customer Provided Equipment
         (CPE) availability statistics for a virtual router static route in the
         system with non-default values set for the
         vRtrInetStaticRouteCpeAddrType and vRtrInetStaticRouteCpeAddr objects.

         Entries cannot be created and deleted via SNMP SET operations."
    INDEX       {
        vRtrID,
        vRtrInetStaticRouteDestType,
        vRtrInetStaticRouteDest,
        vRtrInetStaticRouteDestPfxLen,
        vRtrInetStaticRouteIndex
    }
    ::= { vRtrInetStatRteCpeChkStatsTable 1 }

VRtrInetStatRteCpeChkStatsEntry  ::= SEQUENCE
{
    vRtrInetStatRteCpeChkUpTime      TimeTicks,
    vRtrInetStatRteCpeChkInPktCnt    Counter32,
    vRtrInetStatRteCpeChkOutPktCnt   Counter32,
    vRtrInetStatRteCpeChkDownTrans   Gauge32,
    vRtrInetStatRteCpeChkUpTrans     Gauge32,
    vRtrInetStatRteCpeChkTTL         Unsigned32
}

vRtrInetStatRteCpeChkUpTime      OBJECT-TYPE
    SYNTAX      TimeTicks
    MAX-ACCESS  read-only
    STATUS      current
    DESCRIPTION
        "The value of vRtrInetStatRteCpeChkUpTime indicates how long (in
         centiseconds) that the CPE has been available."
    ::= { vRtrInetStatRteCpeChkStatsEntry 1 }

vRtrInetStatRteCpeChkInPktCnt    OBJECT-TYPE
    SYNTAX      Counter32
    MAX-ACCESS  read-only
    STATUS      current
    DESCRIPTION
        "The value of vRtrInetStatRteCpeChkInPktCnt indicates the number of
         echo reply packets received."
    ::= { vRtrInetStatRteCpeChkStatsEntry 2 }

vRtrInetStatRteCpeChkOutPktCnt   OBJECT-TYPE
    SYNTAX      Counter32
    MAX-ACCESS  read-only
    STATUS      current
    DESCRIPTION
        "The value of vRtrInetStatRteCpeChkOutPktCnt indicates the number of
         echo request packets sent."
    ::= { vRtrInetStatRteCpeChkStatsEntry 3 }

vRtrInetStatRteCpeChkDownTrans   OBJECT-TYPE
    SYNTAX      Gauge32
    MAX-ACCESS  read-only
    STATUS      current
    DESCRIPTION
        "The value of vRtrInetStatRteCpeChkDownTrans indicates the number of
         times the CPE has transitioned to the unavailable state."
    ::= { vRtrInetStatRteCpeChkStatsEntry 4 }

vRtrInetStatRteCpeChkUpTrans     OBJECT-TYPE
    SYNTAX      Gauge32
    MAX-ACCESS  read-only
    STATUS      current
    DESCRIPTION
        "The value of vRtrInetStatRteCpeChkUpTrans indicates the number of
         times the CPE has transitioned to the available state."
    ::= { vRtrInetStatRteCpeChkStatsEntry 5 }

vRtrInetStatRteCpeChkTTL         OBJECT-TYPE
    SYNTAX      Unsigned32
    UNITS       "seconds"
    MAX-ACCESS  read-only
    STATUS      current
    DESCRIPTION
        "The value of vRtrInetStatRteCpeChkTTL indicates the time, in seconds,
         before the CPE will be declared down. Upon receipt of an echo reply,
         it has the value of vRtrInetStaticRouteCpeInterval *
         vRtrInetStaticRouteCpeDropCnt and is decremented by 1 every second."
    ::= { vRtrInetStatRteCpeChkStatsEntry 6 }

tmnxDscpAppTableLastChanged      OBJECT-TYPE
    SYNTAX      TimeStamp
    MAX-ACCESS  read-only
    STATUS      current
    DESCRIPTION
        "The value of tmnxDscpAppTableLastChanged indicates the sysUpTime at
         the time of the last modification of tmnxDscpAppTable.

         If no changes were made to the table since the last re-initialization
         of the local network management subsystem, then this object contains a
         zero value."
    ::= { tmnxVRtrObjs 45 }

tmnxDscpAppTable                 OBJECT-TYPE
    SYNTAX      SEQUENCE OF TmnxDscpAppEntry
    MAX-ACCESS  not-accessible
    STATUS      current
    DESCRIPTION
        "The tmnxDscpAppTable has an entry for each application to Differential
         Services Code Point (DSCP) mapping in a virtual routing context on
         this system."
    ::= { tmnxVRtrObjs 46 }

tmnxDscpAppEntry                 OBJECT-TYPE
    SYNTAX      TmnxDscpAppEntry
    MAX-ACCESS  not-accessible
    STATUS      current
    DESCRIPTION
        "Each row represents a mapping from an application to a DSCP value for
         particular virtual routing context.

         Entries are created at system initialization."
    INDEX       {
        vRtrID,
        tmnxDscpAppId
    }
    ::= { tmnxDscpAppTable 1 }

TmnxDscpAppEntry                 ::= SEQUENCE
{
    tmnxDscpAppId                    TDSCPAppId,
    tmnxDscpAppLastChanged           TimeStamp,
    tmnxDscpAppDscpValue             TDSCPValueOrNone
}

tmnxDscpAppId                    OBJECT-TYPE
    SYNTAX      TDSCPAppId
    MAX-ACCESS  not-accessible
    STATUS      current
    DESCRIPTION
        "The value of tmnxDscpAppId indicates the DSCP application identifier
         for a protocol on the Nokia SROS router which generates control
         traffic over IP.

         The values of 'ptp (29)' and 'igmp-reporter (30)' are applicable to
         the Base router context only (vRtrID = 1).

         The values of 'cflowd (2)' and 'sflowd (34)' are applicable to the
         Base router (vRtrID = 1) and Management router (vRtrID = 4095)
         contexts only."
    ::= { tmnxDscpAppEntry 1 }

tmnxDscpAppLastChanged           OBJECT-TYPE
    SYNTAX      TimeStamp
    MAX-ACCESS  read-only
    STATUS      current
    DESCRIPTION
        "The value of tmnxDscpAppLastChanged indicates the sysUpTime at the
         time of the last modification of this entry.

         If no changes were made to the entry since the last re-initialization
         of the local network management subsystem, then this object contains a
         zero value."
    ::= { tmnxDscpAppEntry 2 }

tmnxDscpAppDscpValue             OBJECT-TYPE
    SYNTAX      TDSCPValueOrNone
    MAX-ACCESS  read-write
    STATUS      current
    DESCRIPTION
        "The value of tmnxDscpAppDscpValue specifies a DSCP Value to assign to
         the traffic generated by the application specified by tmnxDscpAppId.

         A value of -1 specifies that no explicit DSCP re-marking will be done
         for the traffic generated by the application specified by
         tmnxDscpAppId.

         The default value is protocol specific."
    ::= { tmnxDscpAppEntry 3 }

tmnxDscpFCTableLastChanged       OBJECT-TYPE
    SYNTAX      TimeStamp
    MAX-ACCESS  read-only
    STATUS      current
    DESCRIPTION
        "The value of tmnxDscpFCTableLastChanged indicates the sysUpTime at the
         time of the last modification of tmnxDscpFCTable.

         If no changes were made to the entry since the last re-initialization
         of the local network management subsystem, then this object contains a
         zero value."
    ::= { tmnxVRtrObjs 47 }

tmnxDscpFCTable                  OBJECT-TYPE
    SYNTAX      SEQUENCE OF TmnxDscpFCEntry
    MAX-ACCESS  not-accessible
    STATUS      current
    DESCRIPTION
        "The tmnxDscpFCTable has an entry for each mapping between a DSCP value
         and a Forwarding Class for self-generated protocol traffic in a
         virtual routing context on this system."
    ::= { tmnxVRtrObjs 48 }

tmnxDscpFCEntry                  OBJECT-TYPE
    SYNTAX      TmnxDscpFCEntry
    MAX-ACCESS  not-accessible
    STATUS      current
    DESCRIPTION
        "Each row represents a mapping between a DSCP value and a Forwarding
         Class for self-generated protocol traffic in particular virtual
         routing context.

         Entries are created at system initialization."
    INDEX       {
        vRtrID,
        tmnxDscpFCDscpValue
    }
    ::= { tmnxDscpFCTable 1 }

TmnxDscpFCEntry                  ::= SEQUENCE
{
    tmnxDscpFCDscpValue              TDSCPValue,
    tmnxDscpFCLastChanged            TimeStamp,
    tmnxDscpFCValue                  TFCType
}

tmnxDscpFCDscpValue              OBJECT-TYPE
    SYNTAX      TDSCPValue
    MAX-ACCESS  not-accessible
    STATUS      current
    DESCRIPTION
        "The value of tmnxDscpFCDscpValue specifies a DSCP value which will be
         mapped to the Forwarding Class specified by tmnxDscpFCValue."
    ::= { tmnxDscpFCEntry 1 }

tmnxDscpFCLastChanged            OBJECT-TYPE
    SYNTAX      TimeStamp
    MAX-ACCESS  read-only
    STATUS      current
    DESCRIPTION
        "The value of tmnxDscpFCLastChanged indicates the sysUpTime at the time
         of the last modification of this entry.

         If no changes were made to the entry since the last re-initialization
         of the local network management subsystem, then this object contains a
         zero value."
    ::= { tmnxDscpFCEntry 3 }

tmnxDscpFCValue                  OBJECT-TYPE
    SYNTAX      TFCType
    MAX-ACCESS  read-write
    STATUS      current
    DESCRIPTION
        "The value of tmnxDscpFCValue specifies the Forwarding Class value for
         this mapping entry.

         The default value is best effort, which is specified by a value of 0."
    DEFVAL      { be }
    ::= { tmnxDscpFCEntry 4 }

tmnxDot1pAppTableLastChanged     OBJECT-TYPE
    SYNTAX      TimeStamp
    MAX-ACCESS  read-only
    STATUS      current
    DESCRIPTION
        "The value of tmnxDot1pAppTableLastChanged indicates the sysUpTime at
         the time of the last modification of tmnxDot1pAppTable.

         If no changes were made to the table since the last re-initialization
         of the local network management subsystem, then this object contains a
         zero value."
    ::= { tmnxVRtrObjs 49 }

tmnxDot1pAppTable                OBJECT-TYPE
    SYNTAX      SEQUENCE OF TmnxDot1pAppEntry
    MAX-ACCESS  not-accessible
    STATUS      current
    DESCRIPTION
        "The tmnxDot1pAppTable has an entry for each application to IEEE 802.1p
         priority (Dot1p) mapping in a virtual routing context on this system."
    ::= { tmnxVRtrObjs 50 }

tmnxDot1pAppEntry                OBJECT-TYPE
    SYNTAX      TmnxDot1pAppEntry
    MAX-ACCESS  not-accessible
    STATUS      current
    DESCRIPTION
        "Each row represents a mapping from an application to a Dot1p value for
         particular virtual routing context.

         Entries are created at system initialization."
    INDEX       {
        vRtrID,
        tmnxDot1pAppId
    }
    ::= { tmnxDot1pAppTable 1 }

TmnxDot1pAppEntry                ::= SEQUENCE
{
    tmnxDot1pAppId                   TDot1pAppId,
    tmnxDot1pAppLastChanged          TimeStamp,
    tmnxDot1pAppValue                Dot1PPriority
}

tmnxDot1pAppId                   OBJECT-TYPE
    SYNTAX      TDot1pAppId
    MAX-ACCESS  not-accessible
    STATUS      current
    DESCRIPTION
        "The value of tmnxDot1pAppId indicates the Dot1p application identifier
         for a Layer-2 protocol on the Nokia SROS router."
    ::= { tmnxDot1pAppEntry 1 }

tmnxDot1pAppLastChanged          OBJECT-TYPE
    SYNTAX      TimeStamp
    MAX-ACCESS  read-only
    STATUS      current
    DESCRIPTION
        "The value of tmnxDot1pAppLastChanged indicates the sysUpTime at the
         time of the last modification of this entry.

         If no changes were made to the entry since the last re-initialization
         of the local network management subsystem, then this object contains a
         zero value."
    ::= { tmnxDot1pAppEntry 2 }

tmnxDot1pAppValue                OBJECT-TYPE
    SYNTAX      Dot1PPriority
    MAX-ACCESS  read-write
    STATUS      current
    DESCRIPTION
        "The value of tmnxDot1pAppValue specifies a Dot1p value to assign to
         the traffic generated by the application specified by tmnxDot1pAppId.

         The default value is protocol specific."
    ::= { tmnxDot1pAppEntry 3 }

vRtrFibStatTable                 OBJECT-TYPE
    SYNTAX      SEQUENCE OF VRtrFibStatEntry
    MAX-ACCESS  not-accessible
    STATUS      current
    DESCRIPTION
        "The vRtrStatTable has an entry for IOM card configured in the system."
    ::= { tmnxVRtrObjs 51 }

vRtrFibStatEntry                 OBJECT-TYPE
    SYNTAX      VRtrFibStatEntry
    MAX-ACCESS  not-accessible
    STATUS      current
    DESCRIPTION
        "Each row entry represents a collection of summarized statistics for
         each virtual router on an IOM card in the system.

         Entries cannot be created and deleted via SNMP SET operations."
    INDEX       {
        tmnxChassisIndex,
        tmnxCardSlotNum
    }
    ::= { vRtrFibStatTable 1 }

VRtrFibStatEntry                 ::= SEQUENCE
{
    vRtrFibStatStaticRoutes          Gauge32,
    vRtrFibStatDirectRoutes          Gauge32,
    vRtrFibStatHostRoutes            Gauge32,
    vRtrFibStatBGPRoutes             Gauge32,
    vRtrFibStatBGPVpnRoutes          Gauge32,
    vRtrFibStatOSPFRoutes            Gauge32,
    vRtrFibStatISISRoutes            Gauge32,
    vRtrFibStatRIPRoutes             Gauge32,
    vRtrFibStatAggrRoutes            Gauge32,
    vRtrFibStatSubMgmtRoutes         Gauge32,
    vRtrFibStatManagedRoutes         Gauge32,
    vRtrFibStatV6StaticRoutes        Gauge32,
    vRtrFibStatV6DirectRoutes        Gauge32,
    vRtrFibStatV6HostRoutes          Gauge32,
    vRtrFibStatV6BGPRoutes           Gauge32,
    vRtrFibStatV6BGPVpnRoutes        Gauge32,
    vRtrFibStatV6OSPFRoutes          Gauge32,
    vRtrFibStatV6ISISRoutes          Gauge32,
    vRtrFibStatV6RIPRoutes           Gauge32,
    vRtrFibStatV6AggrRoutes          Gauge32,
    vRtrFibStatV6SubMgmtRoutes       Gauge32,
    vRtrFibStatV6ManagedRoutes       Gauge32,
    vRtrFibStatOverflows             Gauge32,
    vRtrFibStatAlarmCount            Gauge32,
    vRtrFibStatLastAlarmTime         TimeStamp,
    vRtrFibStatHighUtilization       TruthValue,
    vRtrFibStatMobileHostRoutes      Gauge32,
    vRtrFibStatV6MobileHostRoutes    Gauge32,
    vRtrFibStatVPNLeakRoutes         Gauge32,
    vRtrFibStatV6VPNLeakRoutes       Gauge32,
    vRtrFibStatNatRoutes             Gauge32,
    vRtrFibStatV6NatRoutes           Gauge32,
    vRtrFibStatBGPEvpnRoutes         Gauge32,
    vRtrFibStatV6BGPEvpnRoutes       Gauge32,
    vRtrFibStatTotalInstalledRoutes  Gauge32,
    vRtrFibStatCurrentUtilization    Gauge32,
    vRtrFibStatFilteredRoutes        Gauge32,
    vRtrFibStatV6TotalInstalledRt    Gauge32,
    vRtrFibStatV6CurrentUtilization  Gauge32,
    vRtrFibStatV6FilteredRoutes      Gauge32,
    vRtrFibStatV6Overflows           Gauge32,
    vRtrFibStatBGPLabelV4Routes      Gauge32,
    vRtrFibStatBGPLabelV6Routes      Gauge32,
    vRtrFibStatBGPEvpnIflRoutes      Gauge32,
    vRtrFibStatV6BGPEvpnIflRoutes    Gauge32,
    vRtrFibStatBGPEvpnIffRoutes      Gauge32,
    vRtrFibStatV6BGPEvpnIffRoutes    Gauge32,
    vRtrFibStatSrV6Routes            Gauge32,
    vRtrFibStatIpVpnCurrUtilization  Gauge32,
    vRtrFibStatBGPEvpnIflHostRoutes  Gauge32,
    vRtrFibStatV6BGPEvpnIflHostRts   Gauge32
}

vRtrFibStatStaticRoutes          OBJECT-TYPE
    SYNTAX      Gauge32
    MAX-ACCESS  read-only
    STATUS      current
    DESCRIPTION
        "vRtrFibStatStaticRoutes indicates current static route counts for the
         virtual router."
    ::= { vRtrFibStatEntry 1 }

vRtrFibStatDirectRoutes          OBJECT-TYPE
    SYNTAX      Gauge32
    MAX-ACCESS  read-only
    STATUS      current
    DESCRIPTION
        "vRtrFibStatDirectRoutes indicates current direct route counts for the
         virtual router."
    ::= { vRtrFibStatEntry 2 }

vRtrFibStatHostRoutes            OBJECT-TYPE
    SYNTAX      Gauge32
    MAX-ACCESS  read-only
    STATUS      current
    DESCRIPTION
        "vRtrFibStatHostRoutes indicates current host route counts for the
         virtual router."
    ::= { vRtrFibStatEntry 3 }

vRtrFibStatBGPRoutes             OBJECT-TYPE
    SYNTAX      Gauge32
    MAX-ACCESS  read-only
    STATUS      current
    DESCRIPTION
        "vRtrFibStatBGPRoutes indicates current BGP route counts for the
         virtual router."
    ::= { vRtrFibStatEntry 4 }

vRtrFibStatBGPVpnRoutes          OBJECT-TYPE
    SYNTAX      Gauge32
    MAX-ACCESS  read-only
    STATUS      current
    DESCRIPTION
        "vRtrFibStatBGPVpnRoutes indicates current BGP VPN route counts for the
         virtual router."
    ::= { vRtrFibStatEntry 5 }

vRtrFibStatOSPFRoutes            OBJECT-TYPE
    SYNTAX      Gauge32
    MAX-ACCESS  read-only
    STATUS      current
    DESCRIPTION
        "vRtrFibStatOSPFRoutes indicates current OSPF route counts for the
         virtual router."
    ::= { vRtrFibStatEntry 6 }

vRtrFibStatISISRoutes            OBJECT-TYPE
    SYNTAX      Gauge32
    MAX-ACCESS  read-only
    STATUS      current
    DESCRIPTION
        "vRtrFibStatISISRoutes indicates current ISIS route counts for the
         virtual router."
    ::= { vRtrFibStatEntry 7 }

vRtrFibStatRIPRoutes             OBJECT-TYPE
    SYNTAX      Gauge32
    MAX-ACCESS  read-only
    STATUS      current
    DESCRIPTION
        "vRtrFibStatRIPRoutes indicates current RIP route counts for the
         virtual router."
    ::= { vRtrFibStatEntry 8 }

vRtrFibStatAggrRoutes            OBJECT-TYPE
    SYNTAX      Gauge32
    MAX-ACCESS  read-only
    STATUS      current
    DESCRIPTION
        "vRtrFibStatAggrRoutes indicates current aggregate route counts for the
         virtual router."
    ::= { vRtrFibStatEntry 9 }

vRtrFibStatSubMgmtRoutes         OBJECT-TYPE
    SYNTAX      Gauge32
    MAX-ACCESS  read-only
    STATUS      current
    DESCRIPTION
        "vRtrFibStatSubMgmtRoutes indicates current Sub-management route counts
         for the virtual router."
    ::= { vRtrFibStatEntry 10 }

vRtrFibStatManagedRoutes         OBJECT-TYPE
    SYNTAX      Gauge32
    MAX-ACCESS  read-only
    STATUS      current
    DESCRIPTION
        "vRtrFibStatManagedRoutes indicates current managed route counts for
         the virtual router."
    ::= { vRtrFibStatEntry 11 }

vRtrFibStatV6StaticRoutes        OBJECT-TYPE
    SYNTAX      Gauge32
    MAX-ACCESS  read-only
    STATUS      current
    DESCRIPTION
        "vRtrFibStatV6StaticRoutes indicates current static route counts for
         the virtual router."
    ::= { vRtrFibStatEntry 12 }

vRtrFibStatV6DirectRoutes        OBJECT-TYPE
    SYNTAX      Gauge32
    MAX-ACCESS  read-only
    STATUS      current
    DESCRIPTION
        "vRtrFibStatV6DirectRoutes indicates current direct route counts for
         the virtual router."
    ::= { vRtrFibStatEntry 13 }

vRtrFibStatV6HostRoutes          OBJECT-TYPE
    SYNTAX      Gauge32
    MAX-ACCESS  read-only
    STATUS      current
    DESCRIPTION
        "vRtrFibStatV6HostRoutes indicates current host route counts for the
         virtual router."
    ::= { vRtrFibStatEntry 14 }

vRtrFibStatV6BGPRoutes           OBJECT-TYPE
    SYNTAX      Gauge32
    MAX-ACCESS  read-only
    STATUS      current
    DESCRIPTION
        "vRtrFibStatV6BGPRoutes indicates current BGP route counts for the
         virtual router."
    ::= { vRtrFibStatEntry 15 }

vRtrFibStatV6BGPVpnRoutes        OBJECT-TYPE
    SYNTAX      Gauge32
    MAX-ACCESS  read-only
    STATUS      current
    DESCRIPTION
        "vRtrFibStatV6BGPVpnRoutes indicates current BGP VPN route counts for
         the virtual router."
    ::= { vRtrFibStatEntry 16 }

vRtrFibStatV6OSPFRoutes          OBJECT-TYPE
    SYNTAX      Gauge32
    MAX-ACCESS  read-only
    STATUS      current
    DESCRIPTION
        "vRtrFibStatV6OSPFRoutes indicates current OSPF route counts for the
         virtual router."
    ::= { vRtrFibStatEntry 17 }

vRtrFibStatV6ISISRoutes          OBJECT-TYPE
    SYNTAX      Gauge32
    MAX-ACCESS  read-only
    STATUS      current
    DESCRIPTION
        "vRtrFibStatV6ISISRoutes indicates current ISIS route counts for the
         virtual router."
    ::= { vRtrFibStatEntry 18 }

vRtrFibStatV6RIPRoutes           OBJECT-TYPE
    SYNTAX      Gauge32
    MAX-ACCESS  read-only
    STATUS      current
    DESCRIPTION
        "vRtrFibStatV6RIPRoutes indicates current RIP route counts for the
         virtual router."
    ::= { vRtrFibStatEntry 19 }

vRtrFibStatV6AggrRoutes          OBJECT-TYPE
    SYNTAX      Gauge32
    MAX-ACCESS  read-only
    STATUS      current
    DESCRIPTION
        "vRtrFibStatV6AggrRoutes indicates current aggregate route counts for
         the virtual router."
    ::= { vRtrFibStatEntry 20 }

vRtrFibStatV6SubMgmtRoutes       OBJECT-TYPE
    SYNTAX      Gauge32
    MAX-ACCESS  read-only
    STATUS      current
    DESCRIPTION
        "vRtrFibStatV6SubMgmtRoutes indicates current Sub-management route
         counts for the virtual router."
    ::= { vRtrFibStatEntry 21 }

vRtrFibStatV6ManagedRoutes       OBJECT-TYPE
    SYNTAX      Gauge32
    MAX-ACCESS  read-only
    STATUS      current
    DESCRIPTION
        "vRtrFibStatV6ManagedRoutes indicates current managed route counts for
         the virtual router."
    ::= { vRtrFibStatEntry 22 }

vRtrFibStatOverflows             OBJECT-TYPE
    SYNTAX      Gauge32
    MAX-ACCESS  read-only
    STATUS      current
    DESCRIPTION
        "vRtrFibStatOverflows indicates the number of times the FIB has run out
         of space due to IPv4 routes."
    ::= { vRtrFibStatEntry 23 }

vRtrFibStatAlarmCount            OBJECT-TYPE
    SYNTAX      Gauge32
    MAX-ACCESS  read-only
    STATUS      current
    DESCRIPTION
        "vRtrFibStatAlarmCount indicates the number of times the FIB has raised
         an alarm due to high FIB usage."
    ::= { vRtrFibStatEntry 24 }

vRtrFibStatLastAlarmTime         OBJECT-TYPE
    SYNTAX      TimeStamp
    MAX-ACCESS  read-only
    STATUS      current
    DESCRIPTION
        "vRtrFibStatLastAlarmTime indicates the last time a high FIB usage
         alarm was raised."
    ::= { vRtrFibStatEntry 25 }

vRtrFibStatHighUtilization       OBJECT-TYPE
    SYNTAX      TruthValue
    MAX-ACCESS  read-only
    STATUS      current
    DESCRIPTION
        "vRtrFibStatHighUtilization indicates whether or not the FIB on the IOM
         is experiences persistent high occupancy."
    ::= { vRtrFibStatEntry 26 }

vRtrFibStatMobileHostRoutes      OBJECT-TYPE
    SYNTAX      Gauge32
    MAX-ACCESS  read-only
    STATUS      current
    DESCRIPTION
        "The value of vRtrFibStatMobileHostRoutes indicates the current IPv4
         Mobile Host route counts for the virtual router."
    ::= { vRtrFibStatEntry 27 }

vRtrFibStatV6MobileHostRoutes    OBJECT-TYPE
    SYNTAX      Gauge32
    MAX-ACCESS  read-only
    STATUS      current
    DESCRIPTION
        "The value of vRtrFibStatV6MobileHostRoutes indicates the current IPv6
         Mobile Host route counts for the virtual router."
    ::= { vRtrFibStatEntry 28 }

vRtrFibStatVPNLeakRoutes         OBJECT-TYPE
    SYNTAX      Gauge32
    MAX-ACCESS  read-only
    STATUS      current
    DESCRIPTION
        "vRtrFibStatVPNLeakRoutes indicates current VPN Leak route counts for
         the virtual router."
    ::= { vRtrFibStatEntry 29 }

vRtrFibStatV6VPNLeakRoutes       OBJECT-TYPE
    SYNTAX      Gauge32
    MAX-ACCESS  read-only
    STATUS      current
    DESCRIPTION
        "vRtrFibStatV6VPNLeakRoutes indicates current IPv6 VPN Leak route
         counts for the virtual router."
    ::= { vRtrFibStatEntry 30 }

vRtrFibStatNatRoutes             OBJECT-TYPE
    SYNTAX      Gauge32
    MAX-ACCESS  read-only
    STATUS      current
    DESCRIPTION
        "vRtrFibStatNatRoutes indicates current NAT route counts for the
         virtual router."
    ::= { vRtrFibStatEntry 33 }

vRtrFibStatV6NatRoutes           OBJECT-TYPE
    SYNTAX      Gauge32
    MAX-ACCESS  read-only
    STATUS      current
    DESCRIPTION
        "vRtrFibStatV6NatRoutes indicates current NAT IPv6 route counts for the
         virtual router."
    ::= { vRtrFibStatEntry 34 }

vRtrFibStatBGPEvpnRoutes         OBJECT-TYPE
    SYNTAX      Gauge32
    MAX-ACCESS  read-only
    STATUS      obsolete
    DESCRIPTION
        "The value of vRtrFibStatBGPEvpnRoutes indicates the current IPv4 BGP
         EVPN route counts for the virtual router.

         This object is replaced by vRtrFibStatBGPEvpnIffRoutes in SR release
         20.10.R1 and obsoleted in 21.2.R1."
    ::= { vRtrFibStatEntry 35 }

vRtrFibStatV6BGPEvpnRoutes       OBJECT-TYPE
    SYNTAX      Gauge32
    MAX-ACCESS  read-only
    STATUS      obsolete
    DESCRIPTION
        "The value of vRtrFibStatV6BGPEvpnRoutes indicates the current IPv6 BGP
         EVPN route counts for the virtual router

         This object is replaced by vRtrFibStatV6BGPEvpnIffRoutes in SR release
         20.10.R1 and obsoleted in 21.2.R1."
    ::= { vRtrFibStatEntry 36 }

vRtrFibStatTotalInstalledRoutes  OBJECT-TYPE
    SYNTAX      Gauge32
    MAX-ACCESS  read-only
    STATUS      current
    DESCRIPTION
        "The value of vRtrFibStatTotalInstalledRoutes indicates the total
         number of IPv4 routes installed in hardware FIB."
    ::= { vRtrFibStatEntry 37 }

vRtrFibStatCurrentUtilization    OBJECT-TYPE
    SYNTAX      Gauge32
    MAX-ACCESS  read-only
    STATUS      current
    DESCRIPTION
        "The value of vRtrFibStatCurrentUtilization indicates the space usage
         by IPv4 routes in hardware FIB in percentage."
    ::= { vRtrFibStatEntry 38 }

vRtrFibStatFilteredRoutes        OBJECT-TYPE
    SYNTAX      Gauge32
    MAX-ACCESS  read-only
    STATUS      current
    DESCRIPTION
        "The value of vRtrFibStatFilteredRoutes indicates the total number of
         IPv4 routes filtered due to selective download and so not installed in
         hardware FIB."
    ::= { vRtrFibStatEntry 39 }

vRtrFibStatV6TotalInstalledRt    OBJECT-TYPE
    SYNTAX      Gauge32
    MAX-ACCESS  read-only
    STATUS      current
    DESCRIPTION
        "The value of vRtrFibStatV6TotalInstalledRt indicates the total number
         of IPv6 routes installed in hardware FIB."
    ::= { vRtrFibStatEntry 40 }

vRtrFibStatV6CurrentUtilization  OBJECT-TYPE
    SYNTAX      Gauge32
    MAX-ACCESS  read-only
    STATUS      current
    DESCRIPTION
        "The value of vRtrFibStatV6CurrentUtilization indicates the space usage
         by IPv6 routes in hardware FIB in percentage."
    ::= { vRtrFibStatEntry 41 }

vRtrFibStatV6FilteredRoutes      OBJECT-TYPE
    SYNTAX      Gauge32
    MAX-ACCESS  read-only
    STATUS      current
    DESCRIPTION
        "The value of vRtrFibStatV6FilteredRoutes indicates the total number of
         IPv6 routes filtered due to selective download and so not installed in
         hardware FIB."
    ::= { vRtrFibStatEntry 42 }

vRtrFibStatV6Overflows           OBJECT-TYPE
    SYNTAX      Gauge32
    MAX-ACCESS  read-only
    STATUS      current
    DESCRIPTION
        "vRtrFibStatV6Overflows indicates the number of times the FIB has run
         out of space due to IPv6 routes."
    ::= { vRtrFibStatEntry 43 }

vRtrFibStatBGPLabelV4Routes      OBJECT-TYPE
    SYNTAX      Gauge32
    MAX-ACCESS  read-only
    STATUS      current
    DESCRIPTION
        "The value of vRtrFibStatBGPLabelV4Routes indicates the current labeled
         IPv4 BGP route counts for the virtual router."
    ::= { vRtrFibStatEntry 44 }

vRtrFibStatBGPLabelV6Routes      OBJECT-TYPE
    SYNTAX      Gauge32
    MAX-ACCESS  read-only
    STATUS      current
    DESCRIPTION
        "The value of vRtrFibStatBGPLabelV6Routes indicates the current labeled
         IPv6 BGP route counts for the virtual router."
    ::= { vRtrFibStatEntry 45 }

vRtrFibStatBGPEvpnIflRoutes      OBJECT-TYPE
    SYNTAX      Gauge32
    MAX-ACCESS  read-only
    STATUS      current
    DESCRIPTION
        "vRtrFibStatBGPEvpnIflRoutes indicates current BGP EVPN IFL route
         counts for the virtual router."
    ::= { vRtrFibStatEntry 46 }

vRtrFibStatV6BGPEvpnIflRoutes    OBJECT-TYPE
    SYNTAX      Gauge32
    MAX-ACCESS  read-only
    STATUS      current
    DESCRIPTION
        "vRtrFibStatV6BGPEvpnIflRoutes indicates current ipv6 BGP EVPN IFL
         route counts for the virtual router."
    ::= { vRtrFibStatEntry 47 }

vRtrFibStatBGPEvpnIffRoutes      OBJECT-TYPE
    SYNTAX      Gauge32
    MAX-ACCESS  read-only
    STATUS      current
    DESCRIPTION
        "vRtrFibStatBGPEvpnIffRoutes indicates current BGP EVPN IFF route
         counts for the virtual router.

         This object replaces vRtrFibStatBGPEvpnRoutes in releases 20.10."
    ::= { vRtrFibStatEntry 48 }

vRtrFibStatV6BGPEvpnIffRoutes    OBJECT-TYPE
    SYNTAX      Gauge32
    MAX-ACCESS  read-only
    STATUS      current
    DESCRIPTION
        "vRtrFibStatV6BGPEvpnIffRoutes indicates current ipv6 BGP EVPN IFF
         route counts for the virtual router.

         This object replaces vRtrFibStatV6BGPEvpnRoutes in releases 20.10."
    ::= { vRtrFibStatEntry 49 }

vRtrFibStatSrV6Routes            OBJECT-TYPE
    SYNTAX      Gauge32
    MAX-ACCESS  read-only
    STATUS      current
    DESCRIPTION
        "vRtrFibStatSrV6Routes indicates current SRV6 route counts for the
         virtual router."
    ::= { vRtrFibStatEntry 50 }

vRtrFibStatIpVpnCurrUtilization  OBJECT-TYPE
    SYNTAX      Gauge32
    MAX-ACCESS  read-only
    STATUS      current
    DESCRIPTION
        "The value of vRtrFibStatIpVpnCurrUtilization indicates the space usage
         by VPRN VRFs IPv4/IPv6 routes in hardware FIB in percentage."
    ::= { vRtrFibStatEntry 51 }

vRtrFibStatBGPEvpnIflHostRoutes  OBJECT-TYPE
    SYNTAX      Gauge32
    MAX-ACCESS  read-only
    STATUS      current
    DESCRIPTION
        "vRtrFibStatBGPEvpnIflHostRoutes indicates current BGP EVPN IFL Host
         route counts for the virtual router."
    ::= { vRtrFibStatEntry 52 }

vRtrFibStatV6BGPEvpnIflHostRts   OBJECT-TYPE
    SYNTAX      Gauge32
    MAX-ACCESS  read-only
    STATUS      current
    DESCRIPTION
        "vRtrFibStatV6BGPEvpnIflHostRts indicates current ipv6 BGP EVPN IFL
         Host route counts for the virtual router."
    ::= { vRtrFibStatEntry 53 }

vRtrFibStatNextHopTable          OBJECT-TYPE
    SYNTAX      SEQUENCE OF VRtrFibStatNextHopEntry
    MAX-ACCESS  not-accessible
    STATUS      current
    DESCRIPTION
        "The vRtrFibStatNextHopTable has an entry for each IOM in the system."
    ::= { tmnxVRtrObjs 52 }

vRtrFibStatNextHopEntry          OBJECT-TYPE
    SYNTAX      VRtrFibStatNextHopEntry
    MAX-ACCESS  not-accessible
    STATUS      current
    DESCRIPTION
        "Each row entry represents a collection of statistics for an IOM card
         in the system.

         Entries cannot be created and deleted via SNMP SET operations."
    INDEX       {
        tmnxChassisIndex,
        tmnxCardSlotNum
    }
    ::= { vRtrFibStatNextHopTable 1 }

VRtrFibStatNextHopEntry          ::= SEQUENCE
{
    vRtrFibStatNextHopIPActive       Gauge32,
    vRtrFibStatNextHopIPAvailable    Gauge32,
    vRtrFibStatNextHopTunnelActive   Gauge32,
    vRtrFibStatNextHopTunnelAvailable Gauge32
}

vRtrFibStatNextHopIPActive       OBJECT-TYPE
    SYNTAX      Gauge32
    MAX-ACCESS  read-only
    STATUS      current
    DESCRIPTION
        "vRtrFibStatNextHopIPActive indicates current active IP next-hop counts
         for the FIB on the IOM."
    ::= { vRtrFibStatNextHopEntry 1 }

vRtrFibStatNextHopIPAvailable    OBJECT-TYPE
    SYNTAX      Gauge32
    MAX-ACCESS  read-only
    STATUS      current
    DESCRIPTION
        "vRtrFibStatNextHopIPAvailable indicates the available IP next-hop
         counts for the FIB on the IOM."
    ::= { vRtrFibStatNextHopEntry 2 }

vRtrFibStatNextHopTunnelActive   OBJECT-TYPE
    SYNTAX      Gauge32
    MAX-ACCESS  read-only
    STATUS      current
    DESCRIPTION
        "vRtrFibStatNextHopTunnelActive indicates current active Tunnel
         next-hop counts for the FIB on the IOM."
    ::= { vRtrFibStatNextHopEntry 3 }

vRtrFibStatNextHopTunnelAvailable OBJECT-TYPE
    SYNTAX      Gauge32
    MAX-ACCESS  read-only
    STATUS      current
    DESCRIPTION
        "vRtrFibStatNextHopTunnelAvailable indicates the available Tunnel
         next-hop counts for the FIB on the IOM."
    ::= { vRtrFibStatNextHopEntry 4 }

vRtrInetAllCidrRouteTable        OBJECT-TYPE
    SYNTAX      SEQUENCE OF VRtrInetAllCidrRouteEntry
    MAX-ACCESS  not-accessible
    STATUS      current
    DESCRIPTION
        "The vRtrInetAllCidrRouteTable provides an extension of the
         inetCidrRouteTable in the IP-FORWARD-MIB, by adding two indexes and
         displaying both active and inactive CIDR routes."
    ::= { tmnxVRtrObjs 53 }

vRtrInetAllCidrRouteEntry        OBJECT-TYPE
    SYNTAX      VRtrInetAllCidrRouteEntry
    MAX-ACCESS  not-accessible
    STATUS      current
    DESCRIPTION
        "Each row entry in the vRtrInetAllCidrRouteTable represents an entry in
         the IP CIDR route table for the Nokia SROS series."
    INDEX       {
        inetCidrRouteDestType,
        inetCidrRouteDest,
        inetCidrRoutePfxLen,
        inetCidrRoutePolicy,
        inetCidrRouteProto,
        vRtrInetAllCidrRouteProtoID,
        inetCidrRouteNextHopType,
        inetCidrRouteNextHop
    }
    ::= { vRtrInetAllCidrRouteTable 1 }

VRtrInetAllCidrRouteEntry        ::= SEQUENCE
{
    vRtrInetAllCidrRouteProtoID      Unsigned32,
    vRtrInetAllCidrRouteIfIndex      InterfaceIndexOrZero,
    vRtrInetAllCidrRouteType         INTEGER,
    vRtrInetAllCidrRouteAge          Gauge32,
    vRtrInetAllCidrRouteNextHopAS    InetAutonomousSystemNumber,
    vRtrInetAllCidrRouteMetric1      Integer32,
    vRtrInetAllCidrRouteMetric2      Integer32,
    vRtrInetAllCidrRouteMetric3      Integer32,
    vRtrInetAllCidrRouteMetric4      Integer32,
    vRtrInetAllCidrRouteMetric5      Integer32,
    vRtrInetAllCidrRoutePreference   Unsigned32,
    vRtrInetAllCidrRouteMetric       Unsigned32,
    vRtrInetAllCidrRouteIfVRtrId     TmnxVRtrIDOrZero,
    vRtrInetAllCidrRouteIsActive     TruthValue,
    vRtrInetAllCidrRouteBkupFlags    INTEGER,
    vRtrInetAllCidrRouteBkupNHopType InetAddressType,
    vRtrInetAllCidrRouteBkupNextHop  InetAddress,
    vRtrInetAllCidrRouteBkupMetric   Unsigned32,
    vRtrInetAllCidrRouteNHopRepCount Unsigned32,
    vRtrInetAllCidrRtNextHopType     TmnxInetCidrNextHopType,
    vRtrInetAllCidrRtNextHopOwner    TmnxInetCidrNextHopOwner,
    vRtrInetAllCidrRtNHOwnerAuxInfo  Unsigned32,
    vRtrInetAllCidrRtBkupNHType      TmnxInetCidrNextHopType,
    vRtrInetAllCidrRtBkupNHOwner     TmnxInetCidrNextHopOwner,
    vRtrInetAllCidrRtBkupNHOwnAxInfo Unsigned32,
    vRtrInetAllCidrRtSrcClassIndex   ClassIndexOrNone,
    vRtrInetAllCidrRtDstClassIndex   ClassIndexOrNone,
    vRtrInetAllCidrRtOperFlags       TmnxRouteOperFlags,
    vRtrInetAllCidrRtNextHopOwnInst  Unsigned32,
    vRtrInetAllCidrRtBkupNHOwnInst   Unsigned32,
    vRtrInetAllCidrRouteNHIsFec      TruthValue,
    vRtrInetAllCidrRouteNHFecPfxLen  InetAddressPrefixLength,
    vRtrInetAllCidrRouteEgrVni       Unsigned32
}

vRtrInetAllCidrRouteProtoID      OBJECT-TYPE
    SYNTAX      Unsigned32
    MAX-ACCESS  not-accessible
    STATUS      current
    DESCRIPTION
        "Additional table index provided to distinguish between multiple routes
         to same destination with the same inetCidrRouteProto index."
    ::= { vRtrInetAllCidrRouteEntry 1 }

vRtrInetAllCidrRouteIfIndex      OBJECT-TYPE
    SYNTAX      InterfaceIndexOrZero
    MAX-ACCESS  read-only
    STATUS      current
    DESCRIPTION
        "The value of vRtrInetAllCidrRouteIfIndex indicates the ifIndex value
         which identifies the local interface through which the next hop
         of this route should be reached.  A value of 0 is valid and
         represents the scenario where no interface is specified."
    ::= { vRtrInetAllCidrRouteEntry 2 }

vRtrInetAllCidrRouteType         OBJECT-TYPE
    SYNTAX      INTEGER {
        other     (1),
        reject    (2),
        local     (3),
        remote    (4),
        blackhole (5)
    }
    MAX-ACCESS  read-only
    STATUS      current
    DESCRIPTION
        "The value of vRtrInetAllCidrRouteType indicates the type of route.
         Note that 'local' refers to a route for which the next hop is the
         final destination; 'remote' refers to a route for which the next hop
         is not the final destination.

         Routes which do not result in traffic forwarding or rejection should
         not be displayed even if the implementation keeps them stored
         internally.

         'reject' refers to a route which, if matched, discards
         the message as unreachable and returns a notification
         (e.g. ICMP error) to the message sender.  This is used
         in some protocols as a means of correctly aggregating
         routes.

         'blackhole' refers to a route which, if matched, discards the message
         silently."
    ::= { vRtrInetAllCidrRouteEntry 3 }

vRtrInetAllCidrRouteAge          OBJECT-TYPE
    SYNTAX      Gauge32
    MAX-ACCESS  read-only
    STATUS      current
    DESCRIPTION
        "The value of vRtrInetAllCidrRouteAge indicates the number
         of seconds since this route was last updated or otherwise
         determined to be correct.  Note that no semantics of
         'too old' can be implied except through knowledge of
         the routing protocol by which the route was learned."
    ::= { vRtrInetAllCidrRouteEntry 4 }

vRtrInetAllCidrRouteNextHopAS    OBJECT-TYPE
    SYNTAX      InetAutonomousSystemNumber
    MAX-ACCESS  read-only
    STATUS      current
    DESCRIPTION
        "The value of vRtrInetAllCidrRouteNextHopAS indicates the Autonomous
         System Number of the Next Hop. The semantics of this object are
         determined by the routing- protocol specified in the route's
         inetCidrRouteProto index. When this object is unknown or not relevant
         its value should be set to zero."
    ::= { vRtrInetAllCidrRouteEntry 5 }

vRtrInetAllCidrRouteMetric1      OBJECT-TYPE
    SYNTAX      Integer32
    MAX-ACCESS  read-only
    STATUS      current
    DESCRIPTION
        "The value of vRtrInetAllCidrRouteMetric1 indicates the primary routing
         metric for this route. The semantics of this metric are determined by
         the routing-protocol indicated in the route's inetCidrRouteProto
         index. If this metric is not used, its value will be -1."
    ::= { vRtrInetAllCidrRouteEntry 6 }

vRtrInetAllCidrRouteMetric2      OBJECT-TYPE
    SYNTAX      Integer32
    MAX-ACCESS  read-only
    STATUS      current
    DESCRIPTION
        "The value of vRtrInetAllCidrRouteMetric2 indicates the primary routing
         metric for this route. The semantics of this metric are determined by
         the routing-protocol indicated in the route's inetCidrRouteProto
         index. If this metric is not used, its value will be -1."
    ::= { vRtrInetAllCidrRouteEntry 7 }

vRtrInetAllCidrRouteMetric3      OBJECT-TYPE
    SYNTAX      Integer32
    MAX-ACCESS  read-only
    STATUS      current
    DESCRIPTION
        "The value of vRtrInetAllCidrRouteMetric3 indicates the primary routing
         metric for this route. The semantics of this metric are determined by
         the routing-protocol indicated in the route's inetCidrRouteProto
         index. If this metric is not used, its value will be -1."
    ::= { vRtrInetAllCidrRouteEntry 8 }

vRtrInetAllCidrRouteMetric4      OBJECT-TYPE
    SYNTAX      Integer32
    MAX-ACCESS  read-only
    STATUS      current
    DESCRIPTION
        "The value of vRtrInetAllCidrRouteMetric4 indicates the primary routing
         metric for this route. The semantics of this metric are determined by
         the routing-protocol indicated in the route's inetCidrRouteProto
         index. If this metric is not used, its value will be -1."
    ::= { vRtrInetAllCidrRouteEntry 9 }

vRtrInetAllCidrRouteMetric5      OBJECT-TYPE
    SYNTAX      Integer32
    MAX-ACCESS  read-only
    STATUS      current
    DESCRIPTION
        "The value of vRtrInetAllCidrRouteMetric5 indicates the primary routing
         metric for this route. The semantics of this metric are determined by
         the routing-protocol indicated in the route's inetCidrRouteProto
         index. If this metric is not used, its value will be -1."
    ::= { vRtrInetAllCidrRouteEntry 10 }

vRtrInetAllCidrRoutePreference   OBJECT-TYPE
    SYNTAX      Unsigned32 (0..255)
    MAX-ACCESS  read-only
    STATUS      current
    DESCRIPTION
        "The value of vRtrInetAllCidrRoutePreference indicates the priority of
         this static route versus the routes from different sources such as BGP
         or OSPF etc, when ipCidrRouteProto has a value of 'netmgmt' to
         indicate that this entry is a static route.

         Different protocols should not be configured with the same preference,
         if this occurs the tiebreaker is determined per the default preference
         value as defined in the table below.

         If multiple routes are learned with an identical preference using the
         same protocol, the lowest cost is used. If multiple routes are learned
         with an identical preference using the same protocol and the costs
         (metrics) are equal, then the decision as to what route to use is
         determined by the configuration of the ecmp command.

         Default preferences:

         Route Type             Preference      Configurable
         ----------             ----------      ------------
         Direct attached                 0                no
         Static route                    5               yes
         MPLS (post FCS)                 7
         OSPF Internal routes           10                no
         OSPF External                 150               yes
         BGP                           170               yes"
    ::= { vRtrInetAllCidrRouteEntry 11 }

vRtrInetAllCidrRouteMetric       OBJECT-TYPE
    SYNTAX      Unsigned32
    MAX-ACCESS  read-only
    STATUS      current
    DESCRIPTION
        "The value of vRtrInetAllCidrRouteMetric indicates the primary routing
         metric  for this route. The semantics of this metric are determined
         by the routing-protocol specified in the route's ipCidrRouteProto
         value."
    ::= { vRtrInetAllCidrRouteEntry 12 }

vRtrInetAllCidrRouteIfVRtrId     OBJECT-TYPE
    SYNTAX      TmnxVRtrIDOrZero
    MAX-ACCESS  read-only
    STATUS      current
    DESCRIPTION
        "The value of vRtrInetAllCidrRouteIfVRtrId indicates the virtual router
         instance of the egress interface defined by
         vRtrInetAllCidrRouteIfIndex. This object is valid only for subscriber
         management routes. For all other route types, this object will have a
         value of zero."
    ::= { vRtrInetAllCidrRouteEntry 13 }

vRtrInetAllCidrRouteIsActive     OBJECT-TYPE
    SYNTAX      TruthValue
    MAX-ACCESS  read-only
    STATUS      current
    DESCRIPTION
        "The value of vRtrInetAllCidrRouteIsActive indicates whether the this
         route is the active route for this destination in the IP CIDR route
         table."
    ::= { vRtrInetAllCidrRouteEntry 14 }

vRtrInetAllCidrRouteBkupFlags    OBJECT-TYPE
    SYNTAX      INTEGER {
        none          (0),
        hasLfa        (1),
        hasBackup     (2),
        isBackup      (3),
        isBgpInactive (4)
    }
    MAX-ACCESS  read-only
    STATUS      current
    DESCRIPTION
        "The value of vRtrInetAllCidrRouteBkupFlags indicates the presence or
         absence of LFA next-hops and backup routes.

         'none' indicates that no next-hop is present. 'hasLfa' indicates that
         an LFA next-hop is present in addition to the regular next-hop.
         'hasBackup' indicates that this route has a backup route. 'isBackup'
         indicates that this route is a backup route to another route with the
         same prefix. 'isBgpInactive' indicates that this route is an inactive
         best-external route exported from BGP."
    ::= { vRtrInetAllCidrRouteEntry 15 }

vRtrInetAllCidrRouteBkupNHopType OBJECT-TYPE
    SYNTAX      InetAddressType
    MAX-ACCESS  read-only
    STATUS      current
    DESCRIPTION
        "The value of vRtrInetAllCidrRouteBkupNHopType indicates the IP address
         type of vRtrInetAllCidrRouteBkupNextHop. The value of
         vRtrInetAllCidrRouteBkupNHopType is only valid when
         vRtrInetAllCidrRouteBkupFlags has a value of 'hasLfa'."
    ::= { vRtrInetAllCidrRouteEntry 16 }

vRtrInetAllCidrRouteBkupNextHop  OBJECT-TYPE
    SYNTAX      InetAddress
    MAX-ACCESS  read-only
    STATUS      current
    DESCRIPTION
        "The value of vRtrInetAllCidrRouteBkupNextHop indicates the IP address
         of a backup next-hop. The value of vRtrInetAllCidrRouteBkupNextHop is
         only valid when vRtrInetAllCidrRouteBkupFlags has a value of 'hasLfa'."
    ::= { vRtrInetAllCidrRouteEntry 17 }

vRtrInetAllCidrRouteBkupMetric   OBJECT-TYPE
    SYNTAX      Unsigned32
    MAX-ACCESS  read-only
    STATUS      current
    DESCRIPTION
        "The value of vRtrInetAllCidrRouteBkupMetric indicates the routing
         metric for a backup route. The semantics of this metric are determined
         by the routing-protocol specified in the route's ipCidrRouteProto
         value. The value of vRtrInetAllCidrRouteBkupMetric is only valid when
         vRtrInetAllCidrRouteBkupFlags has a value of 'hasLfa'."
    ::= { vRtrInetAllCidrRouteEntry 18 }

vRtrInetAllCidrRouteNHopRepCount OBJECT-TYPE
    SYNTAX      Unsigned32
    MAX-ACCESS  read-only
    STATUS      current
    DESCRIPTION
        "The value of vRtrInetAllCidrRouteNHopRepCount indicates the number of
         times the next-hop repeats for a particular route."
    ::= { vRtrInetAllCidrRouteEntry 19 }

vRtrInetAllCidrRtNextHopType     OBJECT-TYPE
    SYNTAX      TmnxInetCidrNextHopType
    MAX-ACCESS  read-only
    STATUS      current
    DESCRIPTION
        "The value of vRtrInetAllCidrRtNextHopType indicates the type of next
         hop for this route."
    ::= { vRtrInetAllCidrRouteEntry 20 }

vRtrInetAllCidrRtNextHopOwner    OBJECT-TYPE
    SYNTAX      TmnxInetCidrNextHopOwner
    MAX-ACCESS  read-only
    STATUS      current
    DESCRIPTION
        "The value of vRtrInetAllCidrRtNextHopOwner indicates the owner of next
         hop for this route."
    ::= { vRtrInetAllCidrRouteEntry 21 }

vRtrInetAllCidrRtNHOwnerAuxInfo  OBJECT-TYPE
    SYNTAX      Unsigned32
    MAX-ACCESS  read-only
    STATUS      current
    DESCRIPTION
        "The value of vRtrInetAllCidrRtNHOwnerAuxInfo indicates the auxiliary
         information for next hop owner as indicated by
         vRtrInetAllCidrRtNextHopOwner.

         The value of vRtrInetAllCidrRtNHOwnerAuxInfo indicates the tunnel id
         existing for this next hop type and owner."
    ::= { vRtrInetAllCidrRouteEntry 22 }

vRtrInetAllCidrRtBkupNHType      OBJECT-TYPE
    SYNTAX      TmnxInetCidrNextHopType
    MAX-ACCESS  read-only
    STATUS      current
    DESCRIPTION
        "The value of vRtrInetAllCidrRtBkupNHType indicates the type of next
         hop for this backup route."
    ::= { vRtrInetAllCidrRouteEntry 23 }

vRtrInetAllCidrRtBkupNHOwner     OBJECT-TYPE
    SYNTAX      TmnxInetCidrNextHopOwner
    MAX-ACCESS  read-only
    STATUS      current
    DESCRIPTION
        "The value of vRtrInetAllCidrRtBkupNHOwner indicates the owner of next
         hop for this backup route."
    ::= { vRtrInetAllCidrRouteEntry 24 }

vRtrInetAllCidrRtBkupNHOwnAxInfo OBJECT-TYPE
    SYNTAX      Unsigned32
    MAX-ACCESS  read-only
    STATUS      current
    DESCRIPTION
        "The value of vRtrInetAllCidrRtBkupNHOwnAxInfo indicates the auxiliary
         information for next hop owner as indicated by
         vRtrInetAllCidrRtBkupNHOwner.

         The value of vRtrInetAllCidrRtBkupNHOwnAxInfo indicates the tunnel id
         existing for this backup next hop type and owner."
    ::= { vRtrInetAllCidrRouteEntry 25 }

vRtrInetAllCidrRtSrcClassIndex   OBJECT-TYPE
    SYNTAX      ClassIndexOrNone
    MAX-ACCESS  read-only
    STATUS      current
    DESCRIPTION
        "The value of vRtrInetAllCidrRtSrcClassIndex indicates the source-class
         for this route."
    ::= { vRtrInetAllCidrRouteEntry 26 }

vRtrInetAllCidrRtDstClassIndex   OBJECT-TYPE
    SYNTAX      ClassIndexOrNone
    MAX-ACCESS  read-only
    STATUS      current
    DESCRIPTION
        "The value of vRtrInetAllCidrRtDstClassIndex indicates the
         destination-class for this route."
    ::= { vRtrInetAllCidrRouteEntry 27 }

vRtrInetAllCidrRtOperFlags       OBJECT-TYPE
    SYNTAX      TmnxRouteOperFlags
    MAX-ACCESS  read-only
    STATUS      current
    DESCRIPTION
        "The value of vRtrInetAllCidrRtOperFlags indicates the status of
         different properties of this route.

         If the 'stickyFlag' bit is set, then it indicates ECMP sticky flag is
         set on this route."
    ::= { vRtrInetAllCidrRouteEntry 28 }

vRtrInetAllCidrRtNextHopOwnInst  OBJECT-TYPE
    SYNTAX      Unsigned32
    MAX-ACCESS  read-only
    STATUS      current
    DESCRIPTION
        "The value of vRtrInetAllCidrRtNextHopOwnInst indicates the instance of
         the next hop owner as indicated by vRtrInetAllCidrRtNextHopOwner."
    ::= { vRtrInetAllCidrRouteEntry 29 }

vRtrInetAllCidrRtBkupNHOwnInst   OBJECT-TYPE
    SYNTAX      Unsigned32
    MAX-ACCESS  read-only
    STATUS      current
    DESCRIPTION
        "The value of vRtrInetAllCidrRtBkupNHOwnInst indicates the instance of
         the back up next hop owner as indicated by
         vRtrInetAllCidrRtBkupNHOwner."
    ::= { vRtrInetAllCidrRouteEntry 30 }

vRtrInetAllCidrRouteNHIsFec      OBJECT-TYPE
    SYNTAX      TruthValue
    MAX-ACCESS  read-only
    STATUS      current
    DESCRIPTION
        "When the value of vRtrInetAllCidrRouteNHIsFec is 'true', it indicates
         inetCidrRouteNextHop is a LDP FEC prefix. This is possible only with
         routes that resolve over LDP FECs. If 'true' then
         vRtrInetAllCidrRouteNHFecPfxLen has the prefix-length to be used with
         inetCidrRouteNextHop."
    ::= { vRtrInetAllCidrRouteEntry 31 }

vRtrInetAllCidrRouteNHFecPfxLen  OBJECT-TYPE
    SYNTAX      InetAddressPrefixLength
    MAX-ACCESS  read-only
    STATUS      current
    DESCRIPTION
        "The value of 'vRtrInetAllCidrRouteNHFecPfxLen' indicates the prefix
         length of the LDP FEC that resolves the route. This is valid only if
         vRtrInetAllCidrRouteNHIsFec is 'true', and when valid, this should be
         used in conjunction with inetCidrRouteNextHop to identify the LDP FEC
         that resolves the route."
    ::= { vRtrInetAllCidrRouteEntry 32 }

vRtrInetAllCidrRouteEgrVni       OBJECT-TYPE
    SYNTAX      Unsigned32 (0 | 1..16777215)
    MAX-ACCESS  read-only
    STATUS      current
    DESCRIPTION
        "The value of vRtrInetAllCidrRouteEgrVni specifies the egress VNI of
         the VXLAN."
    ::= { vRtrInetAllCidrRouteEntry 33 }

vRtrIfStatsTable                 OBJECT-TYPE
    SYNTAX      SEQUENCE OF VRtrIfStatsEntry
    MAX-ACCESS  not-accessible
    STATUS      current
    DESCRIPTION
        "The vRtrIfStatsTable table contains statistics per virtual router
         interface."
    ::= { tmnxVRtrObjs 54 }

vRtrIfStatsEntry                 OBJECT-TYPE
    SYNTAX      VRtrIfStatsEntry
    MAX-ACCESS  not-accessible
    STATUS      current
    DESCRIPTION
        "Each row entry represents the statistics per virtual router interface.
         Entries are created and deleted when entries in the vRtrIfEntry are
         created and deleted."
    INDEX       {
        vRtrID,
        vRtrIfIndex
    }
    ::= { vRtrIfStatsTable 1 }

VRtrIfStatsEntry                 ::= SEQUENCE
{
    vRtrIfuRPFCheckFailPkts          Counter64,
    vRtrIfuRPFCheckFailPktsLow32     Counter32,
    vRtrIfuRPFCheckFailPktsHigh32    Counter32,
    vRtrIfuRPFCheckFailBytes         Counter64,
    vRtrIfuRPFCheckFailBytesLow32    Counter32,
    vRtrIfuRPFCheckFailBytesHigh32   Counter32,
    vRtrIfIpReasFragPktsRcvd         Counter64,
    vRtrIfIpReasFragPktsRcvdLow32    Counter32,
    vRtrIfIpReasFragPktsRcvdHigh32   Counter32,
    vRtrIfIpReasFragBytesRcvd        Counter64,
    vRtrIfIpReasFragBytesRcvdLow32   Counter32,
    vRtrIfIpReasFragBytesRcvdHigh32  Counter32,
    vRtrIfIpReasFragPktsReas         Counter64,
    vRtrIfIpReasFragPktsReasLow32    Counter32,
    vRtrIfIpReasFragPktsReasHigh32   Counter32,
    vRtrIfIpReasFragBytesReas        Counter64,
    vRtrIfIpReasFragBytesReasLow32   Counter32,
    vRtrIfIpReasFragBytesReasHigh32  Counter32,
    vRtrIfIpReasFragReasErrors       Counter64,
    vRtrIfIpReasFragReasErrorsLow32  Counter32,
    vRtrIfIpReasFragReasErrorsHigh32 Counter32,
    vRtrIfIpReasFragDisc             Counter64,
    vRtrIfIpReasFragDiscLow32        Counter32,
    vRtrIfIpReasFragDiscHigh32       Counter32,
    vRtrIfIpReasOutBufRes            Counter64,
    vRtrIfIpReasOutBufResLow32       Counter32,
    vRtrIfIpReasOutBufResHigh32      Counter32,
    vRtrIfIpReasPktsRx               Counter64,
    vRtrIfIpReasPktsRxLow32          Counter32,
    vRtrIfIpReasPktsRxHigh32         Counter32,
    vRtrIfIpReasBytesRx              Counter64,
    vRtrIfIpReasBytesRxLow32         Counter32,
    vRtrIfIpReasBytesRxHigh32        Counter32,
    vRtrIfIpReasPktsTx               Counter64,
    vRtrIfIpReasPktsTxLow32          Counter32,
    vRtrIfIpReasPktsTxHigh32         Counter32,
    vRtrIfIpReasBytesTx              Counter64,
    vRtrIfIpReasBytesTxLow32         Counter32,
    vRtrIfIpReasBytesTxHigh32        Counter32,
    vRtrIfRxPkts                     Counter64,
    vRtrIfRxPktsLow32                Counter32,
    vRtrIfRxPktsHigh32               Counter32,
    vRtrIfRxBytes                    Counter64,
    vRtrIfRxBytesLow32               Counter32,
    vRtrIfRxBytesHigh32              Counter32,
    vRtrIfTxV4Pkts                   Counter64,
    vRtrIfTxV4PktsLow32              Counter32,
    vRtrIfTxV4PktsHigh32             Counter32,
    vRtrIfTxV4Bytes                  Counter64,
    vRtrIfTxV4BytesLow32             Counter32,
    vRtrIfTxV4BytesHigh32            Counter32,
    vRtrIfTxV6Pkts                   Counter64,
    vRtrIfTxV6PktsLow32              Counter32,
    vRtrIfTxV6PktsHigh32             Counter32,
    vRtrIfTxV6Bytes                  Counter64,
    vRtrIfTxV6BytesLow32             Counter32,
    vRtrIfTxV6BytesHigh32            Counter32,
    vRtrIfTxV4DiscardPkts            Counter64,
    vRtrIfTxV4DiscardPktsLow32       Counter32,
    vRtrIfTxV4DiscardPktsHigh32      Counter32,
    vRtrIfTxV4DiscardBytes           Counter64,
    vRtrIfTxV4DiscardBytesLow32      Counter32,
    vRtrIfTxV4DiscardBytesHigh32     Counter32,
    vRtrIfTxV6DiscardPkts            Counter64,
    vRtrIfTxV6DiscardPktsLow32       Counter32,
    vRtrIfTxV6DiscardPktsHigh32      Counter32,
    vRtrIfTxV6DiscardBytes           Counter64,
    vRtrIfTxV6DiscardBytesLow32      Counter32,
    vRtrIfTxV6DiscardBytesHigh32     Counter32,
    vRtrIfIpReasV6FragPktsRcvd       Counter64,
    vRtrIfIpReasV6FragPktsRcvdLow32  Counter32,
    vRtrIfIpReasV6FragPktsRcvdHigh32 Counter32,
    vRtrIfIpReasV6FragBytesRcvd      Counter64,
    vRtrIfIpReasV6FragBytesRcvdL32   Counter32,
    vRtrIfIpReasV6FragBytesRcvdH32   Counter32,
    vRtrIfIpReasV6FragPktsReas       Counter64,
    vRtrIfIpReasV6FragPktsReasLow32  Counter32,
    vRtrIfIpReasV6FragPktsReasHigh32 Counter32,
    vRtrIfIpReasV6FragBytesReas      Counter64,
    vRtrIfIpReasV6FragBytesReasL32   Counter32,
    vRtrIfIpReasV6FragBytesReasH32   Counter32,
    vRtrIfIpReasV6FragReasErrors     Counter64,
    vRtrIfIpReasV6FragReasErrorsL32  Counter32,
    vRtrIfIpReasV6FragReasErrorsH32  Counter32,
    vRtrIfIpReasV6FragDisc           Counter64,
    vRtrIfIpReasV6FragDiscLow32      Counter32,
    vRtrIfIpReasV6FragDiscHigh32     Counter32,
    vRtrIfIpReasV6OutBufRes          Counter64,
    vRtrIfIpReasV6OutBufResLow32     Counter32,
    vRtrIfIpReasV6OutBufResHigh32    Counter32,
    vRtrIfIpReasV6PktsRx             Counter64,
    vRtrIfIpReasV6PktsRxLow32        Counter32,
    vRtrIfIpReasV6PktsRxHigh32       Counter32,
    vRtrIfIpReasV6BytesRx            Counter64,
    vRtrIfIpReasV6BytesRxLow32       Counter32,
    vRtrIfIpReasV6BytesRxHigh32      Counter32,
    vRtrIfIpReasV6PktsTx             Counter64,
    vRtrIfIpReasV6PktsTxLow32        Counter32,
    vRtrIfIpReasV6PktsTxHigh32       Counter32,
    vRtrIfIpReasV6BytesTx            Counter64,
    vRtrIfIpReasV6BytesTxLow32       Counter32,
    vRtrIfIpReasV6BytesTxHigh32      Counter32,
    vRtrIfSpeed                      Counter64,
    vRtrIfRxV6Pkts                   Counter64,
    vRtrIfRxV6PktsLow32              Counter32,
    vRtrIfRxV6PktsHigh32             Counter32,
    vRtrIfRxV6Bytes                  Counter64,
    vRtrIfRxV6BytesLow32             Counter32,
    vRtrIfRxV6BytesHigh32            Counter32,
    vRtrIfV6uRPFCheckFailPkts        Counter64,
    vRtrIfV6uRPFCheckFailPktsLow32   Counter32,
    vRtrIfV6uRPFCheckFailPktsHigh32  Counter32,
    vRtrIfV6uRPFCheckFailBytes       Counter64,
    vRtrIfV6uRPFCheckFailBytesLow32  Counter32,
    vRtrIfV6uRPFCheckFailBytesHigh32 Counter32,
    vRtrIfRxV4Pkts                   Counter64,
    vRtrIfRxV4Bytes                  Counter64,
    vRtrIfV4uRPFCheckFailPkts        Counter64,
    vRtrIfV4uRPFCheckFailBytes       Counter64
}

vRtrIfuRPFCheckFailPkts          OBJECT-TYPE
    SYNTAX      Counter64
    MAX-ACCESS  read-only
    STATUS      current
    DESCRIPTION
        "The value of vRtrIfuRPFCheckFailPkts indicates the number of packets
         that fail uRPF check on this interface."
    ::= { vRtrIfStatsEntry 1 }

vRtrIfuRPFCheckFailPktsLow32     OBJECT-TYPE
    SYNTAX      Counter32
    MAX-ACCESS  read-only
    STATUS      current
    DESCRIPTION
        "The value of vRtrIfuRPFCheckFailPktsLow32 indicates the lower 32 bits
         of the value of vRtrIfuRPFCheckFailPkts."
    ::= { vRtrIfStatsEntry 2 }

vRtrIfuRPFCheckFailPktsHigh32    OBJECT-TYPE
    SYNTAX      Counter32
    MAX-ACCESS  read-only
    STATUS      current
    DESCRIPTION
        "The value of vRtrIfuRPFCheckFailPktsHigh32 indicates the high 32 bits
         of the value of vRtrIfuRPFCheckFailPkts."
    ::= { vRtrIfStatsEntry 3 }

vRtrIfuRPFCheckFailBytes         OBJECT-TYPE
    SYNTAX      Counter64
    MAX-ACCESS  read-only
    STATUS      current
    DESCRIPTION
        "The value of vRtrIfuRPFCheckFailBytes indicates the number of bytes in
         the packets that fail uRPF check."
    ::= { vRtrIfStatsEntry 4 }

vRtrIfuRPFCheckFailBytesLow32    OBJECT-TYPE
    SYNTAX      Counter32
    MAX-ACCESS  read-only
    STATUS      current
    DESCRIPTION
        "The value of vRtrIfuRPFCheckFailBytesLow32 indicates the lower 32 bits
         of the value of vRtrIfuRPFCheckFailBytes."
    ::= { vRtrIfStatsEntry 5 }

vRtrIfuRPFCheckFailBytesHigh32   OBJECT-TYPE
    SYNTAX      Counter32
    MAX-ACCESS  read-only
    STATUS      current
    DESCRIPTION
        "The value of vRtrIfuRPFCheckFailBytesHigh32 indicates the high 32 bits
         of the value of vRtrIfuRPFCheckFailBytes."
    ::= { vRtrIfStatsEntry 6 }

vRtrIfIpReasFragPktsRcvd         OBJECT-TYPE
    SYNTAX      Counter64
    MAX-ACCESS  read-only
    STATUS      current
    DESCRIPTION
        "The value of vRtrIfIpReasFragPktsRcvd indicates the number of
         fragmented packets received on this interface.

         The value of the object is '0' if the MDA type is not 'isa-ip-reas'."
    ::= { vRtrIfStatsEntry 7 }

vRtrIfIpReasFragPktsRcvdLow32    OBJECT-TYPE
    SYNTAX      Counter32
    MAX-ACCESS  read-only
    STATUS      current
    DESCRIPTION
        "The value of vRtrIfIpReasFragPktsRcvdLow32 indicates the lower 32 bits
         of the value of vRtrIfIpReasFragPktsRcvd."
    ::= { vRtrIfStatsEntry 8 }

vRtrIfIpReasFragPktsRcvdHigh32   OBJECT-TYPE
    SYNTAX      Counter32
    MAX-ACCESS  read-only
    STATUS      current
    DESCRIPTION
        "The value of vRtrIfIpReasFragPktsRcvdHigh32 indicates the high 32 bits
         of the value of vRtrIfIpReasFragPktsRcvd."
    ::= { vRtrIfStatsEntry 9 }

vRtrIfIpReasFragBytesRcvd        OBJECT-TYPE
    SYNTAX      Counter64
    MAX-ACCESS  read-only
    STATUS      current
    DESCRIPTION
        "The value of vRtrIfIpReasFragBytesRcvd indicates the number of
         fragmented bytes received on this interface.

         The value of the object is '0' if the MDA type is not 'isa-ip-reas'."
    ::= { vRtrIfStatsEntry 10 }

vRtrIfIpReasFragBytesRcvdLow32   OBJECT-TYPE
    SYNTAX      Counter32
    MAX-ACCESS  read-only
    STATUS      current
    DESCRIPTION
        "The value of vRtrIfIpReasFragBytesRcvdLow32 indicates the lower 32
         bits of the value of vRtrIfIpReasFragBytesRcvd."
    ::= { vRtrIfStatsEntry 11 }

vRtrIfIpReasFragBytesRcvdHigh32  OBJECT-TYPE
    SYNTAX      Counter32
    MAX-ACCESS  read-only
    STATUS      current
    DESCRIPTION
        "The value of vRtrIfIpReasFragBytesRcvdHigh32 indicates the high 32
         bits of the value of vRtrIfIpReasFragBytesRcvd."
    ::= { vRtrIfStatsEntry 12 }

vRtrIfIpReasFragPktsReas         OBJECT-TYPE
    SYNTAX      Counter64
    MAX-ACCESS  read-only
    STATUS      current
    DESCRIPTION
        "The value of vRtrIfIpReasFragPktsReas indicates the number of
         fragmented packets reassembled on this interface.

         The value of the object is '0' if the MDA type is not 'isa-ip-reas'."
    ::= { vRtrIfStatsEntry 13 }

vRtrIfIpReasFragPktsReasLow32    OBJECT-TYPE
    SYNTAX      Counter32
    MAX-ACCESS  read-only
    STATUS      current
    DESCRIPTION
        "The value of vRtrIfIpReasFragPktsReasLow32 indicates the lower 32 bits
         of the value of vRtrIfIpReasFragPktsReas."
    ::= { vRtrIfStatsEntry 14 }

vRtrIfIpReasFragPktsReasHigh32   OBJECT-TYPE
    SYNTAX      Counter32
    MAX-ACCESS  read-only
    STATUS      current
    DESCRIPTION
        "The value of vRtrIfIpReasFragPktsReasHigh32 indicates the high 32 bits
         of the value of vRtrIfIpReasFragPktsRcvd."
    ::= { vRtrIfStatsEntry 15 }

vRtrIfIpReasFragBytesReas        OBJECT-TYPE
    SYNTAX      Counter64
    MAX-ACCESS  read-only
    STATUS      current
    DESCRIPTION
        "The value of vRtrIfIpReasFragBytesReas indicates the number of
         fragmented bytes reassembled on this interface.

         The value of the object is '0' if the MDA type is not 'isa-ip-reas'."
    ::= { vRtrIfStatsEntry 16 }

vRtrIfIpReasFragBytesReasLow32   OBJECT-TYPE
    SYNTAX      Counter32
    MAX-ACCESS  read-only
    STATUS      current
    DESCRIPTION
        "The value of vRtrIfIpReasFragBytesReasLow32 indicates the lower 32
         bits of the value of vRtrIfIpReasFragBytesReas."
    ::= { vRtrIfStatsEntry 17 }

vRtrIfIpReasFragBytesReasHigh32  OBJECT-TYPE
    SYNTAX      Counter32
    MAX-ACCESS  read-only
    STATUS      current
    DESCRIPTION
        "The value of vRtrIfIpReasFragBytesReasHigh32 indicates the high 32
         bits of the value of vRtrIfIpReasFragBytesReas."
    ::= { vRtrIfStatsEntry 18 }

vRtrIfIpReasFragReasErrors       OBJECT-TYPE
    SYNTAX      Counter64
    MAX-ACCESS  read-only
    STATUS      current
    DESCRIPTION
        "The value of vRtrIfIpReasFragReasErrors indicates the number of
         reassembly errors occurred on this interface.

         The value of the object is '0' if the MDA type is not 'isa-ip-reas'."
    ::= { vRtrIfStatsEntry 19 }

vRtrIfIpReasFragReasErrorsLow32  OBJECT-TYPE
    SYNTAX      Counter32
    MAX-ACCESS  read-only
    STATUS      current
    DESCRIPTION
        "The value of vRtrIfIpReasFragReasErrorsLow32 indicates the lower 32
         bits of the value of vRtrIfIpReasFragReasErrors."
    ::= { vRtrIfStatsEntry 20 }

vRtrIfIpReasFragReasErrorsHigh32 OBJECT-TYPE
    SYNTAX      Counter32
    MAX-ACCESS  read-only
    STATUS      current
    DESCRIPTION
        "The value of vRtrIfIpReasFragReasErrorsHigh32 indicates the high 32
         bits of the value of vRtrIfIpReasFragReasErrors."
    ::= { vRtrIfStatsEntry 21 }

vRtrIfIpReasFragDisc             OBJECT-TYPE
    SYNTAX      Counter64
    MAX-ACCESS  read-only
    STATUS      current
    DESCRIPTION
        "The value of vRtrIfIpReasFragDisc indicates the number of packets
         reassembly discarded due to the timeout on this interface.

         The value of the object is '0' if the MDA type is not 'isa-ip-reas'."
    ::= { vRtrIfStatsEntry 22 }

vRtrIfIpReasFragDiscLow32        OBJECT-TYPE
    SYNTAX      Counter32
    MAX-ACCESS  read-only
    STATUS      current
    DESCRIPTION
        "The value of vRtrIfIpReasFragDiscLow32 indicates the lower 32 bits of
         the value of vRtrIfIpReasFragDisc."
    ::= { vRtrIfStatsEntry 23 }

vRtrIfIpReasFragDiscHigh32       OBJECT-TYPE
    SYNTAX      Counter32
    MAX-ACCESS  read-only
    STATUS      current
    DESCRIPTION
        "The value of vRtrIfIpReasFragDiscHigh32 indicates the high 32 bits of
         the value of vRtrIfIpReasFragDisc."
    ::= { vRtrIfStatsEntry 24 }

vRtrIfIpReasOutBufRes            OBJECT-TYPE
    SYNTAX      Counter64
    MAX-ACCESS  read-only
    STATUS      current
    DESCRIPTION
        "The value of vRtrIfIpReasOutBufRes indicates the number of times out
         of buffer resources happened while reassembly on this interface.

         The value of the object is '0' if the MDA type is not 'isa-ip-reas'."
    ::= { vRtrIfStatsEntry 25 }

vRtrIfIpReasOutBufResLow32       OBJECT-TYPE
    SYNTAX      Counter32
    MAX-ACCESS  read-only
    STATUS      current
    DESCRIPTION
        "The value of vRtrIfIpReasOutBufResLow32 indicates the lower 32 bits of
         the value of vRtrIfIpReasOutBufRes."
    ::= { vRtrIfStatsEntry 26 }

vRtrIfIpReasOutBufResHigh32      OBJECT-TYPE
    SYNTAX      Counter32
    MAX-ACCESS  read-only
    STATUS      current
    DESCRIPTION
        "The value of vRtrIfIpReasOutBufResHigh32 indicates the high 32 bits of
         the value of vRtrIfIpReasOutBufRes."
    ::= { vRtrIfStatsEntry 27 }

vRtrIfIpReasPktsRx               OBJECT-TYPE
    SYNTAX      Counter64
    MAX-ACCESS  read-only
    STATUS      current
    DESCRIPTION
        "The value of vRtrIfIpReasPktsRx indicates the number of total packets
         received on this interface.

         The value of the object is '0' if the MDA type is not 'isa-ip-reas'."
    ::= { vRtrIfStatsEntry 28 }

vRtrIfIpReasPktsRxLow32          OBJECT-TYPE
    SYNTAX      Counter32
    MAX-ACCESS  read-only
    STATUS      current
    DESCRIPTION
        "The value of vRtrIfIpReasPktsRxLow32 indicates the lower 32 bits of
         the value of vRtrIfIpReasPktsRx."
    ::= { vRtrIfStatsEntry 29 }

vRtrIfIpReasPktsRxHigh32         OBJECT-TYPE
    SYNTAX      Counter32
    MAX-ACCESS  read-only
    STATUS      current
    DESCRIPTION
        "The value of vRtrIfIpReasPktsRxHigh32 indicates the high 32 bits of
         the value of vRtrIfIpReasPktsRx."
    ::= { vRtrIfStatsEntry 30 }

vRtrIfIpReasBytesRx              OBJECT-TYPE
    SYNTAX      Counter64
    MAX-ACCESS  read-only
    STATUS      current
    DESCRIPTION
        "The value of vRtrIfIpReasBytesRx indicates the number of total bytes
         received on this interface.

         The value of the object is '0' if the MDA type is not 'isa-ip-reas'."
    ::= { vRtrIfStatsEntry 31 }

vRtrIfIpReasBytesRxLow32         OBJECT-TYPE
    SYNTAX      Counter32
    MAX-ACCESS  read-only
    STATUS      current
    DESCRIPTION
        "The value of vRtrIfIpReasBytesRxLow32 indicates the lower 32 bits of
         the value of vRtrIfIpReasBytesRx."
    ::= { vRtrIfStatsEntry 32 }

vRtrIfIpReasBytesRxHigh32        OBJECT-TYPE
    SYNTAX      Counter32
    MAX-ACCESS  read-only
    STATUS      current
    DESCRIPTION
        "The value of vRtrIfIpReasBytesRxHigh32 indicates the high 32 bits of
         the value of vRtrIfIpReasBytesRx."
    ::= { vRtrIfStatsEntry 33 }

vRtrIfIpReasPktsTx               OBJECT-TYPE
    SYNTAX      Counter64
    MAX-ACCESS  read-only
    STATUS      current
    DESCRIPTION
        "The value of vRtrIfIpReasPktsTx indicates the number of total packets
         sent from this interface.

         The value of the object is '0' if the MDA type is not 'isa-ip-reas'."
    ::= { vRtrIfStatsEntry 34 }

vRtrIfIpReasPktsTxLow32          OBJECT-TYPE
    SYNTAX      Counter32
    MAX-ACCESS  read-only
    STATUS      current
    DESCRIPTION
        "The value of vRtrIfIpReasPktsTxLow32 indicates the lower 32 bits of
         the value of vRtrIfIpReasPktsTx."
    ::= { vRtrIfStatsEntry 35 }

vRtrIfIpReasPktsTxHigh32         OBJECT-TYPE
    SYNTAX      Counter32
    MAX-ACCESS  read-only
    STATUS      current
    DESCRIPTION
        "The value of vRtrIfIpReasPktsTxHigh32 indicates the high 32 bits of
         the value of vRtrIfIpReasPktsTx."
    ::= { vRtrIfStatsEntry 36 }

vRtrIfIpReasBytesTx              OBJECT-TYPE
    SYNTAX      Counter64
    MAX-ACCESS  read-only
    STATUS      current
    DESCRIPTION
        "The value of vRtrIfIpReasBytesTx indicates the number of total bytes
         sent from this interface.

         The value of the object is '0' if the MDA type is not 'isa-ip-reas'."
    ::= { vRtrIfStatsEntry 37 }

vRtrIfIpReasBytesTxLow32         OBJECT-TYPE
    SYNTAX      Counter32
    MAX-ACCESS  read-only
    STATUS      current
    DESCRIPTION
        "The value of vRtrIfIpReasBytesTxLow32 indicates the lower 32 bits of
         the value of vRtrIfIpReasBytesTx."
    ::= { vRtrIfStatsEntry 38 }

vRtrIfIpReasBytesTxHigh32        OBJECT-TYPE
    SYNTAX      Counter32
    MAX-ACCESS  read-only
    STATUS      current
    DESCRIPTION
        "The value of vRtrIfIpReasBytesTxHigh32 indicates the high 32 bits of
         the value of vRtrIfIpReasBytesTx."
    ::= { vRtrIfStatsEntry 39 }

vRtrIfRxPkts                     OBJECT-TYPE
    SYNTAX      Counter64
    MAX-ACCESS  read-only
    STATUS      current
    DESCRIPTION
        "The value of vRtrIfRxPkts indicates the number of IP packets received
         by this interface."
    ::= { vRtrIfStatsEntry 40 }

vRtrIfRxPktsLow32                OBJECT-TYPE
    SYNTAX      Counter32
    MAX-ACCESS  read-only
    STATUS      current
    DESCRIPTION
        "The value of vRtrIfRxPktsLow32 indicates the lower 32 bits of the
         value of vRtrIfRxPkts."
    ::= { vRtrIfStatsEntry 41 }

vRtrIfRxPktsHigh32               OBJECT-TYPE
    SYNTAX      Counter32
    MAX-ACCESS  read-only
    STATUS      current
    DESCRIPTION
        "The value of vRtrIfRxPktsHigh32 indicates the high 32 bits of the
         value of vRtrIfRxPkts."
    ::= { vRtrIfStatsEntry 42 }

vRtrIfRxBytes                    OBJECT-TYPE
    SYNTAX      Counter64
    MAX-ACCESS  read-only
    STATUS      current
    DESCRIPTION
        "The value of vRtrIfRxBytes indicates the number of bytes in IPv4 and
         IPv6 packets received by this interface."
    ::= { vRtrIfStatsEntry 43 }

vRtrIfRxBytesLow32               OBJECT-TYPE
    SYNTAX      Counter32
    MAX-ACCESS  read-only
    STATUS      current
    DESCRIPTION
        "The value of vRtrIfRxBytesLow32 indicates the lower 32 bits of the
         value of vRtrIfRxBytes."
    ::= { vRtrIfStatsEntry 44 }

vRtrIfRxBytesHigh32              OBJECT-TYPE
    SYNTAX      Counter32
    MAX-ACCESS  read-only
    STATUS      current
    DESCRIPTION
        "The value of vRtrIfRxBytesHigh32 indicates the high 32 bits of the
         value of vRtrIfRxBytes."
    ::= { vRtrIfStatsEntry 45 }

vRtrIfTxV4Pkts                   OBJECT-TYPE
    SYNTAX      Counter64
    MAX-ACCESS  read-only
    STATUS      current
    DESCRIPTION
        "The value of vRtrIfTxV4Pkts indicates the number of total IPv4 packets
         sent from this interface."
    ::= { vRtrIfStatsEntry 46 }

vRtrIfTxV4PktsLow32              OBJECT-TYPE
    SYNTAX      Counter32
    MAX-ACCESS  read-only
    STATUS      current
    DESCRIPTION
        "The value of vRtrIfTxV4PktsLow32 indicates the lower 32 bits of the
         value of vRtrIfTxV4Pkts."
    ::= { vRtrIfStatsEntry 47 }

vRtrIfTxV4PktsHigh32             OBJECT-TYPE
    SYNTAX      Counter32
    MAX-ACCESS  read-only
    STATUS      current
    DESCRIPTION
        "The value of vRtrIfTxV4PktsHigh32 indicates the high 32 bits of the
         value of vRtrIfTxV4Pkts."
    ::= { vRtrIfStatsEntry 48 }

vRtrIfTxV4Bytes                  OBJECT-TYPE
    SYNTAX      Counter64
    MAX-ACCESS  read-only
    STATUS      current
    DESCRIPTION
        "The value of vRtrIfTxV4Bytes indicates the number of total IPv4 bytes
         sent from this interface."
    ::= { vRtrIfStatsEntry 49 }

vRtrIfTxV4BytesLow32             OBJECT-TYPE
    SYNTAX      Counter32
    MAX-ACCESS  read-only
    STATUS      current
    DESCRIPTION
        "The value of vRtrIfTxV4BytesLow32 indicates the lower 32 bits of the
         value of vRtrIfTxV4Bytes."
    ::= { vRtrIfStatsEntry 50 }

vRtrIfTxV4BytesHigh32            OBJECT-TYPE
    SYNTAX      Counter32
    MAX-ACCESS  read-only
    STATUS      current
    DESCRIPTION
        "The value of vRtrIfTxV4BytesHigh32 indicates the high 32 bits of the
         value of vRtrIfTxV4Bytes."
    ::= { vRtrIfStatsEntry 51 }

vRtrIfTxV6Pkts                   OBJECT-TYPE
    SYNTAX      Counter64
    MAX-ACCESS  read-only
    STATUS      current
    DESCRIPTION
        "The value of vRtrIfTxV6Pkts indicates the number of total IPv6 packets
         sent from this interface."
    ::= { vRtrIfStatsEntry 52 }

vRtrIfTxV6PktsLow32              OBJECT-TYPE
    SYNTAX      Counter32
    MAX-ACCESS  read-only
    STATUS      current
    DESCRIPTION
        "The value of vRtrIfTxV6PktsLow32 indicates the lower 32 bits of the
         value of vRtrIfTxV6Pkts."
    ::= { vRtrIfStatsEntry 53 }

vRtrIfTxV6PktsHigh32             OBJECT-TYPE
    SYNTAX      Counter32
    MAX-ACCESS  read-only
    STATUS      current
    DESCRIPTION
        "The value of vRtrIfTxV6PktsHigh32 indicates the high 32 bits of the
         value of vRtrIfTxV6Pkts."
    ::= { vRtrIfStatsEntry 54 }

vRtrIfTxV6Bytes                  OBJECT-TYPE
    SYNTAX      Counter64
    MAX-ACCESS  read-only
    STATUS      current
    DESCRIPTION
        "The value of vRtrIfTxV6Bytes indicates the number of total IPv6 bytes
         sent from this interface."
    ::= { vRtrIfStatsEntry 55 }

vRtrIfTxV6BytesLow32             OBJECT-TYPE
    SYNTAX      Counter32
    MAX-ACCESS  read-only
    STATUS      current
    DESCRIPTION
        "The value of vRtrIfTxV6BytesLow32 indicates the lower 32 bits of the
         value of vRtrIfTxV6Bytes."
    ::= { vRtrIfStatsEntry 56 }

vRtrIfTxV6BytesHigh32            OBJECT-TYPE
    SYNTAX      Counter32
    MAX-ACCESS  read-only
    STATUS      current
    DESCRIPTION
        "The value of vRtrIfTxV6BytesHigh32 indicates the high 32 bits of the
         value of vRtrIfTxV6Bytes."
    ::= { vRtrIfStatsEntry 57 }

vRtrIfTxV4DiscardPkts            OBJECT-TYPE
    SYNTAX      Counter64
    MAX-ACCESS  read-only
    STATUS      current
    DESCRIPTION
        "The value of vRtrIfTxV4DiscardPkts indicates the number of total IPv4
         transmit packets discarded by this interface."
    ::= { vRtrIfStatsEntry 58 }

vRtrIfTxV4DiscardPktsLow32       OBJECT-TYPE
    SYNTAX      Counter32
    MAX-ACCESS  read-only
    STATUS      current
    DESCRIPTION
        "The value of vRtrIfTxV4DiscardPktsLow32 indicates the lower 32 bits of
         the value of vRtrIfTxV4DiscardPkts."
    ::= { vRtrIfStatsEntry 59 }

vRtrIfTxV4DiscardPktsHigh32      OBJECT-TYPE
    SYNTAX      Counter32
    MAX-ACCESS  read-only
    STATUS      current
    DESCRIPTION
        "The value of vRtrIfTxV4DiscardPktsHigh32 indicates the high 32 bits of
         the value of vRtrIfTxV4DiscardPkts."
    ::= { vRtrIfStatsEntry 60 }

vRtrIfTxV4DiscardBytes           OBJECT-TYPE
    SYNTAX      Counter64
    MAX-ACCESS  read-only
    STATUS      current
    DESCRIPTION
        "The value of vRtrIfTxV4DiscardBytes indicates the number of total IPv4
         transmit bytes discarded by this interface."
    ::= { vRtrIfStatsEntry 61 }

vRtrIfTxV4DiscardBytesLow32      OBJECT-TYPE
    SYNTAX      Counter32
    MAX-ACCESS  read-only
    STATUS      current
    DESCRIPTION
        "The value of vRtrIfTxV4DiscardBytesLow32 indicates the lower 32 bits
         of the value of vRtrIfTxV4DiscardBytes."
    ::= { vRtrIfStatsEntry 62 }

vRtrIfTxV4DiscardBytesHigh32     OBJECT-TYPE
    SYNTAX      Counter32
    MAX-ACCESS  read-only
    STATUS      current
    DESCRIPTION
        "The value of vRtrIfTxV4DiscardBytesHigh32 indicates the high 32 bits
         of the value of vRtrIfTxV4DiscardBytes."
    ::= { vRtrIfStatsEntry 63 }

vRtrIfTxV6DiscardPkts            OBJECT-TYPE
    SYNTAX      Counter64
    MAX-ACCESS  read-only
    STATUS      current
    DESCRIPTION
        "The value of vRtrIfTxV6DiscardPkts indicates the number of total IPv6
         transmit packets discarded by this interface."
    ::= { vRtrIfStatsEntry 64 }

vRtrIfTxV6DiscardPktsLow32       OBJECT-TYPE
    SYNTAX      Counter32
    MAX-ACCESS  read-only
    STATUS      current
    DESCRIPTION
        "The value of vRtrIfTxV6DiscardPktsLow32 indicates the lower 32 bits of
         the value of vRtrIfTxV6DiscardPkts."
    ::= { vRtrIfStatsEntry 65 }

vRtrIfTxV6DiscardPktsHigh32      OBJECT-TYPE
    SYNTAX      Counter32
    MAX-ACCESS  read-only
    STATUS      current
    DESCRIPTION
        "The value of vRtrIfTxV6DiscardPktsHigh32 indicates the high 32 bits of
         the value of vRtrIfTxV6DiscardPkts."
    ::= { vRtrIfStatsEntry 66 }

vRtrIfTxV6DiscardBytes           OBJECT-TYPE
    SYNTAX      Counter64
    MAX-ACCESS  read-only
    STATUS      current
    DESCRIPTION
        "The value of vRtrIfTxV6DiscardBytes indicates the number of total IPv6
         transmit bytes discarded by this interface."
    ::= { vRtrIfStatsEntry 67 }

vRtrIfTxV6DiscardBytesLow32      OBJECT-TYPE
    SYNTAX      Counter32
    MAX-ACCESS  read-only
    STATUS      current
    DESCRIPTION
        "The value of vRtrIfTxV6DiscardBytesLow32 indicates the lower 32 bits
         of the value of vRtrIfTxV6DiscardBytes."
    ::= { vRtrIfStatsEntry 68 }

vRtrIfTxV6DiscardBytesHigh32     OBJECT-TYPE
    SYNTAX      Counter32
    MAX-ACCESS  read-only
    STATUS      current
    DESCRIPTION
        "The value of vRtrIfTxV6DiscardBytesHigh32 indicates the high 32 bits
         of the value of vRtrIfTxV6DiscardBytes."
    ::= { vRtrIfStatsEntry 69 }

vRtrIfIpReasV6FragPktsRcvd       OBJECT-TYPE
    SYNTAX      Counter64
    MAX-ACCESS  read-only
    STATUS      current
    DESCRIPTION
        "The value of vRtrIfIpReasV6FragPktsRcvd indicates the number of IPv6
         fragmented packets received on this interface.

         The value of the object is '0' if the MDA type is not 'isa-ip-reas'."
    ::= { vRtrIfStatsEntry 70 }

vRtrIfIpReasV6FragPktsRcvdLow32  OBJECT-TYPE
    SYNTAX      Counter32
    MAX-ACCESS  read-only
    STATUS      current
    DESCRIPTION
        "The value of vRtrIfIpReasV6FragPktsRcvdLow32 indicates the lower 32
         bits of the value of vRtrIfIpReasV6FragPktsRcvd."
    ::= { vRtrIfStatsEntry 71 }

vRtrIfIpReasV6FragPktsRcvdHigh32 OBJECT-TYPE
    SYNTAX      Counter32
    MAX-ACCESS  read-only
    STATUS      current
    DESCRIPTION
        "The value of vRtrIfIpReasV6FragPktsRcvdHigh32 indicates the high 32
         bits of the value of vRtrIfIpReasV6FragPktsRcvd."
    ::= { vRtrIfStatsEntry 72 }

vRtrIfIpReasV6FragBytesRcvd      OBJECT-TYPE
    SYNTAX      Counter64
    MAX-ACCESS  read-only
    STATUS      current
    DESCRIPTION
        "The value of vRtrIfIpReasV6FragBytesRcvd indicates the number of IPv6
         fragmented bytes received on this interface.

         The value of the object is '0' if the MDA type is not 'isa-ip-reas'."
    ::= { vRtrIfStatsEntry 73 }

vRtrIfIpReasV6FragBytesRcvdL32   OBJECT-TYPE
    SYNTAX      Counter32
    MAX-ACCESS  read-only
    STATUS      current
    DESCRIPTION
        "The value of vRtrIfIpReasV6FragBytesRcvdL32 indicates the lower 32
         bits of the value of vRtrIfIpReasV6FragBytesRcvd."
    ::= { vRtrIfStatsEntry 74 }

vRtrIfIpReasV6FragBytesRcvdH32   OBJECT-TYPE
    SYNTAX      Counter32
    MAX-ACCESS  read-only
    STATUS      current
    DESCRIPTION
        "The value of vRtrIfIpReasV6FragBytesRcvdH32 indicates the high 32 bits
         of the value of vRtrIfIpReasV6FragBytesRcvd."
    ::= { vRtrIfStatsEntry 75 }

vRtrIfIpReasV6FragPktsReas       OBJECT-TYPE
    SYNTAX      Counter64
    MAX-ACCESS  read-only
    STATUS      current
    DESCRIPTION
        "The value of vRtrIfIpReasV6FragPktsReas indicates the number of IPv6
         fragmented packets reassembled on this interface.

         The value of the object is '0' if the MDA type is not 'isa-ip-reas'."
    ::= { vRtrIfStatsEntry 76 }

vRtrIfIpReasV6FragPktsReasLow32  OBJECT-TYPE
    SYNTAX      Counter32
    MAX-ACCESS  read-only
    STATUS      current
    DESCRIPTION
        "The value of vRtrIfIpReasV6FragPktsReasLow32 indicates the lower 32
         bits of the value of vRtrIfIpReasV6FragPktsReas."
    ::= { vRtrIfStatsEntry 77 }

vRtrIfIpReasV6FragPktsReasHigh32 OBJECT-TYPE
    SYNTAX      Counter32
    MAX-ACCESS  read-only
    STATUS      current
    DESCRIPTION
        "The value of vRtrIfIpReasV6FragPktsReasHigh32 indicates the high 32
         bits of the value of vRtrIfIpReasV6FragPktsRcvd."
    ::= { vRtrIfStatsEntry 78 }

vRtrIfIpReasV6FragBytesReas      OBJECT-TYPE
    SYNTAX      Counter64
    MAX-ACCESS  read-only
    STATUS      current
    DESCRIPTION
        "The value of vRtrIfIpReasV6FragBytesReas indicates the number of IPv6
         fragmented bytes reassembled on this interface.

         The value of the object is '0' if the MDA type is not 'isa-ip-reas'."
    ::= { vRtrIfStatsEntry 79 }

vRtrIfIpReasV6FragBytesReasL32   OBJECT-TYPE
    SYNTAX      Counter32
    MAX-ACCESS  read-only
    STATUS      current
    DESCRIPTION
        "The value of vRtrIfIpReasV6FragBytesReasL32 indicates the lower 32
         bits of the value of vRtrIfIpReasV6FragBytesReas."
    ::= { vRtrIfStatsEntry 80 }

vRtrIfIpReasV6FragBytesReasH32   OBJECT-TYPE
    SYNTAX      Counter32
    MAX-ACCESS  read-only
    STATUS      current
    DESCRIPTION
        "The value of vRtrIfIpReasV6FragBytesReasH32 indicates the high 32 bits
         of the value of vRtrIfIpReasV6FragBytesReas."
    ::= { vRtrIfStatsEntry 81 }

vRtrIfIpReasV6FragReasErrors     OBJECT-TYPE
    SYNTAX      Counter64
    MAX-ACCESS  read-only
    STATUS      current
    DESCRIPTION
        "The value of vRtrIfIpReasV6FragReasErrors indicates the number of IPv6
         reassembly errors occurred on this interface.

         The value of the object is '0' if the MDA type is not 'isa-ip-reas'."
    ::= { vRtrIfStatsEntry 82 }

vRtrIfIpReasV6FragReasErrorsL32  OBJECT-TYPE
    SYNTAX      Counter32
    MAX-ACCESS  read-only
    STATUS      current
    DESCRIPTION
        "The value of vRtrIfIpReasV6FragReasErrorsL32 indicates the lower 32
         bits of the value of vRtrIfIpReasV6FragReasErrors."
    ::= { vRtrIfStatsEntry 83 }

vRtrIfIpReasV6FragReasErrorsH32  OBJECT-TYPE
    SYNTAX      Counter32
    MAX-ACCESS  read-only
    STATUS      current
    DESCRIPTION
        "The value of vRtrIfIpReasV6FragReasErrorsH32 indicates the high 32
         bits of the value of vRtrIfIpReasV6FragReasErrors."
    ::= { vRtrIfStatsEntry 84 }

vRtrIfIpReasV6FragDisc           OBJECT-TYPE
    SYNTAX      Counter64
    MAX-ACCESS  read-only
    STATUS      current
    DESCRIPTION
        "The value of vRtrIfIpReasV6FragDisc indicates the number of IPv6
         packets reassembly discarded due to the timeout on this interface.

         The value of the object is '0' if the MDA type is not 'isa-ip-reas'."
    ::= { vRtrIfStatsEntry 85 }

vRtrIfIpReasV6FragDiscLow32      OBJECT-TYPE
    SYNTAX      Counter32
    MAX-ACCESS  read-only
    STATUS      current
    DESCRIPTION
        "The value of vRtrIfIpReasV6FragDiscLow32 indicates the lower 32 bits
         of the value of vRtrIfIpReasV6FragDisc."
    ::= { vRtrIfStatsEntry 86 }

vRtrIfIpReasV6FragDiscHigh32     OBJECT-TYPE
    SYNTAX      Counter32
    MAX-ACCESS  read-only
    STATUS      current
    DESCRIPTION
        "The value of vRtrIfIpReasV6FragDiscHigh32 indicates the high 32 bits
         of the value of vRtrIfIpReasV6FragDisc."
    ::= { vRtrIfStatsEntry 87 }

vRtrIfIpReasV6OutBufRes          OBJECT-TYPE
    SYNTAX      Counter64
    MAX-ACCESS  read-only
    STATUS      current
    DESCRIPTION
        "The value of vRtrIfIpReasV6OutBufRes indicates the number of times out
         of buffer resources happened while IPv6 reassembly on this interface.

         The value of the object is '0' if the MDA type is not 'isa-ip-reas'."
    ::= { vRtrIfStatsEntry 88 }

vRtrIfIpReasV6OutBufResLow32     OBJECT-TYPE
    SYNTAX      Counter32
    MAX-ACCESS  read-only
    STATUS      current
    DESCRIPTION
        "The value of vRtrIfIpReasV6OutBufResLow32 indicates the lower 32 bits
         of the value of vRtrIfIpReasV6OutBufRes."
    ::= { vRtrIfStatsEntry 89 }

vRtrIfIpReasV6OutBufResHigh32    OBJECT-TYPE
    SYNTAX      Counter32
    MAX-ACCESS  read-only
    STATUS      current
    DESCRIPTION
        "The value of vRtrIfIpReasV6OutBufResHigh32 indicates the high 32 bits
         of the value of vRtrIfIpReasV6OutBufRes."
    ::= { vRtrIfStatsEntry 90 }

vRtrIfIpReasV6PktsRx             OBJECT-TYPE
    SYNTAX      Counter64
    MAX-ACCESS  read-only
    STATUS      current
    DESCRIPTION
        "The value of vRtrIfIpReasV6PktsRx indicates the number of total IPv6
         packets received on this interface.

         The value of the object is '0' if the MDA type is not 'isa-ip-reas'."
    ::= { vRtrIfStatsEntry 91 }

vRtrIfIpReasV6PktsRxLow32        OBJECT-TYPE
    SYNTAX      Counter32
    MAX-ACCESS  read-only
    STATUS      current
    DESCRIPTION
        "The value of vRtrIfIpReasV6PktsRxLow32 indicates the lower 32 bits of
         the value of vRtrIfIpReasV6PktsRx."
    ::= { vRtrIfStatsEntry 92 }

vRtrIfIpReasV6PktsRxHigh32       OBJECT-TYPE
    SYNTAX      Counter32
    MAX-ACCESS  read-only
    STATUS      current
    DESCRIPTION
        "The value of vRtrIfIpReasV6PktsRxHigh32 indicates the high 32 bits of
         the value of vRtrIfIpReasV6PktsRx."
    ::= { vRtrIfStatsEntry 93 }

vRtrIfIpReasV6BytesRx            OBJECT-TYPE
    SYNTAX      Counter64
    MAX-ACCESS  read-only
    STATUS      current
    DESCRIPTION
        "The value of vRtrIfIpReasV6BytesRx indicates the number of total IPv6
         bytes received on this interface.

         The value of the object is '0' if the MDA type is not 'isa-ip-reas'."
    ::= { vRtrIfStatsEntry 94 }

vRtrIfIpReasV6BytesRxLow32       OBJECT-TYPE
    SYNTAX      Counter32
    MAX-ACCESS  read-only
    STATUS      current
    DESCRIPTION
        "The value of vRtrIfIpReasV6BytesRxLow32 indicates the lower 32 bits of
         the value of vRtrIfIpReasV6BytesRx."
    ::= { vRtrIfStatsEntry 95 }

vRtrIfIpReasV6BytesRxHigh32      OBJECT-TYPE
    SYNTAX      Counter32
    MAX-ACCESS  read-only
    STATUS      current
    DESCRIPTION
        "The value of vRtrIfIpReasV6BytesRxHigh32 indicates the high 32 bits of
         the value of vRtrIfIpReasV6BytesRx."
    ::= { vRtrIfStatsEntry 96 }

vRtrIfIpReasV6PktsTx             OBJECT-TYPE
    SYNTAX      Counter64
    MAX-ACCESS  read-only
    STATUS      current
    DESCRIPTION
        "The value of vRtrIfIpReasV6PktsTx indicates the number of total IPv6
         packets sent from this interface.

         The value of the object is '0' if the MDA type is not 'isa-ip-reas'."
    ::= { vRtrIfStatsEntry 97 }

vRtrIfIpReasV6PktsTxLow32        OBJECT-TYPE
    SYNTAX      Counter32
    MAX-ACCESS  read-only
    STATUS      current
    DESCRIPTION
        "The value of vRtrIfIpReasV6PktsTxLow32 indicates the lower 32 bits of
         the value of vRtrIfIpReasV6PktsTx."
    ::= { vRtrIfStatsEntry 98 }

vRtrIfIpReasV6PktsTxHigh32       OBJECT-TYPE
    SYNTAX      Counter32
    MAX-ACCESS  read-only
    STATUS      current
    DESCRIPTION
        "The value of vRtrIfIpReasV6PktsTxHigh32 indicates the high 32 bits of
         the value of vRtrIfIpReasV6PktsTx."
    ::= { vRtrIfStatsEntry 99 }

vRtrIfIpReasV6BytesTx            OBJECT-TYPE
    SYNTAX      Counter64
    MAX-ACCESS  read-only
    STATUS      current
    DESCRIPTION
        "The value of vRtrIfIpReasV6BytesTx indicates the number of total IPv6
         bytes sent from this interface.

         The value of the object is '0' if the MDA type is not 'isa-ip-reas'."
    ::= { vRtrIfStatsEntry 100 }

vRtrIfIpReasV6BytesTxLow32       OBJECT-TYPE
    SYNTAX      Counter32
    MAX-ACCESS  read-only
    STATUS      current
    DESCRIPTION
        "The value of vRtrIfIpReasV6BytesTxLow32 indicates the lower 32 bits of
         the value of vRtrIfIpReasV6BytesTx."
    ::= { vRtrIfStatsEntry 101 }

vRtrIfIpReasV6BytesTxHigh32      OBJECT-TYPE
    SYNTAX      Counter32
    MAX-ACCESS  read-only
    STATUS      current
    DESCRIPTION
        "The value of vRtrIfIpReasV6BytesTxHigh32 indicates the high 32 bits of
         the value of vRtrIfIpReasV6BytesTx."
    ::= { vRtrIfStatsEntry 102 }

vRtrIfSpeed                      OBJECT-TYPE
    SYNTAX      Counter64
    MAX-ACCESS  read-only
    STATUS      current
    DESCRIPTION
        "The value of vRtrIfSpeed indicates an estimate of the current
         bandwidth in bits per second for this interface."
    ::= { vRtrIfStatsEntry 103 }

vRtrIfRxV6Pkts                   OBJECT-TYPE
    SYNTAX      Counter64
    MAX-ACCESS  read-only
    STATUS      current
    DESCRIPTION
        "The value of vRtrIfRxV6Pkts indicates the number of IPv6 packets
         received by this interface."
    ::= { vRtrIfStatsEntry 110 }

vRtrIfRxV6PktsLow32              OBJECT-TYPE
    SYNTAX      Counter32
    MAX-ACCESS  read-only
    STATUS      current
    DESCRIPTION
        "The value of vRtrIfRxV6PktsLow32 indicates the lower 32 bits of the
         value of vRtrIfRxV6Pkts."
    ::= { vRtrIfStatsEntry 111 }

vRtrIfRxV6PktsHigh32             OBJECT-TYPE
    SYNTAX      Counter32
    MAX-ACCESS  read-only
    STATUS      current
    DESCRIPTION
        "The value of vRtrIfRxV6PktsHigh32 indicates the high 32 bits of the
         value of vRtrIfRxV6Pkts."
    ::= { vRtrIfStatsEntry 112 }

vRtrIfRxV6Bytes                  OBJECT-TYPE
    SYNTAX      Counter64
    MAX-ACCESS  read-only
    STATUS      current
    DESCRIPTION
        "The value of vRtrIfRxV6Bytes indicates the number of bytes in IPv6
         packets received by this interface."
    ::= { vRtrIfStatsEntry 113 }

vRtrIfRxV6BytesLow32             OBJECT-TYPE
    SYNTAX      Counter32
    MAX-ACCESS  read-only
    STATUS      current
    DESCRIPTION
        "The value of vRtrIfRxV6BytesLow32 indicates the lower 32 bits word of
         the value of vRtrIfRxV6Bytes."
    ::= { vRtrIfStatsEntry 114 }

vRtrIfRxV6BytesHigh32            OBJECT-TYPE
    SYNTAX      Counter32
    MAX-ACCESS  read-only
    STATUS      current
    DESCRIPTION
        "The value of vRtrIfRxV6BytesHigh32 indicates the high 32 bits word of
         the value of vRtrIfRxV6Bytes."
    ::= { vRtrIfStatsEntry 115 }

vRtrIfV6uRPFCheckFailPkts        OBJECT-TYPE
    SYNTAX      Counter64
    MAX-ACCESS  read-only
    STATUS      current
    DESCRIPTION
        "The value of vRtrIfV6uRPFCheckFailPkts indicates the number of IPv6
         packets that fail uRPF check on this interface."
    ::= { vRtrIfStatsEntry 116 }

vRtrIfV6uRPFCheckFailPktsLow32   OBJECT-TYPE
    SYNTAX      Counter32
    MAX-ACCESS  read-only
    STATUS      current
    DESCRIPTION
        "The value of vRtrIfV6uRPFCheckFailPktsLow32 indicates the lower 32
         bits word of the value of vRtrIfV6uRPFCheckFailPkts."
    ::= { vRtrIfStatsEntry 117 }

vRtrIfV6uRPFCheckFailPktsHigh32  OBJECT-TYPE
    SYNTAX      Counter32
    MAX-ACCESS  read-only
    STATUS      current
    DESCRIPTION
        "The value of vRtrIfV6uRPFCheckFailPktsHigh32 indicates the high 32
         bits word of the value of vRtrIfV6uRPFCheckFailPkts."
    ::= { vRtrIfStatsEntry 118 }

vRtrIfV6uRPFCheckFailBytes       OBJECT-TYPE
    SYNTAX      Counter64
    MAX-ACCESS  read-only
    STATUS      current
    DESCRIPTION
        "The value of vRtrIfV6uRPFCheckFailBytes indicates the number of bytes
         in IPv6 packets that fail uRPF check on this interface."
    ::= { vRtrIfStatsEntry 119 }

vRtrIfV6uRPFCheckFailBytesLow32  OBJECT-TYPE
    SYNTAX      Counter32
    MAX-ACCESS  read-only
    STATUS      current
    DESCRIPTION
        "The value of vRtrIfV6uRPFCheckFailBytesLow32 indicates the lower 32
         bits word of the value of vRtrIfV6uRPFCheckFailBytes."
    ::= { vRtrIfStatsEntry 120 }

vRtrIfV6uRPFCheckFailBytesHigh32 OBJECT-TYPE
    SYNTAX      Counter32
    MAX-ACCESS  read-only
    STATUS      current
    DESCRIPTION
        "The value of vRtrIfV6uRPFCheckFailBytesHigh32 indicates the high 32
         bits word of the value of vRtrIfV6uRPFCheckFailBytes."
    ::= { vRtrIfStatsEntry 121 }

vRtrIfRxV4Pkts                   OBJECT-TYPE
    SYNTAX      Counter64
    MAX-ACCESS  read-only
    STATUS      current
    DESCRIPTION
        "The value of vRtrIfRxV4Pkts indicates the number of IPv4 packets
         received by this interface."
    ::= { vRtrIfStatsEntry 122 }

vRtrIfRxV4Bytes                  OBJECT-TYPE
    SYNTAX      Counter64
    MAX-ACCESS  read-only
    STATUS      current
    DESCRIPTION
        "The value of vRtrIfRxV4Bytes indicates the number of bytes in IPv4
         packets received by this interface."
    ::= { vRtrIfStatsEntry 123 }

vRtrIfV4uRPFCheckFailPkts        OBJECT-TYPE
    SYNTAX      Counter64
    MAX-ACCESS  read-only
    STATUS      current
    DESCRIPTION
        "The value of vRtrIfV4uRPFCheckFailPkts indicates the number of IPv4
         packets that fail uRPF check on this interface."
    ::= { vRtrIfStatsEntry 124 }

vRtrIfV4uRPFCheckFailBytes       OBJECT-TYPE
    SYNTAX      Counter64
    MAX-ACCESS  read-only
    STATUS      current
    DESCRIPTION
        "The value of vRtrIfV4uRPFCheckFailBytes indicates the number of bytes
         in IPv4 packets that fail uRPF check on this interface."
    ::= { vRtrIfStatsEntry 125 }

vRtrNetDomainTblLastChanged      OBJECT-TYPE
    SYNTAX      TimeStamp
    MAX-ACCESS  read-only
    STATUS      current
    DESCRIPTION
        "The value of vRtrNetDomainTblLastChanged indicates the sysUpTime at
         the time of the last modification of vRtrNetDomainTable.

         If no changes were made to the table since the last re-initialization
         of the local network management subsystem, then this object contains a
         zero value."
    ::= { tmnxVRtrObjs 55 }

vRtrNetDomainTable               OBJECT-TYPE
    SYNTAX      SEQUENCE OF VRtrNetDomainEntry
    MAX-ACCESS  not-accessible
    STATUS      current
    DESCRIPTION
        "The vRtrNetDomainTable table contains network-domains which can be
         then associated with individual interfaces and SDPs."
    ::= { tmnxVRtrObjs 56 }

vRtrNetDomainEntry               OBJECT-TYPE
    SYNTAX      VRtrNetDomainEntry
    MAX-ACCESS  not-accessible
    STATUS      current
    DESCRIPTION
        "Each row entry represents the network-domains per virtual router
         interface. There will always be at least one row entry in this table
         which represents the 'default' network-domain. This entry is created
         when the system is initialized and can never be deleted."
    INDEX       {
        vRtrID,
        vRtrNetDomainName
    }
    ::= { vRtrNetDomainTable 1 }

VRtrNetDomainEntry               ::= SEQUENCE
{
    vRtrNetDomainName                TNamedItem,
    vRtrNetDomainRowStatus           RowStatus,
    vRtrNetDomainLastChanged         TimeStamp,
    vRtrNetDomainDesc                TItemDescription,
    vRtrNetDomainIfAssociationCnt    Gauge32,
    vRtrNetDomainSdpAssociationCnt   Gauge32,
    vRtrNetDomainMcastAssociationCnt Gauge32
}

vRtrNetDomainName                OBJECT-TYPE
    SYNTAX      TNamedItem
    MAX-ACCESS  not-accessible
    STATUS      current
    DESCRIPTION
        "The value of vRtrNetDomainName specifies the network-domain name
         configured on this virtual router. There will always be at least one
         network-domain  entry defined by the agent with value 'default' which
         represents the default network-domain."
    ::= { vRtrNetDomainEntry 1 }

vRtrNetDomainRowStatus           OBJECT-TYPE
    SYNTAX      RowStatus
    MAX-ACCESS  read-create
    STATUS      current
    DESCRIPTION
        "The value of the object vRtrNetDomainRowStatus specifies the Row
         status of this table row. This object is used to create or delete rows
         in this table."
    ::= { vRtrNetDomainEntry 2 }

vRtrNetDomainLastChanged         OBJECT-TYPE
    SYNTAX      TimeStamp
    MAX-ACCESS  read-only
    STATUS      current
    DESCRIPTION
        "The value of vRtrNetDomainLastChanged indicates the sysUpTime when any
         object of the row is last changed."
    ::= { vRtrNetDomainEntry 3 }

vRtrNetDomainDesc                OBJECT-TYPE
    SYNTAX      TItemDescription
    MAX-ACCESS  read-create
    STATUS      current
    DESCRIPTION
        "The value of vRtrNetDomainDesc is a user provided description
         string for this network-domain.  It can consist of any printable,
         seven-bit ASCII characters up to 80 characters in length."
    DEFVAL      { ''H }
    ::= { vRtrNetDomainEntry 4 }

vRtrNetDomainIfAssociationCnt    OBJECT-TYPE
    SYNTAX      Gauge32
    MAX-ACCESS  read-only
    STATUS      current
    DESCRIPTION
        "The value of vRtrNetDomainIfAssociationCnt indicates the number of
         network interfaces associated with this network-domain."
    ::= { vRtrNetDomainEntry 5 }

vRtrNetDomainSdpAssociationCnt   OBJECT-TYPE
    SYNTAX      Gauge32
    MAX-ACCESS  read-only
    STATUS      current
    DESCRIPTION
        "The value of vRtrNetDomainSdpAssociationCnt indicates the number of
         SDPs associated with this network-domain."
    ::= { vRtrNetDomainEntry 6 }

vRtrNetDomainMcastAssociationCnt OBJECT-TYPE
    SYNTAX      Gauge32
    MAX-ACCESS  read-only
    STATUS      current
    DESCRIPTION
        "The value of vRtrNetDomainMcastAssociationCnt indicates the number of
         multicast-network domains associated with this network-domain."
    ::= { vRtrNetDomainEntry 7 }

vRtrIfNetDomainTblLastChanged    OBJECT-TYPE
    SYNTAX      TimeStamp
    MAX-ACCESS  read-only
    STATUS      current
    DESCRIPTION
        "The value of vRtrIfNetDomainTblLastChanged indicates the sysUpTime at
         the time of the last modification of vRtrIfNetDomainTable.

         If no changes were made to the table since the last re-initialization
         of the local network management subsystem, then this object contains a
         zero value."
    ::= { tmnxVRtrObjs 57 }

vRtrIfNetDomainTable             OBJECT-TYPE
    SYNTAX      SEQUENCE OF VRtrIfNetDomainEntry
    MAX-ACCESS  not-accessible
    STATUS      current
    DESCRIPTION
        "The vRtrIfNetDomainTable provides an extension to the vRtrIfTable. It
         has an entry for each network domain the virtual router interface
         belongs to."
    ::= { tmnxVRtrObjs 58 }

vRtrIfNetDomainEntry             OBJECT-TYPE
    SYNTAX      VRtrIfNetDomainEntry
    MAX-ACCESS  not-accessible
    STATUS      current
    DESCRIPTION
        "Each row entry represents information related to network-domain for a
         virtual router interface in the system."
    INDEX       {
        vRtrID,
        vRtrIfIndex,
        vRtrNetDomainName
    }
    ::= { vRtrIfNetDomainTable 1 }

VRtrIfNetDomainEntry             ::= SEQUENCE
{
    vRtrIfNetDomainRowStatus         RowStatus,
    vRtrIfNetDomainLastChanged       TimeStamp
}

vRtrIfNetDomainRowStatus         OBJECT-TYPE
    SYNTAX      RowStatus
    MAX-ACCESS  read-create
    STATUS      current
    DESCRIPTION
        "The value of the object vRtrIfNetDomainRowStatus specifies the Row
         status of this table row. This object is used to create or delete rows
         in this table."
    ::= { vRtrIfNetDomainEntry 1 }

vRtrIfNetDomainLastChanged       OBJECT-TYPE
    SYNTAX      TimeStamp
    MAX-ACCESS  read-only
    STATUS      current
    DESCRIPTION
        "The value of vRtrIfNetDomainLastChanged indicates the sysUpTime when
         any object of the row is last changed."
    ::= { vRtrIfNetDomainEntry 2 }

vRtrConfExtTable                 OBJECT-TYPE
    SYNTAX      SEQUENCE OF VRtrConfExtEntry
    MAX-ACCESS  not-accessible
    STATUS      current
    DESCRIPTION
        "The vRtrConfExtTable provides an extension of the vRtrConfTable."
    ::= { tmnxVRtrObjs 60 }

vRtrConfExtEntry                 OBJECT-TYPE
    SYNTAX      VRtrConfExtEntry
    MAX-ACCESS  not-accessible
    STATUS      current
    DESCRIPTION
        "Each row entry in the vRtrConfExtTable represents additional columns
         for attributes specific to the Nokia SROS series implementation for
         the router configuration table."
    AUGMENTS    { vRtrConfEntry }
    ::= { vRtrConfExtTable 1 }

VRtrConfExtEntry                 ::= SEQUENCE
{
    vRtrLdpShortcut                  TmnxEnabledDisabled,
    vRtrSingleSfmOverloadAdminState  TmnxAdminState,
    vRtrSingleSfmOverloadHldOffTime  Unsigned32,
    vRtrSingleSfmOverloadState       TmnxVrtrSingleSfmOverloadState,
    vRtrSingleSfmOverloadStart       TimeStamp,
    vRtrSingleSfmOverloadTime        TimeInterval,
    vRtrGrtState                     TruthValue,
    vRtrMvpnIpmsiP2MPAdmin           TmnxAdminState,
    vRtrMvpnSpmsiP2MPAdmin           TmnxAdminState,
    vRtrMvpnIpmsiLspTemplate         TNamedItemOrEmpty,
    vRtrMvpnSpmsiLspTemplate         TNamedItemOrEmpty,
    vRtrMvpnIpmsiType                INTEGER,
    vRtrMvpnSpmsiType                INTEGER,
    vRtrMvpnSpmsiMaxLimit            Unsigned32,
    vRtrFibPriority                  INTEGER,
    vRtrCarrierCarrierVpn            TruthValue,
    vRtrLabelMode                    INTEGER,
    vRtrBgpSharedQueue               TruthValue,
    vRtrBgpSharedQueueCIR            TCIRRate,
    vRtrBgpSharedQueuePIR            TPIRRate,
    vRtrMvpnMdtSafi                  TruthValue,
    vRtrMvpnMdtDefGrpAddrType        InetAddressType,
    vRtrMvpnMdtDefGrpAddress         InetAddress,
    vRtrMvpnIpmsiEnableBfdRoot       TruthValue,
    vRtrMvpnIpmsiEnableBfdLeaf       TruthValue,
    vRtrMvpnIpmsiBfdRtTraInt         Unsigned32,
    vRtrMvpnIpmsiBfdRootMult         Unsigned32,
    vRtrVpnBackupPath                TmnxVpnIpBackupFamily,
    vRtrIpFastReroute                TruthValue,
    vRtrGrtLocalMgmtState            TruthValue,
    vRtrIpv6ReachableTime            Unsigned32,
    vRtrAllowExportBgpVpn            TruthValue,
    vRtrBgpExportInactive            TruthValue,
    vRtrAllowSnmpAccess              TruthValue,
    vRtrIpv6NdCacheStaleTime         Unsigned32,
    vRtrIcmpTunneling                TruthValue,
    vRtrMvpnMdSourceAddrType         InetAddressType,
    vRtrMvpnMdSourceAddress          InetAddress,
    vRtrDisableSelectiveFib          TruthValue,
    vRtrMvpnWildcardSpmsi            TruthValue,
    vRtrMvpnWildcardSpmsiBsrSig      INTEGER,
    vRtrStaticRouteHoldDownEnable    TruthValue,
    vRtrStaticRouteHoldDownInitial   Unsigned32,
    vRtrStaticRouteHoldDownMultiplr  Unsigned32,
    vRtrStaticRouteHoldDownMaxValue  Unsigned32,
    vRtrWeightedEcmp                 TruthValue,
    vRtrBgpAutoRD                    TruthValue,
    vRtrBgpOperRD                    TmnxVPNRouteDistinguisher,
    vRtrBgpOperRDType                TmnxRouteDistType,
    vRtrLdpShortcutType              BITS,
    vRtrEntropyLabel                 TruthValue,
    vRtrLspBfdSession                TmnxEnabledDisabled,
    vRtrLspBfdMaxSessions            Unsigned32,
    vRtrOperRouterId                 IpAddress,
    vRtrClassForwarding              TruthValue,
    vRtrMtrace2AdminState            TmnxAdminState,
    vRtrMtrace2UdpPort               Unsigned32,
    vRtrPolicyReferenceChecks        TruthValue,
    vRtrMvpnIpmsiBierSubDomain       Integer32,
    vRtrMvpnSpmsiBierSubDomain       Integer32,
    vRtrFibTelemetry                 TruthValue,
    vRtrWeightedEcmpStrict           TruthValue,
    vRtrIpv6TeRouterIdIfName         TNamedItem,
    vRtrEcmpUnequalCost              TruthValue,
    vRtrMvpnIpmsiP2mpPolicy          TNamedItemOrEmpty,
    vRtrMvpnSpmsiP2mpPolicy          TNamedItemOrEmpty,
    vRtrMvpnIpmsiSRPolicy            TruthValue,
    vRtrMvpnSpmsiSRPolicy            TruthValue,
    vRtrBgpIpVpnMplsAdminState       TmnxEnabledDisabled,
    vRtrBgpIpVpnMplsDynEgrLblLmt     TruthValue,
    vRtrBgpIpVpnMplsOperState        TmnxEnabledDisabled
}

vRtrLdpShortcut                  OBJECT-TYPE
    SYNTAX      TmnxEnabledDisabled
    MAX-ACCESS  read-create
    STATUS      obsolete
    DESCRIPTION
        "The value of vRtrLdpShortcut specifies if IP packets are being
         forwarded using LDP shortcuts over all network interfaces in the
         system which participate in the IS-IS and OSPF routing protocols.

         This object has been replaced by vRtrLdpShortcutType in 13.0."
    DEFVAL      { disabled }
    ::= { vRtrConfExtEntry 1 }

vRtrSingleSfmOverloadAdminState  OBJECT-TYPE
    SYNTAX      TmnxAdminState
    MAX-ACCESS  read-create
    STATUS      current
    DESCRIPTION
        "The value of the object vRtrSingleSfmOverloadAdminState specifies the
         administrative state of the IGP single-SFM-overload behavior in this
         virtual router instance.

         When the value of vRtrSingleSfmOverloadAdminState is equal to
         'inService', IGP protocols (either IS-IS or OSPF) enter an overload
         state when the node only has a single SFM functioning."
    DEFVAL      { outOfService }
    ::= { vRtrConfExtEntry 2 }

vRtrSingleSfmOverloadHldOffTime  OBJECT-TYPE
    SYNTAX      Unsigned32 (0..600)
    UNITS       "seconds"
    MAX-ACCESS  read-create
    STATUS      current
    DESCRIPTION
        "The value of the object vRtrSingleSfmOverloadHldOffTime specifies the
         delay between the detection of the single-SFM condition and the IGP
         entering the overload state."
    DEFVAL      { 0 }
    ::= { vRtrConfExtEntry 3 }

vRtrSingleSfmOverloadState       OBJECT-TYPE
    SYNTAX      TmnxVrtrSingleSfmOverloadState
    MAX-ACCESS  read-only
    STATUS      current
    DESCRIPTION
        "The value of the object vRtrSingleSfmOverloadState indicates the IGP
         single-SFM-overload state."
    ::= { vRtrConfExtEntry 4 }

vRtrSingleSfmOverloadStart       OBJECT-TYPE
    SYNTAX      TimeStamp
    MAX-ACCESS  read-only
    STATUS      current
    DESCRIPTION
        "The value of vRtrSingleSfmOverloadStart indicates the sysUpTime the
         last time that the vRtrSingleSfmOverloadState had a transition from
         'notApplicable' or 'normal' to 'overload'.

         If such a transition never occurred, this object contains a zero
         value."
    ::= { vRtrConfExtEntry 5 }

vRtrSingleSfmOverloadTime        OBJECT-TYPE
    SYNTAX      TimeInterval
    MAX-ACCESS  read-only
    STATUS      current
    DESCRIPTION
        "The value of vRtrSingleSfmOverloadTime indicates the duration of the
         most recent overload."
    ::= { vRtrConfExtEntry 6 }

vRtrGrtState                     OBJECT-TYPE
    SYNTAX      TruthValue
    MAX-ACCESS  read-create
    STATUS      current
    DESCRIPTION
        "The value of vRtrGrtState specifies if a route lookup is done in the
         Global Route Table (GRT) when the lookup in the local VRF fails. When
         the value of this object is set to 'false', route lookup in the GRT is
         disabled."
    DEFVAL      { false }
    ::= { vRtrConfExtEntry 7 }

vRtrMvpnIpmsiP2MPAdmin           OBJECT-TYPE
    SYNTAX      TmnxAdminState
    MAX-ACCESS  read-create
    STATUS      current
    DESCRIPTION
        "The value of vRtrMvpnIpmsiP2MPAdmin specifies the current
         administrative state of P2MP for the inclusive provider tunnel.

         An 'inconsistentValue' error is returned if this object is set to
         non-default value when vRtrMvpnIpmsiLspTemplate is set to its default
         value."
    DEFVAL      { outOfService }
    ::= { vRtrConfExtEntry 8 }

vRtrMvpnSpmsiP2MPAdmin           OBJECT-TYPE
    SYNTAX      TmnxAdminState
    MAX-ACCESS  read-create
    STATUS      current
    DESCRIPTION
        "The value of vRtrMvpnSpmsiP2MPAdmin specifies the current
         administrative state of P2MP for the selective provider tunnel.

         An 'inconsistentValue' error is returned if this object is set to
         non-default value when vRtrMvpnSpmsiLspTemplate is set to its default
         value."
    DEFVAL      { outOfService }
    ::= { vRtrConfExtEntry 9 }

vRtrMvpnIpmsiLspTemplate         OBJECT-TYPE
    SYNTAX      TNamedItemOrEmpty
    MAX-ACCESS  read-create
    STATUS      current
    DESCRIPTION
        "The value of the vRtrMvpnIpmsiLspTemplate specifies the name of
         the template whose parameters configured in TIMETRA-MPLS-MIB::vRtrMplsLspTemplateTable
         are signalled to the automatically  created  P2MP LSP for the inclusive
         provider tunnel.

         If a corresponding index does not exist in
         TIMETRA-MPLS-MIB::vRtrMplsLspTemplateTable, an 'inconsistentValue'
         error will be returned.

         An inconsistentValue' error is returned if this object is set to
         non-default value when vRtrMvpnIpmsiP2MPAdmin is set to its
         non-default value."
    DEFVAL      { ''H }
    ::= { vRtrConfExtEntry 10 }

vRtrMvpnSpmsiLspTemplate         OBJECT-TYPE
    SYNTAX      TNamedItemOrEmpty
    MAX-ACCESS  read-create
    STATUS      current
    DESCRIPTION
        "The value of the vRtrMvpnSpmsiLspTemplate specifies the name of
         the template whose parameters configured in TIMETRA-MPLS-MIB::vRtrMplsLspTemplateTable
         are signalled to the automatically  created  P2MP LSP for the selective
         provider tunnel.

         If a corresponding index does not exist in
         TIMETRA-MPLS-MIB::vRtrMplsLspTemplateTable, an 'inconsistentValue'
         error will be returned.

         An inconsistentValue' error is returned if this object is set to
         non-default value when vRtrMvpnSpmsiP2MPAdmin is set to its
         non-default value."
    DEFVAL      { ''H }
    ::= { vRtrConfExtEntry 11 }

vRtrMvpnIpmsiType                OBJECT-TYPE
    SYNTAX      INTEGER {
        none    (0),
        rsvp    (1),
        pim     (2),
        ldp     (3),
        bier    (4),
        treesid (5)
    }
    MAX-ACCESS  read-create
    STATUS      current
    DESCRIPTION
        "The value of vRtrMvpnIpmsiType specifies the type of the inclusive
         provider tunnel.

         When the value of vRtrMvpnIpmsiType is set to 'rsvp', the inclusive
         provider tunnel is used for RSVP. When the value is set to 'pim', the
         inclusive provider tunnel is used for PIM. When the value is set to
         'ldp', the inclusive provider tunnel is used for LDP. When the value
         is set to 'bier', the inclusive provider tunnel is used for BIER."
    DEFVAL      { none }
    ::= { vRtrConfExtEntry 12 }

vRtrMvpnSpmsiType                OBJECT-TYPE
    SYNTAX      INTEGER {
        none    (0),
        rsvp    (1),
        pim     (2),
        ldp     (3),
        bier    (4),
        treesid (5)
    }
    MAX-ACCESS  read-create
    STATUS      current
    DESCRIPTION
        "The value of vRtrMvpnSpmsiType specifies the type of the selective
         provider tunnel.

         When the value of vRtrMvpnSpmsiType is set to 'rsvp', the selective
         provider tunnel is used for RSVP. When the value is set to 'pim', the
         selective provider tunnel is used for PIM. When the value is set to
         'ldp', the selective provider tunnel is used for LDP. When the value
         is set to 'bier', the selective provider tunnel is used for BIER."
    DEFVAL      { none }
    ::= { vRtrConfExtEntry 13 }

vRtrMvpnSpmsiMaxLimit            OBJECT-TYPE
    SYNTAX      Unsigned32 (1..4000)
    MAX-ACCESS  read-create
    STATUS      current
    DESCRIPTION
        "The value of the object vRtrMvpnSpmsiMaxLimit specifies the maximum
         number of RSVP/mLDP P2MP S-PMSI tunnels for the mVPN. Once the limit
         is reached, no more RSVP/mLDP P2MP S-PMSI are created and traffic over
         the data-threshold will stay on I-PMSI."
    DEFVAL      { 10 }
    ::= { vRtrConfExtEntry 14 }

vRtrFibPriority                  OBJECT-TYPE
    SYNTAX      INTEGER {
        standard (1),
        high     (2)
    }
    MAX-ACCESS  read-create
    STATUS      current
    DESCRIPTION
        "The value of vRtrFibPriority specifies the priority of updating set of
         routes into the forwarding plane.

         If the value of vRtrFibPriority for the VPRN is set to 'high', the FIB
         (Forwarding Information Base) entries for the VPRN are given priority
         over all other routes.

         By default the vRtrFibPriority for a VPRN is set to 'standard' which
         means the FIB entries for the VPRN do not have any preference over
         routes from other VPRNs."
    DEFVAL      { standard }
    ::= { vRtrConfExtEntry 15 }

vRtrCarrierCarrierVpn            OBJECT-TYPE
    SYNTAX      TruthValue
    MAX-ACCESS  read-create
    STATUS      current
    DESCRIPTION
        "The value of vRtrCarrierCarrierVpn specifies whether Carrier
         supporting Carrier model is supported on this VPRN service."
    DEFVAL      { false }
    ::= { vRtrConfExtEntry 16 }

vRtrLabelMode                    OBJECT-TYPE
    SYNTAX      INTEGER {
        vrf     (1),
        nexthop (2)
    }
    MAX-ACCESS  read-create
    STATUS      current
    DESCRIPTION
        "The value of vRtrLabelMode specifies the mode of allocation of service
         labels to the routes exported by the VPRN as BGP-VPN routes.

         If the value of vRtrLabelMode is set to 'nexthop(2)', the service
         labels are allocated per next-hop.

         By default the value of vRtrLabelMode is set to 'vrf(1)' which means
         the service labels are allocated per VRF(Virtual Routing and
         Forwarding)."
    DEFVAL      { vrf }
    ::= { vRtrConfExtEntry 17 }

vRtrBgpSharedQueue               OBJECT-TYPE
    SYNTAX      TruthValue
    MAX-ACCESS  read-create
    STATUS      current
    DESCRIPTION
        "The value of vRtrBgpSharedQueue specifies whether BGP peers associated
         with this VPRN instance share a single CPM queue."
    DEFVAL      { false }
    ::= { vRtrConfExtEntry 18 }

vRtrBgpSharedQueueCIR            OBJECT-TYPE
    SYNTAX      TCIRRate
    UNITS       "kilo bits per second"
    MAX-ACCESS  read-create
    STATUS      current
    DESCRIPTION
        "The value of the object vRtrBgpSharedQueueCIR specifies the Committed
         information rate (CIR) in kbps for BGP shared queue for this VPRN
         instance."
    DEFVAL      { 4000 }
    ::= { vRtrConfExtEntry 19 }

vRtrBgpSharedQueuePIR            OBJECT-TYPE
    SYNTAX      TPIRRate
    UNITS       "kilo bits per second"
    MAX-ACCESS  read-create
    STATUS      current
    DESCRIPTION
        "The value of the object vRtrBgpSharedQueuePIR specifies the Peak
         information rate (PIR) in kbps for BGP shared queue for this VPRN
         instance."
    DEFVAL      { 4000 }
    ::= { vRtrConfExtEntry 20 }

vRtrMvpnMdtSafi                  OBJECT-TYPE
    SYNTAX      TruthValue
    MAX-ACCESS  read-only
    STATUS      current
    DESCRIPTION
        "The value of vRtrMvpnMdtSafi indicates whether MDT-SAFI is enabled on
         the MVPN or not.

         If the value of the object is 'true', it indicates that the MDT-SAFI
         is enabled for MVPN. If the value of the object is 'false', it
         indicates that the MDT-SAFI is not enabled for MVPN."
    DEFVAL      { false }
    ::= { vRtrConfExtEntry 21 }

vRtrMvpnMdtDefGrpAddrType        OBJECT-TYPE
    SYNTAX      InetAddressType
    MAX-ACCESS  read-only
    STATUS      current
    DESCRIPTION
        "The value of vRtrMvpnMdtDefGrpAddrType indicates the type of default
         core group address of the Multicast Distribution Tree(MDT) specified
         by vRtrMvpnMdtDefGrpAddress."
    ::= { vRtrConfExtEntry 22 }

vRtrMvpnMdtDefGrpAddress         OBJECT-TYPE
    SYNTAX      InetAddress (SIZE (0|4|16))
    MAX-ACCESS  read-only
    STATUS      current
    DESCRIPTION
        "The value of vRtrMvpnMdtDefGrpAddress indicates the default core group
         address of the Multicast Distribution Tree(MDT).

         The value of this object is applicable only when the value of
         vRtrMvpnMdtSafi is 'true'."
    ::= { vRtrConfExtEntry 23 }

vRtrMvpnIpmsiEnableBfdRoot       OBJECT-TYPE
    SYNTAX      TruthValue
    MAX-ACCESS  read-create
    STATUS      current
    DESCRIPTION
        "The value of vRtrMvpnIpmsiEnableBfdRoot specifies whether or not
         Bi-directional Forwarding Detection is enabled on the tunnel root.

         When the value is 'true', the bfd session over RSVP-TE P2MP LSP for
         upstream fast failover tunnel status detection is enabled on the root.
         When it is 'false', the bfd session is disabled on the root.

         An 'inconsistentValue' error is returned if an attempt is made to set
         this object to 'true' without specifying a value for
         vRtrMvpnIpmsiBfdRtTraInt.

         The value of this object is only applicable when vRtrMvpnIpmsiType is
         set to 'rsvp'."
    DEFVAL      { false }
    ::= { vRtrConfExtEntry 24 }

vRtrMvpnIpmsiEnableBfdLeaf       OBJECT-TYPE
    SYNTAX      TruthValue
    MAX-ACCESS  read-create
    STATUS      current
    DESCRIPTION
        "The value of vRtrMvpnIpmsiEnableBfdLeaf specifies whether or not
         Bi-directional Forwarding Detection is enabled on the tunnel leaf.

         When the value is 'true', the bfd session over RSVP-TE P2MP LSP for
         upstream fast failover tunnel status detection is enabled on the leaf.
         When it is 'false', the bfd session is disabled on the leaf.

         The value of this object is only applicable when vRtrMvpnIpmsiType is
         set to 'rsvp'."
    DEFVAL      { false }
    ::= { vRtrConfExtEntry 25 }

vRtrMvpnIpmsiBfdRtTraInt         OBJECT-TYPE
    SYNTAX      Unsigned32 (10..100000)
    UNITS       "milliseconds"
    MAX-ACCESS  read-create
    STATUS      current
    DESCRIPTION
        "The value of vRtrMvpnIpmsiBfdRtTraInt specifies the BFD transmit
         interval over this interface. The minimum accepted value depends on
         the value of 'vRtrIfBfdExtType', as follows:
             'cpmNp(1)' :   10 milliseconds
             'auto(2)'  :  100 milliseconds.

         The value of this object is only applicable when vRtrMvpnIpmsiType is
         set to 'rsvp'.

         An 'inconsistentValue' error is returned if an attempt is made to
         modify the value of this object when vRtrMvpnIpmsiEnableBfdRoot is set
         to false."
    DEFVAL      { 300 }
    ::= { vRtrConfExtEntry 26 }

vRtrMvpnIpmsiBfdRootMult         OBJECT-TYPE
    SYNTAX      Unsigned32 (1..20)
    MAX-ACCESS  read-create
    STATUS      current
    DESCRIPTION
        "The value of vRtrMvpnIpmsiBfdRootMult specifies the number of
         consecutive BFD messages that must be missed from the peer before the
         BFD session state is changed to down and the upper level protocols
         (OSPF, IS-IS or PIM) are notified of the fault.

         The value of this object is only applicable when vRtrMvpnIpmsiType is
         set to 'rsvp'.

         An 'inconsistentValue' error is returned if an attempt is made to
         modify the value of this object when vRtrMvpnIpmsiEnableBfdRoot is set
         to false."
    DEFVAL      { 3 }
    ::= { vRtrConfExtEntry 27 }

vRtrVpnBackupPath                OBJECT-TYPE
    SYNTAX      TmnxVpnIpBackupFamily
    MAX-ACCESS  read-create
    STATUS      current
    DESCRIPTION
        "The value of vRtrVpnBackupPath specifies the address families for
         which the computation and use of a backup path is enabled for BGP-VPN
         routes imported into the VPRN."
    DEFVAL      { {} }
    ::= { vRtrConfExtEntry 28 }

vRtrIpFastReroute                OBJECT-TYPE
    SYNTAX      TruthValue
    MAX-ACCESS  read-create
    STATUS      current
    DESCRIPTION
        "The value of vRtrIpFastReroute specifies whether to enable or disable
         IP fast reroute capability.

         When the value of vRtrIpFastReroute is set to 'true' IP fast reroute
         capability is enabled and when vRtrIpFastReroute is set to 'false' IP
         fast reroute capability is disabled."
    DEFVAL      { false }
    ::= { vRtrConfExtEntry 29 }

vRtrGrtLocalMgmtState            OBJECT-TYPE
    SYNTAX      TruthValue
    MAX-ACCESS  read-create
    STATUS      current
    DESCRIPTION
        "The value of vRtrGrtLocalMgmtState specifies whether to enable or
         disable traffic from GRT-leaking enabled VPRN instances to reach local
         interfaces in the base routing instance.

         When the value of vRtrGrtLocalMgmtState is set to 'true', management
         protocols like SSH, Telnet, FTP, SNMP, etc are allowed from a
         GRT-leaking enabled VPRN to access local interfaces in the global
         routing instance. Ping and traceroute are independent of the value of
         'vRtrGrtLocalMgmtState'."
    DEFVAL      { false }
    ::= { vRtrConfExtEntry 30 }

vRtrIpv6ReachableTime            OBJECT-TYPE
    SYNTAX      Unsigned32 (30..3600)
    UNITS       "seconds"
    MAX-ACCESS  read-create
    STATUS      current
    DESCRIPTION
        "The value of vRtrIpv6ReachableTime specifies the time an IPv6 neighbor
         remains in reachable state. While in this state, no
         neighbor-unreachability detection has to be done."
    DEFVAL      { 30 }
    ::= { vRtrConfExtEntry 32 }

vRtrAllowExportBgpVpn            OBJECT-TYPE
    SYNTAX      TruthValue
    MAX-ACCESS  read-create
    STATUS      current
    DESCRIPTION
        "The value of the object vRtrAllowExportBgpVpn specifies that the
         vrf-export and vrf-target exporting functions will consider BGP-VPN
         routes installed in the route table of the vprn.

         If the value of vRtrAllowExportBgpVpn is 'true', BGP-VPN routes will
         be exported. If the value of vRtrAllowExportBgpVpn is 'false', BGP-VPN
         routes will not be exported."
    DEFVAL      { false }
    ::= { vRtrConfExtEntry 33 }

vRtrBgpExportInactive            OBJECT-TYPE
    SYNTAX      TruthValue
    MAX-ACCESS  read-create
    STATUS      current
    DESCRIPTION
        "The value of the object vRtrBgpExportInactive specifies whether or not
         inactive VPRN-BGP routes are exported to the MP-BGP domain.

         If the value of vRtrBgpExportInactive is 'true', inactive VPRN-BGP
         routes will be exported to the MP-BGP domain. If the value of
         vRtrBgpExportInactive is 'false', inactive VPRN-BGP routes are not
         exported to the MP-BGP domain."
    DEFVAL      { false }
    ::= { vRtrConfExtEntry 34 }

vRtrAllowSnmpAccess              OBJECT-TYPE
    SYNTAX      TruthValue
    MAX-ACCESS  read-create
    STATUS      current
    DESCRIPTION
        "The value of the object vRtrAllowSnmpAccess specifies whether SNMP
         requests are allowed on this VPRN."
    DEFVAL      { false }
    ::= { vRtrConfExtEntry 35 }

vRtrIpv6NdCacheStaleTime         OBJECT-TYPE
    SYNTAX      Unsigned32 (60..65535)
    UNITS       "seconds"
    MAX-ACCESS  read-create
    STATUS      current
    DESCRIPTION
        "The value of vRtrIpv6NdCacheStaleTime specifies the time an IPv6
         neighbor cache entry remains in stale state, for all applicable
         interfaces in this virtual router instance where the value of the
         object vRtrIfIpv6NdCacheStaleTime is equal to zero.

         When this time has elapsed, the system removes the neighbor cache
         entry."
    REFERENCE
        "RFC 2461 Neighbor Discovery for IP Version 6 (IPv6)
         section 7.3.2. Neighbor Cache Entry States"
    DEFVAL      { 14400 }
    ::= { vRtrConfExtEntry 36 }

vRtrIcmpTunneling                OBJECT-TYPE
    SYNTAX      TruthValue
    MAX-ACCESS  read-create
    STATUS      current
    DESCRIPTION
        "The value of the object vRtrIcmpTunneling specifies whether ICMP
         tunneling is enabled or disabled globally on the system."
    DEFVAL      { false }
    ::= { vRtrConfExtEntry 37 }

vRtrMvpnMdSourceAddrType         OBJECT-TYPE
    SYNTAX      InetAddressType
    MAX-ACCESS  read-only
    STATUS      current
    DESCRIPTION
        "The value of vRtrMvpnMdSourceAddrType indicates the address type of
         vRtrMvpnMdSourceAddress."
    ::= { vRtrConfExtEntry 38 }

vRtrMvpnMdSourceAddress          OBJECT-TYPE
    SYNTAX      InetAddress (SIZE (0|4|16))
    MAX-ACCESS  read-only
    STATUS      current
    DESCRIPTION
        "The value of vRtrMvpnMdSourceAddress indicates the source IP address
         to use in MVPN PIM signaling."
    ::= { vRtrConfExtEntry 39 }

vRtrDisableSelectiveFib          OBJECT-TYPE
    SYNTAX      TruthValue
    MAX-ACCESS  read-create
    STATUS      current
    DESCRIPTION
        "The value of the object vRtrDisableSelectiveFib specifies whether the
         system level selective FIB setting is overridden on this routing
         instance.

         If the value of vRtrDisableSelectiveFib is set to true, then the
         selective FIB is disabled and all active routes of this routing
         instance are installed on all line cards."
    DEFVAL      { false }
    ::= { vRtrConfExtEntry 40 }

vRtrMvpnWildcardSpmsi            OBJECT-TYPE
    SYNTAX      TruthValue
    MAX-ACCESS  read-create
    STATUS      current
    DESCRIPTION
        "The value of the object vRtrMvpnWildcardSpmsi specifies whether
         (C-*,C-*) SPMSI is to be used instead of IPMSI. This object is
         supported for NG MVPN only."
    DEFVAL      { false }
    ::= { vRtrConfExtEntry 41 }

vRtrMvpnWildcardSpmsiBsrSig      OBJECT-TYPE
    SYNTAX      INTEGER {
        none    (0),
        unicast (1),
        spmsi   (2)
    }
    MAX-ACCESS  read-create
    STATUS      current
    DESCRIPTION
        "The value of vRtrMvpnWildcardSpmsiBsrSig specifies how the BSR is
         signalled. The value of this object is applicable only when
         vRtrMvpnWildcardSpmsiBsrSig is set to true."
    DEFVAL      { none }
    ::= { vRtrConfExtEntry 42 }

vRtrStaticRouteHoldDownEnable    OBJECT-TYPE
    SYNTAX      TruthValue
    MAX-ACCESS  read-create
    STATUS      current
    DESCRIPTION
        "The value of vRtrStaticRouteHoldDownEnable specifies if hold down
         timer is enabled or disabled for the router instance.

         When the value of vRtrStaticRouteHoldDownEnable is set to 'true',
         hold down timer is enabled on the static routes. To set
         vRtrStaticRouteHoldDownEnable to 'true', it is necessary to set
         the values of the mib objects  vRtrStaticRouteHoldDownInitial,
         vRtrStaticRouteHoldDownMultiplr and vRtrStaticRouteHoldDownMaxValue
         to non zero values.

         When the value of vRtrStaticRouteHoldDownEnable is set to 'false',
         hold down timer is disabled on the static routes and the values of
         vRtrStaticRouteHoldDownInitial, vRtrStaticRouteHoldDownMultiplr and
         vRtrStaticRouteHoldDownMaxValue is set to their default values."
    DEFVAL      { false }
    ::= { vRtrConfExtEntry 43 }

vRtrStaticRouteHoldDownInitial   OBJECT-TYPE
    SYNTAX      Unsigned32 (0..65535)
    UNITS       "seconds"
    MAX-ACCESS  read-create
    STATUS      current
    DESCRIPTION
        "The value of vRtrStaticRouteHoldDownInitial specifies the initial
         hold-down time. When the route flaps for the first time the hold-down
         time is set to this value. The value of vRtrStaticRouteHoldDownInitial
         can be default only when the value of vRtrStaticRouteHoldDownEnable is
         set to 'false'."
    DEFVAL      { 0 }
    ::= { vRtrConfExtEntry 44 }

vRtrStaticRouteHoldDownMultiplr  OBJECT-TYPE
    SYNTAX      Unsigned32 (0..10)
    MAX-ACCESS  read-create
    STATUS      current
    DESCRIPTION
        "The value of vRtrStaticRouteHoldDownMultiplr specifies the value by
         which the previous hold-down time is multiplied to calculate the new
         hold-down time. The value of vRtrStaticRouteHoldDownMultiplr can be
         default only when the value of vRtrStaticRouteHoldDownEnable is set to
         'false'."
    DEFVAL      { 0 }
    ::= { vRtrConfExtEntry 45 }

vRtrStaticRouteHoldDownMaxValue  OBJECT-TYPE
    SYNTAX      Unsigned32 (0..65535)
    UNITS       "seconds"
    MAX-ACCESS  read-create
    STATUS      current
    DESCRIPTION
        "The value of vRtrStaticRouteHoldDownMaxValue specifies the maximum
         value of the hold-down time. When the value of
         vRtrStaticRouteHoldDownEnable is changed to 'false', the value of
         vRtrStaticRouteHoldDownMaxValue is changed to its default value."
    DEFVAL      { 0 }
    ::= { vRtrConfExtEntry 46 }

vRtrWeightedEcmp                 OBJECT-TYPE
    SYNTAX      TruthValue
    MAX-ACCESS  read-create
    STATUS      current
    DESCRIPTION
        "The value of vRtrWeightedEcmp specifies the packets forwarded in the
         global routing table to a set of ECMP tunnel next-hops which will be
         sprayed proportionally to the weights configured for each LSP."
    DEFVAL      { false }
    ::= { vRtrConfExtEntry 47 }

vRtrBgpAutoRD                    OBJECT-TYPE
    SYNTAX      TruthValue
    MAX-ACCESS  read-create
    STATUS      current
    DESCRIPTION
        "The value of vRtrBgpAutoRD specifies that system will automatically
         selects a value for the route-distinguisher from
         TIMETRA-SERV-MIB::svcBgpAutoRDType1Group.

         An 'inconsistentValue' error is returned when trying to set
         svcTlsBgpAutoRD to 'true' and there is no route-distinguisher
         available from TIMETRA-SERV-MIB::svcBgpAutoRDType1Group.

         SNMP set of vRtrBgpAutoRD to 'true' will automatically set
         vRtrRouteDistinguisher to all zeroes."
    DEFVAL      { false }
    ::= { vRtrConfExtEntry 48 }

vRtrBgpOperRD                    OBJECT-TYPE
    SYNTAX      TmnxVPNRouteDistinguisher
    MAX-ACCESS  read-only
    STATUS      current
    DESCRIPTION
        "The value of vRtrBgpOperRD indicates the route-distinguisher value in
         use by the system for this routing instance."
    ::= { vRtrConfExtEntry 49 }

vRtrBgpOperRDType                OBJECT-TYPE
    SYNTAX      TmnxRouteDistType
    MAX-ACCESS  read-only
    STATUS      current
    DESCRIPTION
        "The value of vRtrBgpOperRDType indicates the type of
         route-distinguisher value in use by the system for this routing
         instance."
    ::= { vRtrConfExtEntry 50 }

vRtrLdpShortcutType              OBJECT-TYPE
    SYNTAX      BITS {
        ipv4 (0),
        ipv6 (1)
    }
    MAX-ACCESS  read-create
    STATUS      current
    DESCRIPTION
        "The value of vRtrLdpShortcutType specifies if IP packets are being
         forwarded using LDP shortcuts over all network interfaces in the
         system which participate in the IS-IS and OSPF routing protocols. This
         object replaces vRtrLdpShortcut since it supports only IPv4 LDP
         shortcuts.

         When the value is set to 'ipv4' or 'ipv6', then IPv4 or IPv6 packets
         are being forwarded using LDP shortcuts.

         When both 'ipv4' and 'ipv6' are set, then IPv4 and IPv6 packets are
         forwarded using LDP shortcuts."
    DEFVAL      { {} }
    ::= { vRtrConfExtEntry 51 }

vRtrEntropyLabel                 OBJECT-TYPE
    SYNTAX      TruthValue
    MAX-ACCESS  read-create
    STATUS      current
    DESCRIPTION
        "The value of vRtrEntropyLabel specifies whether the use of entropy
         label is enabled or not for the router instance."
    DEFVAL      { false }
    ::= { vRtrConfExtEntry 52 }

vRtrLspBfdSession                OBJECT-TYPE
    SYNTAX      TmnxEnabledDisabled
    MAX-ACCESS  read-create
    STATUS      current
    DESCRIPTION
        "The value of vRtrLspBfdSession specifies whether or not LSP tail-ends
         are allowed to terminate BFD-on-LSP sessions (on the specified routing
         instance).

         vRtrLspBfdMaxSessions can be used to further limit BFD-on-LSP
         sessions."
    DEFVAL      { disabled }
    ::= { vRtrConfExtEntry 53 }

vRtrLspBfdMaxSessions            OBJECT-TYPE
    SYNTAX      Unsigned32
    MAX-ACCESS  read-create
    STATUS      current
    DESCRIPTION
        "The value of vRtrLspBfdMaxSessions specifies the maximum number of
         BFD-on-LSP sessions that can terminate on LSP tail-ends (on the
         specified routing instance).

         This value is ignored when vRtrLspBfdSession is 'disabled(2)'.

         An attempt to exceed this limit is reported using the notification
         TIMETRA-BFD-MIB::tmnxBfdOnLspSessNoTailResources."
    DEFVAL      { 0 }
    ::= { vRtrConfExtEntry 54 }

vRtrOperRouterId                 OBJECT-TYPE
    SYNTAX      IpAddress
    MAX-ACCESS  read-only
    STATUS      current
    DESCRIPTION
        "The value of vRtrOperRouterId indicates an IPv4 IP-address, uniquely
         identifying the router in the Autonomous System (AS).

         The value of the vRtrOperRouterId will be determined based on the
         following priority rules and context:

         Base Router Instance:
            1. vRtrRouterId (if not set to the default value).
            2. System Interface address (IPv4)
            3. Derived from the chassis MAC address

         VPN Instance:
            1. vRtrRouterId (if not set to the default value).
            2. The Base Router Instance vRtrOperRouterId value."
    ::= { vRtrConfExtEntry 56 }

vRtrClassForwarding              OBJECT-TYPE
    SYNTAX      TruthValue
    MAX-ACCESS  read-create
    STATUS      current
    DESCRIPTION
        "The value of vRtrClassForwarding specifies whether class forwarding is
         enabled or not. If class forwarding is enabled, packets are forwarded
         based on their forwarding class."
    DEFVAL      { false }
    ::= { vRtrConfExtEntry 58 }

vRtrMtrace2AdminState            OBJECT-TYPE
    SYNTAX      TmnxAdminState
    MAX-ACCESS  read-create
    STATUS      current
    DESCRIPTION
        "The value of vRtrMtrace2AdminState specifies whether or not
         1.  Launching a UDP-based IP multicast traceroute test (i.e. an
         mtrace2 test) is administratively enabled for the specified router, and
         2.  Listening for an unsolicited mtrace2 test packet is
         administratively enabled for the specified router.

         An mtrace2 test is launched with
         TIMETRA-OAM-TEST-MIB::tmnxOamMcastTrCtlTestSubMode set to
         'mcastTraceRouteV2(2)'.

         When this object is changed to 'inService(2)', an attempt is made to
         open the UDP port specified by vRtrMtrace2UdpPort.

         If the attempt to open succeeds, vRtrMtrace2OperState is 'enabled(1)'.
         If the attempt to open fails, vRtrMtrace2OperState is 'disabled(2)'.
         In either case, vRtrMtrace2AdminState is 'inService(2)'.

         When this object is changed to 'outOfService(3)' and the UDP port
         specified by vRtrMtrace2UdpPort is used by mtrace2, the UDP port is
         closed."
    REFERENCE
        "IETF draft-ietf-mboned-mtrace-v2-17, 'Mtrace Version 2: Traceroute
         Facility for IP Multicast', 12-Mar-2017."
    DEFVAL      { outOfService }
    ::= { vRtrConfExtEntry 59 }

vRtrMtrace2UdpPort               OBJECT-TYPE
    SYNTAX      Unsigned32 (1024..49151)
    MAX-ACCESS  read-create
    STATUS      current
    DESCRIPTION
        "The value of vRtrMtrace2UdpPort specifies
         1.  The value to be filled in the destination UDP port field of the
             launch packet for a UDP-based IP multicast traceroute test (i.e. an
             mtrace2 test).
         2.  The UDP port used when listening for an unsolicited mtrace2 packet.

         The range is the UDP registered port range.

         This value is relevant when vRtrMtrace2AdminState is 'inService(2)'."
    REFERENCE
        "IETF draft-ietf-mboned-mtrace-v2-17, 'Mtrace Version 2: Traceroute
         Facility for IP Multicast', 12-Mar-2017, Section 8.3, 'UDP Destination
         Port'."
    DEFVAL      { 5000 }
    ::= { vRtrConfExtEntry 62 }

vRtrPolicyReferenceChecks        OBJECT-TYPE
    SYNTAX      TruthValue
    MAX-ACCESS  read-create
    STATUS      current
    DESCRIPTION
        "This value of object vRtrPolicyReferenceChecks specifies whether the
         interactive configuration in CLI should check if a policy that is
         referenced has been configured.

         When the value of vRtrPolicyReferenceChecks is set to true(1),
         referencing non-existent policies or referencing non-existent policy
         objects in policy-statements in CLI configuration fails.

         When the value of vRtrPolicyReferenceChecks is set to false(2), the
         CLI configuration of a reference to a non-existent policy is allowed."
    DEFVAL      { false }
    ::= { vRtrConfExtEntry 63 }

vRtrMvpnIpmsiBierSubDomain       OBJECT-TYPE
    SYNTAX      Integer32 (-1 | 0..255)
    MAX-ACCESS  read-create
    STATUS      current
    DESCRIPTION
        "The value of vRtrMvpnIpmsiBierSubDomain specifies the value of BIER
         sub-domain id.

         The value of this object is only applicable when vRtrMvpnIpmsiType is
         set to 'bier'."
    DEFVAL      { -1 }
    ::= { vRtrConfExtEntry 64 }

vRtrMvpnSpmsiBierSubDomain       OBJECT-TYPE
    SYNTAX      Integer32 (-1 | 0..255)
    MAX-ACCESS  read-create
    STATUS      current
    DESCRIPTION
        "The value of vRtrMvpnSpmsiBierSubDomain specifies the value of BIER
         sub-domain id.

         The value of this object is only applicable when vRtrMvpnIpmsiType is
         set to 'bier'."
    DEFVAL      { -1 }
    ::= { vRtrConfExtEntry 65 }

vRtrFibTelemetry                 OBJECT-TYPE
    SYNTAX      TruthValue
    MAX-ACCESS  read-create
    STATUS      current
    DESCRIPTION
        "The vRtrFibTelemetry specifies whether FIB telemetry collection is
         enabled."
    DEFVAL      { false }
    ::= { vRtrConfExtEntry 66 }

vRtrWeightedEcmpStrict           OBJECT-TYPE
    SYNTAX      TruthValue
    MAX-ACCESS  read-create
    STATUS      current
    DESCRIPTION
        "The value of vRtrWeightedEcmpStrict specifies whether or not to apply
         strict ECMP."
    DEFVAL      { false }
    ::= { vRtrConfExtEntry 67 }

vRtrIpv6TeRouterIdIfName         OBJECT-TYPE
    SYNTAX      TNamedItem
    MAX-ACCESS  read-create
    STATUS      current
    DESCRIPTION
        "The value of vRtrIpv6TeRouterIdIfName specifies the name of the
         interface from which the IP address is obtained to use as IPv6 Traffic
         Engineering Router ID.

         If the value of the vRtrIpv6TeRouterIdIfName is the default value, the
         preferred primary global unicast address of the system interface will
         be used as the IPv6 TE Router ID."
    DEFVAL      { "system" }
    ::= { vRtrConfExtEntry 68 }

vRtrEcmpUnequalCost              OBJECT-TYPE
    SYNTAX      TruthValue
    MAX-ACCESS  read-create
    STATUS      current
    DESCRIPTION
        "The value of vRtrEcmpUnequalCost specifies..."
    DEFVAL      { false }
    ::= { vRtrConfExtEntry 69 }

vRtrMvpnIpmsiP2mpPolicy          OBJECT-TYPE
    SYNTAX      TNamedItemOrEmpty
    MAX-ACCESS  read-create
    STATUS      current
    DESCRIPTION
        "The value of vRtrMvpnIpmsiP2mpPolicy specifies the name of p2mp policy
         whose parameters are configured in
         TIMETRA-TREE-SID-MIB::vRtrTreeSidPolicyEntry table and are signaled to
         the automatically created P2MP LSP for the inclusive provider tunnel.

         If the corresponding index does not exist in
         TIMETRA-TREE-SID-MIB::vRtrTreeSidPolicyEntry table, an
         'inconsistentValue' error will be returned."
    DEFVAL      { ''H }
    ::= { vRtrConfExtEntry 70 }

vRtrMvpnSpmsiP2mpPolicy          OBJECT-TYPE
    SYNTAX      TNamedItemOrEmpty
    MAX-ACCESS  read-create
    STATUS      current
    DESCRIPTION
        "The value of vRtrMvpnSpmsiP2mpPolicy specifies the name of p2mp policy
         whose parameters are configured in
         TIMETRA-TREE-SID-MIB::vRtrTreeSidPolicyEntry table and are signaled to
         the automatically created P2MP LSP for the selective provider tunnel.

         If the corresponding index does not exist in
         TIMETRA-TREE-SID-MIB::vRtrTreeSidPolicyEntry table, an
         'inconsistentValue' error will be returned."
    DEFVAL      { ''H }
    ::= { vRtrConfExtEntry 71 }

vRtrMvpnIpmsiSRPolicy            OBJECT-TYPE
    SYNTAX      TruthValue
    MAX-ACCESS  read-create
    STATUS      current
    DESCRIPTION
        "The value of vRtrMvpnIpmsiSRPolicy specifies the pim p2mp sr policy if
         associated with this inclusive provider tunnel."
    DEFVAL      { false }
    ::= { vRtrConfExtEntry 72 }

vRtrMvpnSpmsiSRPolicy            OBJECT-TYPE
    SYNTAX      TruthValue
    MAX-ACCESS  read-create
    STATUS      current
    DESCRIPTION
        "The value of vRtrMvpnSpmsiSRPolicy specifies the pim p2mp sr policy if
         associated with this selective provider tunnel."
    DEFVAL      { false }
    ::= { vRtrConfExtEntry 73 }

vRtrBgpIpVpnMplsAdminState       OBJECT-TYPE
    SYNTAX      TmnxEnabledDisabled
    MAX-ACCESS  read-create
    STATUS      current
    DESCRIPTION
        "The value of vRtrBgpIpVpnMplsAdminState specifies the administrative
         state of BGP IP VPN MPLS for this service."
    DEFVAL      { disabled }
    ::= { vRtrConfExtEntry 74 }

vRtrBgpIpVpnMplsDynEgrLblLmt     OBJECT-TYPE
    SYNTAX      TruthValue
    MAX-ACCESS  read-create
    STATUS      current
    DESCRIPTION
        "The value vRtrBgpIpVpnMplsDynEgrLblLmt of determines whether, when BGP
         resolves routes, it accounts for the presence of control-word,
         ethernet-segment label etc or not."
    DEFVAL      { false }
    ::= { vRtrConfExtEntry 75 }

vRtrBgpIpVpnMplsOperState        OBJECT-TYPE
    SYNTAX      TmnxEnabledDisabled
    MAX-ACCESS  read-only
    STATUS      current
    DESCRIPTION
        "The vRtrBgpIpVpnMplsOperState indicates the operational state of BGP
         IP VPN MPLS for this service."
    ::= { vRtrConfExtEntry 76 }

vRtrIfExtTable                   OBJECT-TYPE
    SYNTAX      SEQUENCE OF VRtrIfExtEntry
    MAX-ACCESS  not-accessible
    STATUS      current
    DESCRIPTION
        "The vRtrIfExtTable has an entry for each router interface configured
         in the system. This table augments the vRtrIfTable."
    ::= { tmnxVRtrObjs 61 }

vRtrIfExtEntry                   OBJECT-TYPE
    SYNTAX      VRtrIfExtEntry
    MAX-ACCESS  not-accessible
    STATUS      current
    DESCRIPTION
        "Each row entry represents a virtual router interface in the system.
         Entries can be created and deleted via SNMP SET operations using the
         vRtrIfRowStatus variable."
    AUGMENTS    { vRtrIfEntry }
    ::= { vRtrIfExtTable 1 }

VRtrIfExtEntry                   ::= SEQUENCE
{
    vRtrIfLsrIpLoadBalancing         INTEGER,
    vRtrIfIngressIpv4Flowspec        TruthValue,
    vRtrIfInfo                       OCTET STRING,
    vRtrIfInfoEncrypted              TruthValue,
    vRtrIfQosRouteLookup             INTEGER,
    vRtrIfIpv6QosRouteLookup         INTEGER,
    vRtrIfStatusString               DisplayString,
    vRtrIfIpv6uRPFCheckState         TmnxEnabledDisabled,
    vRtrIfIpv6uRPFCheckMode          TmnxUrpfCheckMode,
    vRtrIfTmsOffRampVprn             TmnxServId,
    vRtrIfTmsMgmtVprn                TmnxServId,
    vRtrIfTrackMobile                TmnxEnabledDisabled,
    vRtrIfIpv6TrackMobile            TmnxEnabledDisabled,
    vRtrIfIngressIpv6Flowspec        TruthValue,
    vRtrIfLagLinkMapProfile          TmnxLinkMapProfileIdOrZero,
    vRtrIfLagActivePort              TmnxPortID,
    vRtrIfDCpuProtPolicy             TNamedItemOrEmpty,
    vRtrIfMcastNetworkDomainName     TNamedItemOrEmpty,
    vRtrIfIngressStatsEnabled        TruthValue,
    vRtrIfIpv6ReachableTime          Unsigned32,
    vRtrIfEnableMacAccounting        TruthValue,
    vRtrIfTcpMss                     Unsigned32,
    vRtrIfIpv6TcpMss                 Unsigned32,
    vRtrIfuRPFIgnoreDefault          TruthValue,
    vRtrIfIpv6uRPFIgnoreDefault      TruthValue,
    vRtrIfIpv6DadDisable             TruthValue,
    vRtrIfTeidLoadBalancing          TruthValue,
    vRtrIfEgrIpLoadBalancing         INTEGER,
    vRtrIfPlcyAcctTemplateName       TNamedItemOrEmpty,
    vRtrIfIpv6NdCacheStaleTime       Unsigned32,
    vRtrIfTmsOffRampIgrVrf           TmnxVRtrIDOrZero,
    vRtrIfArpRetryTimer              Unsigned32,
    vRtrIfSpiLoadBalancing           TruthValue,
    vRtrIfArpLimit                   Integer32,
    vRtrIfArpLogOnly                 TruthValue,
    vRtrIfArpThreshold               Unsigned32,
    vRtrIfVasIfType                  INTEGER,
    vRtrIfIpv6NbrLimit               Integer32,
    vRtrIfIpv6NbrLogOnly             TruthValue,
    vRtrIfIpv6NbrThreshold           Unsigned32,
    vRtrIfDelayV4UpSeconds           Unsigned32,
    vRtrIfDelayV4DownSeconds         Unsigned32,
    vRtrIfDelayV6UpSeconds           Unsigned32,
    vRtrIfDelayV6DownSeconds         Unsigned32,
    vRtrIfDelayV4Timer               Integer32,
    vRtrIfDelayV6Timer               Integer32,
    vRtrIfInitDelayV4Enable          TruthValue,
    vRtrIfInitDelayV6Enable          TruthValue,
    vRtrIfOperV4DownReason           BITS,
    vRtrIfOperV6DownReason           BITS,
    vRtrIfLdpEolib                   TruthValue,
    vRtrIfCreationOrigin             TmnxCreateOrigin,
    vRtrIfIcmpV4ParamProblem         TruthValue,
    vRtrIfIcmpV4NumParamProblem      Unsigned32,
    vRtrIfIcmpV4ParamProblemTime     Unsigned32,
    vRtrIfOperDCpuProtPolicy         TNamedItemOrEmpty,
    vRtrIfUrpfSelectedVprnsOnly      TruthValue,
    vRtrIfIpTunnelRemoteIpAddrType   InetAddressType,
    vRtrIfIpTunnelRemoteIpAddr       InetAddress,
    vRtrIfIpv4ArpLearnUnsol          TruthValue,
    vRtrIfIpv4ArpProRef              TruthValue,
    vRtrIfIpv6NdLearnUnsol           INTEGER,
    vRtrIfIpv6NdProRef               INTEGER,
    vRtrIfIpv6FlowLabelHashing       TruthValue,
    vRtrIfIngressIPFilterPair        TruthValue
}

vRtrIfLsrIpLoadBalancing         OBJECT-TYPE
    SYNTAX      INTEGER {
        system           (0),
        label-only       (1),
        label-ip         (2),
        ip-only          (3),
        eth-encap-ip     (4),
        label-ip-l4-teid (5)
    }
    MAX-ACCESS  read-create
    STATUS      current
    DESCRIPTION
        "The value of vRtrIfLsrIpLoadBalancing specifies whether the IP Header
         is used in the LAG and ECMP LSR hashing algorithm. This is the per
         interface setting.

         When set to 'system (0)', the hashing algorithm is inherited from the
         object tmnxLsrIpLoadBalancing.

         When set to 'label-only (1)' only the label is used in the hashing
         algorithm.

         When set to 'label-ip (2)', the IP Header is included in the hashing
         algorithm.

         When set to 'ip-only (3)' the IP Header is used exclusively in the
         hashing Algorithm.

         When set to 'eth-encap-ip (4)' the IP SA/DA fields is used in the
         hashing Algorithm.

         When set to 'label-ip-l4-teid (5)' the hashing algorithm hashes based
         on label, IP header, L4 header, and GTP header (TEID) in order. The
         hashing algorithm will use all the supported headers that are found in
         the header fragment of incoming traffic."
    DEFVAL      { system }
    ::= { vRtrIfExtEntry 1 }

vRtrIfIngressIpv4Flowspec        OBJECT-TYPE
    SYNTAX      TruthValue
    MAX-ACCESS  read-create
    STATUS      obsolete
    DESCRIPTION
        "The value of vRtrIfIngressIpv4Flowspec specifies whether ingress
         Flowspec for IPv4 is enabled for this interface."
    DEFVAL      { false }
    ::= { vRtrIfExtEntry 2 }

vRtrIfInfo                       OBJECT-TYPE
    SYNTAX      OCTET STRING (SIZE (0..257))
    MAX-ACCESS  read-create
    STATUS      obsolete
    DESCRIPTION
        "The value of vRtrIfInfo specifies the information used to authenticate
         the interface."
    DEFVAL      { ''H }
    ::= { vRtrIfExtEntry 3 }

vRtrIfInfoEncrypted              OBJECT-TYPE
    SYNTAX      TruthValue
    MAX-ACCESS  read-create
    STATUS      obsolete
    DESCRIPTION
        "The object vRtrIfInfoEncrypted is currently not supported."
    DEFVAL      { true }
    ::= { vRtrIfExtEntry 4 }

vRtrIfQosRouteLookup             OBJECT-TYPE
    SYNTAX      INTEGER {
        none            (0),
        destination     (1),
        source          (2),
        source-and-dest (3)
    }
    MAX-ACCESS  read-create
    STATUS      current
    DESCRIPTION
        "The value of vRtrIfQosRouteLookup specifies whether QoS classification
         of the ingress IP packets based on the route lookup is enabled for
         ipv4 on this router interface.

         By default the value of vRtrIfQosRouteLookup is set to 'none (0)',
         which means the Qos classification of incoming IP packets based on the
         route lookup is disabled for ipv4 on this interface.

         When the value of vRtrIfQosRouteLookup is 'destination (1)', the QoS
         route lookup is enabled and the Qos classification of incoming IP
         packets is based on the destination address matching.

         When the value of vRtrIfQosRouteLookup is 'source (2)', the QoS route
         lookup is enabled and the Qos classification of incoming IP packets is
         based on the source address matching.

         When the value of vRtrIfQosRouteLookup is 'source-and-dest (3)', the
         QoS route lookup is enabled and the Qos classification of incoming IP
         packets is based on the source address and destination address
         matching."
    DEFVAL      { none }
    ::= { vRtrIfExtEntry 5 }

vRtrIfIpv6QosRouteLookup         OBJECT-TYPE
    SYNTAX      INTEGER {
        none            (0),
        destination     (1),
        source          (2),
        source-and-dest (3)
    }
    MAX-ACCESS  read-create
    STATUS      current
    DESCRIPTION
        "The value of vRtrIfIpv6QosRouteLookup specifies whether QoS
         classification of the ingress IP packets based on the route lookup is
         enabled for ipv6 on this router interface.

         By default the value of vRtrIfIpv6QosRouteLookup is 'none (0)', which
         means the Qos classification of incoming IP packets based on the route
         lookup is disabled on this interface.

         When the value of vRtrIfIpv6QosRouteLookup is 'destination (1)', the
         QoS route lookup is enabled and the Qos classification of incoming IP
         packets is based on the destination address matching.

         When the value of vRtrIfIpv6QosRouteLookup is 'source (2)', the QoS
         route lookup is enabled and the Qos classification of incoming IP
         packets is based on the source address matching.

         When the value of vRtrIfIpv6QosRouteLookup is 'source-and-dest (3)',
         the QoS route lookup is enabled and the Qos classification of incoming
         IP packets is based on the source address and destination address
         matching."
    DEFVAL      { none }
    ::= { vRtrIfExtEntry 6 }

vRtrIfStatusString               OBJECT-TYPE
    SYNTAX      DisplayString
    MAX-ACCESS  read-only
    STATUS      obsolete
    DESCRIPTION
        "The value of vRtrIfStatusString indicates the status information about
         the interface."
    ::= { vRtrIfExtEntry 7 }

vRtrIfIpv6uRPFCheckState         OBJECT-TYPE
    SYNTAX      TmnxEnabledDisabled
    MAX-ACCESS  read-create
    STATUS      current
    DESCRIPTION
        "The value of vRtrIfIpv6uRPFCheckState specifies whether unicast RPF
         (uRPF) check is enabled on this interface."
    DEFVAL      { disabled }
    ::= { vRtrIfExtEntry 8 }

vRtrIfIpv6uRPFCheckMode          OBJECT-TYPE
    SYNTAX      TmnxUrpfCheckMode
    MAX-ACCESS  read-create
    STATUS      current
    DESCRIPTION
        "The value of vRtrIfIpv6uRPFCheckMode specifies the mode of unicast RPF
         check.

         By default the value of vRtrIfIpv6uRPFCheckMode is 'strict (1)',which
         means that uRPF checks whether the incoming packet has a source
         address that matches a prefix in the routing table, and whether the
         interface expects to receive a packet with this source address prefix.

         When the value of vRtrIfIpv6uRPFCheckMode is 'loose (2)', the uRPF
         checks whether the incoming packet has a source address with a
         corresponding prefix in the routing table. It does not check whether
         the interface expects to receive a packet with a specific source
         address prefix.

         When the value of vRtrIfIpv6uRPFCheckMode is 'strictNoEcmp (3)', the
         uRPF checks whether the incoming packet has a source address which
         matches an ECMP route. If the source address matches an ECMP route,
         the packet is dropped by uRPF. Otherwise, the behavior is same as
         'strict' mode.

         This object is valid only when value of vRtrIfIpv6uRPFCheckState is
         set to 'enabled'."
    DEFVAL      { strict }
    ::= { vRtrIfExtEntry 9 }

vRtrIfTmsOffRampVprn             OBJECT-TYPE
    SYNTAX      TmnxServId
    MAX-ACCESS  read-create
    STATUS      obsolete
    DESCRIPTION
        "The vRtrIfTmsOffRampVprn specifies the off-ramp VPRN service
         associated with this threat management service (TMS) interface.

         An 'inconsistentValue' error is returned when this object is set to a
         non-default value when vRtrIfType is not set to 'tmsService'.

         An 'inconsistentValue' error is returned when this object is set to a
         different value when vRtrIfRowStatus is set to 'active'."
    DEFVAL      { 0 }
    ::= { vRtrIfExtEntry 10 }

vRtrIfTmsMgmtVprn                OBJECT-TYPE
    SYNTAX      TmnxServId
    MAX-ACCESS  read-create
    STATUS      obsolete
    DESCRIPTION
        "The vRtrIfTmsMgmtVprn specifies the management VPRN service associated
         with this threat management service (TMS) interface.

         An 'inconsistentValue' error is returned when this object is set to a
         non-default value when vRtrIfType is not set to 'tmsService'.

         An 'inconsistentValue' error is returned when this object is set to a
         different value when vRtrIfRowStatus is set to 'active'."
    DEFVAL      { 0 }
    ::= { vRtrIfExtEntry 11 }

vRtrIfTrackMobile                OBJECT-TYPE
    SYNTAX      TmnxEnabledDisabled
    MAX-ACCESS  read-create
    STATUS      current
    DESCRIPTION
        "The value of vRtrIfTrackMobile specifies whether to track the
         interface's ipv4 route depending on the geo-redundancy state of the
         associated mobile gateway."
    DEFVAL      { disabled }
    ::= { vRtrIfExtEntry 12 }

vRtrIfIpv6TrackMobile            OBJECT-TYPE
    SYNTAX      TmnxEnabledDisabled
    MAX-ACCESS  read-create
    STATUS      current
    DESCRIPTION
        "The value of vRtrIfIpv6TrackMobile specifies whether to track the
         interface's ipv6 route depending on the geo-redundancy state of the
         associated mobile gateway."
    DEFVAL      { disabled }
    ::= { vRtrIfExtEntry 13 }

vRtrIfIngressIpv6Flowspec        OBJECT-TYPE
    SYNTAX      TruthValue
    MAX-ACCESS  read-create
    STATUS      obsolete
    DESCRIPTION
        "The value of vRtrIfIngressIpv6Flowspec specifies whether ingress
         Flowspec for IPv6 is enabled for this interface."
    DEFVAL      { false }
    ::= { vRtrIfExtEntry 14 }

vRtrIfLagLinkMapProfile          OBJECT-TYPE
    SYNTAX      TmnxLinkMapProfileIdOrZero
    MAX-ACCESS  read-create
    STATUS      current
    DESCRIPTION
        "The value of vRtrIfLagLinkMapProfile specifies the lag link map
         profile to be used by the interface when the physical port associated
         with the interface is a LAG"
    DEFVAL      { 0 }
    ::= { vRtrIfExtEntry 15 }

vRtrIfLagActivePort              OBJECT-TYPE
    SYNTAX      TmnxPortID
    MAX-ACCESS  read-only
    STATUS      current
    DESCRIPTION
        "The value of vRtrIfLagActivePort indicates a port on the lag
         associated with this interface, that is used when tLagPerLinkHash is
         enabled on the lag or when vRtrIfLagLinkMapProfile is configured on
         this interface."
    ::= { vRtrIfExtEntry 16 }

vRtrIfDCpuProtPolicy             OBJECT-TYPE
    SYNTAX      TNamedItemOrEmpty
    MAX-ACCESS  read-create
    STATUS      current
    DESCRIPTION
        "The value of vRtrIfDCpuProtPolicy associates Distributed CPU
         Protection Policy with a Virtual Router Interface."
    DEFVAL      { ''H }
    ::= { vRtrIfExtEntry 17 }

vRtrIfMcastNetworkDomainName     OBJECT-TYPE
    SYNTAX      TNamedItemOrEmpty
    MAX-ACCESS  read-create
    STATUS      current
    DESCRIPTION
        "The value of vRtrIfMcastNetworkDomainName specifies the multicast
         network domain name, a group of network interfaces, to be used for
         multicast replication when a spoke-sdp is bound to the interface.

         Multicast traffic is only copied to the subset of network interfaces
         defined by the network domain."
    DEFVAL      { ''H }
    ::= { vRtrIfExtEntry 18 }

vRtrIfIngressStatsEnabled        OBJECT-TYPE
    SYNTAX      TruthValue
    MAX-ACCESS  read-create
    STATUS      current
    DESCRIPTION
        "The value of vRtrIfIngressStatsEnabled specifies if ingress statistics
         gathering is enabled for this interface."
    DEFVAL      { false }
    ::= { vRtrIfExtEntry 20 }

vRtrIfIpv6ReachableTime          OBJECT-TYPE
    SYNTAX      Unsigned32 (0 | 30..3600)
    UNITS       "seconds"
    MAX-ACCESS  read-create
    STATUS      current
    DESCRIPTION
        "The value of vRtrIfIpv6ReachableTime specifies the time an IPv6
         neighbor on this interface remains in reachable state. While in this
         state, no neighbor-unreachability detection has to be done.

         A value of zero (0) indicates that the time specified in
         vRtrIpv6ReachableTime for the parent router is used instead."
    DEFVAL      { 0 }
    ::= { vRtrIfExtEntry 21 }

vRtrIfEnableMacAccounting        OBJECT-TYPE
    SYNTAX      TruthValue
    MAX-ACCESS  read-create
    STATUS      current
    DESCRIPTION
        " The value of vRtrIfEnableMacAccounting specifies if MAC accounting
         functionality is enabled on an interface.

         When the value of vRtrIfEnableMacAccounting is set to 'true', MAC
         accounting functionality is enabled on that interface."
    DEFVAL      { false }
    ::= { vRtrIfExtEntry 23 }

vRtrIfTcpMss                     OBJECT-TYPE
    SYNTAX      Unsigned32 (0 | 384..9746)
    MAX-ACCESS  read-create
    STATUS      current
    DESCRIPTION
        "The value of vRtrIfTcpMss specifies the TCP maximum segment size(MSS)
         for TCP connections originated from the associated IP interface.

         When the value of vRtrIfTcpMss is set to 0, the command removes the
         static value and allows the TCP MSS value to be calculated based on
         the IP MTU value."
    DEFVAL      { 0 }
    ::= { vRtrIfExtEntry 25 }

vRtrIfIpv6TcpMss                 OBJECT-TYPE
    SYNTAX      Unsigned32 (0 | 1220..9726)
    MAX-ACCESS  read-create
    STATUS      current
    DESCRIPTION
        "The value of vRtrIfIpv6TcpMss specifies the TCP maximum segment
         size(MSS) for TCP connections originated from the associated IP
         interface.

         When the value of vRtrIfIpv6TcpMss is set to 0, the command removes
         the static value and allows the TCP MSS value to be calculated based
         on the IP MTU value.

         When the value of vRtrIfIPv6ConfigAllowed is set to true the range
         allowed for vRtrIfIpv6TcpMss is from 1220 to 9138. For FP4 cards the
         range is 1220 to 9726"
    DEFVAL      { 0 }
    ::= { vRtrIfExtEntry 26 }

vRtrIfuRPFIgnoreDefault          OBJECT-TYPE
    SYNTAX      TruthValue
    MAX-ACCESS  read-create
    STATUS      current
    DESCRIPTION
        "The value of vRtrIfuRPFIgnoreDefault specifies if the default route is
         to be disregarded while performing a uRPF check

         When the value of vRtrIfuRPFIgnoreDefault is set to 'true', the
         default route is disregarded while performing a uRPF check. The
         default route is disregarded for all the values of
         vRtrIfuRPFCheckMode."
    DEFVAL      { false }
    ::= { vRtrIfExtEntry 27 }

vRtrIfIpv6uRPFIgnoreDefault      OBJECT-TYPE
    SYNTAX      TruthValue
    MAX-ACCESS  read-create
    STATUS      current
    DESCRIPTION
        "The value of vRtrIfIpv6uRPFIgnoreDefault specifies if the default
         route is to be disregarded while performing a uRPF check.

         When the value of vRtrIfIpv6uRPFIgnoreDefault is set to 'true', the
         default route is disregarded while performing a uRPF check. The
         default route is disregarded for all the values of
         vRtrIfIpv6uRPFCheckMode."
    DEFVAL      { false }
    ::= { vRtrIfExtEntry 28 }

vRtrIfIpv6DadDisable             OBJECT-TYPE
    SYNTAX      TruthValue
    MAX-ACCESS  read-create
    STATUS      current
    DESCRIPTION
        "The value of vRtrIfIpv6DadDisable specifies if the Duplicate Address
         Detection (DAD) is disabled for this interface.

         The value 'false' specifies that DAD is enabled, while the value
         'true' specifies that DAD is disabled.

         Setting this object is only relevant while the value of the object
         vRtrIfIPv6ConfigAllowed is equal to 'true' for the corresponding row
         in the vRtrIfTable."
    REFERENCE
        "RFC2462 IPv6 Stateless Address Autoconfiguration,
         section 5.4 Duplicate Address Detection"
    DEFVAL      { false }
    ::= { vRtrIfExtEntry 35 }

vRtrIfTeidLoadBalancing          OBJECT-TYPE
    SYNTAX      TruthValue
    MAX-ACCESS  read-create
    STATUS      current
    DESCRIPTION
        "The value of vRtrIfTeidLoadBalancing specifies whether TEID load
         balancing is enabled for GTP-U/GTP-C tunnels on all configured
         IES/VPRN/router interfaces."
    DEFVAL      { false }
    ::= { vRtrIfExtEntry 36 }

vRtrIfEgrIpLoadBalancing         OBJECT-TYPE
    SYNTAX      INTEGER {
        both        (0),
        destination (1),
        source      (2),
        innerIp     (3)
    }
    MAX-ACCESS  read-create
    STATUS      current
    DESCRIPTION
        "The value of vRtrIfEgrIpLoadBalancing specifies hash parameters to be
         used for IPv4/v6 header load balancing.

         By default the value of vRtrIfEgrIpLoadBalancing is set to 'both (0)',
         which means vRtrIfEgrIpLoadBalancing uses IP source and destination
         addresses in outer IP header in LAG/ECMP hash on IP interfaces.

         When the value of vRtrIfEgrIpLoadBalancing is 'destination (1)',
         vRtrIfEgrIpLoadBalancing uses only IP destination address in LAG/ECMP
         hash on IP interfaces and ignores source address. If the value of
         vRtrIfEgrIpLoadBalancing is 'destination (1)' and the value of
         TIMETRA-PORT-MIB::tmnxL4LoadBalancing is 'true', then
         vRtrIfEgrIpLoadBalancing uses both IP destination address and port in
         the hash, and ignores IP source address/port.

         When the value of vRtrIfEgrIpLoadBalancing is 'source (2)',
         vRtrIfEgrIpLoadBalancing uses only IP source address in LAG/ECMP hash
         on IP interfaces and ignores destination address. If the value of
         vRtrIfEgrIpLoadBalancing is 'source (2)' and the value of
         TIMETRA-PORT-MIB::tmnxL4LoadBalancing is 'true', then
         vRtrIfEgrIpLoadBalancing uses both IP source address and port in the
         hash, and ignores IP destination address/port.

         When the value of vRtrIfEgrIpLoadBalancing is 'innerIp (3)',
         vRtrIfEgrIpLoadBalancing uses source/destination addresses from the
         inner IPv4 or IPv6 packet tunnelled inside IPv4 tunnel in the hash."
    DEFVAL      { both }
    ::= { vRtrIfExtEntry 37 }

vRtrIfPlcyAcctTemplateName       OBJECT-TYPE
    SYNTAX      TNamedItemOrEmpty
    MAX-ACCESS  read-create
    STATUS      current
    DESCRIPTION
        "The value of vRtrIfPlcyAcctTemplateName specifies the policy
         accounting template associated with this interface."
    DEFVAL      { ''H }
    ::= { vRtrIfExtEntry 38 }

vRtrIfIpv6NdCacheStaleTime       OBJECT-TYPE
    SYNTAX      Unsigned32 (0 | 60..65535)
    UNITS       "seconds"
    MAX-ACCESS  read-create
    STATUS      current
    DESCRIPTION
        "The value of vRtrIfIpv6NdCacheStaleTime specifies the time an IPv6
         neighbor cache entry on this interface remains in stale state.

         When this time has elapsed, the system removes the neighbor cache
         entry.

         The value zero means that the actual value is taken from the object
         vRtrIpv6NdCacheStaleTime in the parent router instance."
    REFERENCE
        "RFC 2461 Neighbor Discovery for IP Version 6 (IPv6)
         section 7.3.2. Neighbor Cache Entry States"
    DEFVAL      { 0 }
    ::= { vRtrIfExtEntry 39 }

vRtrIfTmsOffRampIgrVrf           OBJECT-TYPE
    SYNTAX      TmnxVRtrIDOrZero
    MAX-ACCESS  read-create
    STATUS      obsolete
    DESCRIPTION
        "The value of vRtrIfTmsOffRampIgrVrf specifies the routing context
         that will be used by the system to route traffic originating from
         the TMS module and arriving at the  ingress side of the off-ramp
         interface.

         The (default) value '0' indicates that the traffic will be routed in
         the routing context to which the off-ramp interface belongs.

         When a non zero value is specified the system will attach an internal
         ACL filter to the ingress side of the off-ramp interface, which will
         redirect all traffic to the routing context of the specified vRtrID.

         An 'inconsistentValue' error is returned when this object is set to a
         non-default value when vRtrIfType is not set to 'tmsService'"
    DEFVAL      { 0 }
    ::= { vRtrIfExtEntry 41 }

vRtrIfArpRetryTimer              OBJECT-TYPE
    SYNTAX      Unsigned32 (1..300)
    UNITS       "deciseconds"
    MAX-ACCESS  read-create
    STATUS      current
    DESCRIPTION
        "The value of vRtrIfArpRetryTimer specifies the ARP retry interval in
         deciseconds for an interface."
    DEFVAL      { 50 }
    ::= { vRtrIfExtEntry 42 }

vRtrIfSpiLoadBalancing           OBJECT-TYPE
    SYNTAX      TruthValue
    MAX-ACCESS  read-create
    STATUS      current
    DESCRIPTION
        "The value of vRtrIfSpiLoadBalancing specifies whether SPI use in
         hashing is enabled on the configured IES/VPRN/router interfaces."
    DEFVAL      { false }
    ::= { vRtrIfExtEntry 46 }

vRtrIfArpLimit                   OBJECT-TYPE
    SYNTAX      Integer32 (-1 | 0 | 1..524288)
    MAX-ACCESS  read-create
    STATUS      current
    DESCRIPTION
        "The value of vRtrIfArpLimit specifies the maximum number of IPv4 ARP
         entries that can be learned on an IP interface.

         The tmnxVRtrArpThresholdExceeded notification is sent when the number
         of entries exceeds a percentage of this limit as specified by
         vRtrIfArpThreshold.

         When the number of IPv4 ARP entries exceeds vRtrIfArpLimit, then a
         tmnxVRtrArpLmt notification is sent and no new entries are learned
         until an entry expires.

         When the value of vRtrIfArpLimit is set to '0', dynamic ARP learning
         is disabled and no dynamic ARP entries are learned.

         When the value of vRtrIfArpLimit is set to '-1', dynamic ARP limits
         are disabled and the maximum number of dynamic ARPs can be learned."
    DEFVAL      { -1 }
    ::= { vRtrIfExtEntry 47 }

vRtrIfArpLogOnly                 OBJECT-TYPE
    SYNTAX      TruthValue
    MAX-ACCESS  read-create
    STATUS      current
    DESCRIPTION
        "The value of vRtrIfArpLogOnly specifies whether dynamic learning
         continues or not on the interface when vRtrIfArpLimit is exceeded.

         When the value is set to 'true', dynamic learning will continue after
         the limit is exceeded.

         When the value is set to 'false', dynamic learning will be disabled
         after the limit is exceeded and re-enabled on the interface when the
         number of ARP entries falls below the limit again."
    DEFVAL      { false }
    ::= { vRtrIfExtEntry 48 }

vRtrIfArpThreshold               OBJECT-TYPE
    SYNTAX      Unsigned32 (1..100)
    UNITS       "percent"
    MAX-ACCESS  read-create
    STATUS      current
    DESCRIPTION
        "The value of vRtrIfArpThreshold specifies a percentage of
         vRtrIfArpLimit when exceeded triggers a tmnxVRtrArpThresholdExceeded
         notification to be sent."
    DEFVAL      { 90 }
    ::= { vRtrIfExtEntry 49 }

vRtrIfVasIfType                  OBJECT-TYPE
    SYNTAX      INTEGER {
        none          (0),
        toFromAccess  (1),
        toFromNetwork (2),
        toFromBoth    (3)
    }
    MAX-ACCESS  read-create
    STATUS      current
    DESCRIPTION
        "The value of the object vRtrIfVasIfType specifies whether this is a
         VAS access-facing interface (for ESM/AA this means sub-facing
         interface). It allows to skip over egress PBR for after-VAS traffic
         and allows to skip over AA divert when AA is deployed.

         none (0):
            Used when this interface is not a VAS access facing interface. This
            value is the default value.

         toFromAccess (1):
            Used when two separate toFromAccess and toFromNetwork interfaces
            are used for Value Added Service (VAS) connectivity.
            For VAS chaining: traffic arriving from access interfaces (like
            from a subscriber) is redirected to a PBR target reachable over
            this interface for upstream VAS processing; and downstream traffic
            after VAS processing must arrive on this interface, so the traffic
            is subject to regular routing but is not subject to AA divert, nor
            egress subscriber PBR.

         toFromNetwork (2):
            Used when two separate (toFromAccess and toFromNetwork)
            interfaces are used for Value Added Service (VAS) connectivity.
            For VAS chaining: traffic arriving from network interfaces (like
            destined to a subscriber) is redirected to a PBR target reachable
            over this interface for downstream VAS processing; and upstream
            traffic after VAS processing should arrive on this interface,
            so regular routing can be applied.

         toFromBoth (3):
            Used when single interface is used for Value Added Service (VAS)
            connectivity.
            For VAS chaining: both traffic arriving from access and network
            is redirected to a PBR target reachable over this interface for
            upstream/downstream VAS processing; and downstream traffic after
            VAS processing must arrive on this interface, so the traffic is
            subject to regular routing but is not subject to AA divert,
            nor egress subscriber PBR."
    DEFVAL      { none }
    ::= { vRtrIfExtEntry 50 }

vRtrIfIpv6NbrLimit               OBJECT-TYPE
    SYNTAX      Integer32 (-1 | 0 | 1..102400)
    MAX-ACCESS  read-create
    STATUS      current
    DESCRIPTION
        "The value of vRtrIfIpv6NbrLimit specifies the maximum number of IPv6
         neighbor entries that can be learned on an IP interface.

         The tmnxVRtrIpv6NbrThresholdExceeded notification is sent when the
         number of entries exceeds a percentage of this limit as specified by
         vRtrIfIpv6NbrThreshold.

         When the number of neighbor entries exceeds vRtrIfIpv6NbrLimit, then a
         tmnxVRtrIpv6NbrLmt notification is sent and no new entries are learned
         until an entry expires.

         When the value of vRtrIfIpv6NbrLimit is set to '0', dynamic neighbor
         learning is disabled and no dynamic neighbor entries are learned.

         When the value of vRtrIfIpv6NbrLimit is set to '-1', dynamic neighbor
         limits are disabled and the maximum number of dynamic neighbor entries
         can be learned."
    DEFVAL      { -1 }
    ::= { vRtrIfExtEntry 51 }

vRtrIfIpv6NbrLogOnly             OBJECT-TYPE
    SYNTAX      TruthValue
    MAX-ACCESS  read-create
    STATUS      current
    DESCRIPTION
        "The value of vRtrIfIpv6NbrLogOnly specifies whether dynamic learning
         continues or not on the interface when vRtrIfIpv6NbrLimit is exceeded.

         When the value is set to 'true', dynamic learning will continue after
         the limit is exceeded.

         When the value is set to 'false', dynamic learning will be disabled
         after the limit is exceeded and re-enabled on the interface when the
         number of neighbor entries falls below the limit again."
    DEFVAL      { false }
    ::= { vRtrIfExtEntry 52 }

vRtrIfIpv6NbrThreshold           OBJECT-TYPE
    SYNTAX      Unsigned32 (1..100)
    UNITS       "percent"
    MAX-ACCESS  read-create
    STATUS      current
    DESCRIPTION
        "The value of vRtrIfIpv6NbrThreshold specifies a percentage of
         vRtrIfIpv6NbrLimit when exceeded, triggers a
         tmnxVRtrIpv6NbrThresholdExceeded notification to be sent."
    DEFVAL      { 90 }
    ::= { vRtrIfExtEntry 53 }

vRtrIfDelayV4UpSeconds           OBJECT-TYPE
    SYNTAX      Unsigned32 (0..1200)
    UNITS       "seconds"
    MAX-ACCESS  read-create
    STATUS      current
    DESCRIPTION
        "The value of vRtrIfDelayV4UpSeconds specifies the time in seconds that
         is used to bring up the IPv4 interface.

         When an interface comes up, it will not become operational until after
         the specified delay.

         The value specified can be in the range of 0..1200. The default value
         is 0. (no delay)"
    DEFVAL      { 0 }
    ::= { vRtrIfExtEntry 54 }

vRtrIfDelayV4DownSeconds         OBJECT-TYPE
    SYNTAX      Unsigned32 (0..1200)
    UNITS       "seconds"
    MAX-ACCESS  read-create
    STATUS      current
    DESCRIPTION
        "The value of vRtrIfDelayV4DownSeconds specifies the time in seconds
         that is used to bring down the IPv4 interface.

         The value specified can be in the range of 0..1200. The default value
         is 0. (no delay)"
    DEFVAL      { 0 }
    ::= { vRtrIfExtEntry 55 }

vRtrIfDelayV6UpSeconds           OBJECT-TYPE
    SYNTAX      Unsigned32 (0..1200)
    UNITS       "seconds"
    MAX-ACCESS  read-create
    STATUS      current
    DESCRIPTION
        "The value of vRtrIfDelayV6UpSeconds specifies the time in seconds that
         is used to bring up the IPv6 interface.

         When an interface comes up, it will not become operational until after
         the specified delay.

         The value specified can be in the range of 0..1200. The default value
         is 0. (no delay)"
    DEFVAL      { 0 }
    ::= { vRtrIfExtEntry 56 }

vRtrIfDelayV6DownSeconds         OBJECT-TYPE
    SYNTAX      Unsigned32 (0..1200)
    UNITS       "seconds"
    MAX-ACCESS  read-create
    STATUS      current
    DESCRIPTION
        "The value of vRtrIfDelayV6DownSeconds specifies the time in seconds
         that is used to bring down the IPv6 interface.

         The value specified can be in the range of 0..1200. The default value
         is 0. (no delay)"
    DEFVAL      { 0 }
    ::= { vRtrIfExtEntry 57 }

vRtrIfDelayV4Timer               OBJECT-TYPE
    SYNTAX      Integer32
    UNITS       "seconds"
    MAX-ACCESS  read-only
    STATUS      current
    DESCRIPTION
        "The value of vRtrIfDelayV4Timer indicates the time left before the
         interface comes up or goes down, depending on the ongoing transition
         state of the interface."
    ::= { vRtrIfExtEntry 58 }

vRtrIfDelayV6Timer               OBJECT-TYPE
    SYNTAX      Integer32
    UNITS       "seconds"
    MAX-ACCESS  read-only
    STATUS      current
    DESCRIPTION
        "The value of vRtrIfDelayV6Timer indicates the time left before the
         interface comes up or goes down, depending on the ongoing transition
         state of the interface."
    ::= { vRtrIfExtEntry 59 }

vRtrIfInitDelayV4Enable          OBJECT-TYPE
    SYNTAX      TruthValue
    MAX-ACCESS  read-create
    STATUS      current
    DESCRIPTION
        "The value of vRtrIfInitDelayV4Enable specifies whether
         vRtrIfDelayV4UpSeconds is used only the next time or everytime the
         system attempts to bring the interface operationally up.

         The value of vRtrIfInitDelayV4Enable is ignored if the value of
         vRtrIfDelayV4UpSeconds is set to 0.

         The value of vRtrIfInitDelayV4Enable is only set when interface is of
         type subscriber interface.

         When the value vRtrIfInitDelayV4Enable is set to 'false', everytime
         the system attempts to bring the interface operationally up, it will
         be delayed by the value of vRtrIfDelayV4UpSeconds.

         When the value vRtrIfInitDelayV4Enable is set to 'true', only the next
         time the system attempts to bring the interface operationally up, it
         will be delayed by the value of vRtrIfDelayV4UpSeconds."
    DEFVAL      { false }
    ::= { vRtrIfExtEntry 60 }

vRtrIfInitDelayV6Enable          OBJECT-TYPE
    SYNTAX      TruthValue
    MAX-ACCESS  read-create
    STATUS      current
    DESCRIPTION
        "The value of vRtrIfInitDelayV6Enable specifies whether
         vRtrIfDelayV6UpSeconds is used only the next time or everytime the
         system attempts to bring the interface operationally up.

         The value of vRtrIfInitDelayV6Enable is ignored if the value of
         vRtrIfDelayV6UpSeconds is set to 0.

         The value of vRtrIfInitDelayV6Enable is only set when interface is of
         type subscriber interface.

         When the value vRtrIfInitDelayV6Enable is set to 'false', everytime
         the system attempts to bring the interface operationally up, it will
         be delayed by the value of vRtrIfDelayV6UpSeconds.

         When the value vRtrIfInitDelayV6Enable is set to 'true', only the next
         time the system attempts to bring the interface operationally up, it
         will be delayed by the value of vRtrIfDelayV6UpSeconds."
    DEFVAL      { false }
    ::= { vRtrIfExtEntry 61 }

vRtrIfOperV4DownReason           OBJECT-TYPE
    SYNTAX      BITS {
        ifAdminDown             (0),
        svcAdminDown            (1),
        portOperDown            (2),
        addrOrIfNotReady        (3),
        assocObjNotReady        (4),
        rvplsDown               (5),
        operGrpDown             (6),
        ifAdminDestroy          (7),
        noIfAddress             (8),
        noIfInfo                (9),
        delayedStartEnabled     (10),
        ifProtoOperDown         (11),
        invalidPortCfg          (12),
        unknown                 (13),
        noRouteDistinguisher    (14),
        wlanGwRedundancyStandby (15),
        wlanGwGroupDegraded     (16),
        ipControlTunnelOperDown (17),
        pdnAddressMismatch      (18),
        pingCheckFailure        (19),
        portInternalLoopback    (20),
        noHwResForSrv6Loopback  (21),
        ipTunnelNotReady        (22)
    }
    MAX-ACCESS  read-only
    STATUS      current
    DESCRIPTION
        "The value of vRtrIfOperV4DownReason indicates the reason why the
         interface is operationally down.

         The bit values are:
         'ifAdminDown (0)'              - Interface is administratively down
         'svcAdminDown (1)'             - Service is administratively down
         'portOperDown (2)'             - SAP port is operationally down
         'addrOrIfNotReady (3)'         - Address or Parent interface is not
                                          ready
         'assocObjNotReady (4)'         - Associated object is not ready
         'rvplsDown (5)'                - R-VPLS service is down
         'operGrpDown (6)'              - Associated Operational Group is down
         'ifAdminDestroy (7)'           - Interface is being deleted
         'noIfAddress (8)'              - Interface address is not configured
         'noIfInfo (9)'                 - Interface info not present
         'delayedStartEnabled (10)'     - Delayed start timer is enabled on
                                          the interface
         'ifProtoOperDown (11)'         - Protocols on interface are
                                          operationally down
         'invalidPortCfg (12)'          - Port configuration is not valid
         'unknown (13)'                 - Reason is unknown
         'noRouteDistinguisher (14)'    - Route Distinguisher not configured in VPRN
         'wlanGwRedundancyStandby (15)' - Interface is in standby state for
                                          WLAN-GW redundancy
         'wlanGwGroupDegraded (16)'     - The associated WLAN-GW group is in a
                                          degraded state
         'ipControlTunnelOperDown (17)' - The IP tunnel associated to a control-tunnel
                                          interface is operationally down
         'pdnAddressMismatch (18)'      - The IP address learned from the packet data network
                                          does not match the configured primary IP address
         'pingCheckFailure (19)'        - The IP interface is or went down because of ping-template
                                          failure
         'portInternalLoopback (20)'    - The IP interface is bound to a port that has an
                                          internal loopback configured
         'noHwResForSrv6Loopback (21)'  - There are not enough resources for the SRv6 locator
                                          prefix loopback address
         'ipTunnelNotReady (22)'        - The IP tunnel associated to an
                                          ip-tunnel-interface is not ready"
    ::= { vRtrIfExtEntry 62 }

vRtrIfOperV6DownReason           OBJECT-TYPE
    SYNTAX      BITS {
        ifAdminDown             (0),
        svcAdminDown            (1),
        portOperDown            (2),
        addrOrIfNotReady        (3),
        assocObjNotReady        (4),
        rvplsDown               (5),
        operGrpDown             (6),
        ifAdminDestroy          (7),
        noIfAddress             (8),
        noIfInfo                (9),
        delayedStartEnabled     (10),
        ifProtoOperDown         (11),
        invalidPortCfg          (12),
        unknown                 (13),
        noRouteDistinguisher    (14),
        wlanGwRedundancyStandby (15),
        wlanGwGroupDegraded     (16),
        ipControlTunnelOperDown (17),
        pdnAddressMismatch      (18),
        pingCheckFailure        (19),
        portInternalLoopback    (20),
        noHwResForSrv6Loopback  (21),
        ipTunnelNotReady        (22)
    }
    MAX-ACCESS  read-only
    STATUS      current
    DESCRIPTION
        "The value of vRtrIfOperV6DownReason indicates the reason why the
         interface is operationally down.

         The bit values are:
         'ifAdminDown (0)'              - Interface is administratively down
         'svcAdminDown (1)'             - Service is administratively down
         'portOperDown (2)'             - SAP port is operationally down
         'addrOrIfNotReady (3)'         - Address or Parent interface is not
                                          ready
         'assocObjNotReady (4)'         - Associated object is not ready
         'rvplsDown (5)'                - R-VPLS service is down
         'operGrpDown (6)'              - Associated Operational Group is down
         'ifAdminDestroy (7)'           - Interface is being deleted
         'noIfAddress (8)'              - Interface address is not configured
         'noIfInfo (9)'                 - Interface info not present
         'delayedStartEnabled (10)'     - Delayed start timer is enabled on
                                          the interface
         'ifProtoOperDown (11)'         - Protocols on interface are
                                          operationally down
         'invalidPortCfg (12)'          - Port configuration is not valid
         'unknown (13)'                 - Reason is unknown
         'noRouteDistinguisher (14)'    - Route Distinguisher not configured in VPRN
         'wlanGwRedundancyStandby (15)' - Interface is in standby state for
                                          WLAN-GW redundancy
         'wlanGwGroupDegraded (16)'     - The associated WLAN-GW group is in a
                                          degraded state
         'ipControlTunnelOperDown (17)' - The IP tunnel associated to a control-tunnel
                                          interface is operationally down
         'pdnAddressMismatch (18)'      - The IP address learned from the packet data network
                                          does not match the configured primary IP address
         'pingCheckFailure (19)'        - The IP interface is or went down because of ping-template
                                          failure
         'portInternalLoopback (20)'    - The IP interface is bound to a port that has an
                                          internal loopback configured
         'noHwResForSrv6Loopback (21)'  - There are not enough resources for the SRv6 locator
                                          prefix loopback address
         'ipTunnelNotReady (22)'        - The IP tunnel associated to an
                                          ip-tunnel-interface is not ready"
    ::= { vRtrIfExtEntry 63 }

vRtrIfLdpEolib                   OBJECT-TYPE
    SYNTAX      TruthValue
    MAX-ACCESS  read-create
    STATUS      current
    DESCRIPTION
        "The value of vRtrIfLdpEolib specifies if end-of-lib LDP messages from
         a LDP peer are to be processed or not.

         If the value of vRtrIfLdpEolib is equal to 'true' and the value of the
         vRtrIfLdpSyncTimer object is not zero, the end-of-lib LDP messages are
         processed, the LDP sync timer (see the vRtrIfLdpSyncTimer object) is
         terminated and the IGP link cost is restored accordingly.

         If the value of the vRtrIfLdpSyncTimer object is zero, the value of
         this object is ignored."
    DEFVAL      { false }
    ::= { vRtrIfExtEntry 64 }

vRtrIfCreationOrigin             OBJECT-TYPE
    SYNTAX      TmnxCreateOrigin
    MAX-ACCESS  read-only
    STATUS      current
    DESCRIPTION
        "The value of vRtrIfCreationOrigin indicates the mechanism used to
         create this entry."
    DEFVAL      { manual }
    ::= { vRtrIfExtEntry 67 }

vRtrIfIcmpV4ParamProblem         OBJECT-TYPE
    SYNTAX      TruthValue
    MAX-ACCESS  read-create
    STATUS      current
    DESCRIPTION
        "The value of vRtrIfIcmpV4ParamProblem specifies whether
         parameter-problem ICMPv4 messages should be sent. When it is set to
         'true', ICMPv4 parameter-problem messages are generated by this
         interface. When vRtrIfIcmpV4ParamProblem is set to 'false', ICMPv4
         parameter-problem messages are not sent."
    DEFVAL      { true }
    ::= { vRtrIfExtEntry 68 }

vRtrIfIcmpV4NumParamProblem      OBJECT-TYPE
    SYNTAX      Unsigned32 (10..1000)
    MAX-ACCESS  read-create
    STATUS      current
    DESCRIPTION
        "The value of vRtrIfIcmpV4NumParamProblem specifies how many
         parameter-problem ICMPv4 messages are issued in the time frame
         specified by vRtrIfIcmpV4ParamProblemTime."
    DEFVAL      { 100 }
    ::= { vRtrIfExtEntry 69 }

vRtrIfIcmpV4ParamProblemTime     OBJECT-TYPE
    SYNTAX      Unsigned32 (1..60)
    UNITS       "seconds"
    MAX-ACCESS  read-create
    STATUS      current
    DESCRIPTION
        "The value of vRtrIfIcmpV4ParamProblemTime specifies the time frame in
         seconds that is used to limit the number of parameter-problem ICMPv4
         messages issued per time frame."
    DEFVAL      { 10 }
    ::= { vRtrIfExtEntry 70 }

vRtrIfOperDCpuProtPolicy         OBJECT-TYPE
    SYNTAX      TNamedItemOrEmpty
    MAX-ACCESS  read-only
    STATUS      current
    DESCRIPTION
        "The value of vRtrIfOperDCpuProtPolicy indicates the Operational
         Distributed CPU Protection Policy."
    ::= { vRtrIfExtEntry 71 }

vRtrIfUrpfSelectedVprnsOnly      OBJECT-TYPE
    SYNTAX      TruthValue
    MAX-ACCESS  read-create
    STATUS      current
    DESCRIPTION
        "The value of vRtrIfUrpfSelectedVprnsOnly enables selective uRPF
         checking.

         When the value of vRtrIfUrpfSelectedVprnsOnly is 'true', packets that
         are associated to a VPRN will be subjected to the uRPF treatment
         configured for this interface if the associated VPRN has
         'TIMETRA-SERV-MIB::svcNetIngUrpfCheckState' set to 'true'.

         The uRPF treatment for this interface is configured with the objects
         vRtrIfuRPFCheckState, vRtrIfuRPFCheckMode, vRtrIfuRPFIgnoreDefault for
         IPv4 packets, and vRtrIfIpv6uRPFCheckState, vRtrIfIpv6uRPFCheckMode,
         and vRtrIfIpv6uRPFIgnoreDefault for IPv6 packets.

         When the value of vRtrIfUrpfSelectedVprnsOnly is 'false', uRPF check
         configuration will be done for all packets associated with a VPRN,
         regardless of the value of 'TIMETRA-SERV-MIB::svcNetIngUrpfCheckState'
         and regardless of the uRPF configuration for this interface.

         The value of vRtrIfUrpfSelectedVprnsOnly does not affect uRPF checking
         on packets ingressing a VPRN directly through a SAP or SDP binding
         associated with a service interface; uRPF checking on those packets is
         controlled by the value of the object vRtrIfuRPFCheckState of the
         service interface.

         Setting the value of vRtrIfUrpfSelectedVprnsOnly to 'true' is only
         allowed if the value of the vRtrIfType object in the corresponding row
         in the vRtrIfTable is equal to 'network'."
    DEFVAL      { false }
    ::= { vRtrIfExtEntry 72 }

vRtrIfIpTunnelRemoteIpAddrType   OBJECT-TYPE
    SYNTAX      InetAddressType
    MAX-ACCESS  read-create
    STATUS      obsolete
    DESCRIPTION
        "The value of vRtrIfIpTunnelRemoteIpAddrType specifies the type of
         vRtrIfIpTunnelRemoteIpAddr."
    DEFVAL      { unknown }
    ::= { vRtrIfExtEntry 75 }

vRtrIfIpTunnelRemoteIpAddr       OBJECT-TYPE
    SYNTAX      InetAddress (SIZE (0|4|16))
    MAX-ACCESS  read-create
    STATUS      obsolete
    DESCRIPTION
        "The value of vRtrIfIpTunnelRemoteIpAddr specifies the IP address of
         the remote end of the IP tunnel associated with this interface (the
         source IP address in the tunneled IP datagram headers received by this
         system).

         A non empty value is only allowed if the value of the vRtrIfType
         object in the corresponding row in the vRtrIfTable is equal to
         'controlTunnel'."
    DEFVAL      { ''H }
    ::= { vRtrIfExtEntry 76 }

vRtrIfIpv4ArpLearnUnsol          OBJECT-TYPE
    SYNTAX      TruthValue
    MAX-ACCESS  read-create
    STATUS      current
    DESCRIPTION
        "The value of vRtrIfIpv4ArpLearnUnsol specifies whether unsolicited
         learning is enabled.

         When the value is set to 'true', unsolicited learning is enabled.

         When the value is set to 'false', unsolicited learning is disabled."
    DEFVAL      { false }
    ::= { vRtrIfExtEntry 78 }

vRtrIfIpv4ArpProRef              OBJECT-TYPE
    SYNTAX      TruthValue
    MAX-ACCESS  read-create
    STATUS      current
    DESCRIPTION
        "The value of vRtrIfIpv4ArpProRef specifies whether proactive refresh
         is enabled.

         When the value is set to 'true', proactive refresh is enabled.

         When the value is set to 'false', proactive refresh is disabled."
    DEFVAL      { false }
    ::= { vRtrIfExtEntry 79 }

vRtrIfIpv6NdLearnUnsol           OBJECT-TYPE
    SYNTAX      INTEGER {
        none      (0),
        global    (1),
        linkLocal (2),
        both      (3)
    }
    MAX-ACCESS  read-create
    STATUS      current
    DESCRIPTION
        "The value of vRtrIfIpv6NdLearnUnsol specifies whether unsolicited
         learning is enabled.

         When the value is set to 'global', proactive refresh is global.

         When the value is set to 'linkLocal', proactive refresh is link local."
    DEFVAL      { none }
    ::= { vRtrIfExtEntry 80 }

vRtrIfIpv6NdProRef               OBJECT-TYPE
    SYNTAX      INTEGER {
        none      (0),
        global    (1),
        linkLocal (2),
        both      (3)
    }
    MAX-ACCESS  read-create
    STATUS      current
    DESCRIPTION
        "The value of vRtrIfIpv6NdProRef specifies whether proactive refresh is
         enabled.

         When the value is set to 'global', proactive refresh is global.

         When the value is set to 'linkLocal', proactive refresh is link local."
    DEFVAL      { none }
    ::= { vRtrIfExtEntry 81 }

vRtrIfIpv6FlowLabelHashing       OBJECT-TYPE
    SYNTAX      TruthValue
    MAX-ACCESS  read-create
    STATUS      current
    DESCRIPTION
        "The value of vRtrIfIpv6FlowLabelHashing specifies whether flow-label
         load balancing is enabled for the configured IES/VPRN/router
         interfaces."
    DEFVAL      { false }
    ::= { vRtrIfExtEntry 82 }

vRtrIfIngressIPFilterPair        OBJECT-TYPE
    SYNTAX      TruthValue
    MAX-ACCESS  read-create
    STATUS      current
    DESCRIPTION
        "The value of the object vRtrIfIngressIPFilterPair specifies if ip
         filter pair has been enabled or disabled on this network interface."
    DEFVAL      { false }
    ::= { vRtrIfExtEntry 83 }

vRtrRsvpTunIfTableLastChanged    OBJECT-TYPE
    SYNTAX      TimeStamp
    MAX-ACCESS  read-only
    STATUS      current
    DESCRIPTION
        "The value of vRtrRsvpTunIfTableLastChanged indicates the sysUpTime at
         the time of the last modification to vRtrRsvpTunIfEntryTable by
         adding, deleting an entry or change to a writable object in the table."
    ::= { tmnxVRtrObjs 62 }

vRtrRsvpTunIfEntryTable          OBJECT-TYPE
    SYNTAX      SEQUENCE OF VRtrRsvpTunIfEntry
    MAX-ACCESS  not-accessible
    STATUS      current
    DESCRIPTION
        "The vRtrRsvpTunIfEntryTable has an entry for each P2MP RSVP tunnel
         interface configured in the system."
    ::= { tmnxVRtrObjs 63 }

vRtrRsvpTunIfEntry               OBJECT-TYPE
    SYNTAX      VRtrRsvpTunIfEntry
    MAX-ACCESS  not-accessible
    STATUS      current
    DESCRIPTION
        "Each row entry in the vRtrRsvpTunIfEntryTable represents a P2MP RSVP
         tunnel interface on this router. Entries can be created and deleted
         via SNMP SET operations using the vRtrRsvpTunIfRowStatus variable."
    INDEX       {
        vRtrID,
        vRtrRsvpTunIfLspName,
        vRtrRsvpTunIfSenderAddrType,
        vRtrRsvpTunIfSenderAddr
    }
    ::= { vRtrRsvpTunIfEntryTable 1 }

VRtrRsvpTunIfEntry               ::= SEQUENCE
{
    vRtrRsvpTunIfLspName             TNamedItem,
    vRtrRsvpTunIfSenderAddrType      InetAddressType,
    vRtrRsvpTunIfSenderAddr          InetAddress,
    vRtrRsvpTunIfRowStatus           RowStatus,
    vRtrRsvpTunIfLastChanged         TimeStamp,
    vRtrRsvpTunIfSessionId           Unsigned32,
    vRtrRsvpTunIfTransmitInt         Unsigned32,
    vRtrRsvpTunIfMultiplier          Unsigned32,
    vRtrRsvpTunIfStandbyLspName      TNamedItemOrEmpty,
    vRtrRsvpTunIfStandbyAddrType     InetAddressType,
    vRtrRsvpTunIfStandbyAddr         InetAddress,
    vRtrRsvpTunIfIfIndex             InterfaceIndex,
    vRtrRsvpTunIfHoldTimer           Unsigned32,
    vRtrRsvpTunIfStandbySessionId    Unsigned32,
    vRtrRsvpTunIfStandbyIfIndex      InterfaceIndexOrZero,
    vRtrRsvpTunIfDescription         TItemDescription
}

vRtrRsvpTunIfLspName             OBJECT-TYPE
    SYNTAX      TNamedItem
    MAX-ACCESS  not-accessible
    STATUS      current
    DESCRIPTION
        "The value of vRtrRsvpTunIfLspName indicates the LSP name of the P2MP
         RSVP tunnel interface."
    ::= { vRtrRsvpTunIfEntry 1 }

vRtrRsvpTunIfSenderAddrType      OBJECT-TYPE
    SYNTAX      InetAddressType
    MAX-ACCESS  not-accessible
    STATUS      current
    DESCRIPTION
        "The value of vRtrRsvpTunIfSenderAddrType indicates the type of address
         of an RSVP sender for the P2MP RSVP tunnel interface instance."
    ::= { vRtrRsvpTunIfEntry 2 }

vRtrRsvpTunIfSenderAddr          OBJECT-TYPE
    SYNTAX      InetAddress (SIZE (4|16))
    MAX-ACCESS  not-accessible
    STATUS      current
    DESCRIPTION
        "The value of vRtrRsvpTunIfSenderAddr indicates the address of an RSVP
         sender for the P2MP RSVP tunnel interface instance."
    ::= { vRtrRsvpTunIfEntry 3 }

vRtrRsvpTunIfRowStatus           OBJECT-TYPE
    SYNTAX      RowStatus
    MAX-ACCESS  read-create
    STATUS      current
    DESCRIPTION
        "The value of vRtrRsvpTunIfRowStatus specifies the Row status of this
         table row. This object is used to create or delete rows in this table."
    ::= { vRtrRsvpTunIfEntry 4 }

vRtrRsvpTunIfLastChanged         OBJECT-TYPE
    SYNTAX      TimeStamp
    MAX-ACCESS  read-only
    STATUS      current
    DESCRIPTION
        "The value of vRtrRsvpTunIfLastChanged  indicates the timestamp of
         the last change to this row in vRtrRsvpTunIfEntryTable."
    ::= { vRtrRsvpTunIfEntry 5 }

vRtrRsvpTunIfSessionId           OBJECT-TYPE
    SYNTAX      Unsigned32 (0 | 1..4000)
    MAX-ACCESS  read-create
    STATUS      current
    DESCRIPTION
        "The value of vRtrRsvpTunIfSessionId specifies the discriminator for a
         BFD session for this P2MP RSVP tunnel interface. When
         vRtrRsvpTunIfSessionId has a value of 0, the BFD session is not
         operational. This identifier needs to be unique within a tunnel
         interface."
    DEFVAL      { 0 }
    ::= { vRtrRsvpTunIfEntry 6 }

vRtrRsvpTunIfTransmitInt         OBJECT-TYPE
    SYNTAX      Unsigned32 (0 | 100..100000)
    UNITS       "milliseconds"
    MAX-ACCESS  read-create
    STATUS      current
    DESCRIPTION
        "The value of vRtrRsvpTunIfTransmitInt specifies the transmit interval
         for a BFD session for this P2MP RSVP tunnel interface. When
         vRtrRsvpTunIfTransmitInt has a value of 0, the transmit interval is
         not applicable."
    DEFVAL      { 100 }
    ::= { vRtrRsvpTunIfEntry 7 }

vRtrRsvpTunIfMultiplier          OBJECT-TYPE
    SYNTAX      Unsigned32 (0 | 3..20)
    MAX-ACCESS  read-create
    STATUS      current
    DESCRIPTION
        "The value of vRtrRsvpTunIfMultiplier specifies the multiplier to
         detect if a BFD session is down for this P2MP RSVP tunnel interface.
         When vRtrRsvpTunIfMultiplier has a value of 0, the multiplier is not
         applicable."
    DEFVAL      { 3 }
    ::= { vRtrRsvpTunIfEntry 8 }

vRtrRsvpTunIfStandbyLspName      OBJECT-TYPE
    SYNTAX      TNamedItemOrEmpty
    MAX-ACCESS  read-create
    STATUS      current
    DESCRIPTION
        "The value of vRtrRsvpTunIfStandbyLspName specifies the LSP name of the
         standby P2MP RSVP tunnel interface."
    DEFVAL      { ''H }
    ::= { vRtrRsvpTunIfEntry 9 }

vRtrRsvpTunIfStandbyAddrType     OBJECT-TYPE
    SYNTAX      InetAddressType
    MAX-ACCESS  read-create
    STATUS      current
    DESCRIPTION
        "The value of vRtrRsvpTunIfStandbyAddrType specifies the address type
         of the standby P2MP RSVP tunnel interface."
    DEFVAL      { ipv4 }
    ::= { vRtrRsvpTunIfEntry 10 }

vRtrRsvpTunIfStandbyAddr         OBJECT-TYPE
    SYNTAX      InetAddress (SIZE (4|16))
    MAX-ACCESS  read-create
    STATUS      current
    DESCRIPTION
        "The value of vRtrRsvpTunIfStandbyAddr specifies the standby address of
         the standby P2MP RSVP tunnel interface."
    DEFVAL      { '00000000'H }
    ::= { vRtrRsvpTunIfEntry 11 }

vRtrRsvpTunIfIfIndex             OBJECT-TYPE
    SYNTAX      InterfaceIndex
    MAX-ACCESS  read-only
    STATUS      current
    DESCRIPTION
        "The value of vRtrRsvpTunIfIfIndex indicates the tunnel interface index
         of the P2MP RSVP tunnel interface. It is a unique value among entries
         with the same value of vRtrID."
    ::= { vRtrRsvpTunIfEntry 12 }

vRtrRsvpTunIfHoldTimer           OBJECT-TYPE
    SYNTAX      Unsigned32 (1..30)
    UNITS       "seconds"
    MAX-ACCESS  read-create
    STATUS      current
    DESCRIPTION
        "The value of vRtrRsvpTunIfHoldTimer specifies the time interval that a
         leaf node waits after a BFD session over a primary P2MP RSVP tunnel
         interface is restored and before it programs multicast records to
         accept traffic from that primary tunnel interface."
    DEFVAL      { 10 }
    ::= { vRtrRsvpTunIfEntry 13 }

vRtrRsvpTunIfStandbySessionId    OBJECT-TYPE
    SYNTAX      Unsigned32 (0 | 1..4000)
    MAX-ACCESS  read-create
    STATUS      current
    DESCRIPTION
        "The value of vRtrRsvpTunIfStandbySessionId specifies the discriminator
         for a BFD session over the standby P2MP RSVP tunnel interface. When
         vRtrRsvpTunIfStandbySessionId has a value of 0, the BFD session is not
         operational. This identifier needs to be unique within a tunnel
         interface."
    DEFVAL      { 0 }
    ::= { vRtrRsvpTunIfEntry 14 }

vRtrRsvpTunIfStandbyIfIndex      OBJECT-TYPE
    SYNTAX      InterfaceIndexOrZero
    MAX-ACCESS  read-only
    STATUS      current
    DESCRIPTION
        "The value of vRtrRsvpTunIfStandbyIfIndex indicates the tunnel
         interface index of the standby P2MP RSVP tunnel interface."
    ::= { vRtrRsvpTunIfEntry 15 }

vRtrRsvpTunIfDescription         OBJECT-TYPE
    SYNTAX      TItemDescription
    MAX-ACCESS  read-create
    STATUS      current
    DESCRIPTION
        "The value of vRtrRsvpTunIfDescription specifies a user provided
         description string for this rsvp tunnel interface. It can consist of
         any printable, seven-bit ASCII characters up to 80 characters in
         length."
    DEFVAL      { ''H }
    ::= { vRtrRsvpTunIfEntry 16 }

vRtrRsvpTunIfSrcTableLastChanged OBJECT-TYPE
    SYNTAX      TimeStamp
    MAX-ACCESS  read-only
    STATUS      current
    DESCRIPTION
        "The value of vRtrRsvpTunIfSrcTableLastChanged indicates the sysUpTime
         at the time of the last modification to vRtrRsvpTunIfSrcEntryTable by
         adding, deleting an entry or change to a writable object in the table."
    ::= { tmnxVRtrObjs 64 }

vRtrRsvpTunIfSrcEntryTable       OBJECT-TYPE
    SYNTAX      SEQUENCE OF VRtrRsvpTunIfSrcEntry
    MAX-ACCESS  not-accessible
    STATUS      current
    DESCRIPTION
        "The vRtrRsvpTunIfSrcEntryTable  has an entry for each multicast source
         tracked by BFD over a P2MP RSVP tunnel interface."
    ::= { tmnxVRtrObjs 65 }

vRtrRsvpTunIfSrcEntry            OBJECT-TYPE
    SYNTAX      VRtrRsvpTunIfSrcEntry
    MAX-ACCESS  not-accessible
    STATUS      current
    DESCRIPTION
        "Each row entry represents a multicast source tracked by BFD over P2MP
         RSVP tunnel interface in the system. Entries can be created and
         deleted via SNMP SET operations using the vRtrRsvpTunIfSrcRowStatus
         variable."
    INDEX       {
        vRtrID,
        vRtrRsvpTunIfLspName,
        vRtrRsvpTunIfSenderAddrType,
        vRtrRsvpTunIfSenderAddr,
        vRtrRsvpTunIfSrcAddrType,
        vRtrRsvpTunIfSrcAddr
    }
    ::= { vRtrRsvpTunIfSrcEntryTable 1 }

VRtrRsvpTunIfSrcEntry            ::= SEQUENCE
{
    vRtrRsvpTunIfSrcAddrType         InetAddressType,
    vRtrRsvpTunIfSrcAddr             InetAddress,
    vRtrRsvpTunIfSrcRowStatus        RowStatus,
    vRtrRsvpTunIfSrcLastChanged      TimeStamp,
    vRtrRsvpTunIfSrcBfdEnable        TruthValue,
    vRtrRsvpTunIfSrcSessionId        Unsigned32,
    vRtrRsvpTunIfSrcTransmitInt      Unsigned32,
    vRtrRsvpTunIfSrcMultiplier       Unsigned32,
    vRtrRsvpTunIfSrcStandbySessionId Unsigned32
}

vRtrRsvpTunIfSrcAddrType         OBJECT-TYPE
    SYNTAX      InetAddressType
    MAX-ACCESS  not-accessible
    STATUS      current
    DESCRIPTION
        "The value of vRtrRsvpTunIfSrcAddrType indicates the type of address of
         a multicast source for the P2MP RSVP tunnel interface."
    ::= { vRtrRsvpTunIfSrcEntry 1 }

vRtrRsvpTunIfSrcAddr             OBJECT-TYPE
    SYNTAX      InetAddress (SIZE (4|16))
    MAX-ACCESS  not-accessible
    STATUS      current
    DESCRIPTION
        "The value of vRtrRsvpTunIfSrcAddr indicates the address of a multicast
         source for the P2MP RSVP tunnel interface."
    ::= { vRtrRsvpTunIfSrcEntry 2 }

vRtrRsvpTunIfSrcRowStatus        OBJECT-TYPE
    SYNTAX      RowStatus
    MAX-ACCESS  read-create
    STATUS      current
    DESCRIPTION
        "The value of vRtrRsvpTunIfSrcRowStatus specifies the Row status of
         this table row. This object is used to create or delete rows in this
         table."
    ::= { vRtrRsvpTunIfSrcEntry 3 }

vRtrRsvpTunIfSrcLastChanged      OBJECT-TYPE
    SYNTAX      TimeStamp
    MAX-ACCESS  read-only
    STATUS      current
    DESCRIPTION
        "The value of vRtrRsvpTunIfSrcLastChanged  indicates the timestamp of
         the last change to this row in vRtrRsvpTunIfSrcEntryTable."
    ::= { vRtrRsvpTunIfSrcEntry 4 }

vRtrRsvpTunIfSrcBfdEnable        OBJECT-TYPE
    SYNTAX      TruthValue
    MAX-ACCESS  read-create
    STATUS      current
    DESCRIPTION
        "The value of vRtrRsvpTunIfSrcBfdEnable specifies if the BFD session to
         track the multicast source over the P2MP RSVP tunnel interface is
         enabled or not."
    DEFVAL      { false }
    ::= { vRtrRsvpTunIfSrcEntry 5 }

vRtrRsvpTunIfSrcSessionId        OBJECT-TYPE
    SYNTAX      Unsigned32
    MAX-ACCESS  read-create
    STATUS      current
    DESCRIPTION
        "The value of vRtrRsvpTunIfSrcSessionId specifies the discriminator for
         a BFD session to track the multicast source over the P2MP RSVP tunnel
         interface. When vRtrRsvpTunIfSrcSessionId  has a value of 0, the BFD
         session is not operational. This Id needs to be unique within a tunnel
         interface."
    DEFVAL      { 0 }
    ::= { vRtrRsvpTunIfSrcEntry 6 }

vRtrRsvpTunIfSrcTransmitInt      OBJECT-TYPE
    SYNTAX      Unsigned32 (0 | 100..100000)
    UNITS       "milliseconds"
    MAX-ACCESS  read-create
    STATUS      current
    DESCRIPTION
        "The value of vRtrRsvpTunIfSrcTransmitInt specifies the transmit
         interval for a BFD session to track the multicast source over the P2MP
         RSVP tunnel interface. When vRtrRsvpTunIfSrcTransmitInt has a value of
         0, the transmit interval is not applicable."
    DEFVAL      { 100 }
    ::= { vRtrRsvpTunIfSrcEntry 7 }

vRtrRsvpTunIfSrcMultiplier       OBJECT-TYPE
    SYNTAX      Unsigned32 (0 | 3..20)
    MAX-ACCESS  read-create
    STATUS      current
    DESCRIPTION
        "The value of vRtrRsvpTunIfSrcMultiplier specifies the multiplier to
         detect if a BFD session to track the multicast source over the P2MP
         RSVP tunnel interface is down. When vRtrRsvpTunIfSrcMultiplier has a
         value of 0, the multiplier is not applicable."
    DEFVAL      { 3 }
    ::= { vRtrRsvpTunIfSrcEntry 8 }

vRtrRsvpTunIfSrcStandbySessionId OBJECT-TYPE
    SYNTAX      Unsigned32
    MAX-ACCESS  read-create
    STATUS      current
    DESCRIPTION
        "The value of vRtrRsvpTunIfSrcStandbySessionId specifies the
         discriminator for a BFD session to track the multicast source over the
         standby P2MP RSVP tunnel interface. When
         vRtrRsvpTunIfSrcStandbySessionId  has a value of 0, the BFD session is
         not operational. This Id needs to be unique within a tunnel interface."
    DEFVAL      { 0 }
    ::= { vRtrRsvpTunIfSrcEntry 9 }

vRtrLdpTunIfTableLastChanged     OBJECT-TYPE
    SYNTAX      TimeStamp
    MAX-ACCESS  read-only
    STATUS      current
    DESCRIPTION
        "The value of vRtrLdpTunIfTableLastChanged indicates the sysUpTime at
         the time of the last modification to vRtrLdpTunIfEntryTable by adding,
         deleting an entry or change to a writable object in the table."
    ::= { tmnxVRtrObjs 66 }

vRtrLdpTunIfEntryTable           OBJECT-TYPE
    SYNTAX      SEQUENCE OF VRtrLdpTunIfEntry
    MAX-ACCESS  not-accessible
    STATUS      current
    DESCRIPTION
        "The vRtrLdpTunIfEntryTable has an entry for each Ldp tunnel configured
         in the system. Each row entry represents a virtual router LDP tunnel
         interface in the system."
    ::= { tmnxVRtrObjs 67 }

vRtrLdpTunIfEntry                OBJECT-TYPE
    SYNTAX      VRtrLdpTunIfEntry
    MAX-ACCESS  not-accessible
    STATUS      current
    DESCRIPTION
        "Each row entry represents an Ldp tunnel interface in the system.
         Entries can be created and deleted via SNMP SET operations using the
         vRtrLdpTunIfRowStatus variable."
    INDEX       {
        vRtrID,
        vRtrLdpTunIfP2mpId,
        vRtrLdpTunIfSenderAddrType,
        vRtrLdpTunIfSenderAddr
    }
    ::= { vRtrLdpTunIfEntryTable 1 }

VRtrLdpTunIfEntry                ::= SEQUENCE
{
    vRtrLdpTunIfP2mpId               Unsigned32,
    vRtrLdpTunIfSenderAddrType       InetAddressType,
    vRtrLdpTunIfSenderAddr           InetAddress,
    vRtrLdpTunIfRowStatus            RowStatus,
    vRtrLdpTunIfLastChanged          TimeStamp,
    vRtrLdpTunIfIfIndex              InterfaceIndex,
    vRtrLdpTunIfDescription          TItemDescription,
    vRtrLdpTunIfRootNode             TruthValue
}

vRtrLdpTunIfP2mpId               OBJECT-TYPE
    SYNTAX      Unsigned32
    MAX-ACCESS  not-accessible
    STATUS      current
    DESCRIPTION
        "The value of vRtrLdpTunIfP2mpId indicates the LDP P2MP identifier."
    ::= { vRtrLdpTunIfEntry 1 }

vRtrLdpTunIfSenderAddrType       OBJECT-TYPE
    SYNTAX      InetAddressType
    MAX-ACCESS  not-accessible
    STATUS      current
    DESCRIPTION
        "The value of vRtrLdpTunIfSenderAddrType indicates the type of address
         of an LDP sender for the P2MP RSVP tunnel interface instance."
    ::= { vRtrLdpTunIfEntry 2 }

vRtrLdpTunIfSenderAddr           OBJECT-TYPE
    SYNTAX      InetAddress (SIZE (4|16))
    MAX-ACCESS  not-accessible
    STATUS      current
    DESCRIPTION
        "The value of vRtrLdpTunIfSenderAddr indicates the address of an LDP
         sender for the P2MP RSVP tunnel interface instance."
    ::= { vRtrLdpTunIfEntry 3 }

vRtrLdpTunIfRowStatus            OBJECT-TYPE
    SYNTAX      RowStatus
    MAX-ACCESS  read-create
    STATUS      current
    DESCRIPTION
        "The value of the object vRtrLdpTunIfRowStatus specifies the Row status
         of this table row. This object is used to create or delete rows in
         this table.

         The value of the object 'vRtrLdpTunIfRootNode' specifies if the given
         ldp-p2mp tunnel interface instance is a root node for that tunnel
         interface.The value of this object must be specified when the row is
         created and cannot be changed while 'vRtrLdpTunIfRowStatus' is
         'active'."
    ::= { vRtrLdpTunIfEntry 4 }

vRtrLdpTunIfLastChanged          OBJECT-TYPE
    SYNTAX      TimeStamp
    MAX-ACCESS  read-only
    STATUS      current
    DESCRIPTION
        "The value of vRtrLdpTunIfLastChanged  indicates the timestamp of
         the last change to this row in vRtrLdpTunIfEntryTable."
    ::= { vRtrLdpTunIfEntry 5 }

vRtrLdpTunIfIfIndex              OBJECT-TYPE
    SYNTAX      InterfaceIndex
    MAX-ACCESS  read-only
    STATUS      current
    DESCRIPTION
        "The value of vRtrLdpTunIfIfIndex indicates the interface index of the
         virtual router LDP tunnel interface. It is a unique value among
         entries with the same value of vRtrID."
    ::= { vRtrLdpTunIfEntry 6 }

vRtrLdpTunIfDescription          OBJECT-TYPE
    SYNTAX      TItemDescription
    MAX-ACCESS  read-create
    STATUS      current
    DESCRIPTION
        "The value of vRtrLdpTunIfDescription specifies a user provided
         description string for this ldp tunnel interface. It can consist of
         any printable, seven-bit ASCII characters up to 80 characters in
         length."
    DEFVAL      { ''H }
    ::= { vRtrLdpTunIfEntry 7 }

vRtrLdpTunIfRootNode             OBJECT-TYPE
    SYNTAX      TruthValue
    MAX-ACCESS  read-create
    STATUS      current
    DESCRIPTION
        "The value of vRtrLdpTunIfRootNode specifies if the given ldp-p2mp
         tunnel interface instance is a root node for that tunnel interface.
         The value of this object must be specified when the row is created and
         cannot be changed while 'vRtrLdpTunIfRowStatus' is 'active'. An
         'inconsistentValue' error is returned if an attempt is made to set
         this object individually."
    ::= { vRtrLdpTunIfEntry 8 }

vRtrInetCidrRteTnlExtTable       OBJECT-TYPE
    SYNTAX      SEQUENCE OF VRtrInetCidrRteTnlExtEntry
    MAX-ACCESS  not-accessible
    STATUS      current
    DESCRIPTION
        "The vRtrInetCidrRteTnlExtTable provides an extension of the
         inetCidrRouteTable in the IP-FORWARD-MIB, by adding three indexes and
         displays only tunneled routes."
    ::= { tmnxVRtrObjs 68 }

vRtrInetCidrRteTnlExtEntry       OBJECT-TYPE
    SYNTAX      VRtrInetCidrRteTnlExtEntry
    MAX-ACCESS  not-accessible
    STATUS      current
    DESCRIPTION
        "Each row entry in the vRtrInetCidrRteTnlExtTable represents an entry
         for a tunneled route on the Nokia SROS series."
    INDEX       {
        inetCidrRouteDestType,
        inetCidrRouteDest,
        inetCidrRoutePfxLen,
        inetCidrRoutePolicy,
        inetCidrRouteNextHopType,
        inetCidrRouteNextHop,
        vRtrInetCidrRteTnlNextHopType,
        vRtrInetCidrRteTnlNextHopOwner,
        vRtrInetCidrRteTnlNextHopTnlId
    }
    ::= { vRtrInetCidrRteTnlExtTable 1 }

VRtrInetCidrRteTnlExtEntry       ::= SEQUENCE
{
    vRtrInetCidrRteTnlNextHopType    TmnxInetCidrNextHopType,
    vRtrInetCidrRteTnlNextHopOwner   TmnxInetCidrNextHopOwner,
    vRtrInetCidrRteTnlNextHopTnlId   Unsigned32,
    vRtrInetCidrRteTnlEnabledTime    TimeStamp,
    vRtrInetCidrRteTnlNextHopWeight  Unsigned32
}

vRtrInetCidrRteTnlNextHopType    OBJECT-TYPE
    SYNTAX      TmnxInetCidrNextHopType
    MAX-ACCESS  not-accessible
    STATUS      current
    DESCRIPTION
        "The value of vRtrInetCidrRteTnlNextHopType indicates the type of next
         hop for this route."
    ::= { vRtrInetCidrRteTnlExtEntry 1 }

vRtrInetCidrRteTnlNextHopOwner   OBJECT-TYPE
    SYNTAX      TmnxInetCidrNextHopOwner
    MAX-ACCESS  not-accessible
    STATUS      current
    DESCRIPTION
        "The value of vRtrInetCidrRteTnlNextHopOwner indicates the owner of
         next hop for this route."
    ::= { vRtrInetCidrRteTnlExtEntry 2 }

vRtrInetCidrRteTnlNextHopTnlId   OBJECT-TYPE
    SYNTAX      Unsigned32
    MAX-ACCESS  not-accessible
    STATUS      current
    DESCRIPTION
        "Additional table index provided to distinguish between multiple RSVP
         tunnel ids to same destination with the same
         vRtrInetCidrRteTnlNextHopType and vRtrInetCidrRteTnlNextHopOwner."
    ::= { vRtrInetCidrRteTnlExtEntry 3 }

vRtrInetCidrRteTnlEnabledTime    OBJECT-TYPE
    SYNTAX      TimeStamp
    MAX-ACCESS  read-only
    STATUS      current
    DESCRIPTION
        "The vRtrInetCidrRteTnlEnabledTime variable indicates the sysUpTime
         value for this route entry."
    ::= { vRtrInetCidrRteTnlExtEntry 4 }

vRtrInetCidrRteTnlNextHopWeight  OBJECT-TYPE
    SYNTAX      Unsigned32
    MAX-ACCESS  read-only
    STATUS      current
    DESCRIPTION
        "The value of vRtrInetCidrRteTnlNextHopWeight indicates the weight
         given to traffic this particular next-hop among the ECMP set of
         next-hops."
    ::= { vRtrInetCidrRteTnlExtEntry 5 }

tmnxVRtrMobGatewayObjs           OBJECT IDENTIFIER ::= { tmnxVRtrObjs 69 }

vRtrIpPoolTableLastChanged       OBJECT-TYPE
    SYNTAX      TimeStamp
    MAX-ACCESS  read-only
    STATUS      current
    DESCRIPTION
        "The value of vRtrIpPoolTableLastChanged indicates the sysUpTime at the
         time of the last modification to vRtrIpPoolTable by adding, deleting
         an entry or change to a writable object in the table."
    ::= { tmnxVRtrMobGatewayObjs 1 }

vRtrIpPoolTable                  OBJECT-TYPE
    SYNTAX      SEQUENCE OF VRtrIpPoolEntry
    MAX-ACCESS  not-accessible
    STATUS      current
    DESCRIPTION
        "The vRtrIpPoolTable has an entry for each IP address pool configured
         in the system."
    ::= { tmnxVRtrMobGatewayObjs 2 }

vRtrIpPoolEntry                  OBJECT-TYPE
    SYNTAX      VRtrIpPoolEntry
    MAX-ACCESS  not-accessible
    STATUS      current
    DESCRIPTION
        "Each row entry represents an IP address pool configured in the system.
         Entries can be created and deleted by the user."
    INDEX       {
        vRtrID,
        vRtrIpPoolName
    }
    ::= { vRtrIpPoolTable 1 }

VRtrIpPoolEntry                  ::= SEQUENCE
{
    vRtrIpPoolName                   TNamedItem,
    vRtrIpPoolRowStatus              RowStatus,
    vRtrIpPoolLastChanged            TimeStamp,
    vRtrIpPoolDescription            TItemDescription,
    vRtrIpPoolExclusive              TruthValue,
    vRtrIpPoolAddressHoldTimer       Unsigned32,
    vRtrIpPoolSuppress0and255        TruthValue,
    vRtrIpPoolIsRemote               TruthValue
}

vRtrIpPoolName                   OBJECT-TYPE
    SYNTAX      TNamedItem
    MAX-ACCESS  not-accessible
    STATUS      current
    DESCRIPTION
        "The value of vRtrIpPoolName specifies the name of this IP address
         pool."
    ::= { vRtrIpPoolEntry 1 }

vRtrIpPoolRowStatus              OBJECT-TYPE
    SYNTAX      RowStatus
    MAX-ACCESS  read-create
    STATUS      current
    DESCRIPTION
        "The value of the object vRtrIpPoolRowStatus specifies the row status
         of this entry. This object is used to create or delete rows in this
         table."
    ::= { vRtrIpPoolEntry 2 }

vRtrIpPoolLastChanged            OBJECT-TYPE
    SYNTAX      TimeStamp
    MAX-ACCESS  read-only
    STATUS      current
    DESCRIPTION
        "The value of vRtrIpPoolLastChanged  indicates the timestamp of
         the last change to this row in vRtrIpPoolTable."
    ::= { vRtrIpPoolEntry 3 }

vRtrIpPoolDescription            OBJECT-TYPE
    SYNTAX      TItemDescription
    MAX-ACCESS  read-create
    STATUS      current
    DESCRIPTION
        "The value of vRtrIpPoolDescription specifies the description string
         for this IP address pool. It can consist of any printable, seven-bit
         ASCII characters up to 80 characters in length."
    DEFVAL      { ''H }
    ::= { vRtrIpPoolEntry 4 }

vRtrIpPoolExclusive              OBJECT-TYPE
    SYNTAX      TruthValue
    MAX-ACCESS  read-create
    STATUS      current
    DESCRIPTION
        "The value of the object vRtrIpPoolExclusive specifies if this IP
         address pool will be used exclusively by an Access Point Name (APN) or
         not."
    DEFVAL      { false }
    ::= { vRtrIpPoolEntry 5 }

vRtrIpPoolAddressHoldTimer       OBJECT-TYPE
    SYNTAX      Unsigned32 (0..10)
    UNITS       "minutes"
    MAX-ACCESS  read-create
    STATUS      current
    DESCRIPTION
        "The value of the object vRtrIpPoolAddressHoldTimer specifies the
         amount of time, in minutes, a newly released IP address is held before
         being made available for reassignment."
    DEFVAL      { 3 }
    ::= { vRtrIpPoolEntry 6 }

vRtrIpPoolSuppress0and255        OBJECT-TYPE
    SYNTAX      TruthValue
    MAX-ACCESS  read-create
    STATUS      current
    DESCRIPTION
        "The value of the object vRtrIpPoolSuppress0and255 specifies if
         allocation of all .0 and .255 IP addresses from the local IP pool to
         mobile subscribers are suppressed.

         By default the Packet Data Network Gateway (PGW) supports allocating
         .0 and .255 IP address to mobile subscribers except for the first .0
         and last .255 IP address in the IP Pool."
    DEFVAL      { false }
    ::= { vRtrIpPoolEntry 7 }

vRtrIpPoolIsRemote               OBJECT-TYPE
    SYNTAX      TruthValue
    MAX-ACCESS  read-create
    STATUS      current
    DESCRIPTION
        "The value of the object vRtrIpPoolIsRemote specifies if the IP
         addresses in the remote IP pool on the Packet Data Network Gateway
         (PGW) is managed by the remote server."
    DEFVAL      { false }
    ::= { vRtrIpPoolEntry 8 }

vRtrIpPoolAddrTableLastChanged   OBJECT-TYPE
    SYNTAX      TimeStamp
    MAX-ACCESS  read-only
    STATUS      current
    DESCRIPTION
        "The value of vRtrIpPoolAddrTableLastChanged indicates the sysUpTime at
         the time of the last modification to vRtrIpPoolAddrTable by adding,
         deleting an entry or change to a writable object in the table."
    ::= { tmnxVRtrMobGatewayObjs 3 }

vRtrIpPoolAddrTable              OBJECT-TYPE
    SYNTAX      SEQUENCE OF VRtrIpPoolAddrEntry
    MAX-ACCESS  not-accessible
    STATUS      current
    DESCRIPTION
        "The vRtrIpPoolAddrTable has an entry for each IP prefix configured in
         an IP pool in the system."
    ::= { tmnxVRtrMobGatewayObjs 4 }

vRtrIpPoolAddrEntry              OBJECT-TYPE
    SYNTAX      VRtrIpPoolAddrEntry
    MAX-ACCESS  not-accessible
    STATUS      current
    DESCRIPTION
        "Each row entry represents an IP prefix configured in an IP pool in the
         system. Entries can be created and deleted by the user."
    INDEX       {
        vRtrID,
        vRtrIpPoolName,
        vRtrIpPoolAddrType,
        vRtrIpPoolAddr,
        vRtrIpPoolAddrPrefixLen
    }
    ::= { vRtrIpPoolAddrTable 1 }

VRtrIpPoolAddrEntry              ::= SEQUENCE
{
    vRtrIpPoolAddrType               InetAddressType,
    vRtrIpPoolAddr                   InetAddress,
    vRtrIpPoolAddrPrefixLen          InetAddressPrefixLength,
    vRtrIpPoolAddrRowStatus          RowStatus,
    vRtrIpPoolAddrLastChanged        TimeStamp,
    vRtrIpPoolAddrBlock              TruthValue,
    vRtrIpPoolAddrIpv6AssignedLen    Unsigned32
}

vRtrIpPoolAddrType               OBJECT-TYPE
    SYNTAX      InetAddressType
    MAX-ACCESS  not-accessible
    STATUS      current
    DESCRIPTION
        "The value of vRtrIpPoolAddrType specifies the type of the address
         represented by vRtrIpPoolAddr."
    ::= { vRtrIpPoolAddrEntry 1 }

vRtrIpPoolAddr                   OBJECT-TYPE
    SYNTAX      InetAddress (SIZE (4|16))
    MAX-ACCESS  not-accessible
    STATUS      current
    DESCRIPTION
        "The value of vRtrIpPoolAddr specifies the prefix of the IP address
         being added to the IP pool."
    ::= { vRtrIpPoolAddrEntry 2 }

vRtrIpPoolAddrPrefixLen          OBJECT-TYPE
    SYNTAX      InetAddressPrefixLength
    MAX-ACCESS  not-accessible
    STATUS      current
    DESCRIPTION
        "The value of vRtrIpPoolAddrPrefixLen specifies the length of the IP
         netmask for this IP address.

         The range of this object is 9..32 if the value of vRtrIpPoolAddrType
         is set to 'ipv4'.

         The range of this object is as follows if the value of
         vRtrIpPoolAddrType is set to 'ipv6'.
         - The range of vRtrIpPoolAddrPrefixLen is 41..56, if the value of
           vRtrIpPoolAddrIpv6AssignedLen is set to 64.
         - The range of vRtrIpPoolAddrPrefixLen is 33..48, if the value of
           vRtrIpPoolAddrIpv6AssignedLen is set to 56.
         - The range of vRtrIpPoolAddrPrefixLen is 25..40, if the value of
           vRtrIpPoolAddrIpv6AssignedLen is set to 48."
    ::= { vRtrIpPoolAddrEntry 3 }

vRtrIpPoolAddrRowStatus          OBJECT-TYPE
    SYNTAX      RowStatus
    MAX-ACCESS  read-create
    STATUS      current
    DESCRIPTION
        "The value of the object vRtrIpPoolAddrRowStatus specifies the row
         status of this entry. This object is used to create or delete rows in
         this table."
    ::= { vRtrIpPoolAddrEntry 4 }

vRtrIpPoolAddrLastChanged        OBJECT-TYPE
    SYNTAX      TimeStamp
    MAX-ACCESS  read-only
    STATUS      current
    DESCRIPTION
        "The value of vRtrIpPoolAddrLastChanged  indicates the timestamp of
         the last change to this row in vRtrIpPoolAddrTable."
    ::= { vRtrIpPoolAddrEntry 5 }

vRtrIpPoolAddrBlock              OBJECT-TYPE
    SYNTAX      TruthValue
    MAX-ACCESS  read-create
    STATUS      current
    DESCRIPTION
        "The value of the object vRtrIpPoolAddrBlock specifies if the
         reassignment of the released IP address will be allowed or not. If the
         value of this object is set to 'true', then the reassignment of the
         released IP address will be blocked.

         This will be used to move the block of IP pools from one Packet Data
         Network Gateway (PGW) to another PGW. "
    DEFVAL      { false }
    ::= { vRtrIpPoolAddrEntry 6 }

vRtrIpPoolAddrIpv6AssignedLen    OBJECT-TYPE
    SYNTAX      Unsigned32 (48..64)
    MAX-ACCESS  read-create
    STATUS      current
    DESCRIPTION
        "The value of the object vRtrIpPoolAddrIpv6AssignedLen specifies the
         the prefix length which is used for assigning IP address to User
         Equipment (UE).

         The value of this object can be set only if the value of
         vRtrIpPoolAddrType is set to 'ipv6'.

         The value of this object can be set to 48, 56 and 64."
    DEFVAL      { 64 }
    ::= { vRtrIpPoolAddrEntry 7 }

vRtrIpPoolStatTable              OBJECT-TYPE
    SYNTAX      SEQUENCE OF VRtrIpPoolStatEntry
    MAX-ACCESS  not-accessible
    STATUS      current
    DESCRIPTION
        "The vRtrIpPoolStatTable has an entry for each IP prefix configured in
         an IP pool in the system."
    ::= { tmnxVRtrMobGatewayObjs 5 }

vRtrIpPoolStatEntry              OBJECT-TYPE
    SYNTAX      VRtrIpPoolStatEntry
    MAX-ACCESS  not-accessible
    STATUS      current
    DESCRIPTION
        "Each row entry represents the statistics for an IP prefix configured
         in an IP pool in the system."
    AUGMENTS    { vRtrIpPoolAddrEntry }
    ::= { vRtrIpPoolStatTable 1 }

VRtrIpPoolStatEntry              ::= SEQUENCE
{
    vRtrIpPoolStatAllocated          Gauge32,
    vRtrIpPoolStatFree               Gauge32,
    vRtrIpPoolStatHeld               Gauge32
}

vRtrIpPoolStatAllocated          OBJECT-TYPE
    SYNTAX      Gauge32
    MAX-ACCESS  read-only
    STATUS      current
    DESCRIPTION
        "The value of the object vRtrIpPoolStatAllocated indicates the number
         of IP Addresses used."
    ::= { vRtrIpPoolStatEntry 1 }

vRtrIpPoolStatFree               OBJECT-TYPE
    SYNTAX      Gauge32
    MAX-ACCESS  read-only
    STATUS      current
    DESCRIPTION
        "The value of the object vRtrIpPoolStatFree indicates the number of
         free IP Addresses."
    ::= { vRtrIpPoolStatEntry 2 }

vRtrIpPoolStatHeld               OBJECT-TYPE
    SYNTAX      Gauge32
    MAX-ACCESS  read-only
    STATUS      current
    DESCRIPTION
        "The value of the object vRtrIpPoolStatHeld indicates the number of IP
         Addresses held."
    ::= { vRtrIpPoolStatEntry 3 }

vRtrConfMobGwTableLastChanged    OBJECT-TYPE
    SYNTAX      TimeStamp
    MAX-ACCESS  read-only
    STATUS      current
    DESCRIPTION
        "The value of vRtrConfMobGwTableLastChanged indicates the sysUpTime
         at the time of the last modification to  vRtrConfMobGwTable by
         adding, deleting an entry or change to a writable object in the table."
    ::= { tmnxVRtrMobGatewayObjs 6 }

vRtrConfMobGwTable               OBJECT IDENTIFIER ::= { tmnxVRtrMobGatewayObjs 7 }

vRtrIfBfdExtTableLastChanged     OBJECT-TYPE
    SYNTAX      TimeStamp
    MAX-ACCESS  read-only
    STATUS      current
    DESCRIPTION
        "The value of vRtrIfBfdExtTableLastChanged indicates the sysUpTime at
         the time of the last modification to vRtrIfBfdExtTable by adding,
         deleting an entry or change to a writable object in the table."
    ::= { tmnxVRtrObjs 70 }

vRtrIfBfdExtTable                OBJECT-TYPE
    SYNTAX      SEQUENCE OF VRtrIfBfdExtEntry
    MAX-ACCESS  not-accessible
    STATUS      current
    DESCRIPTION
        "The vRtrIfBfdExtTable table contains the configuration for
         Bi-directional Forwarding Detection (BFD) on the vRtrIfIndex."
    ::= { tmnxVRtrObjs 71 }

vRtrIfBfdExtEntry                OBJECT-TYPE
    SYNTAX      VRtrIfBfdExtEntry
    MAX-ACCESS  not-accessible
    STATUS      current
    DESCRIPTION
        "Each row entry represents the BFD configuration for the vRtrIfIndex."
    INDEX       {
        vRtrID,
        vRtrIfIndex,
        vRtrIfBfdExtAddressType
    }
    ::= { vRtrIfBfdExtTable 1 }

VRtrIfBfdExtEntry                ::= SEQUENCE
{
    vRtrIfBfdExtAddressType          InetAddressType,
    vRtrIfBfdExtAdminState           TmnxAdminState,
    vRtrIfBfdExtTransmitInterval     Unsigned32,
    vRtrIfBfdExtReceiveInterval      Unsigned32,
    vRtrIfBfdExtMultiplier           Unsigned32,
    vRtrIfBfdExtEchoInterval         Unsigned32,
    vRtrIfBfdExtType                 INTEGER
}

vRtrIfBfdExtAddressType          OBJECT-TYPE
    SYNTAX      InetAddressType
    MAX-ACCESS  not-accessible
    STATUS      current
    DESCRIPTION
        "The value of vRtrIfBfdExtAddressType indicates the IP address type of
         the BFD configuration of this interface.

         vRtrIfBfdExtAddressType supports only InetAddressType values 'ipv4
         (1)' and 'ipv6 (2)'."
    ::= { vRtrIfBfdExtEntry 1 }

vRtrIfBfdExtAdminState           OBJECT-TYPE
    SYNTAX      TmnxAdminState
    MAX-ACCESS  read-write
    STATUS      current
    DESCRIPTION
        "The value of vRtrIfBfdExtAdminState specifies the admin state of BFD
         on this interface.

         When the value of vRtrIfBfdExtAdminState is 'inService', BFD sessions
         can be established on this interface. When it is 'outOfService', they
         cannot."
    ::= { vRtrIfBfdExtEntry 2 }

vRtrIfBfdExtTransmitInterval     OBJECT-TYPE
    SYNTAX      Unsigned32 (10..100000)
    UNITS       "milliseconds"
    MAX-ACCESS  read-write
    STATUS      current
    DESCRIPTION
        "The value of vRtrIfBfdExtTransmitInterval specifies the BFD transmit
         interval over this interface.

         The minimum accepted value depends on the value of vRtrIfBfdExtType,
         as follows:
             'cpmNp(1)' :   10 milliseconds
             'auto(2)'  :  100 milliseconds."
    DEFVAL      { 100 }
    ::= { vRtrIfBfdExtEntry 3 }

vRtrIfBfdExtReceiveInterval      OBJECT-TYPE
    SYNTAX      Unsigned32 (10..100000)
    UNITS       "milliseconds"
    MAX-ACCESS  read-write
    STATUS      current
    DESCRIPTION
        "The value of vRtrIfBfdExtReceiveInterval specifies the BFD receive
         interval over this interface.

         The minimum accepted value depends on the value of vRtrIfBfdExtType,
         as follows:
             'cpmNp(1)' :   10 milliseconds
             'auto(2)'  :  100 milliseconds."
    DEFVAL      { 100 }
    ::= { vRtrIfBfdExtEntry 4 }

vRtrIfBfdExtMultiplier           OBJECT-TYPE
    SYNTAX      Unsigned32 (1..20)
    MAX-ACCESS  read-write
    STATUS      current
    DESCRIPTION
        "The value of vRtrIfBfdExtMultiplier specifies the the number of
         consecutive BFD messages that must be missed from the peer before the
         BFD session state is changed to down and the upper level protocols
         (OSPF, IS-IS or PIM) are notified of the fault."
    DEFVAL      { 3 }
    ::= { vRtrIfBfdExtEntry 5 }

vRtrIfBfdExtEchoInterval         OBJECT-TYPE
    SYNTAX      Unsigned32 (0 | 100..100000)
    UNITS       "milliseconds"
    MAX-ACCESS  read-write
    STATUS      current
    DESCRIPTION
        "The value of vRtrIfBfdExtEchoInterval specifies the BFD echo interval
         over this interface."
    DEFVAL      { 0 }
    ::= { vRtrIfBfdExtEntry 6 }

vRtrIfBfdExtType                 OBJECT-TYPE
    SYNTAX      INTEGER {
        cpmNp (1),
        auto  (2),
        fp    (3)
    }
    MAX-ACCESS  read-write
    STATUS      current
    DESCRIPTION
        "The value of vRtrIfBfdExtType specifies the configured termination of
         a BFD session on this interface.

         The value of 'cpmNp(1)' specifies termination on the CPM card's
         Network Processor. The value of 'auto(2)' specifies a system-selected
         termination other than the CPM Network Processor. The value 'fp(3)'
         specifies termination on forwarding plane"
    DEFVAL      { auto }
    ::= { vRtrIfBfdExtEntry 7 }

vRtrIfIpReasTable                OBJECT-TYPE
    SYNTAX      SEQUENCE OF VRtrIfIpReasEntry
    MAX-ACCESS  not-accessible
    STATUS      current
    DESCRIPTION
        "The vRtrIfIpReasTable table contains the configuration for IP
         Reassembly on the vRtrIfEntry with the same indices."
    ::= { tmnxVRtrObjs 72 }

vRtrIfIpReasEntry                OBJECT-TYPE
    SYNTAX      VRtrIfIpReasEntry
    MAX-ACCESS  not-accessible
    STATUS      current
    DESCRIPTION
        "Each row entry represents the IP Reassembly configuration for an
         interface. Entries are created and deleted when entries in the
         vRtrIfTable are created and deleted."
    AUGMENTS    { vRtrIfEntry }
    ::= { vRtrIfIpReasTable 1 }

VRtrIfIpReasEntry                ::= SEQUENCE
{
    vRtrIfIpReasPortID               TmnxPortID,
    vRtrIfIpReasContextValue         TmnxReasContextVal
}

vRtrIfIpReasPortID               OBJECT-TYPE
    SYNTAX      TmnxPortID
    MAX-ACCESS  read-create
    STATUS      current
    DESCRIPTION
        "The value of vRtrIfIpReasPortID specifies the physical port which
         performs IP reassembly. When vRtrIfIpReasPortID is zero (0), then
         there is no IP reassembly supported on the IP interface."
    DEFVAL      { 0 }
    ::= { vRtrIfIpReasEntry 1 }

vRtrIfIpReasContextValue         OBJECT-TYPE
    SYNTAX      TmnxReasContextVal
    MAX-ACCESS  read-create
    STATUS      current
    DESCRIPTION
        "The value of vRtrIfIpReasContextValue along with vRtrIfIpReasPortID
         specifies the reassembly context in a given virtual router instance."
    ::= { vRtrIfIpReasEntry 2 }

vRtrMsPwL2RtTable                OBJECT-TYPE
    SYNTAX      SEQUENCE OF VRtrMsPwL2RtEntry
    MAX-ACCESS  not-accessible
    STATUS      current
    DESCRIPTION
        "The vRtrMsPwL2RtTable contains LDP FEC-129 Attachment Individual
         Identifier (AII) type 2 layer-2 route table entries used by
         multi-segment pseudo-wire."
    ::= { tmnxVRtrObjs 73 }

vRtrMsPwL2RtEntry                OBJECT-TYPE
    SYNTAX      VRtrMsPwL2RtEntry
    MAX-ACCESS  not-accessible
    STATUS      current
    DESCRIPTION
        "The vRtrMsPwL2RtEntry consists of the multi-segment pseudo-wire LDP
         FEC-129 layer 2 route entry information."
    INDEX       {
        vRtrMsPwL2RtDestGlobalId,
        vRtrMsPwL2RtDestPrefix,
        vRtrMsPwL2RtDestAcId,
        vRtrMsPwL2RtDestPrefixLen,
        vRtrMsPwL2RtNextHopOwner,
        vRtrMsPwL2RtDestRD,
        vRtrMsPwL2RtNextHopAddrType,
        vRtrMsPwL2RtNextHopAddr
    }
    ::= { vRtrMsPwL2RtTable 1 }

VRtrMsPwL2RtEntry                ::= SEQUENCE
{
    vRtrMsPwL2RtDestGlobalId         TmnxPwGlobalIdOrZero,
    vRtrMsPwL2RtDestPrefix           Unsigned32,
    vRtrMsPwL2RtDestAcId             Unsigned32,
    vRtrMsPwL2RtDestPrefixLen        InetAddressPrefixLength,
    vRtrMsPwL2RtDestRD               TmnxVPNRouteDistinguisher,
    vRtrMsPwL2RtNextHopAddrType      InetAddressType,
    vRtrMsPwL2RtNextHopAddr          InetAddress,
    vRtrMsPwL2RtNextHopOwner         TmnxL3RouteOwner,
    vRtrMsPwL2RtRDCommunity          Unsigned32,
    vRtrMsPwL2RtIsBestRoute          TruthValue,
    vRtrMsPwL2RtAge                  Gauge32
}

vRtrMsPwL2RtDestGlobalId         OBJECT-TYPE
    SYNTAX      TmnxPwGlobalIdOrZero
    MAX-ACCESS  not-accessible
    STATUS      current
    DESCRIPTION
        "The value of vRtrMsPwL2RtDestGlobalId specifies the global identifier
         of Attachment Individual Identifier (AII) portion of the Generalized
         Id FEC element of the destination of the route entry."
    ::= { vRtrMsPwL2RtEntry 1 }

vRtrMsPwL2RtDestPrefix           OBJECT-TYPE
    SYNTAX      Unsigned32
    MAX-ACCESS  not-accessible
    STATUS      current
    DESCRIPTION
        "The value of vRtrMsPwL2RtDestPrefix specifies the prefix to the
         Attachment Individual Identifier (AII) portion of the Generalized Id
         FEC element of the destination of the route entry."
    ::= { vRtrMsPwL2RtEntry 2 }

vRtrMsPwL2RtDestAcId             OBJECT-TYPE
    SYNTAX      Unsigned32
    MAX-ACCESS  not-accessible
    STATUS      current
    DESCRIPTION
        "The value of vRtrMsPwL2RtDestAcId specifies the attachment circuit
         identifier part of Attachment Individual Identifier (AII) portion of
         the Generalized Id FEC element of the destination of the route entry."
    ::= { vRtrMsPwL2RtEntry 3 }

vRtrMsPwL2RtDestPrefixLen        OBJECT-TYPE
    SYNTAX      InetAddressPrefixLength
    MAX-ACCESS  not-accessible
    STATUS      current
    DESCRIPTION
        "The value of vRtrMsPwL2RtDestPrefixLen specifies the length of the
         prefix to the Attachment Individual Identifier (AII) portion of the
         Generalized Id FEC element of the destination of the route entry."
    ::= { vRtrMsPwL2RtEntry 4 }

vRtrMsPwL2RtDestRD               OBJECT-TYPE
    SYNTAX      TmnxVPNRouteDistinguisher
    MAX-ACCESS  not-accessible
    STATUS      current
    DESCRIPTION
        "The value of vRtrMsPwL2RtDestRD indicates an identifier attached to
         routes that distinguishes to which VPN it belongs."
    ::= { vRtrMsPwL2RtEntry 5 }

vRtrMsPwL2RtNextHopAddrType      OBJECT-TYPE
    SYNTAX      InetAddressType
    MAX-ACCESS  not-accessible
    STATUS      current
    DESCRIPTION
        "The value of vRtrMsPwL2RtNextHopAddrType indicates the address type of
         vRtrMsPwL2RtNextHopAddr object."
    ::= { vRtrMsPwL2RtEntry 6 }

vRtrMsPwL2RtNextHopAddr          OBJECT-TYPE
    SYNTAX      InetAddress (SIZE (4|16))
    MAX-ACCESS  not-accessible
    STATUS      current
    DESCRIPTION
        "The value of vRtrMsPwL2RtNextHopAddr indicates the address of the next
         hop in the LDP FEC-129 route entry."
    ::= { vRtrMsPwL2RtEntry 7 }

vRtrMsPwL2RtNextHopOwner         OBJECT-TYPE
    SYNTAX      TmnxL3RouteOwner
    MAX-ACCESS  not-accessible
    STATUS      current
    DESCRIPTION
        "The value of vRtrMsPwL2RtNextHopOwner indicates the owner of the next
         hop in the LDP FEC-129 route entry."
    ::= { vRtrMsPwL2RtEntry 8 }

vRtrMsPwL2RtRDCommunity          OBJECT-TYPE
    SYNTAX      Unsigned32
    MAX-ACCESS  read-only
    STATUS      current
    DESCRIPTION
        "The value of the object vRtrMsPwL2RtRDCommunity indicates the BGP
         community associated with the route-distinguisher in the LDP FEC-129
         route entry."
    ::= { vRtrMsPwL2RtEntry 9 }

vRtrMsPwL2RtIsBestRoute          OBJECT-TYPE
    SYNTAX      TruthValue
    MAX-ACCESS  read-only
    STATUS      current
    DESCRIPTION
        "The value of the object vRtrMsPwL2RtIsBestRoute indicates the best
         route from the destination to the next hop."
    ::= { vRtrMsPwL2RtEntry 10 }

vRtrMsPwL2RtAge                  OBJECT-TYPE
    SYNTAX      Gauge32
    UNITS       "seconds"
    MAX-ACCESS  read-only
    STATUS      current
    DESCRIPTION
        "The value of vRtrMsPwL2RtAge indicates the number of seconds since
         this route was last updated or otherwise determined to be correct."
    ::= { vRtrMsPwL2RtEntry 11 }

vRtrIfStatsExtTable              OBJECT-TYPE
    SYNTAX      SEQUENCE OF VRtrIfStatsExtEntry
    MAX-ACCESS  not-accessible
    STATUS      current
    DESCRIPTION
        "The vRtrIfStatsExtTable table contains statistics per virtual router
         interface."
    ::= { tmnxVRtrObjs 74 }

vRtrIfStatsExtEntry              OBJECT-TYPE
    SYNTAX      VRtrIfStatsExtEntry
    MAX-ACCESS  not-accessible
    STATUS      current
    DESCRIPTION
        "Each row entry represents the statistics per virtual router interface.
         Entries are created and deleted when entries in the vRtrIfEntry are
         created and deleted."
    AUGMENTS    { vRtrIfStatsEntry }
    ::= { vRtrIfStatsExtTable 1 }

VRtrIfStatsExtEntry              ::= SEQUENCE
{
    vRtrIfTxPkts                     Counter64,
    vRtrIfTxPktsLow32                Counter32,
    vRtrIfTxPktsHigh32               Counter32,
    vRtrIfTxBytes                    Counter64,
    vRtrIfTxBytesLow32               Counter32,
    vRtrIfTxBytesHigh32              Counter32,
    vRtrIfRxMplsPkts                 Counter64,
    vRtrIfTxMplsPkts                 Counter64,
    vRtrIfRxMplsBytes                Counter64,
    vRtrIfTxMplsBytes                Counter64,
    vRtrIfTxNgeEncryptPkts           Counter64,
    vRtrIfTxNgeEncryptBytes          Counter64,
    vRtrIfRxNgeDecryptPkts           Counter64,
    vRtrIfRxNgeDecryptBytes          Counter64,
    vRtrIfRxNgeInvSpiDropPkts        Counter64,
    vRtrIfRxNgeInvSpiDropBytes       Counter64,
    vRtrIfRxNgeOthDropPkts           Counter64,
    vRtrIfRxNgeOthDropBytes          Counter64,
    vRtrIfRxNgeIcmpDropPkts          Counter64,
    vRtrIfRxNgeIcmpDropBytes         Counter64,
    vRtrIfAltRxMplsPkts              Counter64,
    vRtrIfAltTxMplsPkts              Counter64,
    vRtrIfAltRxMplsBytes             Counter64,
    vRtrIfAltTxMplsBytes             Counter64,
    vRtrIfTxV4DirectedBcastPktDrop   Counter64,
    vRtrIfTxV4DirectedBcastByteDrop  Counter64,
    vRtrIfRxV4IpHelperRedirectPkts   Counter64,
    vRtrIfRxV4IpHelperRedirectBytes  Counter64,
    vRtrIfRxIpMplsBytes              Counter64,
    vRtrIfRxIpMplsPkts               Counter64,
    vRtrIfTxIpMplsBytes              Counter64,
    vRtrIfTxIpMplsPkts               Counter64
}

vRtrIfTxPkts                     OBJECT-TYPE
    SYNTAX      Counter64
    MAX-ACCESS  read-only
    STATUS      current
    DESCRIPTION
        "The value of vRtrIfTxPkts indicates the number of total packets sent
         by this interface."
    ::= { vRtrIfStatsExtEntry 1 }

vRtrIfTxPktsLow32                OBJECT-TYPE
    SYNTAX      Counter32
    MAX-ACCESS  read-only
    STATUS      current
    DESCRIPTION
        "The value of vRtrIfTxPktsLow32 indicates the lower 32 bits of the
         value of vRtrIfTxPkts."
    ::= { vRtrIfStatsExtEntry 2 }

vRtrIfTxPktsHigh32               OBJECT-TYPE
    SYNTAX      Counter32
    MAX-ACCESS  read-only
    STATUS      current
    DESCRIPTION
        "The value of vRtrIfTxPktsHigh32 indicates the high 32 bits of the
         value of vRtrIfTxPkts."
    ::= { vRtrIfStatsExtEntry 3 }

vRtrIfTxBytes                    OBJECT-TYPE
    SYNTAX      Counter64
    MAX-ACCESS  read-only
    STATUS      current
    DESCRIPTION
        "The value of vRtrIfTxBytes indicates the number of total bytes sent by
         this interface."
    ::= { vRtrIfStatsExtEntry 4 }

vRtrIfTxBytesLow32               OBJECT-TYPE
    SYNTAX      Counter32
    MAX-ACCESS  read-only
    STATUS      current
    DESCRIPTION
        "The value of vRtrIfTxBytesLow32 indicates the lower 32 bits of the
         value of vRtrIfTxBytes."
    ::= { vRtrIfStatsExtEntry 5 }

vRtrIfTxBytesHigh32              OBJECT-TYPE
    SYNTAX      Counter32
    MAX-ACCESS  read-only
    STATUS      current
    DESCRIPTION
        "The value of vRtrIfTxBytesHigh32 indicates the high 32 bits of the
         value of vRtrIfTxBytes."
    ::= { vRtrIfStatsExtEntry 6 }

vRtrIfRxMplsPkts                 OBJECT-TYPE
    SYNTAX      Counter64
    MAX-ACCESS  read-only
    STATUS      current
    DESCRIPTION
        "The value of vRtrIfRxMplsPkts indicates the total number of MPLS
         packets received by this interface."
    ::= { vRtrIfStatsExtEntry 7 }

vRtrIfTxMplsPkts                 OBJECT-TYPE
    SYNTAX      Counter64
    MAX-ACCESS  read-only
    STATUS      current
    DESCRIPTION
        "The value of vRtrIfTxMplsPkts indicates the total number of MPLS
         packets sent by this interface."
    ::= { vRtrIfStatsExtEntry 8 }

vRtrIfRxMplsBytes                OBJECT-TYPE
    SYNTAX      Counter64
    MAX-ACCESS  read-only
    STATUS      current
    DESCRIPTION
        "The value of vRtrIfRxMplsBytes indicates the total number of MPLS
         bytes received by this interface."
    ::= { vRtrIfStatsExtEntry 9 }

vRtrIfTxMplsBytes                OBJECT-TYPE
    SYNTAX      Counter64
    MAX-ACCESS  read-only
    STATUS      current
    DESCRIPTION
        "The value of vRtrIfTxMplsBytes indicates the total number of MPLS
         bytes sent by this interface."
    ::= { vRtrIfStatsExtEntry 10 }

vRtrIfTxNgeEncryptPkts           OBJECT-TYPE
    SYNTAX      Counter64
    MAX-ACCESS  read-only
    STATUS      current
    DESCRIPTION
        "The value of vRtrIfTxNgeEncryptPkts indicates the number of packets
         successfully encrypted by the interface."
    ::= { vRtrIfStatsExtEntry 11 }

vRtrIfTxNgeEncryptBytes          OBJECT-TYPE
    SYNTAX      Counter64
    MAX-ACCESS  read-only
    STATUS      current
    DESCRIPTION
        "The value of vRtrIfTxNgeEncryptBytes indicates the number of bytes
         successfully encrypted by the interface."
    ::= { vRtrIfStatsExtEntry 12 }

vRtrIfRxNgeDecryptPkts           OBJECT-TYPE
    SYNTAX      Counter64
    MAX-ACCESS  read-only
    STATUS      current
    DESCRIPTION
        "The value of vRtrIfRxNgeDecryptPkts indicates the number of packets
         successfully decrypted by the interface."
    ::= { vRtrIfStatsExtEntry 13 }

vRtrIfRxNgeDecryptBytes          OBJECT-TYPE
    SYNTAX      Counter64
    MAX-ACCESS  read-only
    STATUS      current
    DESCRIPTION
        "The value of vRtrIfRxNgeDecryptBytes indicates the number of bytes
         successfully decrypted by the interface."
    ::= { vRtrIfStatsExtEntry 14 }

vRtrIfRxNgeInvSpiDropPkts        OBJECT-TYPE
    SYNTAX      Counter64
    MAX-ACCESS  read-only
    STATUS      current
    DESCRIPTION
        "The value of vRtrIfRxNgeInvSpiDropPkts indicates the number of packets
         dropped by ingress NGE due to invalid SPI."
    ::= { vRtrIfStatsExtEntry 15 }

vRtrIfRxNgeInvSpiDropBytes       OBJECT-TYPE
    SYNTAX      Counter64
    MAX-ACCESS  read-only
    STATUS      current
    DESCRIPTION
        "The value of vRtrIfRxNgeInvSpiDropBytes indicates the number of
         packets dropped by ingress NGE on the interface."
    ::= { vRtrIfStatsExtEntry 16 }

vRtrIfRxNgeOthDropPkts           OBJECT-TYPE
    SYNTAX      Counter64
    MAX-ACCESS  read-only
    STATUS      current
    DESCRIPTION
        "The value of vRtrIfRxNgeOthDropPkts indicates the number of packets
         dropped by ingress NGE on the interface."
    ::= { vRtrIfStatsExtEntry 17 }

vRtrIfRxNgeOthDropBytes          OBJECT-TYPE
    SYNTAX      Counter64
    MAX-ACCESS  read-only
    STATUS      current
    DESCRIPTION
        "The value of vRtrIfRxNgeOthDropBytes indicates the number of bytes
         dropped by ingress NGE on the interface."
    ::= { vRtrIfStatsExtEntry 18 }

vRtrIfRxNgeIcmpDropPkts          OBJECT-TYPE
    SYNTAX      Counter64
    MAX-ACCESS  read-only
    STATUS      current
    DESCRIPTION
        "The value of vRtrIfRxNgeIcmpDropPkts indicates the number of ICMP
         packets dropped by ingress NGE on the interface."
    ::= { vRtrIfStatsExtEntry 19 }

vRtrIfRxNgeIcmpDropBytes         OBJECT-TYPE
    SYNTAX      Counter64
    MAX-ACCESS  read-only
    STATUS      current
    DESCRIPTION
        "The value of vRtrIfRxNgeIcmpDropBytes indicates the number of ICMP
         bytes dropped by ingress NGE on the interface."
    ::= { vRtrIfStatsExtEntry 20 }

vRtrIfAltRxMplsPkts              OBJECT-TYPE
    SYNTAX      Counter64
    MAX-ACCESS  read-only
    STATUS      current
    DESCRIPTION
        "The value of vRtrIfAltRxMplsPkts indicates the total number of SR-MPLS
         packets received by this interface."
    ::= { vRtrIfStatsExtEntry 21 }

vRtrIfAltTxMplsPkts              OBJECT-TYPE
    SYNTAX      Counter64
    MAX-ACCESS  read-only
    STATUS      current
    DESCRIPTION
        "The value of vRtrIfAltTxMplsPkts indicates the total number of SR-MPLS
         packets sent by this interface."
    ::= { vRtrIfStatsExtEntry 22 }

vRtrIfAltRxMplsBytes             OBJECT-TYPE
    SYNTAX      Counter64
    MAX-ACCESS  read-only
    STATUS      current
    DESCRIPTION
        "The value of vRtrIfAltRxMplsBytes indicates the total number of
         SR-MPLS bytes received by this interface."
    ::= { vRtrIfStatsExtEntry 23 }

vRtrIfAltTxMplsBytes             OBJECT-TYPE
    SYNTAX      Counter64
    MAX-ACCESS  read-only
    STATUS      current
    DESCRIPTION
        "The value of vRtrIfAltTxMplsBytes indicates the total number of
         SR-MPLS bytes sent by this interface."
    ::= { vRtrIfStatsExtEntry 24 }

vRtrIfTxV4DirectedBcastPktDrop   OBJECT-TYPE
    SYNTAX      Counter64
    MAX-ACCESS  read-only
    STATUS      current
    DESCRIPTION
        "The value of vRtrIfTxV4DirectedBcastPktDrop indicates the total number
         of IPv4 directed broadcast packets dropped on an egress interface not
         configured with vRtrIfDirectedBroadcast true."
    ::= { vRtrIfStatsExtEntry 25 }

vRtrIfTxV4DirectedBcastByteDrop  OBJECT-TYPE
    SYNTAX      Counter64
    MAX-ACCESS  read-only
    STATUS      current
    DESCRIPTION
        "The value of vRtrIfTxV4DirectedBcastByteDrop indicates the total
         number of IPv4 directed broadcast bytes dropped on an egress interface
         not configured with vRtrIfDirectedBroadcast true."
    ::= { vRtrIfStatsExtEntry 26 }

vRtrIfRxV4IpHelperRedirectPkts   OBJECT-TYPE
    SYNTAX      Counter64
    MAX-ACCESS  read-only
    STATUS      current
    DESCRIPTION
        "The value vRtrIfRxV4IpHelperRedirectPkts indicates the total number of
         packets redirected to the IP-helper redirect gateway."
    ::= { vRtrIfStatsExtEntry 27 }

vRtrIfRxV4IpHelperRedirectBytes  OBJECT-TYPE
    SYNTAX      Counter64
    MAX-ACCESS  read-only
    STATUS      current
    DESCRIPTION
        "The value vRtrIfRxV4IpHelperRedirectBytes indicates the total number
         of bytes redirected to the IP-helper redirect gateway."
    ::= { vRtrIfStatsExtEntry 28 }

vRtrIfRxIpMplsBytes              OBJECT-TYPE
    SYNTAX      Counter64
    MAX-ACCESS  read-only
    STATUS      current
    DESCRIPTION
        "The value of vRtrIfRxIpMplsBytes indication the total  Rx_IPv4_bytes,
         Rx_IPv6_bytes, Rx_MPLS_bytes."
    ::= { vRtrIfStatsExtEntry 29 }

vRtrIfRxIpMplsPkts               OBJECT-TYPE
    SYNTAX      Counter64
    MAX-ACCESS  read-only
    STATUS      current
    DESCRIPTION
        "The value of vRtrIfRxIpMplsPkts indication the total  Rx_IPv4_Pkts,
         Rx_IPv6_Pkts, Rx_MPLS_Pkts."
    ::= { vRtrIfStatsExtEntry 30 }

vRtrIfTxIpMplsBytes              OBJECT-TYPE
    SYNTAX      Counter64
    MAX-ACCESS  read-only
    STATUS      current
    DESCRIPTION
        "The value of vRtrIfTxIpMplsBytes indication the total  Tx_IPv4_bytes,
         Tx_IPv6_bytes, Tx_MPLS_bytes."
    ::= { vRtrIfStatsExtEntry 31 }

vRtrIfTxIpMplsPkts               OBJECT-TYPE
    SYNTAX      Counter64
    MAX-ACCESS  read-only
    STATUS      current
    DESCRIPTION
        "The value of vRtrIfTxIpMplsPkts indication the total  Tx_IPv4_Pkts,
         Tx_IPv6_Pkts, Tx_MPLS_Pkts."
    ::= { vRtrIfStatsExtEntry 32 }

vRtrStatExtTable                 OBJECT-TYPE
    SYNTAX      SEQUENCE OF VRtrStatExtEntry
    MAX-ACCESS  not-accessible
    STATUS      current
    DESCRIPTION
        "The vRtrStatExtTable has an entry for each virtual router configured
         in the system."
    ::= { tmnxVRtrObjs 75 }

vRtrStatExtEntry                 OBJECT-TYPE
    SYNTAX      VRtrStatExtEntry
    MAX-ACCESS  not-accessible
    STATUS      current
    DESCRIPTION
        "Each row entry represents a collection of statistics for a virtual
         router in the system.

         Entries cannot be created and deleted via SNMP SET operations."
    AUGMENTS    { vRtrConfEntry }
    ::= { vRtrStatExtTable 1 }

VRtrStatExtEntry                 ::= SEQUENCE
{
    vRtrISISAltRoutes                Gauge32,
    vRtrISISActiveAltRoutes          Gauge32,
    vRtrBGPAltRoutes                 Gauge32,
    vRtrBGPActiveAltRoutes           Gauge32,
    vRtrStatCurrNumAltRoutes         Gauge32,
    vRtrV6ISISAltRoutes              Gauge32,
    vRtrV6ISISActiveAltRoutes        Gauge32,
    vRtrV6BGPAltRoutes               Gauge32,
    vRtrV6BGPActiveAltRoutes         Gauge32,
    vRtrV6StatCurrNumAltRoutes       Gauge32,
    vRtrBGPVPNAltRoutes              Gauge32,
    vRtrBGPVPNActiveAltRoutes        Gauge32,
    vRtrV6BGPVPNAltRoutes            Gauge32,
    vRtrV6BGPVPNActiveAltRoutes      Gauge32,
    vRtrOSPFAltRoutes                Gauge32,
    vRtrOSPFActiveAltRoutes          Gauge32,
    vRtrV6OSPFAltRoutes              Gauge32,
    vRtrV6OSPFActiveAltRoutes        Gauge32,
    vRtrOSPFv3Routes                 Gauge32,
    vRtrOSPFv3ActiveRoutes           Gauge32,
    vRtrOSPFv3AltRoutes              Gauge32,
    vRtrOSPFv3ActiveAltRoutes        Gauge32,
    vRtrStatTotalIsisTunnels         Gauge32,
    vRtrStatActiveIsisTunnels        Gauge32,
    vRtrStatTotalOspfTunnels         Gauge32,
    vRtrStatActiveOspfTunnels        Gauge32,
    vRtrV6LDPRoutes                  Gauge32,
    vRtrV6LDPActiveRoutes            Gauge32,
    vRtrStatTotalIsisV6Tunnels       Gauge32,
    vRtrStatActiveIsisV6Tunnels      Gauge32,
    vRtrStatTotalSrTeTunnels         Gauge32,
    vRtrStatActiveSrTeTunnels        Gauge32,
    vRtrStatTotalFpeTunnels          Gauge32,
    vRtrStatActiveFpeTunnels         Gauge32,
    vRtrStatTotalUdpTunnels          Gauge32,
    vRtrStatActiveUdpTunnels         Gauge32,
    vRtrStatArpRoutes                Gauge32,
    vRtrStatArpActiveRoutes          Gauge32,
    vRtrStatNdRoutes                 Gauge32,
    vRtrStatNdActiveRoutes           Gauge32,
    vRtrStatTotalOspfv3Tunnels       Gauge32,
    vRtrStatActiveOspfv3Tunnels      Gauge32,
    vRtrStatTotalSrPolicyTunnels     Gauge32,
    vRtrStatActiveSrPolicyTunnels    Gauge32,
    vRtrStatTotalRibApiV4Routes      Gauge32,
    vRtrStatActiveRibApiV4Routes     Gauge32,
    vRtrStatTotalRibApiV6Routes      Gauge32,
    vRtrStatActiveRibApiV6Routes     Gauge32,
    vRtrStatTotalRibApiV4Tunnels     Gauge32,
    vRtrStatActiveRibApiV4Tunnels    Gauge32,
    vRtrStatTotalRibApiV6Tunnels     Gauge32,
    vRtrStatActiveRibApiV6Tunnels    Gauge32,
    vRtrStatTotMplsFwdPlcyV4Tunnels  Gauge32,
    vRtrStatActMplsFwdPlcyV4Tunnels  Gauge32,
    vRtrStatTotMplsFwdPlcyV6Tunnels  Gauge32,
    vRtrStatActMplsFwdPlcyV6Tunnels  Gauge32,
    vRtrStatTotalOspfv3IPv6Tunnels   Gauge32,
    vRtrStatActiveOspfv3IPv6Tunnels  Gauge32,
    vRtrDHCPRoutes                   Gauge32,
    vRtrDHCPActiveRoutes             Gauge32,
    vRtrV6DHCPRoutes                 Gauge32,
    vRtrV6DHCPActiveRoutes           Gauge32,
    vRtrStatActiveSrPolicyV6Tunnels  Gauge32,
    vRtrStatTotalSrPolicyV6Tunnels   Gauge32,
    vRtrStatTotalSrTeV6Tunnels       Gauge32,
    vRtrStatActiveSrTeV6Tunnels      Gauge32,
    vRtrBgpEvpnIflRoutes             Gauge32,
    vRtrBgpEvpnIflActRoutes          Gauge32,
    vRtrBgpEvpnIflAltRoutes          Gauge32,
    vRtrBgpEvpnIflActAltRoutes       Gauge32,
    vRtrV6BgpEvpnIflRoutes           Gauge32,
    vRtrV6BgpEvpnIflActRoutes        Gauge32,
    vRtrV6BgpEvpnIflAltRoutes        Gauge32,
    vRtrV6BgpEvpnIflActAltRoutes     Gauge32,
    vRtrBgpEvpnIffRoutes             Gauge32,
    vRtrBgpEvpnIffActRoutes          Gauge32,
    vRtrV6BgpEvpnIffRoutes           Gauge32,
    vRtrV6BgpEvpnIffActRoutes        Gauge32,
    vRtrMtrace2OperState             TmnxEnabledDisabled,
    vRtrStatActiveSrV6IsisTunnels    Gauge32,
    vRtrStatTotalSrV6IsisTunnels     Gauge32,
    vRtrStatSrV6ActiveRoutes         Gauge32,
    vRtrStatSrV6TotalRoutes          Gauge32,
    vRtrStatActiveSrV6PolicyTunnels  Gauge32,
    vRtrStatTotalSrV6PolicyTunnels   Gauge32,
    vRtrStatActiveSrV6PolicyRoutes   Gauge32,
    vRtrStatTotalSrV6PolicyRoutes    Gauge32,
    vRtrStatActiveV4VideoRoutes      Gauge32,
    vRtrStatTotalV4VideoRoutes       Gauge32,
    vRtrStatActiveV6VideoRoutes      Gauge32,
    vRtrStatTotalV6VideoRoutes       Gauge32,
    vRtrMcastIpv4ActiveVideoRoutes   Gauge32,
    vRtrMcastIpv4TotalVideoRoutes    Gauge32,
    vRtrMcastIpv6ActiveVideoRoutes   Gauge32,
    vRtrMcastIpv6TotalVideoRoutes    Gauge32,
    vRtrStatV6NdRaRoutes             Gauge32,
    vRtrStatV6NdRaActiveRoutes       Gauge32,
    vRtrStatActiveV4EsmBcastRoutes   Gauge32,
    vRtrStatTotalV4EsmBcastRoutes    Gauge32,
    vRtrBgpEvpnIflHostRoutes         Gauge32,
    vRtrBgpEvpnIflHostActRoutes      Gauge32,
    vRtrV6BgpEvpnIflHostRoutes       Gauge32,
    vRtrV6BgpEvpnIflHostActRoutes    Gauge32
}

vRtrISISAltRoutes                OBJECT-TYPE
    SYNTAX      Gauge32
    MAX-ACCESS  read-only
    STATUS      current
    DESCRIPTION
        "The value of vRtrISISAltRoutes indicates the current number of
         alternate ISIS routes for this instance of the route table."
    ::= { vRtrStatExtEntry 1 }

vRtrISISActiveAltRoutes          OBJECT-TYPE
    SYNTAX      Gauge32
    MAX-ACCESS  read-only
    STATUS      current
    DESCRIPTION
        "The value of vRtrISISActiveAltRoutes indicates the current number of
         alternate ISIS routes that are active for this instance of the route
         table."
    ::= { vRtrStatExtEntry 2 }

vRtrBGPAltRoutes                 OBJECT-TYPE
    SYNTAX      Gauge32
    MAX-ACCESS  read-only
    STATUS      current
    DESCRIPTION
        "The value of vRtrBGPAltRoutes indicates the current number of
         alternate BGP routes for this instance of the route table."
    ::= { vRtrStatExtEntry 3 }

vRtrBGPActiveAltRoutes           OBJECT-TYPE
    SYNTAX      Gauge32
    MAX-ACCESS  read-only
    STATUS      current
    DESCRIPTION
        "The value of vRtrBGPActiveAltRoutes indicates the current number of
         alternate BGP routes that are active for this instance of the route
         table."
    ::= { vRtrStatExtEntry 4 }

vRtrStatCurrNumAltRoutes         OBJECT-TYPE
    SYNTAX      Gauge32
    MAX-ACCESS  read-only
    STATUS      current
    DESCRIPTION
        "The value of vRtrStatCurrNumAltRoutes indicates the current number of
         total alternate routes for this instance of the route table."
    ::= { vRtrStatExtEntry 5 }

vRtrV6ISISAltRoutes              OBJECT-TYPE
    SYNTAX      Gauge32
    MAX-ACCESS  read-only
    STATUS      current
    DESCRIPTION
        "The value of vRtrV6ISISAltRoutes indicates the current number of IPv6
         alternate ISIS routes for this instance of the route table."
    ::= { vRtrStatExtEntry 6 }

vRtrV6ISISActiveAltRoutes        OBJECT-TYPE
    SYNTAX      Gauge32
    MAX-ACCESS  read-only
    STATUS      current
    DESCRIPTION
        "The value of vRtrV6ISISActiveAltRoutes indicates the current number of
         IPv6 alternate ISIS routes that are active for this instance of the
         route table."
    ::= { vRtrStatExtEntry 7 }

vRtrV6BGPAltRoutes               OBJECT-TYPE
    SYNTAX      Gauge32
    MAX-ACCESS  read-only
    STATUS      current
    DESCRIPTION
        "The value of vRtrV6BGPAltRoutes indicates the current number of IPv6
         alternate BGP routes for this instance of the route table."
    ::= { vRtrStatExtEntry 8 }

vRtrV6BGPActiveAltRoutes         OBJECT-TYPE
    SYNTAX      Gauge32
    MAX-ACCESS  read-only
    STATUS      current
    DESCRIPTION
        "The value of vRtrV6BGPActiveAltRoutes indicates the current number of
         IPv6 alternate BGP routes that are active for this instance of the
         route table."
    ::= { vRtrStatExtEntry 9 }

vRtrV6StatCurrNumAltRoutes       OBJECT-TYPE
    SYNTAX      Gauge32
    MAX-ACCESS  read-only
    STATUS      current
    DESCRIPTION
        "The value of vRtrV6StatCurrNumAltRoutes indicates the current number
         of IPv6 total alternate routes for this instance of the route table."
    ::= { vRtrStatExtEntry 10 }

vRtrBGPVPNAltRoutes              OBJECT-TYPE
    SYNTAX      Gauge32
    MAX-ACCESS  read-only
    STATUS      current
    DESCRIPTION
        "The value of vRtrBGPVPNAltRoutes indicates the current number of
         alternate BGP-VPN routes for this instance of the route table."
    ::= { vRtrStatExtEntry 11 }

vRtrBGPVPNActiveAltRoutes        OBJECT-TYPE
    SYNTAX      Gauge32
    MAX-ACCESS  read-only
    STATUS      current
    DESCRIPTION
        "The value of vRtrBGPVPNActiveAltRoutes indicates the current number of
         alternate BGP-VPN routes that are active for this instance of the
         route table."
    ::= { vRtrStatExtEntry 12 }

vRtrV6BGPVPNAltRoutes            OBJECT-TYPE
    SYNTAX      Gauge32
    MAX-ACCESS  read-only
    STATUS      current
    DESCRIPTION
        "The value of vRtrV6BGPVPNAltRoutes indicates the current number of
         IPv6 alternate BGP-VPN routes for this instance of the route table."
    ::= { vRtrStatExtEntry 13 }

vRtrV6BGPVPNActiveAltRoutes      OBJECT-TYPE
    SYNTAX      Gauge32
    MAX-ACCESS  read-only
    STATUS      current
    DESCRIPTION
        "The value of vRtrV6BGPVPNActiveAltRoutes indicates the current number
         of IPv6 alternate BGP-VPN routes that are active for this instance of
         the route table."
    ::= { vRtrStatExtEntry 14 }

vRtrOSPFAltRoutes                OBJECT-TYPE
    SYNTAX      Gauge32
    MAX-ACCESS  read-only
    STATUS      current
    DESCRIPTION
        "The value of vRtrOSPFAltRoutes indicates the current number of
         alternate OSPF routes for this instance of the route table."
    ::= { vRtrStatExtEntry 15 }

vRtrOSPFActiveAltRoutes          OBJECT-TYPE
    SYNTAX      Gauge32
    MAX-ACCESS  read-only
    STATUS      current
    DESCRIPTION
        "The value of vRtrOSPFActiveAltRoutes indicates the current number of
         alternate OSPF routes that are active for this instance of the route
         table."
    ::= { vRtrStatExtEntry 16 }

vRtrV6OSPFAltRoutes              OBJECT-TYPE
    SYNTAX      Gauge32
    MAX-ACCESS  read-only
    STATUS      current
    DESCRIPTION
        "The value of vRtrV6OSPFAltRoutes indicates the current number of IPv6
         alternate OSPF routes for this instance of the route table."
    ::= { vRtrStatExtEntry 17 }

vRtrV6OSPFActiveAltRoutes        OBJECT-TYPE
    SYNTAX      Gauge32
    MAX-ACCESS  read-only
    STATUS      current
    DESCRIPTION
        "The value of vRtrV6OSPFActiveAltRoutes indicates the current number of
         IPv6 alternate OSPF routes that are active for this instance of the
         route table."
    ::= { vRtrStatExtEntry 18 }

vRtrOSPFv3Routes                 OBJECT-TYPE
    SYNTAX      Gauge32
    MAX-ACCESS  read-only
    STATUS      current
    DESCRIPTION
        "vRtrOSPFv3Routes indicates the current number of OSPFv3 routes for
         this instance of the route table."
    ::= { vRtrStatExtEntry 19 }

vRtrOSPFv3ActiveRoutes           OBJECT-TYPE
    SYNTAX      Gauge32
    MAX-ACCESS  read-only
    STATUS      current
    DESCRIPTION
        "vRtrOSPFv3ActiveRoutes indicates the current number of active OSPFv3
         routes for this instance of the route table."
    ::= { vRtrStatExtEntry 20 }

vRtrOSPFv3AltRoutes              OBJECT-TYPE
    SYNTAX      Gauge32
    MAX-ACCESS  read-only
    STATUS      current
    DESCRIPTION
        "The value of vRtrOSPFv3AltRoutes indicates the current number of
         alternate OSPFv3 routes for this instance of the route table."
    ::= { vRtrStatExtEntry 21 }

vRtrOSPFv3ActiveAltRoutes        OBJECT-TYPE
    SYNTAX      Gauge32
    MAX-ACCESS  read-only
    STATUS      current
    DESCRIPTION
        "The value of vRtrOSPFv3ActiveAltRoutes indicates the current number of
         alternate OSPFv3 routes that are active for this instance of the route
         table."
    ::= { vRtrStatExtEntry 22 }

vRtrStatTotalIsisTunnels         OBJECT-TYPE
    SYNTAX      Gauge32
    MAX-ACCESS  read-only
    STATUS      current
    DESCRIPTION
        "The value of vRtrStatTotalIsisTunnels indicates the current number of
         active and inactive ISIS tunnels."
    ::= { vRtrStatExtEntry 23 }

vRtrStatActiveIsisTunnels        OBJECT-TYPE
    SYNTAX      Gauge32
    MAX-ACCESS  read-only
    STATUS      current
    DESCRIPTION
        "The value of vRtrStatActiveIsisTunnels indicates the current number of
         active ISIS tunnels."
    ::= { vRtrStatExtEntry 24 }

vRtrStatTotalOspfTunnels         OBJECT-TYPE
    SYNTAX      Gauge32
    MAX-ACCESS  read-only
    STATUS      current
    DESCRIPTION
        "The value of vRtrStatTotalOspfTunnels indicates the current number of
         active and inactive OSPF tunnels."
    ::= { vRtrStatExtEntry 25 }

vRtrStatActiveOspfTunnels        OBJECT-TYPE
    SYNTAX      Gauge32
    MAX-ACCESS  read-only
    STATUS      current
    DESCRIPTION
        "The value of vRtrStatActiveOspfTunnels indicates the current number of
         active OSPF tunnels."
    ::= { vRtrStatExtEntry 26 }

vRtrV6LDPRoutes                  OBJECT-TYPE
    SYNTAX      Gauge32
    MAX-ACCESS  read-only
    STATUS      current
    DESCRIPTION
        "The value of the object vRtrV6LDPRoutes indicates the current number
         of IPv6 ldp routes for this instance of the route table."
    ::= { vRtrStatExtEntry 27 }

vRtrV6LDPActiveRoutes            OBJECT-TYPE
    SYNTAX      Gauge32
    MAX-ACCESS  read-only
    STATUS      current
    DESCRIPTION
        "The value of the object vRtrV6LDPActiveRoutes indicates the current
         number of active IPv6 ldp routes for this instance of the route table."
    ::= { vRtrStatExtEntry 28 }

vRtrStatTotalIsisV6Tunnels       OBJECT-TYPE
    SYNTAX      Gauge32
    MAX-ACCESS  read-only
    STATUS      current
    DESCRIPTION
        "The value of vRtrStatTotalIsisV6Tunnels indicates the current number
         of active and inactive IPv6 ISIS tunnels."
    ::= { vRtrStatExtEntry 29 }

vRtrStatActiveIsisV6Tunnels      OBJECT-TYPE
    SYNTAX      Gauge32
    MAX-ACCESS  read-only
    STATUS      current
    DESCRIPTION
        "The value of vRtrStatActiveIsisV6Tunnels indicates the current number
         of active IPv6 ISIS tunnels."
    ::= { vRtrStatExtEntry 30 }

vRtrStatTotalSrTeTunnels         OBJECT-TYPE
    SYNTAX      Gauge32
    MAX-ACCESS  read-only
    STATUS      current
    DESCRIPTION
        "vRtrStatTotalSrTeTunnels indicates the current number of both active
         and inactive SR-TE tunnels."
    ::= { vRtrStatExtEntry 31 }

vRtrStatActiveSrTeTunnels        OBJECT-TYPE
    SYNTAX      Gauge32
    MAX-ACCESS  read-only
    STATUS      current
    DESCRIPTION
        "vRtrStatActiveSrTeTunnels indicates the current number of active SR-TE
         tunnels."
    ::= { vRtrStatExtEntry 32 }

vRtrStatTotalFpeTunnels          OBJECT-TYPE
    SYNTAX      Gauge32
    MAX-ACCESS  read-only
    STATUS      current
    DESCRIPTION
        "vRtrStatTotalFpeTunnels indicates the current number of both active
         and inactive FPE tunnels."
    ::= { vRtrStatExtEntry 33 }

vRtrStatActiveFpeTunnels         OBJECT-TYPE
    SYNTAX      Gauge32
    MAX-ACCESS  read-only
    STATUS      current
    DESCRIPTION
        "vRtrStatActiveFpeTunnels indicates the current number of active FPE
         tunnels."
    ::= { vRtrStatExtEntry 34 }

vRtrStatTotalUdpTunnels          OBJECT-TYPE
    SYNTAX      Gauge32
    MAX-ACCESS  read-only
    STATUS      current
    DESCRIPTION
        "vRtrStatTotalUdpTunnels indicates the current number of both active
         and inactive UDP tunnels."
    ::= { vRtrStatExtEntry 35 }

vRtrStatActiveUdpTunnels         OBJECT-TYPE
    SYNTAX      Gauge32
    MAX-ACCESS  read-only
    STATUS      current
    DESCRIPTION
        "vRtrStatActiveUdpTunnels indicates the current number of active UDP
         tunnels."
    ::= { vRtrStatExtEntry 36 }

vRtrStatArpRoutes                OBJECT-TYPE
    SYNTAX      Gauge32
    MAX-ACCESS  read-only
    STATUS      current
    DESCRIPTION
        "vRtrStatArpRoutes indicates the current number of ARP routes for this
         instance of the route table."
    ::= { vRtrStatExtEntry 37 }

vRtrStatArpActiveRoutes          OBJECT-TYPE
    SYNTAX      Gauge32
    MAX-ACCESS  read-only
    STATUS      current
    DESCRIPTION
        "vRtrStatArpActiveRoutes indicates the current number of active ARP
         routes for this instance of the route table."
    ::= { vRtrStatExtEntry 38 }

vRtrStatNdRoutes                 OBJECT-TYPE
    SYNTAX      Gauge32
    MAX-ACCESS  read-only
    STATUS      current
    DESCRIPTION
        "vRtrStatNdRoutes indicates the current number of ND routes for this
         instance of the route table."
    ::= { vRtrStatExtEntry 39 }

vRtrStatNdActiveRoutes           OBJECT-TYPE
    SYNTAX      Gauge32
    MAX-ACCESS  read-only
    STATUS      current
    DESCRIPTION
        "vRtrStatNdActiveRoutes indicates the current number of active ND
         routes for this instance of the route table."
    ::= { vRtrStatExtEntry 40 }

vRtrStatTotalOspfv3Tunnels       OBJECT-TYPE
    SYNTAX      Gauge32
    MAX-ACCESS  read-only
    STATUS      current
    DESCRIPTION
        "The value of vRtrStatTotalOspfv3Tunnels indicates the current number
         of active and inactive OSPFv3 IPv4 segment-routing tunnels."
    ::= { vRtrStatExtEntry 41 }

vRtrStatActiveOspfv3Tunnels      OBJECT-TYPE
    SYNTAX      Gauge32
    MAX-ACCESS  read-only
    STATUS      current
    DESCRIPTION
        "The value of vRtrStatActiveOspfv3Tunnels indicates the current number
         of active OSPFv3 IPv4 segment-routing tunnels."
    ::= { vRtrStatExtEntry 42 }

vRtrStatTotalSrPolicyTunnels     OBJECT-TYPE
    SYNTAX      Gauge32
    MAX-ACCESS  read-only
    STATUS      current
    DESCRIPTION
        "The value of vRtrStatTotalSrPolicyTunnels indicates the current number
         of active and inactive IPv4 SR Policy tunnels."
    ::= { vRtrStatExtEntry 43 }

vRtrStatActiveSrPolicyTunnels    OBJECT-TYPE
    SYNTAX      Gauge32
    MAX-ACCESS  read-only
    STATUS      current
    DESCRIPTION
        "The value of vRtrStatActiveSrPolicyTunnels indicates the current
         number of active IPv4 SR Policy tunnels."
    ::= { vRtrStatExtEntry 44 }

vRtrStatTotalRibApiV4Routes      OBJECT-TYPE
    SYNTAX      Gauge32
    MAX-ACCESS  read-only
    STATUS      current
    DESCRIPTION
        "The value of vRtrStatTotalRibApiV4Routes indicates the current number
         of IPv4 routes added by RIB-API service for this instance of the route
         table."
    ::= { vRtrStatExtEntry 45 }

vRtrStatActiveRibApiV4Routes     OBJECT-TYPE
    SYNTAX      Gauge32
    MAX-ACCESS  read-only
    STATUS      current
    DESCRIPTION
        "The value of vRtrStatActiveRibApiV4Routes indicates the current number
         of IPv4 routes added by RIB-API service that are active for this
         instance of the route table."
    ::= { vRtrStatExtEntry 46 }

vRtrStatTotalRibApiV6Routes      OBJECT-TYPE
    SYNTAX      Gauge32
    MAX-ACCESS  read-only
    STATUS      current
    DESCRIPTION
        "The value of vRtrStatTotalRibApiV6Routes indicates the current number
         of IPv6 routes added by RIB-API service for this instance of the route
         table."
    ::= { vRtrStatExtEntry 47 }

vRtrStatActiveRibApiV6Routes     OBJECT-TYPE
    SYNTAX      Gauge32
    MAX-ACCESS  read-only
    STATUS      current
    DESCRIPTION
        "The value of vRtrStatActiveRibApiV6Routes indicates the current number
         of IPv6 routes added by RIB-API service that are active for this
         instance of the route table."
    ::= { vRtrStatExtEntry 48 }

vRtrStatTotalRibApiV4Tunnels     OBJECT-TYPE
    SYNTAX      Gauge32
    MAX-ACCESS  read-only
    STATUS      current
    DESCRIPTION
        "vRtrStatTotalRibApiV4Tunnels indicates the current number of both
         active and inactive IPv4 tunnels added by RIB-API service."
    ::= { vRtrStatExtEntry 49 }

vRtrStatActiveRibApiV4Tunnels    OBJECT-TYPE
    SYNTAX      Gauge32
    MAX-ACCESS  read-only
    STATUS      current
    DESCRIPTION
        "vRtrStatActiveRibApiV4Tunnels indicates the current number of active
         IPv4 tunnels added by RIB-API service."
    ::= { vRtrStatExtEntry 50 }

vRtrStatTotalRibApiV6Tunnels     OBJECT-TYPE
    SYNTAX      Gauge32
    MAX-ACCESS  read-only
    STATUS      current
    DESCRIPTION
        "vRtrStatTotalRibApiV6Tunnels indicates the current number of both
         active and inactive IPv6 tunnels added by RIB-API service."
    ::= { vRtrStatExtEntry 51 }

vRtrStatActiveRibApiV6Tunnels    OBJECT-TYPE
    SYNTAX      Gauge32
    MAX-ACCESS  read-only
    STATUS      current
    DESCRIPTION
        "vRtrStatActiveRibApiV6Tunnels indicates the current number of active
         IPv6 tunnels added by RIB-API service."
    ::= { vRtrStatExtEntry 52 }

vRtrStatTotMplsFwdPlcyV4Tunnels  OBJECT-TYPE
    SYNTAX      Gauge32
    MAX-ACCESS  read-only
    STATUS      current
    DESCRIPTION
        "vRtrStatTotMplsFwdPlcyV4Tunnels indicates the current number of both
         active and inactive IPv4 tunnels added by MPLS Forward Policy service."
    ::= { vRtrStatExtEntry 53 }

vRtrStatActMplsFwdPlcyV4Tunnels  OBJECT-TYPE
    SYNTAX      Gauge32
    MAX-ACCESS  read-only
    STATUS      current
    DESCRIPTION
        "vRtrStatActMplsFwdPlcyV4Tunnels indicates the current number of both
         active IPv4 tunnels added by MPLS Forward Policy service."
    ::= { vRtrStatExtEntry 54 }

vRtrStatTotMplsFwdPlcyV6Tunnels  OBJECT-TYPE
    SYNTAX      Gauge32
    MAX-ACCESS  read-only
    STATUS      current
    DESCRIPTION
        "vRtrStatTotMplsFwdPlcyV6Tunnels indicates the current number of both
         active and inactive IPv6 tunnels added by MPLS Forward Policy service."
    ::= { vRtrStatExtEntry 55 }

vRtrStatActMplsFwdPlcyV6Tunnels  OBJECT-TYPE
    SYNTAX      Gauge32
    MAX-ACCESS  read-only
    STATUS      current
    DESCRIPTION
        "vRtrStatActMplsFwdPlcyV6Tunnels indicates the current number of both
         active IPv6 tunnels added by MPLS Forward Policy service."
    ::= { vRtrStatExtEntry 56 }

vRtrStatTotalOspfv3IPv6Tunnels   OBJECT-TYPE
    SYNTAX      Gauge32
    MAX-ACCESS  read-only
    STATUS      current
    DESCRIPTION
        "The value of vRtrStatTotalOspfv3IPv6Tunnels indicates the current
         number of active and inactive OSPFv3 IPv6 segment-routing tunnels."
    ::= { vRtrStatExtEntry 57 }

vRtrStatActiveOspfv3IPv6Tunnels  OBJECT-TYPE
    SYNTAX      Gauge32
    MAX-ACCESS  read-only
    STATUS      current
    DESCRIPTION
        "The value of vRtrStatActiveOspfv3IPv6Tunnels indicates the current
         number of active OSPFv3 IPv6 segment-routing tunnels."
    ::= { vRtrStatExtEntry 58 }

vRtrDHCPRoutes                   OBJECT-TYPE
    SYNTAX      Gauge32
    MAX-ACCESS  read-only
    STATUS      current
    DESCRIPTION
        "The value of vRtrDHCPRoutes indicates the current number of IPv4
         routes added by the DHCP client for this instance of the route table."
    ::= { vRtrStatExtEntry 59 }

vRtrDHCPActiveRoutes             OBJECT-TYPE
    SYNTAX      Gauge32
    MAX-ACCESS  read-only
    STATUS      current
    DESCRIPTION
        "The value of vRtrDHCPActiveRoutes indicates the current number of IPv4
         routes added by the DHCP client that are active for this instance of
         the route table."
    ::= { vRtrStatExtEntry 60 }

vRtrV6DHCPRoutes                 OBJECT-TYPE
    SYNTAX      Gauge32
    MAX-ACCESS  read-only
    STATUS      current
    DESCRIPTION
        "The value of vRtrV6DHCPRoutes indicates the current number of IPv6
         routes added by the DHCP client for this instance of the route table."
    ::= { vRtrStatExtEntry 61 }

vRtrV6DHCPActiveRoutes           OBJECT-TYPE
    SYNTAX      Gauge32
    MAX-ACCESS  read-only
    STATUS      current
    DESCRIPTION
        "The value of vRtrV6DHCPActiveRoutes indicates the current number of
         IPv6 routes added by the DHCP client that are active for this instance
         of the route table."
    ::= { vRtrStatExtEntry 62 }

vRtrStatActiveSrPolicyV6Tunnels  OBJECT-TYPE
    SYNTAX      Gauge32
    MAX-ACCESS  read-only
    STATUS      current
    DESCRIPTION
        "The value of vRtrStatActiveSrPolicyV6Tunnels indicates the current
         number of active IPv6 SR Policy tunnels."
    ::= { vRtrStatExtEntry 63 }

vRtrStatTotalSrPolicyV6Tunnels   OBJECT-TYPE
    SYNTAX      Gauge32
    MAX-ACCESS  read-only
    STATUS      current
    DESCRIPTION
        "The value of vRtrStatTotalSrPolicyV6Tunnels indicates the current
         number of active and inactive IPv6 SR Policy tunnels."
    ::= { vRtrStatExtEntry 64 }

vRtrStatTotalSrTeV6Tunnels       OBJECT-TYPE
    SYNTAX      Gauge32
    MAX-ACCESS  read-only
    STATUS      current
    DESCRIPTION
        "vRtrStatTotalSrTeV6Tunnels indicates the current number of both active
         and inactive SR-TE V6 tunnels."
    ::= { vRtrStatExtEntry 65 }

vRtrStatActiveSrTeV6Tunnels      OBJECT-TYPE
    SYNTAX      Gauge32
    MAX-ACCESS  read-only
    STATUS      current
    DESCRIPTION
        "vRtrStatActiveSrTeV6Tunnels indicates the current number of active
         SR-TE V6 tunnels."
    ::= { vRtrStatExtEntry 66 }

vRtrBgpEvpnIflRoutes             OBJECT-TYPE
    SYNTAX      Gauge32
    MAX-ACCESS  read-only
    STATUS      current
    DESCRIPTION
        "The value of vRtrBgpEvpnIflRoutes indicates the current number of
         BGP-EVPN IFL routes for this instance of the route table."
    ::= { vRtrStatExtEntry 67 }

vRtrBgpEvpnIflActRoutes          OBJECT-TYPE
    SYNTAX      Gauge32
    MAX-ACCESS  read-only
    STATUS      current
    DESCRIPTION
        "The value of vRtrBgpEvpnIflActRoutes indicates the current number of
         BGP-EVPN IFL routes that are active for this instance of the route
         table."
    ::= { vRtrStatExtEntry 68 }

vRtrBgpEvpnIflAltRoutes          OBJECT-TYPE
    SYNTAX      Gauge32
    MAX-ACCESS  read-only
    STATUS      current
    DESCRIPTION
        "The value of vRtrBgpEvpnIflAltRoutes indicates the current number of
         alternate BGP-EVPN IFL routes for this instance of the route table."
    ::= { vRtrStatExtEntry 69 }

vRtrBgpEvpnIflActAltRoutes       OBJECT-TYPE
    SYNTAX      Gauge32
    MAX-ACCESS  read-only
    STATUS      current
    DESCRIPTION
        "The value of vRtrBgpEvpnIflActAltRoutes indicates the current number
         of alternate BGP-EVPN IFL routes that are active for this instance of
         the route table."
    ::= { vRtrStatExtEntry 70 }

vRtrV6BgpEvpnIflRoutes           OBJECT-TYPE
    SYNTAX      Gauge32
    MAX-ACCESS  read-only
    STATUS      current
    DESCRIPTION
        "The value of vRtrV6BgpEvpnIflRoutes indicates the current number of
         ipv6 BGP-EVPN IFL routes for this instance of the route table."
    ::= { vRtrStatExtEntry 71 }

vRtrV6BgpEvpnIflActRoutes        OBJECT-TYPE
    SYNTAX      Gauge32
    MAX-ACCESS  read-only
    STATUS      current
    DESCRIPTION
        "The value of vRtrV6BgpEvpnIflActRoutes indicates the current number of
         ipv6 BGP-EVPN IFL routes that are active for this instance of the
         route table."
    ::= { vRtrStatExtEntry 72 }

vRtrV6BgpEvpnIflAltRoutes        OBJECT-TYPE
    SYNTAX      Gauge32
    MAX-ACCESS  read-only
    STATUS      current
    DESCRIPTION
        "The value of vRtrV6BgpEvpnIflAltRoutes indicates the current number of
         ipv6 alternate BGP-EVPN IFL routes for this instance of the route
         table."
    ::= { vRtrStatExtEntry 73 }

vRtrV6BgpEvpnIflActAltRoutes     OBJECT-TYPE
    SYNTAX      Gauge32
    MAX-ACCESS  read-only
    STATUS      current
    DESCRIPTION
        "The value of vRtrV6BgpEvpnIflActAltRoutes indicates the current number
         of ipv6 alternate BGP-EVPN IFL routes that are active for this
         instance of the route table."
    ::= { vRtrStatExtEntry 74 }

vRtrBgpEvpnIffRoutes             OBJECT-TYPE
    SYNTAX      Gauge32
    MAX-ACCESS  read-only
    STATUS      current
    DESCRIPTION
        "The value of vRtrBgpEvpnIffRoutes indicates the total number of IPv4
         EVPN IFF route entries for the specified virtual router in the system.

         vRtrBgpEvpnIffRoutes replaces vRtrStatBGPEvpnRoutes in SR Release
         20.10."
    ::= { vRtrStatExtEntry 75 }

vRtrBgpEvpnIffActRoutes          OBJECT-TYPE
    SYNTAX      Gauge32
    MAX-ACCESS  read-only
    STATUS      current
    DESCRIPTION
        "The value of vRtrBgpEvpnIffActRoutes indicates the total number of
         active IPv4 EVPN IFF route entries for the specified virtual router in
         the system.

         vRtrBgpEvpnIffActRoutes replaces vRtrStatBGPEvpnActiveRoutes in SR
         Release 20.10."
    ::= { vRtrStatExtEntry 76 }

vRtrV6BgpEvpnIffRoutes           OBJECT-TYPE
    SYNTAX      Gauge32
    MAX-ACCESS  read-only
    STATUS      current
    DESCRIPTION
        "The value of vRtrV6BgpEvpnIffRoutes indicates the total number of IPv6
         EVPN IFF route entries for the specified virtual router in the system.

         vRtrV6BgpEvpnIffRoutes replaces vRtrV6StatBGPEvpnRoutes in SR Release
         20.10."
    ::= { vRtrStatExtEntry 77 }

vRtrV6BgpEvpnIffActRoutes        OBJECT-TYPE
    SYNTAX      Gauge32
    MAX-ACCESS  read-only
    STATUS      current
    DESCRIPTION
        "The value of vRtrV6BgpEvpnIffActRoutes indicates the total number of
         active IPv6 EVPN IFF route entries for the specified virtual router in
         the system.

         vRtrV6BgpEvpnIffActRoutes replaces vRtrV6StatBGPEvpnActiveRoutes in SR
         Release 20.10."
    ::= { vRtrStatExtEntry 78 }

vRtrMtrace2OperState             OBJECT-TYPE
    SYNTAX      TmnxEnabledDisabled
    MAX-ACCESS  read-only
    STATUS      current
    DESCRIPTION
        "The value of vRtrMtrace2OperState indicates whether or not
         1.  Launching a UDP-based IP multicast traceroute test (i.e. an
         mtrace2 test) is operationally enabled for the specified router, and
         2.  Listening for an unsolicited mtrace2 test packet is
         operationally enabled for the specified router.

         An mtrace2 test is launched with
         TIMETRA-OAM-TEST-MIB::tmnxOamMcastTrCtlTestSubMode set to
         'mcastTraceRouteV2(2)'.

         When this object is 'enabled(1)', the UDP port specified by
         vRtrMtrace2UdpPort is open for use by mtrace2.

         When this object is 'disabled(2)', the UDP port specified by
         vRtrMtrace2UdpPort is not open for use by mtrace2.

         For example, the following combination can occur if the UDP port
         specified by vRtrMtrace2UdpPort is unavailable for mtrace2:
             vRtrMtrace2AdminState = inService(2)
             vRtrMtrace2OperState  = disabled(2)."
    REFERENCE
        "IETF draft-ietf-mboned-mtrace-v2-17, 'Mtrace Version 2: Traceroute
         Facility for IP Multicast', 12-Mar-2017."
    ::= { vRtrStatExtEntry 79 }

vRtrStatActiveSrV6IsisTunnels    OBJECT-TYPE
    SYNTAX      Gauge32
    MAX-ACCESS  read-only
    STATUS      current
    DESCRIPTION
        "vRtrStatActiveSrV6IsisTunnels indicates the current number of both
         active and inactive SR V6 ISIS tunnels."
    ::= { vRtrStatExtEntry 80 }

vRtrStatTotalSrV6IsisTunnels     OBJECT-TYPE
    SYNTAX      Gauge32
    MAX-ACCESS  read-only
    STATUS      current
    DESCRIPTION
        "vRtrStatTotalSrV6IsisTunnels indicates the current number of total SR
         V6 ISIS tunnels."
    ::= { vRtrStatExtEntry 81 }

vRtrStatSrV6ActiveRoutes         OBJECT-TYPE
    SYNTAX      Gauge32
    MAX-ACCESS  read-only
    STATUS      current
    DESCRIPTION
        "vRtrStatSrV6ActiveRoutes indicates the current number of active SR V6
         routes."
    ::= { vRtrStatExtEntry 82 }

vRtrStatSrV6TotalRoutes          OBJECT-TYPE
    SYNTAX      Gauge32
    MAX-ACCESS  read-only
    STATUS      current
    DESCRIPTION
        "vRtrStatSrV6TotalRoutes indicates the current number of total SR V6
         routes."
    ::= { vRtrStatExtEntry 83 }

vRtrStatActiveSrV6PolicyTunnels  OBJECT-TYPE
    SYNTAX      Gauge32
    MAX-ACCESS  read-only
    STATUS      current
    DESCRIPTION
        "vRtrStatActiveSrV6PolicyTunnels indicates the current number of both
         active and inactive SR V6 Policy tunnels."
    ::= { vRtrStatExtEntry 84 }

vRtrStatTotalSrV6PolicyTunnels   OBJECT-TYPE
    SYNTAX      Gauge32
    MAX-ACCESS  read-only
    STATUS      current
    DESCRIPTION
        "vRtrStatTotalSrV6PolicyTunnels indicates the current number of total
         SR V6 Policy tunnels."
    ::= { vRtrStatExtEntry 85 }

vRtrStatActiveSrV6PolicyRoutes   OBJECT-TYPE
    SYNTAX      Gauge32
    MAX-ACCESS  read-only
    STATUS      current
    DESCRIPTION
        "vRtrStatActiveSrV6PolicyRoutes indicates the current number of both
         active and inactive SR V6 Policy routes."
    ::= { vRtrStatExtEntry 86 }

vRtrStatTotalSrV6PolicyRoutes    OBJECT-TYPE
    SYNTAX      Gauge32
    MAX-ACCESS  read-only
    STATUS      current
    DESCRIPTION
        "vRtrStatTotalSrV6PolicyRoutes indicates the current number of total SR
         V6 Policy routes."
    ::= { vRtrStatExtEntry 87 }

vRtrStatActiveV4VideoRoutes      OBJECT-TYPE
    SYNTAX      Gauge32
    MAX-ACCESS  read-only
    STATUS      current
    DESCRIPTION
        "vRtrStatActiveV4VideoRoutes indicates the current number of both
         active and inactive IPv4 video routes."
    ::= { vRtrStatExtEntry 88 }

vRtrStatTotalV4VideoRoutes       OBJECT-TYPE
    SYNTAX      Gauge32
    MAX-ACCESS  read-only
    STATUS      current
    DESCRIPTION
        "vRtrStatTotalV4VideoRoutes indicates the current number of total IPv4
         video routes."
    ::= { vRtrStatExtEntry 89 }

vRtrStatActiveV6VideoRoutes      OBJECT-TYPE
    SYNTAX      Gauge32
    MAX-ACCESS  read-only
    STATUS      current
    DESCRIPTION
        "vRtrStatActiveV6VideoRoutes indicates the current number of both
         active and inactive IPv6 video routes."
    ::= { vRtrStatExtEntry 90 }

vRtrStatTotalV6VideoRoutes       OBJECT-TYPE
    SYNTAX      Gauge32
    MAX-ACCESS  read-only
    STATUS      current
    DESCRIPTION
        "vRtrStatTotalV6VideoRoutes indicates the current number of total IPv6
         video routes."
    ::= { vRtrStatExtEntry 91 }

vRtrMcastIpv4ActiveVideoRoutes   OBJECT-TYPE
    SYNTAX      Gauge32
    MAX-ACCESS  read-only
    STATUS      current
    DESCRIPTION
        "The value of vRtrMcastIpv4ActiveVideoRoutes indicates the number of
         active and inactive IPv4 Multicast Video route entries for  the
         specified virtual router in the system."
    ::= { vRtrStatExtEntry 92 }

vRtrMcastIpv4TotalVideoRoutes    OBJECT-TYPE
    SYNTAX      Gauge32
    MAX-ACCESS  read-only
    STATUS      current
    DESCRIPTION
        "The value of vRtrMcastIpv4TotalVideoRoutes indicates the number of
         total IPv4 Multicast Video route entries for the specified virtual
         router in the system."
    ::= { vRtrStatExtEntry 93 }

vRtrMcastIpv6ActiveVideoRoutes   OBJECT-TYPE
    SYNTAX      Gauge32
    MAX-ACCESS  read-only
    STATUS      current
    DESCRIPTION
        "The value of vRtrMcastIpv6ActiveVideoRoutes indicates the number of
         active and inactive IPv6 Multicast Video route entries for the
         specified virtual router in the system."
    ::= { vRtrStatExtEntry 94 }

vRtrMcastIpv6TotalVideoRoutes    OBJECT-TYPE
    SYNTAX      Gauge32
    MAX-ACCESS  read-only
    STATUS      current
    DESCRIPTION
        "The value of vRtrMcastIpv6TotalVideoRoutes indicates the number of
         total IPv6 Multicast Video route entries for  the specified virtual
         router in the system."
    ::= { vRtrStatExtEntry 95 }

vRtrStatV6NdRaRoutes             OBJECT-TYPE
    SYNTAX      Gauge32
    MAX-ACCESS  read-only
    STATUS      current
    DESCRIPTION
        "The value of vRtrStatV6NdRaRoutes indicates the current number of IPv6
         ND-RA routes for this instance of the route table."
    ::= { vRtrStatExtEntry 96 }

vRtrStatV6NdRaActiveRoutes       OBJECT-TYPE
    SYNTAX      Gauge32
    MAX-ACCESS  read-only
    STATUS      current
    DESCRIPTION
        "The value of vRtrStatV6NdRaActiveRoutes indicates the current number
         of IPv6 active ND-RA routes for this instance of the route table."
    ::= { vRtrStatExtEntry 97 }

vRtrStatActiveV4EsmBcastRoutes   OBJECT-TYPE
    SYNTAX      Gauge32
    MAX-ACCESS  read-only
    STATUS      current
    DESCRIPTION
        "vRtrStatActiveV4EsmBcastRoutes indicates the current number of both
         active and inactive IPv4 ESM Broadcast routes."
    ::= { vRtrStatExtEntry 98 }

vRtrStatTotalV4EsmBcastRoutes    OBJECT-TYPE
    SYNTAX      Gauge32
    MAX-ACCESS  read-only
    STATUS      current
    DESCRIPTION
        "vRtrStatTotalV4EsmBcastRoutes indicates the current number of total
         IPv4 ESM Broadcast routes."
    ::= { vRtrStatExtEntry 99 }

vRtrBgpEvpnIflHostRoutes         OBJECT-TYPE
    SYNTAX      Gauge32
    MAX-ACCESS  read-only
    STATUS      current
    DESCRIPTION
        "The value of vRtrBgpEvpnIflHostRoutes indicates the total number of
         IPv4 EVPN IFL HOST route entries for the specified virtual router in
         the system."
    ::= { vRtrStatExtEntry 100 }

vRtrBgpEvpnIflHostActRoutes      OBJECT-TYPE
    SYNTAX      Gauge32
    MAX-ACCESS  read-only
    STATUS      current
    DESCRIPTION
        "The value of vRtrBgpEvpnIflHostActRoutes indicates the total number of
         active IPv4 EVPN IFL HOST route entries for the specified virtual
         router in the system."
    ::= { vRtrStatExtEntry 101 }

vRtrV6BgpEvpnIflHostRoutes       OBJECT-TYPE
    SYNTAX      Gauge32
    MAX-ACCESS  read-only
    STATUS      current
    DESCRIPTION
        "The value of vRtrV6BgpEvpnIflHostRoutes indicates the total number of
         IPv6 EVPN IFL HOST route entries for the specified virtual router in
         the system."
    ::= { vRtrStatExtEntry 102 }

vRtrV6BgpEvpnIflHostActRoutes    OBJECT-TYPE
    SYNTAX      Gauge32
    MAX-ACCESS  read-only
    STATUS      current
    DESCRIPTION
        "The value of vRtrV6BgpEvpnIflHostActRoutes indicates the total number
         of active IPv6 EVPN IFL HOST route entries for the specified virtual
         router in the system."
    ::= { vRtrStatExtEntry 103 }

vRtrVrfPolicyTable               OBJECT-TYPE
    SYNTAX      SEQUENCE OF VRtrVrfPolicyEntry
    MAX-ACCESS  not-accessible
    STATUS      current
    DESCRIPTION
        "The vRtrVrfPolicyTable has an entry for each virtual router configured
         in the system."
    ::= { tmnxVRtrObjs 76 }

vRtrVrfPolicyEntry               OBJECT-TYPE
    SYNTAX      VRtrVrfPolicyEntry
    MAX-ACCESS  not-accessible
    STATUS      current
    DESCRIPTION
        "Each row entry represents a collection of policies for a virtual
         router in the system.

         Entries cannot be created and deleted via SNMP SET operations."
    AUGMENTS    { vRtrConfEntry }
    ::= { vRtrVrfPolicyTable 1 }

VRtrVrfPolicyEntry               ::= SEQUENCE
{
    vRtrVrfImportPolicy1             TXLPolicyNameOrExpOrEmpty,
    vRtrVrfImportPolicy2             TLPolicyNameOrExpOrEmpty,
    vRtrVrfImportPolicy3             TLPolicyNameOrExpOrEmpty,
    vRtrVrfImportPolicy4             TLPolicyNameOrExpOrEmpty,
    vRtrVrfImportPolicy5             TLPolicyNameOrExpOrEmpty,
    vRtrVrfImportPolicy6             TLPolicyNameOrExpOrEmpty,
    vRtrVrfImportPolicy7             TLPolicyNameOrExpOrEmpty,
    vRtrVrfImportPolicy8             TLPolicyNameOrExpOrEmpty,
    vRtrVrfImportPolicy9             TLPolicyNameOrExpOrEmpty,
    vRtrVrfImportPolicy10            TLPolicyNameOrExpOrEmpty,
    vRtrVrfImportPolicy11            TLPolicyNameOrExpOrEmpty,
    vRtrVrfImportPolicy12            TLPolicyNameOrExpOrEmpty,
    vRtrVrfImportPolicy13            TLPolicyNameOrExpOrEmpty,
    vRtrVrfImportPolicy14            TLPolicyNameOrExpOrEmpty,
    vRtrVrfImportPolicy15            TLPolicyNameOrExpOrEmpty,
    vRtrVrfExportPolicy1             TXLPolicyNameOrExpOrEmpty,
    vRtrVrfExportPolicy2             TLPolicyNameOrExpOrEmpty,
    vRtrVrfExportPolicy3             TLPolicyNameOrExpOrEmpty,
    vRtrVrfExportPolicy4             TLPolicyNameOrExpOrEmpty,
    vRtrVrfExportPolicy5             TLPolicyNameOrExpOrEmpty,
    vRtrVrfExportPolicy6             TLPolicyNameOrExpOrEmpty,
    vRtrVrfExportPolicy7             TLPolicyNameOrExpOrEmpty,
    vRtrVrfExportPolicy8             TLPolicyNameOrExpOrEmpty,
    vRtrVrfExportPolicy9             TLPolicyNameOrExpOrEmpty,
    vRtrVrfExportPolicy10            TLPolicyNameOrExpOrEmpty,
    vRtrVrfExportPolicy11            TLPolicyNameOrExpOrEmpty,
    vRtrVrfExportPolicy12            TLPolicyNameOrExpOrEmpty,
    vRtrVrfExportPolicy13            TLPolicyNameOrExpOrEmpty,
    vRtrVrfExportPolicy14            TLPolicyNameOrExpOrEmpty,
    vRtrVrfExportPolicy15            TLPolicyNameOrExpOrEmpty,
    vRtrVrfPlcyCreationOrigin        TmnxCreateOrigin
}

vRtrVrfImportPolicy1             OBJECT-TYPE
    SYNTAX      TXLPolicyNameOrExpOrEmpty
    MAX-ACCESS  read-create
    STATUS      current
    DESCRIPTION
        "The value of vRtrVrfImportPolicy1 specifies the first
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 1 }

vRtrVrfImportPolicy2             OBJECT-TYPE
    SYNTAX      TLPolicyNameOrExpOrEmpty
    MAX-ACCESS  read-create
    STATUS      current
    DESCRIPTION
        "The value of vRtrVrfImportPolicy2 specifies the second
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 2 }

vRtrVrfImportPolicy3             OBJECT-TYPE
    SYNTAX      TLPolicyNameOrExpOrEmpty
    MAX-ACCESS  read-create
    STATUS      current
    DESCRIPTION
        "The value of vRtrVrfImportPolicy3 specifies the third
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 3 }

vRtrVrfImportPolicy4             OBJECT-TYPE
    SYNTAX      TLPolicyNameOrExpOrEmpty
    MAX-ACCESS  read-create
    STATUS      current
    DESCRIPTION
        "The value of vRtrVrfImportPolicy4 specifies the fourth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 4 }

vRtrVrfImportPolicy5             OBJECT-TYPE
    SYNTAX      TLPolicyNameOrExpOrEmpty
    MAX-ACCESS  read-create
    STATUS      current
    DESCRIPTION
        "The value of vRtrVrfImportPolicy5 specifies the fifth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 5 }

vRtrVrfImportPolicy6             OBJECT-TYPE
    SYNTAX      TLPolicyNameOrExpOrEmpty
    MAX-ACCESS  read-create
    STATUS      current
    DESCRIPTION
        "The value of vRtrVrfImportPolicy6 specifies the sixth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 6 }

vRtrVrfImportPolicy7             OBJECT-TYPE
    SYNTAX      TLPolicyNameOrExpOrEmpty
    MAX-ACCESS  read-create
    STATUS      current
    DESCRIPTION
        "The value of vRtrVrfImportPolicy7 specifies the seventh
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 7 }

vRtrVrfImportPolicy8             OBJECT-TYPE
    SYNTAX      TLPolicyNameOrExpOrEmpty
    MAX-ACCESS  read-create
    STATUS      current
    DESCRIPTION
        "The value of vRtrVrfImportPolicy8 specifies the eighth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 8 }

vRtrVrfImportPolicy9             OBJECT-TYPE
    SYNTAX      TLPolicyNameOrExpOrEmpty
    MAX-ACCESS  read-create
    STATUS      current
    DESCRIPTION
        "The value of vRtrVrfImportPolicy9 specifies the ninth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 9 }

vRtrVrfImportPolicy10            OBJECT-TYPE
    SYNTAX      TLPolicyNameOrExpOrEmpty
    MAX-ACCESS  read-create
    STATUS      current
    DESCRIPTION
        "The value of vRtrVrfImportPolicy10 specifies the tenth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 10 }

vRtrVrfImportPolicy11            OBJECT-TYPE
    SYNTAX      TLPolicyNameOrExpOrEmpty
    MAX-ACCESS  read-create
    STATUS      current
    DESCRIPTION
        "The value of vRtrVrfImportPolicy11 specifies the eleventh
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 11 }

vRtrVrfImportPolicy12            OBJECT-TYPE
    SYNTAX      TLPolicyNameOrExpOrEmpty
    MAX-ACCESS  read-create
    STATUS      current
    DESCRIPTION
        "The value of vRtrVrfImportPolicy12 specifies the twelfth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 12 }

vRtrVrfImportPolicy13            OBJECT-TYPE
    SYNTAX      TLPolicyNameOrExpOrEmpty
    MAX-ACCESS  read-create
    STATUS      current
    DESCRIPTION
        "The value of vRtrVrfImportPolicy13 specifies the thirteenth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 13 }

vRtrVrfImportPolicy14            OBJECT-TYPE
    SYNTAX      TLPolicyNameOrExpOrEmpty
    MAX-ACCESS  read-create
    STATUS      current
    DESCRIPTION
        "The value of vRtrVrfImportPolicy14 specifies the fourteenth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 14 }

vRtrVrfImportPolicy15            OBJECT-TYPE
    SYNTAX      TLPolicyNameOrExpOrEmpty
    MAX-ACCESS  read-create
    STATUS      current
    DESCRIPTION
        "The value of vRtrVrfImportPolicy15 specifies the fifteenth
         policy to be used for determining which routes are imported
         into the VRF for this virtual router.  If no import policy
         is defined, no routes are accepted into the VRF.

         If multiple policy names are specified, the policies are evaluated
         in the order they are specified.  The first policy that matches
         is applied.

         The import policy name list, vRtrVrfImportPolicy1 through
         vRtrVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 15 }

vRtrVrfExportPolicy1             OBJECT-TYPE
    SYNTAX      TXLPolicyNameOrExpOrEmpty
    MAX-ACCESS  read-create
    STATUS      current
    DESCRIPTION
        "The value of vRtrVrfExportPolicy1 specifies the first
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 16 }

vRtrVrfExportPolicy2             OBJECT-TYPE
    SYNTAX      TLPolicyNameOrExpOrEmpty
    MAX-ACCESS  read-create
    STATUS      current
    DESCRIPTION
        "The value of vRtrVrfExportPolicy2 specifies the second
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 17 }

vRtrVrfExportPolicy3             OBJECT-TYPE
    SYNTAX      TLPolicyNameOrExpOrEmpty
    MAX-ACCESS  read-create
    STATUS      current
    DESCRIPTION
        "The value of vRtrVrfExportPolicy3 specifies the third
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 18 }

vRtrVrfExportPolicy4             OBJECT-TYPE
    SYNTAX      TLPolicyNameOrExpOrEmpty
    MAX-ACCESS  read-create
    STATUS      current
    DESCRIPTION
        "The value of vRtrVrfExportPolicy4 specifies the fourth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 19 }

vRtrVrfExportPolicy5             OBJECT-TYPE
    SYNTAX      TLPolicyNameOrExpOrEmpty
    MAX-ACCESS  read-create
    STATUS      current
    DESCRIPTION
        "The value of vRtrVrfExportPolicy5 specifies the fifth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 20 }

vRtrVrfExportPolicy6             OBJECT-TYPE
    SYNTAX      TLPolicyNameOrExpOrEmpty
    MAX-ACCESS  read-create
    STATUS      current
    DESCRIPTION
        "The value of vRtrVrfExportPolicy6 specifies the sixth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 21 }

vRtrVrfExportPolicy7             OBJECT-TYPE
    SYNTAX      TLPolicyNameOrExpOrEmpty
    MAX-ACCESS  read-create
    STATUS      current
    DESCRIPTION
        "The value of vRtrVrfExportPolicy7 specifies the seventh
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 22 }

vRtrVrfExportPolicy8             OBJECT-TYPE
    SYNTAX      TLPolicyNameOrExpOrEmpty
    MAX-ACCESS  read-create
    STATUS      current
    DESCRIPTION
        "The value of vRtrVrfExportPolicy8 specifies the eighth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 23 }

vRtrVrfExportPolicy9             OBJECT-TYPE
    SYNTAX      TLPolicyNameOrExpOrEmpty
    MAX-ACCESS  read-create
    STATUS      current
    DESCRIPTION
        "The value of vRtrVrfExportPolicy9 specifies the ninth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 24 }

vRtrVrfExportPolicy10            OBJECT-TYPE
    SYNTAX      TLPolicyNameOrExpOrEmpty
    MAX-ACCESS  read-create
    STATUS      current
    DESCRIPTION
        "The value of vRtrVrfExportPolicy10 specifies the tenth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 25 }

vRtrVrfExportPolicy11            OBJECT-TYPE
    SYNTAX      TLPolicyNameOrExpOrEmpty
    MAX-ACCESS  read-create
    STATUS      current
    DESCRIPTION
        "The value of vRtrVrfExportPolicy11 specifies the eleventh
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 26 }

vRtrVrfExportPolicy12            OBJECT-TYPE
    SYNTAX      TLPolicyNameOrExpOrEmpty
    MAX-ACCESS  read-create
    STATUS      current
    DESCRIPTION
        "The value of vRtrVrfExportPolicy12 specifies the twelfth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 27 }

vRtrVrfExportPolicy13            OBJECT-TYPE
    SYNTAX      TLPolicyNameOrExpOrEmpty
    MAX-ACCESS  read-create
    STATUS      current
    DESCRIPTION
        "The value of vRtrVrfExportPolicy13 specifies the thirteenth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 28 }

vRtrVrfExportPolicy14            OBJECT-TYPE
    SYNTAX      TLPolicyNameOrExpOrEmpty
    MAX-ACCESS  read-create
    STATUS      current
    DESCRIPTION
        "The value of vRtrVrfExportPolicy14 specifies the fourteenth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 29 }

vRtrVrfExportPolicy15            OBJECT-TYPE
    SYNTAX      TLPolicyNameOrExpOrEmpty
    MAX-ACCESS  read-create
    STATUS      current
    DESCRIPTION
        "The value of vRtrVrfExportPolicy15 specifies the fifteenth
         policy to be used for determining which routes are exported
         from the VRF for this virtual router.  If no export policy
         is defined, no routes are exported from the VRF.

         If multiple policy names are specified, the policies are evaluated
         in the order they are specified.  The first policy that matches
         is applied.

         The export policy name list, vRtrVrfExportPolicy1 through
         vRtrVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrVrfPolicyEntry 30 }

vRtrVrfPlcyCreationOrigin        OBJECT-TYPE
    SYNTAX      TmnxCreateOrigin
    MAX-ACCESS  read-only
    STATUS      current
    DESCRIPTION
        "The value of vRtrVrfPlcyCreationOrigin indicates the mechanism used to
         create this entry."
    DEFVAL      { manual }
    ::= { vRtrVrfPolicyEntry 31 }

vRtrMvpnVrfPolicyTable           OBJECT-TYPE
    SYNTAX      SEQUENCE OF VRtrMvpnVrfPolicyEntry
    MAX-ACCESS  not-accessible
    STATUS      current
    DESCRIPTION
        "The vRtrMvpnVrfPolicyTable has an entry for each virtual router
         configured in the system."
    ::= { tmnxVRtrObjs 77 }

vRtrMvpnVrfPolicyEntry           OBJECT-TYPE
    SYNTAX      VRtrMvpnVrfPolicyEntry
    MAX-ACCESS  not-accessible
    STATUS      current
    DESCRIPTION
        "Each row entry represents a collection of policies for a virtual
         router in the system.

         Entries cannot be created and deleted via SNMP SET operations."
    AUGMENTS    { vRtrConfEntry }
    ::= { vRtrMvpnVrfPolicyTable 1 }

VRtrMvpnVrfPolicyEntry           ::= SEQUENCE
{
    vRtrMvpnVrfImportPolicy1         TXLPolicyNameOrExpOrEmpty,
    vRtrMvpnVrfImportPolicy2         TLPolicyNameOrExpOrEmpty,
    vRtrMvpnVrfImportPolicy3         TLPolicyNameOrExpOrEmpty,
    vRtrMvpnVrfImportPolicy4         TLPolicyNameOrExpOrEmpty,
    vRtrMvpnVrfImportPolicy5         TLPolicyNameOrExpOrEmpty,
    vRtrMvpnVrfImportPolicy6         TLPolicyNameOrExpOrEmpty,
    vRtrMvpnVrfImportPolicy7         TLPolicyNameOrExpOrEmpty,
    vRtrMvpnVrfImportPolicy8         TLPolicyNameOrExpOrEmpty,
    vRtrMvpnVrfImportPolicy9         TLPolicyNameOrExpOrEmpty,
    vRtrMvpnVrfImportPolicy10        TLPolicyNameOrExpOrEmpty,
    vRtrMvpnVrfImportPolicy11        TLPolicyNameOrExpOrEmpty,
    vRtrMvpnVrfImportPolicy12        TLPolicyNameOrExpOrEmpty,
    vRtrMvpnVrfImportPolicy13        TLPolicyNameOrExpOrEmpty,
    vRtrMvpnVrfImportPolicy14        TLPolicyNameOrExpOrEmpty,
    vRtrMvpnVrfImportPolicy15        TLPolicyNameOrExpOrEmpty,
    vRtrMvpnVrfExportPolicy1         TXLPolicyNameOrExpOrEmpty,
    vRtrMvpnVrfExportPolicy2         TLPolicyNameOrExpOrEmpty,
    vRtrMvpnVrfExportPolicy3         TLPolicyNameOrExpOrEmpty,
    vRtrMvpnVrfExportPolicy4         TLPolicyNameOrExpOrEmpty,
    vRtrMvpnVrfExportPolicy5         TLPolicyNameOrExpOrEmpty,
    vRtrMvpnVrfExportPolicy6         TLPolicyNameOrExpOrEmpty,
    vRtrMvpnVrfExportPolicy7         TLPolicyNameOrExpOrEmpty,
    vRtrMvpnVrfExportPolicy8         TLPolicyNameOrExpOrEmpty,
    vRtrMvpnVrfExportPolicy9         TLPolicyNameOrExpOrEmpty,
    vRtrMvpnVrfExportPolicy10        TLPolicyNameOrExpOrEmpty,
    vRtrMvpnVrfExportPolicy11        TLPolicyNameOrExpOrEmpty,
    vRtrMvpnVrfExportPolicy12        TLPolicyNameOrExpOrEmpty,
    vRtrMvpnVrfExportPolicy13        TLPolicyNameOrExpOrEmpty,
    vRtrMvpnVrfExportPolicy14        TLPolicyNameOrExpOrEmpty,
    vRtrMvpnVrfExportPolicy15        TLPolicyNameOrExpOrEmpty
}

vRtrMvpnVrfImportPolicy1         OBJECT-TYPE
    SYNTAX      TXLPolicyNameOrExpOrEmpty
    MAX-ACCESS  read-create
    STATUS      current
    DESCRIPTION
        "The value of vRtrMvpnVrfImportPolicy1 specifies the first
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 1 }

vRtrMvpnVrfImportPolicy2         OBJECT-TYPE
    SYNTAX      TLPolicyNameOrExpOrEmpty
    MAX-ACCESS  read-create
    STATUS      current
    DESCRIPTION
        "The value of vRtrMvpnVrfImportPolicy2 specifies the second
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 2 }

vRtrMvpnVrfImportPolicy3         OBJECT-TYPE
    SYNTAX      TLPolicyNameOrExpOrEmpty
    MAX-ACCESS  read-create
    STATUS      current
    DESCRIPTION
        "The value of vRtrMvpnVrfImportPolicy3 specifies the third
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 3 }

vRtrMvpnVrfImportPolicy4         OBJECT-TYPE
    SYNTAX      TLPolicyNameOrExpOrEmpty
    MAX-ACCESS  read-create
    STATUS      current
    DESCRIPTION
        "The value of vRtrMvpnVrfImportPolicy4 specifies the fourth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 4 }

vRtrMvpnVrfImportPolicy5         OBJECT-TYPE
    SYNTAX      TLPolicyNameOrExpOrEmpty
    MAX-ACCESS  read-create
    STATUS      current
    DESCRIPTION
        "The value of vRtrMvpnVrfImportPolicy5 specifies the fifth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 5 }

vRtrMvpnVrfImportPolicy6         OBJECT-TYPE
    SYNTAX      TLPolicyNameOrExpOrEmpty
    MAX-ACCESS  read-create
    STATUS      current
    DESCRIPTION
        "The value of vRtrMvpnVrfImportPolicy6 specifies the sixth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 6 }

vRtrMvpnVrfImportPolicy7         OBJECT-TYPE
    SYNTAX      TLPolicyNameOrExpOrEmpty
    MAX-ACCESS  read-create
    STATUS      current
    DESCRIPTION
        "The value of vRtrMvpnVrfImportPolicy7 specifies the seventh
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 7 }

vRtrMvpnVrfImportPolicy8         OBJECT-TYPE
    SYNTAX      TLPolicyNameOrExpOrEmpty
    MAX-ACCESS  read-create
    STATUS      current
    DESCRIPTION
        "The value of vRtrMvpnVrfImportPolicy8 specifies the eighth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 8 }

vRtrMvpnVrfImportPolicy9         OBJECT-TYPE
    SYNTAX      TLPolicyNameOrExpOrEmpty
    MAX-ACCESS  read-create
    STATUS      current
    DESCRIPTION
        "The value of vRtrMvpnVrfImportPolicy9 specifies the ninth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 9 }

vRtrMvpnVrfImportPolicy10        OBJECT-TYPE
    SYNTAX      TLPolicyNameOrExpOrEmpty
    MAX-ACCESS  read-create
    STATUS      current
    DESCRIPTION
        "The value of vRtrMvpnVrfImportPolicy10 specifies the tenth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 10 }

vRtrMvpnVrfImportPolicy11        OBJECT-TYPE
    SYNTAX      TLPolicyNameOrExpOrEmpty
    MAX-ACCESS  read-create
    STATUS      current
    DESCRIPTION
        "The value of vRtrMvpnVrfImportPolicy11 specifies the eleventh
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 11 }

vRtrMvpnVrfImportPolicy12        OBJECT-TYPE
    SYNTAX      TLPolicyNameOrExpOrEmpty
    MAX-ACCESS  read-create
    STATUS      current
    DESCRIPTION
        "The value of vRtrMvpnVrfImportPolicy12 specifies the twelfth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 12 }

vRtrMvpnVrfImportPolicy13        OBJECT-TYPE
    SYNTAX      TLPolicyNameOrExpOrEmpty
    MAX-ACCESS  read-create
    STATUS      current
    DESCRIPTION
        "The value of vRtrMvpnVrfImportPolicy13 specifies the thirteenth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 13 }

vRtrMvpnVrfImportPolicy14        OBJECT-TYPE
    SYNTAX      TLPolicyNameOrExpOrEmpty
    MAX-ACCESS  read-create
    STATUS      current
    DESCRIPTION
        "The value of vRtrMvpnVrfImportPolicy14 specifies the fourteenth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 14 }

vRtrMvpnVrfImportPolicy15        OBJECT-TYPE
    SYNTAX      TLPolicyNameOrExpOrEmpty
    MAX-ACCESS  read-create
    STATUS      current
    DESCRIPTION
        "The value of vRtrMvpnVrfImportPolicy15 specifies the fifteenth
         policy to be used for determining which multicast routes are imported
         into the VRF for this virtual router.  If no import policy
         is defined, no routes are accepted into the VRF.

         If multiple policy names are specified, the policies are evaluated
         in the order they are specified.  The first policy that matches
         is applied.

         The import policy name list, vRtrMvpnVrfImportPolicy1 through
         vRtrMvpnVrfImportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 15 }

vRtrMvpnVrfExportPolicy1         OBJECT-TYPE
    SYNTAX      TXLPolicyNameOrExpOrEmpty
    MAX-ACCESS  read-create
    STATUS      current
    DESCRIPTION
        "The value of vRtrMvpnVrfExportPolicy1 specifies the first
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 16 }

vRtrMvpnVrfExportPolicy2         OBJECT-TYPE
    SYNTAX      TLPolicyNameOrExpOrEmpty
    MAX-ACCESS  read-create
    STATUS      current
    DESCRIPTION
        "The value of vRtrMvpnVrfExportPolicy2 specifies the second
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 17 }

vRtrMvpnVrfExportPolicy3         OBJECT-TYPE
    SYNTAX      TLPolicyNameOrExpOrEmpty
    MAX-ACCESS  read-create
    STATUS      current
    DESCRIPTION
        "The value of vRtrMvpnVrfExportPolicy3 specifies the third
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 18 }

vRtrMvpnVrfExportPolicy4         OBJECT-TYPE
    SYNTAX      TLPolicyNameOrExpOrEmpty
    MAX-ACCESS  read-create
    STATUS      current
    DESCRIPTION
        "The value of vRtrMvpnVrfExportPolicy4 specifies the fourth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 19 }

vRtrMvpnVrfExportPolicy5         OBJECT-TYPE
    SYNTAX      TLPolicyNameOrExpOrEmpty
    MAX-ACCESS  read-create
    STATUS      current
    DESCRIPTION
        "The value of vRtrMvpnVrfExportPolicy5 specifies the fifth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 20 }

vRtrMvpnVrfExportPolicy6         OBJECT-TYPE
    SYNTAX      TLPolicyNameOrExpOrEmpty
    MAX-ACCESS  read-create
    STATUS      current
    DESCRIPTION
        "The value of vRtrMvpnVrfExportPolicy6 specifies the sixth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 21 }

vRtrMvpnVrfExportPolicy7         OBJECT-TYPE
    SYNTAX      TLPolicyNameOrExpOrEmpty
    MAX-ACCESS  read-create
    STATUS      current
    DESCRIPTION
        "The value of vRtrMvpnVrfExportPolicy7 specifies the seventh
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 22 }

vRtrMvpnVrfExportPolicy8         OBJECT-TYPE
    SYNTAX      TLPolicyNameOrExpOrEmpty
    MAX-ACCESS  read-create
    STATUS      current
    DESCRIPTION
        "The value of vRtrMvpnVrfExportPolicy8 specifies the eighth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 23 }

vRtrMvpnVrfExportPolicy9         OBJECT-TYPE
    SYNTAX      TLPolicyNameOrExpOrEmpty
    MAX-ACCESS  read-create
    STATUS      current
    DESCRIPTION
        "The value of vRtrMvpnVrfExportPolicy9 specifies the ninth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 24 }

vRtrMvpnVrfExportPolicy10        OBJECT-TYPE
    SYNTAX      TLPolicyNameOrExpOrEmpty
    MAX-ACCESS  read-create
    STATUS      current
    DESCRIPTION
        "The value of vRtrMvpnVrfExportPolicy10 specifies the tenth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 25 }

vRtrMvpnVrfExportPolicy11        OBJECT-TYPE
    SYNTAX      TLPolicyNameOrExpOrEmpty
    MAX-ACCESS  read-create
    STATUS      current
    DESCRIPTION
        "The value of vRtrMvpnVrfExportPolicy11 specifies the eleventh
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 26 }

vRtrMvpnVrfExportPolicy12        OBJECT-TYPE
    SYNTAX      TLPolicyNameOrExpOrEmpty
    MAX-ACCESS  read-create
    STATUS      current
    DESCRIPTION
        "The value of vRtrMvpnVrfExportPolicy12 specifies the twelfth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 27 }

vRtrMvpnVrfExportPolicy13        OBJECT-TYPE
    SYNTAX      TLPolicyNameOrExpOrEmpty
    MAX-ACCESS  read-create
    STATUS      current
    DESCRIPTION
        "The value of vRtrMvpnVrfExportPolicy13 specifies the thirteenth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 28 }

vRtrMvpnVrfExportPolicy14        OBJECT-TYPE
    SYNTAX      TLPolicyNameOrExpOrEmpty
    MAX-ACCESS  read-create
    STATUS      current
    DESCRIPTION
        "The value of vRtrMvpnVrfExportPolicy14 specifies the fourteenth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 29 }

vRtrMvpnVrfExportPolicy15        OBJECT-TYPE
    SYNTAX      TLPolicyNameOrExpOrEmpty
    MAX-ACCESS  read-create
    STATUS      current
    DESCRIPTION
        "The value of vRtrMvpnVrfExportPolicy15 specifies the fifteenth
         policy to be used for determining which multicast routes are exported
         from the VRF for this virtual router.  If no export policy
         is defined, no routes are exported from the VRF.

         If multiple policy names are specified, the policies are evaluated
         in the order they are specified.  The first policy that matches
         is applied.

         The export policy name list, vRtrMvpnVrfExportPolicy1 through
         vRtrMvpnVrfExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrMvpnVrfPolicyEntry 30 }

vRtrIfQosTable                   OBJECT-TYPE
    SYNTAX      SEQUENCE OF VRtrIfQosEntry
    MAX-ACCESS  not-accessible
    STATUS      current
    DESCRIPTION
        "The vRtrIfQosTable has an entry for each router interface configured
         in the system. This table contains objects managing QoS on the
         interface. This table augments the vRtrIfTable."
    ::= { tmnxVRtrObjs 78 }

vRtrIfQosEntry                   OBJECT-TYPE
    SYNTAX      VRtrIfQosEntry
    MAX-ACCESS  not-accessible
    STATUS      current
    DESCRIPTION
        "Each row entry represents a virtual router interface QoS management
         objects in the system. Entries can be created and deleted via SNMP SET
         operations along with the associated row entry in vRtrIfTable using
         the vRtrIfRowStatus variable."
    AUGMENTS    { vRtrIfEntry }
    ::= { vRtrIfQosTable 1 }

VRtrIfQosEntry                   ::= SEQUENCE
{
    vRtrIfQosNetworkPolicyId         TNetworkPolicyID,
    vRtrIfQosEgrPortRedirectQGrp     TNamedItemOrEmpty,
    vRtrIfQosEgrQGrpInstanceId       TQosQGrpInstanceIDorZero,
    vRtrIfQosIngFpRedirectQGrp       TNamedItemOrEmpty,
    vRtrIfQosIngQGrpInstanceId       TQosQGrpInstanceIDorZero,
    vRtrIfQosEgrVlanQosPlcy          TLNamedItemOrEmpty,
    vRtrIfQosEgrRemarkPlcy           TLNamedItemOrEmpty,
    vRtrIfQosNetworkIngressPolicy    TLNamedItemOrEmpty,
    vRtrIfQosEgrAggRatePIRLmt        Integer32,
    vRtrIfQosEgrAggRateCIRLmt        Integer32,
    vRtrIfQosEgrOperVlanQosPlcy      TLNamedItemOrEmpty,
    vRtrIfQosEgrVlanPlcyPortRedirect TruthValue,
    vRtrIfQosEgrAggRatePIRPercent    Unsigned32,
    vRtrIfQosEgrAggRateCIRPercent    Unsigned32,
    vRtrIfQosEgrAggRateType          TRateType,
    vRtrIfQosEgrAggRateBurstLmt      Integer32,
    vRtrIfQosEgrSinkExcessBW         TruthValue
}

vRtrIfQosNetworkPolicyId         OBJECT-TYPE
    SYNTAX      TNetworkPolicyID
    MAX-ACCESS  read-create
    STATUS      current
    DESCRIPTION
        "The value of vRtrIfQosNetworkPolicyId associates a pre-existing
         network-policy-id to a network interface. Packets are marked using qos
         policies on edge switches; invoking a qos policy on a network port
         allows for the packets that match the policy criteria to be remarked.

         If this entry indicates a service virtual router interface or the
         special out-of-band management interface, this object is meaningless
         and is not applied to the interface."
    DEFVAL      { 1 }
    ::= { vRtrIfQosEntry 1 }

vRtrIfQosEgrPortRedirectQGrp     OBJECT-TYPE
    SYNTAX      TNamedItemOrEmpty
    MAX-ACCESS  read-create
    STATUS      current
    DESCRIPTION
        "The value of vRtrIfQosEgrPortRedirectQGrp specifies the name of the
         QoS queue-group (TIMETRA-QOS-MIB::tQosEgrQGroupName) used with this
         interface.

         An 'inconsistentValue' error is returned if this object is set to a
         non-default value and an entry corresponding to vRtrIfPortID does not
         exist in TIMETRA-PORT-MIB::tPortNetEgrQGrpTable."
    DEFVAL      { ''H }
    ::= { vRtrIfQosEntry 2 }

vRtrIfQosEgrQGrpInstanceId       OBJECT-TYPE
    SYNTAX      TQosQGrpInstanceIDorZero
    MAX-ACCESS  read-create
    STATUS      current
    DESCRIPTION
        "The value of vRtrIfQosEgrQGrpInstanceId specifies the instance of the
         port egress Queue Group for this interface."
    DEFVAL      { 0 }
    ::= { vRtrIfQosEntry 3 }

vRtrIfQosIngFpRedirectQGrp       OBJECT-TYPE
    SYNTAX      TNamedItemOrEmpty
    MAX-ACCESS  read-create
    STATUS      current
    DESCRIPTION
        "The value of vRtrIfQosIngFpRedirectQGrp specifies the forwarding-plane
         queue group Policy for this interface."
    DEFVAL      { "" }
    ::= { vRtrIfQosEntry 4 }

vRtrIfQosIngQGrpInstanceId       OBJECT-TYPE
    SYNTAX      TQosQGrpInstanceIDorZero
    MAX-ACCESS  read-create
    STATUS      current
    DESCRIPTION
        "The value of vRtrIfQosIngQGrpInstanceId specifies the instance of the
         forwarding-plane ingress Queue Group for this interface."
    DEFVAL      { 0 }
    ::= { vRtrIfQosEntry 5 }

vRtrIfQosEgrVlanQosPlcy          OBJECT-TYPE
    SYNTAX      TLNamedItemOrEmpty
    MAX-ACCESS  read-create
    STATUS      current
    DESCRIPTION
        "The value of vRtrIfQosEgrVlanQosPlcy specifies the name to associate
         with this interface."
    DEFVAL      { "default" }
    ::= { vRtrIfQosEntry 6 }

vRtrIfQosEgrRemarkPlcy           OBJECT-TYPE
    SYNTAX      TLNamedItemOrEmpty
    MAX-ACCESS  read-create
    STATUS      current
    DESCRIPTION
        "The value of vRtrIfQosEgrRemarkPlcy specifies the name of the
         egress-remark-policy attached to this interface."
    DEFVAL      { "default" }
    ::= { vRtrIfQosEntry 7 }

vRtrIfQosNetworkIngressPolicy    OBJECT-TYPE
    SYNTAX      TLNamedItemOrEmpty
    MAX-ACCESS  read-create
    STATUS      current
    DESCRIPTION
        "The value of vRtrIfQosNetworkIngressPolicy specifies the name of the
         network ingress policy attached to this router interface"
    DEFVAL      { "default" }
    ::= { vRtrIfQosEntry 8 }

vRtrIfQosEgrAggRatePIRLmt        OBJECT-TYPE
    SYNTAX      Integer32 (-1 | 1..400000000)
    UNITS       "kilobps"
    MAX-ACCESS  read-create
    STATUS      current
    DESCRIPTION
        "The value of vRtrIfQosEgrAggRatePIRLmt specifies the aggregate PIR
         rate for this interface."
    DEFVAL      { -1 }
    ::= { vRtrIfQosEntry 9 }

vRtrIfQosEgrAggRateCIRLmt        OBJECT-TYPE
    SYNTAX      Integer32 (-1..400000000)
    UNITS       "kilobps"
    MAX-ACCESS  read-create
    STATUS      current
    DESCRIPTION
        "The value of vRtrIfQosEgrAggRateCIRLmt specifies the aggregate CIR
         rate for this interface."
    DEFVAL      { 0 }
    ::= { vRtrIfQosEntry 10 }

vRtrIfQosEgrOperVlanQosPlcy      OBJECT-TYPE
    SYNTAX      TLNamedItemOrEmpty
    MAX-ACCESS  read-only
    STATUS      current
    DESCRIPTION
        "The value of vRtrIfQosEgrOperVlanQosPlcy specifies the current
         operational vlan qos policy associated with this interface."
    DEFVAL      { "" }
    ::= { vRtrIfQosEntry 11 }

vRtrIfQosEgrVlanPlcyPortRedirect OBJECT-TYPE
    SYNTAX      TruthValue
    MAX-ACCESS  read-create
    STATUS      current
    DESCRIPTION
        "The value of vRtrIfQosEgrVlanPlcyPortRedirect specifies whether port
         redirect is enabled with the vlan qos policy configured in
         vRtrIfQosEgrVlanQosPlcy."
    DEFVAL      { false }
    ::= { vRtrIfQosEntry 12 }

vRtrIfQosEgrAggRatePIRPercent    OBJECT-TYPE
    SYNTAX      Unsigned32 (1..10000)
    UNITS       "centipercent"
    MAX-ACCESS  read-create
    STATUS      current
    DESCRIPTION
        "The administrative PIR percentage, in centipercent. An
         'inconsistentValue' error is returned if vRtrIfQosEgrAggRatePIRPercent
         is set to non-default value when the object vRtrIfQosEgrAggRateType is
         set to 'kbps'."
    DEFVAL      { 10000 }
    ::= { vRtrIfQosEntry 13 }

vRtrIfQosEgrAggRateCIRPercent    OBJECT-TYPE
    SYNTAX      Unsigned32 (0..10000)
    UNITS       "centipercent"
    MAX-ACCESS  read-create
    STATUS      current
    DESCRIPTION
        "The administrative CIR percentage, in centipercent. An
         'inconsistentValue' error is returned if vRtrIfQosEgrAggRateCIRPercent
         is set to non-default value when the object vRtrIfQosEgrAggRateType is
         set to 'kbps'."
    DEFVAL      { 0 }
    ::= { vRtrIfQosEntry 14 }

vRtrIfQosEgrAggRateType          OBJECT-TYPE
    SYNTAX      TRateType
    MAX-ACCESS  read-create
    STATUS      current
    DESCRIPTION
        "The value of vRtrIfQosEgrAggRateType specifies the type of Egress Agg
         rate.

         When the value of the object is set to 'kbps', the ingress queue rates
         are specified in kbps. The objects vRtrIfQosEgrAggRateCIRPercent and
         vRtrIfQosEgrAggRatePIRPercent will be set to their default values.

         When the value of the object is set to 'percent', the egress queue
         rates are specified in percentage. The objects
         vRtrIfQosEgrAggRateCIRPercent and vRtrIfQosEgrAggRatePIRPercent will
         be set to their default values."
    DEFVAL      { kbps }
    ::= { vRtrIfQosEntry 15 }

vRtrIfQosEgrAggRateBurstLmt      OBJECT-TYPE
    SYNTAX      Integer32 (-1 | 2)
    UNITS       "kilobytes"
    MAX-ACCESS  read-create
    STATUS      current
    DESCRIPTION
        "The value of vRtrIfQosEgrAggRateBurstLmt specifies the burst limit
         for vlan qos aggregate shaper.

         The value of -1 denotes the default burst limit."
    DEFVAL      { -1 }
    ::= { vRtrIfQosEntry 16 }

vRtrIfQosEgrSinkExcessBW         OBJECT-TYPE
    SYNTAX      TruthValue
    MAX-ACCESS  read-create
    STATUS      current
    DESCRIPTION
        "Enable/disable the shared queue sink excess bandwidth."
    DEFVAL      { false }
    ::= { vRtrIfQosEntry 17 }

vRtrDnsTableLastCh               OBJECT-TYPE
    SYNTAX      TimeStamp
    MAX-ACCESS  read-only
    STATUS      current
    DESCRIPTION
        "The value of the object vRtrDnsTableLastCh indicates the value of
         sysUpTime at the time of the last modification of an entry in the
         vRtrDnsTable."
    ::= { tmnxVRtrObjs 79 }

vRtrDnsTable                     OBJECT-TYPE
    SYNTAX      SEQUENCE OF VRtrDnsEntry
    MAX-ACCESS  not-accessible
    STATUS      current
    DESCRIPTION
        "The vRtrDnsTable provides a sparse extension of the vRtrConfTable to
         configure DNS.

         Rows in this table are created and destroyed by means of SNMP set
         operations on the vRtrDnsRowStatus object."
    ::= { tmnxVRtrObjs 80 }

vRtrDnsEntry                     OBJECT-TYPE
    SYNTAX      VRtrDnsEntry
    MAX-ACCESS  not-accessible
    STATUS      current
    DESCRIPTION
        "Each row entry in the vRtrDnsTable represents DNS configuration of a
         specific virtual router instance.

         For some virtual router instances, such as the Base router instance,
         it is not allowed to create a row in this table."
    INDEX       { vRtrID }
    ::= { vRtrDnsTable 1 }

VRtrDnsEntry                     ::= SEQUENCE
{
    vRtrDnsLastCh                    TimeStamp,
    vRtrDnsRowStatus                 RowStatus,
    vRtrDnsAdminState                TmnxEnabledDisabled,
    vRtrDnsPrimaryAddrType           InetAddressType,
    vRtrDnsPrimaryAddr               InetAddress,
    vRtrDnsSecondaryAddrType         InetAddressType,
    vRtrDnsSecondaryAddr             InetAddress,
    vRtrDnsTertiaryAddrType          InetAddressType,
    vRtrDnsTertiaryAddr              InetAddress,
    vRtrDnsIpv4SourceAddr            InetAddressIPv4,
    vRtrDnsIpv6SourceAddr            InetAddressIPv6,
    vRtrDnsDefaultDomainName         DisplayString
}

vRtrDnsLastCh                    OBJECT-TYPE
    SYNTAX      TimeStamp
    MAX-ACCESS  read-only
    STATUS      current
    DESCRIPTION
        "The value of vRtrDnsLastCh indicates the sysUpTime at the time of the
         most recent management-initiated change to this table row."
    ::= { vRtrDnsEntry 1 }

vRtrDnsRowStatus                 OBJECT-TYPE
    SYNTAX      RowStatus
    MAX-ACCESS  read-create
    STATUS      current
    DESCRIPTION
        "The value of vRtrDnsRowStatus specifies the row status of this
         conceptual row."
    ::= { vRtrDnsEntry 2 }

vRtrDnsAdminState                OBJECT-TYPE
    SYNTAX      TmnxEnabledDisabled
    MAX-ACCESS  read-create
    STATUS      current
    DESCRIPTION
        "The value of vRtrDnsAdminState specifies the administrative state of
         DNS in this virtual router instance."
    DEFVAL      { disabled }
    ::= { vRtrDnsEntry 3 }

vRtrDnsPrimaryAddrType           OBJECT-TYPE
    SYNTAX      InetAddressType
    MAX-ACCESS  read-create
    STATUS      current
    DESCRIPTION
        "The value of vRtrDnsPrimaryAddrType specifies the address type of
         vRtrDnsPrimaryAddr."
    DEFVAL      { unknown }
    ::= { vRtrDnsEntry 4 }

vRtrDnsPrimaryAddr               OBJECT-TYPE
    SYNTAX      InetAddress (SIZE (0|4|16))
    MAX-ACCESS  read-create
    STATUS      current
    DESCRIPTION
        "The value of vRtrDnsPrimaryAddr specifies the address of the primary
         DNS server in this virtual router instance."
    DEFVAL      { ''H }
    ::= { vRtrDnsEntry 5 }

vRtrDnsSecondaryAddrType         OBJECT-TYPE
    SYNTAX      InetAddressType
    MAX-ACCESS  read-create
    STATUS      current
    DESCRIPTION
        "The value of vRtrDnsSecondaryAddrType specifies the address type of
         vRtrDnsSecondaryAddr."
    DEFVAL      { unknown }
    ::= { vRtrDnsEntry 6 }

vRtrDnsSecondaryAddr             OBJECT-TYPE
    SYNTAX      InetAddress (SIZE (0|4|16))
    MAX-ACCESS  read-create
    STATUS      current
    DESCRIPTION
        "The value of vRtrDnsSecondaryAddr specifies the address of the
         secondary DNS server in this virtual router instance."
    DEFVAL      { ''H }
    ::= { vRtrDnsEntry 7 }

vRtrDnsTertiaryAddrType          OBJECT-TYPE
    SYNTAX      InetAddressType
    MAX-ACCESS  read-create
    STATUS      current
    DESCRIPTION
        "The value of vRtrDnsTertiaryAddrType specifies the address type of
         vRtrDnsTertiaryAddr."
    DEFVAL      { unknown }
    ::= { vRtrDnsEntry 8 }

vRtrDnsTertiaryAddr              OBJECT-TYPE
    SYNTAX      InetAddress (SIZE (0|4|16))
    MAX-ACCESS  read-create
    STATUS      current
    DESCRIPTION
        "The value of vRtrDnsTertiaryAddr specifies the address of the tertiary
         DNS server in this virtual router instance."
    DEFVAL      { ''H }
    ::= { vRtrDnsEntry 9 }

vRtrDnsIpv4SourceAddr            OBJECT-TYPE
    SYNTAX      InetAddressIPv4
    MAX-ACCESS  read-create
    STATUS      current
    DESCRIPTION
        "The value of vRtrDnsIpv4SourceAddr specifies the source address for
         communication with an IPv4 DNS server in this virtual router instance.

         The value of all zeroes specifies that no DNS IPv4 source address is
         configured."
    DEFVAL      { '00000000'H }
    ::= { vRtrDnsEntry 10 }

vRtrDnsIpv6SourceAddr            OBJECT-TYPE
    SYNTAX      InetAddressIPv6
    MAX-ACCESS  read-create
    STATUS      current
    DESCRIPTION
        "The value of vRtrDnsIpv6SourceAddr specifies the source address for
         communication with an IPv6 DNS server in this virtual router instance.

         The value of all zeroes specifies that no DNS IPv6 source address is
         configured."
    DEFVAL      { '00000000000000000000000000000000'H }
    ::= { vRtrDnsEntry 11 }

vRtrDnsDefaultDomainName         OBJECT-TYPE
    SYNTAX      DisplayString (SIZE (0..255))
    MAX-ACCESS  read-create
    STATUS      current
    DESCRIPTION
        "The value of vRtrDnsDefaultDomainName specifies the default domain
         name to be searched when performing DNS address resolution. Allowed
         characters are 'a' to 'z', '0' to '9', '-' and '.'"
    DEFVAL      { "" }
    ::= { vRtrDnsEntry 12 }

vRtrInetAllCidrRouteTnlExtTable  OBJECT-TYPE
    SYNTAX      SEQUENCE OF VRtrInetAllCidrRouteTnlExtEntry
    MAX-ACCESS  not-accessible
    STATUS      current
    DESCRIPTION
        "The vRtrInetAllCidrRouteTnlExtTable provides an extension of the
         inetCidrRouteTable in the IP-FORWARD-MIB, by adding three indexes and
         displays only tunneled routes."
    ::= { tmnxVRtrObjs 81 }

vRtrInetAllCidrRouteTnlExtEntry  OBJECT-TYPE
    SYNTAX      VRtrInetAllCidrRouteTnlExtEntry
    MAX-ACCESS  not-accessible
    STATUS      current
    DESCRIPTION
        "Each row entry in the vRtrInetAllCidrRouteTable represents an entry in
         the IP CIDR route table for the Nokia SROS series."
    INDEX       {
        inetCidrRouteDestType,
        inetCidrRouteDest,
        inetCidrRoutePfxLen,
        inetCidrRouteProto,
        vRtrInetAllCidrRouteProtoID,
        inetCidrRouteNextHopType,
        inetCidrRouteNextHop,
        vRtrInetAllCidrRteTnlNxtHopType,
        vRtrInetAllCidrRteTnlNxtHopOwner,
        vRtrInetAllCidrRteTnlNxtHopTnlId
    }
    ::= { vRtrInetAllCidrRouteTnlExtTable 1 }

VRtrInetAllCidrRouteTnlExtEntry  ::= SEQUENCE
{
    vRtrInetAllCidrRteTnlNxtHopType  TmnxInetCidrNextHopType,
    vRtrInetAllCidrRteTnlNxtHopOwner TmnxInetCidrNextHopOwner,
    vRtrInetAllCidrRteTnlNxtHopTnlId Unsigned32,
    vRtrInetAllCidrRteTnlEnabledTime TimeStamp
}

vRtrInetAllCidrRteTnlNxtHopType  OBJECT-TYPE
    SYNTAX      TmnxInetCidrNextHopType
    MAX-ACCESS  not-accessible
    STATUS      current
    DESCRIPTION
        "The value of vRtrInetAllCidrRteTnlNxtHopType indicates the type of
         next hop for this route."
    ::= { vRtrInetAllCidrRouteTnlExtEntry 1 }

vRtrInetAllCidrRteTnlNxtHopOwner OBJECT-TYPE
    SYNTAX      TmnxInetCidrNextHopOwner
    MAX-ACCESS  not-accessible
    STATUS      current
    DESCRIPTION
        "The value of vRtrInetAllCidrRteTnlNxtHopOwner indicates the owner of
         next hop for this route."
    ::= { vRtrInetAllCidrRouteTnlExtEntry 2 }

vRtrInetAllCidrRteTnlNxtHopTnlId OBJECT-TYPE
    SYNTAX      Unsigned32
    MAX-ACCESS  not-accessible
    STATUS      current
    DESCRIPTION
        "Additional table index provided to distinguish between multiple RSVP
         tunnel ids to same destination with the same
         vRtrInetAllCidrRteTnlNxtHopType and vRtrInetAllCidrRteTnlNxtHopOwner."
    ::= { vRtrInetAllCidrRouteTnlExtEntry 3 }

vRtrInetAllCidrRteTnlEnabledTime OBJECT-TYPE
    SYNTAX      TimeStamp
    MAX-ACCESS  read-only
    STATUS      current
    DESCRIPTION
        "The vRtrInetAllCidrRteTnlEnabledTime variable indicates the sysUpTime
         value for this route entry."
    ::= { vRtrInetAllCidrRouteTnlExtEntry 4 }

vRtrRsmTableLastCh               OBJECT-TYPE
    SYNTAX      TimeStamp
    MAX-ACCESS  read-only
    STATUS      current
    DESCRIPTION
        "The value of the object vRtrRsmTableLastCh indicates the value of
         sysUpTime at the time of the last modification of an entry in the
         vRtrRsmTable."
    ::= { tmnxVRtrObjs 82 }

vRtrRsmTable                     OBJECT-TYPE
    SYNTAX      SEQUENCE OF VRtrRsmEntry
    MAX-ACCESS  not-accessible
    STATUS      current
    DESCRIPTION
        "The vRtrRsmTable provides a sparse extension of the vRtrConfTable to
         configure reassembly of IP datagram fragments using an ISA-BB card.

         Rows in this table can be created and destroyed with SNMP operations."
    ::= { tmnxVRtrObjs 83 }

vRtrRsmEntry                     OBJECT-TYPE
    SYNTAX      VRtrRsmEntry
    MAX-ACCESS  not-accessible
    STATUS      current
    DESCRIPTION
        "Each row entry in the vRtrRsmTable represents reassembly configuration
         of a specific virtual router instance."
    INDEX       { vRtrID }
    ::= { vRtrRsmTable 1 }

VRtrRsmEntry                     ::= SEQUENCE
{
    vRtrRsmLastCh                    TimeStamp,
    vRtrRsmRowStatus                 RowStatus,
    vRtrRsmGroup                     TmnxIsaBbGrpId,
    vRtrRsmToBaseNetwork             TruthValue
}

vRtrRsmLastCh                    OBJECT-TYPE
    SYNTAX      TimeStamp
    MAX-ACCESS  read-only
    STATUS      current
    DESCRIPTION
        "The value of vRtrRsmLastCh indicates the sysUpTime at the time of the
         most recent management-initiated change to this table row."
    ::= { vRtrRsmEntry 1 }

vRtrRsmRowStatus                 OBJECT-TYPE
    SYNTAX      RowStatus
    MAX-ACCESS  read-create
    STATUS      current
    DESCRIPTION
        "The value of vRtrRsmRowStatus specifies the row status of this row."
    ::= { vRtrRsmEntry 2 }

vRtrRsmGroup                     OBJECT-TYPE
    SYNTAX      TmnxIsaBbGrpId
    MAX-ACCESS  read-create
    STATUS      current
    DESCRIPTION
        "The value of vRtrRsmGroup specifies the ISA-BB group associated with
         this virtual router instance for the purpose of IP datagram fragment
         reassembly.

         The value zero specifies that no such ISA-BB group is associated.

         A nonzero value must correspond to a row in the
         TIMETRA-NAT-MIB::tmnxNatGrpCfgTable.

         Traffic flows are redirected to the reassembly function by means of a
         filter entry with action equal to 'reassembly', for example a row in
         the TIMETRA-FILTER-MIB::tIPFilterParamsTable where the object
         tIPFilterParamsAction is equal to 'reassembly'."
    DEFVAL      { 0 }
    ::= { vRtrRsmEntry 3 }

vRtrRsmToBaseNetwork             OBJECT-TYPE
    SYNTAX      TruthValue
    MAX-ACCESS  read-create
    STATUS      current
    DESCRIPTION
        "The value of vRtrRsmToBaseNetwork specifies whether the reassembled
         traffic must be sent to the network interface of the Base router."
    DEFVAL      { false }
    ::= { vRtrRsmEntry 4 }

vRtrIfLocalPoolTable             OBJECT-TYPE
    SYNTAX      SEQUENCE OF VRtrIfLocalPoolEntry
    MAX-ACCESS  not-accessible
    STATUS      current
    DESCRIPTION
        "The vRtrIfLocalPoolTable provides an extension to the vRtrIfTable. It
         has an entry for each virtual router interface configured in the
         system."
    ::= { tmnxVRtrObjs 84 }

vRtrIfLocalPoolEntry             OBJECT-TYPE
    SYNTAX      VRtrIfLocalPoolEntry
    MAX-ACCESS  not-accessible
    STATUS      current
    DESCRIPTION
        "Each row entry represents information related to Local Pool for a
         virtual router interface in the system.

         Entries cannot be created and deleted via SNMP SET operations."
    AUGMENTS    { vRtrIfEntry }
    ::= { vRtrIfLocalPoolTable 1 }

VRtrIfLocalPoolEntry             ::= SEQUENCE
{
    vRtrIfLocalPoolAdminState        TmnxAdminState,
    vRtrIfLocalPoolServerName        TNamedItemOrEmpty,
    vRtrIfLocalPoolClientApps        BITS,
    vRtrIfLocalPoolDefPoolName       TNamedItemOrEmpty,
    vRtrIfLocalPoolSecPoolName       TNamedItemOrEmpty,
    vRtrIfLocalPoolV6ServerName      TNamedItemOrEmpty,
    vRtrIfLocalPoolV6ClientApps      BITS
}

vRtrIfLocalPoolAdminState        OBJECT-TYPE
    SYNTAX      TmnxAdminState
    MAX-ACCESS  read-create
    STATUS      current
    DESCRIPTION
        "The value of the object vRtrIfLocalPoolAdminState specifies the
         administrative state of the vRtrIfLocalPoolEntry."
    DEFVAL      { outOfService }
    ::= { vRtrIfLocalPoolEntry 1 }

vRtrIfLocalPoolServerName        OBJECT-TYPE
    SYNTAX      TNamedItemOrEmpty
    MAX-ACCESS  read-create
    STATUS      current
    DESCRIPTION
        "The value of the object vRtrIfLocalPoolServerName specifies the name
         of the local DHCP server instance."
    DEFVAL      { "" }
    ::= { vRtrIfLocalPoolEntry 2 }

vRtrIfLocalPoolClientApps        OBJECT-TYPE
    SYNTAX      BITS {
        ppp-v4  (0),
        ipoe-v4 (1)
    }
    MAX-ACCESS  read-create
    STATUS      current
    DESCRIPTION
        "The value of vRtrIfLocalPoolClientApps specifies the set of client
         applications that can make use of the local address assignment on this
         interface."
    DEFVAL      { {} }
    ::= { vRtrIfLocalPoolEntry 3 }

vRtrIfLocalPoolDefPoolName       OBJECT-TYPE
    SYNTAX      TNamedItemOrEmpty
    MAX-ACCESS  read-create
    STATUS      current
    DESCRIPTION
        "The value of the object vRtrIfLocalPoolDefPoolName specifies the name
         of the default IP address pool."
    DEFVAL      { "" }
    ::= { vRtrIfLocalPoolEntry 4 }

vRtrIfLocalPoolSecPoolName       OBJECT-TYPE
    SYNTAX      TNamedItemOrEmpty
    MAX-ACCESS  read-create
    STATUS      current
    DESCRIPTION
        "The value of the object vRtrIfLocalPoolSecPoolName specifies the name
         of the secondary IP address pool."
    DEFVAL      { "" }
    ::= { vRtrIfLocalPoolEntry 5 }

vRtrIfLocalPoolV6ServerName      OBJECT-TYPE
    SYNTAX      TNamedItemOrEmpty
    MAX-ACCESS  read-create
    STATUS      current
    DESCRIPTION
        "The value of the object vRtrIfLocalPoolV6ServerName specifies the name
         of the local DHCPv6 server instance."
    DEFVAL      { "" }
    ::= { vRtrIfLocalPoolEntry 6 }

vRtrIfLocalPoolV6ClientApps      OBJECT-TYPE
    SYNTAX      BITS {
        pppSlaac  (0),
        ipoeWan   (1),
        ipoeSlaac (2)
    }
    MAX-ACCESS  read-create
    STATUS      current
    DESCRIPTION
        "The value of vRtrIfLocalPoolV6ClientApps specifies the set of client
         applications that can make use of the IPv6 local address assignment on
         this interface."
    DEFVAL      { {} }
    ::= { vRtrIfLocalPoolEntry 7 }

vRtrIfDcpFpStaticStatTable       OBJECT-TYPE
    SYNTAX      SEQUENCE OF VRtrIfDcpFpStaticStatEntry
    MAX-ACCESS  not-accessible
    STATUS      current
    DESCRIPTION
        "The vRtrIfDcpFpStaticStatTable has the statistics information of the
         static-policer configured on Distributed CPU Protection Policy per
         network-interface per forwarding plane."
    ::= { tmnxVRtrObjs 85 }

vRtrIfDcpFpStaticStatEntry       OBJECT-TYPE
    SYNTAX      VRtrIfDcpFpStaticStatEntry
    MAX-ACCESS  not-accessible
    STATUS      current
    DESCRIPTION
        "The value of vRtrIfDcpFpStaticStatEntry represents statistics
         information per network-interface per forwarding plane for the
         static-policer configured on Distributed CPU Protection Policy."
    INDEX       {
        vRtrID,
        vRtrIfIndex,
        tmnxChassisIndex,
        tmnxCardSlotNum,
        tmnxFPNum,
        vRtrIfDcpFpStaticPlcrName
    }
    ::= { vRtrIfDcpFpStaticStatTable 1 }

VRtrIfDcpFpStaticStatEntry       ::= SEQUENCE
{
    vRtrIfDcpFpStaticPlcrName        TNamedItem,
    vRtrIfDcpFpStaticState           TmnxDistCpuProtState,
    vRtrIfDcpFpStaticExcdCount       Counter64,
    vRtrIfDcpFpStaticExcdCountHi     Counter32,
    vRtrIfDcpFpStaticExcdCountLo     Counter32,
    vRtrIfDcpFpStaticHoldDown        TmnxDistCpuProtActionDuration,
    vRtrIfDcpFpStaticDetectionTime   Unsigned32,
    vRtrIfDcpFpStaticTotalExcdCount  Counter64,
    vRtrIfDcpFpStaticExtCnfrmStCount Counter32
}

vRtrIfDcpFpStaticPlcrName        OBJECT-TYPE
    SYNTAX      TNamedItem
    MAX-ACCESS  not-accessible
    STATUS      current
    DESCRIPTION
        "The value of vRtrIfDcpFpStaticPlcrName specifies the static-policer
         name for Distributed CPU Protection Policy."
    ::= { vRtrIfDcpFpStaticStatEntry 1 }

vRtrIfDcpFpStaticState           OBJECT-TYPE
    SYNTAX      TmnxDistCpuProtState
    MAX-ACCESS  read-only
    STATUS      current
    DESCRIPTION
        "The value of vRtrIfDcpFpStaticState indicates the state of the
         static-policer configured on Distributed CPU Protection Policy."
    ::= { vRtrIfDcpFpStaticStatEntry 2 }

vRtrIfDcpFpStaticExcdCount       OBJECT-TYPE
    SYNTAX      Counter64
    MAX-ACCESS  read-only
    STATUS      current
    DESCRIPTION
        "The value of vRtrIfDcpFpStaticExcdCount indicates number of packets
         exceeding the policing parameters since the given static-policer was
         previously declared as conformant or newly instantiated."
    ::= { vRtrIfDcpFpStaticStatEntry 3 }

vRtrIfDcpFpStaticExcdCountHi     OBJECT-TYPE
    SYNTAX      Counter32
    MAX-ACCESS  read-only
    STATUS      current
    DESCRIPTION
        "The value of vRtrIfDcpFpStaticExcdCountHi indicates upper 32-bits of
         vRtrIfDcpFpStaticExcdCount."
    ::= { vRtrIfDcpFpStaticStatEntry 4 }

vRtrIfDcpFpStaticExcdCountLo     OBJECT-TYPE
    SYNTAX      Counter32
    MAX-ACCESS  read-only
    STATUS      current
    DESCRIPTION
        "The value of vRtrIfDcpFpStaticExcdCountLo indicates lower 32-bits of
         vRtrIfDcpFpStaticExcdCount."
    ::= { vRtrIfDcpFpStaticStatEntry 5 }

vRtrIfDcpFpStaticHoldDown        OBJECT-TYPE
    SYNTAX      TmnxDistCpuProtActionDuration
    UNITS       "seconds"
    MAX-ACCESS  read-only
    STATUS      current
    DESCRIPTION
        "The value of vRtrIfDcpFpStaticHoldDown indicates the remaining
         hold-down period for a given static-policer."
    ::= { vRtrIfDcpFpStaticStatEntry 6 }

vRtrIfDcpFpStaticDetectionTime   OBJECT-TYPE
    SYNTAX      Unsigned32
    UNITS       "seconds"
    MAX-ACCESS  read-only
    STATUS      current
    DESCRIPTION
        "The value of vRtrIfDcpFpStaticDetectionTime indicates the detection
         time remaining for a given static-policer."
    ::= { vRtrIfDcpFpStaticStatEntry 7 }

vRtrIfDcpFpStaticTotalExcdCount  OBJECT-TYPE
    SYNTAX      Counter64
    MAX-ACCESS  read-only
    STATUS      current
    DESCRIPTION
        "The value of vRtrIfDcpFpStaticTotalExcdCount indicates the total
         number of packets exceeding the policing parameters."
    ::= { vRtrIfDcpFpStaticStatEntry 8 }

vRtrIfDcpFpStaticExtCnfrmStCount OBJECT-TYPE
    SYNTAX      Counter32
    MAX-ACCESS  read-only
    STATUS      current
    DESCRIPTION
        "The value of vRtrIfDcpFpStaticExtCnfrmStCount indicates the total
         number of transition of the policer to the exceed state."
    ::= { vRtrIfDcpFpStaticStatEntry 9 }

vRtrIfDcpFpDynStatTable          OBJECT-TYPE
    SYNTAX      SEQUENCE OF VRtrIfDcpFpDynStatEntry
    MAX-ACCESS  not-accessible
    STATUS      current
    DESCRIPTION
        "The vRtrIfDcpFpDynStatTable has the statistics information of the
         dynamic policer for a particular protocol configured on Distributed
         CPU Protection Policy per network-interface per forwarding plane."
    ::= { tmnxVRtrObjs 86 }

vRtrIfDcpFpDynStatEntry          OBJECT-TYPE
    SYNTAX      VRtrIfDcpFpDynStatEntry
    MAX-ACCESS  not-accessible
    STATUS      current
    DESCRIPTION
        "The value of vRtrIfDcpFpDynStatEntry represents statistics information
         per network-interface per forwarding plane for the dynamic policer for
         a particular protocol configured on Distributed CPU Protection Policy."
    INDEX       {
        vRtrID,
        vRtrIfIndex,
        tmnxChassisIndex,
        tmnxCardSlotNum,
        tmnxFPNum,
        vRtrIfDcpFpProtocol
    }
    ::= { vRtrIfDcpFpDynStatTable 1 }

VRtrIfDcpFpDynStatEntry          ::= SEQUENCE
{
    vRtrIfDcpFpProtocol              TmnxDistCpuProtProtocolId,
    vRtrIfDcpFpDynState              TmnxDistCpuProtState,
    vRtrIfDcpFpDynExcdCount          Counter64,
    vRtrIfDcpFpDynExcdCountHi        Counter32,
    vRtrIfDcpFpDynExcdCountLo        Counter32,
    vRtrIfDcpFpDynHoldDown           TmnxDistCpuProtActionDuration,
    vRtrIfDcpFpDynDetectionTime      Unsigned32,
    vRtrIfDcpFpDynAllocated          TruthValue,
    vRtrIfDcpFpDynTotalExcdCount     Counter64,
    vRtrIfDcpFpDynExtCnfrmStateCount Counter32
}

vRtrIfDcpFpProtocol              OBJECT-TYPE
    SYNTAX      TmnxDistCpuProtProtocolId
    MAX-ACCESS  not-accessible
    STATUS      current
    DESCRIPTION
        "The value of vRtrIfDcpFpProtocol specifies the protocol name to be
         monitored by Distributed CPU Protection Policy."
    ::= { vRtrIfDcpFpDynStatEntry 1 }

vRtrIfDcpFpDynState              OBJECT-TYPE
    SYNTAX      TmnxDistCpuProtState
    MAX-ACCESS  read-only
    STATUS      current
    DESCRIPTION
        "The value of vRtrIfDcpFpDynState indicates the state of the dynamic
         policer for a particular protocol configured on Distributed CPU
         Protection Policy."
    ::= { vRtrIfDcpFpDynStatEntry 2 }

vRtrIfDcpFpDynExcdCount          OBJECT-TYPE
    SYNTAX      Counter64
    MAX-ACCESS  read-only
    STATUS      current
    DESCRIPTION
        "The value of vRtrIfDcpFpDynExcdCount indicates number of packets
         exceeding the policing parameters since the dynamic policer for a
         given protocol was previously declared as conformant or newly
         instantiated."
    ::= { vRtrIfDcpFpDynStatEntry 3 }

vRtrIfDcpFpDynExcdCountHi        OBJECT-TYPE
    SYNTAX      Counter32
    MAX-ACCESS  read-only
    STATUS      current
    DESCRIPTION
        "The value of vRtrIfDcpFpDynExcdCountHi indicates upper 32-bits of
         vRtrIfDcpFpDynExcdCount."
    ::= { vRtrIfDcpFpDynStatEntry 4 }

vRtrIfDcpFpDynExcdCountLo        OBJECT-TYPE
    SYNTAX      Counter32
    MAX-ACCESS  read-only
    STATUS      current
    DESCRIPTION
        "The value of vRtrIfDcpFpDynExcdCountLo indicates lower 32-bits of
         vRtrIfDcpFpDynExcdCount."
    ::= { vRtrIfDcpFpDynStatEntry 5 }

vRtrIfDcpFpDynHoldDown           OBJECT-TYPE
    SYNTAX      TmnxDistCpuProtActionDuration
    UNITS       "seconds"
    MAX-ACCESS  read-only
    STATUS      current
    DESCRIPTION
        "The value of vRtrIfDcpFpDynHoldDown indicates the remaining hold-down
         period for the dynamic policer for given protocol."
    ::= { vRtrIfDcpFpDynStatEntry 6 }

vRtrIfDcpFpDynDetectionTime      OBJECT-TYPE
    SYNTAX      Unsigned32
    UNITS       "seconds"
    MAX-ACCESS  read-only
    STATUS      current
    DESCRIPTION
        "The value of vRtrIfDcpFpDynDetectionTime indicates the detection time
         remaining for the dynamic policer for given protocol."
    ::= { vRtrIfDcpFpDynStatEntry 7 }

vRtrIfDcpFpDynAllocated          OBJECT-TYPE
    SYNTAX      TruthValue
    MAX-ACCESS  read-only
    STATUS      current
    DESCRIPTION
        "The value of vRtrIfDcpFpDynAllocated indicates whether dynamic policer
         has been allocated for this protocol."
    ::= { vRtrIfDcpFpDynStatEntry 8 }

vRtrIfDcpFpDynTotalExcdCount     OBJECT-TYPE
    SYNTAX      Counter64
    MAX-ACCESS  read-only
    STATUS      current
    DESCRIPTION
        "The value of vRtrIfDcpFpDynTotalExcdCount indicates the total number
         of packets exceeding the policing parameters."
    ::= { vRtrIfDcpFpDynStatEntry 9 }

vRtrIfDcpFpDynExtCnfrmStateCount OBJECT-TYPE
    SYNTAX      Counter32
    MAX-ACCESS  read-only
    STATUS      current
    DESCRIPTION
        "The value of vRtrIfDcpFpDynExtCnfrmStateCount indicates the total
         number of transition of the policer to the exceed state."
    ::= { vRtrIfDcpFpDynStatEntry 10 }

vRtrIfDcpFpLocMonStatTable       OBJECT-TYPE
    SYNTAX      SEQUENCE OF VRtrIfDcpFpLocMonStatEntry
    MAX-ACCESS  not-accessible
    STATUS      current
    DESCRIPTION
        "The vRtrIfDcpFpLocMonStatTable has the statistics information of
         the local-monitoring policer configured on Distributed CPU Protection
          Policy per network-interface per forwarding plane."
    ::= { tmnxVRtrObjs 87 }

vRtrIfDcpFpLocMonStatEntry       OBJECT-TYPE
    SYNTAX      VRtrIfDcpFpLocMonStatEntry
    MAX-ACCESS  not-accessible
    STATUS      current
    DESCRIPTION
        "The value of vRtrIfDcpFpLocMonStatTable represents statistics
         information per network-interface per forwarding plane for the
         local-monitoring policer configured on Distributed CPU Protection
         Policy."
    INDEX       {
        vRtrID,
        vRtrIfIndex,
        tmnxChassisIndex,
        tmnxCardSlotNum,
        tmnxFPNum,
        vRtrIfDcpFpLocMonPlcrName
    }
    ::= { vRtrIfDcpFpLocMonStatTable 1 }

VRtrIfDcpFpLocMonStatEntry       ::= SEQUENCE
{
    vRtrIfDcpFpLocMonPlcrName        TNamedItem,
    vRtrIfDcpFpLocMonState           TmnxDistCpuProtState,
    vRtrIfDcpFpLocMonExcdCount       Counter64,
    vRtrIfDcpFpLocMonExcdCountHi     Counter32,
    vRtrIfDcpFpLocMonExcdCountLo     Counter32,
    vRtrIfDcpFpLocMonAllDynAlloc     TruthValue,
    vRtrIfDcpFpLocMonTotalExcdCount  Counter64,
    vRtrIfDcpFpLocMonExtCnfrmStCount Counter32
}

vRtrIfDcpFpLocMonPlcrName        OBJECT-TYPE
    SYNTAX      TNamedItem
    MAX-ACCESS  not-accessible
    STATUS      current
    DESCRIPTION
        "The value of vRtrIfDcpFpLocMonPlcrName specifies the local monitoring
         policy name for Distributed CPU Protection Policy."
    ::= { vRtrIfDcpFpLocMonStatEntry 1 }

vRtrIfDcpFpLocMonState           OBJECT-TYPE
    SYNTAX      TmnxDistCpuProtState
    MAX-ACCESS  read-only
    STATUS      current
    DESCRIPTION
        "The value of vRtrIfDcpFpLocMonState indicates the state of the
         local-monitoring policer configured on Distributed CPU Protection
         Policy."
    ::= { vRtrIfDcpFpLocMonStatEntry 2 }

vRtrIfDcpFpLocMonExcdCount       OBJECT-TYPE
    SYNTAX      Counter64
    MAX-ACCESS  read-only
    STATUS      current
    DESCRIPTION
        "The value of vRtrIfDcpFpLocMonExcdCount indicates number of packets
         exceeding the policing parameters since the given local-monitoring
         policer was previously declared as conformant or newly instantiated."
    ::= { vRtrIfDcpFpLocMonStatEntry 3 }

vRtrIfDcpFpLocMonExcdCountHi     OBJECT-TYPE
    SYNTAX      Counter32
    MAX-ACCESS  read-only
    STATUS      current
    DESCRIPTION
        "The value of vRtrIfDcpFpLocMonExcdCountHi indicates upper 32-bits of
         vRtrIfDcpFpLocMonExcdCount."
    ::= { vRtrIfDcpFpLocMonStatEntry 4 }

vRtrIfDcpFpLocMonExcdCountLo     OBJECT-TYPE
    SYNTAX      Counter32
    MAX-ACCESS  read-only
    STATUS      current
    DESCRIPTION
        "The value of vRtrIfDcpFpLocMonExcdCountLo indicates lower 32-bits of
         vRtrIfDcpFpLocMonExcdCount."
    ::= { vRtrIfDcpFpLocMonStatEntry 5 }

vRtrIfDcpFpLocMonAllDynAlloc     OBJECT-TYPE
    SYNTAX      TruthValue
    MAX-ACCESS  read-only
    STATUS      current
    DESCRIPTION
        "The value of vRtrIfDcpFpLocMonAllDynAlloc indicates whether all the
         dynamic policers associated with this local-monitor have been
         allocated."
    ::= { vRtrIfDcpFpLocMonStatEntry 6 }

vRtrIfDcpFpLocMonTotalExcdCount  OBJECT-TYPE
    SYNTAX      Counter64
    MAX-ACCESS  read-only
    STATUS      current
    DESCRIPTION
        "The value of vRtrIfDcpFpLocMonTotalExcdCount indicates the total
         number of packets exceeding the policing parameters."
    ::= { vRtrIfDcpFpLocMonStatEntry 7 }

vRtrIfDcpFpLocMonExtCnfrmStCount OBJECT-TYPE
    SYNTAX      Counter32
    MAX-ACCESS  read-only
    STATUS      current
    DESCRIPTION
        "The value of vRtrIfDcpFpLocMonExtCnfrmStCount indicates the total
         number of transition of the policer to the exceed state."
    ::= { vRtrIfDcpFpLocMonStatEntry 8 }

vRtrIfDHCP6ProxyDuidTableLastCh  OBJECT-TYPE
    SYNTAX      TimeStamp
    MAX-ACCESS  read-only
    STATUS      current
    DESCRIPTION
        "The value of the object vRtrIfDHCP6ProxyDuidTableLastCh indicates the
         time of the last change to any row of vRtrIfDHCP6ProxyDuidTable"
    ::= { tmnxVRtrObjs 88 }

vRtrIfDHCP6ProxyDuidTable        OBJECT-TYPE
    SYNTAX      SEQUENCE OF VRtrIfDHCP6ProxyDuidEntry
    MAX-ACCESS  not-accessible
    STATUS      current
    DESCRIPTION
        "The vRtrIfDHCP6ProxyDuidTable provides an extension to the
         vRtrIfTable. It has an entry for each virtual router interface
         configured in the system to configure parameters for DHCP Unique
         Identifier (DUID)."
    ::= { tmnxVRtrObjs 89 }

vRtrIfDHCP6ProxyDuidEntry        OBJECT-TYPE
    SYNTAX      VRtrIfDHCP6ProxyDuidEntry
    MAX-ACCESS  not-accessible
    STATUS      current
    DESCRIPTION
        "Each row entry represents information related to DUID for a virtual
         router interface in the system.

         Entries cannot be created and deleted via SNMP SET operations."
    AUGMENTS    { vRtrIfEntry }
    ::= { vRtrIfDHCP6ProxyDuidTable 1 }

VRtrIfDHCP6ProxyDuidEntry        ::= SEQUENCE
{
    vRtrIfDHCP6ProxyDuidLastChanged  TimeStamp,
    vRtrIfDHCP6ProxyDuidTypeCode     TmnxDhcpServerDUIDTypeCode,
    vRtrIfDHCP6ProxyDuidEnNumber     Unsigned32,
    vRtrIfDHCP6ProxyDuidEnIdData     OCTET STRING,
    vRtrIfDHCP6ProxyDuidEnIdDataType TmnxDhcpOptionType
}

vRtrIfDHCP6ProxyDuidLastChanged  OBJECT-TYPE
    SYNTAX      TimeStamp
    MAX-ACCESS  read-only
    STATUS      current
    DESCRIPTION
        "The value of vRtrIfDHCP6ProxyDuidLastChanged indicates the sysUpTime
         at the time of the last change of an entry in the
         vRtrIfDHCP6ProxyDuidTable."
    ::= { vRtrIfDHCP6ProxyDuidEntry 1 }

vRtrIfDHCP6ProxyDuidTypeCode     OBJECT-TYPE
    SYNTAX      TmnxDhcpServerDUIDTypeCode
    MAX-ACCESS  read-create
    STATUS      current
    DESCRIPTION
        "The value of vRtrIfDHCP6ProxyDuidTypeCode specifies the type code of
         the server DUID."
    REFERENCE
        "RFC 3315 paragraph 9.1"
    DEFVAL      { duidLinkLocal }
    ::= { vRtrIfDHCP6ProxyDuidEntry 2 }

vRtrIfDHCP6ProxyDuidEnNumber     OBJECT-TYPE
    SYNTAX      Unsigned32
    MAX-ACCESS  read-only
    STATUS      current
    DESCRIPTION
        "The value of vRtrIfDHCP6ProxyDuidEnNumber indicates the
         enterprise-number. The enterprise-number is the vendor's registered
         Private Enterprise Number as maintained by IANA."
    REFERENCE
        "RFC 3315 paragraph 9.3"
    ::= { vRtrIfDHCP6ProxyDuidEntry 3 }

vRtrIfDHCP6ProxyDuidEnIdData     OBJECT-TYPE
    SYNTAX      OCTET STRING (SIZE (0..58))
    MAX-ACCESS  read-create
    STATUS      current
    DESCRIPTION
        "The value vRtrIfDHCP6ProxyDuidEnIdData specifies the variable length
         identifier following the type code and enterprise-number."
    REFERENCE
        "RFC 3315 paragraph 9.3"
    DEFVAL      { "" }
    ::= { vRtrIfDHCP6ProxyDuidEntry 4 }

vRtrIfDHCP6ProxyDuidEnIdDataType OBJECT-TYPE
    SYNTAX      TmnxDhcpOptionType
    MAX-ACCESS  read-create
    STATUS      current
    DESCRIPTION
        "The value vRtrIfDHCP6ProxyDuidEnIdDataType specifies the type of
         vRtrIfDHCP6ProxyDuidEnIdData."
    DEFVAL      { ascii }
    ::= { vRtrIfDHCP6ProxyDuidEntry 5 }

vRtrIfMacAccountingStatsTable    OBJECT-TYPE
    SYNTAX      SEQUENCE OF VRtrIfMacAccountingStatsEntry
    MAX-ACCESS  not-accessible
    STATUS      current
    DESCRIPTION
        "The vRtrIfMacAccountingStatsTable table contains MAC statistics per
         virtual router interface."
    ::= { tmnxVRtrObjs 90 }

vRtrIfMacAccountingStatsEntry    OBJECT-TYPE
    SYNTAX      VRtrIfMacAccountingStatsEntry
    MAX-ACCESS  not-accessible
    STATUS      current
    DESCRIPTION
        "Each row entry represents the MAC statistics per virtual router
         interface."
    INDEX       {
        vRtrID,
        vRtrIfIndex,
        vRtrIfSourceMacAddress
    }
    ::= { vRtrIfMacAccountingStatsTable 1 }

VRtrIfMacAccountingStatsEntry    ::= SEQUENCE
{
    vRtrIfSourceMacAddress           MacAddress,
    vRtrIfMacAccountingInOctets      Counter64,
    vRtrIfMacAccountingInOctetsL     Counter32,
    vRtrIfMacAccountingInOctetsH     Counter32,
    vRtrIfMacAccountingInFrames      Counter64,
    vRtrIfMacAccountingInFramesL     Counter32,
    vRtrIfMacAccountingInFramesH     Counter32,
    vRtrIfMacAccountingOutOctets     Counter64,
    vRtrIfMacAccountingOutOctetsL    Counter32,
    vRtrIfMacAccountingOutOctetsH    Counter32,
    vRtrIfMacAccountingOutFrames     Counter64,
    vRtrIfMacAccountingOutFramesL    Counter32,
    vRtrIfMacAccountingOutFramesH    Counter32
}

vRtrIfSourceMacAddress           OBJECT-TYPE
    SYNTAX      MacAddress
    MAX-ACCESS  not-accessible
    STATUS      current
    DESCRIPTION
        "The value of the object vRtrIfSourceMacAddress indicates the source
         MAC address."
    ::= { vRtrIfMacAccountingStatsEntry 1 }

vRtrIfMacAccountingInOctets      OBJECT-TYPE
    SYNTAX      Counter64
    MAX-ACCESS  read-only
    STATUS      current
    DESCRIPTION
        "The value of the object vRtrIfMacAccountingInOctets indicates the
         number of total octets received in this MAC Address."
    ::= { vRtrIfMacAccountingStatsEntry 2 }

vRtrIfMacAccountingInOctetsL     OBJECT-TYPE
    SYNTAX      Counter32
    MAX-ACCESS  read-only
    STATUS      current
    DESCRIPTION
        "The value of vRtrIfMacAccountingInOctetsL indicates the lower 32 bits
         of vRtrIfMacAccountingInOctets."
    ::= { vRtrIfMacAccountingStatsEntry 3 }

vRtrIfMacAccountingInOctetsH     OBJECT-TYPE
    SYNTAX      Counter32
    MAX-ACCESS  read-only
    STATUS      current
    DESCRIPTION
        "The value of vRtrIfMacAccountingInOctetsH indicates the higher 32 bits
         of vRtrIfMacAccountingInOctets."
    ::= { vRtrIfMacAccountingStatsEntry 4 }

vRtrIfMacAccountingInFrames      OBJECT-TYPE
    SYNTAX      Counter64
    MAX-ACCESS  read-only
    STATUS      current
    DESCRIPTION
        "The value of the object vRtrIfMacAccountingInFrames indicates the
         number of total frames received in this MAC Address."
    ::= { vRtrIfMacAccountingStatsEntry 5 }

vRtrIfMacAccountingInFramesL     OBJECT-TYPE
    SYNTAX      Counter32
    MAX-ACCESS  read-only
    STATUS      current
    DESCRIPTION
        "The value of vRtrIfMacAccountingInFramesL indicates the lower 32 bits
         of vRtrIfMacAccountingInFrames."
    ::= { vRtrIfMacAccountingStatsEntry 6 }

vRtrIfMacAccountingInFramesH     OBJECT-TYPE
    SYNTAX      Counter32
    MAX-ACCESS  read-only
    STATUS      current
    DESCRIPTION
        "The value of vRtrIfMacAccountingInFramesH indicates the higher 32 bits
         of vRtrIfMacAccountingInFrames."
    ::= { vRtrIfMacAccountingStatsEntry 7 }

vRtrIfMacAccountingOutOctets     OBJECT-TYPE
    SYNTAX      Counter64
    MAX-ACCESS  read-only
    STATUS      current
    DESCRIPTION
        "The value of the object vRtrIfMacAccountingOutOctets indicates the
         number of total octets transmitted in this MAC Address."
    ::= { vRtrIfMacAccountingStatsEntry 8 }

vRtrIfMacAccountingOutOctetsL    OBJECT-TYPE
    SYNTAX      Counter32
    MAX-ACCESS  read-only
    STATUS      current
    DESCRIPTION
        "The value of vRtrIfMacAccountingOutOctetsL indicates the lower 32 bits
         of vRtrIfMacAccountingOutOctets."
    ::= { vRtrIfMacAccountingStatsEntry 9 }

vRtrIfMacAccountingOutOctetsH    OBJECT-TYPE
    SYNTAX      Counter32
    MAX-ACCESS  read-only
    STATUS      current
    DESCRIPTION
        "The value of vRtrIfMacAccountingOutOctetsH indicates the higher 32
         bits of vRtrIfMacAccountingOutOctets."
    ::= { vRtrIfMacAccountingStatsEntry 10 }

vRtrIfMacAccountingOutFrames     OBJECT-TYPE
    SYNTAX      Counter64
    MAX-ACCESS  read-only
    STATUS      current
    DESCRIPTION
        "The value of the object vRtrIfMacAccountingOutFrames indicates the
         number of total frames transmitted in this MAC Address."
    ::= { vRtrIfMacAccountingStatsEntry 11 }

vRtrIfMacAccountingOutFramesL    OBJECT-TYPE
    SYNTAX      Counter32
    MAX-ACCESS  read-only
    STATUS      current
    DESCRIPTION
        "The value of vRtrIfMacAccountingOutFramesL indicates the lower 32 bits
         of vRtrIfMacAccountingOutFrames."
    ::= { vRtrIfMacAccountingStatsEntry 12 }

vRtrIfMacAccountingOutFramesH    OBJECT-TYPE
    SYNTAX      Counter32
    MAX-ACCESS  read-only
    STATUS      current
    DESCRIPTION
        "The value of vRtrIfMacAccountingOutFramesH indicates the higher 32
         bits of vRtrIfMacAccountingOutFrames."
    ::= { vRtrIfMacAccountingStatsEntry 13 }

vRtrIpv6RtrAdvertTable           OBJECT-TYPE
    SYNTAX      SEQUENCE OF VRtrIpv6RtrAdvertEntry
    MAX-ACCESS  not-accessible
    STATUS      current
    DESCRIPTION
        "The vRtrIpv6RtrAdvertTable provides an extension to the
         ipv6RouterAdvertTable in the IP-MIB."
    ::= { tmnxVRtrObjs 91 }

vRtrIpv6RtrAdvertEntry           OBJECT-TYPE
    SYNTAX      VRtrIpv6RtrAdvertEntry
    MAX-ACCESS  not-accessible
    STATUS      current
    DESCRIPTION
        "The vRtrIpv6RtrAdvertEntry provides virtual router specific extension
         to the ipv6RouterAdvertEntry in the IP-MIB.

         Use of AUGMENTS clause implies a one-to-one dependent relationship
         between the base table, ipv6RouterAdvertTable, and the augmenting
         table, vRtrIpv6RtrAdvertTable. This in effect extends the
         ipv6RouterAdvertTable with additional columns.

         Creation (or deletion) of a row in the ipv6RouterAdvertTable results
         in the same fate for the row in the vRtrIpv6RtrAdvertTable."
    AUGMENTS    { ipv6RouterAdvertEntry }
    ::= { vRtrIpv6RtrAdvertTable 1 }

VRtrIpv6RtrAdvertEntry           ::= SEQUENCE
{
    vRtrIpv6RtrAdvertCreationOrigin  TmnxCreateOrigin,
    vRtrIpv6RtrAdvertNdRtrPreference INTEGER
}

vRtrIpv6RtrAdvertCreationOrigin  OBJECT-TYPE
    SYNTAX      TmnxCreateOrigin
    MAX-ACCESS  read-only
    STATUS      current
    DESCRIPTION
        "The value of vRtrIpv6RtrAdvertCreationOrigin indicates the mechanism
         which created this router advertisement."
    ::= { vRtrIpv6RtrAdvertEntry 1 }

vRtrIpv6RtrAdvertNdRtrPreference OBJECT-TYPE
    SYNTAX      INTEGER {
        medium (0),
        high   (1),
        low    (3)
    }
    MAX-ACCESS  read-create
    STATUS      current
    DESCRIPTION
        "The value of vRtrIpv6RtrAdvertNdRtrPreference specifies the  default
         router preference that is present in Neighbor Discovery router
         advertisements."
    DEFVAL      { medium }
    ::= { vRtrIpv6RtrAdvertEntry 2 }

vRtrIfBfdSessExtTable            OBJECT-TYPE
    SYNTAX      SEQUENCE OF VRtrIfBfdSessExtEntry
    MAX-ACCESS  not-accessible
    STATUS      current
    DESCRIPTION
        "The vRtrIfBfdSessExtTable table contains per BFD session statistics
         and operational settings."
    ::= { tmnxVRtrObjs 92 }

vRtrIfBfdSessExtEntry            OBJECT-TYPE
    SYNTAX      VRtrIfBfdSessExtEntry
    MAX-ACCESS  not-accessible
    STATUS      current
    DESCRIPTION
        "Each row entry represents a BFD session. Entries are created
         automatically by the system, or when a static route is configured to
         use BFD."
    INDEX       {
        vRtrIfBfdSessExtLinkType,
        vRtrIfBfdSessExtRxInfoId,
        vRtrID,
        vRtrIfIndex,
        vRtrIfBfdSessExtLclAddrType,
        vRtrIfBfdSessExtLclAddr,
        vRtrIfBfdSessExtRemAddrType,
        vRtrIfBfdSessExtRemAddr
    }
    ::= { vRtrIfBfdSessExtTable 1 }

VRtrIfBfdSessExtEntry            ::= SEQUENCE
{
    vRtrIfBfdSessExtLinkType         INTEGER,
    vRtrIfBfdSessExtRxInfoId         Unsigned32,
    vRtrIfBfdSessExtLclAddrType      InetAddressType,
    vRtrIfBfdSessExtLclAddr          InetAddress,
    vRtrIfBfdSessExtRemAddrType      InetAddressType,
    vRtrIfBfdSessExtRemAddr          InetAddress,
    vRtrIfBfdSessExtOperState        TmnxOperState,
    vRtrIfBfdSessExtState            TmnxBfdSessProtocolState,
    vRtrIfBfdSessExtOperFlags        TmnxBfdSessOperFlags,
    vRtrIfBfdSessExtMesgRecv         Counter32,
    vRtrIfBfdSessExtMesgSent         Counter32,
    vRtrIfBfdSessExtLastDownTime     TimeTicks,
    vRtrIfBfdSessExtLastUpTime       TimeTicks,
    vRtrIfBfdSessExtUpCount          Counter32,
    vRtrIfBfdSessExtDownCount        Counter32,
    vRtrIfBfdSessExtLclDisc          Unsigned32,
    vRtrIfBfdSessExtRemDisc          Unsigned32,
    vRtrIfBfdSessExtProtocols        TmnxBfdSessionProtocols,
    vRtrIfBfdSessExtTxInterval       Unsigned32,
    vRtrIfBfdSessExtRxInterval       Unsigned32,
    vRtrIfBfdSessExtType             TmnxBfdTermination,
    vRtrIfBfdSessExtVerMismatch      Counter32,
    vRtrIfBfdSessExtTimeSinceLastRx  Unsigned32,
    vRtrIfBfdSessExtTimeSinceLastTx  Unsigned32,
    vRtrIfBfdSessExtRemoteLspNum     Unsigned32,
    vRtrIfBfdSessExtRemoteTunnelNum  Unsigned32,
    vRtrIfBfdSessExtRemoteNodeId     TmnxMplsTpNodeID,
    vRtrIfBfdSessExtRemoteGlobalId   TmnxMplsTpGlobalID,
    vRtrIfBfdSessExtLspPathTunnelId  Unsigned32,
    vRtrIfBfdSessExtLspPathId        INTEGER,
    vRtrIfBfdSessExtSvcId            TmnxServId,
    vRtrIfBfdSessExtSdpBindId        SdpBindId
}

vRtrIfBfdSessExtLinkType         OBJECT-TYPE
    SYNTAX      INTEGER {
        pointToPoint (0),
        head         (1),
        tail         (2),
        client       (3),
        ccOnly       (4),
        ccWithCv     (5),
        microBfd     (6),
        vccvBfd      (7),
        reserved10   (10)
    }
    MAX-ACCESS  not-accessible
    STATUS      current
    DESCRIPTION
        "The value of vRtrIfBfdSessExtLinkType indicates the link type of the
         BFD session."
    ::= { vRtrIfBfdSessExtEntry 1 }

vRtrIfBfdSessExtRxInfoId         OBJECT-TYPE
    SYNTAX      Unsigned32
    MAX-ACCESS  not-accessible
    STATUS      current
    DESCRIPTION
        "The value of vRtrIfBfdSessExtRxInfoId indicates the incoming label id
         or port id or VCCV BFD session identifier."
    ::= { vRtrIfBfdSessExtEntry 2 }

vRtrIfBfdSessExtLclAddrType      OBJECT-TYPE
    SYNTAX      InetAddressType
    MAX-ACCESS  not-accessible
    STATUS      current
    DESCRIPTION
        "The value of vRtrIfBfdSessExtLclAddrType indicates the address type in
         vRtrIfBfdSessExtLclAddr."
    ::= { vRtrIfBfdSessExtEntry 3 }

vRtrIfBfdSessExtLclAddr          OBJECT-TYPE
    SYNTAX      InetAddress (SIZE (0|4|16|20))
    MAX-ACCESS  not-accessible
    STATUS      current
    DESCRIPTION
        "The value of vRtrIfBfdSessExtLclAddr indicates the address of the
         local endpoint of this BFD session. Its type is specified by
         vRtrIfBfdSessExtLclAddrType."
    ::= { vRtrIfBfdSessExtEntry 4 }

vRtrIfBfdSessExtRemAddrType      OBJECT-TYPE
    SYNTAX      InetAddressType
    MAX-ACCESS  not-accessible
    STATUS      current
    DESCRIPTION
        "The value of vRtrIfBfdSessExtRemAddrType indicates the address type in
         vRtrIfBfdSessExtRemAddr."
    ::= { vRtrIfBfdSessExtEntry 5 }

vRtrIfBfdSessExtRemAddr          OBJECT-TYPE
    SYNTAX      InetAddress (SIZE (0|4|16|20))
    MAX-ACCESS  not-accessible
    STATUS      current
    DESCRIPTION
        "The value of vRtrIfBfdSessExtRemAddr indicates the address of the
         remote endpoint of this BFD session. Its type is specified by
         vRtrIfBfdSessExtRemAddrType."
    ::= { vRtrIfBfdSessExtEntry 6 }

vRtrIfBfdSessExtOperState        OBJECT-TYPE
    SYNTAX      TmnxOperState
    MAX-ACCESS  read-only
    STATUS      current
    DESCRIPTION
        "The value of vRtrIfBfdSessExtOperState indicates the operational state
         of BFD on this interface."
    ::= { vRtrIfBfdSessExtEntry 7 }

vRtrIfBfdSessExtState            OBJECT-TYPE
    SYNTAX      TmnxBfdSessProtocolState
    MAX-ACCESS  read-only
    STATUS      current
    DESCRIPTION
        "The value of vRtrIfBfdSessExtState indicates the state of the BFD
         protocol on this interface."
    ::= { vRtrIfBfdSessExtEntry 8 }

vRtrIfBfdSessExtOperFlags        OBJECT-TYPE
    SYNTAX      TmnxBfdSessOperFlags
    MAX-ACCESS  read-only
    STATUS      current
    DESCRIPTION
        "The value of vRtrIfBfdSessExtOperFlags indicates the reasons why a BFD
         session is not up."
    ::= { vRtrIfBfdSessExtEntry 9 }

vRtrIfBfdSessExtMesgRecv         OBJECT-TYPE
    SYNTAX      Counter32
    MAX-ACCESS  read-only
    STATUS      current
    DESCRIPTION
        "The value of vRtrIfBfdSessExtMesgRecv indicates the number of messages
         received in this session.

         This object is applicable if vRtrIfBfdSessExtType is 'iom(1)' or
         'cpm(2)'.  Otherwise, zero is returned."
    ::= { vRtrIfBfdSessExtEntry 10 }

vRtrIfBfdSessExtMesgSent         OBJECT-TYPE
    SYNTAX      Counter32
    MAX-ACCESS  read-only
    STATUS      current
    DESCRIPTION
        "The value of vRtrIfBfdSessExtMesgSent indicates the number of messages
         sent in this session.

         This object is applicable if vRtrIfBfdSessExtType is 'iom(1)' or
         'cpm(2)'.  Otherwise, zero is returned."
    ::= { vRtrIfBfdSessExtEntry 11 }

vRtrIfBfdSessExtLastDownTime     OBJECT-TYPE
    SYNTAX      TimeTicks
    MAX-ACCESS  read-only
    STATUS      current
    DESCRIPTION
        "The value of vRtrIfBfdSessExtLastDownTime indicates the the time
         elapsed since this session last went down."
    ::= { vRtrIfBfdSessExtEntry 12 }

vRtrIfBfdSessExtLastUpTime       OBJECT-TYPE
    SYNTAX      TimeTicks
    MAX-ACCESS  read-only
    STATUS      current
    DESCRIPTION
        "The value of vRtrIfBfdSessExtLastUpTime indicates the time elapsed
         since the session last came up."
    ::= { vRtrIfBfdSessExtEntry 13 }

vRtrIfBfdSessExtUpCount          OBJECT-TYPE
    SYNTAX      Counter32
    MAX-ACCESS  read-only
    STATUS      current
    DESCRIPTION
        "The value of vRtrIfBfdSessExtUpCount indicates the number of times
         vRtrIfBfdSessExtOperState changed from 'outOfService' to 'inService'."
    ::= { vRtrIfBfdSessExtEntry 14 }

vRtrIfBfdSessExtDownCount        OBJECT-TYPE
    SYNTAX      Counter32
    MAX-ACCESS  read-only
    STATUS      current
    DESCRIPTION
        "The value of vRtrIfBfdSessExtDownCount indicates the number of times
         vRtrIfBfdSessExtOperState changed from 'inService' to 'outOfService'."
    ::= { vRtrIfBfdSessExtEntry 15 }

vRtrIfBfdSessExtLclDisc          OBJECT-TYPE
    SYNTAX      Unsigned32
    MAX-ACCESS  read-only
    STATUS      current
    DESCRIPTION
        "The value of vRtrIfBfdSessExtLclDisc indicates the unique local
         discriminator for this session."
    ::= { vRtrIfBfdSessExtEntry 16 }

vRtrIfBfdSessExtRemDisc          OBJECT-TYPE
    SYNTAX      Unsigned32
    MAX-ACCESS  read-only
    STATUS      current
    DESCRIPTION
        "The value of vRtrIfBfdSessExtRemDisc indicates the remote
         discriminator for this session."
    ::= { vRtrIfBfdSessExtEntry 17 }

vRtrIfBfdSessExtProtocols        OBJECT-TYPE
    SYNTAX      TmnxBfdSessionProtocols
    MAX-ACCESS  read-only
    STATUS      current
    DESCRIPTION
        "The value of vRtrIfBfdSessExtProtocols indicates which protocols are
         using this BFD session."
    ::= { vRtrIfBfdSessExtEntry 18 }

vRtrIfBfdSessExtTxInterval       OBJECT-TYPE
    SYNTAX      Unsigned32
    UNITS       "milliseconds"
    MAX-ACCESS  read-only
    STATUS      current
    DESCRIPTION
        "The value of vRtrIfBfdSessExtTxInterval indicates the negotiated
         transmit interval. This value is the minimum of the local node's
         'vRtrIfBfdExtTransmitInterval' and the remote node's receive interval."
    ::= { vRtrIfBfdSessExtEntry 19 }

vRtrIfBfdSessExtRxInterval       OBJECT-TYPE
    SYNTAX      Unsigned32
    UNITS       "milliseconds"
    MAX-ACCESS  read-only
    STATUS      current
    DESCRIPTION
        "The value of vRtrIfBfdSessExtRxInterval indicates the negotiated
         receive interval. This value is the minimum of the local node's
         'vRtrIfBfdExtReceiveInterval' and the remote node's transmit interval."
    ::= { vRtrIfBfdSessExtEntry 20 }

vRtrIfBfdSessExtType             OBJECT-TYPE
    SYNTAX      TmnxBfdTermination
    MAX-ACCESS  read-only
    STATUS      current
    DESCRIPTION
        "The value of vRtrIfBfdSessExtType indicates the termination of the BFD
         session."
    ::= { vRtrIfBfdSessExtEntry 21 }

vRtrIfBfdSessExtVerMismatch      OBJECT-TYPE
    SYNTAX      Counter32
    MAX-ACCESS  read-only
    STATUS      current
    DESCRIPTION
        "The value of vRtrIfBfdSessExtVerMismatch indicates the number of
         version mismatch errors for the bfd session."
    ::= { vRtrIfBfdSessExtEntry 22 }

vRtrIfBfdSessExtTimeSinceLastRx  OBJECT-TYPE
    SYNTAX      Unsigned32
    UNITS       "milliseconds"
    MAX-ACCESS  read-only
    STATUS      current
    DESCRIPTION
        "The value of vRtrIfBfdSessExtTimeSinceLastRx indicates the number of
         milliseconds elapsed since the most recent message was received on the
         BFD session.  If the session is down, zero is returned.

         This object is applicable to sessions with vRtrIfBfdSessExtType equal
         to 'cpmNp(3)'.  Otherwise, zero is returned."
    ::= { vRtrIfBfdSessExtEntry 23 }

vRtrIfBfdSessExtTimeSinceLastTx  OBJECT-TYPE
    SYNTAX      Unsigned32
    UNITS       "milliseconds"
    MAX-ACCESS  read-only
    STATUS      current
    DESCRIPTION
        "The value of vRtrIfBfdSessExtTimeSinceLastTx indicates the number of
         milliseconds elapsed since the most recent message was transmitted on
         the BFD session.  If the session is down, zero is returned.

         This object is applicable to sessions with vRtrIfBfdSessExtType equal
         to 'cpmNp(3)'.  Otherwise, zero is returned."
    ::= { vRtrIfBfdSessExtEntry 24 }

vRtrIfBfdSessExtRemoteLspNum     OBJECT-TYPE
    SYNTAX      Unsigned32
    MAX-ACCESS  read-only
    STATUS      current
    DESCRIPTION
        "The value of vRtrIfBfdSessExtRemoteLspNum indicates the MPLS-TP LSP
         destination path number."
    REFERENCE
        "RFC 6370 Section 5.2"
    ::= { vRtrIfBfdSessExtEntry 25 }

vRtrIfBfdSessExtRemoteTunnelNum  OBJECT-TYPE
    SYNTAX      Unsigned32
    MAX-ACCESS  read-only
    STATUS      current
    DESCRIPTION
        "The value of vRtrIfBfdSessExtRemoteTunnelNum indicates the destination
         tunnel id for the MPLS-TP path."
    ::= { vRtrIfBfdSessExtEntry 26 }

vRtrIfBfdSessExtRemoteNodeId     OBJECT-TYPE
    SYNTAX      TmnxMplsTpNodeID
    MAX-ACCESS  read-only
    STATUS      current
    DESCRIPTION
        "The value of vRtrIfBfdSessExtRemoteNodeId indicates the destination
         node id of an MPLS-TP LSP."
    ::= { vRtrIfBfdSessExtEntry 27 }

vRtrIfBfdSessExtRemoteGlobalId   OBJECT-TYPE
    SYNTAX      TmnxMplsTpGlobalID
    MAX-ACCESS  read-only
    STATUS      current
    DESCRIPTION
        "The value of vRtrIfBfdSessExtRemoteGlobalId indicates the global
         identifier for an MPLS-TP LSP."
    ::= { vRtrIfBfdSessExtEntry 28 }

vRtrIfBfdSessExtLspPathTunnelId  OBJECT-TYPE
    SYNTAX      Unsigned32
    MAX-ACCESS  read-only
    STATUS      current
    DESCRIPTION
        "The value of vRtrIfBfdSessExtLspPathTunnelId indicates the source
         tunnel id for the MPLS-TP path."
    ::= { vRtrIfBfdSessExtEntry 29 }

vRtrIfBfdSessExtLspPathId        OBJECT-TYPE
    SYNTAX      INTEGER {
        notApplicable (0),
        working       (1),
        protecting    (2)
    }
    MAX-ACCESS  read-only
    STATUS      current
    DESCRIPTION
        "The value of vRtrIfBfdSessExtLspPathId indicates the source path index
         for the MPLS-TP LSP path.
         notApplicable (0) - Indicates vRtrIfBfdSessExtLinkType is neither
                             'ccOnly' or 'ccWithCv'.
         working (1)    - A working path is the primary path for the LSP.
         protecting (2) - A protection path is the secondary path for the
                          LSP."
    ::= { vRtrIfBfdSessExtEntry 30 }

vRtrIfBfdSessExtSvcId            OBJECT-TYPE
    SYNTAX      TmnxServId
    MAX-ACCESS  read-only
    STATUS      current
    DESCRIPTION
        "The vRtrIfBfdSessExtSvcId indicates associated service-id with this
         BFD session when vRtrIfBfdExtType is set to 'vccvBfd'."
    ::= { vRtrIfBfdSessExtEntry 31 }

vRtrIfBfdSessExtSdpBindId        OBJECT-TYPE
    SYNTAX      SdpBindId
    MAX-ACCESS  read-only
    STATUS      current
    DESCRIPTION
        "The vRtrIfBfdSessExtSdpBindId indicates associated SDP Bind identifier
         with this BFD session when vRtrIfBfdExtType is set to 'vccvBfd'."
    ::= { vRtrIfBfdSessExtEntry 32 }

tmnxVrtrIfAdminGrpTableLastCh    OBJECT-TYPE
    SYNTAX      TimeStamp
    MAX-ACCESS  read-only
    STATUS      current
    DESCRIPTION
        "The value of the object tmnxVrtrIfAdminGrpTableLastCh indicates the
         time of the last change to any row of tmnxVrtrIfAdminGroupTable"
    ::= { tmnxVRtrObjs 93 }

tmnxVrtrIfAdminGroupTable        OBJECT-TYPE
    SYNTAX      SEQUENCE OF TmnxVrtrIfAdminGroupEntry
    MAX-ACCESS  not-accessible
    STATUS      current
    DESCRIPTION
        "The tmnxVrtrIfAdminGroupTable table contains the Interface Admin
         Groups that are mapped to this vRtr Interface."
    ::= { tmnxVRtrObjs 94 }

tmnxVrtrIfAdminGroupEntry        OBJECT-TYPE
    SYNTAX      TmnxVrtrIfAdminGroupEntry
    MAX-ACCESS  not-accessible
    STATUS      current
    DESCRIPTION
        "Each row entry represents a mapping between a vRtr interface and an
         Interface Admin Group."
    INDEX       {
        vRtrID,
        vRtrIfIndex,
        IMPLIED tmnxAdminGrpName
    }
    ::= { tmnxVrtrIfAdminGroupTable 1 }

TmnxVrtrIfAdminGroupEntry        ::= SEQUENCE
{
    tmnxVrtrIfAdminGroupRowStatus    RowStatus,
    tmnxVrtrIfAdminGroupLastCh       TimeStamp
}

tmnxVrtrIfAdminGroupRowStatus    OBJECT-TYPE
    SYNTAX      RowStatus
    MAX-ACCESS  read-create
    STATUS      current
    DESCRIPTION
        "The value of the object tmnxVrtrIfAdminGroupRowStatus specifies the
         Row status of this table row. This object is used to create or delete
         rows in this table."
    ::= { tmnxVrtrIfAdminGroupEntry 1 }

tmnxVrtrIfAdminGroupLastCh       OBJECT-TYPE
    SYNTAX      TimeStamp
    MAX-ACCESS  read-only
    STATUS      current
    DESCRIPTION
        "The value of tmnxVrtrIfAdminGroupLastCh indicates the sysUpTime when
         any object of the row is last changed."
    ::= { tmnxVrtrIfAdminGroupEntry 2 }

tmnxVrtrIfSrlgGrpTableLastCh     OBJECT-TYPE
    SYNTAX      TimeStamp
    MAX-ACCESS  read-only
    STATUS      current
    DESCRIPTION
        "The value of the object tmnxVrtrIfSrlgGrpTableLastCh indicates the
         time of the last change to any row of tmnxVrtrIfSrlgGroupTable"
    ::= { tmnxVRtrObjs 95 }

tmnxVrtrIfSrlgGroupTable         OBJECT-TYPE
    SYNTAX      SEQUENCE OF TmnxVrtrIfSrlgGroupEntry
    MAX-ACCESS  not-accessible
    STATUS      current
    DESCRIPTION
        "The tmnxVrtrIfSrlgGroupTable table contains the Interface SRLG Groups
         that are mapped to this vRtr Interface."
    ::= { tmnxVRtrObjs 96 }

tmnxVrtrIfSrlgGroupEntry         OBJECT-TYPE
    SYNTAX      TmnxVrtrIfSrlgGroupEntry
    MAX-ACCESS  not-accessible
    STATUS      current
    DESCRIPTION
        "Each row entry represents a mapping between a vRtr interface and an
         Interface SRLG Group."
    INDEX       {
        vRtrID,
        vRtrIfIndex,
        IMPLIED tmnxSrlgGrpName
    }
    ::= { tmnxVrtrIfSrlgGroupTable 1 }

TmnxVrtrIfSrlgGroupEntry         ::= SEQUENCE
{
    tmnxVrtrIfSrlgGroupRowStatus     RowStatus,
    tmnxVrtrIfSrlgGroupLastCh        TimeStamp
}

tmnxVrtrIfSrlgGroupRowStatus     OBJECT-TYPE
    SYNTAX      RowStatus
    MAX-ACCESS  read-create
    STATUS      current
    DESCRIPTION
        "The value of the object tmnxVrtrIfSrlgGroupRowStatus specifies the Row
         status of this table row. This object is used to create or delete rows
         in this table."
    ::= { tmnxVrtrIfSrlgGroupEntry 1 }

tmnxVrtrIfSrlgGroupLastCh        OBJECT-TYPE
    SYNTAX      TimeStamp
    MAX-ACCESS  read-only
    STATUS      current
    DESCRIPTION
        "The value of tmnxVrtrIfSrlgGroupLastCh indicates the sysUpTime when
         any object of the row is last changed."
    ::= { tmnxVrtrIfSrlgGroupEntry 2 }

vRtrIfSendTableLastChanged       OBJECT-TYPE
    SYNTAX      TimeStamp
    MAX-ACCESS  read-only
    STATUS      current
    DESCRIPTION
        "The value of the object vRtrIfSendTableLastChanged indicates the time
         of the last change to any row of vRtrIfSendTable."
    ::= { tmnxVRtrObjs 97 }

vRtrIfSendTable                  OBJECT-TYPE
    SYNTAX      SEQUENCE OF VRtrIfSendEntry
    MAX-ACCESS  not-accessible
    STATUS      current
    DESCRIPTION
        "The vRtrIfSendTable provides a sparse extension to the vRtrIfTable to
         configure parameters for SEcure Neighbor Discovery (SEND). It has an
         entry for IPv6-enabled interfaces. This is not supported on subscriber
         and group interfaces."
    ::= { tmnxVRtrObjs 98 }

vRtrIfSendEntry                  OBJECT-TYPE
    SYNTAX      VRtrIfSendEntry
    MAX-ACCESS  not-accessible
    STATUS      current
    DESCRIPTION
        "Each row entry represents information related to SEND for a virtual
         router interface in the system.

         Entries cannot be created and deleted via SNMP SET operations."
    INDEX       {
        vRtrID,
        vRtrIfIndex
    }
    ::= { vRtrIfSendTable 1 }

VRtrIfSendEntry                  ::= SEQUENCE
{
    vRtrIfSendLastChanged            TimeStamp,
    vRtrIfSendAdminState             TmnxAdminState,
    vRtrIfSendAllowUnsecuredMsgs     TruthValue,
    vRtrIfSendCgaSecurityParameter   Unsigned32,
    vRtrIfSendCgaVerificationMinbits Unsigned32,
    vRtrIfSendLinkLocalCgaModifier   TmnxSendCgaModifier
}

vRtrIfSendLastChanged            OBJECT-TYPE
    SYNTAX      TimeStamp
    MAX-ACCESS  read-only
    STATUS      current
    DESCRIPTION
        "The value of vRtrIfSendLastChanged indicates the sysUpTime at the time
         of the last change of an entry in the vRtrIfSendTable."
    ::= { vRtrIfSendEntry 1 }

vRtrIfSendAdminState             OBJECT-TYPE
    SYNTAX      TmnxAdminState
    MAX-ACCESS  read-write
    STATUS      current
    DESCRIPTION
        "The value of vRtrIfSendAdminState specifies the administrative state
         of this entry."
    DEFVAL      { outOfService }
    ::= { vRtrIfSendEntry 2 }

vRtrIfSendAllowUnsecuredMsgs     OBJECT-TYPE
    SYNTAX      TruthValue
    MAX-ACCESS  read-write
    STATUS      current
    DESCRIPTION
        "The value of vRtrIfSendAllowUnsecuredMsgs specifies whether unsecured
         Neighbor Solicitation and Advertisement, Router Solicitation and
         Advertisement, and Redirect messages are accepted or ignored."
    REFERENCE
        "RFC 3971 paragraph 8"
    DEFVAL      { true }
    ::= { vRtrIfSendEntry 3 }

vRtrIfSendCgaSecurityParameter   OBJECT-TYPE
    SYNTAX      Unsigned32 (0..1)
    MAX-ACCESS  read-write
    STATUS      current
    DESCRIPTION
        "The value of vRtrIfSendCgaSecurityParameter specifies the security
         parameter to be used during the cryptographic generation of an
         address. It determines the strength of the Cryptographically Generated
         Address (CGA) against brute-force attacks."
    REFERENCE
        "RFC 3972 paragraph 2"
    DEFVAL      { 1 }
    ::= { vRtrIfSendEntry 4 }

vRtrIfSendCgaVerificationMinbits OBJECT-TYPE
    SYNTAX      Unsigned32 (512..1024)
    MAX-ACCESS  read-write
    STATUS      current
    DESCRIPTION
        "The value of vRtrIfSendCgaVerificationMinbits specifies the minimum
         acceptable key length for public keys used in the generation of CGAs."
    REFERENCE
        "RFC 3971 paragraph 5.1.3"
    DEFVAL      { 1024 }
    ::= { vRtrIfSendEntry 5 }

vRtrIfSendLinkLocalCgaModifier   OBJECT-TYPE
    SYNTAX      TmnxSendCgaModifier
    MAX-ACCESS  read-write
    STATUS      current
    DESCRIPTION
        "The value of vRtrIfSendLinkLocalCgaModifier specifies the modifier
         used during link-local CGA generation.

         The value of vRtrIfSendLinkLocalCgaModifier must have been generated
         with the RSA key pair and security parameter that is associated with
         this interface.

         The value all zeroes means that no modifier is specified; however,
         setting the value to all zeroes in an existing row while Secure
         Neighbor Discovery is enabled on its interface, causes the generation
         of a new CGA and a new modifier; Secure Neighbor Discovery is enabled
         on its interface by means of the object vRtrIfSendAdminState."
    REFERENCE
        "RFC 3972 Cryptographically Generated Addresses
         section 3 CGA Parameters"
    DEFVAL      { '00000000000000000000000000000000'H }
    ::= { vRtrIfSendEntry 6 }

tmnxAdminGroupTblLastCh          OBJECT-TYPE
    SYNTAX      TimeStamp
    MAX-ACCESS  read-only
    STATUS      current
    DESCRIPTION
        "The value of tmnxAdminGroupTblLastCh indicates the sysUpTime at the
         time of the last modification of an entry in the tmnxAdminGroupTable."
    ::= { tmnxVRtrObjs 99 }

tmnxAdminGroupTable              OBJECT-TYPE
    SYNTAX      SEQUENCE OF TmnxAdminGroupEntry
    MAX-ACCESS  not-accessible
    STATUS      current
    DESCRIPTION
        "The tmnxAdminGroupTable contains the administrative groups used to tag
         IP interfaces which share a specific characteristic with the same
         identifier."
    ::= { tmnxVRtrObjs 100 }

tmnxAdminGroupEntry              OBJECT-TYPE
    SYNTAX      TmnxAdminGroupEntry
    MAX-ACCESS  not-accessible
    STATUS      current
    DESCRIPTION
        "Each row represents an administrative group."
    INDEX       { IMPLIED tmnxAdminGrpName }
    ::= { tmnxAdminGroupTable 1 }

TmnxAdminGroupEntry              ::= SEQUENCE
{
    tmnxAdminGrpName                 TNamedItem,
    tmnxAdminGrpRowStatus            RowStatus,
    tmnxAdminGrpRowLstChng           TimeStamp,
    tmnxAdminGrpValue                Unsigned32
}

tmnxAdminGrpName                 OBJECT-TYPE
    SYNTAX      TNamedItem
    MAX-ACCESS  not-accessible
    STATUS      current
    DESCRIPTION
        "The value of tmnxAdminGrpName specifies the name defined for the admin
         group."
    ::= { tmnxAdminGroupEntry 1 }

tmnxAdminGrpRowStatus            OBJECT-TYPE
    SYNTAX      RowStatus
    MAX-ACCESS  read-create
    STATUS      current
    DESCRIPTION
        "The value of tmnxAdminGrpRowStatus controls the creation and deletion
         of rows in the table.

         A value must be set for tmnxAdminGrpValue as well at time of row
         creation."
    ::= { tmnxAdminGroupEntry 2 }

tmnxAdminGrpRowLstChng           OBJECT-TYPE
    SYNTAX      TimeStamp
    MAX-ACCESS  read-only
    STATUS      current
    DESCRIPTION
        "The value tmnxAdminGrpRowLstChng indicates the sysUpTime at the time
         of the most recent management-initiated change to this admin group."
    ::= { tmnxAdminGroupEntry 3 }

tmnxAdminGrpValue                OBJECT-TYPE
    SYNTAX      Unsigned32 (0..255)
    MAX-ACCESS  read-create
    STATUS      current
    DESCRIPTION
        "The value of tmnxAdminGrpValue specifies the group value associated
         with this administrative group. This value is unique within a virtual
         router instance.

         This object must be set at row creation."
    ::= { tmnxAdminGroupEntry 4 }

tmnxSrlgGroupTblLastCh           OBJECT-TYPE
    SYNTAX      TimeStamp
    MAX-ACCESS  read-only
    STATUS      current
    DESCRIPTION
        "The value of tmnxSrlgGroupTblLastCh indicates the sysUpTime at the
         time of the last modification of an entry in the tmnxSrlgGroupTable."
    ::= { tmnxVRtrObjs 101 }

tmnxSrlgGroupTable               OBJECT-TYPE
    SYNTAX      SEQUENCE OF TmnxSrlgGroupEntry
    MAX-ACCESS  not-accessible
    STATUS      current
    DESCRIPTION
        "The tmnxSrlgGroupTable contains the Shared Risk Loss Groups (SRLG)
         used to tag IP interfaces which share a specific fate."
    ::= { tmnxVRtrObjs 102 }

tmnxSrlgGroupEntry               OBJECT-TYPE
    SYNTAX      TmnxSrlgGroupEntry
    MAX-ACCESS  not-accessible
    STATUS      current
    DESCRIPTION
        "Each row represents a Shared Risk Loss Group (SRLG)."
    INDEX       { IMPLIED tmnxSrlgGrpName }
    ::= { tmnxSrlgGroupTable 1 }

TmnxSrlgGroupEntry               ::= SEQUENCE
{
    tmnxSrlgGrpName                  TNamedItem,
    tmnxSrlgGrpRowStatus             RowStatus,
    tmnxSrlgGrpRowLstChng            TimeStamp,
    tmnxSrlgGrpValue                 Unsigned32,
    tmnxSrlgGrpPenaltyWeight         Unsigned32
}

tmnxSrlgGrpName                  OBJECT-TYPE
    SYNTAX      TNamedItem
    MAX-ACCESS  not-accessible
    STATUS      current
    DESCRIPTION
        "The value of tmnxSrlgGrpName specifies the name defined for the Shared
         Risk Loss Group (SRLG)."
    ::= { tmnxSrlgGroupEntry 1 }

tmnxSrlgGrpRowStatus             OBJECT-TYPE
    SYNTAX      RowStatus
    MAX-ACCESS  read-create
    STATUS      current
    DESCRIPTION
        "The value of tmnxSrlgGrpRowStatus controls the creation and deletion
         of rows in the table.

         A value must be set for tmnxSrlgGrpValue as well at time of row
         creation."
    ::= { tmnxSrlgGroupEntry 2 }

tmnxSrlgGrpRowLstChng            OBJECT-TYPE
    SYNTAX      TimeStamp
    MAX-ACCESS  read-only
    STATUS      current
    DESCRIPTION
        "The value tmnxSrlgGrpRowLstChng indicates the sysUpTime at the time of
         the most recent management-initiated change to this SRLG."
    ::= { tmnxSrlgGroupEntry 3 }

tmnxSrlgGrpValue                 OBJECT-TYPE
    SYNTAX      Unsigned32
    MAX-ACCESS  read-create
    STATUS      current
    DESCRIPTION
        "The value of tmnxSrlgGrpValue specifies the group value associated
         with this row. This value is unique within a virtual router instance.

         This object must be set at time of row creation."
    ::= { tmnxSrlgGroupEntry 4 }

tmnxSrlgGrpPenaltyWeight         OBJECT-TYPE
    SYNTAX      Unsigned32 (0..65535)
    MAX-ACCESS  read-create
    STATUS      current
    DESCRIPTION
        "The value of tmnxSrlgGrpPenaltyWeight specifies the penalty weight
         associated with this SRLG group.

         The value of tmnxSrlgGrpPenaltyWeight will be used by CSPF in the
         computation of a FRR detour or bypass for protecting the primary LSP
         path at a PLR node. The penalty for the SRLG is taken into account in
         a pruning process by CSPF. Links with a higher SRLG penalty should be
         more likely to be pruned than links with a lower SRLG penalty."
    DEFVAL      { 0 }
    ::= { tmnxSrlgGroupEntry 5 }

vRtrPlcyAcctTemplTblLastChanged  OBJECT-TYPE
    SYNTAX      TimeStamp
    MAX-ACCESS  read-only
    STATUS      current
    DESCRIPTION
        "The value of vRtrPlcyAcctTemplTblLastChanged indicates the sysUpTime
         at the time of the last modification of an entry in the
         vRtrPlcyAcctTemplateTable.

         If no changes were made to the table since the last re-initialization
         of the local network management subsystem, then this object contains a
         zero value."
    ::= { tmnxVRtrObjs 103 }

vRtrPlcyAcctTemplateTable        OBJECT-TYPE
    SYNTAX      SEQUENCE OF VRtrPlcyAcctTemplateEntry
    MAX-ACCESS  not-accessible
    STATUS      current
    DESCRIPTION
        "The vRtrPlcyAcctTemplateTable has an entry for each Policy Accounting
         template configured."
    ::= { tmnxVRtrObjs 104 }

vRtrPlcyAcctTemplateEntry        OBJECT-TYPE
    SYNTAX      VRtrPlcyAcctTemplateEntry
    MAX-ACCESS  not-accessible
    STATUS      current
    DESCRIPTION
        "Each row entry in the vRtrPlcyAcctTemplateTable represents information
         related to the Policy Accounting template."
    INDEX       { vRtrPlcyAcctTemplateName }
    ::= { vRtrPlcyAcctTemplateTable 1 }

VRtrPlcyAcctTemplateEntry        ::= SEQUENCE
{
    vRtrPlcyAcctTemplateName         TNamedItem,
    vRtrPlcyAcctTemplateRowStatus    RowStatus,
    vRtrPlcyAcctTemplateLastChgd     TimeStamp
}

vRtrPlcyAcctTemplateName         OBJECT-TYPE
    SYNTAX      TNamedItem
    MAX-ACCESS  not-accessible
    STATUS      current
    DESCRIPTION
        "The value of the object vRtrPlcyAcctTemplateName specifies the name of
         the Policy Accounting which is used as a guideline to allocate exact
         set of source and destination class indexes specified in the template."
    ::= { vRtrPlcyAcctTemplateEntry 1 }

vRtrPlcyAcctTemplateRowStatus    OBJECT-TYPE
    SYNTAX      RowStatus
    MAX-ACCESS  read-create
    STATUS      current
    DESCRIPTION
        "The value of vRtrPlcyAcctTemplateRowStatus specifies the Row Status
         for this entry."
    ::= { vRtrPlcyAcctTemplateEntry 2 }

vRtrPlcyAcctTemplateLastChgd     OBJECT-TYPE
    SYNTAX      TimeStamp
    MAX-ACCESS  read-only
    STATUS      current
    DESCRIPTION
        "The value of vRtrPlcyAcctTemplateLastChgd indicates the timestamp of
         last change to this row in vRtrPlcyAcctTemplateTable."
    ::= { vRtrPlcyAcctTemplateEntry 3 }

vRtrPlcyAcctSrcClassTblLstChgd   OBJECT-TYPE
    SYNTAX      TimeStamp
    MAX-ACCESS  read-only
    STATUS      current
    DESCRIPTION
        "The value of vRtrPlcyAcctSrcClassTblLstChgd indicates the sysUpTime at
         the time of the last modification of an entry in the
         vRtrPlcyAcctSrcClassTable.

         If no changes were made to the table since the last re-initialization
         of the local network management subsystem, then this object contains a
         zero value."
    ::= { tmnxVRtrObjs 105 }

vRtrPlcyAcctSrcClassTable        OBJECT-TYPE
    SYNTAX      SEQUENCE OF VRtrPlcyAcctSrcClassEntry
    MAX-ACCESS  not-accessible
    STATUS      current
    DESCRIPTION
        "The vRtrPlcyAcctSrcClassTable has an entry for each Policy Accounting
         source class index configured."
    ::= { tmnxVRtrObjs 106 }

vRtrPlcyAcctSrcClassEntry        OBJECT-TYPE
    SYNTAX      VRtrPlcyAcctSrcClassEntry
    MAX-ACCESS  not-accessible
    STATUS      current
    DESCRIPTION
        "Each row entry in the vRtrPlcyAcctSrcClassTable represents information
         related to the source class index associated with
         vRtrPlcyAcctTemplateName."
    INDEX       {
        vRtrPlcyAcctTemplateName,
        vRtrPlcyAcctSrcClassIndex
    }
    ::= { vRtrPlcyAcctSrcClassTable 1 }

VRtrPlcyAcctSrcClassEntry        ::= SEQUENCE
{
    vRtrPlcyAcctSrcClassIndex        ClassIndex,
    vRtrPlcyAcctSrcClassRowStatus    RowStatus,
    vRtrPlcyAcctSrcClassLastChgd     TimeStamp
}

vRtrPlcyAcctSrcClassIndex        OBJECT-TYPE
    SYNTAX      ClassIndex
    MAX-ACCESS  not-accessible
    STATUS      current
    DESCRIPTION
        "The value of the object vRtrPlcyAcctSrcClassIndex specifies the source
         class index associated with the policy accounting template."
    ::= { vRtrPlcyAcctSrcClassEntry 1 }

vRtrPlcyAcctSrcClassRowStatus    OBJECT-TYPE
    SYNTAX      RowStatus
    MAX-ACCESS  read-create
    STATUS      current
    DESCRIPTION
        "The value of vRtrPlcyAcctSrcClassRowStatus specifies the Row Status
         for this entry."
    ::= { vRtrPlcyAcctSrcClassEntry 2 }

vRtrPlcyAcctSrcClassLastChgd     OBJECT-TYPE
    SYNTAX      TimeStamp
    MAX-ACCESS  read-only
    STATUS      current
    DESCRIPTION
        "The value of vRtrPlcyAcctSrcClassLastChgd indicates the timestamp of
         last change to this row in vRtrPlcyAcctSrcClassTable."
    ::= { vRtrPlcyAcctSrcClassEntry 3 }

vRtrPlcyAcctDestClassTblLstChgd  OBJECT-TYPE
    SYNTAX      TimeStamp
    MAX-ACCESS  read-only
    STATUS      current
    DESCRIPTION
        "The value of vRtrPlcyAcctDestClassTblLstChgd indicates the sysUpTime
         at the time of the last modification of an entry in the
         vRtrPlcyAcctDestClassTable.

         If no changes were made to the table since the last re-initialization
         of the local network management subsystem, then this object contains a
         zero value."
    ::= { tmnxVRtrObjs 107 }

vRtrPlcyAcctDestClassTable       OBJECT-TYPE
    SYNTAX      SEQUENCE OF VRtrPlcyAcctDestClassEntry
    MAX-ACCESS  not-accessible
    STATUS      current
    DESCRIPTION
        "The vRtrPlcyAcctDestClassTable has an entry for each Policy Accounting
         destination class index configured."
    ::= { tmnxVRtrObjs 108 }

vRtrPlcyAcctDestClassEntry       OBJECT-TYPE
    SYNTAX      VRtrPlcyAcctDestClassEntry
    MAX-ACCESS  not-accessible
    STATUS      current
    DESCRIPTION
        "Each row entry in the vRtrPlcyAcctDestClassTable represents
         information related to the destination class index associated with
         vRtrPlcyAcctTemplateName."
    INDEX       {
        vRtrPlcyAcctTemplateName,
        vRtrPlcyAcctDestClassIndex
    }
    ::= { vRtrPlcyAcctDestClassTable 1 }

VRtrPlcyAcctDestClassEntry       ::= SEQUENCE
{
    vRtrPlcyAcctDestClassIndex       ClassIndex,
    vRtrPlcyAcctDestClassRowStatus   RowStatus,
    vRtrPlcyAcctDestClassLastChgd    TimeStamp,
    vRtrPlcyAcctDestClassPolicerId   Unsigned32
}

vRtrPlcyAcctDestClassIndex       OBJECT-TYPE
    SYNTAX      ClassIndex
    MAX-ACCESS  not-accessible
    STATUS      current
    DESCRIPTION
        "The value of the object vRtrPlcyAcctDestClassIndex specifies the
         destination class index associated with the policy accounting
         template."
    ::= { vRtrPlcyAcctDestClassEntry 1 }

vRtrPlcyAcctDestClassRowStatus   OBJECT-TYPE
    SYNTAX      RowStatus
    MAX-ACCESS  read-create
    STATUS      current
    DESCRIPTION
        "The value of vRtrPlcyAcctDestClassRowStatus specifies the Row Status
         for this entry."
    ::= { vRtrPlcyAcctDestClassEntry 2 }

vRtrPlcyAcctDestClassLastChgd    OBJECT-TYPE
    SYNTAX      TimeStamp
    MAX-ACCESS  read-only
    STATUS      current
    DESCRIPTION
        "The value of vRtrPlcyAcctDestClassLastChgd indicates the timestamp of
         last change to this row in vRtrPlcyAcctDestClassTable."
    ::= { vRtrPlcyAcctDestClassEntry 3 }

vRtrPlcyAcctDestClassPolicerId   OBJECT-TYPE
    SYNTAX      Unsigned32 (0..63)
    MAX-ACCESS  read-create
    STATUS      current
    DESCRIPTION
        "The value of vRtrPlcyAcctDestClassPolicerId indicates the policer
         index in vRtrPlcyAcctDestClassTable."
    DEFVAL      { 0 }
    ::= { vRtrPlcyAcctDestClassEntry 4 }

vRtrPlcyAcctIfStatsTblLstChgd    OBJECT-TYPE
    SYNTAX      TimeStamp
    MAX-ACCESS  read-only
    STATUS      current
    DESCRIPTION
        "The value of vRtrPlcyAcctIfStatsTblLstChgd indicates the sysUpTime at
         the time of the last modification of an entry in the
         vRtrPlcyAcctInterfaceStatsTable.

         If no changes were made to the table since the last re-initialization
         of the local network management subsystem, then this object contains a
         zero value."
    ::= { tmnxVRtrObjs 109 }

vRtrPlcyAcctInterfaceStatsTable  OBJECT-TYPE
    SYNTAX      SEQUENCE OF VRtrPlcyAcctInterfaceStatsEntry
    MAX-ACCESS  not-accessible
    STATUS      current
    DESCRIPTION
        "The vRtrPlcyAcctInterfaceStatsTable has stats for each source class
         and dest class associated with an interface."
    ::= { tmnxVRtrObjs 110 }

vRtrPlcyAcctInterfaceStatsEntry  OBJECT-TYPE
    SYNTAX      VRtrPlcyAcctInterfaceStatsEntry
    MAX-ACCESS  not-accessible
    STATUS      current
    DESCRIPTION
        "Each row entry in the vRtrPlcyAcctInterfaceStatsTable represents
         statistics related to the vRtrPlcyAcctSrcClassTable and
         vRtrPlcyAcctDestClassTable."
    INDEX       {
        vRtrID,
        vRtrIfIndex,
        vRtrPlcyAcctType,
        vRtrPlcyAcctIndex
    }
    ::= { vRtrPlcyAcctInterfaceStatsTable 1 }

VRtrPlcyAcctInterfaceStatsEntry  ::= SEQUENCE
{
    vRtrPlcyAcctType                 INTEGER,
    vRtrPlcyAcctIndex                Unsigned32,
    vRtrPlcyAcctRxFwdPkts            Counter64,
    vRtrPlcyAcctRxFwdBytes           Counter64,
    vRtrPlcyAcctRxIncompleteCnt      TruthValue
}

vRtrPlcyAcctType                 OBJECT-TYPE
    SYNTAX      INTEGER {
        sourceClass (0),
        destClass   (1)
    }
    MAX-ACCESS  not-accessible
    STATUS      current
    DESCRIPTION
        "The value of the object vRtrPlcyAcctType specifies the type of the
         policy accounting class."
    ::= { vRtrPlcyAcctInterfaceStatsEntry 1 }

vRtrPlcyAcctIndex                OBJECT-TYPE
    SYNTAX      Unsigned32 (1..255)
    MAX-ACCESS  not-accessible
    STATUS      current
    DESCRIPTION
        "The value of the object vRtrPlcyAcctIndex specifies the index of the
         policy accounting class associated with vRtrPlcyAcctType."
    ::= { vRtrPlcyAcctInterfaceStatsEntry 2 }

vRtrPlcyAcctRxFwdPkts            OBJECT-TYPE
    SYNTAX      Counter64
    MAX-ACCESS  read-only
    STATUS      current
    DESCRIPTION
        "The value of the object vRtrPlcyAcctRxFwdPkts indicates the total
         number of packets received for this vRtrPlcyAcctIndex associated with
         the interface."
    ::= { vRtrPlcyAcctInterfaceStatsEntry 3 }

vRtrPlcyAcctRxFwdBytes           OBJECT-TYPE
    SYNTAX      Counter64
    MAX-ACCESS  read-only
    STATUS      current
    DESCRIPTION
        "The value of the object vRtrPlcyAcctRxFwdBytes indicates the total
         number of bytes received for this vRtrPlcyAcctIndex associated with
         the interface."
    ::= { vRtrPlcyAcctInterfaceStatsEntry 4 }

vRtrPlcyAcctRxIncompleteCnt      OBJECT-TYPE
    SYNTAX      TruthValue
    MAX-ACCESS  read-only
    STATUS      current
    DESCRIPTION
        "The value of the object vRtrPlcyAcctRxIncompleteCnt indicates whether
         the count of vRtrPlcyAcctRxFwdBytes and vRtrPlcyAcctRxFwdPkts is
         incomplete or not.

         When the value of vRtrPlcyAcctRxIncompleteCnt is 'true', both
         vRtrPlcyAcctRxFwdBytes and vRtrPlcyAcctRxFwdPkts will be incomplete."
    ::= { vRtrPlcyAcctInterfaceStatsEntry 5 }

vRtrIfBfdSessSdpBindTable        OBJECT-TYPE
    SYNTAX      SEQUENCE OF VRtrIfBfdSessSdpBindEntry
    MAX-ACCESS  not-accessible
    STATUS      current
    DESCRIPTION
        "The vRtrIfBfdSessSdpBindTable maintains VCCV BFD session index for
         each SDP binding for all services."
    ::= { tmnxVRtrObjs 111 }

vRtrIfBfdSessSdpBindEntry        OBJECT-TYPE
    SYNTAX      VRtrIfBfdSessSdpBindEntry
    MAX-ACCESS  not-accessible
    STATUS      current
    DESCRIPTION
        "Each row entry in the vRtrIfBfdSessSdpBindTable represents VCCV BFD
         session index for specific SDP binding for specific service."
    INDEX       {
        vRtrIfBfdSessExtSvcId,
        vRtrIfBfdSessExtSdpBindId
    }
    ::= { vRtrIfBfdSessSdpBindTable 1 }

VRtrIfBfdSessSdpBindEntry        ::= SEQUENCE
{ vRtrIfBfdSessSdpBindIndex        Unsigned32 }

vRtrIfBfdSessSdpBindIndex        OBJECT-TYPE
    SYNTAX      Unsigned32
    MAX-ACCESS  read-only
    STATUS      current
    DESCRIPTION
        "The value of vRtrIfBfdSessSdpBindIndex indicates the index of VCCV BFD
         session used as vRtrIfBfdSessExtRxInfoId in vRtrIfBfdSessExtTable for
         the SDP Binding in this service."
    ::= { vRtrIfBfdSessSdpBindEntry 1 }

vRtrRATable                      OBJECT-TYPE
    SYNTAX      SEQUENCE OF VRtrRAEntry
    MAX-ACCESS  not-accessible
    STATUS      current
    DESCRIPTION
        "The vRtrRATable provides an extension of the vRtrConfTable."
    ::= { tmnxVRtrObjs 112 }

vRtrRAEntry                      OBJECT-TYPE
    SYNTAX      VRtrRAEntry
    MAX-ACCESS  not-accessible
    STATUS      current
    DESCRIPTION
        "Each row entry in the vRtrRATable represents router advertisement
         attributes for a given virtual router."
    INDEX       { vRtrID }
    ::= { vRtrRATable 1 }

VRtrRAEntry                      ::= SEQUENCE
{
    vRtrRARowStatus                  RowStatus,
    vRtrRADnsOptServer1              InetAddressIPv6,
    vRtrRADnsOptServer2              InetAddressIPv6,
    vRtrRADnsOptServer3              InetAddressIPv6,
    vRtrRADnsOptServer4              InetAddressIPv6,
    vRtrRADnsOptRdnssLtime           Integer32
}

vRtrRARowStatus                  OBJECT-TYPE
    SYNTAX      RowStatus
    MAX-ACCESS  read-create
    STATUS      current
    DESCRIPTION
        "The value of vRtrRARowStatus is used to create or delete an entry in
         this table."
    ::= { vRtrRAEntry 1 }

vRtrRADnsOptServer1              OBJECT-TYPE
    SYNTAX      InetAddressIPv6
    MAX-ACCESS  read-create
    STATUS      current
    DESCRIPTION
        "The value of the object vRtrRADnsOptServer1 specifies the first server
         where the router advertisements will be forwarded to."
    DEFVAL      { '00000000000000000000000000000000'H }
    ::= { vRtrRAEntry 2 }

vRtrRADnsOptServer2              OBJECT-TYPE
    SYNTAX      InetAddressIPv6
    MAX-ACCESS  read-create
    STATUS      current
    DESCRIPTION
        "The value of the object vRtrRADnsOptServer2 specifies the second
         server where the router advertisements will be forwarded to."
    DEFVAL      { '00000000000000000000000000000000'H }
    ::= { vRtrRAEntry 3 }

vRtrRADnsOptServer3              OBJECT-TYPE
    SYNTAX      InetAddressIPv6
    MAX-ACCESS  read-create
    STATUS      current
    DESCRIPTION
        "The value of the object vRtrRADnsOptServer3 specifies the third server
         where the router advertisements will be forwarded to."
    DEFVAL      { '00000000000000000000000000000000'H }
    ::= { vRtrRAEntry 4 }

vRtrRADnsOptServer4              OBJECT-TYPE
    SYNTAX      InetAddressIPv6
    MAX-ACCESS  read-create
    STATUS      current
    DESCRIPTION
        "The value of the object vRtrRADnsOptServer4 specifies the fourth
         server where the router advertisements will be forwarded to."
    DEFVAL      { '00000000000000000000000000000000'H }
    ::= { vRtrRAEntry 5 }

vRtrRADnsOptRdnssLtime           OBJECT-TYPE
    SYNTAX      Integer32 (-1..0 | 4..3600)
    UNITS       "seconds"
    MAX-ACCESS  read-create
    STATUS      current
    DESCRIPTION
        "The value of vRtrRADnsOptRdnssLtime specifies the maximum time in
         seconds over which the RDNSS address in the RDNSS server option '25'
         is valid.

         A value of '-1' indicates that the lifetime is set to infinite."
    REFERENCE
        "RFC6106 Section 5.1"
    DEFVAL      { -1 }
    ::= { vRtrRAEntry 6 }

vRtrRAIfTable                    OBJECT-TYPE
    SYNTAX      SEQUENCE OF VRtrRAIfEntry
    MAX-ACCESS  not-accessible
    STATUS      current
    DESCRIPTION
        "The vRtrRAIfTable has an entry for each router interface configured in
         the system. This table augments the vRtrIfTable."
    ::= { tmnxVRtrObjs 113 }

vRtrRAIfEntry                    OBJECT-TYPE
    SYNTAX      VRtrRAIfEntry
    MAX-ACCESS  not-accessible
    STATUS      current
    DESCRIPTION
        "Each row entry represents router advertisement attributes for a
         virtual router interface in the system."
    INDEX       {
        vRtrID,
        vRtrIfIndex
    }
    ::= { vRtrRAIfTable 1 }

VRtrRAIfEntry                    ::= SEQUENCE
{
    vRtrRAIfRowStatus                RowStatus,
    vRtrRAIfDnsOptServer1            InetAddressIPv6,
    vRtrRAIfDnsOptServer2            InetAddressIPv6,
    vRtrRAIfDnsOptServer3            InetAddressIPv6,
    vRtrRAIfDnsOptServer4            InetAddressIPv6,
    vRtrRAIfDnsOptRdnssLtime         Integer32,
    vRtrRAIfDnsOptInclDns            TruthValue
}

vRtrRAIfRowStatus                OBJECT-TYPE
    SYNTAX      RowStatus
    MAX-ACCESS  read-create
    STATUS      current
    DESCRIPTION
        "The value of vRtrRAIfRowStatus is used to create or delete an entry in
         this table."
    ::= { vRtrRAIfEntry 1 }

vRtrRAIfDnsOptServer1            OBJECT-TYPE
    SYNTAX      InetAddressIPv6
    MAX-ACCESS  read-create
    STATUS      current
    DESCRIPTION
        "The value of the object vRtrRAIfDnsOptServer1 specifies the first
         server where the router advertisements will be forwarded to."
    DEFVAL      { '00000000000000000000000000000000'H }
    ::= { vRtrRAIfEntry 2 }

vRtrRAIfDnsOptServer2            OBJECT-TYPE
    SYNTAX      InetAddressIPv6
    MAX-ACCESS  read-create
    STATUS      current
    DESCRIPTION
        "The value of the object vRtrRAIfDnsOptServer2 specifies the second
         server where the router advertisements will be forwarded to."
    DEFVAL      { '00000000000000000000000000000000'H }
    ::= { vRtrRAIfEntry 3 }

vRtrRAIfDnsOptServer3            OBJECT-TYPE
    SYNTAX      InetAddressIPv6
    MAX-ACCESS  read-create
    STATUS      current
    DESCRIPTION
        "The value of the object vRtrRAIfDnsOptServer3 specifies the third
         server where the router advertisements will be forwarded to."
    DEFVAL      { '00000000000000000000000000000000'H }
    ::= { vRtrRAIfEntry 4 }

vRtrRAIfDnsOptServer4            OBJECT-TYPE
    SYNTAX      InetAddressIPv6
    MAX-ACCESS  read-create
    STATUS      current
    DESCRIPTION
        "The value of the object vRtrRAIfDnsOptServer4 specifies the fourth
         server where the router advertisements will be forwarded to."
    DEFVAL      { '00000000000000000000000000000000'H }
    ::= { vRtrRAIfEntry 5 }

vRtrRAIfDnsOptRdnssLtime         OBJECT-TYPE
    SYNTAX      Integer32 (-2..0 | 4..3600)
    UNITS       "seconds"
    MAX-ACCESS  read-create
    STATUS      current
    DESCRIPTION
        "The value of vRtrRAIfDnsOptRdnssLtime specifies the maximum time in
         seconds over which the RDNSS address in the RDNSS server option '25'
         is valid.

         A value of '-2' indicates that the value of vRtrRADnsOptRdnssLtime for
         the corresponding vRtrID shall be used.

         A value of '-1' indicates that the lifetime is set to infinite."
    REFERENCE
        "RFC6106 Section 5.1"
    DEFVAL      { -2 }
    ::= { vRtrRAIfEntry 6 }

vRtrRAIfDnsOptInclDns            OBJECT-TYPE
    SYNTAX      TruthValue
    MAX-ACCESS  read-create
    STATUS      current
    DESCRIPTION
        "The value of vRtrRAIfDnsOptInclDns specifies whether The RDNSS server
         option '25' is included in the router advertisements sent from this
         interface."
    REFERENCE
        "RFC6106 Section 5.1"
    DEFVAL      { true }
    ::= { vRtrRAIfEntry 7 }

vRtrTTLPropTblLstChgd            OBJECT-TYPE
    SYNTAX      TimeStamp
    MAX-ACCESS  read-only
    STATUS      current
    DESCRIPTION
        "The value of vRtrTTLPropTblLstChgd indicates the sysUpTime at the time
         of the last modification of an entry in the vRtrTTLPropTable.

         If no changes were made to the table since the last re-initialization
         of the local network management subsystem, then this object contains a
         zero value."
    ::= { tmnxVRtrObjs 114 }

vRtrTTLPropTable                 OBJECT-TYPE
    SYNTAX      SEQUENCE OF VRtrTTLPropEntry
    MAX-ACCESS  not-accessible
    STATUS      current
    DESCRIPTION
        "vRtrTTLPropTable consists of information about TTL propagation for in
         transit and CPM generated IP packets for base router instance."
    ::= { tmnxVRtrObjs 115 }

vRtrTTLPropEntry                 OBJECT-TYPE
    SYNTAX      VRtrTTLPropEntry
    MAX-ACCESS  not-accessible
    STATUS      current
    DESCRIPTION
        "An entry (conceptual row) in the vRtrTTLPropTable. Each entry
         represents information about TTL propagation for in transit and CPM
         generated for base router instance."
    INDEX       { vRtrID }
    ::= { vRtrTTLPropTable 1 }

VRtrTTLPropEntry                 ::= SEQUENCE
{
    vRtrTTLPropVprnLocal             VRtrVprnTTLPropagateType,
    vRtrTTLPropVprnTransit           VRtrVprnTTLPropagateType,
    vRtrTTLPropLabelRouteLocal       VRtrTTLPropagateType,
    vRtrTTLPropLabelRouteTransit     VRtrTTLPropagateType,
    vRtrTTLPropLsrLabelRoute         VRtrTTLPropagateType,
    vRtrTTLPropSrMplsLocal           VRtrTTLPropagateType,
    vRtrTTLPropSrMplsTransit         VRtrTTLPropagateType
}

vRtrTTLPropVprnLocal             OBJECT-TYPE
    SYNTAX      VRtrVprnTTLPropagateType
    MAX-ACCESS  read-create
    STATUS      current
    DESCRIPTION
        "The value of vRtrTTLPropVprnLocal specifies whether or not to enable
         the propagation of time to live (TTL) at Ingress LER from the header
         of IP packet into all labels in the stack for all local packets.

         The value 'inherit' for object vRtrTTLPropVprnLocal, is not applicable
         for base router instance."
    DEFVAL      { vcOnly }
    ::= { vRtrTTLPropEntry 1 }

vRtrTTLPropVprnTransit           OBJECT-TYPE
    SYNTAX      VRtrVprnTTLPropagateType
    MAX-ACCESS  read-create
    STATUS      current
    DESCRIPTION
        "The value of vRtrTTLPropVprnTransit specifies whether or not to enable
         the propagation of time to live (TTL) at Ingress LER from the header
         of IP packet into all labels in the stack for all transit packets.

         The value 'inherit' for object vRtrTTLPropVprnTransit, is not
         applicable for base router instance."
    DEFVAL      { vcOnly }
    ::= { vRtrTTLPropEntry 2 }

vRtrTTLPropLabelRouteLocal       OBJECT-TYPE
    SYNTAX      VRtrTTLPropagateType
    MAX-ACCESS  read-create
    STATUS      current
    DESCRIPTION
        "The value of vRtrTTLPropLabelRouteLocal specifies whether or not to
         enable the propagation of time to live (TTL) for RFC 3107 label routes
         at Ingress LER from the header of IP packet into all labels in the
         stack for all local packets."
    DEFVAL      { none }
    ::= { vRtrTTLPropEntry 3 }

vRtrTTLPropLabelRouteTransit     OBJECT-TYPE
    SYNTAX      VRtrTTLPropagateType
    MAX-ACCESS  read-create
    STATUS      current
    DESCRIPTION
        "The value of vRtrTTLPropLabelRouteTransit specifies whether or not to
         enable the propagation of time to live (TTL) for RFC 3107 label routes
         at Ingress LER from the header of IP packet into all labels in the
         stack for all transit packets."
    DEFVAL      { none }
    ::= { vRtrTTLPropEntry 4 }

vRtrTTLPropLsrLabelRoute         OBJECT-TYPE
    SYNTAX      VRtrTTLPropagateType
    MAX-ACCESS  read-create
    STATUS      current
    DESCRIPTION
        "The value of vRtrTTLPropLsrLabelRoute specifies whether or not to
         enable the propagation of time to live (TTL) for RFC 3107 label routes
         at LSR from the header of IP packet into all labels in the stack."
    DEFVAL      { none }
    ::= { vRtrTTLPropEntry 5 }

vRtrTTLPropSrMplsLocal           OBJECT-TYPE
    SYNTAX      VRtrTTLPropagateType
    MAX-ACCESS  read-create
    STATUS      current
    DESCRIPTION
        "The value of vRtrTTLPropSrMplsLocal specifies at an ingress LER
         whether or not to enable the propagation of IP TTL into the label
         stack  for Segment Routing MPLS tunnels."
    DEFVAL      { all }
    ::= { vRtrTTLPropEntry 6 }

vRtrTTLPropSrMplsTransit         OBJECT-TYPE
    SYNTAX      VRtrTTLPropagateType
    MAX-ACCESS  read-create
    STATUS      current
    DESCRIPTION
        "The value of vRtrTTLPropSrMplsTransit specifies at transit nodes
         whether or not to enable the propagation of IP TTL into the label
         stack  for Segment Routing MPLS tunnels."
    DEFVAL      { all }
    ::= { vRtrTTLPropEntry 7 }

vRtrSvcTTLPropTblLstChgd         OBJECT-TYPE
    SYNTAX      TimeStamp
    MAX-ACCESS  read-only
    STATUS      current
    DESCRIPTION
        "The value of vRtrSvcTTLPropTblLstChgd indicates the sysUpTime at the
         time of the last modification of an entry in the vRtrSvcTTLPropTable.

         If no changes were made to the table since the last re-initialization
         of the local network management subsystem, then this object contains a
         zero value."
    ::= { tmnxVRtrObjs 116 }

vRtrSvcTTLPropTable              OBJECT-TYPE
    SYNTAX      SEQUENCE OF VRtrSvcTTLPropEntry
    MAX-ACCESS  not-accessible
    STATUS      current
    DESCRIPTION
        "vRtrSvcTTLPropTable consists of information about TTL propagation for
         in transit and CPM generated IP packets for VPRN instance."
    ::= { tmnxVRtrObjs 117 }

vRtrSvcTTLPropEntry              OBJECT-TYPE
    SYNTAX      VRtrSvcTTLPropEntry
    MAX-ACCESS  not-accessible
    STATUS      current
    DESCRIPTION
        "An entry (conceptual row) in the vRtrSvcTTLPropTable. Each entry
         represents information about TTL propagation for in transit and CPM
         generated for VPRN instance."
    INDEX       { vRtrID }
    ::= { vRtrSvcTTLPropTable 1 }

VRtrSvcTTLPropEntry              ::= SEQUENCE
{
    vRtrSvcTTLPropVprnLocal          VRtrVprnTTLPropagateType,
    vRtrSvcTTLPropVprnTransit        VRtrVprnTTLPropagateType
}

vRtrSvcTTLPropVprnLocal          OBJECT-TYPE
    SYNTAX      VRtrVprnTTLPropagateType
    MAX-ACCESS  read-create
    STATUS      current
    DESCRIPTION
        "The value of vRtrSvcTTLPropVprnLocal specifies whether or not to
         enable the propagation of time to live (TTL) at Ingress LER from the
         header of IP packet into all labels in the stack for all local
         packets.

         When the value for object vRtrSvcTTLPropVprnLocal is set to 'inherit',
         the VPRN instance inherits the base router instance configuration."
    DEFVAL      { inherit }
    ::= { vRtrSvcTTLPropEntry 1 }

vRtrSvcTTLPropVprnTransit        OBJECT-TYPE
    SYNTAX      VRtrVprnTTLPropagateType
    MAX-ACCESS  read-create
    STATUS      current
    DESCRIPTION
        "The value of vRtrSvcTTLPropVprnTransit specifies whether or not to
         enable the propagation of time to live (TTL) at Ingress LER from the
         header of IP packet into all labels in the stack for all transit
         packets.

         When the value for object vRtrSvcTTLPropVprnTransit is set to
         'inherit', the VPRN instance inherits the base router instance
         configuration."
    DEFVAL      { inherit }
    ::= { vRtrSvcTTLPropEntry 2 }

vRtrInetTunnelTable              OBJECT-TYPE
    SYNTAX      SEQUENCE OF VRtrInetTunnelEntry
    MAX-ACCESS  not-accessible
    STATUS      obsolete
    DESCRIPTION
        "vRtrInetTunnelTable maintains a list of tunnels for the specific
         router instance.

         This table has been replaced by vRtrInetExtTunnelTable in 16.0."
    ::= { tmnxVRtrObjs 118 }

vRtrInetTunnelEntry              OBJECT-TYPE
    SYNTAX      VRtrInetTunnelEntry
    MAX-ACCESS  not-accessible
    STATUS      obsolete
    DESCRIPTION
        "vRtrInetTunnelEntry defines a tunnel to a particular destination in a
         specific router context."
    INDEX       {
        vRtrID,
        vRtrInetTunnelDestAddrType,
        vRtrInetTunnelDestAddr,
        vRtrInetTunnelDestPfxLen,
        vRtrInetTunnelPreference,
        vRtrInetTunnelType,
        vRtrInetTunnelTypeInstance,
        vRtrInetTunnelID,
        vRtrInetTunnelNextHopAddrType,
        vRtrInetTunnelNextHopAddr
    }
    ::= { vRtrInetTunnelTable 1 }

VRtrInetTunnelEntry              ::= SEQUENCE
{
    vRtrInetTunnelDestAddrType       InetAddressType,
    vRtrInetTunnelDestAddr           InetAddress,
    vRtrInetTunnelDestPfxLen         InetAddressPrefixLength,
    vRtrInetTunnelPreference         Unsigned32,
    vRtrInetTunnelType               TmnxTunnelTypeExt,
    vRtrInetTunnelTypeInstance       Unsigned32,
    vRtrInetTunnelID                 TmnxTunnelID,
    vRtrInetTunnelNextHopAddrType    InetAddressType,
    vRtrInetTunnelNextHopAddr        InetAddress,
    vRtrInetTunnelMetric             Unsigned32,
    vRtrInetTunnelAge                Integer32,
    vRtrInetTunnelNextHopFlags       INTEGER,
    vRtrInetTunnelLspBandwidth       Counter64,
    vRtrInetTunnelMTU                Unsigned32,
    vRtrInetTunnelLspWeight          Unsigned32,
    vRtrInetTunnelLspId              Unsigned32,
    vRtrInetTunnelFlags              BITS,
    vRtrInetTunnelRelativeMetric     Integer32,
    vRtrInetTunnelLabel              Integer32,
    vRtrInetTunnelBypassLabel        Integer32,
    vRtrInetTunnelLspFC              TmnxCBFClasses,
    vRtrInetTunnelMaxLabels          Integer32,
    vRtrInetTunnelNhTunnelId         TmnxTunnelID,
    vRtrInetTunnelNhTunnelType       TmnxTunnelTypeExt,
    vRtrInetTunnelNhTunnelInst       Unsigned32
}

vRtrInetTunnelDestAddrType       OBJECT-TYPE
    SYNTAX      InetAddressType
    MAX-ACCESS  not-accessible
    STATUS      obsolete
    DESCRIPTION
        "The value of vRtrInetTunnelDestAddrType indicates the address type of
         vRtrInetTunnelDestAddr."
    ::= { vRtrInetTunnelEntry 1 }

vRtrInetTunnelDestAddr           OBJECT-TYPE
    SYNTAX      InetAddress (SIZE (0|4|16))
    MAX-ACCESS  not-accessible
    STATUS      obsolete
    DESCRIPTION
        "The value of vRtrInetTunnelDestAddr maintains the destination IP address
         of this tunnel. This object may not take a Multicast (Class  D) address
         value.

         Any assignment (implicit or otherwise) of an instance of this object
         to a value x must be rejected if the bitwise logical-AND of x with the
         value of mask representing the corresponding instance of the
         vRtrInetTunnelDestPfxLen object is not equal to x."
    ::= { vRtrInetTunnelEntry 2 }

vRtrInetTunnelDestPfxLen         OBJECT-TYPE
    SYNTAX      InetAddressPrefixLength
    MAX-ACCESS  not-accessible
    STATUS      obsolete
    DESCRIPTION
        "The value of vRtrInetTunnelDestPfxLen indicates the mask length for
         vRtrInetTunnelDestAddr. For those systems that do not support
         arbitrary subnet masks, an agent constructs the value of the
         vRtrInetTunnelDestPfxLen by reference to the IP Address Class.

         Any assignment (implicit or otherwise) of an instance of this object
         to a value x must be rejected if the bitwise logical-AND of the mask
         representing x with the value of the corresponding instance of
         vRtrInetTunnelDestAddr is not equal to vRtrInetTunnelDestAddr."
    ::= { vRtrInetTunnelEntry 3 }

vRtrInetTunnelPreference         OBJECT-TYPE
    SYNTAX      Unsigned32 (1..255)
    MAX-ACCESS  not-accessible
    STATUS      obsolete
    DESCRIPTION
        "The value of vRtrInetTunnelPreference determines the priority of this
         tunnel versus the other tunnels from different sources such as LDP,
         RSVP, GRE etc. This is an absolute number used internally by the
         system to specify preferences for the tunnel.

         Lowest number signifies the most preferred entry in the table."
    ::= { vRtrInetTunnelEntry 4 }

vRtrInetTunnelType               OBJECT-TYPE
    SYNTAX      TmnxTunnelTypeExt
    MAX-ACCESS  not-accessible
    STATUS      obsolete
    DESCRIPTION
        "The value of vRtrInetTunnelType indicates the type of this tunnel
         entity."
    ::= { vRtrInetTunnelEntry 5 }

vRtrInetTunnelTypeInstance       OBJECT-TYPE
    SYNTAX      Unsigned32
    MAX-ACCESS  not-accessible
    STATUS      obsolete
    DESCRIPTION
        "The value of vRtrInetTunnelTypeInstance indicates an instance of the
         tunnel of the type indicated by vRtrInetTunnelType."
    ::= { vRtrInetTunnelEntry 6 }

vRtrInetTunnelID                 OBJECT-TYPE
    SYNTAX      TmnxTunnelID
    MAX-ACCESS  not-accessible
    STATUS      obsolete
    DESCRIPTION
        "The value of vRtrInetTunnelID is a global value and represents a
         particular tunnel type like an MPLS type tunnel or an SDP."
    ::= { vRtrInetTunnelEntry 7 }

vRtrInetTunnelNextHopAddrType    OBJECT-TYPE
    SYNTAX      InetAddressType
    MAX-ACCESS  not-accessible
    STATUS      obsolete
    DESCRIPTION
        "The value of vRtrInetTunnelNextHopAddrType indicates the address type
         of vRtrInetTunnelNextHopAddr."
    ::= { vRtrInetTunnelEntry 8 }

vRtrInetTunnelNextHopAddr        OBJECT-TYPE
    SYNTAX      InetAddress (SIZE (0|4|16|20))
    MAX-ACCESS  not-accessible
    STATUS      obsolete
    DESCRIPTION
        "The value of vRtrInetTunnelNextHopAddr indicates the address of the
         next system en route."
    ::= { vRtrInetTunnelEntry 9 }

vRtrInetTunnelMetric             OBJECT-TYPE
    SYNTAX      Unsigned32
    MAX-ACCESS  read-only
    STATUS      obsolete
    DESCRIPTION
        "The value of vRtrInetTunnelMetric indicates the metric of the tunnel.
         This is used in addition to the preference for this tunnel."
    ::= { vRtrInetTunnelEntry 10 }

vRtrInetTunnelAge                OBJECT-TYPE
    SYNTAX      Integer32
    MAX-ACCESS  read-only
    STATUS      obsolete
    DESCRIPTION
        "The value of vRtrInetTunnelAge indicates the number of seconds since
         this tunnel entry was last updated or otherwise determined to be
         correct. No semantics of 'too old' can be implied except through
         knowledge of owner of the tunnel."
    ::= { vRtrInetTunnelEntry 11 }

vRtrInetTunnelNextHopFlags       OBJECT-TYPE
    SYNTAX      INTEGER {
        none          (0),
        hasLfa        (1),
        hasBackup     (2),
        isBackup      (3),
        isBgpInactive (4)
    }
    MAX-ACCESS  read-only
    STATUS      obsolete
    DESCRIPTION
        "The value of vRtrInetTunnelNextHopFlags indicates the properties of
         the tunnel next hop.

         A value of 'none' indicates that no next-hop flags are present.

         A value of 'hasLfa' indicates that an LFA next-hop is present in
         addition to the regular next-hop.

         A value of 'hasBackup' indicates that this route has a backup route.

         A value of 'isBackup' indicates that this route is a backup route to
         another route with the same prefix.

         A value of 'isBgpInactive' indicates that this route is an inactive
         best-external route exported from BGP."
    ::= { vRtrInetTunnelEntry 12 }

vRtrInetTunnelLspBandwidth       OBJECT-TYPE
    SYNTAX      Counter64
    UNITS       "mega-bits per second"
    MAX-ACCESS  read-only
    STATUS      obsolete
    DESCRIPTION
        "The value of vRtrInetTunnelLspBandwidth indicates the reserved
         bandwidth that is available in the LSP.

         When the value of the object is set to zero then it indicates that
         there is no reserved bandwidth in this tunnel"
    ::= { vRtrInetTunnelEntry 13 }

vRtrInetTunnelMTU                OBJECT-TYPE
    SYNTAX      Unsigned32
    MAX-ACCESS  read-only
    STATUS      obsolete
    DESCRIPTION
        "The value of vRtrInetTunnelMTU indicates the MTU value for the tunnel."
    ::= { vRtrInetTunnelEntry 14 }

vRtrInetTunnelLspWeight          OBJECT-TYPE
    SYNTAX      Unsigned32
    MAX-ACCESS  read-only
    STATUS      obsolete
    DESCRIPTION
        "The value of vRtrInetTunnelLspWeight indicates the load balancing
         weight applicable to the LSP."
    ::= { vRtrInetTunnelEntry 15 }

vRtrInetTunnelLspId              OBJECT-TYPE
    SYNTAX      Unsigned32
    MAX-ACCESS  read-only
    STATUS      obsolete
    DESCRIPTION
        "The value of vRtrInetTunnelLspId indicates an instance/epoch
         identifier associated with a RSVP tunnel."
    ::= { vRtrInetTunnelEntry 16 }

vRtrInetTunnelFlags              OBJECT-TYPE
    SYNTAX      BITS {
        isOverTunnel               (0),
        useRelativeMetric          (1),
        autoLSP                    (2),
        hasLFA                     (3),
        excludeForLdpOverRsvp      (4),
        excludeForL3VPN            (5),
        excludeForBGPShortcuts     (6),
        excludeForBGPLabeledRoutes (7),
        excludeForLFA              (8),
        excludeForIGPShortcuts     (9),
        entropyLabelCapable        (10),
        isAdjacencyTunnel          (11),
        lspBfdDown                 (12)
    }
    MAX-ACCESS  read-only
    STATUS      obsolete
    DESCRIPTION
        "The value of vRtrInetTunnelFlags indicates the following -:

         If value of 'isOverTunnel' is set, it indicates that this tunnel is
         over another tunnel.

         A value of 'useRelativeMetric' indicates to use the relative metric
         info to offset IGP path cost to tunnel destination instead of absolute
         tunnel metric.

         A value of 'autoLSP' indicates if the LSP is an automatic LSP.

         If value of 'hasLFA' is set, then this tunnel next-hop has a loop-free
         alternate hop.

         If value of 'excludeForLdpOverRsvp' is set (applicable to RSVP tunnel
         only), then the MPLS LSP is not allowed to be used for LDP over RSVP.

         If value of 'excludeForL3VPN' is set, it indicates not to use this
         tunnel for L3 VPNs.

         If value of 'excludeForBGPShortcuts' is set, it indicates not to use
         this tunnel for BGP shortcuts.

         If value of 'excludeForBGPLabeledRoutes' is set, it indicates not to
         use this tunnel for BGP labeled routes.

         If value of 'excludeForLFA' is set, it indicates not to use this
         tunnel for loop-free alternate.

         If value of 'excludeForIGPShortcuts' is set, it indicates not to use
         this tunnel for IGP shortcuts.

         If value of 'entropyLabelCapable' is set, it indicates this tunnel is
         entropy capable.

         If value of 'isAdjacencyTunnel' is set, it indicates that this tunnel
         is a segment routing adjacency tunnel.

         If value of 'lspBfdDown' is set, it indicates that BFD is down on this
         tunnel/FEC and that it will not be used as a transport tunnel. If this
         value is not set, then LSP-BFD is not configured on the tunnel/FEC, or
         LSP-BFD is configured and the BFD state is up."
    ::= { vRtrInetTunnelEntry 17 }

vRtrInetTunnelRelativeMetric     OBJECT-TYPE
    SYNTAX      Integer32
    MAX-ACCESS  read-only
    STATUS      obsolete
    DESCRIPTION
        "The value of vRtrInetTunnelRelativeMetric indicates the metric offset
         to IGP cost to tunnel destination. This value is applicable only if
         'useRelativeMetric' bit is set for the object vRtrInetTunnelFlags."
    ::= { vRtrInetTunnelEntry 18 }

vRtrInetTunnelLabel              OBJECT-TYPE
    SYNTAX      Integer32
    MAX-ACCESS  read-only
    STATUS      obsolete
    DESCRIPTION
        "The value of vRtrInetTunnelLabel indicates the label corresponding to
         tunnel of type LDP/MPLS."
    ::= { vRtrInetTunnelEntry 19 }

vRtrInetTunnelBypassLabel        OBJECT-TYPE
    SYNTAX      Integer32
    MAX-ACCESS  read-only
    STATUS      obsolete
    DESCRIPTION
        "The value of vRtrInetTunnelBypassLabel indicates the MPLS bypass
         tunnel label."
    ::= { vRtrInetTunnelEntry 20 }

vRtrInetTunnelLspFC              OBJECT-TYPE
    SYNTAX      TmnxCBFClasses
    MAX-ACCESS  read-only
    STATUS      obsolete
    DESCRIPTION
        "The value of vRtrInetTunnelLspFC indicates a set of forwarding classes
         configured for this LSP expressed as a bit map. If a bit from 0
         through 7 is set, then the corresponding forwarding class has been
         configured for this LSP. If bit 8 is set, the LSP has been designated
         as the default forwarding LSP.

         If no bits are set, then Class-based forwarding is not enabled for
         this LSP."
    ::= { vRtrInetTunnelEntry 21 }

vRtrInetTunnelMaxLabels          OBJECT-TYPE
    SYNTAX      Integer32
    MAX-ACCESS  read-only
    STATUS      obsolete
    DESCRIPTION
        "The value of vRtrInetTunnelMaxLabels is the sum of the maximum number
         of labels that will be used by this tunnel and all underlying tunnels."
    ::= { vRtrInetTunnelEntry 22 }

vRtrInetTunnelNhTunnelId         OBJECT-TYPE
    SYNTAX      TmnxTunnelID
    MAX-ACCESS  read-only
    STATUS      obsolete
    DESCRIPTION
        "The value of vRtrInetTunnelNhTunnelId indicates the value of the
         tunnel ID of the underlying tunnel when the value of
         vRtrInetTunnelFlags has 'isOverTunnel' set, otherwise the value is 0."
    ::= { vRtrInetTunnelEntry 23 }

vRtrInetTunnelNhTunnelType       OBJECT-TYPE
    SYNTAX      TmnxTunnelTypeExt
    MAX-ACCESS  read-only
    STATUS      obsolete
    DESCRIPTION
        "The value of vRtrInetTunnelNhTunnelType indicates the type of
         underlying tunnel when the value of vRtrInetTunnelFlags has
         'isOverTunnel' set.

         If the value of vRtrInetTunnelFlags does not have 'isOverTunnel' set,
         the value of vRtrInetTunnelType is invalid."
    ::= { vRtrInetTunnelEntry 24 }

vRtrInetTunnelNhTunnelInst       OBJECT-TYPE
    SYNTAX      Unsigned32
    MAX-ACCESS  read-only
    STATUS      obsolete
    DESCRIPTION
        "The value of vRtrInetTunnelNhTunnelInst indicates the instance of the
         underlying tunnel type indicated by vRtrInetTunnelNhTunnelType.

         If the value of vRtrInetTunnelFlags does not have 'isOverTunnel' set,
         the value of vRtrInetTunnelNhTunnelInst is set to 0."
    ::= { vRtrInetTunnelEntry 25 }

vRtrInetSRIndirectTable          OBJECT-TYPE
    SYNTAX      SEQUENCE OF VRtrInetSRIndirectEntry
    MAX-ACCESS  not-accessible
    STATUS      current
    DESCRIPTION
        "The vRtrInetSRIndirectTable provides an extension of the
         vRtrInetStaticRouteTable in the IP-MIB."
    ::= { tmnxVRtrObjs 119 }

vRtrInetSRIndirectEntry          OBJECT-TYPE
    SYNTAX      VRtrInetSRIndirectEntry
    MAX-ACCESS  not-accessible
    STATUS      current
    DESCRIPTION
        "Each row entry in the vRtrInetSRIndirectTable represents additional
         columns for attributes specific to the Nokia SROS series
         implementation for the vRtrInetStaticRouteTable."
    AUGMENTS    { vRtrInetStaticRouteEntry }
    ::= { vRtrInetSRIndirectTable 1 }

VRtrInetSRIndirectEntry          ::= SEQUENCE
{
    vRtrInetSRIndirectTunnelLdp      TruthValue,
    vRtrInetSRIndirectTunnelRsvpTe   TruthValue,
    vRtrInetSRIndirectTunnelDisalIgp TruthValue,
    vRtrInetSRIndirectTunResStatus   TResolveStatus,
    vRtrInetSRIndirectTunnelSrIsis   TruthValue,
    vRtrInetSRIndirectTunnelSrOspf   TruthValue,
    vRtrInetSRIndirectTunnelSrTe     TruthValue,
    vRtrInetSRIndirectTunnelRibApi   TruthValue,
    vRtrInetSRIndirectTnlMplsFwdPlcy TruthValue,
    vRtrInetSRIndirectTunnelSrOspf3  TruthValue,
    vRtrInetSRIndirectTunFlexAlgoId  TmnxFlexAlgoIdOrZero
}

vRtrInetSRIndirectTunnelLdp      OBJECT-TYPE
    SYNTAX      TruthValue
    MAX-ACCESS  read-create
    STATUS      current
    DESCRIPTION
        "The value of vRtrInetSRIndirectTunnelLdp specifies if  LDP Route
         Forwarding Equivalence Class (FEC) tunneling mechanism will be used to
         resolve next-hop for the static route or not.

         The value of vRtrInetSRIndirectTunnelLdp is valid only for indirect
         static routes (i.e. vRtrInetStaticRouteStaticType is 'indirect').

         If the value of vRtrInetSRIndirectTunnelLdp is set to 'true', IGP
         shortcuts associated with LDP Route Forwarding Equivalence Class (FEC)
         tunneling mechanism will be used to resolve next-hop for the static
         route."
    DEFVAL      { false }
    ::= { vRtrInetSRIndirectEntry 1 }

vRtrInetSRIndirectTunnelRsvpTe   OBJECT-TYPE
    SYNTAX      TruthValue
    MAX-ACCESS  read-create
    STATUS      current
    DESCRIPTION
        "The value of vRtrInetSRIndirectTunnelRsvpTe specifies if RSVP Traffic
         Engineering tunneling mechanism will be used to resolve next-hop for
         the static route or not.

         The value of vRtrInetSRIndirectTunnelRsvpTe is valid only for indirect
         static routes (i.e. vRtrInetStaticRouteStaticType is 'indirect').

         If the value of vRtrInetSRIndirectTunnelRsvpTe is set to 'true', IGP
         shortcuts associated with RSVP Traffic Engineering tunneling mechanism
         will be used to resolve next-hop for the static route."
    DEFVAL      { false }
    ::= { vRtrInetSRIndirectEntry 2 }

vRtrInetSRIndirectTunnelDisalIgp OBJECT-TYPE
    SYNTAX      TruthValue
    MAX-ACCESS  read-create
    STATUS      current
    DESCRIPTION
        "The value of vRtrInetSRIndirectTunnelDisalIgp specifies if IGP routes
         are to be used or not.

         The value of vRtrInetSRIndirectTunnelDisalIgp is valid only for
         indirect static routes (i.e. vRtrInetStaticRouteStaticType is
         'indirect').

         If the value of vRtrInetSRIndirectTunnelDisalIgp is set to 'true', and
         if none of the defined tunneling mechanisms (RSVP-TE, LDP or IP)
         qualify as a next-hop, the normal IGP next-hop to the indirect
         next-hop address will not be used.

         If the value is set to 'false', IGP next-hop to the indirect next-hop
         address can be used as the next-hop of the last resort."
    DEFVAL      { false }
    ::= { vRtrInetSRIndirectEntry 3 }

vRtrInetSRIndirectTunResStatus   OBJECT-TYPE
    SYNTAX      TResolveStatus
    MAX-ACCESS  read-create
    STATUS      current
    DESCRIPTION
        "The value of vRtrInetSRIndirectTunResStatus specifies the resolution
         status of this entry."
    DEFVAL      { disabled }
    ::= { vRtrInetSRIndirectEntry 4 }

vRtrInetSRIndirectTunnelSrIsis   OBJECT-TYPE
    SYNTAX      TruthValue
    MAX-ACCESS  read-create
    STATUS      current
    DESCRIPTION
        "The value of vRtrInetSRIndirectTunnelSrIsis specifies if SR ISIS
         tunneling mechanism will be used to resolve next-hop for the static
         route or not.

         The value of vRtrInetSRIndirectTunnelSrIsis is valid only for indirect
         static routes (i.e. vRtrInetStaticRouteStaticType is 'indirect').

         If the value of vRtrInetSRIndirectTunnelSrIsis is set to 'true', IGP
         shortcuts associated with SR ISIS tunneling mechanism will be used to
         resolve next-hop for the static route."
    DEFVAL      { false }
    ::= { vRtrInetSRIndirectEntry 5 }

vRtrInetSRIndirectTunnelSrOspf   OBJECT-TYPE
    SYNTAX      TruthValue
    MAX-ACCESS  read-create
    STATUS      current
    DESCRIPTION
        "The value of vRtrInetSRIndirectTunnelSrOspf specifies if SR OSPF
         tunneling mechanism will be used to resolve next-hop for the static
         route or not.

         The value of vRtrInetSRIndirectTunnelSrOspf is valid only for indirect
         static routes (i.e. vRtrInetStaticRouteStaticType is 'indirect').

         If the value of vRtrInetSRIndirectTunnelSrOspf is set to 'true', IGP
         shortcuts associated with SR OSPF tunneling mechanism will be used to
         resolve next-hop for the static route."
    DEFVAL      { false }
    ::= { vRtrInetSRIndirectEntry 6 }

vRtrInetSRIndirectTunnelSrTe     OBJECT-TYPE
    SYNTAX      TruthValue
    MAX-ACCESS  read-create
    STATUS      current
    DESCRIPTION
        "The value of vRtrInetSRIndirectTunnelSrTe specifies if SR Traffic
         Engineering tunneling mechanism will be used to resolve next-hop for
         the static route or not.

         The value of vRtrInetSRIndirectTunnelSrTe is valid only for indirect
         static routes (i.e. vRtrInetStaticRouteStaticType is 'indirect').

         If the value of vRtrInetSRIndirectTunnelSrTe is set to 'true', IGP
         shortcuts associated with SR Traffic Engineering tunneling mechanism
         will be used to resolve next-hop for the static route."
    DEFVAL      { false }
    ::= { vRtrInetSRIndirectEntry 7 }

vRtrInetSRIndirectTunnelRibApi   OBJECT-TYPE
    SYNTAX      TruthValue
    MAX-ACCESS  read-create
    STATUS      current
    DESCRIPTION
        "The value of vRtrInetSRIndirectTunnelRibApi specifies whether MPLS RIB
         API is enabled on this static route."
    DEFVAL      { false }
    ::= { vRtrInetSRIndirectEntry 8 }

vRtrInetSRIndirectTnlMplsFwdPlcy OBJECT-TYPE
    SYNTAX      TruthValue
    MAX-ACCESS  read-create
    STATUS      current
    DESCRIPTION
        "The value of vRtrInetSRIndirectTnlMplsFwdPlcy specifies whether MPLS
         FWD POLICY is enabled on this static route."
    DEFVAL      { false }
    ::= { vRtrInetSRIndirectEntry 9 }

vRtrInetSRIndirectTunnelSrOspf3  OBJECT-TYPE
    SYNTAX      TruthValue
    MAX-ACCESS  read-create
    STATUS      current
    DESCRIPTION
        "The value of vRtrInetSRIndirectTunnelSrOspf3 specifies if SR OSPFv3
         tunneling mechanism will be used to resolve next-hop for the static
         route or not.

         The value of vRtrInetSRIndirectTunnelSrOspf3 is valid only for
         indirect static routes (i.e. vRtrInetStaticRouteStaticType is
         'indirect').

         If the value of vRtrInetSRIndirectTunnelSrOspf3 is set to 'true', IGP
         shortcuts associated with SR OSPFv3 tunneling mechanism will be used
         to resolve next-hop for the static route."
    DEFVAL      { false }
    ::= { vRtrInetSRIndirectEntry 10 }

vRtrInetSRIndirectTunFlexAlgoId  OBJECT-TYPE
    SYNTAX      TmnxFlexAlgoIdOrZero
    MAX-ACCESS  read-create
    STATUS      current
    DESCRIPTION
        "This specifies the Flexible Algorithm ID to use when resolving over
         the Segment Routing tunnels.

         Only tunnels that match this ID will be used to resolve the tunnel
         destination."
    DEFVAL      { 0 }
    ::= { vRtrInetSRIndirectEntry 11 }

vRtrInetSRIndirectLspTable       OBJECT-TYPE
    SYNTAX      SEQUENCE OF VRtrInetSRIndirectLspEntry
    MAX-ACCESS  not-accessible
    STATUS      current
    DESCRIPTION
        "The vRtrInetSRIndirectLspTable contains the different LSP names used
         to resolve a single indirect next-hop."
    ::= { tmnxVRtrObjs 120 }

vRtrInetSRIndirectLspEntry       OBJECT-TYPE
    SYNTAX      VRtrInetSRIndirectLspEntry
    MAX-ACCESS  not-accessible
    STATUS      current
    DESCRIPTION
        "Each row entry represents a Labeled Switch Path (LSP) configured for
         a virtual router in the system.  Entries can be created and deleted
         via SNMP SET operations.  Setting RowStatus to 'create and go'
         requires vRtrInetSRIndirectLspName to have been assigned a valid
         value. Creation of vRtrInetSRIndirectLspEntry is allowed only if value
         of vRtrInetSRIndirectTunnelRsvpTe is set to 'true'."
    INDEX       {
        vRtrID,
        vRtrInetStaticRouteDestType,
        vRtrInetStaticRouteDest,
        vRtrInetStaticRouteDestPfxLen,
        vRtrInetStaticRouteIndex,
        vRtrInetSRIndirectLspName
    }
    ::= { vRtrInetSRIndirectLspTable 1 }

VRtrInetSRIndirectLspEntry       ::= SEQUENCE
{
    vRtrInetSRIndirectLspName        TLNamedItemOrEmpty,
    vRtrInetSRIndirectLspRowStatus   RowStatus
}

vRtrInetSRIndirectLspName        OBJECT-TYPE
    SYNTAX      TLNamedItemOrEmpty
    MAX-ACCESS  not-accessible
    STATUS      current
    DESCRIPTION
        "The value of vRtrInetSRIndirectLspName specifies the administrative
         name for the Labeled Switch Path. The vRtrInetSRIndirectLspName must
         be unique within a virtual router instance."
    ::= { vRtrInetSRIndirectLspEntry 1 }

vRtrInetSRIndirectLspRowStatus   OBJECT-TYPE
    SYNTAX      RowStatus
    MAX-ACCESS  read-create
    STATUS      current
    DESCRIPTION
        "The value of vRtrInetSRIndirectLspRowStatus is used to create or
         delete an entry in this table."
    ::= { vRtrInetSRIndirectLspEntry 2 }

vRtrIfLagPerLinkHashTable        OBJECT-TYPE
    SYNTAX      SEQUENCE OF VRtrIfLagPerLinkHashEntry
    MAX-ACCESS  not-accessible
    STATUS      current
    DESCRIPTION
        "The vRtrIfLagPerLinkHashTable maintains weighted per-link-hash related
         lag attributes per interface. A LAG that has weighted per link hash
         enabled, will use the class and weight associated with the interface
         to select a link for egress traffic over port of this interface.
         Selection is done such that within each class the total weight of all
         interfaces on each LAG link is as close as possible to other links in
         the LAG."
    ::= { tmnxVRtrObjs 121 }

vRtrIfLagPerLinkHashEntry        OBJECT-TYPE
    SYNTAX      VRtrIfLagPerLinkHashEntry
    MAX-ACCESS  not-accessible
    STATUS      current
    DESCRIPTION
        "The vRtrIfLagPerLinkHashEntry maintains weighted per-link-hash related
         lag attributes for specific interface."
    INDEX       {
        vRtrID,
        vRtrIfIndex
    }
    ::= { vRtrIfLagPerLinkHashTable 1 }

VRtrIfLagPerLinkHashEntry        ::= SEQUENCE
{
    vRtrIfLagPerLinkHashLastChgd     TimeStamp,
    vRtrIfLagPerLinkHashClass        TmnxLagPerLinkHashClass,
    vRtrIfLagPerLinkHashWeight       TmnxLagPerLinkHashWeight
}

vRtrIfLagPerLinkHashLastChgd     OBJECT-TYPE
    SYNTAX      TimeStamp
    MAX-ACCESS  read-only
    STATUS      current
    DESCRIPTION
        "The value of vRtrIfLagPerLinkHashLastChgd indicates the sysUpTime at
         the time of the last modification of this entry."
    ::= { vRtrIfLagPerLinkHashEntry 1 }

vRtrIfLagPerLinkHashClass        OBJECT-TYPE
    SYNTAX      TmnxLagPerLinkHashClass
    MAX-ACCESS  read-write
    STATUS      current
    DESCRIPTION
        "The value of vRtrIfLagPerLinkHashClass specifies the class to be used
         to select a LAG link for this interface."
    DEFVAL      { 1 }
    ::= { vRtrIfLagPerLinkHashEntry 2 }

vRtrIfLagPerLinkHashWeight       OBJECT-TYPE
    SYNTAX      TmnxLagPerLinkHashWeight
    MAX-ACCESS  read-write
    STATUS      current
    DESCRIPTION
        "The value of vRtrIfLagPerLinkHashWeight specifies the weight to be
         associated with this interface when selecting a LAG link for this
         interface."
    DEFVAL      { 1 }
    ::= { vRtrIfLagPerLinkHashEntry 3 }

tmnxVrtrIfIndexIfNameTable       OBJECT-TYPE
    SYNTAX      SEQUENCE OF TmnxVrtrIfIndexIfNameEntry
    MAX-ACCESS  not-accessible
    STATUS      current
    DESCRIPTION
        "The tmnxVrtrIfIndexIfNameTable lists the IP interfaces per vRtrIfIndex
         and virtual router instance."
    ::= { tmnxVRtrObjs 122 }

tmnxVrtrIfIndexIfNameEntry       OBJECT-TYPE
    SYNTAX      TmnxVrtrIfIndexIfNameEntry
    MAX-ACCESS  not-accessible
    STATUS      current
    DESCRIPTION
        "Each conceptual row corresponds to an IP interface."
    INDEX       {
        vRtrIfIndex,
        vRtrID
    }
    ::= { tmnxVrtrIfIndexIfNameTable 1 }

TmnxVrtrIfIndexIfNameEntry       ::= SEQUENCE
{ tmnxVrtrIfIndexVrtrIfName        TNamedItem }

tmnxVrtrIfIndexVrtrIfName        OBJECT-TYPE
    SYNTAX      TNamedItem
    MAX-ACCESS  read-only
    STATUS      current
    DESCRIPTION
        "The value of tmnxVrtrIfIndexVrtrIfName is the name of this IP
         interface."
    ::= { tmnxVrtrIfIndexIfNameEntry 1 }

vRtrInetStaticRoutePfxTable      OBJECT-TYPE
    SYNTAX      SEQUENCE OF VRtrInetStaticRoutePfxEntry
    MAX-ACCESS  not-accessible
    STATUS      current
    DESCRIPTION
        "The table of addressing information relevant to this entity's Static
         Routing table."
    ::= { tmnxVRtrObjs 123 }

vRtrInetStaticRoutePfxEntry      OBJECT-TYPE
    SYNTAX      VRtrInetStaticRoutePfxEntry
    MAX-ACCESS  not-accessible
    STATUS      current
    DESCRIPTION
        "A particular route to a particular destination, through a particular
         next hop."
    INDEX       {
        vRtrID,
        vRtrInetStaticRouteDestType,
        vRtrInetStaticRouteDest,
        vRtrInetStaticRouteDestPfxLen
    }
    ::= { vRtrInetStaticRoutePfxTable 1 }

VRtrInetStaticRoutePfxEntry      ::= SEQUENCE
{
    vRtrInetStaticRoutePfxRowStatus  RowStatus,
    vRtrInetStaticRoutePfxCreateOrig TmnxCreateOrigin,
    vRtrInetStaticRoutePfxCfgNHCount Counter32,
    vRtrInetStaticRoutePfxCommVal1   DisplayString,
    vRtrInetStaticRoutePfxCommVal2   DisplayString,
    vRtrInetStaticRoutePfxCommVal3   DisplayString,
    vRtrInetStaticRoutePfxCommVal4   DisplayString,
    vRtrInetStaticRoutePfxCommVal5   DisplayString,
    vRtrInetStaticRoutePfxCommVal6   DisplayString,
    vRtrInetStaticRoutePfxCommVal7   DisplayString,
    vRtrInetStaticRoutePfxCommVal8   DisplayString,
    vRtrInetStaticRoutePfxCommVal9   DisplayString,
    vRtrInetStaticRoutePfxCommVal10  DisplayString,
    vRtrInetStaticRoutePfxCommVal11  DisplayString,
    vRtrInetStaticRoutePfxCommVal12  DisplayString,
    vRtrInetStaticRoutePfxTag        Unsigned32,
    vRtrInetStaticRoutePfxBackupTag  Unsigned32
}

vRtrInetStaticRoutePfxRowStatus  OBJECT-TYPE
    SYNTAX      RowStatus
    MAX-ACCESS  read-create
    STATUS      current
    DESCRIPTION
        "vRtrInetStaticRouteRowStatus controls the creation and deletion of
         rows in the table."
    ::= { vRtrInetStaticRoutePfxEntry 1 }

vRtrInetStaticRoutePfxCreateOrig OBJECT-TYPE
    SYNTAX      TmnxCreateOrigin
    MAX-ACCESS  read-only
    STATUS      current
    DESCRIPTION
        "The value of vRtrInetStaticRoutePfxCreateOrig indicates the mechanism
         that created this static route."
    ::= { vRtrInetStaticRoutePfxEntry 2 }

vRtrInetStaticRoutePfxCfgNHCount OBJECT-TYPE
    SYNTAX      Counter32
    MAX-ACCESS  read-only
    STATUS      current
    DESCRIPTION
        "vRtrInetStaticRoutePfxCfgNHCount indicates the number of nexthops
         configured under this prefix row entry."
    ::= { vRtrInetStaticRoutePfxEntry 3 }

vRtrInetStaticRoutePfxCommVal1   OBJECT-TYPE
    SYNTAX      DisplayString (SIZE (0..72))
    MAX-ACCESS  read-create
    STATUS      current
    DESCRIPTION
        "The value of vRtrInetStaticRoutePfxCommVal1 specifies the community
         name that is used to add to the static route. This value could then
         be used in route policies to control the distribution of the route
         into other protocols and by BGP to control the distribution of this
         route into other routers. A value of ''H  indicates that the
         vRtrInetStaticRoutePfxCommVal1 has not been set."
    DEFVAL      { ''H }
    ::= { vRtrInetStaticRoutePfxEntry 4 }

vRtrInetStaticRoutePfxCommVal2   OBJECT-TYPE
    SYNTAX      DisplayString (SIZE (0..72))
    MAX-ACCESS  read-create
    STATUS      current
    DESCRIPTION
        "The value of vRtrInetStaticRoutePfxCommVal2 specifies the community
         name that is used to add to the static route. This value could then
         be used in route policies to control the distribution of the route
         into other protocols and by BGP to control the distribution of this
         route into other routers. A value of ''H  indicates that the
         vRtrInetStaticRoutePfxCommVal2 has not been set."
    DEFVAL      { ''H }
    ::= { vRtrInetStaticRoutePfxEntry 5 }

vRtrInetStaticRoutePfxCommVal3   OBJECT-TYPE
    SYNTAX      DisplayString (SIZE (0..72))
    MAX-ACCESS  read-create
    STATUS      current
    DESCRIPTION
        "The value of vRtrInetStaticRoutePfxCommVal3 specifies the community
         name that is used to add to the static route. This value could then
         be used in route policies to control the distribution of the route
         into other protocols and by BGP to control the distribution of this
         route into other routers. A value of ''H  indicates that the
         vRtrInetStaticRoutePfxCommVal3 has not been set."
    DEFVAL      { ''H }
    ::= { vRtrInetStaticRoutePfxEntry 6 }

vRtrInetStaticRoutePfxCommVal4   OBJECT-TYPE
    SYNTAX      DisplayString (SIZE (0..72))
    MAX-ACCESS  read-create
    STATUS      current
    DESCRIPTION
        "The value of vRtrInetStaticRoutePfxCommVal4 specifies the community
         name that is used to add to the static route. This value could then
         be used in route policies to control the distribution of the route
         into other protocols and by BGP to control the distribution of this
         route into other routers. A value of ''H  indicates that the
         vRtrInetStaticRoutePfxCommVal4 has not been set."
    DEFVAL      { ''H }
    ::= { vRtrInetStaticRoutePfxEntry 7 }

vRtrInetStaticRoutePfxCommVal5   OBJECT-TYPE
    SYNTAX      DisplayString (SIZE (0..72))
    MAX-ACCESS  read-create
    STATUS      current
    DESCRIPTION
        "The value of vRtrInetStaticRoutePfxCommVal5 specifies the community
         name that is used to add to the static route. This value could then
         be used in route policies to control the distribution of the route
         into other protocols and by BGP to control the distribution of this
         route into other routers. A value of ''H  indicates that the
         vRtrInetStaticRoutePfxCommVal5 has not been set."
    DEFVAL      { ''H }
    ::= { vRtrInetStaticRoutePfxEntry 8 }

vRtrInetStaticRoutePfxCommVal6   OBJECT-TYPE
    SYNTAX      DisplayString (SIZE (0..72))
    MAX-ACCESS  read-create
    STATUS      current
    DESCRIPTION
        "The value of vRtrInetStaticRoutePfxCommVal6 specifies the community
         name that is used to add to the static route. This value could then
         be used in route policies to control the distribution of the route
         into other protocols and by BGP to control the distribution of this
         route into other routers. A value of ''H  indicates that the
         vRtrInetStaticRoutePfxCommVal6 has not been set."
    DEFVAL      { ''H }
    ::= { vRtrInetStaticRoutePfxEntry 9 }

vRtrInetStaticRoutePfxCommVal7   OBJECT-TYPE
    SYNTAX      DisplayString (SIZE (0..72))
    MAX-ACCESS  read-create
    STATUS      current
    DESCRIPTION
        "The value of vRtrInetStaticRoutePfxCommVal7 specifies the community
         name that is used to add to the static route. This value could then
         be used in route policies to control the distribution of the route
         into other protocols and by BGP to control the distribution of this
         route into other routers. A value of ''H  indicates that the
         vRtrInetStaticRoutePfxCommVal7 has not been set."
    DEFVAL      { ''H }
    ::= { vRtrInetStaticRoutePfxEntry 10 }

vRtrInetStaticRoutePfxCommVal8   OBJECT-TYPE
    SYNTAX      DisplayString (SIZE (0..72))
    MAX-ACCESS  read-create
    STATUS      current
    DESCRIPTION
        "The value of vRtrInetStaticRoutePfxCommVal8 specifies the community
         name that is used to add to the static route. This value could then
         be used in route policies to control the distribution of the route
         into other protocols and by BGP to control the distribution of this
         route into other routers. A value of ''H  indicates that the
         vRtrInetStaticRoutePfxCommVal8 has not been set."
    DEFVAL      { ''H }
    ::= { vRtrInetStaticRoutePfxEntry 11 }

vRtrInetStaticRoutePfxCommVal9   OBJECT-TYPE
    SYNTAX      DisplayString (SIZE (0..72))
    MAX-ACCESS  read-create
    STATUS      current
    DESCRIPTION
        "The value of vRtrInetStaticRoutePfxCommVal9 specifies the community
         name that is used to add to the static route. This value could then
         be used in route policies to control the distribution of the route
         into other protocols and by BGP to control the distribution of this
         route into other routers. A value of ''H  indicates that the
         vRtrInetStaticRoutePfxCommVal9 has not been set."
    DEFVAL      { ''H }
    ::= { vRtrInetStaticRoutePfxEntry 12 }

vRtrInetStaticRoutePfxCommVal10  OBJECT-TYPE
    SYNTAX      DisplayString (SIZE (0..72))
    MAX-ACCESS  read-create
    STATUS      current
    DESCRIPTION
        "The value of vRtrInetStaticRoutePfxCommVal10 specifies the community
         name that is used to add to the static route. This value could then
         be used in route policies to control the distribution of the route
         into other protocols and by BGP to control the distribution of this
         route into other routers. A value of ''H  indicates that the
         vRtrInetStaticRoutePfxCommVal10 has not been set."
    DEFVAL      { ''H }
    ::= { vRtrInetStaticRoutePfxEntry 13 }

vRtrInetStaticRoutePfxCommVal11  OBJECT-TYPE
    SYNTAX      DisplayString (SIZE (0..72))
    MAX-ACCESS  read-create
    STATUS      current
    DESCRIPTION
        "The value of vRtrInetStaticRoutePfxCommVal11 specifies the community
         name that is used to add to the static route. This value could then
         be used in route policies to control the distribution of the route
         into other protocols and by BGP to control the distribution of this
         route into other routers. A value of ''H  indicates that the
         vRtrInetStaticRoutePfxCommVal11 has not been set."
    DEFVAL      { ''H }
    ::= { vRtrInetStaticRoutePfxEntry 14 }

vRtrInetStaticRoutePfxCommVal12  OBJECT-TYPE
    SYNTAX      DisplayString (SIZE (0..72))
    MAX-ACCESS  read-create
    STATUS      current
    DESCRIPTION
        "The value of vRtrInetStaticRoutePfxCommVal12 specifies the community
         name that is used to add to the static route. This value could then
         be used in route policies to control the distribution of the route
         into other protocols and by BGP to control the distribution of this
         route into other routers. A value of ''H  indicates that the
         vRtrInetStaticRoutePfxCommVal12 has not been set."
    DEFVAL      { ''H }
    ::= { vRtrInetStaticRoutePfxEntry 15 }

vRtrInetStaticRoutePfxTag        OBJECT-TYPE
    SYNTAX      Unsigned32 (0..4294967295)
    MAX-ACCESS  read-create
    STATUS      current
    DESCRIPTION
        "The value of vRtrInetStaticRoutePfxTag specifies a 32-bit integer tag
         that is used to add to the static route. This tag could then be used
         in route policies to control distribution of the route into other
         protocols. A value of 0 indicates that the tag has not been set."
    DEFVAL      { 0 }
    ::= { vRtrInetStaticRoutePfxEntry 16 }

vRtrInetStaticRoutePfxBackupTag  OBJECT-TYPE
    SYNTAX      Unsigned32 (0..4294967295)
    MAX-ACCESS  read-create
    STATUS      current
    DESCRIPTION
        "The value of vRtrInetStaticRoutePfxBackupTag specifies a 32-bit
         integer tag that is used as the tag when the static route uses a
         backup next-hop.  This tag could then be used in route policies to
         control distribution  of the route into other protocols. A value of 0
         indicates that the tag has  not been set."
    DEFVAL      { 0 }
    ::= { vRtrInetStaticRoutePfxEntry 17 }

tmnxVrtrMssAdjTableLastCh        OBJECT-TYPE
    SYNTAX      TimeStamp
    MAX-ACCESS  read-only
    STATUS      current
    DESCRIPTION
        "The value of the object tmnxVrtrMssAdjTableLastCh indicates the value
         of sysUpTime at the time of the last modification of an entry in the
         tmnxVrtrMssAdjTable."
    ::= { tmnxVRtrObjs 124 }

tmnxVrtrMssAdjTable              OBJECT-TYPE
    SYNTAX      SEQUENCE OF TmnxVrtrMssAdjEntry
    MAX-ACCESS  not-accessible
    STATUS      current
    DESCRIPTION
        "The tmnxVrtrMssAdjTable provides a sparse extension of the
         vRtrConfTable to configure TCP Maximum Segment Size adjustment using
         an ISA-BB card.

         Rows in this table can be created and destroyed with SNMP operations."
    ::= { tmnxVRtrObjs 125 }

tmnxVrtrMssAdjEntry              OBJECT-TYPE
    SYNTAX      TmnxVrtrMssAdjEntry
    MAX-ACCESS  not-accessible
    STATUS      current
    DESCRIPTION
        "Each row entry in the tmnxVrtrMssAdjTable represents MSS adjustment
         configuration of a specific virtual router instance."
    INDEX       { vRtrID }
    ::= { tmnxVrtrMssAdjTable 1 }

TmnxVrtrMssAdjEntry              ::= SEQUENCE
{
    tmnxVrtrMssAdjLastCh             TimeStamp,
    tmnxVrtrMssAdjRowStatus          RowStatus,
    tmnxVrtrMssAdjGroup              TmnxIsaBbGrpId,
    tmnxVrtrMssAdjSegmentSize        Unsigned32
}

tmnxVrtrMssAdjLastCh             OBJECT-TYPE
    SYNTAX      TimeStamp
    MAX-ACCESS  read-only
    STATUS      current
    DESCRIPTION
        "The value of tmnxVrtrMssAdjLastCh indicates the sysUpTime at the time
         of the most recent management-initiated change to this table row."
    ::= { tmnxVrtrMssAdjEntry 1 }

tmnxVrtrMssAdjRowStatus          OBJECT-TYPE
    SYNTAX      RowStatus
    MAX-ACCESS  read-create
    STATUS      current
    DESCRIPTION
        "The value of tmnxVrtrMssAdjRowStatus specifies the row status of this
         row."
    ::= { tmnxVrtrMssAdjEntry 2 }

tmnxVrtrMssAdjGroup              OBJECT-TYPE
    SYNTAX      TmnxIsaBbGrpId (1..4)
    MAX-ACCESS  read-create
    STATUS      current
    DESCRIPTION
        "The value of tmnxVrtrMssAdjGroup specifies the ISA-BB group associated
         with this virtual router instance for the purpose of TCP Maximum
         Segment Size (MSS) option adjustment.

         The value must be specified when a row is created, and correspond to a
         row in the TIMETRA-NAT-MIB::tmnxNatGrpCfgTable.

         Traffic flows are redirected to the MSS adjustment function by means
         of a filter entry with action equal to 'tcpMssAdjust', for example a
         row in the TIMETRA-FILTER-MIB::tIPvXFltrEntryActionTable where the
         object tIPvXFltrEntryActAction is equal to 'tcpMssAdjust'."
    ::= { tmnxVrtrMssAdjEntry 3 }

tmnxVrtrMssAdjSegmentSize        OBJECT-TYPE
    SYNTAX      Unsigned32 (160..10240)
    MAX-ACCESS  read-create
    STATUS      current
    DESCRIPTION
        "The value of tmnxVrtrMssAdjSegmentSize specifies the intended value
         for the Maximum Segment Size (MSS) option in transmitted TCP SYN
         requests.

         A value must be specified when the row is created.

         If the MSS option is present in TCP SYN requests to be transmitted
         with a value smaller than or equal to the value of
         tmnxVrtrMssAdjSegmentSize, no adjustment is done.

         If the MSS option is not present, it is inserted with the value of
         tmnxVrtrMssAdjSegmentSize.

         If the MSS option is present in TCP SYN requests to be transmitted
         with a value greater than the value of tmnxVrtrMssAdjSegmentSize, it
         is replaced with the value of tmnxVrtrMssAdjSegmentSize."
    REFERENCE
        "RFC 793 Transmission Control Protocol Functional Specification
         section 3.1. Header Format."
    ::= { tmnxVrtrMssAdjEntry 4 }

vRtrConfFlowspecTableLstChg      OBJECT-TYPE
    SYNTAX      TimeStamp
    MAX-ACCESS  read-only
    STATUS      current
    DESCRIPTION
        "The value of the object vRtrConfFlowspecTableLstChg indicates the
         sysUpTime at the time of the last modification of
         vRtrConfFlowspecTable.

         If no changes were made to the table since the last re-initialization
         of the local network management subsystem, this object contains the
         value zero."
    ::= { tmnxVRtrObjs 126 }

vRtrConfFlowspecTable            OBJECT-TYPE
    SYNTAX      SEQUENCE OF VRtrConfFlowspecEntry
    MAX-ACCESS  not-accessible
    STATUS      current
    DESCRIPTION
        "The vRtrConfFlowspecTable provides an extension of the vRtrConfTable."
    ::= { tmnxVRtrObjs 127 }

vRtrConfFlowspecEntry            OBJECT-TYPE
    SYNTAX      VRtrConfFlowspecEntry
    MAX-ACCESS  not-accessible
    STATUS      current
    DESCRIPTION
        "Each row entry in the vRtrConfFlowspecEntry represents an additional
         column for vRtrConfTable specific to BGP Flowspec configuration."
    AUGMENTS    { vRtrConfEntry }
    ::= { vRtrConfFlowspecTable 1 }

VRtrConfFlowspecEntry            ::= SEQUENCE
{
    vRtrConfFlowspecLastChanged      TimeStamp,
    vRtrIpEmbeddedFlowspecMaxSize    TmnxEmbFlowspecFltrMaxSize,
    vRtrIpv6EmbeddedFlowspecMaxSize  TmnxEmbFlowspecFltrMaxSize,
    vRtrFlowspecFltrCamType          TIPvXFilterType
}

vRtrConfFlowspecLastChanged      OBJECT-TYPE
    SYNTAX      TimeStamp
    MAX-ACCESS  read-only
    STATUS      current
    DESCRIPTION
        "The value of vRtrConfFlowspecLastChanged indicates the sysUpTime at
         the time of last change to this row in vRtrConfFlowspecEntry."
    ::= { vRtrConfFlowspecEntry 1 }

vRtrIpEmbeddedFlowspecMaxSize    OBJECT-TYPE
    SYNTAX      TmnxEmbFlowspecFltrMaxSize
    MAX-ACCESS  read-create
    STATUS      current
    DESCRIPTION
        "The value of vRtrIpEmbeddedFlowspecMaxSize specifies the maximum
         number of entries reserved in the auto-created embedded IP filter for
         flowspec rules on this virtual router.

         Flowspec rules that do not fit within this limit will be rejected.

         The value 0 has special meaning, where all rules are silently rejected"
    DEFVAL      { 512 }
    ::= { vRtrConfFlowspecEntry 2 }

vRtrIpv6EmbeddedFlowspecMaxSize  OBJECT-TYPE
    SYNTAX      TmnxEmbFlowspecFltrMaxSize
    MAX-ACCESS  read-create
    STATUS      current
    DESCRIPTION
        "The value of vRtrIpv6EmbeddedFlowspecMaxSize specifies the maximum
         number of entries reserved in the auto-created embedded IPv6 filter
         for flowspec rules on this virtual router.

         Flowspec rules that do not fit within this limit will be rejected.

         The value 0 has special meaning, where all rules are silently rejected"
    DEFVAL      { 512 }
    ::= { vRtrConfFlowspecEntry 3 }

vRtrFlowspecFltrCamType          OBJECT-TYPE
    SYNTAX      TIPvXFilterType
    MAX-ACCESS  read-create
    STATUS      current
    DESCRIPTION
        "The value of vRtrFlowspecFltrCamType specifies the CAM type of the
         auto-created embedded filters for flowspec rules on this virtual
         router."
    DEFVAL      { normal }
    ::= { vRtrConfFlowspecEntry 4 }

vRtrInetSRIndirectSrTeLspTable   OBJECT-TYPE
    SYNTAX      SEQUENCE OF VRtrInetSRIndirectSrTeLspEntry
    MAX-ACCESS  not-accessible
    STATUS      current
    DESCRIPTION
        "The vRtrInetSRIndirectSrTeLspTable contains the different SR-TE LSP
         names used to resolve a single indirect next-hop."
    ::= { tmnxVRtrObjs 128 }

vRtrInetSRIndirectSrTeLspEntry   OBJECT-TYPE
    SYNTAX      VRtrInetSRIndirectSrTeLspEntry
    MAX-ACCESS  not-accessible
    STATUS      current
    DESCRIPTION
        "Each row entry represents a Labeled Switch Path (LSP) configured for
         a virtual router in the system.  Entries can be created and deleted
         via SNMP SET operations.  Setting RowStatus to 'create and go'
         requires vRtrInetSRIndirectSrTeLspName to have been assigned a valid
         value. Creation of vRtrInetSRIndirectSrTeLspEntry is allowed only if
         value of vRtrInetSRIndirectTunnelSrTe is set to 'true'."
    INDEX       {
        vRtrID,
        vRtrInetStaticRouteDestType,
        vRtrInetStaticRouteDest,
        vRtrInetStaticRouteDestPfxLen,
        vRtrInetStaticRouteIndex,
        vRtrInetSRIndirectSrTeLspName
    }
    ::= { vRtrInetSRIndirectSrTeLspTable 1 }

VRtrInetSRIndirectSrTeLspEntry   ::= SEQUENCE
{
    vRtrInetSRIndirectSrTeLspName    TLNamedItemOrEmpty,
    vRtrInetSRIndSrTeLspRowStatus    RowStatus
}

vRtrInetSRIndirectSrTeLspName    OBJECT-TYPE
    SYNTAX      TLNamedItemOrEmpty
    MAX-ACCESS  not-accessible
    STATUS      current
    DESCRIPTION
        "The value of vRtrInetSRIndirectSrTeLspName specifies the
         administrative name for the Labeled Switch Path. The
         vRtrInetSRIndirectSrTeLspName must be unique within a virtual router
         instance."
    ::= { vRtrInetSRIndirectSrTeLspEntry 1 }

vRtrInetSRIndSrTeLspRowStatus    OBJECT-TYPE
    SYNTAX      RowStatus
    MAX-ACCESS  read-create
    STATUS      current
    DESCRIPTION
        "The value of vRtrInetSRIndSrTeLspRowStatus is used to create or delete
         an entry in this table."
    ::= { vRtrInetSRIndirectSrTeLspEntry 2 }

vRtrIcmpStatTable                OBJECT-TYPE
    SYNTAX      SEQUENCE OF VRtrIcmpStatEntry
    MAX-ACCESS  not-accessible
    STATUS      current
    DESCRIPTION
        "The vRtrIcmpStatTable contains statistics of ICMPv4 messages that are
         received and sourced by a router instance."
    ::= { tmnxVRtrObjs 129 }

vRtrIcmpStatEntry                OBJECT-TYPE
    SYNTAX      VRtrIcmpStatEntry
    MAX-ACCESS  not-accessible
    STATUS      current
    DESCRIPTION
        "Each row entry represents the ICMPv4 statistics of a virtual router
         instance. Entries are created and deleted when entries in the
         vRtrConfEntry are created and deleted."
    AUGMENTS    { vRtrConfEntry }
    ::= { vRtrIcmpStatTable 1 }

VRtrIcmpStatEntry                ::= SEQUENCE
{
    vRtrIcmpInMsgs                   Counter32,
    vRtrIcmpInErrors                 Counter32,
    vRtrIcmpInDestUnreachs           Counter32,
    vRtrIcmpInRedirects              Counter32,
    vRtrIcmpInEchos                  Counter32,
    vRtrIcmpInEchoReplies            Counter32,
    vRtrIcmpInTimeExcds              Counter32,
    vRtrIcmpInSrcQuenchs             Counter32,
    vRtrIcmpInTimestamps             Counter32,
    vRtrIcmpInTimestampReps          Counter32,
    vRtrIcmpInAddrMasks              Counter32,
    vRtrIcmpInAddrMaskReps           Counter32,
    vRtrIcmpInParmProblems           Counter32,
    vRtrIcmpOutMsgs                  Counter32,
    vRtrIcmpOutErrors                Counter32,
    vRtrIcmpOutDestUnreachs          Counter32,
    vRtrIcmpOutRedirects             Counter32,
    vRtrIcmpOutEchos                 Counter32,
    vRtrIcmpOutEchoReplies           Counter32,
    vRtrIcmpOutTimeExcds             Counter32,
    vRtrIcmpOutSrcQuenchs            Counter32,
    vRtrIcmpOutTimestamps            Counter32,
    vRtrIcmpOutTimestampReps         Counter32,
    vRtrIcmpOutAddrMasks             Counter32,
    vRtrIcmpOutAddrMaskReps          Counter32,
    vRtrIcmpOutParmProblems          Counter32,
    vRtrIcmpOutDiscards              Counter32
}

vRtrIcmpInMsgs                   OBJECT-TYPE
    SYNTAX      Counter32
    MAX-ACCESS  read-only
    STATUS      current
    DESCRIPTION
        "The value of vRtrIcmpInMsgs indicates the total number of ICMPv4
         messages received by this router instance which includes all those
         counted by vRtrIcmpInErrors."
    ::= { vRtrIcmpStatEntry 1 }

vRtrIcmpInErrors                 OBJECT-TYPE
    SYNTAX      Counter32
    MAX-ACCESS  read-only
    STATUS      current
    DESCRIPTION
        "The value of vRtrIcmpInErrors indicates the number of ICMPv4 messages
         which this router instance received but determined as having
         ICMP-specific errors (bad ICMPv4 checksums, bad length , etc.)."
    ::= { vRtrIcmpStatEntry 2 }

vRtrIcmpInDestUnreachs           OBJECT-TYPE
    SYNTAX      Counter32
    MAX-ACCESS  read-only
    STATUS      current
    DESCRIPTION
        "The value of vRtrIcmpInDestUnreachs indicates the number of ICMPv4
         Destination Unreachable messages received by this router instance."
    ::= { vRtrIcmpStatEntry 3 }

vRtrIcmpInRedirects              OBJECT-TYPE
    SYNTAX      Counter32
    MAX-ACCESS  read-only
    STATUS      current
    DESCRIPTION
        "The value of vRtrIcmpInRedirects indicates number of ICMPv4 Redirect
         messages received by this router instance."
    ::= { vRtrIcmpStatEntry 4 }

vRtrIcmpInEchos                  OBJECT-TYPE
    SYNTAX      Counter32
    MAX-ACCESS  read-only
    STATUS      current
    DESCRIPTION
        "The value of vRtrIcmpInEchos indicates the number of ICMPv4 Echo
         (request) messages received by this router instance."
    ::= { vRtrIcmpStatEntry 5 }

vRtrIcmpInEchoReplies            OBJECT-TYPE
    SYNTAX      Counter32
    MAX-ACCESS  read-only
    STATUS      current
    DESCRIPTION
        "The value of vRtrIcmpInEchoReplies indicates the number of ICMPv4 Echo
         Reply messages received by this router instance."
    ::= { vRtrIcmpStatEntry 6 }

vRtrIcmpInTimeExcds              OBJECT-TYPE
    SYNTAX      Counter32
    MAX-ACCESS  read-only
    STATUS      current
    DESCRIPTION
        "The value of vRtrIcmpInTimeExcds indicates the number of ICMPv4 Time
         Exceeded messages received by this router instance."
    ::= { vRtrIcmpStatEntry 7 }

vRtrIcmpInSrcQuenchs             OBJECT-TYPE
    SYNTAX      Counter32
    MAX-ACCESS  read-only
    STATUS      current
    DESCRIPTION
        "The value of vRtrIcmpInSrcQuenchs indicates number of ICMPv4 Source
         Quench messages received by this router instance."
    ::= { vRtrIcmpStatEntry 8 }

vRtrIcmpInTimestamps             OBJECT-TYPE
    SYNTAX      Counter32
    MAX-ACCESS  read-only
    STATUS      current
    DESCRIPTION
        "The value of vRtrIcmpInTimestamps indicates number of ICMPv4 Timestamp
         (request) messages received by this router instance."
    ::= { vRtrIcmpStatEntry 9 }

vRtrIcmpInTimestampReps          OBJECT-TYPE
    SYNTAX      Counter32
    MAX-ACCESS  read-only
    STATUS      current
    DESCRIPTION
        "The value of vRtrIcmpInTimestampReps indicates number of ICMPv4
         Timestamp Reply messages received by this router instance."
    ::= { vRtrIcmpStatEntry 10 }

vRtrIcmpInAddrMasks              OBJECT-TYPE
    SYNTAX      Counter32
    MAX-ACCESS  read-only
    STATUS      current
    DESCRIPTION
        "The value of vRtrIcmpInAddrMasks indicates number of ICMPv4 Address
         Mask Request received by this router instance."
    ::= { vRtrIcmpStatEntry 11 }

vRtrIcmpInAddrMaskReps           OBJECT-TYPE
    SYNTAX      Counter32
    MAX-ACCESS  read-only
    STATUS      current
    DESCRIPTION
        "The value of vRtrIcmpInAddrMaskReps indicates number of ICMPv4 Address
         Mask Reply messages received by this router instance."
    ::= { vRtrIcmpStatEntry 12 }

vRtrIcmpInParmProblems           OBJECT-TYPE
    SYNTAX      Counter32
    MAX-ACCESS  read-only
    STATUS      current
    DESCRIPTION
        "The value of vRtrIcmpInParmProblems indicates the number of ICMPv4
         Parameter Problem messages received by this router instance."
    ::= { vRtrIcmpStatEntry 13 }

vRtrIcmpOutMsgs                  OBJECT-TYPE
    SYNTAX      Counter32
    MAX-ACCESS  read-only
    STATUS      current
    DESCRIPTION
        "The value of vRtrIcmpOutMsgs indicates the total number of ICMPv4
         messages which this router instance attempted to send.  Note that
         this counter includes all those counted by vRtrIcmpOutErrors."
    ::= { vRtrIcmpStatEntry 14 }

vRtrIcmpOutErrors                OBJECT-TYPE
    SYNTAX      Counter32
    MAX-ACCESS  read-only
    STATUS      current
    DESCRIPTION
        "The value of vRtrIcmpOutErrors indicates the number of ICMPv4
         messages which this router instance did not send due to problems
         discovered within ICMPv4 such as a lack of buffers.  This value
         should not include errors discovered outside the ICMPv4 layer such
         as the inability of VRtr IPv4 to route the resultant datagram.  In
         some implementations there may be no types of error which contribute
         to this counter's value."
    ::= { vRtrIcmpStatEntry 15 }

vRtrIcmpOutDestUnreachs          OBJECT-TYPE
    SYNTAX      Counter32
    MAX-ACCESS  read-only
    STATUS      current
    DESCRIPTION
        "The value of vRtrIcmpOutDestUnreachs indicates the number of ICMPv4
         Destination Unreachable messages sent by this router instance."
    ::= { vRtrIcmpStatEntry 16 }

vRtrIcmpOutRedirects             OBJECT-TYPE
    SYNTAX      Counter32
    MAX-ACCESS  read-only
    STATUS      current
    DESCRIPTION
        "The value of vRtrIcmpOutRedirects indicates the number of ICMPv4
         Redirect messages sent by this router instance."
    ::= { vRtrIcmpStatEntry 17 }

vRtrIcmpOutEchos                 OBJECT-TYPE
    SYNTAX      Counter32
    MAX-ACCESS  read-only
    STATUS      current
    DESCRIPTION
        "The value of vRtrIcmpOutEchos indicates the number of ICMPv4 Echo
         Request messages sent by this router instance."
    ::= { vRtrIcmpStatEntry 18 }

vRtrIcmpOutEchoReplies           OBJECT-TYPE
    SYNTAX      Counter32
    MAX-ACCESS  read-only
    STATUS      current
    DESCRIPTION
        "The value of vRtrIcmpOutEchoReplies indicates the number of ICMPv4
         Echo Reply messages sent by this router instance."
    ::= { vRtrIcmpStatEntry 19 }

vRtrIcmpOutTimeExcds             OBJECT-TYPE
    SYNTAX      Counter32
    MAX-ACCESS  read-only
    STATUS      current
    DESCRIPTION
        "The value of vRtrIcmpOutTimeExcds indicates the number of ICMPv4 Time
         Exceeded messages sent by this router instance."
    ::= { vRtrIcmpStatEntry 20 }

vRtrIcmpOutSrcQuenchs            OBJECT-TYPE
    SYNTAX      Counter32
    MAX-ACCESS  read-only
    STATUS      current
    DESCRIPTION
        "The value of vRtrIcmpOutSrcQuenchs indicates the number of ICMPv4
         Source Quench messages sent by this router instance."
    ::= { vRtrIcmpStatEntry 21 }

vRtrIcmpOutTimestamps            OBJECT-TYPE
    SYNTAX      Counter32
    MAX-ACCESS  read-only
    STATUS      current
    DESCRIPTION
        "The value of vRtrIcmpOutTimestamps indicates the number of ICMPv4
         Timestamp (request) messages sent by this router instance."
    ::= { vRtrIcmpStatEntry 22 }

vRtrIcmpOutTimestampReps         OBJECT-TYPE
    SYNTAX      Counter32
    MAX-ACCESS  read-only
    STATUS      current
    DESCRIPTION
        "The value of vRtrIcmpOutTimestampReps indicates the number of ICMPv4
         Timestamp Reply messages sent by this router instance."
    ::= { vRtrIcmpStatEntry 23 }

vRtrIcmpOutAddrMasks             OBJECT-TYPE
    SYNTAX      Counter32
    MAX-ACCESS  read-only
    STATUS      current
    DESCRIPTION
        "The value of vRtrIcmpOutAddrMasks indicates the number of ICMPv4
         Address Mask Request sent by this router instance."
    ::= { vRtrIcmpStatEntry 24 }

vRtrIcmpOutAddrMaskReps          OBJECT-TYPE
    SYNTAX      Counter32
    MAX-ACCESS  read-only
    STATUS      current
    DESCRIPTION
        "The value of vRtrIcmpOutAddrMaskReps indicates the number of ICMPv4
         Address Mask Reply messages sent by this router instance."
    ::= { vRtrIcmpStatEntry 25 }

vRtrIcmpOutParmProblems          OBJECT-TYPE
    SYNTAX      Counter32
    MAX-ACCESS  read-only
    STATUS      current
    DESCRIPTION
        "The value of vRtrIcmpOutParmProblems indicates the number of ICMPv4
         Parameter Problem messages sent by this router instance."
    ::= { vRtrIcmpStatEntry 26 }

vRtrIcmpOutDiscards              OBJECT-TYPE
    SYNTAX      Counter32
    MAX-ACCESS  read-only
    STATUS      current
    DESCRIPTION
        "The value of vRtrIcmpOutDiscards indicates the number of ICMPv4
         outgoing packets that were dropped by this router instance."
    ::= { vRtrIcmpStatEntry 27 }

vRtrIfIcmpStatTable              OBJECT-TYPE
    SYNTAX      SEQUENCE OF VRtrIfIcmpStatEntry
    MAX-ACCESS  not-accessible
    STATUS      current
    DESCRIPTION
        "The vRtrIfIcmpStatTable table contains statistics of ICMPv4 messages
         that are received and sourced by a router interface."
    ::= { tmnxVRtrObjs 130 }

vRtrIfIcmpStatEntry              OBJECT-TYPE
    SYNTAX      VRtrIfIcmpStatEntry
    MAX-ACCESS  not-accessible
    STATUS      current
    DESCRIPTION
        "Each row entry represents the ICMPv4 statistics of a virtual router
         interface. Entries are created and deleted when entries in the
         vRtrIfTable are created and deleted."
    AUGMENTS    { vRtrIfEntry }
    ::= { vRtrIfIcmpStatTable 1 }

VRtrIfIcmpStatEntry              ::= SEQUENCE
{
    vRtrIfIcmpInMsgs                 Counter32,
    vRtrIfIcmpInErrors               Counter32,
    vRtrIfIcmpInDestUnreachs         Counter32,
    vRtrIfIcmpInRedirects            Counter32,
    vRtrIfIcmpInEchos                Counter32,
    vRtrIfIcmpInEchoReplies          Counter32,
    vRtrIfIcmpInTimeExcds            Counter32,
    vRtrIfIcmpInSrcQuenchs           Counter32,
    vRtrIfIcmpInTimestamps           Counter32,
    vRtrIfIcmpInTimestampReps        Counter32,
    vRtrIfIcmpInAddrMasks            Counter32,
    vRtrIfIcmpInAddrMaskReps         Counter32,
    vRtrIfIcmpInParmProblems         Counter32,
    vRtrIfIcmpOutMsgs                Counter32,
    vRtrIfIcmpOutErrors              Counter32,
    vRtrIfIcmpOutDestUnreachs        Counter32,
    vRtrIfIcmpOutRedirects           Counter32,
    vRtrIfIcmpOutEchos               Counter32,
    vRtrIfIcmpOutEchoReplies         Counter32,
    vRtrIfIcmpOutTimeExcds           Counter32,
    vRtrIfIcmpOutSrcQuenchs          Counter32,
    vRtrIfIcmpOutTimestamps          Counter32,
    vRtrIfIcmpOutTimestampReps       Counter32,
    vRtrIfIcmpOutAddrMasks           Counter32,
    vRtrIfIcmpOutAddrMaskReps        Counter32,
    vRtrIfIcmpOutParmProblems        Counter32,
    vRtrIfIcmpOutDiscards            Counter32
}

vRtrIfIcmpInMsgs                 OBJECT-TYPE
    SYNTAX      Counter32
    MAX-ACCESS  read-only
    STATUS      current
    DESCRIPTION
        "The value of vRtrIfIcmpInMsgs indicates the total number of ICMPv4
         messages received by this interface which includes all those counted
         by vRtrIfIcmpInErrors. Note that this interface is the interface to
         which the ICMPv4 messages were addressed which may not be necessarily
         the input interface for the messages."
    ::= { vRtrIfIcmpStatEntry 1 }

vRtrIfIcmpInErrors               OBJECT-TYPE
    SYNTAX      Counter32
    MAX-ACCESS  read-only
    STATUS      current
    DESCRIPTION
        "The value of vRtrIfIcmpInErrors indicates the number of ICMPv4
         messages which this interface received but determined as having
         ICMPv4-specific errors (bad ICMPv4 checksums, bad length , etc.)."
    ::= { vRtrIfIcmpStatEntry 2 }

vRtrIfIcmpInDestUnreachs         OBJECT-TYPE
    SYNTAX      Counter32
    MAX-ACCESS  read-only
    STATUS      current
    DESCRIPTION
        "The value of vRtrIfIcmpInDestUnreachs indicates the number of ICMPv4
         Destination Unreachable messages received by this interface."
    ::= { vRtrIfIcmpStatEntry 3 }

vRtrIfIcmpInRedirects            OBJECT-TYPE
    SYNTAX      Counter32
    MAX-ACCESS  read-only
    STATUS      current
    DESCRIPTION
        "The value of vRtrIfIcmpInRedirects indicates number of ICMPv4 Redirect
         messages received by this interface."
    ::= { vRtrIfIcmpStatEntry 4 }

vRtrIfIcmpInEchos                OBJECT-TYPE
    SYNTAX      Counter32
    MAX-ACCESS  read-only
    STATUS      current
    DESCRIPTION
        "The value of vRtrIfIcmpInEchos indicates the number of ICMPv4 Echo
         (request) messages received by this interface."
    ::= { vRtrIfIcmpStatEntry 5 }

vRtrIfIcmpInEchoReplies          OBJECT-TYPE
    SYNTAX      Counter32
    MAX-ACCESS  read-only
    STATUS      current
    DESCRIPTION
        "The value of vRtrIfIcmpInEchoReplies indicates the number of ICMPv4
         Echo Reply messages received by this interface."
    ::= { vRtrIfIcmpStatEntry 6 }

vRtrIfIcmpInTimeExcds            OBJECT-TYPE
    SYNTAX      Counter32
    MAX-ACCESS  read-only
    STATUS      current
    DESCRIPTION
        "The value of vRtrIfIcmpInTimeExcds indicates the number of ICMPv4 Time
         Exceeded messages received by this interface."
    ::= { vRtrIfIcmpStatEntry 7 }

vRtrIfIcmpInSrcQuenchs           OBJECT-TYPE
    SYNTAX      Counter32
    MAX-ACCESS  read-only
    STATUS      current
    DESCRIPTION
        "The value of vRtrIfIcmpInSrcQuenchs indicates the number of ICMPv4
         Source Quench messages received by this interface."
    ::= { vRtrIfIcmpStatEntry 8 }

vRtrIfIcmpInTimestamps           OBJECT-TYPE
    SYNTAX      Counter32
    MAX-ACCESS  read-only
    STATUS      current
    DESCRIPTION
        "The value of vRtrIfIcmpInTimestamps indicates the number of ICMPv4
         Timestamp (request) messages received by this interface."
    ::= { vRtrIfIcmpStatEntry 9 }

vRtrIfIcmpInTimestampReps        OBJECT-TYPE
    SYNTAX      Counter32
    MAX-ACCESS  read-only
    STATUS      current
    DESCRIPTION
        "The value of vRtrIfIcmpInTimestampReps indicates the number of ICMPv4
         Timestamp Reply messages received by this interface."
    ::= { vRtrIfIcmpStatEntry 10 }

vRtrIfIcmpInAddrMasks            OBJECT-TYPE
    SYNTAX      Counter32
    MAX-ACCESS  read-only
    STATUS      current
    DESCRIPTION
        "The value of vRtrIfIcmpInAddrMasks indicates the number of ICMPv4
         Address Mask Request received by this interface."
    ::= { vRtrIfIcmpStatEntry 11 }

vRtrIfIcmpInAddrMaskReps         OBJECT-TYPE
    SYNTAX      Counter32
    MAX-ACCESS  read-only
    STATUS      current
    DESCRIPTION
        "The value of vRtrIfIcmpInAddrMaskReps indicates the number of ICMPv4
         Address Mask Reply messages received by this interface."
    ::= { vRtrIfIcmpStatEntry 12 }

vRtrIfIcmpInParmProblems         OBJECT-TYPE
    SYNTAX      Counter32
    MAX-ACCESS  read-only
    STATUS      current
    DESCRIPTION
        "The value of vRtrIfIcmpInParmProblems indicates the number of ICMPv4
         Parameter Problem messages received by this interface."
    ::= { vRtrIfIcmpStatEntry 13 }

vRtrIfIcmpOutMsgs                OBJECT-TYPE
    SYNTAX      Counter32
    MAX-ACCESS  read-only
    STATUS      current
    DESCRIPTION
        "The value of vRtrIfIcmpOutMsgs indicates the total number of ICMPv4
         messages which this interface attempted to send.  Note that this
         counter includes all those counted by vRtrIfIcmpOutErrors."
    ::= { vRtrIfIcmpStatEntry 14 }

vRtrIfIcmpOutErrors              OBJECT-TYPE
    SYNTAX      Counter32
    MAX-ACCESS  read-only
    STATUS      current
    DESCRIPTION
        "The value of vRtrIfIcmpOutErrors indicates the number of ICMPv4
         messages which this interface did not send due to problems discovered
         within ICMPv4 such as a lack of buffers.  This value should not include
         errors discovered outside the ICMPv4 layer such as the inability of
         VRtr IPv6 to route the resultant datagram.  In some implementations
         there may be no types of error which contribute to this counter's
         value."
    ::= { vRtrIfIcmpStatEntry 15 }

vRtrIfIcmpOutDestUnreachs        OBJECT-TYPE
    SYNTAX      Counter32
    MAX-ACCESS  read-only
    STATUS      current
    DESCRIPTION
        "The value of vRtrIfIcmpOutDestUnreachs indicates the number of ICMPv4
         Destination Unreachable messages sent by this interface."
    ::= { vRtrIfIcmpStatEntry 16 }

vRtrIfIcmpOutRedirects           OBJECT-TYPE
    SYNTAX      Counter32
    MAX-ACCESS  read-only
    STATUS      current
    DESCRIPTION
        "The value of vRtrIfIcmpOutRedirects indicates the number of ICMPv4
         Redirect messages sent by this interface."
    ::= { vRtrIfIcmpStatEntry 17 }

vRtrIfIcmpOutEchos               OBJECT-TYPE
    SYNTAX      Counter32
    MAX-ACCESS  read-only
    STATUS      current
    DESCRIPTION
        "The value of vRtrIfIcmpOutEchos indicates the number of ICMPv4 Echo
         Request messages sent by this interface."
    ::= { vRtrIfIcmpStatEntry 18 }

vRtrIfIcmpOutEchoReplies         OBJECT-TYPE
    SYNTAX      Counter32
    MAX-ACCESS  read-only
    STATUS      current
    DESCRIPTION
        "The value of vRtrIfIcmpOutEchoReplies indicates the number of ICMPv4
         Echo Reply messages sent by this interface."
    ::= { vRtrIfIcmpStatEntry 19 }

vRtrIfIcmpOutTimeExcds           OBJECT-TYPE
    SYNTAX      Counter32
    MAX-ACCESS  read-only
    STATUS      current
    DESCRIPTION
        "The value of vRtrIfIcmpOutTimeExcds indicates the number of ICMPv4
         Time Exceeded messages sent by this interface."
    ::= { vRtrIfIcmpStatEntry 20 }

vRtrIfIcmpOutSrcQuenchs          OBJECT-TYPE
    SYNTAX      Counter32
    MAX-ACCESS  read-only
    STATUS      current
    DESCRIPTION
        "The value of vRtrIfIcmpOutSrcQuenchs indicates the number of ICMPv4
         Source Quench messages sent by this interface."
    ::= { vRtrIfIcmpStatEntry 21 }

vRtrIfIcmpOutTimestamps          OBJECT-TYPE
    SYNTAX      Counter32
    MAX-ACCESS  read-only
    STATUS      current
    DESCRIPTION
        "The value of vRtrIfIcmpOutTimestamps indicates the number of ICMPv4
         Timestamp (request) messages sent by this interface."
    ::= { vRtrIfIcmpStatEntry 22 }

vRtrIfIcmpOutTimestampReps       OBJECT-TYPE
    SYNTAX      Counter32
    MAX-ACCESS  read-only
    STATUS      current
    DESCRIPTION
        "The value of vRtrIfIcmpOutTimestampReps indicates the number of ICMPv4
         Timestamp Reply messages sent by this interface."
    ::= { vRtrIfIcmpStatEntry 23 }

vRtrIfIcmpOutAddrMasks           OBJECT-TYPE
    SYNTAX      Counter32
    MAX-ACCESS  read-only
    STATUS      current
    DESCRIPTION
        "The value of vRtrIfIcmpOutAddrMasks indicates the number of ICMPv4
         Address Mask Request sent by this interface."
    ::= { vRtrIfIcmpStatEntry 24 }

vRtrIfIcmpOutAddrMaskReps        OBJECT-TYPE
    SYNTAX      Counter32
    MAX-ACCESS  read-only
    STATUS      current
    DESCRIPTION
        "The value of vRtrIfIcmpOutAddrMaskReps indicates the number of ICMPv4
         Address Mask Reply messages sent by this interface."
    ::= { vRtrIfIcmpStatEntry 25 }

vRtrIfIcmpOutParmProblems        OBJECT-TYPE
    SYNTAX      Counter32
    MAX-ACCESS  read-only
    STATUS      current
    DESCRIPTION
        "The value of vRtrIfIcmpOutParmProblems indicates the number of ICMPv4
         Parameter Problem messages sent by this interface."
    ::= { vRtrIfIcmpStatEntry 26 }

vRtrIfIcmpOutDiscards            OBJECT-TYPE
    SYNTAX      Counter32
    MAX-ACCESS  read-only
    STATUS      current
    DESCRIPTION
        "The value of vRtrIfIcmpOutDiscards indicates the number of ICMPv4
         outgoing packets that were dropped on this interface."
    ::= { vRtrIfIcmpStatEntry 27 }

vRtrIfExtParmsTable              OBJECT-TYPE
    SYNTAX      SEQUENCE OF VRtrIfExtParmsEntry
    MAX-ACCESS  not-accessible
    STATUS      current
    DESCRIPTION
        "The vRtrIfExtParmsTable has an entry for each router interface
         configured in the system. This table augments the vRtrIfTable."
    ::= { tmnxVRtrObjs 131 }

vRtrIfExtParmsEntry              OBJECT-TYPE
    SYNTAX      VRtrIfExtParmsEntry
    MAX-ACCESS  not-accessible
    STATUS      current
    DESCRIPTION
        "Each row entry represents a virtual router interface in the system.
         Entries can be created and deleted via SNMP SET operations using the
         vRtrIfRowStatus variable."
    AUGMENTS    { vRtrIfEntry }
    ::= { vRtrIfExtParmsTable 1 }

VRtrIfExtParmsEntry              ::= SEQUENCE
{
    vRtrIfIpv4ArpPopulateHost        TruthValue,
    vRtrIfIpv4ArpRouteTag            Unsigned32,
    vRtrIfIpv6NdPopulateHost         TruthValue,
    vRtrIfIpv6NdRouteTag             Unsigned32,
    vRtrIfIpHelperGatewayAddress     IpAddress,
    vRtrIfGreTermination             TruthValue,
    vRtrIfIlmUntrusted               TruthValue,
    vRtrIfIlmDefaultForwarding       INTEGER,
    vRtrIfIpv6ForwardIpv4            TruthValue,
    vRtrIfAcctPolicyId               Unsigned32,
    vRtrIfCollectStats               TruthValue,
    vRtrIfUnidirectionalLinkDelay    Integer32,
    vRtrIfIngrDestinationClassLookup TruthValue,
    vRtrIfIcmpTtlExpiredMatchingAddr TruthValue,
    vRtrIfExtRefOcSubIfPresence      TruthValue,
    vRtrIfExtRefOcSubIf              Unsigned32,
    vRtrIfMtuProfile                 TruthValue,
    vRtrIfOperMtuProfile             Unsigned32,
    vRtrIfAllocMtuProfile            Unsigned32,
    vRtrIfIpv6GreTermination         TruthValue
}

vRtrIfIpv4ArpPopulateHost        OBJECT-TYPE
    SYNTAX      TruthValue
    MAX-ACCESS  read-create
    STATUS      obsolete
    DESCRIPTION
        "The value of vRtrIfIpv4ArpPopulateHost specifies whether populate host
         is enabled.

         When the value is set to 'true', unsolicited learning is enabled.

         When the value is set to 'false', unsolicited learning is disabled."
    DEFVAL      { false }
    ::= { vRtrIfExtParmsEntry 1 }

vRtrIfIpv4ArpRouteTag            OBJECT-TYPE
    SYNTAX      Unsigned32 (0 | 1..255)
    MAX-ACCESS  read-create
    STATUS      obsolete
    DESCRIPTION
        "The value of vRtrIfIpv4ArpRouteTag specifies route tag."
    DEFVAL      { 0 }
    ::= { vRtrIfExtParmsEntry 2 }

vRtrIfIpv6NdPopulateHost         OBJECT-TYPE
    SYNTAX      TruthValue
    MAX-ACCESS  read-create
    STATUS      obsolete
    DESCRIPTION
        "The value of vRtrIfIpv6NdPopulateHost specifies whether populate host
         is enabled.

         When the value is set to 'true', unsolicited learning is enabled.

         When the value is set to 'false', unsolicited learning is disabled."
    DEFVAL      { false }
    ::= { vRtrIfExtParmsEntry 3 }

vRtrIfIpv6NdRouteTag             OBJECT-TYPE
    SYNTAX      Unsigned32 (0 | 1..255)
    MAX-ACCESS  read-create
    STATUS      obsolete
    DESCRIPTION
        "The value of vRtrIfIpv6NdRouteTag specifies route tag."
    DEFVAL      { 0 }
    ::= { vRtrIfExtParmsEntry 4 }

vRtrIfIpHelperGatewayAddress     OBJECT-TYPE
    SYNTAX      IpAddress
    MAX-ACCESS  read-create
    STATUS      current
    DESCRIPTION
        "The value of vRtrIfIpHelperGatewayAddress specifies the gateway
         address to forward the UDP traffic sent to the local broadcast
         address.

         A value of 0.0.0.0, the default value indicates that no gateway is
         configured."
    DEFVAL      { '00000000'H }
    ::= { vRtrIfExtParmsEntry 5 }

vRtrIfGreTermination             OBJECT-TYPE
    SYNTAX      TruthValue
    MAX-ACCESS  read-create
    STATUS      current
    DESCRIPTION
        "The value of vRtrIfGreTermination specifies whether the user can
         terminate MPLS-over-GRE as well as IP-over-GRE packets concurrently on
         the system interface address or an address from an user defined
         subnet.

         When the value is set to 'true', GRE packet termination will happen
         concurrently to the system interface IPv4 address and to any address
         that falls in the subnet of the interface primary IPv4 address. This
         is only applicable to network interfaces and there can be only one
         network interface with GRE termination enabled in the virtual router.

         When the value is set to 'false', GRE packet termination can only
         happen to the system interface IPv4 address. When this interface is
         unnumbered GRE termination will be enabled to the subnet of the
         primary IPv4 address of the parent interface."
    DEFVAL      { false }
    ::= { vRtrIfExtParmsEntry 6 }

vRtrIfIlmUntrusted               OBJECT-TYPE
    SYNTAX      TruthValue
    MAX-ACCESS  read-create
    STATUS      current
    DESCRIPTION
        "The value of vRtrIfIlmUntrusted specifies whether the interface can
         participate in the Selective ILM (Incoming Label Map) feature. This is
         usually done for an inter-AS interface.

         A maximum of 15 interfaces can be selected."
    DEFVAL      { false }
    ::= { vRtrIfExtParmsEntry 7 }

vRtrIfIlmDefaultForwarding       OBJECT-TYPE
    SYNTAX      INTEGER {
        forward (1),
        drop    (2)
    }
    MAX-ACCESS  read-create
    STATUS      current
    DESCRIPTION
        "The value of vRtrIfIlmDefaultForwarding specifies the
         default-forwarding for the inter-AS Selective ILM interface.

         When the value is set to 'forward', the labeled packets will be
         checked normally against the table of programmed ILMs to decide if it
         should be dropped or forwarded in a GRT, a VRF, or a L2 service
         context.

         When the value is set to 'drop', all labeled packets received on that
         interface will automatically be dropped.

         For backwards compatibility the default value is 'forward'."
    DEFVAL      { forward }
    ::= { vRtrIfExtParmsEntry 8 }

vRtrIfIpv6ForwardIpv4            OBJECT-TYPE
    SYNTAX      TruthValue
    MAX-ACCESS  read-create
    STATUS      current
    DESCRIPTION
        "The value of vRtrIfIpv6ForwardIpv4 specifies if the interface forwards
         unencapsulated IPv4 packets while IPv6 is enabled
         (vRtrIfIPv6ConfigAllowed) and the interface has no IPv4 address
         configured (vRtrIpAddrTable).

         This can be used in the context of IETF RFC5549 Advertising IPv4
         Network Layer Reachability Information with an IPv6 Next Hop.

         A value of 'true' is only allowed for an interface where the value of
         vRtrIfType is equal to 'network', 'serviceIes' or 'serviceVprn'."
    DEFVAL      { false }
    ::= { vRtrIfExtParmsEntry 9 }

vRtrIfAcctPolicyId               OBJECT-TYPE
    SYNTAX      Unsigned32 (0 | 1..99)
    MAX-ACCESS  read-create
    STATUS      current
    DESCRIPTION
        "The value of vRtrIfAcctPolicyId specifies the
         TIMETRA-LOG-MIB::tmnxLogApPolicyId that identifies the policy entry in
         TIMETRA-LOG-MIB::tmnxLogApTable which is associated with this router
         interface for the purpose of collecting physical layer router
         interface statistics.

         A zero value indicates that there is no accounting policy associated
         with this router interface."
    DEFVAL      { 0 }
    ::= { vRtrIfExtParmsEntry 10 }

vRtrIfCollectStats               OBJECT-TYPE
    SYNTAX      TruthValue
    MAX-ACCESS  read-create
    STATUS      current
    DESCRIPTION
        "The value of vRtrIfCollectStats specifies whether or not the
         collection of physical layer ethernet accounting and statistical data
         for the router interface is enabled.

         When a non-zero value is specified for vRtrIfAcctPolicyId and
         vRtrIfCollectStats is set to true, data will be collected in the
         appropriate records and written to the designated billing file.

         When a non-zero value is specified for vRtrIfAcctPolicyId and
         vRtrIfCollectStats is set to false, the statistics are still
         accumulated by the IOM cards; however, the CPM will not obtain the
         results and write them to the billing file."
    DEFVAL      { false }
    ::= { vRtrIfExtParmsEntry 11 }

vRtrIfUnidirectionalLinkDelay    OBJECT-TYPE
    SYNTAX      Integer32 (0 | 1..16777214)
    UNITS       "microseconds"
    MAX-ACCESS  read-create
    STATUS      current
    DESCRIPTION
        "The value of vRtrIfUnidirectionalLinkDelay specifies the average link
         delay in microseconds for this router interface.

         A value of 0 indicates that the delay is not specified for this router
         interface."
    DEFVAL      { 0 }
    ::= { vRtrIfExtParmsEntry 12 }

vRtrIfIngrDestinationClassLookup OBJECT-TYPE
    SYNTAX      TruthValue
    MAX-ACCESS  read-create
    STATUS      current
    DESCRIPTION
        "The value of vRtrIfIngrDestinationClassLookup specifies if traffic
         coming in through this interface can be filtered at the egress side
         based on the destination class.

         A value of 'true' is only allowed for an interface where the value of
         vRtrIfType is equal to 'network', 'serviceIes' or 'serviceVprn'."
    DEFVAL      { false }
    ::= { vRtrIfExtParmsEntry 13 }

vRtrIfIcmpTtlExpiredMatchingAddr OBJECT-TYPE
    SYNTAX      TruthValue
    MAX-ACCESS  read-create
    STATUS      current
    DESCRIPTION
        "When vRtrIfIcmpTtlExpiredMatchingAddr is set to 'true', the reply will
         use a matching subscriber interface IP address as source address.

         Value 'true' is allowed only for group interfaces and will be 'false'
         otherwise."
    DEFVAL      { false }
    ::= { vRtrIfExtParmsEntry 14 }

vRtrIfExtRefOcSubIfPresence      OBJECT-TYPE
    SYNTAX      TruthValue
    MAX-ACCESS  read-create
    STATUS      current
    DESCRIPTION
        "The value of vRtrIfExtRefOcSubIfPresence specifies the presence of a
         valid OC subinterface reference in vRtrIfExtRefOcSubIf."
    DEFVAL      { false }
    ::= { vRtrIfExtParmsEntry 15 }

vRtrIfExtRefOcSubIf              OBJECT-TYPE
    SYNTAX      Unsigned32
    MAX-ACCESS  read-create
    STATUS      current
    DESCRIPTION
        "The value of vRtrIfExtRefOcSubIf specifies the reference to the OC
         subinterface that allows to access the state in OC while  there is no
         configuration for this same OC subinterface."
    DEFVAL      { 0 }
    ::= { vRtrIfExtParmsEntry 16 }

vRtrIfMtuProfile                 OBJECT-TYPE
    SYNTAX      TruthValue
    MAX-ACCESS  read-create
    STATUS      current
    DESCRIPTION
        "The value of vRtrIfMtuProfile specifies that a HW profile must be
         allocated in order to enforce MTU checks and ICMP 'Packet too big'
         error reporting."
    DEFVAL      { false }
    ::= { vRtrIfExtParmsEntry 17 }

vRtrIfOperMtuProfile             OBJECT-TYPE
    SYNTAX      Unsigned32
    MAX-ACCESS  read-only
    STATUS      current
    DESCRIPTION
        "The value of vRtrIfOperMtuProfile indicates the operational HW MTU
         profile ID.

         When the interface is not of type IP tunnel, vRtrIfOperMtuProfile is
         only applicable when a port is bound to the interface and if either
         the port or the interface have MTU profile enabled.
         The value of vRtrIfOperMtuProfile could be inherited from the port in case
         the port has a smaller MTU value or in case only the port has MTU profile enabled,
         else it will be set to the value of vRtrIfAllocMtuProfile.

         When the interface is of type serviceIesIpTunnel or
         serviceVprnIpTunnel the value of vRtrIfOperMtuProfile will be set to
         the value of vRtrIfAllocMtuProfile.

         The MTU value that will be enforced with the MTU profile is the value
         of vRtrIfOperMtu."
    DEFVAL      { 0 }
    ::= { vRtrIfExtParmsEntry 18 }

vRtrIfAllocMtuProfile            OBJECT-TYPE
    SYNTAX      Unsigned32
    MAX-ACCESS  read-only
    STATUS      current
    DESCRIPTION
        "The value of vRtrIfAllocMtuProfile indicates the allocated HW MTU
         profile ID.

         When the interface is not of type IP tunnel a HW MTU profile ID is
         allocated when vRtrIfMtuProfile is enabled.

         When the interface is of type serviceIesIpTunnel or
         serviceVprnIpTunnel a HW MTU profile ID is allocated when an entry is
         created in the vRtrIfIpTunnelTable and when the encapsulated MTU is
         configured."
    DEFVAL      { 0 }
    ::= { vRtrIfExtParmsEntry 19 }

vRtrIfIpv6GreTermination         OBJECT-TYPE
    SYNTAX      TruthValue
    MAX-ACCESS  read-create
    STATUS      current
    DESCRIPTION
        "The vRtrIfIpv6GreTermination value specifies whether a user can
         terminate MPLS-over-GRE traffic on a primary IPv6 address (restricted
         to a /128 prefix) of a non-system loopback interface in the Base
         router. When set to true, this interface can terminate IPv6 GRE
         packets."
    DEFVAL      { false }
    ::= { vRtrIfExtParmsEntry 20 }

vRtrAdminTagsTable               OBJECT-TYPE
    SYNTAX      SEQUENCE OF VRtrAdminTagsEntry
    MAX-ACCESS  not-accessible
    STATUS      current
    DESCRIPTION
        "A nodal database table of admin-tags."
    ::= { tmnxVRtrObjs 133 }

vRtrAdminTagsEntry               OBJECT-TYPE
    SYNTAX      VRtrAdminTagsEntry
    MAX-ACCESS  not-accessible
    STATUS      current
    DESCRIPTION
        "An entry in the vRtrAdminTagsTable. Each entry represents an admin-tag
         ."
    INDEX       {
        vRtrID,
        vRtrAdminTag
    }
    ::= { vRtrAdminTagsTable 1 }

VRtrAdminTagsEntry               ::= SEQUENCE
{
    vRtrAdminTag                     TNamedItem,
    vRtrAdminTagsRowStatus           RowStatus
}

vRtrAdminTag                     OBJECT-TYPE
    SYNTAX      TNamedItem
    MAX-ACCESS  not-accessible
    STATUS      current
    DESCRIPTION
        "Index for the vRtrAdminTagsTable. The value of vRtrAdminTag specifies
         the admin-tag. Up to 256 admin-tags can be configured per system. An
         admin-tag is a max 32-character string"
    ::= { vRtrAdminTagsEntry 1 }

vRtrAdminTagsRowStatus           OBJECT-TYPE
    SYNTAX      RowStatus
    MAX-ACCESS  read-create
    STATUS      current
    DESCRIPTION
        "RowStatus for the vRtrAdminTagsTable."
    ::= { vRtrAdminTagsEntry 2 }

vRtrAdminTagsPolicyTable         OBJECT-TYPE
    SYNTAX      SEQUENCE OF VRtrAdminTagsPolicyEntry
    MAX-ACCESS  not-accessible
    STATUS      current
    DESCRIPTION
        "A nodal database table of route admin-tag policies."
    ::= { tmnxVRtrObjs 134 }

vRtrAdminTagsPolicyEntry         OBJECT-TYPE
    SYNTAX      VRtrAdminTagsPolicyEntry
    MAX-ACCESS  not-accessible
    STATUS      current
    DESCRIPTION
        "An entry in the vRtrAdminTagsPolicyTable. Each entry represents a
         policy."
    INDEX       {
        vRtrID,
        vRtrAdminTagPolicy
    }
    ::= { vRtrAdminTagsPolicyTable 1 }

VRtrAdminTagsPolicyEntry         ::= SEQUENCE
{
    vRtrAdminTagPolicy               TLPolicyNameOrExpOrEmpty,
    vRtrAdminTagsPolicyRowStatus     RowStatus
}

vRtrAdminTagPolicy               OBJECT-TYPE
    SYNTAX      TLPolicyNameOrExpOrEmpty
    MAX-ACCESS  not-accessible
    STATUS      current
    DESCRIPTION
        "Index for the vRtrAdminTagsPolicyTable. The value of
         vRtrAdminTagPolicy specifies the policy name. Up to 2k policies can be
         configured per system."
    ::= { vRtrAdminTagsPolicyEntry 1 }

vRtrAdminTagsPolicyRowStatus     OBJECT-TYPE
    SYNTAX      RowStatus
    MAX-ACCESS  read-create
    STATUS      current
    DESCRIPTION
        "RowStatus for the vRtrAdminTagsPolicyTable."
    ::= { vRtrAdminTagsPolicyEntry 2 }

vRtrAdminTagsPolicyIncludeTable  OBJECT-TYPE
    SYNTAX      SEQUENCE OF VRtrAdminTagsPolicyIncludeEntry
    MAX-ACCESS  not-accessible
    STATUS      current
    DESCRIPTION
        "A database table of included admin-tags for a policy."
    ::= { tmnxVRtrObjs 135 }

vRtrAdminTagsPolicyIncludeEntry  OBJECT-TYPE
    SYNTAX      VRtrAdminTagsPolicyIncludeEntry
    MAX-ACCESS  not-accessible
    STATUS      current
    DESCRIPTION
        "An entry in the vRtrAdminTagsPolicyIncludeTable. Each entry represents
         an admin-tag."
    INDEX       {
        vRtrID,
        vRtrAdminTagPolicy,
        vRtrIncludeAdminTag
    }
    ::= { vRtrAdminTagsPolicyIncludeTable 1 }

VRtrAdminTagsPolicyIncludeEntry  ::= SEQUENCE
{
    vRtrIncludeAdminTag              TNamedItem,
    vRtrATPolicyIncludeRowStatus     RowStatus
}

vRtrIncludeAdminTag              OBJECT-TYPE
    SYNTAX      TNamedItem
    MAX-ACCESS  not-accessible
    STATUS      current
    DESCRIPTION
        "The value of vRtrIncludeAdminTag specifies an admin-tag to be included
         when matching a route against an LSP."
    ::= { vRtrAdminTagsPolicyIncludeEntry 1 }

vRtrATPolicyIncludeRowStatus     OBJECT-TYPE
    SYNTAX      RowStatus
    MAX-ACCESS  read-create
    STATUS      current
    DESCRIPTION
        "RowStatus for the vRtrAdminTagsPolicyIncludeTable."
    ::= { vRtrAdminTagsPolicyIncludeEntry 2 }

vRtrAdminTagsPolicyExcludeTable  OBJECT-TYPE
    SYNTAX      SEQUENCE OF VRtrAdminTagsPolicyExcludeEntry
    MAX-ACCESS  not-accessible
    STATUS      current
    DESCRIPTION
        "A database table of excluded admin-tags for a policy."
    ::= { tmnxVRtrObjs 136 }

vRtrAdminTagsPolicyExcludeEntry  OBJECT-TYPE
    SYNTAX      VRtrAdminTagsPolicyExcludeEntry
    MAX-ACCESS  not-accessible
    STATUS      current
    DESCRIPTION
        "An entry in the vRtrAdminTagsPolicyExcludeTable. Each entry represents
         an admin-tag."
    INDEX       {
        vRtrID,
        vRtrAdminTagPolicy,
        vRtrExcludeAdminTag
    }
    ::= { vRtrAdminTagsPolicyExcludeTable 1 }

VRtrAdminTagsPolicyExcludeEntry  ::= SEQUENCE
{
    vRtrExcludeAdminTag              TNamedItem,
    vRtrATPolicyExcludeRowStatus     RowStatus
}

vRtrExcludeAdminTag              OBJECT-TYPE
    SYNTAX      TNamedItem
    MAX-ACCESS  not-accessible
    STATUS      current
    DESCRIPTION
        "The value of vRtrExcludeAdminTag specifies an admin-tag to be excluded
         when matching a route against an LSP."
    ::= { vRtrAdminTagsPolicyExcludeEntry 1 }

vRtrATPolicyExcludeRowStatus     OBJECT-TYPE
    SYNTAX      RowStatus
    MAX-ACCESS  read-create
    STATUS      current
    DESCRIPTION
        "RowStatus for the vRtrAdminTagsPolicyExcludeTable."
    ::= { vRtrAdminTagsPolicyExcludeEntry 2 }

vRtrInetExtTunnelTable           OBJECT-TYPE
    SYNTAX      SEQUENCE OF VRtrInetExtTunnelEntry
    MAX-ACCESS  not-accessible
    STATUS      current
    DESCRIPTION
        "vRtrInetExtTunnelTable maintains a list of tunnels for the specific
         router instance."
    ::= { tmnxVRtrObjs 137 }

vRtrInetExtTunnelEntry           OBJECT-TYPE
    SYNTAX      VRtrInetExtTunnelEntry
    MAX-ACCESS  not-accessible
    STATUS      current
    DESCRIPTION
        "vRtrInetExtTunnelEntry defines a tunnel to a particular destination in
         a specific router context."
    INDEX       {
        vRtrID,
        vRtrInetExtTunnelDestAddrType,
        vRtrInetExtTunnelDestAddr,
        vRtrInetExtTunnelDestPfxLen,
        vRtrInetExtTunnelListIndex,
        vRtrInetExtTunnelNhListIndex
    }
    ::= { vRtrInetExtTunnelTable 1 }

VRtrInetExtTunnelEntry           ::= SEQUENCE
{
    vRtrInetExtTunnelDestAddrType    InetAddressType,
    vRtrInetExtTunnelDestAddr        InetAddress,
    vRtrInetExtTunnelDestPfxLen      InetAddressPrefixLength,
    vRtrInetExtTunnelListIndex       Unsigned32,
    vRtrInetExtTunnelNhListIndex     Unsigned32,
    vRtrInetExtTunnelPreference      Unsigned32,
    vRtrInetExtTunnelType            TmnxTunnelTypeExt,
    vRtrInetExtTunnelTypeInstance    Unsigned32,
    vRtrInetExtTunnelID              TmnxTunnelID,
    vRtrInetExtTunnelNextHopAddrType InetAddressType,
    vRtrInetExtTunnelNextHopAddr     InetAddress,
    vRtrInetExtTunnelMetric          Unsigned32,
    vRtrInetExtTunnelAge             Integer32,
    vRtrInetExtTunnelNextHopFlags    INTEGER,
    vRtrInetExtTunnelLspBandwidth    Counter64,
    vRtrInetExtTunnelMTU             Unsigned32,
    vRtrInetExtTunnelLspWeight       Unsigned32,
    vRtrInetExtTunnelLspId           Unsigned32,
    vRtrInetExtTunnelFlags           BITS,
    vRtrInetExtTunnelRelativeMetric  Integer32,
    vRtrInetExtTunnelLabel           Integer32,
    vRtrInetExtTunnelBypassLabel     Integer32,
    vRtrInetExtTunnelLspFC           TmnxCBFClasses,
    vRtrInetExtTunnelMaxLabels       Integer32,
    vRtrInetExtTunnelNhTunnelId      TmnxTunnelID,
    vRtrInetExtTunnelNhTunnelType    TmnxTunnelTypeExt,
    vRtrInetExtTunnelNhTunnelInst    Unsigned32,
    vRtrInetExtTunnelColor           Unsigned32,
    vRtrInetExtTunnelNhWeight        Unsigned32,
    vRtrInetExtTunnelNhBitFlags      BITS,
    vRtrInetExtTunnelNhGroupId       Unsigned32,
    vRtrInetExtTunnelAlgorithm       TmnxAlgorithmId,
    vRtrInetExtTunnelSidAddrType     InetAddressType,
    vRtrInetExtTunnelSidAddr         InetAddress
}

vRtrInetExtTunnelDestAddrType    OBJECT-TYPE
    SYNTAX      InetAddressType
    MAX-ACCESS  not-accessible
    STATUS      current
    DESCRIPTION
        "The value of vRtrInetExtTunnelDestAddrType indicates the address type
         of vRtrInetExtTunnelDestAddr."
    ::= { vRtrInetExtTunnelEntry 1 }

vRtrInetExtTunnelDestAddr        OBJECT-TYPE
    SYNTAX      InetAddress (SIZE (0|4|16))
    MAX-ACCESS  not-accessible
    STATUS      current
    DESCRIPTION
        "The value of vRtrInetExtTunnelDestAddr maintains the destination IP address
         of this tunnel. This object may not take a Multicast (Class  D) address
         value.

         Any assignment (implicit or otherwise) of an instance of this object
         to a value x must be rejected if the bitwise logical-AND of x with the
         value of mask representing the corresponding instance of the
         vRtrInetExtTunnelDestPfxLen object is not equal to x."
    ::= { vRtrInetExtTunnelEntry 2 }

vRtrInetExtTunnelDestPfxLen      OBJECT-TYPE
    SYNTAX      InetAddressPrefixLength
    MAX-ACCESS  not-accessible
    STATUS      current
    DESCRIPTION
        "The value of vRtrInetExtTunnelDestPfxLen indicates the mask length for
         vRtrInetExtTunnelDestAddr. For those systems that do not support
         arbitrary subnet masks, an agent constructs the value of the
         vRtrInetExtTunnelDestPfxLen by reference to the IP Address Class.

         Any assignment (implicit or otherwise) of an instance of this object
         to a value x must be rejected if the bitwise logical-AND of the mask
         representing x with the value of the corresponding instance of
         vRtrInetExtTunnelDestAddr is not equal to vRtrInetExtTunnelDestAddr."
    ::= { vRtrInetExtTunnelEntry 3 }

vRtrInetExtTunnelListIndex       OBJECT-TYPE
    SYNTAX      Unsigned32
    MAX-ACCESS  not-accessible
    STATUS      current
    DESCRIPTION
        "The value of vRtrInetExtTunnelListIndex is the index of the next
         tunnel available to the destination"
    ::= { vRtrInetExtTunnelEntry 4 }

vRtrInetExtTunnelNhListIndex     OBJECT-TYPE
    SYNTAX      Unsigned32
    MAX-ACCESS  not-accessible
    STATUS      current
    DESCRIPTION
        "The value of vRtrInetExtTunnelNhListIndex is the index of the next
         next-hop that the tunnel destination is ECMP'ed across."
    ::= { vRtrInetExtTunnelEntry 5 }

vRtrInetExtTunnelPreference      OBJECT-TYPE
    SYNTAX      Unsigned32 (0..255)
    MAX-ACCESS  read-only
    STATUS      current
    DESCRIPTION
        "The value of vRtrInetExtTunnelPreference determines the priority of
         this tunnel versus the other tunnels from different sources such as
         LDP, RSVP, GRE etc. This is an absolute number used internally by the
         system to specify preferences for the tunnel.

         Lowest number signifies the most preferred entry in the table."
    ::= { vRtrInetExtTunnelEntry 6 }

vRtrInetExtTunnelType            OBJECT-TYPE
    SYNTAX      TmnxTunnelTypeExt
    MAX-ACCESS  read-only
    STATUS      current
    DESCRIPTION
        "The value of vRtrInetExtTunnelType indicates the type of this tunnel
         entity."
    ::= { vRtrInetExtTunnelEntry 7 }

vRtrInetExtTunnelTypeInstance    OBJECT-TYPE
    SYNTAX      Unsigned32
    MAX-ACCESS  read-only
    STATUS      current
    DESCRIPTION
        "The value of vRtrInetExtTunnelTypeInstance indicates an instance of
         the tunnel of the type indicated by vRtrInetExtTunnelType."
    ::= { vRtrInetExtTunnelEntry 8 }

vRtrInetExtTunnelID              OBJECT-TYPE
    SYNTAX      TmnxTunnelID
    MAX-ACCESS  read-only
    STATUS      current
    DESCRIPTION
        "The value of vRtrInetExtTunnelID is a global value and represents a
         particular tunnel type like an MPLS type tunnel or an SDP."
    ::= { vRtrInetExtTunnelEntry 9 }

vRtrInetExtTunnelNextHopAddrType OBJECT-TYPE
    SYNTAX      InetAddressType
    MAX-ACCESS  read-only
    STATUS      current
    DESCRIPTION
        "The value of vRtrInetExtTunnelNextHopAddrType indicates the address
         type of vRtrInetExtTunnelNextHopAddr."
    ::= { vRtrInetExtTunnelEntry 10 }

vRtrInetExtTunnelNextHopAddr     OBJECT-TYPE
    SYNTAX      InetAddress (SIZE (0|4|16|20))
    MAX-ACCESS  read-only
    STATUS      current
    DESCRIPTION
        "The value of vRtrInetExtTunnelNextHopAddr indicates the address of the
         next system en route."
    ::= { vRtrInetExtTunnelEntry 11 }

vRtrInetExtTunnelMetric          OBJECT-TYPE
    SYNTAX      Unsigned32
    MAX-ACCESS  read-only
    STATUS      current
    DESCRIPTION
        "The value of vRtrInetExtTunnelMetric indicates the metric of the
         tunnel. This is used in addition to the preference for this tunnel."
    ::= { vRtrInetExtTunnelEntry 12 }

vRtrInetExtTunnelAge             OBJECT-TYPE
    SYNTAX      Integer32
    MAX-ACCESS  read-only
    STATUS      current
    DESCRIPTION
        "The value of vRtrInetExtTunnelAge indicates the number of seconds
         since this tunnel entry was last updated or otherwise determined to be
         correct. No semantics of 'too old' can be implied except through
         knowledge of owner of the tunnel."
    ::= { vRtrInetExtTunnelEntry 13 }

vRtrInetExtTunnelNextHopFlags    OBJECT-TYPE
    SYNTAX      INTEGER {
        none          (0),
        hasLfa        (1),
        hasBackup     (2),
        isBackup      (3),
        isBgpInactive (4),
        isLfa         (5)
    }
    MAX-ACCESS  read-only
    STATUS      current
    DESCRIPTION
        "The value of vRtrInetExtTunnelNextHopFlags indicates the properties of
         the tunnel next hop.

         A value of 'none' indicates that no next-hop flags are present.

         A value of 'hasLfa' indicates that an LFA next-hop is present in
         addition to the regular next-hop.

         A value of 'hasBackup' indicates that this route has a backup route.

         A value of 'isBackup' indicates that this route is a backup route to
         another route with the same prefix.

         A value of 'isBgpInactive' indicates that this route is an inactive
         best-external route exported from BGP.

         A value of 'isLfa' indicates that this next-hop is a LFA hop."
    ::= { vRtrInetExtTunnelEntry 14 }

vRtrInetExtTunnelLspBandwidth    OBJECT-TYPE
    SYNTAX      Counter64
    UNITS       "mega-bits per second"
    MAX-ACCESS  read-only
    STATUS      current
    DESCRIPTION
        "The value of vRtrInetExtTunnelLspBandwidth indicates the reserved
         bandwidth that is available in the LSP.

         When the value of the object is set to zero then it indicates that
         there is no reserved bandwidth in this tunnel"
    ::= { vRtrInetExtTunnelEntry 15 }

vRtrInetExtTunnelMTU             OBJECT-TYPE
    SYNTAX      Unsigned32
    MAX-ACCESS  read-only
    STATUS      current
    DESCRIPTION
        "The value of vRtrInetExtTunnelMTU indicates the MTU value for the
         tunnel."
    ::= { vRtrInetExtTunnelEntry 16 }

vRtrInetExtTunnelLspWeight       OBJECT-TYPE
    SYNTAX      Unsigned32
    MAX-ACCESS  read-only
    STATUS      current
    DESCRIPTION
        "The value of vRtrInetExtTunnelLspWeight indicates the load balancing
         weight applicable to the LSP."
    ::= { vRtrInetExtTunnelEntry 17 }

vRtrInetExtTunnelLspId           OBJECT-TYPE
    SYNTAX      Unsigned32
    MAX-ACCESS  read-only
    STATUS      current
    DESCRIPTION
        "The value of vRtrInetExtTunnelLspId indicates an instance/epoch
         identifier associated with a RSVP tunnel."
    ::= { vRtrInetExtTunnelEntry 18 }

vRtrInetExtTunnelFlags           OBJECT-TYPE
    SYNTAX      BITS {
        isOverTunnel               (0),
        useRelativeMetric          (1),
        autoLSP                    (2),
        hasLFA                     (3),
        excludeForLdpOverRsvp      (4),
        excludeForL3VPN            (5),
        excludeForBGPShortcuts     (6),
        excludeForBGPLabeledRoutes (7),
        excludeForLFA              (8),
        excludeForIGPShortcuts     (9),
        entropyLabelCapable        (10),
        isAdjacencyTunnel          (11),
        lspBfdDown                 (12),
        hasColor                   (13),
        preferTransportFRR         (14),
        allowSrOverSrTe            (15),
        encryptedTunnel            (16)
    }
    MAX-ACCESS  read-only
    STATUS      current
    DESCRIPTION
        "The value of vRtrInetExtTunnelFlags indicates the following -:

         If value of 'isOverTunnel' is set, it indicates that this tunnel is
         over another tunnel.

         A value of 'useRelativeMetric' indicates to use the relative metric
         info to offset IGP path cost to tunnel destination instead of absolute
         tunnel metric.

         A value of 'autoLSP' indicates if the LSP is an automatic LSP.

         If value of 'hasLFA' is set, then this tunnel next-hop has a loop-free
         alternate hop.

         If value of 'excludeForLdpOverRsvp' is set (applicable to RSVP tunnel
         only), then the MPLS LSP is not allowed to be used for LDP over RSVP.

         If value of 'excludeForL3VPN' is set, it indicates not to use this
         tunnel for L3 VPNs.

         If value of 'excludeForBGPShortcuts' is set, it indicates not to use
         this tunnel for BGP shortcuts.

         If value of 'excludeForBGPLabeledRoutes' is set, it indicates not to
         use this tunnel for BGP labeled routes.

         If value of 'excludeForLFA' is set, it indicates not to use this
         tunnel for loop-free alternate.

         If value of 'excludeForIGPShortcuts' is set, it indicates not to use
         this tunnel for IGP shortcuts.

         If value of 'entropyLabelCapable' is set, it indicates this tunnel is
         entropy capable.

         If value of 'isAdjacencyTunnel' is set, it indicates that this tunnel
         is a segment routing adjacency tunnel.

         If value of 'lspBfdDown' is set, it indicates that BFD is down on this
         tunnel/FEC and that it will not be used as a transport tunnel. If this
         value is not set, then LSP-BFD is not configured on the tunnel/FEC, or
         LSP-BFD is configured and the BFD state is up.

         If value of 'hasColor' is set, it indicates that this tunnel has
         color.

         If value of 'preferTransportFRR' is set, it indicates that for this
         tunnel, if it is over another transport tunnel, the underlying
         transport tunnel's FRR is deferred to if that tunnel is in FRR.

         If value of 'allowSrOverSrTe' is set, it indicates that SR over SR-TE
         is allowed for this tunnel.

         If value of 'encryptedTunnel' is set, it indicates that this tunnel is
         encrypted."
    ::= { vRtrInetExtTunnelEntry 19 }

vRtrInetExtTunnelRelativeMetric  OBJECT-TYPE
    SYNTAX      Integer32
    MAX-ACCESS  read-only
    STATUS      current
    DESCRIPTION
        "The value of vRtrInetExtTunnelRelativeMetric indicates the metric
         offset to IGP cost to tunnel destination. This value is applicable
         only if 'useRelativeMetric' bit is set for the object
         vRtrInetExtTunnelFlags."
    ::= { vRtrInetExtTunnelEntry 20 }

vRtrInetExtTunnelLabel           OBJECT-TYPE
    SYNTAX      Integer32
    MAX-ACCESS  read-only
    STATUS      current
    DESCRIPTION
        "The value of vRtrInetExtTunnelLabel indicates the label corresponding
         to tunnel of type LDP/MPLS."
    ::= { vRtrInetExtTunnelEntry 21 }

vRtrInetExtTunnelBypassLabel     OBJECT-TYPE
    SYNTAX      Integer32
    MAX-ACCESS  read-only
    STATUS      current
    DESCRIPTION
        "The value of vRtrInetExtTunnelBypassLabel indicates the MPLS bypass
         tunnel label."
    ::= { vRtrInetExtTunnelEntry 22 }

vRtrInetExtTunnelLspFC           OBJECT-TYPE
    SYNTAX      TmnxCBFClasses
    MAX-ACCESS  read-only
    STATUS      current
    DESCRIPTION
        "The value of vRtrInetExtTunnelLspFC indicates a set of forwarding
         classes configured for this LSP expressed as a bit map. If a bit from
         0 through 7 is set, then the corresponding forwarding class has been
         configured for this LSP. If bit 8 is set, the LSP has been designated
         as the default forwarding LSP.

         If no bits are set, then Class-based forwarding is not enabled for
         this LSP."
    ::= { vRtrInetExtTunnelEntry 23 }

vRtrInetExtTunnelMaxLabels       OBJECT-TYPE
    SYNTAX      Integer32
    MAX-ACCESS  read-only
    STATUS      current
    DESCRIPTION
        "The value of vRtrInetExtTunnelMaxLabels is the sum of the maximum
         number of labels that will be used by this tunnel and all underlying
         tunnels."
    ::= { vRtrInetExtTunnelEntry 24 }

vRtrInetExtTunnelNhTunnelId      OBJECT-TYPE
    SYNTAX      TmnxTunnelID
    MAX-ACCESS  read-only
    STATUS      current
    DESCRIPTION
        "The value of vRtrInetExtTunnelNhTunnelId indicates the value of the
         tunnel ID of the underlying tunnel when the value of
         vRtrInetExtTunnelFlags has 'isOverTunnel' set, otherwise the value is
         0."
    ::= { vRtrInetExtTunnelEntry 25 }

vRtrInetExtTunnelNhTunnelType    OBJECT-TYPE
    SYNTAX      TmnxTunnelTypeExt
    MAX-ACCESS  read-only
    STATUS      current
    DESCRIPTION
        "The value of vRtrInetExtTunnelNhTunnelType indicates the type of
         underlying tunnel when the value of vRtrInetExtTunnelFlags has
         'isOverTunnel' set.

         If the value of vRtrInetExtTunnelFlags does not have 'isOverTunnel'
         set, the value of vRtrInetExtTunnelType is invalid."
    ::= { vRtrInetExtTunnelEntry 26 }

vRtrInetExtTunnelNhTunnelInst    OBJECT-TYPE
    SYNTAX      Unsigned32
    MAX-ACCESS  read-only
    STATUS      current
    DESCRIPTION
        "The value of vRtrInetExtTunnelNhTunnelInst indicates the instance of
         the underlying tunnel type indicated by vRtrInetExtTunnelNhTunnelType.

         If the value of vRtrInetExtTunnelFlags does not have 'isOverTunnel'
         set, the value of vRtrInetExtTunnelNhTunnelInst is set to 0."
    ::= { vRtrInetExtTunnelEntry 27 }

vRtrInetExtTunnelColor           OBJECT-TYPE
    SYNTAX      Unsigned32
    MAX-ACCESS  read-only
    STATUS      current
    DESCRIPTION
        "The value of vRtrInetExtTunnelColor indicates the color associated
         with the tunnel and is valid only if the 'hasColor' flag is set in
         vRtrInetExtTunnelFlags."
    ::= { vRtrInetExtTunnelEntry 28 }

vRtrInetExtTunnelNhWeight        OBJECT-TYPE
    SYNTAX      Unsigned32
    MAX-ACCESS  read-only
    STATUS      current
    DESCRIPTION
        "The value of vRtrInetExtTunnelNhWeight indicates the weight associated
         with this tunnel next-hop. It is 0 if no weight was associated with
         this next-hop."
    ::= { vRtrInetExtTunnelEntry 29 }

vRtrInetExtTunnelNhBitFlags      OBJECT-TYPE
    SYNTAX      BITS {
        hasGroupId (0),
        isInactive (1),
        isBackup   (2)
    }
    MAX-ACCESS  read-only
    STATUS      current
    DESCRIPTION
        "The value of vRtrInetExtTunnelNhBitFlags provides additional
         information about the next hop.

         If 'hasGroupId' is set, it indicates that the
         vRtrInetExtTunnelNhGroupId object has valid information.

         If 'isInactive' is set, it indicates that this next hop is inactive.

         If 'isBackup' is set, it indicates that this route is a backup next
         hop to another next hop with the same next-hop group ID."
    ::= { vRtrInetExtTunnelEntry 30 }

vRtrInetExtTunnelNhGroupId       OBJECT-TYPE
    SYNTAX      Unsigned32
    MAX-ACCESS  read-only
    STATUS      current
    DESCRIPTION
        "The value of vRtrInetExtTunnelNhGroupId indicates the group this next
         hop belongs to. This is valid only if the vRtrInetExtTunnelNhBitFlags
         has the 'hasGroupId' flag set. This next-hop group ID is available
         only for some next hops that have a backup next hop as part of a
         group. At any time only one next hop in the group is active. The
         inactive next hops are flagged with the 'isInactive' flag in the
         vRtrInetExtTunnelNhBitFlags object. The backup next hop is flagged
         with the 'isBackup' flag in the vRtrInetExtTunnelNhBitFlags object."
    ::= { vRtrInetExtTunnelEntry 31 }

vRtrInetExtTunnelAlgorithm       OBJECT-TYPE
    SYNTAX      TmnxAlgorithmId
    MAX-ACCESS  read-only
    STATUS      current
    DESCRIPTION
        "The value of vRtrInetExtTunnelAlgorithm is the identifier of the
         algorithm instance that the tunnel belongs."
    ::= { vRtrInetExtTunnelEntry 32 }

vRtrInetExtTunnelSidAddrType     OBJECT-TYPE
    SYNTAX      InetAddressType
    MAX-ACCESS  read-only
    STATUS      current
    DESCRIPTION
        "The value of vRtrInetExtTunnelSidAddrType indicates the address type
         of vRtrInetExtTunnelSidAddr."
    ::= { vRtrInetExtTunnelEntry 33 }

vRtrInetExtTunnelSidAddr         OBJECT-TYPE
    SYNTAX      InetAddress (SIZE (0|16))
    MAX-ACCESS  read-only
    STATUS      current
    DESCRIPTION
        "The value of vRtrInetExtTunnelSidAddr indicates the address of the SID
         on this tunnel."
    ::= { vRtrInetExtTunnelEntry 34 }

vRtrLeakExportPolicyTable        OBJECT-TYPE
    SYNTAX      SEQUENCE OF VRtrLeakExportPolicyEntry
    MAX-ACCESS  not-accessible
    STATUS      current
    DESCRIPTION
        "The vRtrLeakExportPolicyTable has an entry only for the base router
         instance in the system."
    ::= { tmnxVRtrObjs 138 }

vRtrLeakExportPolicyEntry        OBJECT-TYPE
    SYNTAX      VRtrLeakExportPolicyEntry
    MAX-ACCESS  not-accessible
    STATUS      current
    DESCRIPTION
        "Each row represents the set of policies that are applied to the routes
         from the base instance to create a set of routes that are eligible to
         be leaked to other router instances and limit on the number of such
         routes."
    INDEX       { vRtrID }
    ::= { vRtrLeakExportPolicyTable 1 }

VRtrLeakExportPolicyEntry        ::= SEQUENCE
{
    vRtrLeakExportPolicy1            TXLPolicyNameOrExpOrEmpty,
    vRtrLeakExportPolicy2            TLPolicyNameOrExpOrEmpty,
    vRtrLeakExportPolicy3            TLPolicyNameOrExpOrEmpty,
    vRtrLeakExportPolicy4            TLPolicyNameOrExpOrEmpty,
    vRtrLeakExportPolicy5            TLPolicyNameOrExpOrEmpty,
    vRtrLeakExportLimit              Unsigned32
}

vRtrLeakExportPolicy1            OBJECT-TYPE
    SYNTAX      TXLPolicyNameOrExpOrEmpty
    MAX-ACCESS  read-create
    STATUS      current
    DESCRIPTION
        "The value of vRtrLeakExportPolicy1 specifies the name of the first
         policy that will be applied to the routes to create a set of routes
         that are eligible for leaking to other router instances.

         A value of ''H indicates that the vRtrLeakExportPolicy1 has not been
         set."
    DEFVAL      { ''H }
    ::= { vRtrLeakExportPolicyEntry 1 }

vRtrLeakExportPolicy2            OBJECT-TYPE
    SYNTAX      TLPolicyNameOrExpOrEmpty
    MAX-ACCESS  read-create
    STATUS      current
    DESCRIPTION
        "The value of vRtrLeakExportPolicy2 specifies the name of the second
         policy that will be applied to the routes to create a set of routes
         that are eligible for leaking to other router instances.

         A value of ''H indicates that the vRtrLeakExportPolicy2 has not been
         set.

         It is required to configure vRtrLeakExportPolicy1 before configuring
         vRtrLeakExportPolicy2."
    DEFVAL      { ''H }
    ::= { vRtrLeakExportPolicyEntry 2 }

vRtrLeakExportPolicy3            OBJECT-TYPE
    SYNTAX      TLPolicyNameOrExpOrEmpty
    MAX-ACCESS  read-create
    STATUS      current
    DESCRIPTION
        "The value of vRtrLeakExportPolicy3 specifies the name of the third
         policy that will be applied to the routes to create a set of routes
         that are eligible for leaking to other router instances.

         A value of ''H indicates that the vRtrLeakExportPolicy3 has not been
         set.

         It is required to configure vRtrLeakExportPolicy2 before configuring
         vRtrLeakExportPolicy3."
    DEFVAL      { ''H }
    ::= { vRtrLeakExportPolicyEntry 3 }

vRtrLeakExportPolicy4            OBJECT-TYPE
    SYNTAX      TLPolicyNameOrExpOrEmpty
    MAX-ACCESS  read-create
    STATUS      current
    DESCRIPTION
        "The value of vRtrLeakExportPolicy4 specifies the name of the fourth
         policy that will be applied to the routes to create a set of routes
         that are eligible for leaking to other router instances.

         A value of ''H indicates that the vRtrLeakExportPolicy4 has not been
         set.

         It is required to configure vRtrLeakExportPolicy3 before configuring
         vRtrLeakExportPolicy4."
    DEFVAL      { ''H }
    ::= { vRtrLeakExportPolicyEntry 4 }

vRtrLeakExportPolicy5            OBJECT-TYPE
    SYNTAX      TLPolicyNameOrExpOrEmpty
    MAX-ACCESS  read-create
    STATUS      current
    DESCRIPTION
        "The value of vRtrLeakExportPolicy5 specifies the name of the fifth
         policy that will be applied to the routes to create a set of routes
         that are eligible for leaking to other router instances.

         A value of ''H indicates that the vRtrLeakExportPolicy5 has not been
         set.

         It is required to configure vRtrLeakExportPolicy4 before configuring
         vRtrLeakExportPolicy5."
    DEFVAL      { ''H }
    ::= { vRtrLeakExportPolicyEntry 5 }

vRtrLeakExportLimit              OBJECT-TYPE
    SYNTAX      Unsigned32 (1..10000)
    MAX-ACCESS  read-create
    STATUS      current
    DESCRIPTION
        "The value of vRtrLeakExportLimit specifies the  limit on the number of routes
         that are filtered by the leak-export configuration."
    DEFVAL      { 5 }
    ::= { vRtrLeakExportPolicyEntry 6 }

vRtrRibApiMplsTable              OBJECT-TYPE
    SYNTAX      SEQUENCE OF VRtrRibApiMplsEntry
    MAX-ACCESS  not-accessible
    STATUS      current
    DESCRIPTION
        "The vRtrRibApiMplsTable has an entry for each RIB-API MPLS configured
         under each virtual router in the system."
    ::= { tmnxVRtrObjs 139 }

vRtrRibApiMplsEntry              OBJECT-TYPE
    SYNTAX      VRtrRibApiMplsEntry
    MAX-ACCESS  not-accessible
    STATUS      current
    DESCRIPTION
        "Each row entry represents information about RIB-API MPLS for a virtual
         router in the system.

         Entries cannot be created and deleted via SNMP SET operations."
    INDEX       { vRtrID }
    ::= { vRtrRibApiMplsTable 1 }

VRtrRibApiMplsEntry              ::= SEQUENCE
{
    vRtrRibApiMplsLastChanged        TimeStamp,
    vRtrRibApiMplsAdminState         TmnxAdminState,
    vRtrRibApiMplsReservedLblBlk     TLNamedItemOrEmpty
}

vRtrRibApiMplsLastChanged        OBJECT-TYPE
    SYNTAX      TimeStamp
    MAX-ACCESS  read-only
    STATUS      current
    DESCRIPTION
        "The vRtrRibApiMplsLastChanged indicates the sysUpTime at the time of
         last change to this row."
    ::= { vRtrRibApiMplsEntry 1 }

vRtrRibApiMplsAdminState         OBJECT-TYPE
    SYNTAX      TmnxAdminState
    MAX-ACCESS  read-write
    STATUS      current
    DESCRIPTION
        "The vRtrRibApiMplsAdminState specifies the desired administrative
         state of RIB-API MPLS for this virtual router."
    DEFVAL      { outOfService }
    ::= { vRtrRibApiMplsEntry 2 }

vRtrRibApiMplsReservedLblBlk     OBJECT-TYPE
    SYNTAX      TLNamedItemOrEmpty
    MAX-ACCESS  read-write
    STATUS      current
    DESCRIPTION
        "The vRtrRibApiMplsReservedLblBlk specifies the reserved label block
         used."
    DEFVAL      { "" }
    ::= { vRtrRibApiMplsEntry 3 }

tmnxVRtrNeInfoTable              OBJECT-TYPE
    SYNTAX      SEQUENCE OF TmnxVRtrNeInfoEntry
    MAX-ACCESS  not-accessible
    STATUS      current
    DESCRIPTION
        "The tmnxVRtrNeInfoTable contains Network Element (NE) information.

         Conceptual rows in this table are created and destroyed automatically
         by the system."
    ::= { tmnxVRtrObjs 140 }

tmnxVRtrNeInfoEntry              OBJECT-TYPE
    SYNTAX      TmnxVRtrNeInfoEntry
    MAX-ACCESS  not-accessible
    STATUS      current
    DESCRIPTION
        "Each row entry represents the Network Element information for a
         specific NE ID in a virtual router instance."
    INDEX       {
        vRtrID,
        tmnxVRtrNeInfoNeid
    }
    ::= { tmnxVRtrNeInfoTable 1 }

TmnxVRtrNeInfoEntry              ::= SEQUENCE
{
    tmnxVRtrNeInfoNeid               TmnxVrtrNeid,
    tmnxVRtrNeInfoNeidHex            TmnxVrtrNeid,
    tmnxVRtrNeInfoNeipV4Type         InetAddressType,
    tmnxVRtrNeInfoNeipV4             InetAddress,
    tmnxVRtrNeInfoNeipV4PrefixLen    InetAddressPrefixLength,
    tmnxVRtrNeInfoNeipV6Type         InetAddressType,
    tmnxVRtrNeInfoNeipV6             InetAddress,
    tmnxVRtrNeInfoNeipV6PrefixLen    InetAddressPrefixLength,
    tmnxVRtrNeInfoSystemMac          MacAddress,
    tmnxVRtrNeInfoPlatformType       DisplayString,
    tmnxVRtrNeInfoVendorId           DisplayString
}

tmnxVRtrNeInfoNeid               OBJECT-TYPE
    SYNTAX      TmnxVrtrNeid
    MAX-ACCESS  not-accessible
    STATUS      current
    DESCRIPTION
        "The value of tmnxVRtrNeInfoNeid specifies the Network Element
         Identifier.

         The total valid length is 24 bit; the first 8 high-order bits indicate
         the subnet ID and the 16 low-order bits indicate the basic ID.

         The neid valid value ranges from 0x00010001 to 0x00FEFFFE."
    ::= { tmnxVRtrNeInfoEntry 1 }

tmnxVRtrNeInfoNeidHex            OBJECT-TYPE
    SYNTAX      TmnxVrtrNeid
    MAX-ACCESS  read-only
    STATUS      current
    DESCRIPTION
        "The value of tmnxVRtrNeInfoNeidHex indicates the Network Element
         Identifier in Hex format.

         The total valid length is 24 bit; the first 8 high-order bits indicate
         the subnet ID and the 16 low-order bits indicate the basic ID.

         The neid valid value ranges from 0x00010001 to 0x00FEFFFE."
    ::= { tmnxVRtrNeInfoEntry 2 }

tmnxVRtrNeInfoNeipV4Type         OBJECT-TYPE
    SYNTAX      InetAddressType
    MAX-ACCESS  read-only
    STATUS      current
    DESCRIPTION
        "The value of tmnxVRtrNeInfoNeipV4Type indicates the IP address type of
         tmnxVRtrNeInfoNeipV4."
    ::= { tmnxVRtrNeInfoEntry 3 }

tmnxVRtrNeInfoNeipV4             OBJECT-TYPE
    SYNTAX      InetAddress (SIZE (0|4))
    MAX-ACCESS  read-only
    STATUS      current
    DESCRIPTION
        "The value of tmnxVRtrNeInfoNeipV4 indicates the IPv4 address  of the
         Network Element."
    ::= { tmnxVRtrNeInfoEntry 4 }

tmnxVRtrNeInfoNeipV4PrefixLen    OBJECT-TYPE
    SYNTAX      InetAddressPrefixLength
    MAX-ACCESS  read-only
    STATUS      current
    DESCRIPTION
        "The value of tmnxVRtrNeInfoNeipV4PrefixLen indicates the length of the
         IP netmask for tmnxVRtrNeInfoNeipV4."
    ::= { tmnxVRtrNeInfoEntry 5 }

tmnxVRtrNeInfoNeipV6Type         OBJECT-TYPE
    SYNTAX      InetAddressType
    MAX-ACCESS  read-only
    STATUS      current
    DESCRIPTION
        "The value of tmnxVRtrNeInfoNeipV6Type indicates the IP address type of
         tmnxVRtrNeInfoNeipV6."
    ::= { tmnxVRtrNeInfoEntry 6 }

tmnxVRtrNeInfoNeipV6             OBJECT-TYPE
    SYNTAX      InetAddress (SIZE (0|16))
    MAX-ACCESS  read-only
    STATUS      current
    DESCRIPTION
        "The value of tmnxVRtrNeInfoNeipV6 indicates the IPv6 address of the
         Network Element."
    ::= { tmnxVRtrNeInfoEntry 7 }

tmnxVRtrNeInfoNeipV6PrefixLen    OBJECT-TYPE
    SYNTAX      InetAddressPrefixLength
    MAX-ACCESS  read-only
    STATUS      current
    DESCRIPTION
        "The value of tmnxVRtrNeInfoNeipV6PrefixLen indicates the length of the
         IP netmask for tmnxVRtrNeInfoNeipV6."
    ::= { tmnxVRtrNeInfoEntry 8 }

tmnxVRtrNeInfoSystemMac          OBJECT-TYPE
    SYNTAX      MacAddress
    MAX-ACCESS  read-only
    STATUS      current
    DESCRIPTION
        "The value of tmnxVRtrNeInfoSystemMac indicates the system MAC address
         of the node."
    ::= { tmnxVRtrNeInfoEntry 9 }

tmnxVRtrNeInfoPlatformType       OBJECT-TYPE
    SYNTAX      DisplayString
    MAX-ACCESS  read-only
    STATUS      current
    DESCRIPTION
        "The value of tmnxVRtrNeInfoPlatformType indicates the product
         identifier."
    ::= { tmnxVRtrNeInfoEntry 10 }

tmnxVRtrNeInfoVendorId           OBJECT-TYPE
    SYNTAX      DisplayString
    MAX-ACCESS  read-only
    STATUS      current
    DESCRIPTION
        "The value of tmnxVRtrNeInfoVendorId indicates the vendor identifier."
    ::= { tmnxVRtrNeInfoEntry 11 }

vRtrIfDHCPOSelSrvrTable          OBJECT-TYPE
    SYNTAX      SEQUENCE OF VRtrIfDHCPOSelSrvrEntry
    MAX-ACCESS  not-accessible
    STATUS      current
    DESCRIPTION
        "The vRtrIfDHCPOSelSrvrTable is used to configure the interface
         parameters related to DHCP Offer Selection for a specific server."
    ::= { tmnxVRtrObjs 141 }

vRtrIfDHCPOSelSrvrEntry          OBJECT-TYPE
    SYNTAX      VRtrIfDHCPOSelSrvrEntry
    MAX-ACCESS  not-accessible
    STATUS      current
    DESCRIPTION
        "Each row entry represents information related to DHCP for a virtual
         router interface in the system."
    INDEX       {
        vRtrID,
        vRtrIfIndex,
        vRtrIfDHCPOSelSrvrAddressType,
        vRtrIfDHCPOSelSrvrAddress
    }
    ::= { vRtrIfDHCPOSelSrvrTable 1 }

VRtrIfDHCPOSelSrvrEntry          ::= SEQUENCE
{
    vRtrIfDHCPOSelSrvrAddressType    InetAddressType,
    vRtrIfDHCPOSelSrvrAddress        InetAddress,
    vRtrIfDHCPOSelSrvrRowStatus      RowStatus,
    vRtrIfDHCPOSelSrvrDiscoDly       Integer32
}

vRtrIfDHCPOSelSrvrAddressType    OBJECT-TYPE
    SYNTAX      InetAddressType
    MAX-ACCESS  not-accessible
    STATUS      current
    DESCRIPTION
        "The value of vRtrIfDHCPOSelSrvrAddressType indicates the type of IP
         address of vRtrIfDHCPOSelSrvrAddress."
    ::= { vRtrIfDHCPOSelSrvrEntry 1 }

vRtrIfDHCPOSelSrvrAddress        OBJECT-TYPE
    SYNTAX      InetAddress (SIZE (0|4))
    MAX-ACCESS  not-accessible
    STATUS      current
    DESCRIPTION
        "The value of vRtrIfDHCPOSelSrvrAddress specifies the address of a DHCP
         server."
    ::= { vRtrIfDHCPOSelSrvrEntry 2 }

vRtrIfDHCPOSelSrvrRowStatus      OBJECT-TYPE
    SYNTAX      RowStatus
    MAX-ACCESS  read-create
    STATUS      current
    DESCRIPTION
        "Entries can be created and deleted via SNMP SET operations using the
         vRtrIfDHCPOSelSrvrRowStatus variable."
    ::= { vRtrIfDHCPOSelSrvrEntry 3 }

vRtrIfDHCPOSelSrvrDiscoDly       OBJECT-TYPE
    SYNTAX      Integer32 (0..100)
    UNITS       "deci-seconds"
    MAX-ACCESS  read-create
    STATUS      current
    DESCRIPTION
        "The value of vRtrIfDHCPOSelSrvrDiscoDly specifies the amount of time
         to  delay DHCP Discover messages relayed to the server."
    DEFVAL      { 0 }
    ::= { vRtrIfDHCPOSelSrvrEntry 4 }

vRtrIfDHCP6ASelSrvrTable         OBJECT-TYPE
    SYNTAX      SEQUENCE OF VRtrIfDHCP6ASelSrvrEntry
    MAX-ACCESS  not-accessible
    STATUS      current
    DESCRIPTION
        "The vRtrIfDHCP6ASelSrvrTable is used to configure the interface
         parameters related to DHCPv6 Advertise Selection for a specific
         server."
    ::= { tmnxVRtrObjs 142 }

vRtrIfDHCP6ASelSrvrEntry         OBJECT-TYPE
    SYNTAX      VRtrIfDHCP6ASelSrvrEntry
    MAX-ACCESS  not-accessible
    STATUS      current
    DESCRIPTION
        "Each row entry represents information related to DHCP6 for a virtual
         router interface in the system."
    INDEX       {
        vRtrID,
        vRtrIfIndex,
        vRtrIfDHCP6ASelSrvrAddressType,
        vRtrIfDHCP6ASelSrvrAddress
    }
    ::= { vRtrIfDHCP6ASelSrvrTable 1 }

VRtrIfDHCP6ASelSrvrEntry         ::= SEQUENCE
{
    vRtrIfDHCP6ASelSrvrAddressType   InetAddressType,
    vRtrIfDHCP6ASelSrvrAddress       InetAddress,
    vRtrIfDHCP6ASelSrvrRowStatus     RowStatus,
    vRtrIfDHCP6ASelSrvrSolDly        Integer32,
    vRtrIfDHCP6ASelSrvrPref          Integer32
}

vRtrIfDHCP6ASelSrvrAddressType   OBJECT-TYPE
    SYNTAX      InetAddressType
    MAX-ACCESS  not-accessible
    STATUS      current
    DESCRIPTION
        "The value of vRtrIfDHCP6ASelSrvrAddressType indicates the type of IP
         address of vRtrIfDHCP6ASelSrvrAddress."
    ::= { vRtrIfDHCP6ASelSrvrEntry 1 }

vRtrIfDHCP6ASelSrvrAddress       OBJECT-TYPE
    SYNTAX      InetAddress (SIZE (0|16))
    MAX-ACCESS  not-accessible
    STATUS      current
    DESCRIPTION
        "The value of vRtrIfDHCP6ASelSrvrAddress specifies the address of a
         DHCPv6 server."
    ::= { vRtrIfDHCP6ASelSrvrEntry 2 }

vRtrIfDHCP6ASelSrvrRowStatus     OBJECT-TYPE
    SYNTAX      RowStatus
    MAX-ACCESS  read-create
    STATUS      current
    DESCRIPTION
        "Entries can be created and deleted via SNMP SET operations using the
         vRtrIfDHCP6ASelSrvrRowStatus variable."
    ::= { vRtrIfDHCP6ASelSrvrEntry 3 }

vRtrIfDHCP6ASelSrvrSolDly        OBJECT-TYPE
    SYNTAX      Integer32 (0..100)
    UNITS       "deci-seconds"
    MAX-ACCESS  read-create
    STATUS      current
    DESCRIPTION
        "The value of vRtrIfDHCP6ASelSrvrSolDly specifies the amount  of time
         to delay DHCPv6 Solicit messages relayed to the server."
    DEFVAL      { 0 }
    ::= { vRtrIfDHCP6ASelSrvrEntry 4 }

vRtrIfDHCP6ASelSrvrPref          OBJECT-TYPE
    SYNTAX      Integer32 (-1..255)
    MAX-ACCESS  read-create
    STATUS      current
    DESCRIPTION
        "The value of vRtrIfDHCP6ASelSrvrPref specifies the value for the
         Preference option inserted when a DHCPv6 Reply message from the server
         is relayed to clients."
    DEFVAL      { -1 }
    ::= { vRtrIfDHCP6ASelSrvrEntry 5 }

vRtrLspBfdTableLastChanged       OBJECT-TYPE
    SYNTAX      TimeStamp
    MAX-ACCESS  read-only
    STATUS      current
    DESCRIPTION
        "Timestamp of the last change to the vRtrLspBfdTable either from adding
         a row or removing a row."
    ::= { tmnxVRtrObjs 143 }

vRtrLspBfdTable                  OBJECT-TYPE
    SYNTAX      SEQUENCE OF VRtrLspBfdEntry
    MAX-ACCESS  not-accessible
    STATUS      current
    DESCRIPTION
        "The vRtrLspBfdTable is used to configure the parameters related to LSP
         BFD."
    ::= { tmnxVRtrObjs 144 }

vRtrLspBfdEntry                  OBJECT-TYPE
    SYNTAX      VRtrLspBfdEntry
    MAX-ACCESS  not-accessible
    STATUS      current
    DESCRIPTION
        "Each row entry represents information related to an LSP BFD."
    INDEX       { vRtrID }
    ::= { vRtrLspBfdTable 1 }

VRtrLspBfdEntry                  ::= SEQUENCE
{
    vRtrLspBfdLastChanged            TimeStamp,
    vRtrLspBfdTailEndTxInterval      Unsigned32,
    vRtrLspBfdTailEndRxInterval      Unsigned32,
    vRtrLspBfdTailEndMultiplier      Unsigned32
}

vRtrLspBfdLastChanged            OBJECT-TYPE
    SYNTAX      TimeStamp
    MAX-ACCESS  read-only
    STATUS      current
    DESCRIPTION
        "The value of vRtrLspBfdLastChanged indicates the sysUpTime
          at the time of the last configuration change in this conceptual row."
    ::= { vRtrLspBfdEntry 1 }

vRtrLspBfdTailEndTxInterval      OBJECT-TYPE
    SYNTAX      Unsigned32 (100..1000)
    UNITS       "milliseconds"
    MAX-ACCESS  read-create
    STATUS      current
    DESCRIPTION
        "The value of vRtrLspBfdTailEndTxInterval specifies the BFD transmit
         interval for the LSP tail-end"
    DEFVAL      { 1000 }
    ::= { vRtrLspBfdEntry 2 }

vRtrLspBfdTailEndRxInterval      OBJECT-TYPE
    SYNTAX      Unsigned32 (100..1000)
    UNITS       "milliseconds"
    MAX-ACCESS  read-create
    STATUS      current
    DESCRIPTION
        "The value of vRtrLspBfdTailEndRxInterval specifies the BFD receive
         interval for the LSP tail-end"
    DEFVAL      { 1000 }
    ::= { vRtrLspBfdEntry 3 }

vRtrLspBfdTailEndMultiplier      OBJECT-TYPE
    SYNTAX      Unsigned32 (1..20)
    MAX-ACCESS  read-create
    STATUS      current
    DESCRIPTION
        "The value of vRtrLspBfdTailEndMultiplier specifies the number of
         consecutive BFD messages that must be missed from the peer before the
         BFD session state is changed to down and the upper level protocols are
         notified of the fault"
    DEFVAL      { 3 }
    ::= { vRtrLspBfdEntry 4 }

vRtrIfIpTunnelTableLastChanged   OBJECT-TYPE
    SYNTAX      TimeStamp
    MAX-ACCESS  read-only
    STATUS      current
    DESCRIPTION
        "The value of vRtrIfIpTunnelTableLastChanged indicates the sysUpTime at
         the time of the last modification to vRtrIfIpTunnelTable by adding,
         deleting an entry or change to a writable object in the table.

         If no changes were made to the table since the last re-initialization
         of the local network management subsystem, then this object contains a
         zero value."
    ::= { tmnxVRtrObjs 145 }

vRtrIfIpTunnelTable              OBJECT-TYPE
    SYNTAX      SEQUENCE OF VRtrIfIpTunnelEntry
    MAX-ACCESS  not-accessible
    STATUS      current
    DESCRIPTION
        "The vRtrIfIpTunnelTable contains IP Tunnel entries for each interface.

         Entries are created/deleted by the user."
    ::= { tmnxVRtrObjs 146 }

vRtrIfIpTunnelEntry              OBJECT-TYPE
    SYNTAX      VRtrIfIpTunnelEntry
    MAX-ACCESS  not-accessible
    STATUS      current
    DESCRIPTION
        "The vRtrIfIpTunnelEntry contains information about a single IP Tunnel
         entry."
    INDEX       {
        vRtrID,
        vRtrIfIndex,
        vRtrIfIpTunnelName
    }
    ::= { vRtrIfIpTunnelTable 1 }

VRtrIfIpTunnelEntry              ::= SEQUENCE
{
    vRtrIfIpTunnelName               TNamedItem,
    vRtrIfIpTunnelRowStatus          RowStatus,
    vRtrIfIpTunnelLastChanged        TimeStamp,
    vRtrIfIpTunnelGreHeader          TruthValue,
    vRtrIfIpTunnelDescription        TItemDescription,
    vRtrIfIpTunnelLclIpAddrType      InetAddressType,
    vRtrIfIpTunnelLclIpAddr          InetAddress,
    vRtrIfIpTunnelRemIpAddrType      InetAddressType,
    vRtrIfIpTunnelRemIpAddr          InetAddress,
    vRtrIfIpTunnelOperRemIpAddrType  InetAddressType,
    vRtrIfIpTunnelOperRemIpAddr      InetAddress,
    vRtrIfIpTunnelDlvryRtrId         TmnxServId,
    vRtrIfIpTunnelAdminState         TmnxAdminState,
    vRtrIfIpTunnelOperState          VrtrIpTunnelOperState,
    vRtrIfIpTunnelOperFlags          BITS,
    vRtrIfIpTunnelOperChanged        TimeStamp,
    vRtrIfIpTunnelIngStatsEnabled    TruthValue,
    vRtrIfIpTunnelEgrStatsEnabled    TruthValue,
    vRtrIfIpTunnelEncapsulatedMtu    Unsigned32
}

vRtrIfIpTunnelName               OBJECT-TYPE
    SYNTAX      TNamedItem
    MAX-ACCESS  accessible-for-notify
    STATUS      current
    DESCRIPTION
        "The value of vRtrIfIpTunnelName specifies the name of the tunnel and
         is part of the index for the table vRtrIfIpTunnelTable."
    ::= { vRtrIfIpTunnelEntry 1 }

vRtrIfIpTunnelRowStatus          OBJECT-TYPE
    SYNTAX      RowStatus
    MAX-ACCESS  read-create
    STATUS      current
    DESCRIPTION
        "The vRtrIfIpTunnelRowStatus object is used to create and delete rows
         in the vRtrIfIpTunnelTable."
    ::= { vRtrIfIpTunnelEntry 2 }

vRtrIfIpTunnelLastChanged        OBJECT-TYPE
    SYNTAX      TimeStamp
    MAX-ACCESS  read-only
    STATUS      current
    DESCRIPTION
        "The value of vRtrIfIpTunnelLastChanged indicates the sysUpTime at the
         time of the last modification of this entry."
    ::= { vRtrIfIpTunnelEntry 3 }

vRtrIfIpTunnelGreHeader          OBJECT-TYPE
    SYNTAX      TruthValue
    MAX-ACCESS  read-create
    STATUS      current
    DESCRIPTION
        "The value of vRtrIfIpTunnelGreHeader specifies whether the tunnel will
         include a GRE header in it."
    DEFVAL      { false }
    ::= { vRtrIfIpTunnelEntry 4 }

vRtrIfIpTunnelDescription        OBJECT-TYPE
    SYNTAX      TItemDescription
    MAX-ACCESS  read-create
    STATUS      current
    DESCRIPTION
        "The value of vRtrIfIpTunnelDescription specifies the user-provided
         description for each vRtrIfIpTunnelEntry in the table
         vRtrIfIpTunnelTable."
    DEFVAL      { "" }
    ::= { vRtrIfIpTunnelEntry 5 }

vRtrIfIpTunnelLclIpAddrType      OBJECT-TYPE
    SYNTAX      InetAddressType
    MAX-ACCESS  read-create
    STATUS      current
    DESCRIPTION
        "The value of vRtrIfIpTunnelLclIpAddrType specifies the address type of
         address in vRtrIfIpTunnelLclIpAddr."
    DEFVAL      { unknown }
    ::= { vRtrIfIpTunnelEntry 6 }

vRtrIfIpTunnelLclIpAddr          OBJECT-TYPE
    SYNTAX      InetAddress (SIZE (0|4|16|20))
    MAX-ACCESS  read-create
    STATUS      current
    DESCRIPTION
        "The value of vRtrIfIpTunnelLclIpAddr specifies the address of the
         local endpoint of this IP tunnel."
    DEFVAL      { ''H }
    ::= { vRtrIfIpTunnelEntry 7 }

vRtrIfIpTunnelRemIpAddrType      OBJECT-TYPE
    SYNTAX      InetAddressType
    MAX-ACCESS  read-create
    STATUS      current
    DESCRIPTION
        "The value of vRtrIfIpTunnelRemIpAddrType specifies the address type of
         address in vRtrIfIpTunnelRemIpAddr."
    DEFVAL      { unknown }
    ::= { vRtrIfIpTunnelEntry 8 }

vRtrIfIpTunnelRemIpAddr          OBJECT-TYPE
    SYNTAX      InetAddress (SIZE (0|4|16|20))
    MAX-ACCESS  read-create
    STATUS      current
    DESCRIPTION
        "The value of vRtrIfIpTunnelRemIpAddr specifies the address of the
         remote endpoint of this IP tunnel."
    DEFVAL      { ''H }
    ::= { vRtrIfIpTunnelEntry 9 }

vRtrIfIpTunnelOperRemIpAddrType  OBJECT-TYPE
    SYNTAX      InetAddressType
    MAX-ACCESS  read-only
    STATUS      current
    DESCRIPTION
        "The value of vRtrIfIpTunnelOperRemIpAddrType indicates the address
         type of address in vRtrIfIpTunnelOperRemIpAddr."
    ::= { vRtrIfIpTunnelEntry 10 }

vRtrIfIpTunnelOperRemIpAddr      OBJECT-TYPE
    SYNTAX      InetAddress (SIZE (0|4|16|20))
    MAX-ACCESS  read-only
    STATUS      current
    DESCRIPTION
        "The value of vRtrIfIpTunnelOperRemIpAddr indicates the address of the
         operational remote endpoint of this IP tunnel."
    ::= { vRtrIfIpTunnelEntry 11 }

vRtrIfIpTunnelDlvryRtrId         OBJECT-TYPE
    SYNTAX      TmnxServId
    MAX-ACCESS  read-create
    STATUS      current
    DESCRIPTION
        "The value of vRtrIfIpTunnelDlvryRtrId specifies the ID of the tunnel
         delivery service."
    DEFVAL      { 0 }
    ::= { vRtrIfIpTunnelEntry 12 }

vRtrIfIpTunnelAdminState         OBJECT-TYPE
    SYNTAX      TmnxAdminState
    MAX-ACCESS  read-create
    STATUS      current
    DESCRIPTION
        "The value of vRtrIfIpTunnelAdminState specifies the administrative
         state of the vRtrIfIpTunnelEntry."
    DEFVAL      { outOfService }
    ::= { vRtrIfIpTunnelEntry 13 }

vRtrIfIpTunnelOperState          OBJECT-TYPE
    SYNTAX      VrtrIpTunnelOperState
    MAX-ACCESS  read-only
    STATUS      current
    DESCRIPTION
        "The value of vRtrIfIpTunnelOperState indicates the operational status
         of vRtrIfIpTunnelEntry."
    ::= { vRtrIfIpTunnelEntry 14 }

vRtrIfIpTunnelOperFlags          OBJECT-TYPE
    SYNTAX      BITS {
        interfaceAdminDown (0),
        interfaceOperDown  (1),
        interfaceNoAddress (2),
        tunnelAdminDown    (3),
        unresolvedLocalIp  (4),
        remIpUnreachable   (5)
    }
    MAX-ACCESS  read-only
    STATUS      current
    DESCRIPTION
        "The value of vRtrIfIpTunnelOperFlags indicates the reason why the
         tunnel is operationally down."
    ::= { vRtrIfIpTunnelEntry 15 }

vRtrIfIpTunnelOperChanged        OBJECT-TYPE
    SYNTAX      TimeStamp
    MAX-ACCESS  read-only
    STATUS      current
    DESCRIPTION
        "The value of vRtrIfIpTunnelOperChanged indicates the sysUpTime at the
         time of the last operational status change of this entry."
    ::= { vRtrIfIpTunnelEntry 16 }

vRtrIfIpTunnelIngStatsEnabled    OBJECT-TYPE
    SYNTAX      TruthValue
    MAX-ACCESS  read-create
    STATUS      current
    DESCRIPTION
        "The value of vRtrIfIpTunnelIngStatsEnabled specifies if ingress
         statistics gathering is enabled for this tunnel."
    DEFVAL      { false }
    ::= { vRtrIfIpTunnelEntry 19 }

vRtrIfIpTunnelEgrStatsEnabled    OBJECT-TYPE
    SYNTAX      TruthValue
    MAX-ACCESS  read-create
    STATUS      current
    DESCRIPTION
        "The value of vRtrIfIpTunnelEgrStatsEnabled specifies if egress
         statistics gathering is enabled for this tunnel."
    DEFVAL      { false }
    ::= { vRtrIfIpTunnelEntry 20 }

vRtrIfIpTunnelEncapsulatedMtu    OBJECT-TYPE
    SYNTAX      Unsigned32 (0 | 512..9786)
    UNITS       "bytes"
    MAX-ACCESS  read-create
    STATUS      current
    DESCRIPTION
        "The value of vRtrIfIpTunnelEncapsulatedMtu specifies the MTU size for
         IP packets after the tunnel encapsulation has been added.

         A value set to zero resets the MTU to the calculated default size for
         this tunnel."
    DEFVAL      { 0 }
    ::= { vRtrIfIpTunnelEntry 21 }

vRtrIfNatTableLastChanged        OBJECT-TYPE
    SYNTAX      TimeStamp
    MAX-ACCESS  read-only
    STATUS      current
    DESCRIPTION
        "The value of the object vRtrIfNatTableLastChanged indicates the value
         of sysUpTime at the time of the last modification of an entry in the
         vRtrIfNatTable."
    ::= { tmnxVRtrObjs 147 }

vRtrIfNatTable                   OBJECT-TYPE
    SYNTAX      SEQUENCE OF VRtrIfNatEntry
    MAX-ACCESS  not-accessible
    STATUS      current
    DESCRIPTION
        "The vRtrIfNatTable is used to configure the interface parameters for
         NAT (Network Address Translation)."
    ::= { tmnxVRtrObjs 148 }

vRtrIfNatEntry                   OBJECT-TYPE
    SYNTAX      VRtrIfNatEntry
    MAX-ACCESS  not-accessible
    STATUS      current
    DESCRIPTION
        "Each row entry represents information related to NAT for a virtual
         router interface in the system.

         Entries can be created and deleted via SNMP SET operations using the
         vRtrIfNatRowStatus variable."
    INDEX       {
        vRtrID,
        vRtrIfIndex
    }
    ::= { vRtrIfNatTable 1 }

VRtrIfNatEntry                   ::= SEQUENCE
{
    vRtrIfNatRowStatus               RowStatus,
    vRtrIfNatLastChanged             TimeStamp,
    vRtrIfNatCpmPolicy               TNamedItemOrEmpty,
    vRtrIfNatCpmSpfPolicy            TNamedItemOrEmpty
}

vRtrIfNatRowStatus               OBJECT-TYPE
    SYNTAX      RowStatus
    MAX-ACCESS  read-create
    STATUS      current
    DESCRIPTION
        "The value of vRtrIfNatRowStatus specifies the row status of this row."
    ::= { vRtrIfNatEntry 1 }

vRtrIfNatLastChanged             OBJECT-TYPE
    SYNTAX      TimeStamp
    MAX-ACCESS  read-only
    STATUS      current
    DESCRIPTION
        "The value of vRtrIfNatLastChanged indicates the sysUpTime at the time
         of the last configuration change in this conceptual row."
    ::= { vRtrIfNatEntry 2 }

vRtrIfNatCpmPolicy               OBJECT-TYPE
    SYNTAX      TNamedItemOrEmpty
    MAX-ACCESS  read-create
    STATUS      current
    DESCRIPTION
        "The value of vRtrIfNatCpmPolicy specifies the name of the CPM NAT
         Policy associated with this interface.

         This object refers to a conceptual row in the
         TIMETRA-NAT-MIB::tmnxNatCpmPlcyTable."
    DEFVAL      { "" }
    ::= { vRtrIfNatEntry 3 }

vRtrIfNatCpmSpfPolicy            OBJECT-TYPE
    SYNTAX      TNamedItemOrEmpty
    MAX-ACCESS  read-create
    STATUS      current
    DESCRIPTION
        "The value of vRtrIfNatCpmSpfPolicy specifies the name of the Static
         Port Forwarding CPM NAT Policy associated with this interface.

         This object refers to a conceptual row in the
         TIMETRA-NAT-MIB::tmnxNatCpmPlcyTable."
    DEFVAL      { "" }
    ::= { vRtrIfNatEntry 4 }

tmnxVRtrDCObjs                   OBJECT IDENTIFIER ::= { tmnxVRtrObjs 200 }

tmnxVrtrSys                      OBJECT IDENTIFIER ::= { tmnxVRtrObjs 201 }

tmnxVrtrSysEnforceUniqueIfIndex  OBJECT-TYPE
    SYNTAX      TruthValue
    MAX-ACCESS  read-write
    STATUS      current
    DESCRIPTION
        "The value of tmnxVrtrSysEnforceUniqueIfIndex specifies if, while an
         SNMP client creates a conceptual row in the vRtrIfTable, this system
         enforces values for the object vRtrIfIndex that are unique within the
         scope of the system.

         While the value of tmnxVrtrSysEnforceUniqueIfIndex is equal to 'true',
         this system only accepts values for vRtrIfIndex that are unique within
         the scope of this system.

         While the value of tmnxVrtrSysEnforceUniqueIfIndex is equal to
         'false', this system accepts values for vRtrIfIndex that are unique
         within the scope of the virtual router instance.

         Regardless of the value of tmnxVrtrSysEnforceUniqueIfIndex, values
         suggested by the object vRtrNewIfIndex are unique within the scope of
         the system.

         Regardless of the value of tmnxVrtrSysEnforceUniqueIfIndex, when this
         system creates a conceptual row in the vRtrIfTable automatically, as a
         consequence of the creation of some other row, for example in the
         TIMETRA-SERV-MIB::iesIfTable, the value of vRtrIfIndex is unique
         within the scope of the system.

         While there are conceptual rows in the vRtrIfTable having values for
         the vRtrIfIndex object that are not unique within the system, it is
         not allowed to set the value of tmnxVrtrSysEnforceUniqueIfIndex to
         'true'."
    DEFVAL      { false }
    ::= { tmnxVrtrSys 1 }

tmnxVrtrSysAllowQinQNetworkIntf  OBJECT-TYPE
    SYNTAX      TruthValue
    MAX-ACCESS  read-write
    STATUS      current
    DESCRIPTION
        "The value of tmnxVrtrSysAllowQinQNetworkIntf specifies if the system
         allows network interfaces on ports with a QinQ encapsulation."
    DEFVAL      { false }
    ::= { tmnxVrtrSys 2 }

tmnxVrtrSysMplsTunnelMode        OBJECT-TYPE
    SYNTAX      VrtrMplsTunnelMode
    MAX-ACCESS  read-write
    STATUS      current
    DESCRIPTION
        "The value of tmnxVrtrSysMplsTunnelMode is used to configure the MPLS
         tunnel mode."
    DEFVAL      { uniform }
    ::= { tmnxVrtrSys 3 }

tmnxVrtrSysMplsLblStackStatCount OBJECT-TYPE
    SYNTAX      Unsigned32 (1..2)
    MAX-ACCESS  read-write
    STATUS      current
    DESCRIPTION
        "The value of tmnxVrtrSysMplsLblStackStatCount is used to configure
         number of labels in stack that must increment the statistics counter."
    DEFVAL      { 1 }
    ::= { tmnxVrtrSys 4 }

tmnxVrtrFwdIPoverIPv6            OBJECT-TYPE
    SYNTAX      TruthValue
    MAX-ACCESS  read-create
    STATUS      current
    DESCRIPTION
        "The value of tmnxVrtrFwdIPoverIPv6 specifies if ip traffic  sent to
         system address is forwarded or not. "
    DEFVAL      { false }
    ::= { tmnxVrtrSys 5 }

tmnxVrtrFwdIPoverGre             OBJECT-TYPE
    SYNTAX      TruthValue
    MAX-ACCESS  read-create
    STATUS      current
    DESCRIPTION
        "The value of tmnxVrtrFwdIPoverGre specifies if ip traffic encapsulated
          in GRE transport sent to system address is forwarded or not. "
    DEFVAL      { false }
    ::= { tmnxVrtrSys 6 }

tmnxVrtrIPEHPerform              OBJECT-TYPE
    SYNTAX      INTEGER {
        max     (1),
        limited (2)
    }
    MAX-ACCESS  read-create
    STATUS      current
    DESCRIPTION
        "The value of tmnxVrtrIPEHPerform specifies a setting to provide line
         rate performance  for IPv6 traffic with/without EH for L2 and L3
         traffic:"
    DEFVAL      { max }
    ::= { tmnxVrtrSys 7 }

tmnxVrtrIPAllowCPUFragmentation  OBJECT-TYPE
    SYNTAX      TruthValue
    MAX-ACCESS  read-write
    STATUS      current
    DESCRIPTION
        "The value of tmnxVrtrIPAllowCPUFragmentation  enables IP fragmentation
         for packets exceeding IP MTU via system CPU."
    DEFVAL      { false }
    ::= { tmnxVrtrSys 8 }

tmnxVrtrIPAllowICMPRedirect      OBJECT-TYPE
    SYNTAX      TruthValue
    MAX-ACCESS  read-write
    STATUS      current
    DESCRIPTION
        "The value of tmnxVrtrIPAllowICMPRedirect specifies if ICMP Redirect is
         enabled or not."
    DEFVAL      { false }
    ::= { tmnxVrtrSys 9 }

tmnxVrtrIPStartMacAddress        OBJECT-TYPE
    SYNTAX      MacAddress
    MAX-ACCESS  read-only
    STATUS      current
    DESCRIPTION
        "The value of tmnxVrtrIPStartMacAddress indicates the start of the
         range of valid MAC addresses that can be used on an IP interface."
    ::= { tmnxVrtrSys 10 }

tmnxVrtrIPEndMacAddress          OBJECT-TYPE
    SYNTAX      MacAddress
    MAX-ACCESS  read-only
    STATUS      current
    DESCRIPTION
        "The value of tmnxVrtrIPEndMacAddress indicates the end of the range of
         valid MAC addresses that can be used on an IP interface."
    ::= { tmnxVrtrSys 11 }

tmnxVrtrIPCommonMacAddress       OBJECT-TYPE
    SYNTAX      MacAddress
    MAX-ACCESS  read-only
    STATUS      current
    DESCRIPTION
        "The value of tmnxVrtrIPCommonMacAddress indicates the common MAC
         address that can be used on an IP interface.

         The first IP interface that has a configured MAC address outside the
         range tmnxVrtrIPStartMacAddress to tmnxVrtrIPEndMacAddress will set
         the value of tmnxVrtrIPCommonMacAddress, then the configuration of a
         MAC address on any other IP interface must use the
         tmnxVrtrIPCommonMacAddress or a MAC address from the range
         tmnxVrtrIPStartMacAddress to tmnxVrtrIPEndMacAddress."
    ::= { tmnxVrtrSys 12 }

tmnxVrtrIPBufferUnresolvedPkts   OBJECT-TYPE
    SYNTAX      TruthValue
    MAX-ACCESS  read-write
    STATUS      current
    DESCRIPTION
        "The value of tmnxVrtrIPBufferUnresolvedPkts specifies whether
         unresolved packets should be buffered or not."
    DEFVAL      { true }
    ::= { tmnxVrtrSys 13 }

tmnxVrtrSysuRPFIgnoreDefault     OBJECT-TYPE
    SYNTAX      TruthValue
    MAX-ACCESS  read-create
    STATUS      current
    DESCRIPTION
        "The value of tmnxVrtrSysuRPFIgnoreDefault specifies if the default
         route is to be disregarded while performing a uRPF check

         When the value of tmnxVrtrSysuRPFIgnoreDefault is set to 'true', the
         default route is disregarded while performing a uRPF check. The
         default route is disregarded for all the values of
         vRtrIfuRPFCheckMode."
    DEFVAL      { false }
    ::= { tmnxVrtrSys 14 }

tmnxVrtrAutoconfiguration        OBJECT IDENTIFIER ::= { tmnxVRtrObjs 202 }

tmnxVrtrDhcpClient               OBJECT IDENTIFIER ::= { tmnxVrtrAutoconfiguration 1 }

vRtrIfDhcpClTable                OBJECT-TYPE
    SYNTAX      SEQUENCE OF VRtrIfDhcpClEntry
    MAX-ACCESS  not-accessible
    STATUS      current
    DESCRIPTION
        "The vRtrIfDhcpClTable is used to configure DHCP Client configuration
         for interfaces."
    ::= { tmnxVrtrDhcpClient 1 }

vRtrIfDhcpClEntry                OBJECT-TYPE
    SYNTAX      VRtrIfDhcpClEntry
    MAX-ACCESS  not-accessible
    STATUS      current
    DESCRIPTION
        "Each conceptual row represents DHCP Client configuration for a
         specific virtual router interface in the system.

         An SNMP client can create a row in this table for each corresponding
         row in the vRtrIfTable that supports DHCP client functionality.

         Applicable interfaces are interfaces where vRtrIfType is equal to
         'network', and vRtrID is equal to one, excluding the system interface.

         If the corresponding row in the vRtrIfTable is destroyed, the system
         automatically destroys this conceptual row."
    INDEX       {
        vRtrID,
        vRtrIfIndex
    }
    ::= { vRtrIfDhcpClTable 1 }

VRtrIfDhcpClEntry                ::= SEQUENCE
{
    vRtrIfDhcpClLastChanged          TimeStamp,
    vRtrIfDhcpClRowStatus            RowStatus,
    vRtrIfDhcpClAdminState           TmnxAdminState,
    vRtrIfDhcpClVendorClassIdFmt     TmnxDataFormat,
    vRtrIfDhcpClVendorClassId        OCTET STRING,
    vRtrIfDhcpClClientIdOrigin       INTEGER,
    vRtrIfDhcpClClientIdFmt          TmnxDataFormat,
    vRtrIfDhcpClClientId             OCTET STRING,
    vRtrIfDhcpClLeaseTime            Unsigned32,
    vRtrIfDhcpClRequestOptions       BITS
}

vRtrIfDhcpClLastChanged          OBJECT-TYPE
    SYNTAX      TimeStamp
    MAX-ACCESS  read-only
    STATUS      current
    DESCRIPTION
        "The value of vRtrIfDhcpClLastChanged indicates the sysUpTime at the
         time of the last configuration change in this conceptual row."
    ::= { vRtrIfDhcpClEntry 1 }

vRtrIfDhcpClRowStatus            OBJECT-TYPE
    SYNTAX      RowStatus
    MAX-ACCESS  read-create
    STATUS      current
    DESCRIPTION
        "The value of vRtrIfDhcpClRowStatus specifies the row status of this
         row."
    ::= { vRtrIfDhcpClEntry 2 }

vRtrIfDhcpClAdminState           OBJECT-TYPE
    SYNTAX      TmnxAdminState
    MAX-ACCESS  read-create
    STATUS      current
    DESCRIPTION
        "The value of vRtrIfDhcpClAdminState specifies the administrative state
         of this entry."
    DEFVAL      { outOfService }
    ::= { vRtrIfDhcpClEntry 3 }

vRtrIfDhcpClVendorClassIdFmt     OBJECT-TYPE
    SYNTAX      TmnxDataFormat
    MAX-ACCESS  read-create
    STATUS      current
    DESCRIPTION
        "The value of the object vRtrIfDhcpClVendorClassIdFmt specifies how the
         value of vRtrIfDhcpClVendorClassId must be formatted."
    DEFVAL      { ascii }
    ::= { vRtrIfDhcpClEntry 4 }

vRtrIfDhcpClVendorClassId        OBJECT-TYPE
    SYNTAX      OCTET STRING (SIZE (0..127))
    MAX-ACCESS  read-create
    STATUS      current
    DESCRIPTION
        "The value of the object vRtrIfDhcpClVendorClassId specifies the Vendor
         Class identifier.

         If the value of this object is the empty string, then it is not used."
    DEFVAL      { ''H }
    ::= { vRtrIfDhcpClEntry 5 }

vRtrIfDhcpClClientIdOrigin       OBJECT-TYPE
    SYNTAX      INTEGER {
        useMac     (0),
        interface  (1),
        configured (2)
    }
    MAX-ACCESS  read-create
    STATUS      current
    DESCRIPTION
        "The value of the object vRtrIfDhcpClClientIdOrigin specifies the
         origin of the Client-identifier.

         The value 'configured' means the system uses the value configured in
         the object vRtrIfDhcpClClientId."
    DEFVAL      { useMac }
    ::= { vRtrIfDhcpClEntry 6 }

vRtrIfDhcpClClientIdFmt          OBJECT-TYPE
    SYNTAX      TmnxDataFormat
    MAX-ACCESS  read-create
    STATUS      current
    DESCRIPTION
        "The value of the object vRtrIfDhcpClClientIdFmt specifies how the
         value of vRtrIfDhcpClClientId must be formatted."
    DEFVAL      { ascii }
    ::= { vRtrIfDhcpClEntry 7 }

vRtrIfDhcpClClientId             OBJECT-TYPE
    SYNTAX      OCTET STRING (SIZE (0..127))
    MAX-ACCESS  read-create
    STATUS      current
    DESCRIPTION
        "The value of the object vRtrIfDhcpClClientId specifies the
         Client-identifier.

         If the value of this object is the empty string, then it is not used."
    DEFVAL      { ''H }
    ::= { vRtrIfDhcpClEntry 8 }

vRtrIfDhcpClLeaseTime            OBJECT-TYPE
    SYNTAX      Unsigned32 (10..315446399 | 4294967295)
    UNITS       "seconds"
    MAX-ACCESS  read-create
    STATUS      current
    DESCRIPTION
        "The value of the object vRtrIfDhcpClLeaseTime specifies the lease time
         the DHCP client requests.

         The value 4294967295 means 'infinite'."
    DEFVAL      { 86400 }
    ::= { vRtrIfDhcpClEntry 9 }

vRtrIfDhcpClRequestOptions       OBJECT-TYPE
    SYNTAX      BITS {
        router      (0),
        staticRoute (1),
        dnsServer   (2)
    }
    MAX-ACCESS  read-create
    STATUS      current
    DESCRIPTION
        "The value of vRtrIfDhcpClRequestOptions specifies what DHCP options
         the DHCP client includes in option 55, Parameter Request List."
    DEFVAL      { {} }
    ::= { vRtrIfDhcpClEntry 10 }

vRtrIfDhcpClStatsTable           OBJECT-TYPE
    SYNTAX      SEQUENCE OF VRtrIfDhcpClStatsEntry
    MAX-ACCESS  not-accessible
    STATUS      current
    DESCRIPTION
        "The vRtrIfDhcpClStatsTable contains DHCP client statistics.

         Conceptual rows in this table are created and destroyed automatically
         by the system, when DHCP clients are enabled and disabled, by means of
         the vRtrIfDhcpClTable or the Boot Options File (BOF)."
    ::= { tmnxVrtrDhcpClient 2 }

vRtrIfDhcpClStatsEntry           OBJECT-TYPE
    SYNTAX      VRtrIfDhcpClStatsEntry
    MAX-ACCESS  not-accessible
    STATUS      current
    DESCRIPTION
        "Each row contains statistics of a particular DHCP client instance."
    INDEX       {
        vRtrID,
        vRtrIfIndex
    }
    ::= { vRtrIfDhcpClStatsTable 1 }

VRtrIfDhcpClStatsEntry           ::= SEQUENCE
{
    vRtrIfDhcpClStatsClearedTime     TimeStamp,
    vRtrIfDhcpClStatsTxDiscovers     Counter64,
    vRtrIfDhcpClStatsTxRequests      Counter64,
    vRtrIfDhcpClStatsTxReleases      Counter64,
    vRtrIfDhcpClStatsTxDeclines      Counter64,
    vRtrIfDhcpClStatsRxOffers        Counter64,
    vRtrIfDhcpClStatsRxAcks          Counter64,
    vRtrIfDhcpClStatsRxNaks          Counter64,
    vRtrIfDhcpClStatsRxDrops         Counter64
}

vRtrIfDhcpClStatsClearedTime     OBJECT-TYPE
    SYNTAX      TimeStamp
    MAX-ACCESS  read-only
    STATUS      current
    DESCRIPTION
        "The value of vRtrIfDhcpClStatsClearedTime indicates the sysUpTime at
         the time the counters in this conceptual row were cleared for the last
         time.

         If the counters were never cleared, the value of
         vRtrIfDhcpClStatsClearedTime is zero."
    ::= { vRtrIfDhcpClStatsEntry 1 }

vRtrIfDhcpClStatsTxDiscovers     OBJECT-TYPE
    SYNTAX      Counter64
    MAX-ACCESS  read-only
    STATUS      current
    DESCRIPTION
        "The value of vRtrIfDhcpClStatsTxDiscovers indicates the number of
         DHCPDISCOVER messages the DHCP client has sent."
    ::= { vRtrIfDhcpClStatsEntry 2 }

vRtrIfDhcpClStatsTxRequests      OBJECT-TYPE
    SYNTAX      Counter64
    MAX-ACCESS  read-only
    STATUS      current
    DESCRIPTION
        "The value of vRtrIfDhcpClStatsTxRequests indicates the number of
         DHCPREQUEST messages the DHCP client has sent."
    ::= { vRtrIfDhcpClStatsEntry 3 }

vRtrIfDhcpClStatsTxReleases      OBJECT-TYPE
    SYNTAX      Counter64
    MAX-ACCESS  read-only
    STATUS      current
    DESCRIPTION
        "The value of vRtrIfDhcpClStatsTxReleases indicates the number of
         DHCPRELEASE messages the DHCP client has sent."
    ::= { vRtrIfDhcpClStatsEntry 4 }

vRtrIfDhcpClStatsTxDeclines      OBJECT-TYPE
    SYNTAX      Counter64
    MAX-ACCESS  read-only
    STATUS      current
    DESCRIPTION
        "The value of vRtrIfDhcpClStatsTxDeclines indicates the number of
         DHCPDECLINE messages the DHCP client has sent."
    ::= { vRtrIfDhcpClStatsEntry 5 }

vRtrIfDhcpClStatsRxOffers        OBJECT-TYPE
    SYNTAX      Counter64
    MAX-ACCESS  read-only
    STATUS      current
    DESCRIPTION
        "The value of vRtrIfDhcpClStatsRxOffers indicates the number of
         DHCPOFFER messages the DHCP client has received."
    ::= { vRtrIfDhcpClStatsEntry 6 }

vRtrIfDhcpClStatsRxAcks          OBJECT-TYPE
    SYNTAX      Counter64
    MAX-ACCESS  read-only
    STATUS      current
    DESCRIPTION
        "The value of vRtrIfDhcpClStatsRxAcks indicates the number of DHCPACK
         messages the DHCP client has received."
    ::= { vRtrIfDhcpClStatsEntry 7 }

vRtrIfDhcpClStatsRxNaks          OBJECT-TYPE
    SYNTAX      Counter64
    MAX-ACCESS  read-only
    STATUS      current
    DESCRIPTION
        "The value of vRtrIfDhcpClStatsRxNaks indicates the number of DHCPNAK
         messages the DHCP client has received."
    ::= { vRtrIfDhcpClStatsEntry 8 }

vRtrIfDhcpClStatsRxDrops         OBJECT-TYPE
    SYNTAX      Counter64
    MAX-ACCESS  read-only
    STATUS      current
    DESCRIPTION
        "The value of vRtrIfDhcpClStatsRxDrops indicates the number of DHCP
         messages that the DHCP client has received and dropped."
    ::= { vRtrIfDhcpClStatsEntry 9 }

vRtrIfDhcpClStateTable           OBJECT-TYPE
    SYNTAX      SEQUENCE OF VRtrIfDhcpClStateEntry
    MAX-ACCESS  not-accessible
    STATUS      current
    DESCRIPTION
        "The vRtrIfDhcpClStateTable contains DHCP client status information.

         Conceptual rows in this table are created and destroyed automatically
         by the system, when DHCP clients are enabled and disabled, by means of
         the vRtrIfDhcpClTable or the Boot Options File (BOF)."
    ::= { tmnxVrtrDhcpClient 3 }

vRtrIfDhcpClStateEntry           OBJECT-TYPE
    SYNTAX      VRtrIfDhcpClStateEntry
    MAX-ACCESS  not-accessible
    STATUS      current
    DESCRIPTION
        "Each row contains status information of a particular DHCP client
         instance."
    INDEX       {
        vRtrID,
        vRtrIfIndex
    }
    ::= { vRtrIfDhcpClStateTable 1 }

VRtrIfDhcpClStateEntry           ::= SEQUENCE
{
    vRtrIfDhcpClStateCiAddrType      InetAddressType,
    vRtrIfDhcpClStateCiAddr          InetAddress,
    vRtrIfDhcpClStateCiAddrMaskLen   Unsigned32,
    vRtrIfDhcpClStateChAddr          MacAddress,
    vRtrIfDhcpClStateSiAddrType      InetAddressType,
    vRtrIfDhcpClStateSiAddr          InetAddress,
    vRtrIfDhcpClStateRtAddrType      InetAddressType,
    vRtrIfDhcpClStateRtAddr          InetAddress,
    vRtrIfDhcpClStateDnsPriAddrType  InetAddressType,
    vRtrIfDhcpClStateDnsPriAddr      InetAddress,
    vRtrIfDhcpClStateDnsSecAddrType  InetAddressType,
    vRtrIfDhcpClStateDnsSecAddr      InetAddress,
    vRtrIfDhcpClStateDnsTerAddrType  InetAddressType,
    vRtrIfDhcpClStateDnsTerAddr      InetAddress,
    vRtrIfDhcpClStateLeaseAcquired   DateAndTimeOrEmpty,
    vRtrIfDhcpClStateLeaseRenew      DateAndTimeOrEmpty,
    vRtrIfDhcpClStateLeaseRebind     DateAndTimeOrEmpty,
    vRtrIfDhcpClStateLeaseEnd        DateAndTimeOrEmpty,
    vRtrIfDhcpClDhcpState            TmnxDhcpClientState,
    vRtrIfDhcpClStateStatus          INTEGER,
    vRtrIfDhcpClStateDescription     DisplayString
}

vRtrIfDhcpClStateCiAddrType      OBJECT-TYPE
    SYNTAX      InetAddressType
    MAX-ACCESS  read-only
    STATUS      current
    DESCRIPTION
        "The value of vRtrIfDhcpClStateCiAddrType indicates the address type of
         vRtrIfDhcpClStateCiAddr."
    ::= { vRtrIfDhcpClStateEntry 1 }

vRtrIfDhcpClStateCiAddr          OBJECT-TYPE
    SYNTAX      InetAddress (SIZE (0|4|16))
    MAX-ACCESS  read-only
    STATUS      current
    DESCRIPTION
        "The value of vRtrIfDhcpClStateCiAddr indicates the client IP address."
    ::= { vRtrIfDhcpClStateEntry 2 }

vRtrIfDhcpClStateCiAddrMaskLen   OBJECT-TYPE
    SYNTAX      Unsigned32 (0..128)
    MAX-ACCESS  read-only
    STATUS      current
    DESCRIPTION
        "The value of vRtrIfDhcpClStateCiAddrMaskLen indicates the length of
         the subnet mask for a DHCP lease, or the prefix length for a DHCPv6
         lease."
    ::= { vRtrIfDhcpClStateEntry 3 }

vRtrIfDhcpClStateChAddr          OBJECT-TYPE
    SYNTAX      MacAddress
    MAX-ACCESS  read-only
    STATUS      current
    DESCRIPTION
        "The value of vRtrIfDhcpClStateChAddr indicates
          the MAC address of the client."
    ::= { vRtrIfDhcpClStateEntry 4 }

vRtrIfDhcpClStateSiAddrType      OBJECT-TYPE
    SYNTAX      InetAddressType
    MAX-ACCESS  read-only
    STATUS      current
    DESCRIPTION
        "The value of vRtrIfDhcpClStateSiAddrType indicates the address type of
         vRtrIfDhcpClStateSiAddr."
    ::= { vRtrIfDhcpClStateEntry 5 }

vRtrIfDhcpClStateSiAddr          OBJECT-TYPE
    SYNTAX      InetAddress (SIZE (0|4|16))
    MAX-ACCESS  read-only
    STATUS      current
    DESCRIPTION
        "The value of vRtrIfDhcpClStateSiAddr indicates the Server Identifier."
    ::= { vRtrIfDhcpClStateEntry 6 }

vRtrIfDhcpClStateRtAddrType      OBJECT-TYPE
    SYNTAX      InetAddressType
    MAX-ACCESS  read-only
    STATUS      current
    DESCRIPTION
        "The value of vRtrIfDhcpClStateRtAddrType indicates the address type of
         vRtrIfDhcpClStateRtAddr."
    ::= { vRtrIfDhcpClStateEntry 7 }

vRtrIfDhcpClStateRtAddr          OBJECT-TYPE
    SYNTAX      InetAddress (SIZE (0|4|16))
    MAX-ACCESS  read-only
    STATUS      current
    DESCRIPTION
        "The value of vRtrIfDhcpClStateRtAddr indicates the router IP address."
    REFERENCE
        "RFC 2132 DHCP Options and BOOTP Vendor Extensions
         section 3.5. Router Option"
    ::= { vRtrIfDhcpClStateEntry 8 }

vRtrIfDhcpClStateDnsPriAddrType  OBJECT-TYPE
    SYNTAX      InetAddressType
    MAX-ACCESS  read-only
    STATUS      current
    DESCRIPTION
        "The value of vRtrIfDhcpClStateDnsPriAddrType indicates the address
         type of vRtrIfDhcpClStateDnsPriAddr."
    ::= { vRtrIfDhcpClStateEntry 9 }

vRtrIfDhcpClStateDnsPriAddr      OBJECT-TYPE
    SYNTAX      InetAddress (SIZE (0|4|16))
    MAX-ACCESS  read-only
    STATUS      current
    DESCRIPTION
        "The value of vRtrIfDhcpClStateDnsPriAddr indicates the address of the
         primary DNS server."
    REFERENCE
        "RFC 2132 DHCP Options and BOOTP Vendor Extensions
         3.8. Domain Name Server Option"
    ::= { vRtrIfDhcpClStateEntry 10 }

vRtrIfDhcpClStateDnsSecAddrType  OBJECT-TYPE
    SYNTAX      InetAddressType
    MAX-ACCESS  read-only
    STATUS      current
    DESCRIPTION
        "The value of vRtrIfDhcpClStateDnsSecAddrType indicates the address
         type of vRtrIfDhcpClStateDnsSecAddr."
    ::= { vRtrIfDhcpClStateEntry 11 }

vRtrIfDhcpClStateDnsSecAddr      OBJECT-TYPE
    SYNTAX      InetAddress (SIZE (0|4|16))
    MAX-ACCESS  read-only
    STATUS      current
    DESCRIPTION
        "The value of vRtrIfDhcpClStateDnsSecAddr indicates the address of the
         secondary DNS server."
    REFERENCE
        "RFC 2132 DHCP Options and BOOTP Vendor Extensions
         3.8. Domain Name Server Option"
    ::= { vRtrIfDhcpClStateEntry 12 }

vRtrIfDhcpClStateDnsTerAddrType  OBJECT-TYPE
    SYNTAX      InetAddressType
    MAX-ACCESS  read-only
    STATUS      current
    DESCRIPTION
        "The value of vRtrIfDhcpClStateDnsTerAddrType indicates the address
         type of vRtrIfDhcpClStateDnsTerAddr."
    ::= { vRtrIfDhcpClStateEntry 13 }

vRtrIfDhcpClStateDnsTerAddr      OBJECT-TYPE
    SYNTAX      InetAddress (SIZE (0|4|16))
    MAX-ACCESS  read-only
    STATUS      current
    DESCRIPTION
        "The value of vRtrIfDhcpClStateDnsTerAddr indicates the address of the
         tertiary DNS server."
    REFERENCE
        "RFC 2132 DHCP Options and BOOTP Vendor Extensions
         3.8. Domain Name Server Option"
    ::= { vRtrIfDhcpClStateEntry 14 }

vRtrIfDhcpClStateLeaseAcquired   OBJECT-TYPE
    SYNTAX      DateAndTimeOrEmpty
    MAX-ACCESS  read-only
    STATUS      current
    DESCRIPTION
        "The value of vRtrIfDhcpClStateLeaseAcquired indicates the UTC date
         when the latest DHCP lease was acquired from the server. The address
         of the server is indicated by vRtrIfDhcpClStateSiAddr.

         The value of vRtrIfDhcpClStateLeaseAcquired can be the time when the
         DHCP lease was first obtained, or the time when the lease was renewed
         or rebound."
    ::= { vRtrIfDhcpClStateEntry 15 }

vRtrIfDhcpClStateLeaseRenew      OBJECT-TYPE
    SYNTAX      DateAndTimeOrEmpty
    MAX-ACCESS  read-only
    STATUS      current
    DESCRIPTION
        "The value of vRtrIfDhcpClStateLeaseRenew indicates the UTC date when
         the current DHCP lease needs to be renewed."
    ::= { vRtrIfDhcpClStateEntry 16 }

vRtrIfDhcpClStateLeaseRebind     OBJECT-TYPE
    SYNTAX      DateAndTimeOrEmpty
    MAX-ACCESS  read-only
    STATUS      current
    DESCRIPTION
        "The value of vRtrIfDhcpClStateLeaseRebind indicates the UTC date when
         the current DHCP lease needs to be rebound."
    ::= { vRtrIfDhcpClStateEntry 17 }

vRtrIfDhcpClStateLeaseEnd        OBJECT-TYPE
    SYNTAX      DateAndTimeOrEmpty
    MAX-ACCESS  read-only
    STATUS      current
    DESCRIPTION
        "The value of vRtrIfDhcpClStateLeaseEnd indicates the UTC date when the
         current DHCP lease can no longer be used."
    ::= { vRtrIfDhcpClStateEntry 18 }

vRtrIfDhcpClDhcpState            OBJECT-TYPE
    SYNTAX      TmnxDhcpClientState
    MAX-ACCESS  read-only
    STATUS      current
    DESCRIPTION
        "The value of vRtrIfDhcpClDhcpState indicates the DHCP protocol state
         the DHCP client is in."
    REFERENCE
        "RFC 2131 Dynamic Host Configuration Protocol
         Figure 5:  State-transition diagram for DHCP clients"
    ::= { vRtrIfDhcpClStateEntry 19 }

vRtrIfDhcpClStateStatus          OBJECT-TYPE
    SYNTAX      INTEGER {
        disabled     (0),
        initializing (1),
        requesting   (2),
        lost         (3),
        established  (4),
        failed       (5)
    }
    MAX-ACCESS  read-only
    STATUS      current
    DESCRIPTION
        "The value of vRtrIfDhcpClStateStatus indicates the status of the DHCP
         client.

          A value of 'disabled' indicates that the DHCP client was not enabled.

          A value of 'initializing' indicates that the DHCP client is starting.

          A value of 'requesting' indicates that the DHCP client is broadcasting
          requests waiting for a server.

          A value of 'lost' indicates that no valid DHCP server was discovered within
          supplied timeout (applicable only when timeout can be configured).

          A value of 'established' indicates a successfully received and applied offer.

          A value of 'failed' indicates that the system encountered a
          runtime validation error attempting to parse the received offer or
          installing the IP received in the offer. DHCP client will restart."
    ::= { vRtrIfDhcpClStateEntry 20 }

vRtrIfDhcpClStateDescription     OBJECT-TYPE
    SYNTAX      DisplayString (SIZE (0..255))
    MAX-ACCESS  read-only
    STATUS      current
    DESCRIPTION
        "The value of vRtrIfDhcpClStateDescription indicates the description of
         the status of this DHCP client.

         It may describe the cause of the problem while the value of the object
         vRtrIfDhcpClStateStatus is equal to 'failed'."
    ::= { vRtrIfDhcpClStateEntry 21 }

vRtrIfDhcpClRtTable              OBJECT-TYPE
    SYNTAX      SEQUENCE OF VRtrIfDhcpClRtEntry
    MAX-ACCESS  not-accessible
    STATUS      current
    DESCRIPTION
        "The vRtrIfDhcpClRtTable contains routes that the DHCP client received
         by means of the DHCP protocol.

         Conceptual rows in this table are created and destroyed automatically
         by the system."
    ::= { tmnxVrtrDhcpClient 4 }

vRtrIfDhcpClRtEntry              OBJECT-TYPE
    SYNTAX      VRtrIfDhcpClRtEntry
    MAX-ACCESS  not-accessible
    STATUS      current
    DESCRIPTION
        "Each row contains information about a particular DHCP client route."
    INDEX       {
        vRtrID,
        vRtrIfIndex,
        vRtrIfDhcpClRtAddrType,
        vRtrIfDhcpClRtAddr,
        vRtrIfDhcpClRtPrefixLen,
        vRtrIfDhcpClRtNhAddrType,
        vRtrIfDhcpClRtNhAddr
    }
    ::= { vRtrIfDhcpClRtTable 1 }

VRtrIfDhcpClRtEntry              ::= SEQUENCE
{
    vRtrIfDhcpClRtAddrType           InetAddressType,
    vRtrIfDhcpClRtAddr               InetAddress,
    vRtrIfDhcpClRtPrefixLen          InetAddressPrefixLength,
    vRtrIfDhcpClRtNhAddrType         InetAddressType,
    vRtrIfDhcpClRtNhAddr             InetAddress,
    vRtrIfDhcpClRtStatus             INTEGER
}

vRtrIfDhcpClRtAddrType           OBJECT-TYPE
    SYNTAX      InetAddressType
    MAX-ACCESS  not-accessible
    STATUS      current
    DESCRIPTION
        "The value of vRtrIfDhcpClRtAddrType indicates the address type of
         vRtrIfDhcpClRtAddr."
    ::= { vRtrIfDhcpClRtEntry 1 }

vRtrIfDhcpClRtAddr               OBJECT-TYPE
    SYNTAX      InetAddress (SIZE (0|4))
    MAX-ACCESS  not-accessible
    STATUS      current
    DESCRIPTION
        "The value of vRtrIfDhcpClRtAddr indicates the IP address of the route."
    ::= { vRtrIfDhcpClRtEntry 2 }

vRtrIfDhcpClRtPrefixLen          OBJECT-TYPE
    SYNTAX      InetAddressPrefixLength
    MAX-ACCESS  not-accessible
    STATUS      current
    DESCRIPTION
        "The value of vRtrIfDhcpClRtPrefixLen indicates the prefix length of
         the subnet associated with vRtrIfDhcpClRtAddr."
    ::= { vRtrIfDhcpClRtEntry 3 }

vRtrIfDhcpClRtNhAddrType         OBJECT-TYPE
    SYNTAX      InetAddressType
    MAX-ACCESS  not-accessible
    STATUS      current
    DESCRIPTION
        "The value of vRtrIfDhcpClRtNhAddrType indicates the address type of
         vRtrIfDhcpClRtNhAddr."
    ::= { vRtrIfDhcpClRtEntry 4 }

vRtrIfDhcpClRtNhAddr             OBJECT-TYPE
    SYNTAX      InetAddress (SIZE (0|4))
    MAX-ACCESS  not-accessible
    STATUS      current
    DESCRIPTION
        "The value of vRtrIfDhcpClRtNhAddr indicates the IP address of the next
         hop."
    ::= { vRtrIfDhcpClRtEntry 5 }

vRtrIfDhcpClRtStatus             OBJECT-TYPE
    SYNTAX      INTEGER {
        installed              (1),
        invalid                (2),
        noRouteToNexthop       (3),
        errorInternal          (4),
        errorOutOfMemory       (5),
        errorInstallCheck      (6),
        errorInstallInternal   (7),
        errorUninstallCheck    (8),
        errorUninstallInternal (9),
        lowerServerId          (10)
    }
    MAX-ACCESS  read-only
    STATUS      current
    DESCRIPTION
        "The value of vRtrIfDhcpClRtStatus indicates the state of this route.

         A value of 'installed' indicates the received route is valid, and is
         successfully installed in the route table.

         A value of 'invalid' indicates that the received route is invalid for
         this DHCP client, and no attempt is made to install it in the route
         table.

         A value of 'noRouteToNexthop' indicates that the route is valid, but
         the next hop is unreachable, and no attempt is made to install it in
         the route table.

         A value of 'errorInternal' indicates that the system encountered a
         generic error attempting to install the route in the route table.

         A value of 'errorInstallCheck' indicates that the system encountered a
         configuration validation check error attempting to install the route
         in the route table.

         A value of 'errorInstallInternal' indicates that the system
         encountered a runtime validation error attempting to install the route
         in the route table.

         A value of 'errorUninstallCheck' indicates that the system encountered
         a configuration validation check error attempting to uninstall the
         route in the route table.

         A value of 'errorUninstallInternal' indicates that the system
         encountered a runtime validation error attempting to uninstall the
         route in the route table.

         A value of 'lowerServerId' indicates that the route is valid but the
         server id of the DHCP server that sent the route is higher than the
         server id of another route that is installed in the route table."
    ::= { vRtrIfDhcpClRtEntry 6 }

vRtrIfDhcp6ClStatsTable          OBJECT-TYPE
    SYNTAX      SEQUENCE OF VRtrIfDhcp6ClStatsEntry
    MAX-ACCESS  not-accessible
    STATUS      current
    DESCRIPTION
        "The vRtrIfDhcp6ClStatsTable contains DHCPv6 client statistics.

         Conceptual rows in this table are created and destroyed automatically
         by the system, when DHCP6 clients are enabled and disabled by means of
         the Boot Options File (BOF)."
    ::= { tmnxVrtrDhcpClient 10 }

vRtrIfDhcp6ClStatsEntry          OBJECT-TYPE
    SYNTAX      VRtrIfDhcp6ClStatsEntry
    MAX-ACCESS  not-accessible
    STATUS      current
    DESCRIPTION
        "Each row contains statistics of a particular DHCPv6 client instance."
    INDEX       {
        vRtrID,
        vRtrIfIndex
    }
    ::= { vRtrIfDhcp6ClStatsTable 1 }

VRtrIfDhcp6ClStatsEntry          ::= SEQUENCE
{
    vRtrIfDhcp6ClStatsClearedTime    TimeStamp,
    vRtrIfDhcp6ClStatsTxSolicits     Counter64,
    vRtrIfDhcp6ClStatsRxAdvertises   Counter64,
    vRtrIfDhcp6ClStatsTxRequests     Counter64,
    vRtrIfDhcp6ClStatsTxConfirms     Counter64,
    vRtrIfDhcp6ClStatsTxRenews       Counter64,
    vRtrIfDhcp6ClStatsTxRebinds      Counter64,
    vRtrIfDhcp6ClStatsRxReplies      Counter64,
    vRtrIfDhcp6ClStatsTxReleases     Counter64,
    vRtrIfDhcp6ClStatsTxDeclines     Counter64,
    vRtrIfDhcp6ClStatsRxReconfigures Counter64,
    vRtrIfDhcp6ClStatsTxInfRequests  Counter64,
    vRtrIfDhcp6ClStatsRxDrops        Counter64
}

vRtrIfDhcp6ClStatsClearedTime    OBJECT-TYPE
    SYNTAX      TimeStamp
    MAX-ACCESS  read-only
    STATUS      current
    DESCRIPTION
        "The value of vRtrIfDhcp6ClStatsClearedTime indicates the sysUpTime at
         the time the counters in this conceptual row were cleared for the last
         time.

         If the counters were never cleared, the value of
         vRtrIfDhcp6ClStatsClearedTime is zero."
    ::= { vRtrIfDhcp6ClStatsEntry 1 }

vRtrIfDhcp6ClStatsTxSolicits     OBJECT-TYPE
    SYNTAX      Counter64
    MAX-ACCESS  read-only
    STATUS      current
    DESCRIPTION
        "The value of vRtrIfDhcp6ClStatsTxSolicits indicates the number of
         SOLICIT messages the DHCPv6 has sent."
    ::= { vRtrIfDhcp6ClStatsEntry 2 }

vRtrIfDhcp6ClStatsRxAdvertises   OBJECT-TYPE
    SYNTAX      Counter64
    MAX-ACCESS  read-only
    STATUS      current
    DESCRIPTION
        "The value of vRtrIfDhcp6ClStatsRxAdvertises indicates the number of
         ADVERTISE messages the DHCPv6 client has received."
    ::= { vRtrIfDhcp6ClStatsEntry 3 }

vRtrIfDhcp6ClStatsTxRequests     OBJECT-TYPE
    SYNTAX      Counter64
    MAX-ACCESS  read-only
    STATUS      current
    DESCRIPTION
        "The value of vRtrIfDhcp6ClStatsTxRequests indicates the number of
         REQUEST messages the DHCPv6 client has sent."
    ::= { vRtrIfDhcp6ClStatsEntry 4 }

vRtrIfDhcp6ClStatsTxConfirms     OBJECT-TYPE
    SYNTAX      Counter64
    MAX-ACCESS  read-only
    STATUS      current
    DESCRIPTION
        "The value of vRtrIfDhcp6ClStatsTxConfirms indicates the number of
         CONFIRM messages the DHCPv6 client has sent."
    ::= { vRtrIfDhcp6ClStatsEntry 5 }

vRtrIfDhcp6ClStatsTxRenews       OBJECT-TYPE
    SYNTAX      Counter64
    MAX-ACCESS  read-only
    STATUS      current
    DESCRIPTION
        "The value of vRtrIfDhcp6ClStatsTxRenews indicates the number of RENEW
         messages the DHCPv6 client has sent."
    ::= { vRtrIfDhcp6ClStatsEntry 6 }

vRtrIfDhcp6ClStatsTxRebinds      OBJECT-TYPE
    SYNTAX      Counter64
    MAX-ACCESS  read-only
    STATUS      current
    DESCRIPTION
        "The value of vRtrIfDhcp6ClStatsTxRebinds indicates the number of
         REBIND messages the DHCPv6 client has sent."
    ::= { vRtrIfDhcp6ClStatsEntry 7 }

vRtrIfDhcp6ClStatsRxReplies      OBJECT-TYPE
    SYNTAX      Counter64
    MAX-ACCESS  read-only
    STATUS      current
    DESCRIPTION
        "The value of vRtrIfDhcp6ClStatsRxReplies indicates the number of REPLY
         messages the DHCPv6 client has received."
    ::= { vRtrIfDhcp6ClStatsEntry 8 }

vRtrIfDhcp6ClStatsTxReleases     OBJECT-TYPE
    SYNTAX      Counter64
    MAX-ACCESS  read-only
    STATUS      current
    DESCRIPTION
        "The value of vRtrIfDhcp6ClStatsTxReleases indicates the number of
         RELEASE messages the DHCPv6 client has sent."
    ::= { vRtrIfDhcp6ClStatsEntry 9 }

vRtrIfDhcp6ClStatsTxDeclines     OBJECT-TYPE
    SYNTAX      Counter64
    MAX-ACCESS  read-only
    STATUS      current
    DESCRIPTION
        "The value of vRtrIfDhcp6ClStatsTxDeclines indicates the number of
         DECLINE messages the DHCPv6 client has sent."
    ::= { vRtrIfDhcp6ClStatsEntry 10 }

vRtrIfDhcp6ClStatsRxReconfigures OBJECT-TYPE
    SYNTAX      Counter64
    MAX-ACCESS  read-only
    STATUS      current
    DESCRIPTION
        "The value of vRtrIfDhcp6ClStatsRxReconfigures indicates the number of
         RECONFIGURE messages the DHCPv6 client has received."
    ::= { vRtrIfDhcp6ClStatsEntry 11 }

vRtrIfDhcp6ClStatsTxInfRequests  OBJECT-TYPE
    SYNTAX      Counter64
    MAX-ACCESS  read-only
    STATUS      current
    DESCRIPTION
        "The value of vRtrIfDhcp6ClStatsTxInfRequests indicates the number of
         INFORMATION REQUEST messages the DHCPv6 client has sent."
    ::= { vRtrIfDhcp6ClStatsEntry 12 }

vRtrIfDhcp6ClStatsRxDrops        OBJECT-TYPE
    SYNTAX      Counter64
    MAX-ACCESS  read-only
    STATUS      current
    DESCRIPTION
        "The value of vRtrIfDhcp6ClStatsRxDrops indicates the number of DHCPv6
         messages the DHCPv6 client has received and dropped."
    ::= { vRtrIfDhcp6ClStatsEntry 13 }

vRtrIfDhcp6ClStateTable          OBJECT-TYPE
    SYNTAX      SEQUENCE OF VRtrIfDhcp6ClStateEntry
    MAX-ACCESS  not-accessible
    STATUS      current
    DESCRIPTION
        "The vRtrIfDhcp6ClStateTable contains DHCP6 client status information.

         Conceptual rows in this table are created and destroyed automatically
         by the system, when DHCP6 clients are enabled and disabled by means of
         the Boot Options File (BOF)."
    ::= { tmnxVrtrDhcpClient 11 }

vRtrIfDhcp6ClStateEntry          OBJECT-TYPE
    SYNTAX      VRtrIfDhcp6ClStateEntry
    MAX-ACCESS  not-accessible
    STATUS      current
    DESCRIPTION
        "Each row contains status information of a particular DHCP client
         instance."
    INDEX       {
        vRtrID,
        vRtrIfIndex
    }
    ::= { vRtrIfDhcp6ClStateTable 1 }

VRtrIfDhcp6ClStateEntry          ::= SEQUENCE
{
    vRtrIfDhcp6ClStateCiAddrType     InetAddressType,
    vRtrIfDhcp6ClStateCiAddr         InetAddress,
    vRtrIfDhcp6ClStateCiAddrMaskLen  Unsigned32,
    vRtrIfDhcp6ClStateClientDuid     OCTET STRING,
    vRtrIfDhcp6ClStateSiAddrType     InetAddressType,
    vRtrIfDhcp6ClStateSiAddr         InetAddress,
    vRtrIfDhcp6ClStateServerDuid     OCTET STRING,
    vRtrIfDhcp6ClStateDnsPriAddrType InetAddressType,
    vRtrIfDhcp6ClStateDnsPriAddr     InetAddress,
    vRtrIfDhcp6ClStateDnsSecAddrType InetAddressType,
    vRtrIfDhcp6ClStateDnsSecAddr     InetAddress,
    vRtrIfDhcp6ClStateDnsTerAddrType InetAddressType,
    vRtrIfDhcp6ClStateDnsTerAddr     InetAddress,
    vRtrIfDhcp6ClStateLeaseCreated   DateAndTimeOrEmpty,
    vRtrIfDhcp6ClStateLeaseAcquired  DateAndTimeOrEmpty,
    vRtrIfDhcp6ClStateLeaseRenew     DateAndTimeOrEmpty,
    vRtrIfDhcp6ClStateLeaseRebind    DateAndTimeOrEmpty,
    vRtrIfDhcp6ClStateLeasePrefLftm  DateAndTimeOrEmpty,
    vRtrIfDhcp6ClStateLeaseValidLftm DateAndTimeOrEmpty,
    vRtrIfDhcp6ClStateStatus         INTEGER,
    vRtrIfDhcp6ClStateDescription    DisplayString
}

vRtrIfDhcp6ClStateCiAddrType     OBJECT-TYPE
    SYNTAX      InetAddressType
    MAX-ACCESS  read-only
    STATUS      current
    DESCRIPTION
        "The value of vRtrIfDhcp6ClStateCiAddrType indicates the address type
         of vRtrIfDhcp6ClStateCiAddr."
    ::= { vRtrIfDhcp6ClStateEntry 1 }

vRtrIfDhcp6ClStateCiAddr         OBJECT-TYPE
    SYNTAX      InetAddress (SIZE (0|4|16))
    MAX-ACCESS  read-only
    STATUS      current
    DESCRIPTION
        "The value of vRtrIfDhcp6ClStateCiAddr indicates the client IP address."
    ::= { vRtrIfDhcp6ClStateEntry 2 }

vRtrIfDhcp6ClStateCiAddrMaskLen  OBJECT-TYPE
    SYNTAX      Unsigned32 (0..128)
    MAX-ACCESS  read-only
    STATUS      current
    DESCRIPTION
        "The value of vRtrIfDhcp6ClStateCiAddrMaskLen indicates the length of
         the subnet mask for a DHCP lease, or the prefix length for a DHCPv6
         lease."
    ::= { vRtrIfDhcp6ClStateEntry 3 }

vRtrIfDhcp6ClStateClientDuid     OBJECT-TYPE
    SYNTAX      OCTET STRING (SIZE (0..129))
    MAX-ACCESS  read-only
    STATUS      current
    DESCRIPTION
        "The value vRtrIfDhcp6ClStateClientDuid specifies the variable length
         identifier used by this client."
    REFERENCE
        "RFC 3315 paragraph 22.2. 'Client Identifier Option',
         paragraph 9.3,
         paragraph 9.1 'A DUID can be no more than 128 octets long (not including the type code)''"
    ::= { vRtrIfDhcp6ClStateEntry 4 }

vRtrIfDhcp6ClStateSiAddrType     OBJECT-TYPE
    SYNTAX      InetAddressType
    MAX-ACCESS  read-only
    STATUS      current
    DESCRIPTION
        "The value of vRtrIfDhcp6ClStateSiAddrType indicates the address type
         of vRtrIfDhcp6ClStateSiAddr."
    ::= { vRtrIfDhcp6ClStateEntry 5 }

vRtrIfDhcp6ClStateSiAddr         OBJECT-TYPE
    SYNTAX      InetAddress (SIZE (0|4|16))
    MAX-ACCESS  read-only
    STATUS      current
    DESCRIPTION
        "The value of vRtrIfDhcp6ClStateSiAddr indicates the Server Identifier."
    ::= { vRtrIfDhcp6ClStateEntry 6 }

vRtrIfDhcp6ClStateServerDuid     OBJECT-TYPE
    SYNTAX      OCTET STRING (SIZE (0..129))
    MAX-ACCESS  read-only
    STATUS      current
    DESCRIPTION
        "The value vRtrIfDhcp6ClStateServerDuid specifies the variable length
         identifier used by the server."
    REFERENCE
        "RFC 3315 paragraph 22.3. 'Server Identifier Option',
         paragraph 9.3,
         paragraph 9.1 'A DUID can be no more than 128 octets long (not including the type code)''"
    ::= { vRtrIfDhcp6ClStateEntry 7 }

vRtrIfDhcp6ClStateDnsPriAddrType OBJECT-TYPE
    SYNTAX      InetAddressType
    MAX-ACCESS  read-only
    STATUS      current
    DESCRIPTION
        "The value of vRtrIfDhcp6ClStateDnsPriAddrType indicates the address
         type of vRtrIfDhcp6ClStateDnsPriAddr."
    ::= { vRtrIfDhcp6ClStateEntry 8 }

vRtrIfDhcp6ClStateDnsPriAddr     OBJECT-TYPE
    SYNTAX      InetAddress (SIZE (0|4|16))
    MAX-ACCESS  read-only
    STATUS      current
    DESCRIPTION
        "The value of vRtrIfDhcp6ClStateDnsPriAddr indicates the address of the
         primary IPv6 DNS server."
    REFERENCE
        "RFC 3646 DNS Configuration options for Dynamic Host Configuration Protocol for IPv6 (DHCPv6)
         3. DNS Recursive Name Server option"
    ::= { vRtrIfDhcp6ClStateEntry 9 }

vRtrIfDhcp6ClStateDnsSecAddrType OBJECT-TYPE
    SYNTAX      InetAddressType
    MAX-ACCESS  read-only
    STATUS      current
    DESCRIPTION
        "The value of vRtrIfDhcp6ClStateDnsSecAddrType indicates the address
         type of vRtrIfDhcp6ClStateDnsSecAddr."
    ::= { vRtrIfDhcp6ClStateEntry 10 }

vRtrIfDhcp6ClStateDnsSecAddr     OBJECT-TYPE
    SYNTAX      InetAddress (SIZE (0|4|16))
    MAX-ACCESS  read-only
    STATUS      current
    DESCRIPTION
        "The value of vRtrIfDhcp6ClStateDnsSecAddr indicates the address of the
         secondary IPv6 DNS server."
    REFERENCE
        "RFC 3646 DNS Configuration options for Dynamic Host Configuration Protocol for IPv6 (DHCPv6)
         3. DNS Recursive Name Server option"
    ::= { vRtrIfDhcp6ClStateEntry 11 }

vRtrIfDhcp6ClStateDnsTerAddrType OBJECT-TYPE
    SYNTAX      InetAddressType
    MAX-ACCESS  read-only
    STATUS      current
    DESCRIPTION
        "The value of vRtrIfDhcp6ClStateDnsTerAddrType indicates the address
         type of vRtrIfDhcp6ClStateDnsTerAddr."
    ::= { vRtrIfDhcp6ClStateEntry 12 }

vRtrIfDhcp6ClStateDnsTerAddr     OBJECT-TYPE
    SYNTAX      InetAddress (SIZE (0|4|16))
    MAX-ACCESS  read-only
    STATUS      current
    DESCRIPTION
        "The value of vRtrIfDhcp6ClStateDnsTerAddr indicates the address of the
         tertiary IPv6 DNS server."
    REFERENCE
        "RFC 3646 DNS Configuration options for Dynamic Host Configuration Protocol for IPv6 (DHCPv6)
         3. DNS Recursive Name Server option"
    ::= { vRtrIfDhcp6ClStateEntry 13 }

vRtrIfDhcp6ClStateLeaseCreated   OBJECT-TYPE
    SYNTAX      DateAndTimeOrEmpty
    MAX-ACCESS  read-only
    STATUS      current
    DESCRIPTION
        "The value of vRtrIfDhcp6ClStateLeaseCreated indicates the UTC date
         when the latest DHCP lease was first obtained from the server. The
         address of the server is indicated by vRtrIfDhcp6ClStateSiAddr."
    ::= { vRtrIfDhcp6ClStateEntry 14 }

vRtrIfDhcp6ClStateLeaseAcquired  OBJECT-TYPE
    SYNTAX      DateAndTimeOrEmpty
    MAX-ACCESS  read-only
    STATUS      current
    DESCRIPTION
        "The value of vRtrIfDhcp6ClStateLeaseAcquired indicates the UTC date
         when the latest DHCP lease was acquired from the server. The address
         of the server is indicated by vRtrIfDhcp6ClStateSiAddr.

         The value of vRtrIfDhcp6ClStateLeaseAcquired can be the time when the
         DHCP lease was first obtained, or the time when the lease was renewed
         or rebound."
    ::= { vRtrIfDhcp6ClStateEntry 15 }

vRtrIfDhcp6ClStateLeaseRenew     OBJECT-TYPE
    SYNTAX      DateAndTimeOrEmpty
    MAX-ACCESS  read-only
    STATUS      current
    DESCRIPTION
        "The value of vRtrIfDhcp6ClStateLeaseRenew indicates the UTC date when
         the current DHCP lease needs to be renewed."
    ::= { vRtrIfDhcp6ClStateEntry 16 }

vRtrIfDhcp6ClStateLeaseRebind    OBJECT-TYPE
    SYNTAX      DateAndTimeOrEmpty
    MAX-ACCESS  read-only
    STATUS      current
    DESCRIPTION
        "The value of vRtrIfDhcp6ClStateLeaseRebind indicates the UTC date when
         the current DHCP lease needs to be rebound."
    ::= { vRtrIfDhcp6ClStateEntry 17 }

vRtrIfDhcp6ClStateLeasePrefLftm  OBJECT-TYPE
    SYNTAX      DateAndTimeOrEmpty
    MAX-ACCESS  read-only
    STATUS      current
    DESCRIPTION
        "The value of vRtrIfDhcp6ClStateLeasePrefLftm indicates the UTC date
         when the preferred lifetime of the private IP address (i.e.,
         vRtrIfDhcp6ClStateCiAddr) will expire.

         In the preferred state, vRtrIfDhcp6ClStateCiAddr can be used without
         any restriction. Once the lifetime expires, vRtrIfDhcp6ClStateCiAddr
         is still valid, but needs to be renewed or rebound."
    REFERENCE
        "RFC 4862. 'IPv6 Stateless Address Autoconfiguration', IETF, September
         2007."
    ::= { vRtrIfDhcp6ClStateEntry 18 }

vRtrIfDhcp6ClStateLeaseValidLftm OBJECT-TYPE
    SYNTAX      DateAndTimeOrEmpty
    MAX-ACCESS  read-only
    STATUS      current
    DESCRIPTION
        "The value of vRtrIfDhcp6ClStateLeaseValidLftm indicates the UTC date
         when the valid lifetime of the private IP address (i.e.,
         vRtrIfDhcp6ClStateCiAddr) will expire.

         Once the valid lifetime expires, vRtrIfDhcp6ClStateCiAddr must be
         renewed or rebound."
    REFERENCE
        "RFC 4862. 'IPv6 Stateless Address Autoconfiguration', IETF, September
         2007."
    ::= { vRtrIfDhcp6ClStateEntry 19 }

vRtrIfDhcp6ClStateStatus         OBJECT-TYPE
    SYNTAX      INTEGER {
        disabled     (0),
        initializing (1),
        requesting   (2),
        lost         (3),
        established  (4),
        failed       (5),
        released     (6)
    }
    MAX-ACCESS  read-only
    STATUS      current
    DESCRIPTION
        "The value of vRtrIfDhcp6ClStateStatus indicates the status of the DHCP
         client."
    ::= { vRtrIfDhcp6ClStateEntry 20 }

vRtrIfDhcp6ClStateDescription    OBJECT-TYPE
    SYNTAX      DisplayString (SIZE (0..255))
    MAX-ACCESS  read-only
    STATUS      current
    DESCRIPTION
        "The value of vRtrIfDhcp6ClStateDescription indicates the description
         of the status of this DHCP client.

         It may describe the cause of the problem while the value of the object
         vRtrIfDhcp6ClStateStatus is equal to 'failed'."
    ::= { vRtrIfDhcp6ClStateEntry 21 }

tmnxVrtrRouterAdvertisement      OBJECT IDENTIFIER ::= { tmnxVrtrAutoconfiguration 2 }

vRtrAutoCfgRaRtTable             OBJECT-TYPE
    SYNTAX      SEQUENCE OF VRtrAutoCfgRaRtEntry
    MAX-ACCESS  not-accessible
    STATUS      current
    DESCRIPTION
        "The vRtrAutoCfgRaRtTable contains routes received by means of the
         Neighbor Discovery Protocol inside Router Advertisements.

         Conceptual rows in this table are created and destroyed automatically
         by the system."
    ::= { tmnxVrtrRouterAdvertisement 1 }

vRtrAutoCfgRaRtEntry             OBJECT-TYPE
    SYNTAX      VRtrAutoCfgRaRtEntry
    MAX-ACCESS  not-accessible
    STATUS      current
    DESCRIPTION
        "Each row contains information about a particular Router Advertisement
         client route."
    INDEX       {
        vRtrID,
        vRtrAutoCfgRaRtAddrType,
        vRtrAutoCfgRaRtAddr,
        vRtrAutoCfgRaRtPrefixLen,
        vRtrAutoCfgRaRtNhAddrType,
        vRtrAutoCfgRaRtNhAddr
    }
    ::= { vRtrAutoCfgRaRtTable 1 }

VRtrAutoCfgRaRtEntry             ::= SEQUENCE
{
    vRtrAutoCfgRaRtAddrType          InetAddressType,
    vRtrAutoCfgRaRtAddr              InetAddress,
    vRtrAutoCfgRaRtPrefixLen         InetAddressPrefixLength,
    vRtrAutoCfgRaRtNhAddrType        InetAddressType,
    vRtrAutoCfgRaRtNhAddr            InetAddressIPv6z,
    vRtrAutoCfgRaRtStatus            INTEGER,
    vRtrAutoCfgRaRtTimer             Unsigned32
}

vRtrAutoCfgRaRtAddrType          OBJECT-TYPE
    SYNTAX      InetAddressType
    MAX-ACCESS  not-accessible
    STATUS      current
    DESCRIPTION
        "The value of vRtrAutoCfgRaRtAddrType indicates the address type of
         vRtrAutoCfgRaRtAddr."
    ::= { vRtrAutoCfgRaRtEntry 1 }

vRtrAutoCfgRaRtAddr              OBJECT-TYPE
    SYNTAX      InetAddress (SIZE (0|16))
    MAX-ACCESS  not-accessible
    STATUS      current
    DESCRIPTION
        "The value of vRtrAutoCfgRaRtAddr indicates the IP address of the
         route."
    ::= { vRtrAutoCfgRaRtEntry 2 }

vRtrAutoCfgRaRtPrefixLen         OBJECT-TYPE
    SYNTAX      InetAddressPrefixLength
    MAX-ACCESS  not-accessible
    STATUS      current
    DESCRIPTION
        "The value of vRtrAutoCfgRaRtPrefixLen indicates the prefix length of
         the subnet associated with vRtrAutoCfgRaRtAddr."
    ::= { vRtrAutoCfgRaRtEntry 3 }

vRtrAutoCfgRaRtNhAddrType        OBJECT-TYPE
    SYNTAX      InetAddressType
    MAX-ACCESS  not-accessible
    STATUS      current
    DESCRIPTION
        "The value of vRtrAutoCfgRaRtNhAddrType indicates the address type of
         vRtrAutoCfgRaRtNhAddr."
    ::= { vRtrAutoCfgRaRtEntry 4 }

vRtrAutoCfgRaRtNhAddr            OBJECT-TYPE
    SYNTAX      InetAddressIPv6z
    MAX-ACCESS  not-accessible
    STATUS      current
    DESCRIPTION
        "The value of vRtrAutoCfgRaRtNhAddr indicates the IP address of the
         next hop."
    ::= { vRtrAutoCfgRaRtEntry 5 }

vRtrAutoCfgRaRtStatus            OBJECT-TYPE
    SYNTAX      INTEGER {
        installed              (1),
        invalid                (2),
        interfaceDown          (3),
        errorInternal          (4),
        errorOutOfMemory       (5),
        errorInstallCheck      (6),
        errorInstallInternal   (7),
        errorUninstallCheck    (8),
        errorUninstallInternal (9),
        expired                (10),
        standby                (11),
        lowerPreference        (12)
    }
    MAX-ACCESS  read-only
    STATUS      current
    DESCRIPTION
        "The value of vRtrAutoCfgRaRtStatus indicates the state of this route.

         A value of 'installed' indicates the received route is valid, and is
         successfully installed in the route table.

         A value of 'invalid' indicates that the received route is invalid for
         this DHCP client, and no attempt is made to install it in the route
         table.

         A value of 'errorInternal' indicates that the system encountered a
         generic error attempting to install the route in the route table.

         A value of 'errorInstallCheck' indicates that the system encountered a
         configuration validation check error attempting to install the route
         in the route table.

         A value of 'errorInstallInternal' indicates that the system
         encountered a runtime validation error attempting to install the route
         in the route table.

         A value of 'errorUninstallCheck' indicates that the system encountered
         a configuration validation check error attempting to uninstall the
         route in the route table.

         A value of 'errorUninstallInternal' indicates that the system
         encountered a runtime validation error attempting to uninstall the
         route in the route table.

         A value of 'expired' indicates the received route got uninstalled from
         the route table after lifetime expiry.

         A value of 'standby' indicates that the route is valid but the
         preference of the route is the same as the preference of another route
         that is already installed in the route table and no attempt is made to
         install it.

         A value of 'lowerPreference' indicates that the route is valid but the
         preference of the route is lower than the preference of another route
         that is already installed in the route table and no attempt is made to
         install it."
    ::= { vRtrAutoCfgRaRtEntry 6 }

vRtrAutoCfgRaRtTimer             OBJECT-TYPE
    SYNTAX      Unsigned32 (0..4294967295)
    UNITS       "seconds"
    MAX-ACCESS  read-only
    STATUS      current
    DESCRIPTION
        "The value of vRtrAutoCfgRaRtTimer indicates how much longer a route
         entry remains installed. It is initially set to the route lifetime.

         A value of 4294967295 represents infinity."
    ::= { vRtrAutoCfgRaRtEntry 8 }

vRtrAutoCfgRaRouterTable         OBJECT-TYPE
    SYNTAX      SEQUENCE OF VRtrAutoCfgRaRouterEntry
    MAX-ACCESS  not-accessible
    STATUS      current
    DESCRIPTION
        "The vRtrAutoCfgRaRouterTable contains IPv6 routers that sent by means
         of the Neighbor Discovery Protocol inside Router Advertisements.

         Conceptual rows in this table are created and destroyed automatically
         by the system.

         The value of the objects in this table is ignored by the Nokia SROS
         series with the exception of the value of objects
         vRtrAutoCfgRaRouterLifetime, vRtrAutoCfgRaRouterPreference, ."
    ::= { tmnxVrtrRouterAdvertisement 2 }

vRtrAutoCfgRaRouterEntry         OBJECT-TYPE
    SYNTAX      VRtrAutoCfgRaRouterEntry
    MAX-ACCESS  not-accessible
    STATUS      current
    DESCRIPTION
        "An entry in the vRtrAutoCfgRaRouterTable."
    INDEX       {
        vRtrID,
        vRtrAutoCfgRaRouterNbrAddrType,
        vRtrAutoCfgRaRouterNbrAddr
    }
    ::= { vRtrAutoCfgRaRouterTable 1 }

VRtrAutoCfgRaRouterEntry         ::= SEQUENCE
{
    vRtrAutoCfgRaRouterNbrAddrType   InetAddressType,
    vRtrAutoCfgRaRouterNbrAddr       InetAddressIPv6z,
    vRtrAutoCfgRaRouterIfIndex       InterfaceIndex,
    vRtrAutoCfgRaRouterCurHopLimit   Unsigned32,
    vRtrAutoCfgRaRouterManagedFlag   TruthValue,
    vRtrAutoCfgRaRouterOtherCfgFlag  TruthValue,
    vRtrAutoCfgRaRouterPreference    INTEGER,
    vRtrAutoCfgRaRouterLifetime      Unsigned32,
    vRtrAutoCfgRaRouterReachableTime Unsigned32,
    vRtrAutoCfgRaRouterRetransTimer  Unsigned32
}

vRtrAutoCfgRaRouterNbrAddrType   OBJECT-TYPE
    SYNTAX      InetAddressType
    MAX-ACCESS  not-accessible
    STATUS      current
    DESCRIPTION
        "The value of vRtrAutoCfgRaRouterNbrAddrType indicates the address type
         of vRtrAutoCfgRaRouterNbrAddr."
    ::= { vRtrAutoCfgRaRouterEntry 2 }

vRtrAutoCfgRaRouterNbrAddr       OBJECT-TYPE
    SYNTAX      InetAddressIPv6z
    MAX-ACCESS  not-accessible
    STATUS      current
    DESCRIPTION
        "The value of vRtrAutoCfgRaRouterNbrAddr indicates the IP address of
         the source router."
    ::= { vRtrAutoCfgRaRouterEntry 3 }

vRtrAutoCfgRaRouterIfIndex       OBJECT-TYPE
    SYNTAX      InterfaceIndex
    MAX-ACCESS  read-only
    STATUS      current
    DESCRIPTION
        "The index value which uniquely identifies the interface on
         which this router originated.  The interface identified
         by a particular value of this index is the same interface as
         identified by the same value of the IF-MIB's ifIndex."
    ::= { vRtrAutoCfgRaRouterEntry 4 }

vRtrAutoCfgRaRouterCurHopLimit   OBJECT-TYPE
    SYNTAX      Unsigned32
    MAX-ACCESS  read-only
    STATUS      current
    DESCRIPTION
        "The default value that should be placed in the Hop Count field of the
         IP header for outgoing IP packets."
    REFERENCE
        "For IPv6 RFC4861, especially section 4.2  Router Advertisement Message Format"
    ::= { vRtrAutoCfgRaRouterEntry 5 }

vRtrAutoCfgRaRouterManagedFlag   OBJECT-TYPE
    SYNTAX      TruthValue
    MAX-ACCESS  read-only
    STATUS      current
    DESCRIPTION
        "This object has the value 'true(1)', if addresses are available via
         Dynamic Host Configuration Protocol [DHCPv6] and the value 'false(2)'
         otherwise."
    REFERENCE
        "For IPv6 RFC4861, especially section 4.2  Router Advertisement Message Format"
    ::= { vRtrAutoCfgRaRouterEntry 6 }

vRtrAutoCfgRaRouterOtherCfgFlag  OBJECT-TYPE
    SYNTAX      TruthValue
    MAX-ACCESS  read-only
    STATUS      current
    DESCRIPTION
        "Other configuration flag. When true(1),
         indicates that other configuration information is
         available via DHCPv6.  Examples of such information
         are DNS-related information or information on other
         servers within the network. Value is false(2) otherwise."
    REFERENCE
        "For IPv6 RFC4861, especially section 4.2  Router Advertisement Message Format"
    ::= { vRtrAutoCfgRaRouterEntry 7 }

vRtrAutoCfgRaRouterPreference    OBJECT-TYPE
    SYNTAX      INTEGER {
        high     (1),
        medium   (2),
        low      (3),
        reserved (4)
    }
    MAX-ACCESS  read-only
    STATUS      current
    DESCRIPTION
        "The value of vRtrAutoCfgRaRouterPreference indicates whether to prefer
         this router over other default routers. ."
    REFERENCE
        "For IPv6 RFC4191, especially section 2.2.  Changes to Router Advertisement Message Format"
    ::= { vRtrAutoCfgRaRouterEntry 8 }

vRtrAutoCfgRaRouterLifetime      OBJECT-TYPE
    SYNTAX      Unsigned32
    UNITS       "seconds"
    MAX-ACCESS  read-only
    STATUS      current
    DESCRIPTION
        "The lifetime associated with the default router.

         A value of 4,294,967,295 represents infinity.

         A Lifetime of 0 indicates that the router is not a default router."
    REFERENCE
        "For IPv6 RFC4861, especially section 4.2  Router Advertisement Message Format"
    ::= { vRtrAutoCfgRaRouterEntry 9 }

vRtrAutoCfgRaRouterReachableTime OBJECT-TYPE
    SYNTAX      Unsigned32
    UNITS       "milliseconds"
    MAX-ACCESS  read-only
    STATUS      current
    DESCRIPTION
        "The time that a node assumes a neighbor is reachable after having
         received a reachability confirmation."
    REFERENCE
        "For IPv6 RFC4861, especially section 4.2  Router Advertisement Message Format"
    ::= { vRtrAutoCfgRaRouterEntry 10 }

vRtrAutoCfgRaRouterRetransTimer  OBJECT-TYPE
    SYNTAX      Unsigned32
    UNITS       "milliseconds"
    MAX-ACCESS  read-only
    STATUS      current
    DESCRIPTION
        "The time between retransmitted Neighbor Solicitation messages."
    REFERENCE
        "For IPv6 RFC4861, especially section 4.2  Router Advertisement Message Format"
    ::= { vRtrAutoCfgRaRouterEntry 11 }

vRtrAutoCfgRaPrefixTable         OBJECT-TYPE
    SYNTAX      SEQUENCE OF VRtrAutoCfgRaPrefixEntry
    MAX-ACCESS  not-accessible
    STATUS      current
    DESCRIPTION
        "The vRtrAutoCfgRaPrefixTable contains IPv6 prefixes received by means
         of the Neighbor Discovery Protocol inside Router Advertisements.

         Conceptual rows in this table are created and destroyed automatically
         by the system.

         The value of the objects in this table is ignored by the Nokia SROS
         series."
    ::= { tmnxVrtrRouterAdvertisement 3 }

vRtrAutoCfgRaPrefixEntry         OBJECT-TYPE
    SYNTAX      VRtrAutoCfgRaPrefixEntry
    MAX-ACCESS  not-accessible
    STATUS      current
    DESCRIPTION
        "An entry in the vRtrAutoCfgRaPrefixTable."
    INDEX       {
        vRtrID,
        vRtrAutoCfgRaPrefixNbrAddrType,
        vRtrAutoCfgRaPrefixNbrAddr,
        vRtrAutoCfgRaPrefixPrefix,
        vRtrAutoCfgRaPrefixLength
    }
    ::= { vRtrAutoCfgRaPrefixTable 1 }

VRtrAutoCfgRaPrefixEntry         ::= SEQUENCE
{
    vRtrAutoCfgRaPrefixNbrAddrType   InetAddressType,
    vRtrAutoCfgRaPrefixNbrAddr       InetAddressIPv6z,
    vRtrAutoCfgRaPrefixPrefix        InetAddress,
    vRtrAutoCfgRaPrefixLength        InetAddressPrefixLength,
    vRtrAutoCfgRaPrefixIfIndex       InterfaceIndex,
    vRtrAutoCfgRaPrefixOnLinkFlag    TruthValue,
    vRtrAutoCfgRaPrefixAutonomFlag   TruthValue,
    vRtrAutoCfgRaPrefixPrefLftm      Unsigned32,
    vRtrAutoCfgRaPrefixValidLftm     Unsigned32
}

vRtrAutoCfgRaPrefixNbrAddrType   OBJECT-TYPE
    SYNTAX      InetAddressType
    MAX-ACCESS  not-accessible
    STATUS      current
    DESCRIPTION
        "The value of vRtrAutoCfgRaPrefixNbrAddrType indicates the address type
         of vRtrAutoCfgRaPrefixNbrAddr."
    ::= { vRtrAutoCfgRaPrefixEntry 2 }

vRtrAutoCfgRaPrefixNbrAddr       OBJECT-TYPE
    SYNTAX      InetAddressIPv6z
    MAX-ACCESS  not-accessible
    STATUS      current
    DESCRIPTION
        "The value of vRtrAutoCfgRaPrefixNbrAddr indicates the IP address of
         the source router."
    ::= { vRtrAutoCfgRaPrefixEntry 3 }

vRtrAutoCfgRaPrefixPrefix        OBJECT-TYPE
    SYNTAX      InetAddress (SIZE (16))
    MAX-ACCESS  not-accessible
    STATUS      current
    DESCRIPTION
        "The ipv6 address prefix. The length of this object is the standard
         length (16 bytes ) for IPv6 prefixes."
    ::= { vRtrAutoCfgRaPrefixEntry 4 }

vRtrAutoCfgRaPrefixLength        OBJECT-TYPE
    SYNTAX      InetAddressPrefixLength
    MAX-ACCESS  not-accessible
    STATUS      current
    DESCRIPTION
        "The prefix length associated with this prefix."
    REFERENCE
        "For IPv6 RFC2461, especially section 4.6.2. 'Prefix Information'
         'Prefix Length  8-bit unsigned integer.  The number of leading bits
          in the Prefix that are valid.  The value ranges
          from 0 to 128.'"
    ::= { vRtrAutoCfgRaPrefixEntry 5 }

vRtrAutoCfgRaPrefixIfIndex       OBJECT-TYPE
    SYNTAX      InterfaceIndex
    MAX-ACCESS  read-only
    STATUS      current
    DESCRIPTION
        "The index value which uniquely identifies the interface on
         which this prefix originated.  The interface identified
         by a particular value of this index is the same interface as
         identified by the same value of the IF-MIB's ifIndex."
    ::= { vRtrAutoCfgRaPrefixEntry 6 }

vRtrAutoCfgRaPrefixOnLinkFlag    OBJECT-TYPE
    SYNTAX      TruthValue
    MAX-ACCESS  read-only
    STATUS      current
    DESCRIPTION
        "This object has the value 'true(1)', if this prefix can be
         used  for on-link determination and the value 'false(2)'
         otherwise."
    REFERENCE
        "For IPv6 RFC2461, especially sections 2 and 4.6.2 and
         RFC2462"
    ::= { vRtrAutoCfgRaPrefixEntry 7 }

vRtrAutoCfgRaPrefixAutonomFlag   OBJECT-TYPE
    SYNTAX      TruthValue
    MAX-ACCESS  read-only
    STATUS      current
    DESCRIPTION
        "Autonomous address configuration flag. When true(1),
         indicates that this prefix can be used for autonomous
         address configuration (i.e. can be used to form a local
         interface address).  If false(2), it is not used to auto-
         configure a local interface address."
    REFERENCE
        "For IPv6 RFC2461, especially sections 2 and 4.6.2 and
         RFC2462"
    ::= { vRtrAutoCfgRaPrefixEntry 8 }

vRtrAutoCfgRaPrefixPrefLftm      OBJECT-TYPE
    SYNTAX      Unsigned32
    UNITS       "seconds"
    MAX-ACCESS  read-only
    STATUS      current
    DESCRIPTION
        "The length of time in seconds that this prefix is preferred.

         A value of 4,294,967,295 represents infinity."
    REFERENCE
        "For IPv6 RFC2461, especially sections 2 and 4.6.2 and
         RFC2462"
    ::= { vRtrAutoCfgRaPrefixEntry 9 }

vRtrAutoCfgRaPrefixValidLftm     OBJECT-TYPE
    SYNTAX      Unsigned32
    UNITS       "seconds"
    MAX-ACCESS  read-only
    STATUS      current
    DESCRIPTION
        "The length of time, in seconds, that this prefix is valid.

         A value of 4,294,967,295 represents infinity."
    REFERENCE
        "For IPv6 RFC2461, especially sections 2 and 4.6.2 and
         RFC2462"
    ::= { vRtrAutoCfgRaPrefixEntry 10 }

vRtrAutoCfgRaSpecRtTable         OBJECT-TYPE
    SYNTAX      SEQUENCE OF VRtrAutoCfgRaSpecRtEntry
    MAX-ACCESS  not-accessible
    STATUS      current
    DESCRIPTION
        "The vRtrAutoCfgRaSpecRtTable contains IPv6 more-specific routes
         received by means of the Neighbor Discovery Protocol inside Router
         Advertisements.

         Conceptual rows in this table are created and destroyed automatically
         by the system."
    ::= { tmnxVrtrRouterAdvertisement 4 }

vRtrAutoCfgRaSpecRtEntry         OBJECT-TYPE
    SYNTAX      VRtrAutoCfgRaSpecRtEntry
    MAX-ACCESS  not-accessible
    STATUS      current
    DESCRIPTION
        "An entry in the vRtrAutoCfgRaSpecRtTable."
    INDEX       {
        vRtrID,
        vRtrAutoCfgRaSpecRtNbrAddrType,
        vRtrAutoCfgRaSpecRtNbrAddr,
        vRtrAutoCfgRaSpecRtPrefix,
        vRtrAutoCfgRaSpecRtPrefixLength
    }
    ::= { vRtrAutoCfgRaSpecRtTable 1 }

VRtrAutoCfgRaSpecRtEntry         ::= SEQUENCE
{
    vRtrAutoCfgRaSpecRtNbrAddrType   InetAddressType,
    vRtrAutoCfgRaSpecRtNbrAddr       InetAddressIPv6z,
    vRtrAutoCfgRaSpecRtPrefix        InetAddress,
    vRtrAutoCfgRaSpecRtPrefixLength  InetAddressPrefixLength,
    vRtrAutoCfgRaSpecRtIfIndex       InterfaceIndex,
    vRtrAutoCfgRaSpecRtPreference    INTEGER,
    vRtrAutoCfgRaSpecRtLifetime      Unsigned32
}

vRtrAutoCfgRaSpecRtNbrAddrType   OBJECT-TYPE
    SYNTAX      InetAddressType
    MAX-ACCESS  not-accessible
    STATUS      current
    DESCRIPTION
        "The value of vRtrAutoCfgRaSpecRtNbrAddrType indicates the address type
         of vRtrAutoCfgRaSpecRtNbrAddr."
    ::= { vRtrAutoCfgRaSpecRtEntry 2 }

vRtrAutoCfgRaSpecRtNbrAddr       OBJECT-TYPE
    SYNTAX      InetAddressIPv6z
    MAX-ACCESS  not-accessible
    STATUS      current
    DESCRIPTION
        "The value of vRtrAutoCfgRaSpecRtNbrAddr indicates the IP address of
         the source router."
    ::= { vRtrAutoCfgRaSpecRtEntry 3 }

vRtrAutoCfgRaSpecRtPrefix        OBJECT-TYPE
    SYNTAX      InetAddress (SIZE (16))
    MAX-ACCESS  not-accessible
    STATUS      current
    DESCRIPTION
        "The ipv6 address prefix. The length of this object is the standard
         length (16 bytes ) for IPv6 prefixes."
    ::= { vRtrAutoCfgRaSpecRtEntry 4 }

vRtrAutoCfgRaSpecRtPrefixLength  OBJECT-TYPE
    SYNTAX      InetAddressPrefixLength
    MAX-ACCESS  not-accessible
    STATUS      current
    DESCRIPTION
        "The value of vRtrAutoCfgRaSpecRtPrefixLength indicates the prefix
         length of the subnet associated with this route."
    ::= { vRtrAutoCfgRaSpecRtEntry 5 }

vRtrAutoCfgRaSpecRtIfIndex       OBJECT-TYPE
    SYNTAX      InterfaceIndex
    MAX-ACCESS  read-only
    STATUS      current
    DESCRIPTION
        "The index value which uniquely identifies the interface on
         which this route originated.  The interface identified
         by a particular value of this index is the same interface as
         identified by the same value of the IF-MIB's ifIndex."
    ::= { vRtrAutoCfgRaSpecRtEntry 6 }

vRtrAutoCfgRaSpecRtPreference    OBJECT-TYPE
    SYNTAX      INTEGER {
        high     (1),
        medium   (2),
        low      (3),
        reserved (4)
    }
    MAX-ACCESS  read-only
    STATUS      current
    DESCRIPTION
        "The value of vRtrAutoCfgRaSpecRtPreference indicates the preference of
         this route."
    REFERENCE
        "For IPv6 RFC4191, especially section 2.1.  Preference Values"
    ::= { vRtrAutoCfgRaSpecRtEntry 7 }

vRtrAutoCfgRaSpecRtLifetime      OBJECT-TYPE
    SYNTAX      Unsigned32
    UNITS       "seconds"
    MAX-ACCESS  read-only
    STATUS      current
    DESCRIPTION
        "The length of time, in seconds, that this route is valid.

         When vRtrAutoCfgRaSpecRtLifetime has a value of zero, '0', the entry
         is uninstalled from the route table.

         A value of 4,294,967,295 represents infinity."
    REFERENCE
        "For IPv6 RFC4191, especially section 2.3. Route Information Option"
    ::= { vRtrAutoCfgRaSpecRtEntry 9 }

vRtrIfAutoCfgRaStatsTable        OBJECT-TYPE
    SYNTAX      SEQUENCE OF VRtrIfAutoCfgRaStatsEntry
    MAX-ACCESS  not-accessible
    STATUS      current
    DESCRIPTION
        "The vRtrIfAutoCfgRaStatsTable contains Neighbor Discovery Protocol
         Router Advertisements host statistics of ICMPv6 messages that are
         received and sourced by a router interface.

         Conceptual rows in this table are created and destroyed automatically
         by the system, when autoconfiguration is enabled and disabled for the
         interface."
    ::= { tmnxVrtrRouterAdvertisement 5 }

vRtrIfAutoCfgRaStatsEntry        OBJECT-TYPE
    SYNTAX      VRtrIfAutoCfgRaStatsEntry
    MAX-ACCESS  not-accessible
    STATUS      current
    DESCRIPTION
        "Each row contains statistics of a particular router interface."
    INDEX       {
        vRtrID,
        vRtrIfIndex
    }
    ::= { vRtrIfAutoCfgRaStatsTable 1 }

VRtrIfAutoCfgRaStatsEntry        ::= SEQUENCE
{
    vRtrIfAutoCfgRaStatsClearedTime  TimeStamp,
    vRtrIfAutoCfgRaStatsOutRtrSol    Counter64,
    vRtrIfAutoCfgRaStatsRtrSolTime   TimeTicks,
    vRtrIfAutoCfgRaStatsOutRtrSolErr Counter64,
    vRtrIfAutoCfgRaStatsInRtrAdv     Counter64,
    vRtrIfAutoCfgRaStatsRtrAdvTime   TimeTicks,
    vRtrIfAutoCfgRaStatsInRtrAdvErr  Counter64
}

vRtrIfAutoCfgRaStatsClearedTime  OBJECT-TYPE
    SYNTAX      TimeStamp
    MAX-ACCESS  read-only
    STATUS      current
    DESCRIPTION
        "The value of vRtrIfAutoCfgRaStatsClearedTime indicates the sysUpTime
         at the time the counters in this conceptual row were cleared for the
         last time.

         If the counters were never cleared, the value of
         vRtrIfAutoCfgRaStatsClearedTime is zero."
    ::= { vRtrIfAutoCfgRaStatsEntry 1 }

vRtrIfAutoCfgRaStatsOutRtrSol    OBJECT-TYPE
    SYNTAX      Counter64
    MAX-ACCESS  read-only
    STATUS      current
    DESCRIPTION
        "The value of vRtrIfAutoCfgRaStatsOutRtrSol indicates the number of
         ICMP Router Solicitation messages sent on this interface."
    ::= { vRtrIfAutoCfgRaStatsEntry 2 }

vRtrIfAutoCfgRaStatsRtrSolTime   OBJECT-TYPE
    SYNTAX      TimeTicks
    MAX-ACCESS  read-only
    STATUS      current
    DESCRIPTION
        "The value of vRtrIfAutoCfgRaStatsRtrSolTime indicates the time elapsed
         since the last router solicitation message was sent on this interface."
    ::= { vRtrIfAutoCfgRaStatsEntry 3 }

vRtrIfAutoCfgRaStatsOutRtrSolErr OBJECT-TYPE
    SYNTAX      Counter64
    MAX-ACCESS  read-only
    STATUS      current
    DESCRIPTION
        "The value of vRtrIfAutoCfgRaStatsOutRtrSolErr indicates
         the  number errors encountered while attempting to send
         ICMP Router Solicitation messages."
    ::= { vRtrIfAutoCfgRaStatsEntry 4 }

vRtrIfAutoCfgRaStatsInRtrAdv     OBJECT-TYPE
    SYNTAX      Counter64
    MAX-ACCESS  read-only
    STATUS      current
    DESCRIPTION
        "The value of vRtrIfAutoCfgRaStatsInRtrAdv indicates the number of ICMP
         Router Advertisement messages received on this interface."
    ::= { vRtrIfAutoCfgRaStatsEntry 5 }

vRtrIfAutoCfgRaStatsRtrAdvTime   OBJECT-TYPE
    SYNTAX      TimeTicks
    MAX-ACCESS  read-only
    STATUS      current
    DESCRIPTION
        "The value of vRtrIfAutoCfgRaStatsRtrAdvTime indicates the time elapsed
         since the last router advertisement message was received on this
         interface."
    ::= { vRtrIfAutoCfgRaStatsEntry 6 }

vRtrIfAutoCfgRaStatsInRtrAdvErr  OBJECT-TYPE
    SYNTAX      Counter64
    MAX-ACCESS  read-only
    STATUS      current
    DESCRIPTION
        "The value of vRtrIfAutoCfgRaStatsInRtrAdvErr indicates
         the  number errors encountered while attempting to send
         ICMP Router Solicitation messages."
    ::= { vRtrIfAutoCfgRaStatsEntry 7 }

vRtrIfEgressQueueStatsTable      OBJECT-TYPE
    SYNTAX      SEQUENCE OF VRtrIfEgressQueueStatsEntry
    MAX-ACCESS  not-accessible
    STATUS      current
    DESCRIPTION
        "The vRtrIfEgressQueueStatsTable table contains statistics per virtual
         router interface egress queues."
    ::= { tmnxVRtrObjs 203 }

vRtrIfEgressQueueStatsEntry      OBJECT-TYPE
    SYNTAX      VRtrIfEgressQueueStatsEntry
    MAX-ACCESS  not-accessible
    STATUS      current
    DESCRIPTION
        "Each row entry represents the statistics per virtual router interface
         queue. Entries are created and deleted when entries in the vRtrIfEntry
         are created and deleted."
    INDEX       {
        vRtrID,
        vRtrIfIndex,
        vRtrIfEgressQueueIndex
    }
    ::= { vRtrIfEgressQueueStatsTable 1 }

VRtrIfEgressQueueStatsEntry      ::= SEQUENCE
{
    vRtrIfEgressQueueIndex           Unsigned32,
    vRtrIfEgressQueueFwdPkts         Counter64,
    vRtrIfEgressQueueFwdOcts         Counter64,
    vRtrIfEgressQueueDrpPkts         Counter64,
    vRtrIfEgressQueueDrpOcts         Counter64,
    vRtrIfEgrQFwdInProfPkts          Counter64,
    vRtrIfEgrQFwdInProfOcts          Counter64,
    vRtrIfEgrQDrpInProfPkts          Counter64,
    vRtrIfEgrQDrpInProfOcts          Counter64,
    vRtrIfEgrQFwdOutProfPkts         Counter64,
    vRtrIfEgrQFwdOutProfOcts         Counter64,
    vRtrIfEgrQDrpOutProfPkts         Counter64,
    vRtrIfEgrQDrpOutProfOcts         Counter64,
    vRtrIfEgrQFwdExdProfPkts         Counter64,
    vRtrIfEgrQFwdExdProfOcts         Counter64,
    vRtrIfEgrQDrpExdProfPkts         Counter64,
    vRtrIfEgrQDrpExdProfOcts         Counter64,
    vRtrIfEgrQFwdInPlusProfPkts      Counter64,
    vRtrIfEgrQFwdInPlusProfOcts      Counter64,
    vRtrIfEgrQDrpInPlusProfPkts      Counter64,
    vRtrIfEgrQDrpInPlusProfOcts      Counter64
}

vRtrIfEgressQueueIndex           OBJECT-TYPE
    SYNTAX      Unsigned32
    MAX-ACCESS  not-accessible
    STATUS      current
    DESCRIPTION
        "Additional table index provided to distinguish between multiple queues"
    ::= { vRtrIfEgressQueueStatsEntry 1 }

vRtrIfEgressQueueFwdPkts         OBJECT-TYPE
    SYNTAX      Counter64
    MAX-ACCESS  read-only
    STATUS      current
    DESCRIPTION
        "The value of vRtrIfEgressQueueFwdPkts indicates the number of packets
         forwarded on this egress queue."
    ::= { vRtrIfEgressQueueStatsEntry 2 }

vRtrIfEgressQueueFwdOcts         OBJECT-TYPE
    SYNTAX      Counter64
    MAX-ACCESS  read-only
    STATUS      current
    DESCRIPTION
        "The value of vRtrIfEgressQueueFwdOcts indicates the number of octets
         forwarded on this egress queue."
    ::= { vRtrIfEgressQueueStatsEntry 3 }

vRtrIfEgressQueueDrpPkts         OBJECT-TYPE
    SYNTAX      Counter64
    MAX-ACCESS  read-only
    STATUS      current
    DESCRIPTION
        "The value of vRtrIfEgressQueueDrpPkts indicates the number of packets
         dropped on this egress queue."
    ::= { vRtrIfEgressQueueStatsEntry 4 }

vRtrIfEgressQueueDrpOcts         OBJECT-TYPE
    SYNTAX      Counter64
    MAX-ACCESS  read-only
    STATUS      current
    DESCRIPTION
        "The value of vRtrIfEgressQueueDrpOcts indicates the number of octets
         dropped on this egress queue."
    ::= { vRtrIfEgressQueueStatsEntry 5 }

vRtrIfEgrQFwdInProfPkts          OBJECT-TYPE
    SYNTAX      Counter64
    MAX-ACCESS  read-only
    STATUS      current
    DESCRIPTION
        "The value of vRtrIfEgrQFwdInProfPkts indicates the number of
         in-profile packets forwarded on this egress queue."
    ::= { vRtrIfEgressQueueStatsEntry 6 }

vRtrIfEgrQFwdInProfOcts          OBJECT-TYPE
    SYNTAX      Counter64
    MAX-ACCESS  read-only
    STATUS      current
    DESCRIPTION
        "The value of vRtrIfEgrQFwdInProfOcts indicates the number of
         in-profile octets forwarded on this egress queue."
    ::= { vRtrIfEgressQueueStatsEntry 7 }

vRtrIfEgrQDrpInProfPkts          OBJECT-TYPE
    SYNTAX      Counter64
    MAX-ACCESS  read-only
    STATUS      current
    DESCRIPTION
        "The value of vRtrIfEgrQDrpInProfPkts indicates the number of
         in-profile packets dropped on this egress queue."
    ::= { vRtrIfEgressQueueStatsEntry 8 }

vRtrIfEgrQDrpInProfOcts          OBJECT-TYPE
    SYNTAX      Counter64
    MAX-ACCESS  read-only
    STATUS      current
    DESCRIPTION
        "The value of vRtrIfEgrQDrpInProfOcts indicates the number of
         in-profile octets dropped on this egress queue."
    ::= { vRtrIfEgressQueueStatsEntry 9 }

vRtrIfEgrQFwdOutProfPkts         OBJECT-TYPE
    SYNTAX      Counter64
    MAX-ACCESS  read-only
    STATUS      current
    DESCRIPTION
        "The value of vRtrIfEgrQFwdOutProfPkts indicates the number of
         out-profile packets forwarded on this egress queue."
    ::= { vRtrIfEgressQueueStatsEntry 10 }

vRtrIfEgrQFwdOutProfOcts         OBJECT-TYPE
    SYNTAX      Counter64
    MAX-ACCESS  read-only
    STATUS      current
    DESCRIPTION
        "The value of vRtrIfEgrQFwdOutProfOcts indicates the number of
         out-profile octets forwarded on this egress queue."
    ::= { vRtrIfEgressQueueStatsEntry 11 }

vRtrIfEgrQDrpOutProfPkts         OBJECT-TYPE
    SYNTAX      Counter64
    MAX-ACCESS  read-only
    STATUS      current
    DESCRIPTION
        "The value of vRtrIfEgrQDrpOutProfPkts indicates the number of
         out-profile packets dropped on this egress queue."
    ::= { vRtrIfEgressQueueStatsEntry 12 }

vRtrIfEgrQDrpOutProfOcts         OBJECT-TYPE
    SYNTAX      Counter64
    MAX-ACCESS  read-only
    STATUS      current
    DESCRIPTION
        "The value of vRtrIfEgrQDrpOutProfOcts indicates the number of
         out-profile octets dropped on this egress queue."
    ::= { vRtrIfEgressQueueStatsEntry 13 }

vRtrIfEgrQFwdExdProfPkts         OBJECT-TYPE
    SYNTAX      Counter64
    MAX-ACCESS  read-only
    STATUS      current
    DESCRIPTION
        "The value of vRtrIfEgrQFwdExdProfPkts indicates the number
         exceed-profile packets forwarded on this egress queue."
    ::= { vRtrIfEgressQueueStatsEntry 14 }

vRtrIfEgrQFwdExdProfOcts         OBJECT-TYPE
    SYNTAX      Counter64
    MAX-ACCESS  read-only
    STATUS      current
    DESCRIPTION
        "The value of vRtrIfEgrQFwdExdProfOcts indicates the number
         exceed-profile octets forwarded on this egress queue."
    ::= { vRtrIfEgressQueueStatsEntry 15 }

vRtrIfEgrQDrpExdProfPkts         OBJECT-TYPE
    SYNTAX      Counter64
    MAX-ACCESS  read-only
    STATUS      current
    DESCRIPTION
        "The value of vRtrIfEgrQDrpExdProfPkts indicates the number of
         exceed-profile packets dropped on this egress queue."
    ::= { vRtrIfEgressQueueStatsEntry 16 }

vRtrIfEgrQDrpExdProfOcts         OBJECT-TYPE
    SYNTAX      Counter64
    MAX-ACCESS  read-only
    STATUS      current
    DESCRIPTION
        "The value of vRtrIfEgrQDrpExdProfOcts indicates the number of
         exceed-profile octets dropped on this egress queue."
    ::= { vRtrIfEgressQueueStatsEntry 17 }

vRtrIfEgrQFwdInPlusProfPkts      OBJECT-TYPE
    SYNTAX      Counter64
    MAX-ACCESS  read-only
    STATUS      current
    DESCRIPTION
        "The value of vRtrIfEgrQFwdInPlusProfPkts indicates the number of
         inplus-profile packets forwarded on this egress queue."
    ::= { vRtrIfEgressQueueStatsEntry 18 }

vRtrIfEgrQFwdInPlusProfOcts      OBJECT-TYPE
    SYNTAX      Counter64
    MAX-ACCESS  read-only
    STATUS      current
    DESCRIPTION
        "The value of vRtrIfEgrQFwdInPlusProfOcts indicates the number of
         inplus-profile octets forwarded on this egress queue."
    ::= { vRtrIfEgressQueueStatsEntry 19 }

vRtrIfEgrQDrpInPlusProfPkts      OBJECT-TYPE
    SYNTAX      Counter64
    MAX-ACCESS  read-only
    STATUS      current
    DESCRIPTION
        "The value of vRtrIfEgrQDrpInPlusProfPkts indicates the number of
         inplus-profile packets dropped on this egress queue."
    ::= { vRtrIfEgressQueueStatsEntry 20 }

vRtrIfEgrQDrpInPlusProfOcts      OBJECT-TYPE
    SYNTAX      Counter64
    MAX-ACCESS  read-only
    STATUS      current
    DESCRIPTION
        "The value of vRtrIfEgrQDrpInPlusProfOcts indicates the number of
         inplus-profile octets dropped on this egress queue."
    ::= { vRtrIfEgressQueueStatsEntry 21 }

vRtrIfIngPolicerStatsTable       OBJECT-TYPE
    SYNTAX      SEQUENCE OF VRtrIfIngPolicerStatsEntry
    MAX-ACCESS  not-accessible
    STATUS      current
    DESCRIPTION
        "The vRtrIfIngPolicerStatsTable table contains ingress policer
         statistics per virtual router interface."
    ::= { tmnxVRtrObjs 204 }

vRtrIfIngPolicerStatsEntry       OBJECT-TYPE
    SYNTAX      VRtrIfIngPolicerStatsEntry
    MAX-ACCESS  not-accessible
    STATUS      current
    DESCRIPTION
        "Each row entry represents the ingress policer statistics per virtual
         router interface. Entries are created and deleted when entries in the
         vRtrIfEntry are created and deleted."
    INDEX       {
        vRtrID,
        vRtrIfIndex,
        vRtrIfIngPolicerIndex
    }
    ::= { vRtrIfIngPolicerStatsTable 1 }

VRtrIfIngPolicerStatsEntry       ::= SEQUENCE
{
    vRtrIfIngPolicerIndex            Unsigned32,
    vRtrIfIngPolicerFwdInProfPkts    Counter64,
    vRtrIfIngPolicerFwdOutProfPkts   Counter64,
    vRtrIfIngPolicerFwdInProfOcts    Counter64,
    vRtrIfIngPolicerFwdOutProfOcts   Counter64,
    vRtrIfIngPolicerDrpExdProfPkts   Counter64,
    vRtrIfIngPolicerDrpExdProfOcts   Counter64
}

vRtrIfIngPolicerIndex            OBJECT-TYPE
    SYNTAX      Unsigned32 (0..16)
    MAX-ACCESS  not-accessible
    STATUS      current
    DESCRIPTION
        "The value of vRtrIfIngPolicerIndex serves as the tertiary index. When
         used in conjunction with vRtrID and vRtrIfIndex, it uniquely
         identifies a network ingress policer for the specified router
         interface in the managed system."
    ::= { vRtrIfIngPolicerStatsEntry 1 }

vRtrIfIngPolicerFwdInProfPkts    OBJECT-TYPE
    SYNTAX      Counter64
    MAX-ACCESS  read-only
    STATUS      current
    DESCRIPTION
        "The value of vRtrIfIngPolicerFwdInProfPkts indicates the number of
         in-prof ingress packets forwarded."
    ::= { vRtrIfIngPolicerStatsEntry 2 }

vRtrIfIngPolicerFwdOutProfPkts   OBJECT-TYPE
    SYNTAX      Counter64
    MAX-ACCESS  read-only
    STATUS      current
    DESCRIPTION
        "The value of vRtrIfIngPolicerFwdOutProfPkts indicates the number of
         out-prof ingress packets forwarded."
    ::= { vRtrIfIngPolicerStatsEntry 3 }

vRtrIfIngPolicerFwdInProfOcts    OBJECT-TYPE
    SYNTAX      Counter64
    MAX-ACCESS  read-only
    STATUS      current
    DESCRIPTION
        "The value of vRtrIfIngPolicerFwdInProfOcts indicates the number of
         in-prof ingress octets forwarded."
    ::= { vRtrIfIngPolicerStatsEntry 4 }

vRtrIfIngPolicerFwdOutProfOcts   OBJECT-TYPE
    SYNTAX      Counter64
    MAX-ACCESS  read-only
    STATUS      current
    DESCRIPTION
        "The value of vRtrIfIngPolicerFwdOutProfOcts indicates the number of
         out-prof ingress octets forwarded."
    ::= { vRtrIfIngPolicerStatsEntry 5 }

vRtrIfIngPolicerDrpExdProfPkts   OBJECT-TYPE
    SYNTAX      Counter64
    MAX-ACCESS  read-only
    STATUS      current
    DESCRIPTION
        "The value of vRtrIfIngPolicerDrpExdProfPkts indicates the number of
         exceed-profile ingress packets dropped."
    ::= { vRtrIfIngPolicerStatsEntry 6 }

vRtrIfIngPolicerDrpExdProfOcts   OBJECT-TYPE
    SYNTAX      Counter64
    MAX-ACCESS  read-only
    STATUS      current
    DESCRIPTION
        "The value of vRtrIfIngPolicerDrpExdProfOcts indicates the number of
         exceed-profile ingress octets dropped."
    ::= { vRtrIfIngPolicerStatsEntry 7 }

vRtrIfArpHostRtTblLstChg         OBJECT-TYPE
    SYNTAX      TimeStamp
    MAX-ACCESS  read-only
    STATUS      current
    DESCRIPTION
        "The vRtrIfArpHostRtTblLstChg indicates the sysUpTime at the time of
         the last modification of vRtrIfArpHostRtTable.

         If no changes were made to the table since the last re-initialization
         of the local network management subsystem, this object contains the
         value zero."
    ::= { tmnxVRtrObjs 205 }

vRtrIfArpHostRtTable             OBJECT-TYPE
    SYNTAX      SEQUENCE OF VRtrIfArpHostRtEntry
    MAX-ACCESS  not-accessible
    STATUS      current
    DESCRIPTION
        "The vRtrIfArpHostRtTable has an entry for each type of ARP entry to
         create host route from on the router interface in the system."
    ::= { tmnxVRtrObjs 206 }

vRtrIfArpHostRtEntry             OBJECT-TYPE
    SYNTAX      VRtrIfArpHostRtEntry
    MAX-ACCESS  not-accessible
    STATUS      current
    DESCRIPTION
        "Each row entry represents an entry for each type of ARP entry to
         create host route from on the router interface in the system. Entries
         can be created and deleted via SNMP SET operations using the
         vRtrIfArpHostRtRowStatus variable."
    INDEX       {
        vRtrID,
        vRtrIfIndex,
        vRtrIfArpHostRtType
    }
    ::= { vRtrIfArpHostRtTable 1 }

VRtrIfArpHostRtEntry             ::= SEQUENCE
{
    vRtrIfArpHostRtType              INTEGER,
    vRtrIfArpHostRtRowStatus         RowStatus,
    vRtrIfArpHostRtLastChgd          TimeStamp,
    vRtrIfArpHostRtRouteTag          Unsigned32
}

vRtrIfArpHostRtType              OBJECT-TYPE
    SYNTAX      INTEGER {
        static  (1),
        dynamic (2),
        evpn    (3)
    }
    MAX-ACCESS  not-accessible
    STATUS      current
    DESCRIPTION
        "The value of vRtrIfArpHostRtType specifies the ARP type to create a
         host route from."
    ::= { vRtrIfArpHostRtEntry 1 }

vRtrIfArpHostRtRowStatus         OBJECT-TYPE
    SYNTAX      RowStatus
    MAX-ACCESS  read-create
    STATUS      current
    DESCRIPTION
        "The value of vRtrIfArpHostRtRowStatus specifies the row status of this
         row."
    ::= { vRtrIfArpHostRtEntry 2 }

vRtrIfArpHostRtLastChgd          OBJECT-TYPE
    SYNTAX      TimeStamp
    MAX-ACCESS  read-only
    STATUS      current
    DESCRIPTION
        "The value of vRtrIfArpHostRtLastChgd indicates the sysUpTime at the
         time of the last configuration change in this conceptual row."
    ::= { vRtrIfArpHostRtEntry 3 }

vRtrIfArpHostRtRouteTag          OBJECT-TYPE
    SYNTAX      Unsigned32 (0 | 1..255)
    MAX-ACCESS  read-create
    STATUS      current
    DESCRIPTION
        "The value of vRtrIfArpHostRtRouteTag specifies the route tag to use
         with the route created from an ARP entry."
    DEFVAL      { 0 }
    ::= { vRtrIfArpHostRtEntry 4 }

vRtrIfNdHostRtTblLstChg          OBJECT-TYPE
    SYNTAX      TimeStamp
    MAX-ACCESS  read-only
    STATUS      current
    DESCRIPTION
        "The vRtrIfNdHostRtTblLstChg indicates the sysUpTime at the time of the
         last modification of vRtrIfNdHostRtTable.

         If no changes were made to the table since the last re-initialization
         of the local network management subsystem, this object contains the
         value zero."
    ::= { tmnxVRtrObjs 207 }

vRtrIfNdHostRtTable              OBJECT-TYPE
    SYNTAX      SEQUENCE OF VRtrIfNdHostRtEntry
    MAX-ACCESS  not-accessible
    STATUS      current
    DESCRIPTION
        "The vRtrIfNdHostRtTable has an entry for each type of ND entry to
         create host route from on the router interface in the system."
    ::= { tmnxVRtrObjs 208 }

vRtrIfNdHostRtEntry              OBJECT-TYPE
    SYNTAX      VRtrIfNdHostRtEntry
    MAX-ACCESS  not-accessible
    STATUS      current
    DESCRIPTION
        "Each row entry represents an entry for each type of ND entry to create
         host route from on the router interface in the system. Entries can be
         created and deleted via SNMP SET operations using the
         vRtrIfNdHostRtRowStatus variable."
    INDEX       {
        vRtrID,
        vRtrIfIndex,
        vRtrIfNdHostRtType
    }
    ::= { vRtrIfNdHostRtTable 1 }

VRtrIfNdHostRtEntry              ::= SEQUENCE
{
    vRtrIfNdHostRtType               INTEGER,
    vRtrIfNdHostRtRowStatus          RowStatus,
    vRtrIfNdHostRtLastChgd           TimeStamp,
    vRtrIfNdHostRtRouteTag           Unsigned32
}

vRtrIfNdHostRtType               OBJECT-TYPE
    SYNTAX      INTEGER {
        static  (1),
        dynamic (2),
        evpn    (3)
    }
    MAX-ACCESS  not-accessible
    STATUS      current
    DESCRIPTION
        "The value of vRtrIfNdHostRtType specifies the ND type to create a host
         route from."
    ::= { vRtrIfNdHostRtEntry 1 }

vRtrIfNdHostRtRowStatus          OBJECT-TYPE
    SYNTAX      RowStatus
    MAX-ACCESS  read-create
    STATUS      current
    DESCRIPTION
        "The value of vRtrIfNdHostRtRowStatus specifies the row status of this
         row."
    ::= { vRtrIfNdHostRtEntry 2 }

vRtrIfNdHostRtLastChgd           OBJECT-TYPE
    SYNTAX      TimeStamp
    MAX-ACCESS  read-only
    STATUS      current
    DESCRIPTION
        "The value of vRtrIfNdHostRtLastChgd indicates the sysUpTime at the
         time of the last configuration change in this conceptual row."
    ::= { vRtrIfNdHostRtEntry 3 }

vRtrIfNdHostRtRouteTag           OBJECT-TYPE
    SYNTAX      Unsigned32 (0 | 1..255)
    MAX-ACCESS  read-create
    STATUS      current
    DESCRIPTION
        "The value of vRtrIfNdHostRtRouteTag specifies route tag to use with
         the route created from a ND entry."
    DEFVAL      { 0 }
    ::= { vRtrIfNdHostRtEntry 4 }

vRtrDnsRedirectTableLastChanged  OBJECT-TYPE
    SYNTAX      TimeStamp
    MAX-ACCESS  read-only
    STATUS      current
    DESCRIPTION
        "The value of the object vRtrDnsRedirectTableLastChanged indicates the
         value of sysUpTime at the time of the last modification of an entry in
         the vRtrDnsRedirectTable."
    ::= { tmnxVRtrObjs 209 }

vRtrDnsRedirectTable             OBJECT-TYPE
    SYNTAX      SEQUENCE OF VRtrDnsRedirectEntry
    MAX-ACCESS  not-accessible
    STATUS      current
    DESCRIPTION
        "The vRtrDnsRedirectTable contains the redirect configuration for DNS
         resolution via virtual router instances."
    ::= { tmnxVRtrObjs 210 }

vRtrDnsRedirectEntry             OBJECT-TYPE
    SYNTAX      VRtrDnsRedirectEntry
    MAX-ACCESS  not-accessible
    STATUS      current
    DESCRIPTION
        "Each row entry in the vRtrDnsRedirectTable represents a specific
         redirect configuration for DNS resolution via VPRN."
    INDEX       {
        vRtrDnsRedirectRequestRouterId,
        vRtrDnsRedirectDnsRouterId
    }
    ::= { vRtrDnsRedirectTable 1 }

VRtrDnsRedirectEntry             ::= SEQUENCE
{
    vRtrDnsRedirectRequestRouterId   Unsigned32,
    vRtrDnsRedirectDnsRouterId       Unsigned32,
    vRtrDnsRedirectRowStatus         RowStatus,
    vRtrDnsRedirectPreference        Unsigned32,
    vRtrDnsRedirectLastChanged       TimeStamp
}

vRtrDnsRedirectRequestRouterId   OBJECT-TYPE
    SYNTAX      Unsigned32
    MAX-ACCESS  not-accessible
    STATUS      current
    DESCRIPTION
        "The value of vRtrDnsRedirectRequestRouterId specifies the router
         instance where the DNS request is coming from."
    DEFVAL      { 0 }
    ::= { vRtrDnsRedirectEntry 1 }

vRtrDnsRedirectDnsRouterId       OBJECT-TYPE
    SYNTAX      Unsigned32
    MAX-ACCESS  not-accessible
    STATUS      current
    DESCRIPTION
        "The value of vRtrDnsRedirectDnsRouterId specifies the router instance
         where the DNS request will be executed."
    DEFVAL      { 0 }
    ::= { vRtrDnsRedirectEntry 2 }

vRtrDnsRedirectRowStatus         OBJECT-TYPE
    SYNTAX      RowStatus
    MAX-ACCESS  read-create
    STATUS      current
    DESCRIPTION
        "The row status used for creation, deletion, or control of
         vRtrDnsRedirectTable entries."
    ::= { vRtrDnsRedirectEntry 3 }

vRtrDnsRedirectPreference        OBJECT-TYPE
    SYNTAX      Unsigned32 (0..255)
    MAX-ACCESS  read-create
    STATUS      current
    DESCRIPTION
        "The value of vRtrDnsRedirectPreference specifies a number that
         indicates the relative preference assigned to the redirect router
         instance. Redirect router instances with a lower value for preference
         will be tried first."
    DEFVAL      { 0 }
    ::= { vRtrDnsRedirectEntry 4 }

vRtrDnsRedirectLastChanged       OBJECT-TYPE
    SYNTAX      TimeStamp
    MAX-ACCESS  read-only
    STATUS      current
    DESCRIPTION
        "The value of vRtrDnsRedirectLastChanged indicates the sysUpTime at the
         time of the last configuration change in this conceptual row."
    ::= { vRtrDnsRedirectEntry 5 }

tmnxVrtrFlexAlgoObjs             OBJECT IDENTIFIER ::= { tmnxVRtrObjs 211 }

tmnxFlexAlgoDefTblLastCh         OBJECT-TYPE
    SYNTAX      TimeStamp
    MAX-ACCESS  read-only
    STATUS      current
    DESCRIPTION
        "The value of tmnxFlexAlgoDefTblLastCh indicates the sysUpTime at the
         time of the last modification of an entry in the
         tmnxFlexAlgoDefinitionTable."
    ::= { tmnxVrtrFlexAlgoObjs 1 }

tmnxFlexAlgoDefinitionTable      OBJECT-TYPE
    SYNTAX      SEQUENCE OF TmnxFlexAlgoDefinitionEntry
    MAX-ACCESS  not-accessible
    STATUS      current
    DESCRIPTION
        "The tmnxFlexAlgoDefinitionTable contains the Flexible Algorithm
         definition  to customize IGP shortest path computation."
    ::= { tmnxVrtrFlexAlgoObjs 2 }

tmnxFlexAlgoDefinitionEntry      OBJECT-TYPE
    SYNTAX      TmnxFlexAlgoDefinitionEntry
    MAX-ACCESS  not-accessible
    STATUS      current
    DESCRIPTION
        "Each row represents a Flexible Algorithm definition.

         Rows in this table are created and destroyed by SNMP Set operations on
         the object tmnxFlexAlgoRowStatus."
    INDEX       { tmnxFlexAlgoName }
    ::= { tmnxFlexAlgoDefinitionTable 1 }

TmnxFlexAlgoDefinitionEntry      ::= SEQUENCE
{
    tmnxFlexAlgoName                 TNamedItem,
    tmnxFlexAlgoRowLstChng           TimeStamp,
    tmnxFlexAlgoRowStatus            RowStatus,
    tmnxFlexAlgoAdminState           TmnxAdminState,
    tmnxFlexAlgoDescription          TItemDescription,
    tmnxFlexAlgoMetricType           INTEGER,
    tmnxFlexAlgoPriority             Integer32,
    tmnxFlexAlgoFlagsTlv             TmnxEnabledDisabled
}

tmnxFlexAlgoName                 OBJECT-TYPE
    SYNTAX      TNamedItem
    MAX-ACCESS  not-accessible
    STATUS      current
    DESCRIPTION
        "The value of tmnxFlexAlgoName specifies a flexible algorithm."
    ::= { tmnxFlexAlgoDefinitionEntry 1 }

tmnxFlexAlgoRowLstChng           OBJECT-TYPE
    SYNTAX      TimeStamp
    MAX-ACCESS  read-only
    STATUS      current
    DESCRIPTION
        "The value tmnxFlexAlgoRowLstChng indicates the sysUpTime at the time
         of the most recent management-initiated change to this row."
    ::= { tmnxFlexAlgoDefinitionEntry 2 }

tmnxFlexAlgoRowStatus            OBJECT-TYPE
    SYNTAX      RowStatus
    MAX-ACCESS  read-create
    STATUS      current
    DESCRIPTION
        "The value of tmnxFlexAlgoRowStatus controls the creation and deletion
         of rows in the table."
    ::= { tmnxFlexAlgoDefinitionEntry 3 }

tmnxFlexAlgoAdminState           OBJECT-TYPE
    SYNTAX      TmnxAdminState
    MAX-ACCESS  read-create
    STATUS      current
    DESCRIPTION
        "The value of tmnxFlexAlgoAdminState specifies the
         administrative state of the Flex Algo definition.

         Flex Algo definition changes are only allowed when the admin state is
         'outOfService'."
    DEFVAL      { outOfService }
    ::= { tmnxFlexAlgoDefinitionEntry 4 }

tmnxFlexAlgoDescription          OBJECT-TYPE
    SYNTAX      TItemDescription
    MAX-ACCESS  read-create
    STATUS      current
    DESCRIPTION
        "The value of tmnxFlexAlgoDescription specifies the description of this
         Flex Algo."
    DEFVAL      { "" }
    ::= { tmnxFlexAlgoDefinitionEntry 5 }

tmnxFlexAlgoMetricType           OBJECT-TYPE
    SYNTAX      INTEGER {
        igp      (0),
        delay    (1),
        teMetric (2)
    }
    MAX-ACCESS  read-create
    STATUS      current
    DESCRIPTION
        "The value of tmnxFlexAlgoMetricType specifies the metric type used by
         the Flex Algo during calculation.

         igp(0)      - the regular IGP metric
         delay(1)    - the Min Unidirectional Link Delay
         teMetric(2) - the TE default metric"
    DEFVAL      { igp }
    ::= { tmnxFlexAlgoDefinitionEntry 6 }

tmnxFlexAlgoPriority             OBJECT-TYPE
    SYNTAX      Integer32 (0..255)
    MAX-ACCESS  read-create
    STATUS      current
    DESCRIPTION
        "The value of tmnxFlexAlgoPriority specifies the priority used during
         the Flex Algo definition election."
    DEFVAL      { 100 }
    ::= { tmnxFlexAlgoDefinitionEntry 7 }

tmnxFlexAlgoFlagsTlv             OBJECT-TYPE
    SYNTAX      TmnxEnabledDisabled
    MAX-ACCESS  read-create
    STATUS      current
    DESCRIPTION
        "The value of the object tmnxFlexAlgoFlagsTlv specifies whether the
         Flexible Algorithm Definition (FAD) Flags TLV is enabled or disabled.

         When the value is 'enabled', the optional FAD Flags sub-TLV is
         advertised."
    DEFVAL      { enabled }
    ::= { tmnxFlexAlgoDefinitionEntry 8 }

tmnxFlexAlgoAdminGrpTblLstCh     OBJECT-TYPE
    SYNTAX      TimeStamp
    MAX-ACCESS  read-only
    STATUS      current
    DESCRIPTION
        "The value of tmnxFlexAlgoAdminGrpTblLstCh indicates the sysUpTime at
         the time of the last modification of an entry in the
         tmnxFlexAlgoAdminGrpTable."
    ::= { tmnxVrtrFlexAlgoObjs 3 }

tmnxFlexAlgoAdminGrpTable        OBJECT-TYPE
    SYNTAX      SEQUENCE OF TmnxFlexAlgoAdminGrpEntry
    MAX-ACCESS  not-accessible
    STATUS      current
    DESCRIPTION
        "The tmnxFlexAlgoAdminGrpTable contains the information pertaining to
         the admin groups out of which the Flex Algorithm can select a link."
    ::= { tmnxVrtrFlexAlgoObjs 4 }

tmnxFlexAlgoAdminGrpEntry        OBJECT-TYPE
    SYNTAX      TmnxFlexAlgoAdminGrpEntry
    MAX-ACCESS  not-accessible
    STATUS      current
    DESCRIPTION
        "Each row represents an admin group that a Flex Algorithm can use to
         restrict paths to links with specific affinities or to avoid links
         with specific affinities.

         Rows in this table are created and destroyed by SNMP Set operations on
         the object tmnxFlexAlgoAdminGrpRowStatus."
    INDEX       {
        tmnxFlexAlgoName,
        tmnxFlexAlgoAdminGrpType,
        tmnxAdminGrpName
    }
    ::= { tmnxFlexAlgoAdminGrpTable 1 }

TmnxFlexAlgoAdminGrpEntry        ::= SEQUENCE
{
    tmnxFlexAlgoAdminGrpType         INTEGER,
    tmnxFlexAlgoAdminGrpRowLstCh     TimeStamp,
    tmnxFlexAlgoAdminGrpRowStatus    RowStatus
}

tmnxFlexAlgoAdminGrpType         OBJECT-TYPE
    SYNTAX      INTEGER {
        exclude    (1),
        includeAny (2),
        includeAll (3)
    }
    MAX-ACCESS  not-accessible
    STATUS      current
    DESCRIPTION
        "The value of tmnxFlexAlgoAdminGrpType specifies whether the links in
         the specified IP admin group should be used by the Flex Algo or not.

         The value 'exclude(1)' specifies that the Flex Algo must check if any
         color that is part of the exclude rule is also set on the link. If
         such a color is set, the link MUST be pruned from the computation.

         The value of 'include-any(2)' specifies the Flex Algo must check if
         any color that is part of the include-any rule is also set on the
         link. If no such color is set, the link MUST be pruned from the
         computation.

         A value of 'include-all(2)' specifies the Flex Algo must check if all
         colors that are part of the include-all rule are also set on the link.
         If all such colors are not set on the link, the link MUST be pruned
         from the computation."
    ::= { tmnxFlexAlgoAdminGrpEntry 1 }

tmnxFlexAlgoAdminGrpRowLstCh     OBJECT-TYPE
    SYNTAX      TimeStamp
    MAX-ACCESS  read-only
    STATUS      current
    DESCRIPTION
        "The value tmnxFlexAlgoAdminGrpRowLstCh indicates the sysUpTime at the
         time of the most recent management-initiated change to this row."
    ::= { tmnxFlexAlgoAdminGrpEntry 2 }

tmnxFlexAlgoAdminGrpRowStatus    OBJECT-TYPE
    SYNTAX      RowStatus
    MAX-ACCESS  read-create
    STATUS      current
    DESCRIPTION
        "The value of tmnxFlexAlgoAdminGrpRowStatus controls the creation and
         deletion of rows in the table."
    ::= { tmnxFlexAlgoAdminGrpEntry 3 }

vRtrBgpEvpnObjs                  OBJECT IDENTIFIER ::= { tmnxVRtrObjs 212 }

vRtrBgpEvpnTblLastCh             OBJECT-TYPE
    SYNTAX      TimeStamp
    MAX-ACCESS  read-only
    STATUS      current
    DESCRIPTION
        "The value of vRtrBgpEvpnTblLastCh indicates the sysUpTime at the time
         of the last modification of an entry in the vRtrBgpEvpnTable."
    ::= { vRtrBgpEvpnObjs 1 }

vRtrBgpEvpnTable                 OBJECT-TYPE
    SYNTAX      SEQUENCE OF VRtrBgpEvpnEntry
    MAX-ACCESS  not-accessible
    STATUS      current
    DESCRIPTION
        "The vRtrBgpEvpnTable contains entries for all the BGP EVPN instances
         for a particular VPRN service."
    ::= { vRtrBgpEvpnObjs 2 }

vRtrBgpEvpnEntry                 OBJECT-TYPE
    SYNTAX      VRtrBgpEvpnEntry
    MAX-ACCESS  not-accessible
    STATUS      current
    DESCRIPTION
        "A BGP EVPN instance entry in the vRtrBgpEvpnTable."
    INDEX       {
        vRtrID,
        vRtrBgpEvpnInstance
    }
    ::= { vRtrBgpEvpnTable 1 }

VRtrBgpEvpnEntry                 ::= SEQUENCE
{
    vRtrBgpEvpnInstance              Integer32,
    vRtrBgpEvpnRowStatus             RowStatus,
    vRtrBgpEvpnLastChanged           TimeStamp,
    vRtrBgpEvpnAdminState            TmnxEnabledDisabled,
    vRtrBgpEvpnDefRtTag              Unsigned32,
    vRtrBgpEvpnVrfRD                 TmnxVPNRouteDistinguisher,
    vRtrBgpEvpnExportRteTarget       TNamedItemOrEmpty,
    vRtrBgpEvpnImportRteTarget       TNamedItemOrEmpty,
    vRtrBgpEvpnAutoRD                TruthValue,
    vRtrBgpEvpnOperRD                TmnxVPNRouteDistinguisher,
    vRtrBgpEvpnOperRDType            TmnxRouteDistType,
    vRtrBgpEvpnVrfTarget             TNamedItemOrEmpty,
    vRtrBgpEvpnDomainId              TmnxDPathDomainId,
    vRtrBgpEvpnDynEgrLblLmt          TruthValue,
    vRtrBgpEvpnEvi                   Unsigned32,
    vRtrBgpEvpnAdLinkBw              TruthValue,
    vRtrBgpEvpnAdLinkBwWeight        Unsigned32,
    vRtrBgpEvpnAdLinkBwMaxWeight     Unsigned32,
    vRtrBgpEvpnWeightedEcmp          TruthValue,
    vRtrBgpEvpnOperState             TmnxEnabledDisabled,
    vRtrBgpEvpnGwIpAdvertise         TruthValue,
    vRtrBgpEvpnGwIpResolve           TruthValue,
    vRtrBgpEvpnAnySecEncGrp          TNamedItemOrEmpty
}

vRtrBgpEvpnInstance              OBJECT-TYPE
    SYNTAX      Integer32 (1..1)
    MAX-ACCESS  not-accessible
    STATUS      current
    DESCRIPTION
        "The value of vRtrBgpEvpnInstance specifies the BGP instance used with
         this service."
    ::= { vRtrBgpEvpnEntry 1 }

vRtrBgpEvpnRowStatus             OBJECT-TYPE
    SYNTAX      RowStatus
    MAX-ACCESS  read-create
    STATUS      current
    DESCRIPTION
        "The value of the object  vRtrBgpEvpnRowStatus
         specifies the status of this row."
    ::= { vRtrBgpEvpnEntry 2 }

vRtrBgpEvpnLastChanged           OBJECT-TYPE
    SYNTAX      TimeStamp
    MAX-ACCESS  read-only
    STATUS      current
    DESCRIPTION
        "The value of the object vRtrBgpEvpnLastChanged indicates the timestamp
         of the modification of this entry."
    ::= { vRtrBgpEvpnEntry 3 }

vRtrBgpEvpnAdminState            OBJECT-TYPE
    SYNTAX      TmnxEnabledDisabled
    MAX-ACCESS  read-create
    STATUS      current
    DESCRIPTION
        "The value of vRtrBgpEvpnAdminState specifies if the BGP instance is
         enabled or not.

         The admin state cannot be set in the same request as
         vRtrBgpEvpnRowStatus, if no explicit route-distinguisher and
         route-targets are configured for the BGP instance (referenced by
         vRtrBgpEvpnInstance)."
    DEFVAL      { disabled }
    ::= { vRtrBgpEvpnEntry 4 }

vRtrBgpEvpnDefRtTag              OBJECT-TYPE
    SYNTAX      Unsigned32 (0..255)
    MAX-ACCESS  read-create
    STATUS      current
    DESCRIPTION
        "The value of vRtrBgpEvpnDefRtTag specifies the default route tag
         passed by EVPN onto the policy module so that it can be matched on
         export policies."
    DEFVAL      { 0 }
    ::= { vRtrBgpEvpnEntry 8 }

vRtrBgpEvpnVrfRD                 OBJECT-TYPE
    SYNTAX      TmnxVPNRouteDistinguisher
    MAX-ACCESS  read-create
    STATUS      current
    DESCRIPTION
        "The value of vRtrBgpEvpnVrfRD specifies the high-order 6 bytes used to
         compose the Virtual Routing and Forwarding (VRF) instance to use for
         NLRI in BGP in this VPRN service.

         SNMP set of vRtrBgpEvpnVrfRD to non-default value will automatically
         set vRtrBgpEvpnAutoRD to 'false'."
    DEFVAL      { '0000000000000000'H }
    ::= { vRtrBgpEvpnEntry 9 }

vRtrBgpEvpnExportRteTarget       OBJECT-TYPE
    SYNTAX      TNamedItemOrEmpty
    MAX-ACCESS  read-create
    STATUS      current
    DESCRIPTION
        "The value of vRtrBgpEvpnExportRteTarget specifies the
         extended community name for the default export policy
         to use for BGP  in this VPRN service.

         It must be set to default before it is set to a non-default value."
    DEFVAL      { "" }
    ::= { vRtrBgpEvpnEntry 10 }

vRtrBgpEvpnImportRteTarget       OBJECT-TYPE
    SYNTAX      TNamedItemOrEmpty
    MAX-ACCESS  read-create
    STATUS      current
    DESCRIPTION
        "The value of vRtrBgpEvpnImportRteTarget specifies the
         extended community name for the default import policy
         to use for BGP  in this VPRN service.

         It must be set to default before it is set to a non-default value."
    DEFVAL      { "" }
    ::= { vRtrBgpEvpnEntry 11 }

vRtrBgpEvpnAutoRD                OBJECT-TYPE
    SYNTAX      TruthValue
    MAX-ACCESS  read-create
    STATUS      current
    DESCRIPTION
        "The value of vRtrBgpEvpnAutoRD specifies that system will
         automatically select a value for the route-distinguisher from  from
         TIMETRA-SERV-MIB::svcBgpAutoRDType1Group.

         An 'inconsistentValue' error is returned when trying to set
         vRtrBgpEvpnAutoRD to 'true' and there is no route-distinguisher
         available from TIMETRA-SERV-MIB::svcBgpAutoRDType1Group.

         SNMP set of vRtrBgpEvpnAutoRD to 'true' will automatically set
         vRtrBgpEvpnVrfRD to all zeroes."
    DEFVAL      { false }
    ::= { vRtrBgpEvpnEntry 12 }

vRtrBgpEvpnOperRD                OBJECT-TYPE
    SYNTAX      TmnxVPNRouteDistinguisher
    MAX-ACCESS  read-only
    STATUS      current
    DESCRIPTION
        "The value of vRtrBgpEvpnOperRD indicates the route-distinguisher value
         in use by the system for this service."
    ::= { vRtrBgpEvpnEntry 13 }

vRtrBgpEvpnOperRDType            OBJECT-TYPE
    SYNTAX      TmnxRouteDistType
    MAX-ACCESS  read-only
    STATUS      current
    DESCRIPTION
        "The value of vRtrBgpEvpnOperRDType indicates the type of
         route-distinguisher value in use by the system for this service."
    ::= { vRtrBgpEvpnEntry 14 }

vRtrBgpEvpnVrfTarget             OBJECT-TYPE
    SYNTAX      TNamedItemOrEmpty
    MAX-ACCESS  read-create
    STATUS      current
    DESCRIPTION
        "The value of vRtrBgpEvpnVrfTarget specifies the extended community
         name for the default vrf-import or vrf-export policy to use for the
         vRtrID if no entries are configured in the vRtrBgpEvpnVrfPolicyTable
         for this vRtrID instance.

         This object can not be set if either vRtrBgpEvpnExportRteTarget or
         vRtrBgpEvpnImportRteTarget has been set."
    ::= { vRtrBgpEvpnEntry 15 }

vRtrBgpEvpnDomainId              OBJECT-TYPE
    SYNTAX      TmnxDPathDomainId
    MAX-ACCESS  read-create
    STATUS      current
    DESCRIPTION
        "The value of vRtrBgpEvpnDomainId specifies the Domain ID used in
         D-Path for routes advertisement for BGP EVPN MPLS service."
    DEFVAL      { '000000000000'H }
    ::= { vRtrBgpEvpnEntry 16 }

vRtrBgpEvpnDynEgrLblLmt          OBJECT-TYPE
    SYNTAX      TruthValue
    MAX-ACCESS  read-create
    STATUS      current
    DESCRIPTION
        "The value of vRtrBgpEvpnDynEgrLblLmt determines whether, when BGP
         resolves routes, it accounts for the presence of control-word,
         ethernet-segment label etc or not."
    DEFVAL      { false }
    ::= { vRtrBgpEvpnEntry 17 }

vRtrBgpEvpnEvi                   OBJECT-TYPE
    SYNTAX      Unsigned32 (0..16777215)
    MAX-ACCESS  read-create
    STATUS      current
    DESCRIPTION
        "BGP EVPN identifier used for the service-carving algorithm used for
         multi-homing and for auto-deriving the route-distinguisher and
         route-target."
    DEFVAL      { 0 }
    ::= { vRtrBgpEvpnEntry 18 }

vRtrBgpEvpnAdLinkBw              OBJECT-TYPE
    SYNTAX      TruthValue
    MAX-ACCESS  read-create
    STATUS      current
    DESCRIPTION
        "The value of vRtrBgpEvpnAdLinkBw specifies whether to advertise link
         bandwidth for evpn-ifl routes."
    DEFVAL      { false }
    ::= { vRtrBgpEvpnEntry 19 }

vRtrBgpEvpnAdLinkBwWeight        OBJECT-TYPE
    SYNTAX      Unsigned32 (0 | 1..128)
    MAX-ACCESS  read-create
    STATUS      current
    DESCRIPTION
        "The value of vRtrBgpEvpnAdLinkBwWeight specifies the weight to be
         advertised with evpn-ifl routes. This is effective only when
         vRtrBgpEvpnAdLinkBwWeight is enabled."
    DEFVAL      { 0 }
    ::= { vRtrBgpEvpnEntry 20 }

vRtrBgpEvpnAdLinkBwMaxWeight     OBJECT-TYPE
    SYNTAX      Unsigned32 (1..128)
    MAX-ACCESS  read-create
    STATUS      current
    DESCRIPTION
        "The value of vRtrBgpEvpnAdLinkBwMaxWeight specifies the maximum weight
         to be advertised with evpn-ifl routes. This is effective only when
         vRtrBgpEvpnAdLinkBwMaxWeight is enabled."
    DEFVAL      { 128 }
    ::= { vRtrBgpEvpnEntry 21 }

vRtrBgpEvpnWeightedEcmp          OBJECT-TYPE
    SYNTAX      TruthValue
    MAX-ACCESS  read-create
    STATUS      current
    DESCRIPTION
        "The value of vRtrBgpEvpnWeightedEcmp specifies whether unequal ecmp
         will be performed based on link bandwidth weights for evpn-ifl routes."
    DEFVAL      { false }
    ::= { vRtrBgpEvpnEntry 22 }

vRtrBgpEvpnOperState             OBJECT-TYPE
    SYNTAX      TmnxEnabledDisabled
    MAX-ACCESS  read-only
    STATUS      current
    DESCRIPTION
        "The vRtrBgpEvpnOperState indicates if the VPRN BGP EVPN MPLS instance
         is enabled or not."
    ::= { vRtrBgpEvpnEntry 23 }

vRtrBgpEvpnGwIpAdvertise         OBJECT-TYPE
    SYNTAX      TruthValue
    MAX-ACCESS  read-create
    STATUS      current
    DESCRIPTION
        "The value of vRtrBgpEvpnGwIpAdvertise specifies whether to advertise
         the GW IP address for evpn-ifl routes."
    DEFVAL      { false }
    ::= { vRtrBgpEvpnEntry 24 }

vRtrBgpEvpnGwIpResolve           OBJECT-TYPE
    SYNTAX      TruthValue
    MAX-ACCESS  read-create
    STATUS      current
    DESCRIPTION
        "The value of vRtrBgpEvpnGwIpResolve specifies whether the GW IP
         addresses for the evpn-ifl routes should be processed."
    DEFVAL      { false }
    ::= { vRtrBgpEvpnEntry 25 }

vRtrBgpEvpnAnySecEncGrp          OBJECT-TYPE
    SYNTAX      TNamedItemOrEmpty
    MAX-ACCESS  read-create
    STATUS      current
    DESCRIPTION
        "The vRtrBgpEvpnAnySecEncGrp specifies the name of ANY-SEC encryption
         group for this service."
    DEFVAL      { "" }
    ::= { vRtrBgpEvpnEntry 26 }

vRtrBgpEvpnMplsTblLastCh         OBJECT-TYPE
    SYNTAX      TimeStamp
    MAX-ACCESS  read-only
    STATUS      current
    DESCRIPTION
        "The value of vRtrBgpEvpnMplsTblLastCh indicates the sysUpTime at the
         time of the last modification of an entry in the vRtrBgpEvpnMplsTable."
    ::= { vRtrBgpEvpnObjs 3 }

vRtrBgpEvpnMplsTable             OBJECT-TYPE
    SYNTAX      SEQUENCE OF VRtrBgpEvpnMplsEntry
    MAX-ACCESS  not-accessible
    STATUS      current
    DESCRIPTION
        "vRtrBgpEvpnMplsTable contains entries for BGP EVPN MPLS in a VPRN
         service and BGP instance context."
    ::= { vRtrBgpEvpnObjs 4 }

vRtrBgpEvpnMplsEntry             OBJECT-TYPE
    SYNTAX      VRtrBgpEvpnMplsEntry
    MAX-ACCESS  not-accessible
    STATUS      current
    DESCRIPTION
        "A BGP EVPN MPLS entry in the vRtrBgpEvpnMplsTable."
    INDEX       {
        vRtrID,
        vRtrBgpEvpnInstance
    }
    ::= { vRtrBgpEvpnMplsTable 1 }

VRtrBgpEvpnMplsEntry             ::= SEQUENCE
{
    vRtrBgpEvpnMplsLastChanged       TimeStamp,
    vRtrBgpEvpnMplsTnlEncapMpls      TruthValue,
    vRtrBgpEvpnMplsTnlEncapMoUdp     TruthValue
}

vRtrBgpEvpnMplsLastChanged       OBJECT-TYPE
    SYNTAX      TimeStamp
    MAX-ACCESS  read-only
    STATUS      current
    DESCRIPTION
        "The value of vRtrBgpEvpnMplsLastChanged indicates the sysUpTime at the
         time of the last modification of this entry.

         If no changes were made to the entry since the last re-initialization
         of the local network management subsystem, then this object contains a
         zero value."
    ::= { vRtrBgpEvpnMplsEntry 1 }

vRtrBgpEvpnMplsTnlEncapMpls      OBJECT-TYPE
    SYNTAX      TruthValue
    MAX-ACCESS  read-create
    STATUS      current
    DESCRIPTION
        "The value of vRtrBgpEvpnMplsTnlEncapMpls specifies the whether the use
         of MPLS encapsulation is enabled for this service."
    DEFVAL      { true }
    ::= { vRtrBgpEvpnMplsEntry 2 }

vRtrBgpEvpnMplsTnlEncapMoUdp     OBJECT-TYPE
    SYNTAX      TruthValue
    MAX-ACCESS  read-create
    STATUS      current
    DESCRIPTION
        "The value of vRtrBgpEvpnMplsTnlEncapMoUdp specifies the whether the
         use of MPLS over UDP encapsulation is enabled for this service."
    DEFVAL      { false }
    ::= { vRtrBgpEvpnMplsEntry 3 }

vRtrBgpEvpnABTTblLastCh          OBJECT-TYPE
    SYNTAX      TimeStamp
    MAX-ACCESS  read-only
    STATUS      current
    DESCRIPTION
        "The value of vRtrBgpEvpnABTTblLastCh indicates the sysUpTime at the
         time of the last modification of an entry in the
         vRtrBgpEvpnAutoBndTnlTable."
    ::= { vRtrBgpEvpnObjs 5 }

vRtrBgpEvpnAutoBndTnlTable       OBJECT-TYPE
    SYNTAX      SEQUENCE OF VRtrBgpEvpnAutoBndTnlEntry
    MAX-ACCESS  not-accessible
    STATUS      current
    DESCRIPTION
        "The vRtrBgpEvpnAutoBndTnlTable contains entries for supported tunnel
         type which may be chosen as tunnel type within service and BGP
         instance."
    ::= { vRtrBgpEvpnObjs 6 }

vRtrBgpEvpnAutoBndTnlEntry       OBJECT-TYPE
    SYNTAX      VRtrBgpEvpnAutoBndTnlEntry
    MAX-ACCESS  not-accessible
    STATUS      current
    DESCRIPTION
        "An Auto bind tunnel entry in the vRtrBgpEvpnAutoBndTnlTable. Each row
         entry contains the type of tunnel chosen within service."
    INDEX       {
        vRtrID,
        vRtrBgpEvpnInstance
    }
    ::= { vRtrBgpEvpnAutoBndTnlTable 1 }

VRtrBgpEvpnAutoBndTnlEntry       ::= SEQUENCE
{
    vRtrBgpEvpnAutoBndTnlLastChg     TimeStamp,
    vRtrBgpEvpnAutoBndTnlStatus      TResolveStatus,
    vRtrBgpEvpnAutoBndTnlTag         TruthValue,
    vRtrBgpEvpnAutoBndTnlEcmp        Unsigned32,
    vRtrBgpEvpnAutoBndTnlLdp         TruthValue,
    vRtrBgpEvpnAutoBndTnlRsvpTe      TruthValue,
    vRtrBgpEvpnAutoBndTnlSrIsis      TruthValue,
    vRtrBgpEvpnAutoBndTnlSrOspf      TruthValue,
    vRtrBgpEvpnAutoBndTnlBgp         TruthValue,
    vRtrBgpEvpnAutoBndTnlSrTe        TruthValue,
    vRtrBgpEvpnAutoBndTnlUdp         TruthValue,
    vRtrBgpEvpnAutoBndTnlSrPlcy      TruthValue,
    vRtrBgpEvpnBndTnlMplsFwdPlcy     TruthValue,
    vRtrBgpEvpnBndTnlRibApi          TruthValue,
    vRtrBgpEvpnAutoBndTnlSrOspf3     TruthValue,
    vRtrBgpEvpnAutoBndTnlFlexAlgoFb  TruthValue,
    vRtrBgpEvpnAutoBndTnlUntagRt     TBgpUntaggedRouteType
}

vRtrBgpEvpnAutoBndTnlLastChg     OBJECT-TYPE
    SYNTAX      TimeStamp
    MAX-ACCESS  read-only
    STATUS      current
    DESCRIPTION
        "The value of vRtrBgpEvpnAutoBndTnlLastChg indicates the sysUpTime at
         the time of the last modification of this entry."
    ::= { vRtrBgpEvpnAutoBndTnlEntry 1 }

vRtrBgpEvpnAutoBndTnlStatus      OBJECT-TYPE
    SYNTAX      TResolveStatus
    MAX-ACCESS  read-write
    STATUS      current
    DESCRIPTION
        "The value of vRtrBgpEvpnAutoBndTnlStatus specifies the resolution
         status of this entry."
    DEFVAL      { disabled }
    ::= { vRtrBgpEvpnAutoBndTnlEntry 2 }

vRtrBgpEvpnAutoBndTnlTag         OBJECT-TYPE
    SYNTAX      TruthValue
    MAX-ACCESS  read-write
    STATUS      current
    DESCRIPTION
        "The value of vRtrBgpEvpnAutoBndTnlTag specifies whether tunnel-tagging
         is strictly enforced."
    DEFVAL      { false }
    ::= { vRtrBgpEvpnAutoBndTnlEntry 3 }

vRtrBgpEvpnAutoBndTnlEcmp        OBJECT-TYPE
    SYNTAX      Unsigned32 (1..32)
    MAX-ACCESS  read-write
    STATUS      current
    DESCRIPTION
        "The vRtrBgpEvpnAutoBndTnlEcmp specifies the maximum number of equal
         cost paths that can be used for load balancing when binding a BGP-EVPN
         next-hop to a set of LSPs."
    DEFVAL      { 1 }
    ::= { vRtrBgpEvpnAutoBndTnlEntry 4 }

vRtrBgpEvpnAutoBndTnlLdp         OBJECT-TYPE
    SYNTAX      TruthValue
    MAX-ACCESS  read-write
    STATUS      current
    DESCRIPTION
        "The value of vRtrBgpEvpnAutoBndTnlLdp specifies whether LDP type
         tunnel may be chosen as the tunnel within the service."
    DEFVAL      { false }
    ::= { vRtrBgpEvpnAutoBndTnlEntry 5 }

vRtrBgpEvpnAutoBndTnlRsvpTe      OBJECT-TYPE
    SYNTAX      TruthValue
    MAX-ACCESS  read-write
    STATUS      current
    DESCRIPTION
        "The value of vRtrBgpEvpnAutoBndTnlRsvpTe specifies whether RSVP TE
         type tunnel may be chosen as the tunnel within the service."
    DEFVAL      { false }
    ::= { vRtrBgpEvpnAutoBndTnlEntry 6 }

vRtrBgpEvpnAutoBndTnlSrIsis      OBJECT-TYPE
    SYNTAX      TruthValue
    MAX-ACCESS  read-write
    STATUS      current
    DESCRIPTION
        "The value of vRtrBgpEvpnAutoBndTnlSrIsis specifies whether IS-IS type
         tunnel may be chosen as the tunnel within the service."
    DEFVAL      { false }
    ::= { vRtrBgpEvpnAutoBndTnlEntry 7 }

vRtrBgpEvpnAutoBndTnlSrOspf      OBJECT-TYPE
    SYNTAX      TruthValue
    MAX-ACCESS  read-write
    STATUS      current
    DESCRIPTION
        "The value of vRtrBgpEvpnAutoBndTnlSrOspf specifies whether OSPF type
         tunnel may be chosen as the tunnel within the service."
    DEFVAL      { false }
    ::= { vRtrBgpEvpnAutoBndTnlEntry 8 }

vRtrBgpEvpnAutoBndTnlBgp         OBJECT-TYPE
    SYNTAX      TruthValue
    MAX-ACCESS  read-write
    STATUS      current
    DESCRIPTION
        "The value of vRtrBgpEvpnAutoBndTnlBgp specifies whether BGP type
         tunnel may be chosen as the tunnel within the service."
    DEFVAL      { false }
    ::= { vRtrBgpEvpnAutoBndTnlEntry 9 }

vRtrBgpEvpnAutoBndTnlSrTe        OBJECT-TYPE
    SYNTAX      TruthValue
    MAX-ACCESS  read-write
    STATUS      current
    DESCRIPTION
        "The value of vRtrBgpEvpnAutoBndTnlSrTe specifies whether SR-TE type
         tunnel may be chosen as the tunnel within the service."
    DEFVAL      { false }
    ::= { vRtrBgpEvpnAutoBndTnlEntry 10 }

vRtrBgpEvpnAutoBndTnlUdp         OBJECT-TYPE
    SYNTAX      TruthValue
    MAX-ACCESS  read-write
    STATUS      current
    DESCRIPTION
        "The value of vRtrBgpEvpnAutoBndTnlUdp specifies whether UDP type
         tunnel may be chosen as the tunnel within the service."
    DEFVAL      { false }
    ::= { vRtrBgpEvpnAutoBndTnlEntry 11 }

vRtrBgpEvpnAutoBndTnlSrPlcy      OBJECT-TYPE
    SYNTAX      TruthValue
    MAX-ACCESS  read-write
    STATUS      current
    DESCRIPTION
        "The value of vRtrBgpEvpnAutoBndTnlSrPlcy specifies whether
         segment-routing policy tunnel may be chosen as the tunnel within the
         service."
    DEFVAL      { false }
    ::= { vRtrBgpEvpnAutoBndTnlEntry 12 }

vRtrBgpEvpnBndTnlMplsFwdPlcy     OBJECT-TYPE
    SYNTAX      TruthValue
    MAX-ACCESS  read-write
    STATUS      current
    DESCRIPTION
        "The value of vRtrBgpEvpnBndTnlMplsFwdPlcy specifies whether MPLS
         Forwarding policy tunnel may be chosen as the tunnel within the
         service."
    DEFVAL      { false }
    ::= { vRtrBgpEvpnAutoBndTnlEntry 13 }

vRtrBgpEvpnBndTnlRibApi          OBJECT-TYPE
    SYNTAX      TruthValue
    MAX-ACCESS  read-write
    STATUS      current
    DESCRIPTION
        "The value of vRtrBgpEvpnBndTnlRibApi specifies whether RIB API  tunnel
         may be chosen as the tunnel within the service."
    DEFVAL      { false }
    ::= { vRtrBgpEvpnAutoBndTnlEntry 14 }

vRtrBgpEvpnAutoBndTnlSrOspf3     OBJECT-TYPE
    SYNTAX      TruthValue
    MAX-ACCESS  read-write
    STATUS      current
    DESCRIPTION
        "The value of vRtrBgpEvpnAutoBndTnlSrOspf3 specifies whether OSPFv3
         tunnel may be chosen as the tunnel within the service."
    DEFVAL      { false }
    ::= { vRtrBgpEvpnAutoBndTnlEntry 15 }

vRtrBgpEvpnAutoBndTnlFlexAlgoFb  OBJECT-TYPE
    SYNTAX      TruthValue
    MAX-ACCESS  read-write
    STATUS      current
    DESCRIPTION
        "Allow the use of routes with another flex-algo-id than configured as a
         fallback option"
    DEFVAL      { false }
    ::= { vRtrBgpEvpnAutoBndTnlEntry 16 }

vRtrBgpEvpnAutoBndTnlUntagRt     OBJECT-TYPE
    SYNTAX      TBgpUntaggedRouteType
    MAX-ACCESS  read-write
    STATUS      current
    DESCRIPTION
        "The value of vRtrBgpEvpnAutoBndTnlUntagRt specifies the type of tunnel
         used to resolve untagged routes."
    DEFVAL      { none }
    ::= { vRtrBgpEvpnAutoBndTnlEntry 18 }

vRtrBgpEvpnVrfPolicyTblLastCh    OBJECT-TYPE
    SYNTAX      TimeStamp
    MAX-ACCESS  read-only
    STATUS      current
    DESCRIPTION
        "The value of vRtrBgpEvpnVrfPolicyTblLastCh indicates the sysUpTime at
         the time of the last modification of an entry in the
         vRtrBgpEvpnVrfPolicyTable."
    ::= { vRtrBgpEvpnObjs 7 }

vRtrBgpEvpnVrfPolicyTable        OBJECT-TYPE
    SYNTAX      SEQUENCE OF VRtrBgpEvpnVrfPolicyEntry
    MAX-ACCESS  not-accessible
    STATUS      current
    DESCRIPTION
        "The vRtrBgpEvpnVrfPolicyTable contains entries for BGP in a VPRN
         service context."
    ::= { vRtrBgpEvpnObjs 8 }

vRtrBgpEvpnVrfPolicyEntry        OBJECT-TYPE
    SYNTAX      VRtrBgpEvpnVrfPolicyEntry
    MAX-ACCESS  not-accessible
    STATUS      current
    DESCRIPTION
        "The vRtrBgpEvpnVrfPolicyEntry contains BGP related information for a
         specific service."
    INDEX       {
        vRtrID,
        vRtrBgpEvpnInstance
    }
    ::= { vRtrBgpEvpnVrfPolicyTable 1 }

VRtrBgpEvpnVrfPolicyEntry        ::= SEQUENCE
{
    vRtrBgpEvpnVrfPolicyLastChg      TimeStamp,
    vRtrBgpEvpnVrfPolicyImp1         TXLPolicyNameOrExpOrEmpty,
    vRtrBgpEvpnVrfPolicyImp2         TLPolicyNameOrExpOrEmpty,
    vRtrBgpEvpnVrfPolicyImp3         TLPolicyNameOrExpOrEmpty,
    vRtrBgpEvpnVrfPolicyImp4         TLPolicyNameOrExpOrEmpty,
    vRtrBgpEvpnVrfPolicyImp5         TLPolicyNameOrExpOrEmpty,
    vRtrBgpEvpnVrfPolicyImp6         TLPolicyNameOrExpOrEmpty,
    vRtrBgpEvpnVrfPolicyImp7         TLPolicyNameOrExpOrEmpty,
    vRtrBgpEvpnVrfPolicyImp8         TLPolicyNameOrExpOrEmpty,
    vRtrBgpEvpnVrfPolicyImp9         TLPolicyNameOrExpOrEmpty,
    vRtrBgpEvpnVrfPolicyImp10        TLPolicyNameOrExpOrEmpty,
    vRtrBgpEvpnVrfPolicyImp11        TLPolicyNameOrExpOrEmpty,
    vRtrBgpEvpnVrfPolicyImp12        TLPolicyNameOrExpOrEmpty,
    vRtrBgpEvpnVrfPolicyImp13        TLPolicyNameOrExpOrEmpty,
    vRtrBgpEvpnVrfPolicyImp14        TLPolicyNameOrExpOrEmpty,
    vRtrBgpEvpnVrfPolicyImp15        TLPolicyNameOrExpOrEmpty,
    vRtrBgpEvpnVrfPolicyExp1         TXLPolicyNameOrExpOrEmpty,
    vRtrBgpEvpnVrfPolicyExp2         TLPolicyNameOrExpOrEmpty,
    vRtrBgpEvpnVrfPolicyExp3         TLPolicyNameOrExpOrEmpty,
    vRtrBgpEvpnVrfPolicyExp4         TLPolicyNameOrExpOrEmpty,
    vRtrBgpEvpnVrfPolicyExp5         TLPolicyNameOrExpOrEmpty,
    vRtrBgpEvpnVrfPolicyExp6         TLPolicyNameOrExpOrEmpty,
    vRtrBgpEvpnVrfPolicyExp7         TLPolicyNameOrExpOrEmpty,
    vRtrBgpEvpnVrfPolicyExp8         TLPolicyNameOrExpOrEmpty,
    vRtrBgpEvpnVrfPolicyExp9         TLPolicyNameOrExpOrEmpty,
    vRtrBgpEvpnVrfPolicyExp10        TLPolicyNameOrExpOrEmpty,
    vRtrBgpEvpnVrfPolicyExp11        TLPolicyNameOrExpOrEmpty,
    vRtrBgpEvpnVrfPolicyExp12        TLPolicyNameOrExpOrEmpty,
    vRtrBgpEvpnVrfPolicyExp13        TLPolicyNameOrExpOrEmpty,
    vRtrBgpEvpnVrfPolicyExp14        TLPolicyNameOrExpOrEmpty,
    vRtrBgpEvpnVrfPolicyExp15        TLPolicyNameOrExpOrEmpty,
    vRtrBgpEvpnVrfPolicyCreateOrig   TmnxCreateOrigin
}

vRtrBgpEvpnVrfPolicyLastChg      OBJECT-TYPE
    SYNTAX      TimeStamp
    MAX-ACCESS  read-only
    STATUS      current
    DESCRIPTION
        "The value of vRtrBgpEvpnVrfPolicyLastChg indicates the sysUpTime at
         the time of the last modification of this entry."
    ::= { vRtrBgpEvpnVrfPolicyEntry 1 }

vRtrBgpEvpnVrfPolicyImp1         OBJECT-TYPE
    SYNTAX      TXLPolicyNameOrExpOrEmpty
    MAX-ACCESS  read-create
    STATUS      current
    DESCRIPTION
        "The value of vRtrBgpEvpnVrfPolicyImp1 specifies the first
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 2 }

vRtrBgpEvpnVrfPolicyImp2         OBJECT-TYPE
    SYNTAX      TLPolicyNameOrExpOrEmpty
    MAX-ACCESS  read-create
    STATUS      current
    DESCRIPTION
        "The value of vRtrBgpEvpnVrfPolicyImp2 specifies the second
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 3 }

vRtrBgpEvpnVrfPolicyImp3         OBJECT-TYPE
    SYNTAX      TLPolicyNameOrExpOrEmpty
    MAX-ACCESS  read-create
    STATUS      current
    DESCRIPTION
        "The value of vRtrBgpEvpnVrfPolicyImp3 specifies the third
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 4 }

vRtrBgpEvpnVrfPolicyImp4         OBJECT-TYPE
    SYNTAX      TLPolicyNameOrExpOrEmpty
    MAX-ACCESS  read-create
    STATUS      current
    DESCRIPTION
        "The value of vRtrBgpEvpnVrfPolicyImp4 specifies the fourth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 5 }

vRtrBgpEvpnVrfPolicyImp5         OBJECT-TYPE
    SYNTAX      TLPolicyNameOrExpOrEmpty
    MAX-ACCESS  read-create
    STATUS      current
    DESCRIPTION
        "The value of vRtrBgpEvpnVrfPolicyImp5 specifies the fifth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 6 }

vRtrBgpEvpnVrfPolicyImp6         OBJECT-TYPE
    SYNTAX      TLPolicyNameOrExpOrEmpty
    MAX-ACCESS  read-create
    STATUS      current
    DESCRIPTION
        "The value of vRtrBgpEvpnVrfPolicyImp6 specifies the sixth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 7 }

vRtrBgpEvpnVrfPolicyImp7         OBJECT-TYPE
    SYNTAX      TLPolicyNameOrExpOrEmpty
    MAX-ACCESS  read-create
    STATUS      current
    DESCRIPTION
        "The value of vRtrBgpEvpnVrfPolicyImp7 specifies the seventh
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 8 }

vRtrBgpEvpnVrfPolicyImp8         OBJECT-TYPE
    SYNTAX      TLPolicyNameOrExpOrEmpty
    MAX-ACCESS  read-create
    STATUS      current
    DESCRIPTION
        "The value of vRtrBgpEvpnVrfPolicyImp8 specifies the eighth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 9 }

vRtrBgpEvpnVrfPolicyImp9         OBJECT-TYPE
    SYNTAX      TLPolicyNameOrExpOrEmpty
    MAX-ACCESS  read-create
    STATUS      current
    DESCRIPTION
        "The value of vRtrBgpEvpnVrfPolicyImp9 specifies the ninth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp5, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 10 }

vRtrBgpEvpnVrfPolicyImp10        OBJECT-TYPE
    SYNTAX      TLPolicyNameOrExpOrEmpty
    MAX-ACCESS  read-create
    STATUS      current
    DESCRIPTION
        "The value of vRtrBgpEvpnVrfPolicyImp10 specifies the tenth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 11 }

vRtrBgpEvpnVrfPolicyImp11        OBJECT-TYPE
    SYNTAX      TLPolicyNameOrExpOrEmpty
    MAX-ACCESS  read-create
    STATUS      current
    DESCRIPTION
        "The value of vRtrBgpEvpnVrfPolicyImp11 specifies the eleventh
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 12 }

vRtrBgpEvpnVrfPolicyImp12        OBJECT-TYPE
    SYNTAX      TLPolicyNameOrExpOrEmpty
    MAX-ACCESS  read-create
    STATUS      current
    DESCRIPTION
        "The value of vRtrBgpEvpnVrfPolicyImp12 specifies the twelfth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 13 }

vRtrBgpEvpnVrfPolicyImp13        OBJECT-TYPE
    SYNTAX      TLPolicyNameOrExpOrEmpty
    MAX-ACCESS  read-create
    STATUS      current
    DESCRIPTION
        "The value of vRtrBgpEvpnVrfPolicyImp13 specifies the thirteenth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 14 }

vRtrBgpEvpnVrfPolicyImp14        OBJECT-TYPE
    SYNTAX      TLPolicyNameOrExpOrEmpty
    MAX-ACCESS  read-create
    STATUS      current
    DESCRIPTION
        "The value of vRtrBgpEvpnVrfPolicyImp14 specifies the fourteenth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 15 }

vRtrBgpEvpnVrfPolicyImp15        OBJECT-TYPE
    SYNTAX      TLPolicyNameOrExpOrEmpty
    MAX-ACCESS  read-create
    STATUS      current
    DESCRIPTION
        "The value of vRtrBgpEvpnVrfPolicyImp15 specifies the fifteenth
         policy to be used for determining which routes are imported
         into the VRF for this virtual router.  If no import policy
         is defined, no routes are accepted into the VRF.

         If multiple policy names are specified, the policies are evaluated
         in the order they are specified.  The first policy that matches
         is applied.

         The import policy name list, vRtrBgpEvpnVrfPolicyImp1 through
         vRtrBgpEvpnVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 16 }

vRtrBgpEvpnVrfPolicyExp1         OBJECT-TYPE
    SYNTAX      TXLPolicyNameOrExpOrEmpty
    MAX-ACCESS  read-create
    STATUS      current
    DESCRIPTION
        "The value of vRtrBgpEvpnVrfPolicyExp1 specifies the first
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 17 }

vRtrBgpEvpnVrfPolicyExp2         OBJECT-TYPE
    SYNTAX      TLPolicyNameOrExpOrEmpty
    MAX-ACCESS  read-create
    STATUS      current
    DESCRIPTION
        "The value of vRtrBgpEvpnVrfPolicyExp2 specifies the second
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 18 }

vRtrBgpEvpnVrfPolicyExp3         OBJECT-TYPE
    SYNTAX      TLPolicyNameOrExpOrEmpty
    MAX-ACCESS  read-create
    STATUS      current
    DESCRIPTION
        "The value of vRtrBgpEvpnVrfPolicyExp3 specifies the third
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 19 }

vRtrBgpEvpnVrfPolicyExp4         OBJECT-TYPE
    SYNTAX      TLPolicyNameOrExpOrEmpty
    MAX-ACCESS  read-create
    STATUS      current
    DESCRIPTION
        "The value of vRtrBgpEvpnVrfPolicyExp4 specifies the fourth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 20 }

vRtrBgpEvpnVrfPolicyExp5         OBJECT-TYPE
    SYNTAX      TLPolicyNameOrExpOrEmpty
    MAX-ACCESS  read-create
    STATUS      current
    DESCRIPTION
        "The value of vRtrBgpEvpnVrfPolicyExp5 specifies the fifth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 21 }

vRtrBgpEvpnVrfPolicyExp6         OBJECT-TYPE
    SYNTAX      TLPolicyNameOrExpOrEmpty
    MAX-ACCESS  read-create
    STATUS      current
    DESCRIPTION
        "The value of vRtrBgpEvpnVrfPolicyExp6 specifies the sixth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 22 }

vRtrBgpEvpnVrfPolicyExp7         OBJECT-TYPE
    SYNTAX      TLPolicyNameOrExpOrEmpty
    MAX-ACCESS  read-create
    STATUS      current
    DESCRIPTION
        "The value of vRtrBgpEvpnVrfPolicyExp7 specifies the seventh
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 23 }

vRtrBgpEvpnVrfPolicyExp8         OBJECT-TYPE
    SYNTAX      TLPolicyNameOrExpOrEmpty
    MAX-ACCESS  read-create
    STATUS      current
    DESCRIPTION
        "The value of vRtrBgpEvpnVrfPolicyExp8 specifies the eighth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 24 }

vRtrBgpEvpnVrfPolicyExp9         OBJECT-TYPE
    SYNTAX      TLPolicyNameOrExpOrEmpty
    MAX-ACCESS  read-create
    STATUS      current
    DESCRIPTION
        "The value of vRtrBgpEvpnVrfPolicyExp9 specifies the ninth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 25 }

vRtrBgpEvpnVrfPolicyExp10        OBJECT-TYPE
    SYNTAX      TLPolicyNameOrExpOrEmpty
    MAX-ACCESS  read-create
    STATUS      current
    DESCRIPTION
        "The value of vRtrBgpEvpnVrfPolicyExp10 specifies the tenth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 26 }

vRtrBgpEvpnVrfPolicyExp11        OBJECT-TYPE
    SYNTAX      TLPolicyNameOrExpOrEmpty
    MAX-ACCESS  read-create
    STATUS      current
    DESCRIPTION
        "The value of vRtrBgpEvpnVrfPolicyExp11 specifies the eleventh
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 27 }

vRtrBgpEvpnVrfPolicyExp12        OBJECT-TYPE
    SYNTAX      TLPolicyNameOrExpOrEmpty
    MAX-ACCESS  read-create
    STATUS      current
    DESCRIPTION
        "The value of vRtrBgpEvpnVrfPolicyExp12 specifies the twelfth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 28 }

vRtrBgpEvpnVrfPolicyExp13        OBJECT-TYPE
    SYNTAX      TLPolicyNameOrExpOrEmpty
    MAX-ACCESS  read-create
    STATUS      current
    DESCRIPTION
        "The value of vRtrBgpEvpnVrfPolicyExp13 specifies the thirteenth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 29 }

vRtrBgpEvpnVrfPolicyExp14        OBJECT-TYPE
    SYNTAX      TLPolicyNameOrExpOrEmpty
    MAX-ACCESS  read-create
    STATUS      current
    DESCRIPTION
        "The value of vRtrBgpEvpnVrfPolicyExp14 specifies the fourteenth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 30 }

vRtrBgpEvpnVrfPolicyExp15        OBJECT-TYPE
    SYNTAX      TLPolicyNameOrExpOrEmpty
    MAX-ACCESS  read-create
    STATUS      current
    DESCRIPTION
        "The value of vRtrBgpEvpnVrfPolicyExp15 specifies the fifteenth
         policy to be used for determining which routes are exported
         from the VRF for this virtual router.  If no export policy
         is defined, no routes are exported from the VRF.

         If multiple policy names are specified, the policies are evaluated
         in the order they are specified.  The first policy that matches
         is applied.

         The export policy name list, vRtrBgpEvpnVrfPolicyExp1 through
         vRtrBgpEvpnVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVrfPolicyEntry 31 }

vRtrBgpEvpnVrfPolicyCreateOrig   OBJECT-TYPE
    SYNTAX      TmnxCreateOrigin
    MAX-ACCESS  read-only
    STATUS      current
    DESCRIPTION
        "The value of vRtrBgpEvpnVrfPolicyCreateOrig indicates the mechanism
         used to create this entry."
    DEFVAL      { manual }
    ::= { vRtrBgpEvpnVrfPolicyEntry 32 }

vRtrBgpEvpnVxTblLastCh           OBJECT-TYPE
    SYNTAX      TimeStamp
    MAX-ACCESS  read-only
    STATUS      current
    DESCRIPTION
        "The value of vRtrBgpEvpnVxTblLastCh indicates the sysUpTime at the
         time of the last modification of an entry in the vRtrBgpEvpnVxTable."
    ::= { vRtrBgpEvpnObjs 9 }

vRtrBgpEvpnVxTable               OBJECT-TYPE
    SYNTAX      SEQUENCE OF VRtrBgpEvpnVxEntry
    MAX-ACCESS  not-accessible
    STATUS      current
    DESCRIPTION
        "The vRtrBgpEvpnVxTable contains entries for all the BGP EVPN instances
         for a particular VPRN service."
    ::= { vRtrBgpEvpnObjs 10 }

vRtrBgpEvpnVxEntry               OBJECT-TYPE
    SYNTAX      VRtrBgpEvpnVxEntry
    MAX-ACCESS  not-accessible
    STATUS      current
    DESCRIPTION
        "A BGP EVPN instance entry in the vRtrBgpEvpnVxTable."
    INDEX       {
        vRtrID,
        vRtrBgpEvpnVxBgpInstance
    }
    ::= { vRtrBgpEvpnVxTable 1 }

VRtrBgpEvpnVxEntry               ::= SEQUENCE
{
    vRtrBgpEvpnVxBgpInstance         Integer32,
    vRtrBgpEvpnVxRowStatus           RowStatus,
    vRtrBgpEvpnVxLastChanged         TimeStamp,
    vRtrBgpEvpnVxAdminState          TmnxEnabledDisabled,
    vRtrBgpEvpnVxDefRtTag            Unsigned32,
    vRtrBgpEvpnVxVrfRD               TmnxVPNRouteDistinguisher,
    vRtrBgpEvpnVxExportRteTarget     TNamedItemOrEmpty,
    vRtrBgpEvpnVxImportRteTarget     TNamedItemOrEmpty,
    vRtrBgpEvpnVxAutoRD              TruthValue,
    vRtrBgpEvpnVxOperRD              TmnxVPNRouteDistinguisher,
    vRtrBgpEvpnVxOperRDType          TmnxRouteDistType,
    vRtrBgpEvpnVxVrfTarget           TNamedItemOrEmpty,
    vRtrBgpEvpnVxDomainId            TmnxDPathDomainId,
    vRtrBgpEvpnVxEvi                 Unsigned32,
    vRtrBgpEvpnVxAdLinkBw            TruthValue,
    vRtrBgpEvpnVxAdLinkBwWeight      Unsigned32,
    vRtrBgpEvpnVxAdLinkBwMaxWeight   Unsigned32,
    vRtrBgpEvpnVxWeightedEcmp        TruthValue,
    vRtrBgpEvpnVxOperState           TmnxEnabledDisabled,
    vRtrBgpEvpnVxInstance            Integer32,
    vRtrBgpEvpnVxGwIpAdvertise       TruthValue,
    vRtrBgpEvpnVxGwIpResolve         TruthValue
}

vRtrBgpEvpnVxBgpInstance         OBJECT-TYPE
    SYNTAX      Integer32 (1..1)
    MAX-ACCESS  not-accessible
    STATUS      current
    DESCRIPTION
        "The value of vRtrBgpEvpnVxBgpInstance specifies the BGP instance used
         with this service."
    ::= { vRtrBgpEvpnVxEntry 1 }

vRtrBgpEvpnVxRowStatus           OBJECT-TYPE
    SYNTAX      RowStatus
    MAX-ACCESS  read-create
    STATUS      current
    DESCRIPTION
        "The value of the object  vRtrBgpEvpnVxRowStatus
         specifies the status of this row."
    ::= { vRtrBgpEvpnVxEntry 2 }

vRtrBgpEvpnVxLastChanged         OBJECT-TYPE
    SYNTAX      TimeStamp
    MAX-ACCESS  read-only
    STATUS      current
    DESCRIPTION
        "The value of the object vRtrBgpEvpnVxLastChanged indicates the
         timestamp of the modification of this entry."
    ::= { vRtrBgpEvpnVxEntry 3 }

vRtrBgpEvpnVxAdminState          OBJECT-TYPE
    SYNTAX      TmnxEnabledDisabled
    MAX-ACCESS  read-create
    STATUS      current
    DESCRIPTION
        "The value of vRtrBgpEvpnVxAdminState specifies if the BGP instance is
         enabled or not.

         The admin state cannot be set in the same request as
         vRtrBgpEvpnVxRowStatus, if no explicit route-distinguisher and
         route-targets are configured for the BGP instance (referenced by
         vRtrBgpEvpnVxBgpInstance)."
    DEFVAL      { disabled }
    ::= { vRtrBgpEvpnVxEntry 4 }

vRtrBgpEvpnVxDefRtTag            OBJECT-TYPE
    SYNTAX      Unsigned32 (0..255)
    MAX-ACCESS  read-create
    STATUS      current
    DESCRIPTION
        "The value of vRtrBgpEvpnVxDefRtTag specifies the default route tag
         passed by EVPN onto the policy module so that it can be matched on
         export policies."
    DEFVAL      { 0 }
    ::= { vRtrBgpEvpnVxEntry 8 }

vRtrBgpEvpnVxVrfRD               OBJECT-TYPE
    SYNTAX      TmnxVPNRouteDistinguisher
    MAX-ACCESS  read-create
    STATUS      current
    DESCRIPTION
        "The value of vRtrBgpEvpnVxVrfRD specifies the high-order 6 bytes used
         to compose the Virtual Routing and Forwarding (VRF) instance to use
         for NLRI in BGP in this VPRN service.

         SNMP set of vRtrBgpEvpnVxVrfRD to non-default value will automatically
         set vRtrBgpEvpnVxAutoRD to 'false'."
    DEFVAL      { '0000000000000000'H }
    ::= { vRtrBgpEvpnVxEntry 9 }

vRtrBgpEvpnVxExportRteTarget     OBJECT-TYPE
    SYNTAX      TNamedItemOrEmpty
    MAX-ACCESS  read-create
    STATUS      current
    DESCRIPTION
        "The value of vRtrBgpEvpnVxExportRteTarget specifies the
         extended community name for the default export policy
         to use for BGP  in this VPRN service.

         It must be set to default before it is set to a non-default value."
    DEFVAL      { "" }
    ::= { vRtrBgpEvpnVxEntry 10 }

vRtrBgpEvpnVxImportRteTarget     OBJECT-TYPE
    SYNTAX      TNamedItemOrEmpty
    MAX-ACCESS  read-create
    STATUS      current
    DESCRIPTION
        "The value of vRtrBgpEvpnVxImportRteTarget specifies the
         extended community name for the default import policy
         to use for BGP  in this VPRN service.

         It must be set to default before it is set to a non-default value."
    DEFVAL      { "" }
    ::= { vRtrBgpEvpnVxEntry 11 }

vRtrBgpEvpnVxAutoRD              OBJECT-TYPE
    SYNTAX      TruthValue
    MAX-ACCESS  read-create
    STATUS      current
    DESCRIPTION
        "The value of vRtrBgpEvpnVxAutoRD specifies that system will
         automatically select a value for the route-distinguisher from  from
         TIMETRA-SERV-MIB::svcBgpAutoRDType1Group.

         An 'inconsistentValue' error is returned when trying to set
         vRtrBgpEvpnVxAutoRD to 'true' and there is no route-distinguisher
         available from TIMETRA-SERV-MIB::svcBgpAutoRDType1Group.

         SNMP set of vRtrBgpEvpnVxAutoRD to 'true' will automatically set
         vRtrBgpEvpnVxVrfRD to all zeroes."
    DEFVAL      { false }
    ::= { vRtrBgpEvpnVxEntry 12 }

vRtrBgpEvpnVxOperRD              OBJECT-TYPE
    SYNTAX      TmnxVPNRouteDistinguisher
    MAX-ACCESS  read-only
    STATUS      current
    DESCRIPTION
        "The value of vRtrBgpEvpnVxOperRD indicates the route-distinguisher
         value in use by the system for this service."
    ::= { vRtrBgpEvpnVxEntry 13 }

vRtrBgpEvpnVxOperRDType          OBJECT-TYPE
    SYNTAX      TmnxRouteDistType
    MAX-ACCESS  read-only
    STATUS      current
    DESCRIPTION
        "The value of vRtrBgpEvpnVxOperRDType indicates the type of
         route-distinguisher value in use by the system for this service."
    ::= { vRtrBgpEvpnVxEntry 14 }

vRtrBgpEvpnVxVrfTarget           OBJECT-TYPE
    SYNTAX      TNamedItemOrEmpty
    MAX-ACCESS  read-create
    STATUS      current
    DESCRIPTION
        "The value of vRtrBgpEvpnVxVrfTarget specifies the extended community
         name for the default vrf-import or vrf-export policy to use for the
         vRtrID if no entries are configured in the vRtrBgpEvpnVxVrfPolicyTable
         for this vRtrID instance.

         This object can not be set if either vRtrBgpEvpnVxExportRteTarget or
         vRtrBgpEvpnVxImportRteTarget has been set."
    ::= { vRtrBgpEvpnVxEntry 15 }

vRtrBgpEvpnVxDomainId            OBJECT-TYPE
    SYNTAX      TmnxDPathDomainId
    MAX-ACCESS  read-create
    STATUS      current
    DESCRIPTION
        "The value of vRtrBgpEvpnVxDomainId specifies the Domain ID used in
         D-Path for routes advertisement for BGP EVPN VXLAN service."
    DEFVAL      { '000000000000'H }
    ::= { vRtrBgpEvpnVxEntry 16 }

vRtrBgpEvpnVxEvi                 OBJECT-TYPE
    SYNTAX      Unsigned32 (0..16777215)
    MAX-ACCESS  read-create
    STATUS      current
    DESCRIPTION
        "BGP EVPN identifier used for the service-carving algorithm used for
         multi-homing and for auto-deriving the route-distinguisher and
         route-target."
    DEFVAL      { 0 }
    ::= { vRtrBgpEvpnVxEntry 17 }

vRtrBgpEvpnVxAdLinkBw            OBJECT-TYPE
    SYNTAX      TruthValue
    MAX-ACCESS  read-create
    STATUS      current
    DESCRIPTION
        "The value of vRtrBgpEvpnVxAdLinkBw specifies whether to advertise link
         bandwidth for evpn-ifl routes."
    DEFVAL      { false }
    ::= { vRtrBgpEvpnVxEntry 18 }

vRtrBgpEvpnVxAdLinkBwWeight      OBJECT-TYPE
    SYNTAX      Unsigned32 (0 | 1..128)
    MAX-ACCESS  read-create
    STATUS      current
    DESCRIPTION
        "The value of vRtrBgpEvpnVxAdLinkBwWeight specifies the weight to be
         advertised with evpn-ifl routes. This is effective only when
         vRtrBgpEvpnVxAdLinkBwWeight is enabled."
    DEFVAL      { 0 }
    ::= { vRtrBgpEvpnVxEntry 19 }

vRtrBgpEvpnVxAdLinkBwMaxWeight   OBJECT-TYPE
    SYNTAX      Unsigned32 (1..128)
    MAX-ACCESS  read-create
    STATUS      current
    DESCRIPTION
        "The value of vRtrBgpEvpnVxAdLinkBwMaxWeight specifies the maximum
         weight to be advertised with evpn-ifl routes. This is effective only
         when  vRtrBgpEvpnVxAdLinkBwMaxWeight is enabled."
    DEFVAL      { 128 }
    ::= { vRtrBgpEvpnVxEntry 20 }

vRtrBgpEvpnVxWeightedEcmp        OBJECT-TYPE
    SYNTAX      TruthValue
    MAX-ACCESS  read-create
    STATUS      current
    DESCRIPTION
        "The value of vRtrBgpEvpnVxWeightedEcmp specifies whether unequal ecmp
         will be performed based on link bandwidth weights for evpn-ifl routes."
    DEFVAL      { false }
    ::= { vRtrBgpEvpnVxEntry 21 }

vRtrBgpEvpnVxOperState           OBJECT-TYPE
    SYNTAX      TmnxEnabledDisabled
    MAX-ACCESS  read-only
    STATUS      current
    DESCRIPTION
        "The vRtrBgpEvpnVxOperState indicates if the VPRN BGP EVPN VXLAN
         instance is enabled or not."
    ::= { vRtrBgpEvpnVxEntry 22 }

vRtrBgpEvpnVxInstance            OBJECT-TYPE
    SYNTAX      Integer32 (1)
    MAX-ACCESS  read-create
    STATUS      current
    DESCRIPTION
        "The value of vRtrBgpEvpnVxInstance specifies the VXLAN instance used
         for this entry."
    DEFVAL      { 1 }
    ::= { vRtrBgpEvpnVxEntry 23 }

vRtrBgpEvpnVxGwIpAdvertise       OBJECT-TYPE
    SYNTAX      TruthValue
    MAX-ACCESS  read-create
    STATUS      current
    DESCRIPTION
        "The value of vRtrBgpEvpnVxGwIpAdvertise specifies whether to advertise
         the GW IP address for evpn-ifl routes."
    DEFVAL      { false }
    ::= { vRtrBgpEvpnVxEntry 24 }

vRtrBgpEvpnVxGwIpResolve         OBJECT-TYPE
    SYNTAX      TruthValue
    MAX-ACCESS  read-create
    STATUS      current
    DESCRIPTION
        "The value of vRtrBgpEvpnVxGwIpResolve specifies whether the GW IP
         addresses for the evpn-ifl routes should be processed."
    DEFVAL      { false }
    ::= { vRtrBgpEvpnVxEntry 25 }

vRtrBgpEvpnVxVrfPlcyTblLastCh    OBJECT-TYPE
    SYNTAX      TimeStamp
    MAX-ACCESS  read-only
    STATUS      current
    DESCRIPTION
        "The value of vRtrBgpEvpnVxVrfPlcyTblLastCh indicates the sysUpTime at
         the time of the last modification of an entry in the
         vRtrBgpEvpnVxVrfPolicyTable."
    ::= { vRtrBgpEvpnObjs 11 }

vRtrBgpEvpnVxVrfPolicyTable      OBJECT-TYPE
    SYNTAX      SEQUENCE OF VRtrBgpEvpnVxVrfPolicyEntry
    MAX-ACCESS  not-accessible
    STATUS      current
    DESCRIPTION
        "The vRtrBgpEvpnVxVrfPolicyTable contains entries for BGP in a VPRN
         service context."
    ::= { vRtrBgpEvpnObjs 12 }

vRtrBgpEvpnVxVrfPolicyEntry      OBJECT-TYPE
    SYNTAX      VRtrBgpEvpnVxVrfPolicyEntry
    MAX-ACCESS  not-accessible
    STATUS      current
    DESCRIPTION
        "The vRtrBgpEvpnVxVrfPolicyEntry contains BGP related information for a
         specific service."
    INDEX       {
        vRtrID,
        vRtrBgpEvpnVxBgpInstance
    }
    ::= { vRtrBgpEvpnVxVrfPolicyTable 1 }

VRtrBgpEvpnVxVrfPolicyEntry      ::= SEQUENCE
{
    vRtrBgpEvpnVxVrfPolicyLastChg    TimeStamp,
    vRtrBgpEvpnVxVrfPolicyImp1       TXLPolicyNameOrExpOrEmpty,
    vRtrBgpEvpnVxVrfPolicyImp2       TLPolicyNameOrExpOrEmpty,
    vRtrBgpEvpnVxVrfPolicyImp3       TLPolicyNameOrExpOrEmpty,
    vRtrBgpEvpnVxVrfPolicyImp4       TLPolicyNameOrExpOrEmpty,
    vRtrBgpEvpnVxVrfPolicyImp5       TLPolicyNameOrExpOrEmpty,
    vRtrBgpEvpnVxVrfPolicyImp6       TLPolicyNameOrExpOrEmpty,
    vRtrBgpEvpnVxVrfPolicyImp7       TLPolicyNameOrExpOrEmpty,
    vRtrBgpEvpnVxVrfPolicyImp8       TLPolicyNameOrExpOrEmpty,
    vRtrBgpEvpnVxVrfPolicyImp9       TLPolicyNameOrExpOrEmpty,
    vRtrBgpEvpnVxVrfPolicyImp10      TLPolicyNameOrExpOrEmpty,
    vRtrBgpEvpnVxVrfPolicyImp11      TLPolicyNameOrExpOrEmpty,
    vRtrBgpEvpnVxVrfPolicyImp12      TLPolicyNameOrExpOrEmpty,
    vRtrBgpEvpnVxVrfPolicyImp13      TLPolicyNameOrExpOrEmpty,
    vRtrBgpEvpnVxVrfPolicyImp14      TLPolicyNameOrExpOrEmpty,
    vRtrBgpEvpnVxVrfPolicyImp15      TLPolicyNameOrExpOrEmpty,
    vRtrBgpEvpnVxVrfPolicyExp1       TXLPolicyNameOrExpOrEmpty,
    vRtrBgpEvpnVxVrfPolicyExp2       TLPolicyNameOrExpOrEmpty,
    vRtrBgpEvpnVxVrfPolicyExp3       TLPolicyNameOrExpOrEmpty,
    vRtrBgpEvpnVxVrfPolicyExp4       TLPolicyNameOrExpOrEmpty,
    vRtrBgpEvpnVxVrfPolicyExp5       TLPolicyNameOrExpOrEmpty,
    vRtrBgpEvpnVxVrfPolicyExp6       TLPolicyNameOrExpOrEmpty,
    vRtrBgpEvpnVxVrfPolicyExp7       TLPolicyNameOrExpOrEmpty,
    vRtrBgpEvpnVxVrfPolicyExp8       TLPolicyNameOrExpOrEmpty,
    vRtrBgpEvpnVxVrfPolicyExp9       TLPolicyNameOrExpOrEmpty,
    vRtrBgpEvpnVxVrfPolicyExp10      TLPolicyNameOrExpOrEmpty,
    vRtrBgpEvpnVxVrfPolicyExp11      TLPolicyNameOrExpOrEmpty,
    vRtrBgpEvpnVxVrfPolicyExp12      TLPolicyNameOrExpOrEmpty,
    vRtrBgpEvpnVxVrfPolicyExp13      TLPolicyNameOrExpOrEmpty,
    vRtrBgpEvpnVxVrfPolicyExp14      TLPolicyNameOrExpOrEmpty,
    vRtrBgpEvpnVxVrfPolicyExp15      TLPolicyNameOrExpOrEmpty,
    vRtrBgpEvpnVxVrfPolicyCreateOrig TmnxCreateOrigin
}

vRtrBgpEvpnVxVrfPolicyLastChg    OBJECT-TYPE
    SYNTAX      TimeStamp
    MAX-ACCESS  read-only
    STATUS      current
    DESCRIPTION
        "The value of vRtrBgpEvpnVxVrfPolicyLastChg indicates the sysUpTime at
         the time of the last modification of this entry."
    ::= { vRtrBgpEvpnVxVrfPolicyEntry 1 }

vRtrBgpEvpnVxVrfPolicyImp1       OBJECT-TYPE
    SYNTAX      TXLPolicyNameOrExpOrEmpty
    MAX-ACCESS  read-create
    STATUS      current
    DESCRIPTION
        "The value of vRtrBgpEvpnVxVrfPolicyImp1 specifies the first
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 2 }

vRtrBgpEvpnVxVrfPolicyImp2       OBJECT-TYPE
    SYNTAX      TLPolicyNameOrExpOrEmpty
    MAX-ACCESS  read-create
    STATUS      current
    DESCRIPTION
        "The value of vRtrBgpEvpnVxVrfPolicyImp2 specifies the second
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 3 }

vRtrBgpEvpnVxVrfPolicyImp3       OBJECT-TYPE
    SYNTAX      TLPolicyNameOrExpOrEmpty
    MAX-ACCESS  read-create
    STATUS      current
    DESCRIPTION
        "The value of vRtrBgpEvpnVxVrfPolicyImp3 specifies the third
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 4 }

vRtrBgpEvpnVxVrfPolicyImp4       OBJECT-TYPE
    SYNTAX      TLPolicyNameOrExpOrEmpty
    MAX-ACCESS  read-create
    STATUS      current
    DESCRIPTION
        "The value of vRtrBgpEvpnVxVrfPolicyImp4 specifies the fourth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 5 }

vRtrBgpEvpnVxVrfPolicyImp5       OBJECT-TYPE
    SYNTAX      TLPolicyNameOrExpOrEmpty
    MAX-ACCESS  read-create
    STATUS      current
    DESCRIPTION
        "The value of vRtrBgpEvpnVxVrfPolicyImp5 specifies the fifth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 6 }

vRtrBgpEvpnVxVrfPolicyImp6       OBJECT-TYPE
    SYNTAX      TLPolicyNameOrExpOrEmpty
    MAX-ACCESS  read-create
    STATUS      current
    DESCRIPTION
        "The value of vRtrBgpEvpnVxVrfPolicyImp6 specifies the sixth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 7 }

vRtrBgpEvpnVxVrfPolicyImp7       OBJECT-TYPE
    SYNTAX      TLPolicyNameOrExpOrEmpty
    MAX-ACCESS  read-create
    STATUS      current
    DESCRIPTION
        "The value of vRtrBgpEvpnVxVrfPolicyImp7 specifies the seventh
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 8 }

vRtrBgpEvpnVxVrfPolicyImp8       OBJECT-TYPE
    SYNTAX      TLPolicyNameOrExpOrEmpty
    MAX-ACCESS  read-create
    STATUS      current
    DESCRIPTION
        "The value of vRtrBgpEvpnVxVrfPolicyImp8 specifies the eighth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 9 }

vRtrBgpEvpnVxVrfPolicyImp9       OBJECT-TYPE
    SYNTAX      TLPolicyNameOrExpOrEmpty
    MAX-ACCESS  read-create
    STATUS      current
    DESCRIPTION
        "The value of vRtrBgpEvpnVxVrfPolicyImp9 specifies the ninth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp5, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 10 }

vRtrBgpEvpnVxVrfPolicyImp10      OBJECT-TYPE
    SYNTAX      TLPolicyNameOrExpOrEmpty
    MAX-ACCESS  read-create
    STATUS      current
    DESCRIPTION
        "The value of vRtrBgpEvpnVxVrfPolicyImp10 specifies the tenth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 11 }

vRtrBgpEvpnVxVrfPolicyImp11      OBJECT-TYPE
    SYNTAX      TLPolicyNameOrExpOrEmpty
    MAX-ACCESS  read-create
    STATUS      current
    DESCRIPTION
        "The value of vRtrBgpEvpnVxVrfPolicyImp11 specifies the eleventh
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 12 }

vRtrBgpEvpnVxVrfPolicyImp12      OBJECT-TYPE
    SYNTAX      TLPolicyNameOrExpOrEmpty
    MAX-ACCESS  read-create
    STATUS      current
    DESCRIPTION
        "The value of vRtrBgpEvpnVxVrfPolicyImp12 specifies the twelfth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 13 }

vRtrBgpEvpnVxVrfPolicyImp13      OBJECT-TYPE
    SYNTAX      TLPolicyNameOrExpOrEmpty
    MAX-ACCESS  read-create
    STATUS      current
    DESCRIPTION
        "The value of vRtrBgpEvpnVxVrfPolicyImp13 specifies the thirteenth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 14 }

vRtrBgpEvpnVxVrfPolicyImp14      OBJECT-TYPE
    SYNTAX      TLPolicyNameOrExpOrEmpty
    MAX-ACCESS  read-create
    STATUS      current
    DESCRIPTION
        "The value of vRtrBgpEvpnVxVrfPolicyImp14 specifies the fourteenth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 15 }

vRtrBgpEvpnVxVrfPolicyImp15      OBJECT-TYPE
    SYNTAX      TLPolicyNameOrExpOrEmpty
    MAX-ACCESS  read-create
    STATUS      current
    DESCRIPTION
        "The value of vRtrBgpEvpnVxVrfPolicyImp15 specifies the fifteenth
         policy to be used for determining which routes are imported
         into the VRF for this virtual router.  If no import policy
         is defined, no routes are accepted into the VRF.

         If multiple policy names are specified, the policies are evaluated
         in the order they are specified.  The first policy that matches
         is applied.

         The import policy name list, vRtrBgpEvpnVxVrfPolicyImp1 through
         vRtrBgpEvpnVxVrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 16 }

vRtrBgpEvpnVxVrfPolicyExp1       OBJECT-TYPE
    SYNTAX      TXLPolicyNameOrExpOrEmpty
    MAX-ACCESS  read-create
    STATUS      current
    DESCRIPTION
        "The value of vRtrBgpEvpnVxVrfPolicyExp1 specifies the first
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 17 }

vRtrBgpEvpnVxVrfPolicyExp2       OBJECT-TYPE
    SYNTAX      TLPolicyNameOrExpOrEmpty
    MAX-ACCESS  read-create
    STATUS      current
    DESCRIPTION
        "The value of vRtrBgpEvpnVxVrfPolicyExp2 specifies the second
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 18 }

vRtrBgpEvpnVxVrfPolicyExp3       OBJECT-TYPE
    SYNTAX      TLPolicyNameOrExpOrEmpty
    MAX-ACCESS  read-create
    STATUS      current
    DESCRIPTION
        "The value of vRtrBgpEvpnVxVrfPolicyExp3 specifies the third
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 19 }

vRtrBgpEvpnVxVrfPolicyExp4       OBJECT-TYPE
    SYNTAX      TLPolicyNameOrExpOrEmpty
    MAX-ACCESS  read-create
    STATUS      current
    DESCRIPTION
        "The value of vRtrBgpEvpnVxVrfPolicyExp4 specifies the fourth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 20 }

vRtrBgpEvpnVxVrfPolicyExp5       OBJECT-TYPE
    SYNTAX      TLPolicyNameOrExpOrEmpty
    MAX-ACCESS  read-create
    STATUS      current
    DESCRIPTION
        "The value of vRtrBgpEvpnVxVrfPolicyExp5 specifies the fifth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 21 }

vRtrBgpEvpnVxVrfPolicyExp6       OBJECT-TYPE
    SYNTAX      TLPolicyNameOrExpOrEmpty
    MAX-ACCESS  read-create
    STATUS      current
    DESCRIPTION
        "The value of vRtrBgpEvpnVxVrfPolicyExp6 specifies the sixth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 22 }

vRtrBgpEvpnVxVrfPolicyExp7       OBJECT-TYPE
    SYNTAX      TLPolicyNameOrExpOrEmpty
    MAX-ACCESS  read-create
    STATUS      current
    DESCRIPTION
        "The value of vRtrBgpEvpnVxVrfPolicyExp7 specifies the seventh
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 23 }

vRtrBgpEvpnVxVrfPolicyExp8       OBJECT-TYPE
    SYNTAX      TLPolicyNameOrExpOrEmpty
    MAX-ACCESS  read-create
    STATUS      current
    DESCRIPTION
        "The value of vRtrBgpEvpnVxVrfPolicyExp8 specifies the eighth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 24 }

vRtrBgpEvpnVxVrfPolicyExp9       OBJECT-TYPE
    SYNTAX      TLPolicyNameOrExpOrEmpty
    MAX-ACCESS  read-create
    STATUS      current
    DESCRIPTION
        "The value of vRtrBgpEvpnVxVrfPolicyExp9 specifies the ninth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 25 }

vRtrBgpEvpnVxVrfPolicyExp10      OBJECT-TYPE
    SYNTAX      TLPolicyNameOrExpOrEmpty
    MAX-ACCESS  read-create
    STATUS      current
    DESCRIPTION
        "The value of vRtrBgpEvpnVxVrfPolicyExp10 specifies the tenth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 26 }

vRtrBgpEvpnVxVrfPolicyExp11      OBJECT-TYPE
    SYNTAX      TLPolicyNameOrExpOrEmpty
    MAX-ACCESS  read-create
    STATUS      current
    DESCRIPTION
        "The value of vRtrBgpEvpnVxVrfPolicyExp11 specifies the eleventh
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 27 }

vRtrBgpEvpnVxVrfPolicyExp12      OBJECT-TYPE
    SYNTAX      TLPolicyNameOrExpOrEmpty
    MAX-ACCESS  read-create
    STATUS      current
    DESCRIPTION
        "The value of vRtrBgpEvpnVxVrfPolicyExp12 specifies the twelfth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 28 }

vRtrBgpEvpnVxVrfPolicyExp13      OBJECT-TYPE
    SYNTAX      TLPolicyNameOrExpOrEmpty
    MAX-ACCESS  read-create
    STATUS      current
    DESCRIPTION
        "The value of vRtrBgpEvpnVxVrfPolicyExp13 specifies the thirteenth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 29 }

vRtrBgpEvpnVxVrfPolicyExp14      OBJECT-TYPE
    SYNTAX      TLPolicyNameOrExpOrEmpty
    MAX-ACCESS  read-create
    STATUS      current
    DESCRIPTION
        "The value of vRtrBgpEvpnVxVrfPolicyExp14 specifies the fourteenth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 30 }

vRtrBgpEvpnVxVrfPolicyExp15      OBJECT-TYPE
    SYNTAX      TLPolicyNameOrExpOrEmpty
    MAX-ACCESS  read-create
    STATUS      current
    DESCRIPTION
        "The value of vRtrBgpEvpnVxVrfPolicyExp15 specifies the fifteenth
         policy to be used for determining which routes are exported
         from the VRF for this virtual router.  If no export policy
         is defined, no routes are exported from the VRF.

         If multiple policy names are specified, the policies are evaluated
         in the order they are specified.  The first policy that matches
         is applied.

         The export policy name list, vRtrBgpEvpnVxVrfPolicyExp1 through
         vRtrBgpEvpnVxVrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpEvpnVxVrfPolicyEntry 31 }

vRtrBgpEvpnVxVrfPolicyCreateOrig OBJECT-TYPE
    SYNTAX      TmnxCreateOrigin
    MAX-ACCESS  read-only
    STATUS      current
    DESCRIPTION
        "The value of vRtrBgpEvpnVxVrfPolicyCreateOrig indicates the mechanism
         used to create this entry."
    DEFVAL      { manual }
    ::= { vRtrBgpEvpnVxVrfPolicyEntry 32 }

vRtrIfEthLoopbackObjs            OBJECT IDENTIFIER ::= { tmnxVRtrObjs 213 }

vRtrIfEthLoopbackTblLastCh       OBJECT-TYPE
    SYNTAX      TimeStamp
    MAX-ACCESS  read-only
    STATUS      current
    DESCRIPTION
        "The value of vRtrIfEthLoopbackTblLastCh indicates the sysUpTime at the
         time of the last modification of an entry in the
         vRtrIfEthLoopbackTable."
    ::= { vRtrIfEthLoopbackObjs 1 }

vRtrIfEthLoopbackTable           OBJECT-TYPE
    SYNTAX      SEQUENCE OF VRtrIfEthLoopbackEntry
    MAX-ACCESS  not-accessible
    STATUS      current
    DESCRIPTION
        "The vRtrIfEthLoopbackTable has an entry for each router interface in
         the system on which loopback configured."
    ::= { vRtrIfEthLoopbackObjs 2 }

vRtrIfEthLoopbackEntry           OBJECT-TYPE
    SYNTAX      VRtrIfEthLoopbackEntry
    MAX-ACCESS  not-accessible
    STATUS      current
    DESCRIPTION
        "Each row entry represents loopback configured on virtual router
         interface in the system. Entries can be created and deleted via SNMP
         SET operations using the vRtrIfEthLoopbackRowStatus variable."
    INDEX       {
        vRtrID,
        vRtrIfIndex
    }
    ::= { vRtrIfEthLoopbackTable 1 }

VRtrIfEthLoopbackEntry           ::= SEQUENCE
{
    vRtrIfEthLoopbackRowStatus       RowStatus,
    vRtrIfEthLoopbackMacSwap         TmnxEnabledDisabled,
    vRtrIfEthLoopbackOperState       TmnxOperState
}

vRtrIfEthLoopbackRowStatus       OBJECT-TYPE
    SYNTAX      RowStatus
    MAX-ACCESS  read-create
    STATUS      current
    DESCRIPTION
        "The vRtrIfEthLoopbackRowStatus specifies the row status. It allows
         entries to be created and deleted in the table."
    ::= { vRtrIfEthLoopbackEntry 1 }

vRtrIfEthLoopbackMacSwap         OBJECT-TYPE
    SYNTAX      TmnxEnabledDisabled
    MAX-ACCESS  read-create
    STATUS      current
    DESCRIPTION
        "The value of the object vRtrIfEthLoopbackMacSwap specifies the
         enabling or disabling of source address and destination address
         swapping for the reflected packets when the arriving packet is
         unicast. With vRtrIfEthLoopbackMacSwap enabled, any broadcast or
         multicast packets arriving on a looped point will be dropped."
    DEFVAL      { disabled }
    ::= { vRtrIfEthLoopbackEntry 2 }

vRtrIfEthLoopbackOperState       OBJECT-TYPE
    SYNTAX      TmnxOperState
    MAX-ACCESS  read-only
    STATUS      current
    DESCRIPTION
        "The value of the object vRtrIfEthLoopbackOperState indicates
         operational status of the active interface loopback."
    ::= { vRtrIfEthLoopbackEntry 3 }

vRtrPlcyAcctPolicerTblLstChgd    OBJECT-TYPE
    SYNTAX      TimeStamp
    MAX-ACCESS  read-only
    STATUS      current
    DESCRIPTION
        "The value of vRtrPlcyAcctPolicerTblLstChgd indicates the sysUpTime at
         the time of the last modification of an entry in the
         vRtrPlcyAcctPolicerTable.

         If no changes were made to the table since the last re-initialization
         of the local network management subsystem, then this object contains a
         zero value."
    ::= { tmnxVRtrObjs 214 }

vRtrPlcyAcctPolicerTable         OBJECT-TYPE
    SYNTAX      SEQUENCE OF VRtrPlcyAcctPolicerEntry
    MAX-ACCESS  not-accessible
    STATUS      current
    DESCRIPTION
        "The vRtrPlcyAcctPolicerTable has an entry for each Policy Accounting
         policer index configured."
    ::= { tmnxVRtrObjs 215 }

vRtrPlcyAcctPolicerEntry         OBJECT-TYPE
    SYNTAX      VRtrPlcyAcctPolicerEntry
    MAX-ACCESS  not-accessible
    STATUS      current
    DESCRIPTION
        "Each row entry in the vRtrPlcyAcctPolicerTable represents information
         related to the policer index associated with vRtrPlcyAcctTemplateName."
    INDEX       {
        vRtrPlcyAcctTemplateName,
        vRtrPlcyAcctPolicerIndex
    }
    ::= { vRtrPlcyAcctPolicerTable 1 }

VRtrPlcyAcctPolicerEntry         ::= SEQUENCE
{
    vRtrPlcyAcctPolicerIndex         TPlcyAcctPolicerId,
    vRtrPlcyAcctPolicerRowStatus     RowStatus,
    vRtrPlcyAcctPolicerLastChgd      TimeStamp,
    vRtrPlcyAcctPolicerPeakRateHi    TmnxQosRateHigh32,
    vRtrPlcyAcctPolicerPeakRateLo    TmnxQosRateLow32,
    vRtrPlcyAcctPolicerMaxBurstSize  TPlcrBurstSizeBytes
}

vRtrPlcyAcctPolicerIndex         OBJECT-TYPE
    SYNTAX      TPlcyAcctPolicerId
    MAX-ACCESS  not-accessible
    STATUS      current
    DESCRIPTION
        "The value of the object vRtrPlcyAcctPolicerIndex specifies the policer
         index associated with the policy accounting template."
    ::= { vRtrPlcyAcctPolicerEntry 1 }

vRtrPlcyAcctPolicerRowStatus     OBJECT-TYPE
    SYNTAX      RowStatus
    MAX-ACCESS  read-create
    STATUS      current
    DESCRIPTION
        "The value of vRtrPlcyAcctPolicerRowStatus specifies the Row Status for
         this entry."
    ::= { vRtrPlcyAcctPolicerEntry 2 }

vRtrPlcyAcctPolicerLastChgd      OBJECT-TYPE
    SYNTAX      TimeStamp
    MAX-ACCESS  read-only
    STATUS      current
    DESCRIPTION
        "The value of vRtrPlcyAcctPolicerLastChgd indicates the timestamp of
         last change to this row in vRtrPlcyAcctPolicerTable."
    ::= { vRtrPlcyAcctPolicerEntry 3 }

vRtrPlcyAcctPolicerPeakRateHi    OBJECT-TYPE
    SYNTAX      TmnxQosRateHigh32
    UNITS       "kilobps"
    MAX-ACCESS  read-create
    STATUS      current
    DESCRIPTION
        "The value of vRtrPlcyAcctPolicerPeakRateHi specifies the upper 32 bits
         of the administrative peak rate specified by the user.

         This value should always be set along with
         vRtrPlcyAcctPolicerPeakRateLo, otherwise an 'inconsistentValue' error
         is returned.

         When the value of vRtrPlcyAcctPolicerPeakRateHi along with the value
         of vRtrPlcyAcctPolicerPeakRateLo is set to 4294967295 (0xFFFFFFFF),
         rate for this queue indicates maximum rate."
    DEFVAL      { 4294967295 }
    ::= { vRtrPlcyAcctPolicerEntry 4 }

vRtrPlcyAcctPolicerPeakRateLo    OBJECT-TYPE
    SYNTAX      TmnxQosRateLow32
    UNITS       "kilobps"
    MAX-ACCESS  read-create
    STATUS      current
    DESCRIPTION
        "The value of vRtrPlcyAcctPolicerPeakRateLo specifies the lower 32 bits
         of the administrative peak rate specified by the user.

         This value should always be set along with
         vRtrPlcyAcctPolicerPeakRateHi, otherwise an 'inconsistentValue' error
         is returned.

         When the value of vRtrPlcyAcctPolicerPeakRateHi along with the value
         of vRtrPlcyAcctPolicerPeakRateLo is set to 4294967295 (0xFFFFFFFF),
         rate for this queue indicates maximum rate."
    DEFVAL      { 4294967295 }
    ::= { vRtrPlcyAcctPolicerEntry 5 }

vRtrPlcyAcctPolicerMaxBurstSize  OBJECT-TYPE
    SYNTAX      TPlcrBurstSizeBytes
    UNITS       "bytes"
    MAX-ACCESS  read-create
    STATUS      current
    DESCRIPTION
        "The vRtrPlcyAcctPolicerMaxBurstSize specifies the high priority
         'violate' threshold of PIR leaky bucket of this policy accounting
         template."
    DEFVAL      { -1 }
    ::= { vRtrPlcyAcctPolicerEntry 6 }

vRtrPlcyAcctIfPolStatsTblLstChgd OBJECT-TYPE
    SYNTAX      TimeStamp
    MAX-ACCESS  read-only
    STATUS      current
    DESCRIPTION
        "The value of vRtrPlcyAcctIfPolStatsTblLstChgd indicates the sysUpTime
         at the time of the last modification of an entry in the
         vRtrPlcyAcctIntfPolStatsTable.

         If no changes were made to the table since the last re-initialization
         of the local network management subsystem, then this object contains a
         zero value."
    ::= { tmnxVRtrObjs 216 }

vRtrPlcyAcctIntfPolStatsTable    OBJECT-TYPE
    SYNTAX      SEQUENCE OF VRtrPlcyAcctIntfPolStatsEntry
    MAX-ACCESS  not-accessible
    STATUS      current
    DESCRIPTION
        "The vRtrPlcyAcctIntfPolStatsTable has stats for each policer in the
         policy accounting template bound to the interface."
    ::= { tmnxVRtrObjs 217 }

vRtrPlcyAcctIntfPolStatsEntry    OBJECT-TYPE
    SYNTAX      VRtrPlcyAcctIntfPolStatsEntry
    MAX-ACCESS  not-accessible
    STATUS      current
    DESCRIPTION
        "Each row entry in the vRtrPlcyAcctIntfPolStatsTable represents
         statistics related to the vRtrPlcyAcctPolicerTable."
    INDEX       {
        vRtrID,
        vRtrIfIndex,
        vRtrPlcyAcctPolicerIndex
    }
    ::= { vRtrPlcyAcctIntfPolStatsTable 1 }

VRtrPlcyAcctIntfPolStatsEntry    ::= SEQUENCE
{
    vRtrPlcyAcctPolicerDropPkts      Counter64,
    vRtrPlcyAcctPolicerDropBytes     Counter64,
    vRtrPlcyAcctPolicerFwdPkts       Counter64,
    vRtrPlcyAcctPolicerFwdBytes      Counter64,
    vRtrPlcyAcctPolicerIncompleteCnt TruthValue
}

vRtrPlcyAcctPolicerDropPkts      OBJECT-TYPE
    SYNTAX      Counter64
    MAX-ACCESS  read-only
    STATUS      current
    DESCRIPTION
        "The value of the object vRtrPlcyAcctPolicerDropPkts indicates the
         total number of packets dropped for this vRtrPlcyAcctPolicerIndex
         associated with the interface."
    ::= { vRtrPlcyAcctIntfPolStatsEntry 1 }

vRtrPlcyAcctPolicerDropBytes     OBJECT-TYPE
    SYNTAX      Counter64
    MAX-ACCESS  read-only
    STATUS      current
    DESCRIPTION
        "The value of the object vRtrPlcyAcctPolicerDropBytes indicates the
         total number of bytes dropped for this vRtrPlcyAcctPolicerIndex
         associated with the interface."
    ::= { vRtrPlcyAcctIntfPolStatsEntry 2 }

vRtrPlcyAcctPolicerFwdPkts       OBJECT-TYPE
    SYNTAX      Counter64
    MAX-ACCESS  read-only
    STATUS      current
    DESCRIPTION
        "The value of the object vRtrPlcyAcctPolicerFwdPkts indicates the total
         number of packets received for this vRtrPlcyAcctPolicerIndex
         associated with the interface."
    ::= { vRtrPlcyAcctIntfPolStatsEntry 3 }

vRtrPlcyAcctPolicerFwdBytes      OBJECT-TYPE
    SYNTAX      Counter64
    MAX-ACCESS  read-only
    STATUS      current
    DESCRIPTION
        "The value of the object vRtrPlcyAcctPolicerFwdBytes indicates the
         total number of bytes received for this vRtrPlcyAcctPolicerIndex
         associated with the interface."
    ::= { vRtrPlcyAcctIntfPolStatsEntry 4 }

vRtrPlcyAcctPolicerIncompleteCnt OBJECT-TYPE
    SYNTAX      TruthValue
    MAX-ACCESS  read-only
    STATUS      current
    DESCRIPTION
        "The value of the object vRtrPlcyAcctPolicerIncompleteCnt indicates
         whether the count of vRtrPlcyAcctPolicerFwdBytes and
         vRtrPlcyAcctPolicerFwdPkts is incomplete or not.

         When the value of vRtrPlcyAcctPolicerIncompleteCnt is 'true', both
         vRtrPlcyAcctPolicerFwdBytes and vRtrPlcyAcctPolicerFwdPkts will be
         incomplete."
    ::= { vRtrPlcyAcctIntfPolStatsEntry 5 }

vRtrBgpSrv6Objs                  OBJECT IDENTIFIER ::= { tmnxVRtrObjs 218 }

vRtrBgpSrv6TblLastCh             OBJECT-TYPE
    SYNTAX      TimeStamp
    MAX-ACCESS  read-only
    STATUS      current
    DESCRIPTION
        "The value of vRtrBgpSrv6TblLastCh indicates the sysUpTime at the time
         of the last modification of an entry in the vRtrBgpSrv6Table."
    ::= { vRtrBgpSrv6Objs 1 }

vRtrBgpSrv6Table                 OBJECT-TYPE
    SYNTAX      SEQUENCE OF VRtrBgpSrv6Entry
    MAX-ACCESS  not-accessible
    STATUS      current
    DESCRIPTION
        "The vRtrBgpSrv6Table contains entries for all the BGP SRv6 instances
         for a particular VPRN service."
    ::= { vRtrBgpSrv6Objs 2 }

vRtrBgpSrv6Entry                 OBJECT-TYPE
    SYNTAX      VRtrBgpSrv6Entry
    MAX-ACCESS  not-accessible
    STATUS      current
    DESCRIPTION
        "A BGP SRv6 instance entry in the vRtrBgpSrv6Table."
    INDEX       {
        vRtrID,
        vRtrBgpSrv6BgpInstType,
        vRtrBgpSrv6BgpInstance
    }
    ::= { vRtrBgpSrv6Table 1 }

VRtrBgpSrv6Entry                 ::= SEQUENCE
{
    vRtrBgpSrv6BgpInstType           INTEGER,
    vRtrBgpSrv6BgpInstance           Integer32,
    vRtrBgpSrv6RowStatus             RowStatus,
    vRtrBgpSrv6LastChanged           TimeStamp,
    vRtrBgpSrv6AdminState            TmnxEnabledDisabled,
    vRtrBgpSrv6Instance              Integer32,
    vRtrBgpSrv6DefLocator            TLNamedItemOrEmpty,
    vRtrBgpSrv6VrfRD                 TmnxVPNRouteDistinguisher,
    vRtrBgpSrv6AutoRD                TruthValue,
    vRtrBgpSrv6OperRD                TmnxVPNRouteDistinguisher,
    vRtrBgpSrv6OperRDType            TmnxRouteDistType,
    vRtrBgpSrv6VrfTarget             TNamedItemOrEmpty,
    vRtrBgpSrv6ExportVrfTarget       TNamedItemOrEmpty,
    vRtrBgpSrv6ImportVrfTarget       TNamedItemOrEmpty,
    vRtrBgpSrv6SrcAddrType           InetAddressType,
    vRtrBgpSrv6SrcAddr               InetAddress,
    vRtrBgpSrv6DefRtTag              Unsigned32,
    vRtrBgpSrv6DomainId              TmnxDPathDomainId,
    vRtrBgpSrv6Evi                   Unsigned32,
    vRtrBgpSrv6Resolution            TSrv6RouteResolution,
    vRtrBgpSrv6OperState             TmnxEnabledDisabled,
    vRtrBgpSrv6AdLinkBw              TruthValue,
    vRtrBgpSrv6AdLinkBwWeight        Integer32,
    vRtrBgpSrv6AdLinkBwMaxWeight     Unsigned32,
    vRtrBgpSrv6WeightedEcmp          TruthValue,
    vRtrBgpSrv6UpaTriggerNextHop     TBgpSrv6UpaTriggerNextHop
}

vRtrBgpSrv6BgpInstType           OBJECT-TYPE
    SYNTAX      INTEGER {
        ipvpn (1),
        evpn  (2)
    }
    MAX-ACCESS  not-accessible
    STATUS      current
    DESCRIPTION
        "The value of vRtrBgpSrv6BgpInstType specifies the BGP protocol family
         used with this service."
    ::= { vRtrBgpSrv6Entry 1 }

vRtrBgpSrv6BgpInstance           OBJECT-TYPE
    SYNTAX      Integer32 (1..2)
    MAX-ACCESS  not-accessible
    STATUS      current
    DESCRIPTION
        "The value of vRtrBgpSrv6BgpInstance specifies the BGP instance used
         with this service."
    ::= { vRtrBgpSrv6Entry 2 }

vRtrBgpSrv6RowStatus             OBJECT-TYPE
    SYNTAX      RowStatus
    MAX-ACCESS  read-create
    STATUS      current
    DESCRIPTION
        "The value of the object  vRtrBgpSrv6RowStatus
         specifies the status of this row."
    ::= { vRtrBgpSrv6Entry 3 }

vRtrBgpSrv6LastChanged           OBJECT-TYPE
    SYNTAX      TimeStamp
    MAX-ACCESS  read-only
    STATUS      current
    DESCRIPTION
        "The value of the object vRtrBgpSrv6LastChanged indicates the timestamp
         of the modification of this entry."
    ::= { vRtrBgpSrv6Entry 4 }

vRtrBgpSrv6AdminState            OBJECT-TYPE
    SYNTAX      TmnxEnabledDisabled
    MAX-ACCESS  read-create
    STATUS      current
    DESCRIPTION
        "The value of vRtrBgpSrv6AdminState specifies if the BGP instance is
         enabled or not.

         The admin state cannot be set in the same request as
         vRtrBgpSrv6RowStatus, if no explicit route-distinguisher,
         route-targets, source-address, SRv6 instance and default locator are
         configured for the BGP instance."
    DEFVAL      { disabled }
    ::= { vRtrBgpSrv6Entry 5 }

vRtrBgpSrv6Instance              OBJECT-TYPE
    SYNTAX      Integer32 (0..2)
    MAX-ACCESS  read-create
    STATUS      current
    DESCRIPTION
        "The value of vRtrBgpSrv6Instance specifies the SRv6 instance used with
         this service."
    DEFVAL      { 0 }
    ::= { vRtrBgpSrv6Entry 6 }

vRtrBgpSrv6DefLocator            OBJECT-TYPE
    SYNTAX      TLNamedItemOrEmpty
    MAX-ACCESS  read-create
    STATUS      current
    DESCRIPTION
        "The value of vRtrBgpSrv6DefLocator specifies the default locator name
         for the SRv6 instance to use for BGP in this VPRN service."
    DEFVAL      { "" }
    ::= { vRtrBgpSrv6Entry 7 }

vRtrBgpSrv6VrfRD                 OBJECT-TYPE
    SYNTAX      TmnxVPNRouteDistinguisher
    MAX-ACCESS  read-create
    STATUS      current
    DESCRIPTION
        "The value of vRtrBgpSrv6VrfRD specifies the high-order 6 bytes used to
         compose the Virtual Routing and Forwarding (VRF) instance to use for
         NLRI in BGP in this VPRN service.

         SNMP set of vRtrBgpSrv6VrfRD to non-default value will automatically
         set vRtrBgpSrv6AutoRD to 'false'."
    DEFVAL      { '0000000000000000'H }
    ::= { vRtrBgpSrv6Entry 8 }

vRtrBgpSrv6AutoRD                OBJECT-TYPE
    SYNTAX      TruthValue
    MAX-ACCESS  read-create
    STATUS      current
    DESCRIPTION
        "The value of vRtrBgpSrv6AutoRD specifies that system will
         automatically select a value for the route-distinguisher from  from
         TIMETRA-SERV-MIB::svcBgpAutoRDType1Group.

         An 'inconsistentValue' error is returned when trying to set
         vRtrBgpSrv6AutoRD to 'true' and there is no route-distinguisher
         available from TIMETRA-SERV-MIB::svcBgpAutoRDType1Group.

         SNMP set of vRtrBgpSrv6AutoRD to 'true' will automatically set
         vRtrBgpSrv6VrfRD to all zeroes."
    DEFVAL      { false }
    ::= { vRtrBgpSrv6Entry 10 }

vRtrBgpSrv6OperRD                OBJECT-TYPE
    SYNTAX      TmnxVPNRouteDistinguisher
    MAX-ACCESS  read-only
    STATUS      current
    DESCRIPTION
        "The value of vRtrBgpSrv6OperRD indicates the route-distinguisher value
         in use by the system for this service."
    ::= { vRtrBgpSrv6Entry 11 }

vRtrBgpSrv6OperRDType            OBJECT-TYPE
    SYNTAX      TmnxRouteDistType
    MAX-ACCESS  read-only
    STATUS      current
    DESCRIPTION
        "The value of vRtrBgpSrv6OperRDType indicates the type of
         route-distinguisher value in use by the system for this service."
    ::= { vRtrBgpSrv6Entry 12 }

vRtrBgpSrv6VrfTarget             OBJECT-TYPE
    SYNTAX      TNamedItemOrEmpty
    MAX-ACCESS  read-create
    STATUS      current
    DESCRIPTION
        "The value of vRtrBgpSrv6VrfTarget specifies the extended community
         name for the default vrf-import or vrf-export policy to use for the
         vRtrID if no entries are configured in the vRtrBgpSrv6VrfPolicyTable
         for this vRtrID instance.

         This object can not be set if either vRtrBgpSrv6ExportVrfTarget or
         vRtrBgpSrv6ImportVrfTarget has been set."
    ::= { vRtrBgpSrv6Entry 13 }

vRtrBgpSrv6ExportVrfTarget       OBJECT-TYPE
    SYNTAX      TNamedItemOrEmpty
    MAX-ACCESS  read-create
    STATUS      current
    DESCRIPTION
        "The value of vRtrBgpSrv6ExportVrfTarget specifies the
         extended community name for the default export policy
         to use for BGP  in this VPRN service.

         It must be set to default before it is set to a non-default value."
    DEFVAL      { "" }
    ::= { vRtrBgpSrv6Entry 14 }

vRtrBgpSrv6ImportVrfTarget       OBJECT-TYPE
    SYNTAX      TNamedItemOrEmpty
    MAX-ACCESS  read-create
    STATUS      current
    DESCRIPTION
        "The value of vRtrBgpSrv6ImportVrfTarget specifies the
         extended community name for the default import policy
         to use for BGP  in this VPRN service.

         It must be set to default before it is set to a non-default value."
    DEFVAL      { "" }
    ::= { vRtrBgpSrv6Entry 15 }

vRtrBgpSrv6SrcAddrType           OBJECT-TYPE
    SYNTAX      InetAddressType
    MAX-ACCESS  read-create
    STATUS      current
    DESCRIPTION
        "The value of vRtrBgpSrv6SrcAddrType indicates the address type of
         vRtrBgpSrv6SrcAddr."
    DEFVAL      { unknown }
    ::= { vRtrBgpSrv6Entry 16 }

vRtrBgpSrv6SrcAddr               OBJECT-TYPE
    SYNTAX      InetAddress (SIZE (0|16))
    MAX-ACCESS  read-create
    STATUS      current
    DESCRIPTION
        "The value of vRtrBgpSrv6SrcAddr indicates the IP address of the source
         router."
    DEFVAL      { ''H }
    ::= { vRtrBgpSrv6Entry 17 }

vRtrBgpSrv6DefRtTag              OBJECT-TYPE
    SYNTAX      Unsigned32 (0..255)
    MAX-ACCESS  read-create
    STATUS      current
    DESCRIPTION
        "The value of vRtrBgpSrv6DefRtTag specifies the default route tag
         passed by SRv6 onto the policy module so that it can be matched on
         export policies."
    DEFVAL      { 0 }
    ::= { vRtrBgpSrv6Entry 18 }

vRtrBgpSrv6DomainId              OBJECT-TYPE
    SYNTAX      TmnxDPathDomainId
    MAX-ACCESS  read-create
    STATUS      current
    DESCRIPTION
        "The value of vRtrBgpSrv6DomainId specifies the Domain ID used in
         D-Path for routes advertisement for BGP IPVPN  or EVPN
         Segment-Routing-V6 service."
    DEFVAL      { '000000000000'H }
    ::= { vRtrBgpSrv6Entry 19 }

vRtrBgpSrv6Evi                   OBJECT-TYPE
    SYNTAX      Unsigned32 (0..16777215)
    MAX-ACCESS  read-create
    STATUS      current
    DESCRIPTION
        "BGP EVPN identifier used for the service-carving algorithm used for
         multi-homing and for auto-deriving the route-distinguisher and
         route-target."
    DEFVAL      { 0 }
    ::= { vRtrBgpSrv6Entry 20 }

vRtrBgpSrv6Resolution            OBJECT-TYPE
    SYNTAX      TSrv6RouteResolution
    MAX-ACCESS  read-create
    STATUS      current
    DESCRIPTION
        "The value of vRtrBgpSrv6Resolution specifies the resolution options
         for routes for BGP IPVPN or EVPN Segment-Routing-V6 service."
    DEFVAL      { routeTable }
    ::= { vRtrBgpSrv6Entry 21 }

vRtrBgpSrv6OperState             OBJECT-TYPE
    SYNTAX      TmnxEnabledDisabled
    MAX-ACCESS  read-only
    STATUS      current
    DESCRIPTION
        "The vRtrBgpSrv6OperState indicates if the VPRN BGP SRv6 instance is
         enabled or not."
    ::= { vRtrBgpSrv6Entry 22 }

vRtrBgpSrv6AdLinkBw              OBJECT-TYPE
    SYNTAX      TruthValue
    MAX-ACCESS  read-create
    STATUS      current
    DESCRIPTION
        "The value of vRtrBgpSrv6AdLinkBw specifies whether to advertise the
         link bandwidth for VPRN BGP SRv6 EVPN-IFL routes."
    DEFVAL      { false }
    ::= { vRtrBgpSrv6Entry 23 }

vRtrBgpSrv6AdLinkBwWeight        OBJECT-TYPE
    SYNTAX      Integer32 (0 | 1..128)
    MAX-ACCESS  read-create
    STATUS      current
    DESCRIPTION
        "The value of vRtrBgpSrv6AdLinkBwWeight specifies the weight to be
         advertised with EVPN-IFL routes. This is effective only when
         vRtrBgpSrv6AdLinkBwWeight is enabled."
    DEFVAL      { 0 }
    ::= { vRtrBgpSrv6Entry 24 }

vRtrBgpSrv6AdLinkBwMaxWeight     OBJECT-TYPE
    SYNTAX      Unsigned32 (1..128)
    MAX-ACCESS  read-create
    STATUS      current
    DESCRIPTION
        "The value of vRtrBgpSrv6AdLinkBwMaxWeight specifies the maximum weight
         to be advertised with EVPN-IFL routes. This is effective only when
         vRtrBgpSrv6AdLinkBwMaxWeight is enabled."
    DEFVAL      { 128 }
    ::= { vRtrBgpSrv6Entry 25 }

vRtrBgpSrv6WeightedEcmp          OBJECT-TYPE
    SYNTAX      TruthValue
    MAX-ACCESS  read-create
    STATUS      current
    DESCRIPTION
        "The value of vRtrBgpSrv6WeightedEcmp specifies whether the unequal
         ecmp will be performed based on the link bandwidth weights for
         EVPN-IFL routes."
    DEFVAL      { false }
    ::= { vRtrBgpSrv6Entry 26 }

vRtrBgpSrv6UpaTriggerNextHop     OBJECT-TYPE
    SYNTAX      TBgpSrv6UpaTriggerNextHop
    MAX-ACCESS  read-create
    STATUS      current
    DESCRIPTION
        "The value of vRtrBgpSrv6UpaTriggerNextHop specifies the handling of
         UPA trigger for next-hop.

         none - BGP won't check the Unreachable Prefix Table to verify that
         there is no matching UPA entry.

         frr  - activate BGP to check the Unreachable Prefix Table to verify
         that there is no matching UPA entry (Longest Prefix Match).  Next-Hop
         of all BGP AFI/SAFI can use Unreachable Prefix Table fast detecting
         next-hop unreachability."
    DEFVAL      { none }
    ::= { vRtrBgpSrv6Entry 27 }

vRtrBgpSrv6VrfPolicyTblLastCh    OBJECT-TYPE
    SYNTAX      TimeStamp
    MAX-ACCESS  read-only
    STATUS      current
    DESCRIPTION
        "The value of vRtrBgpSrv6VrfPolicyTblLastCh indicates the sysUpTime at
         the time of the last modification of an entry in the
         vRtrBgpSrv6VrfPolicyTable."
    ::= { vRtrBgpSrv6Objs 3 }

vRtrBgpSrv6VrfPolicyTable        OBJECT-TYPE
    SYNTAX      SEQUENCE OF VRtrBgpSrv6VrfPolicyEntry
    MAX-ACCESS  not-accessible
    STATUS      current
    DESCRIPTION
        "The vRtrBgpSrv6VrfPolicyTable contains entries for BGP in a VPRN
         service context."
    ::= { vRtrBgpSrv6Objs 4 }

vRtrBgpSrv6VrfPolicyEntry        OBJECT-TYPE
    SYNTAX      VRtrBgpSrv6VrfPolicyEntry
    MAX-ACCESS  not-accessible
    STATUS      current
    DESCRIPTION
        "The vRtrBgpSrv6VrfPolicyEntry contains BGP related information for a
         specific service."
    INDEX       {
        vRtrID,
        vRtrBgpSrv6BgpInstType,
        vRtrBgpSrv6BgpInstance
    }
    ::= { vRtrBgpSrv6VrfPolicyTable 1 }

VRtrBgpSrv6VrfPolicyEntry        ::= SEQUENCE
{
    vRtrBgpSrv6VrfPolicyLastChg      TimeStamp,
    vRtrBgpSrv6VrfPolicyImp1         TXLPolicyNameOrExpOrEmpty,
    vRtrBgpSrv6VrfPolicyImp2         TLPolicyNameOrExpOrEmpty,
    vRtrBgpSrv6VrfPolicyImp3         TLPolicyNameOrExpOrEmpty,
    vRtrBgpSrv6VrfPolicyImp4         TLPolicyNameOrExpOrEmpty,
    vRtrBgpSrv6VrfPolicyImp5         TLPolicyNameOrExpOrEmpty,
    vRtrBgpSrv6VrfPolicyImp6         TLPolicyNameOrExpOrEmpty,
    vRtrBgpSrv6VrfPolicyImp7         TLPolicyNameOrExpOrEmpty,
    vRtrBgpSrv6VrfPolicyImp8         TLPolicyNameOrExpOrEmpty,
    vRtrBgpSrv6VrfPolicyImp9         TLPolicyNameOrExpOrEmpty,
    vRtrBgpSrv6VrfPolicyImp10        TLPolicyNameOrExpOrEmpty,
    vRtrBgpSrv6VrfPolicyImp11        TLPolicyNameOrExpOrEmpty,
    vRtrBgpSrv6VrfPolicyImp12        TLPolicyNameOrExpOrEmpty,
    vRtrBgpSrv6VrfPolicyImp13        TLPolicyNameOrExpOrEmpty,
    vRtrBgpSrv6VrfPolicyImp14        TLPolicyNameOrExpOrEmpty,
    vRtrBgpSrv6VrfPolicyImp15        TLPolicyNameOrExpOrEmpty,
    vRtrBgpSrv6VrfPolicyExp1         TXLPolicyNameOrExpOrEmpty,
    vRtrBgpSrv6VrfPolicyExp2         TLPolicyNameOrExpOrEmpty,
    vRtrBgpSrv6VrfPolicyExp3         TLPolicyNameOrExpOrEmpty,
    vRtrBgpSrv6VrfPolicyExp4         TLPolicyNameOrExpOrEmpty,
    vRtrBgpSrv6VrfPolicyExp5         TLPolicyNameOrExpOrEmpty,
    vRtrBgpSrv6VrfPolicyExp6         TLPolicyNameOrExpOrEmpty,
    vRtrBgpSrv6VrfPolicyExp7         TLPolicyNameOrExpOrEmpty,
    vRtrBgpSrv6VrfPolicyExp8         TLPolicyNameOrExpOrEmpty,
    vRtrBgpSrv6VrfPolicyExp9         TLPolicyNameOrExpOrEmpty,
    vRtrBgpSrv6VrfPolicyExp10        TLPolicyNameOrExpOrEmpty,
    vRtrBgpSrv6VrfPolicyExp11        TLPolicyNameOrExpOrEmpty,
    vRtrBgpSrv6VrfPolicyExp12        TLPolicyNameOrExpOrEmpty,
    vRtrBgpSrv6VrfPolicyExp13        TLPolicyNameOrExpOrEmpty,
    vRtrBgpSrv6VrfPolicyExp14        TLPolicyNameOrExpOrEmpty,
    vRtrBgpSrv6VrfPolicyExp15        TLPolicyNameOrExpOrEmpty,
    vRtrBgpSrv6VrfPolicyCreateOrig   TmnxCreateOrigin
}

vRtrBgpSrv6VrfPolicyLastChg      OBJECT-TYPE
    SYNTAX      TimeStamp
    MAX-ACCESS  read-only
    STATUS      current
    DESCRIPTION
        "The value of vRtrBgpSrv6VrfPolicyLastChg indicates the sysUpTime at
         the time of the last modification of this entry."
    ::= { vRtrBgpSrv6VrfPolicyEntry 1 }

vRtrBgpSrv6VrfPolicyImp1         OBJECT-TYPE
    SYNTAX      TXLPolicyNameOrExpOrEmpty
    MAX-ACCESS  read-create
    STATUS      current
    DESCRIPTION
        "The value of vRtrBgpSrv6VrfPolicyImp1 specifies the first
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 2 }

vRtrBgpSrv6VrfPolicyImp2         OBJECT-TYPE
    SYNTAX      TLPolicyNameOrExpOrEmpty
    MAX-ACCESS  read-create
    STATUS      current
    DESCRIPTION
        "The value of vRtrBgpSrv6VrfPolicyImp2 specifies the second
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 3 }

vRtrBgpSrv6VrfPolicyImp3         OBJECT-TYPE
    SYNTAX      TLPolicyNameOrExpOrEmpty
    MAX-ACCESS  read-create
    STATUS      current
    DESCRIPTION
        "The value of vRtrBgpSrv6VrfPolicyImp3 specifies the third
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 4 }

vRtrBgpSrv6VrfPolicyImp4         OBJECT-TYPE
    SYNTAX      TLPolicyNameOrExpOrEmpty
    MAX-ACCESS  read-create
    STATUS      current
    DESCRIPTION
        "The value of vRtrBgpSrv6VrfPolicyImp4 specifies the fourth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 5 }

vRtrBgpSrv6VrfPolicyImp5         OBJECT-TYPE
    SYNTAX      TLPolicyNameOrExpOrEmpty
    MAX-ACCESS  read-create
    STATUS      current
    DESCRIPTION
        "The value of vRtrBgpSrv6VrfPolicyImp5 specifies the fifth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 6 }

vRtrBgpSrv6VrfPolicyImp6         OBJECT-TYPE
    SYNTAX      TLPolicyNameOrExpOrEmpty
    MAX-ACCESS  read-create
    STATUS      current
    DESCRIPTION
        "The value of vRtrBgpSrv6VrfPolicyImp6 specifies the sixth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 7 }

vRtrBgpSrv6VrfPolicyImp7         OBJECT-TYPE
    SYNTAX      TLPolicyNameOrExpOrEmpty
    MAX-ACCESS  read-create
    STATUS      current
    DESCRIPTION
        "The value of vRtrBgpSrv6VrfPolicyImp7 specifies the seventh
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 8 }

vRtrBgpSrv6VrfPolicyImp8         OBJECT-TYPE
    SYNTAX      TLPolicyNameOrExpOrEmpty
    MAX-ACCESS  read-create
    STATUS      current
    DESCRIPTION
        "The value of vRtrBgpSrv6VrfPolicyImp8 specifies the eighth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 9 }

vRtrBgpSrv6VrfPolicyImp9         OBJECT-TYPE
    SYNTAX      TLPolicyNameOrExpOrEmpty
    MAX-ACCESS  read-create
    STATUS      current
    DESCRIPTION
        "The value of vRtrBgpSrv6VrfPolicyImp9 specifies the ninth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp5, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 10 }

vRtrBgpSrv6VrfPolicyImp10        OBJECT-TYPE
    SYNTAX      TLPolicyNameOrExpOrEmpty
    MAX-ACCESS  read-create
    STATUS      current
    DESCRIPTION
        "The value of vRtrBgpSrv6VrfPolicyImp10 specifies the tenth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 11 }

vRtrBgpSrv6VrfPolicyImp11        OBJECT-TYPE
    SYNTAX      TLPolicyNameOrExpOrEmpty
    MAX-ACCESS  read-create
    STATUS      current
    DESCRIPTION
        "The value of vRtrBgpSrv6VrfPolicyImp11 specifies the eleventh
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 12 }

vRtrBgpSrv6VrfPolicyImp12        OBJECT-TYPE
    SYNTAX      TLPolicyNameOrExpOrEmpty
    MAX-ACCESS  read-create
    STATUS      current
    DESCRIPTION
        "The value of vRtrBgpSrv6VrfPolicyImp12 specifies the twelfth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 13 }

vRtrBgpSrv6VrfPolicyImp13        OBJECT-TYPE
    SYNTAX      TLPolicyNameOrExpOrEmpty
    MAX-ACCESS  read-create
    STATUS      current
    DESCRIPTION
        "The value of vRtrBgpSrv6VrfPolicyImp13 specifies the thirteenth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 14 }

vRtrBgpSrv6VrfPolicyImp14        OBJECT-TYPE
    SYNTAX      TLPolicyNameOrExpOrEmpty
    MAX-ACCESS  read-create
    STATUS      current
    DESCRIPTION
        "The value of vRtrBgpSrv6VrfPolicyImp14 specifies the fourteenth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 15 }

vRtrBgpSrv6VrfPolicyImp15        OBJECT-TYPE
    SYNTAX      TLPolicyNameOrExpOrEmpty
    MAX-ACCESS  read-create
    STATUS      current
    DESCRIPTION
        "The value of vRtrBgpSrv6VrfPolicyImp15 specifies the fifteenth
         policy to be used for determining which routes are imported
         into the VRF for this virtual router.  If no import policy
         is defined, no routes are accepted into the VRF.

         If multiple policy names are specified, the policies are evaluated
         in the order they are specified.  The first policy that matches
         is applied.

         The import policy name list, vRtrBgpSrv6VrfPolicyImp1 through
         vRtrBgpSrv6VrfPolicyImp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 16 }

vRtrBgpSrv6VrfPolicyExp1         OBJECT-TYPE
    SYNTAX      TXLPolicyNameOrExpOrEmpty
    MAX-ACCESS  read-create
    STATUS      current
    DESCRIPTION
        "The value of vRtrBgpSrv6VrfPolicyExp1 specifies the first
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 17 }

vRtrBgpSrv6VrfPolicyExp2         OBJECT-TYPE
    SYNTAX      TLPolicyNameOrExpOrEmpty
    MAX-ACCESS  read-create
    STATUS      current
    DESCRIPTION
        "The value of vRtrBgpSrv6VrfPolicyExp2 specifies the second
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 18 }

vRtrBgpSrv6VrfPolicyExp3         OBJECT-TYPE
    SYNTAX      TLPolicyNameOrExpOrEmpty
    MAX-ACCESS  read-create
    STATUS      current
    DESCRIPTION
        "The value of vRtrBgpSrv6VrfPolicyExp3 specifies the third
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 19 }

vRtrBgpSrv6VrfPolicyExp4         OBJECT-TYPE
    SYNTAX      TLPolicyNameOrExpOrEmpty
    MAX-ACCESS  read-create
    STATUS      current
    DESCRIPTION
        "The value of vRtrBgpSrv6VrfPolicyExp4 specifies the fourth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 20 }

vRtrBgpSrv6VrfPolicyExp5         OBJECT-TYPE
    SYNTAX      TLPolicyNameOrExpOrEmpty
    MAX-ACCESS  read-create
    STATUS      current
    DESCRIPTION
        "The value of vRtrBgpSrv6VrfPolicyExp5 specifies the fifth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 21 }

vRtrBgpSrv6VrfPolicyExp6         OBJECT-TYPE
    SYNTAX      TLPolicyNameOrExpOrEmpty
    MAX-ACCESS  read-create
    STATUS      current
    DESCRIPTION
        "The value of vRtrBgpSrv6VrfPolicyExp6 specifies the sixth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 22 }

vRtrBgpSrv6VrfPolicyExp7         OBJECT-TYPE
    SYNTAX      TLPolicyNameOrExpOrEmpty
    MAX-ACCESS  read-create
    STATUS      current
    DESCRIPTION
        "The value of vRtrBgpSrv6VrfPolicyExp7 specifies the seventh
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 23 }

vRtrBgpSrv6VrfPolicyExp8         OBJECT-TYPE
    SYNTAX      TLPolicyNameOrExpOrEmpty
    MAX-ACCESS  read-create
    STATUS      current
    DESCRIPTION
        "The value of vRtrBgpSrv6VrfPolicyExp8 specifies the eighth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 24 }

vRtrBgpSrv6VrfPolicyExp9         OBJECT-TYPE
    SYNTAX      TLPolicyNameOrExpOrEmpty
    MAX-ACCESS  read-create
    STATUS      current
    DESCRIPTION
        "The value of vRtrBgpSrv6VrfPolicyExp9 specifies the ninth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 25 }

vRtrBgpSrv6VrfPolicyExp10        OBJECT-TYPE
    SYNTAX      TLPolicyNameOrExpOrEmpty
    MAX-ACCESS  read-create
    STATUS      current
    DESCRIPTION
        "The value of vRtrBgpSrv6VrfPolicyExp10 specifies the tenth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 26 }

vRtrBgpSrv6VrfPolicyExp11        OBJECT-TYPE
    SYNTAX      TLPolicyNameOrExpOrEmpty
    MAX-ACCESS  read-create
    STATUS      current
    DESCRIPTION
        "The value of vRtrBgpSrv6VrfPolicyExp11 specifies the eleventh
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 27 }

vRtrBgpSrv6VrfPolicyExp12        OBJECT-TYPE
    SYNTAX      TLPolicyNameOrExpOrEmpty
    MAX-ACCESS  read-create
    STATUS      current
    DESCRIPTION
        "The value of vRtrBgpSrv6VrfPolicyExp12 specifies the twelfth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 28 }

vRtrBgpSrv6VrfPolicyExp13        OBJECT-TYPE
    SYNTAX      TLPolicyNameOrExpOrEmpty
    MAX-ACCESS  read-create
    STATUS      current
    DESCRIPTION
        "The value of vRtrBgpSrv6VrfPolicyExp13 specifies the thirteenth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 29 }

vRtrBgpSrv6VrfPolicyExp14        OBJECT-TYPE
    SYNTAX      TLPolicyNameOrExpOrEmpty
    MAX-ACCESS  read-create
    STATUS      current
    DESCRIPTION
        "The value of vRtrBgpSrv6VrfPolicyExp14 specifies the fourteenth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 30 }

vRtrBgpSrv6VrfPolicyExp15        OBJECT-TYPE
    SYNTAX      TLPolicyNameOrExpOrEmpty
    MAX-ACCESS  read-create
    STATUS      current
    DESCRIPTION
        "The value of vRtrBgpSrv6VrfPolicyExp15 specifies the fifteenth
         policy to be used for determining which routes are exported
         from the VRF for this virtual router.  If no export policy
         is defined, no routes are exported from the VRF.

         If multiple policy names are specified, the policies are evaluated
         in the order they are specified.  The first policy that matches
         is applied.

         The export policy name list, vRtrBgpSrv6VrfPolicyExp1 through
         vRtrBgpSrv6VrfPolicyExp15, is handled by the SNMP agent as a single
         entity.  When an SNMP SET request is received to modify one or
         more of the policy names, all the policy variables are first
         set to the empty string, ''H, and then the new names are set
         into the specified policy variables within a single SNMP SET PDU."
    DEFVAL      { ''H }
    ::= { vRtrBgpSrv6VrfPolicyEntry 31 }

vRtrBgpSrv6VrfPolicyCreateOrig   OBJECT-TYPE
    SYNTAX      TmnxCreateOrigin
    MAX-ACCESS  read-only
    STATUS      current
    DESCRIPTION
        "The value of vRtrBgpSrv6VrfPolicyCreateOrig indicates the mechanism
         used to create this entry."
    DEFVAL      { manual }
    ::= { vRtrBgpSrv6VrfPolicyEntry 32 }

vRtrIfLinkDelayTable             OBJECT-TYPE
    SYNTAX      SEQUENCE OF VRtrIfLinkDelayEntry
    MAX-ACCESS  not-accessible
    STATUS      current
    DESCRIPTION
        "The vRtrIfLinkDelayTable is used to configure the link delay
         parameters for each router interface configured in the system. This
         table augments the vRtrIfTable."
    ::= { tmnxVRtrObjs 219 }

vRtrIfLinkDelayEntry             OBJECT-TYPE
    SYNTAX      VRtrIfLinkDelayEntry
    MAX-ACCESS  not-accessible
    STATUS      current
    DESCRIPTION
        "Each row entry represents a virtual router interface in the system.
         Entries can be created and deleted via SNMP SET operations using the
         vRtrIfRowStatus variable."
    AUGMENTS    { vRtrIfEntry }
    ::= { vRtrIfLinkDelayTable 1 }

VRtrIfLinkDelayEntry             ::= SEQUENCE
{
    vRtrIfLinkDelaySelection         INTEGER,
    vRtrIfLinkDelayStatic            Integer32,
    vRtrIfLinkDelayDynamic           Integer32,
    vRtrIfLinkDelayOper              Integer32,
    vRtrIfLinkDelayMeasureTemplName  TLNamedItemOrEmpty,
    vRtrIfLnkDlyTwampIpv4AdminState  TmnxAdminState,
    vRtrIfLnkDlyTwampIpv4DstAddrType InetAddressType,
    vRtrIfLnkDlyTwampIpv4DstAddr     InetAddress,
    vRtrIfLnkDlyTwampIpv4SrcAddrType InetAddressType,
    vRtrIfLnkDlyTwampIpv4SrcAddr     InetAddress,
    vRtrIfLnkDlyTwampIpv6AdminState  TmnxAdminState,
    vRtrIfLnkDlyTwampIpv6DstAddrType InetAddressType,
    vRtrIfLnkDlyTwampIpv6DstAddr     InetAddress,
    vRtrIfLnkDlyTwampIpv6SrcAddrType InetAddressType,
    vRtrIfLnkDlyTwampIpv6SrcAddr     InetAddress,
    vRtrIfLinkDelayLagMeasTemplName  TLNamedItemOrEmpty
}

vRtrIfLinkDelaySelection         OBJECT-TYPE
    SYNTAX      INTEGER {
        static           (1),
        dynamic          (2),
        staticPreferred  (3),
        dynamicPreferred (4)
    }
    MAX-ACCESS  read-create
    STATUS      current
    DESCRIPTION
        "The value of vRtrIfLinkDelaySelection specifies how to choose the link
         delay value that will be advertised for this interface.

         A value of 'static' specifies that the value of vRtrIfLinkDelayStatic
         will be used as the interface link delay. The value of
         vRtrIfLinkDelayDynamic will be ignored.

         A value of 'dynamic' specifies that the calculated link delay value of
         vRtrIfLinkDelayDynamic will be used as the interface link delay. The
         value of vRtrIfLinkDelayStatic will be ignored.

         A value of 'staticPreferred' specifies that the value of
         vRtrIfLinkDelayStatic will be used unless its value is 0
         (unconfigured). If the value of vRtrIfLinkDelayStatic is 0, then the
         value of vRtrIfLinkDelayDynamic will be used instead. This is the
         default.

         A value of 'dynamicPreferred' specifies that the value of
         vRtrIfLinkDelayDynamic will be used if it is available (non-zero). If
         the value of vRtrIfLinkDelayDynamic is 0, then the value of
         vRtrIfLinkDelayStatic will be used instead."
    DEFVAL      { staticPreferred }
    ::= { vRtrIfLinkDelayEntry 1 }

vRtrIfLinkDelayStatic            OBJECT-TYPE
    SYNTAX      Integer32 (0 | 1..16777214)
    UNITS       "microseconds"
    MAX-ACCESS  read-create
    STATUS      current
    DESCRIPTION
        "The value of vRtrIfLinkDelayStatic specifies a static value for the
         average link delay in microseconds for this router interface.

         A value of 0 indicates that the static delay is not specified for this
         router interface."
    DEFVAL      { 0 }
    ::= { vRtrIfLinkDelayEntry 2 }

vRtrIfLinkDelayDynamic           OBJECT-TYPE
    SYNTAX      Integer32 (0 | 1..16777214)
    UNITS       "microseconds"
    MAX-ACCESS  read-only
    STATUS      current
    DESCRIPTION
        "The value of vRtrIfLinkDelayDynamic indicates the average link delay
         in microseconds as measured for this router interface.

         A value of 0 indicates that the delay has not been measured for this
         router interface."
    DEFVAL      { 0 }
    ::= { vRtrIfLinkDelayEntry 3 }

vRtrIfLinkDelayOper              OBJECT-TYPE
    SYNTAX      Integer32 (0 | 1..16777214)
    UNITS       "microseconds"
    MAX-ACCESS  read-only
    STATUS      current
    DESCRIPTION
        "The value of vRtrIfLinkDelayOper indicates the operational link delay
         in microseconds for this router interface, as used by ISIS and OSPF.
         The operational value will be either vRtrIfLinkDelayStatic or
         vRtrIfLinkDelayDynamic, depending on the value of
         vRtrIfLinkDelaySelection.

         A value of 0 indicates that the delay is not specified for this router
         interface."
    DEFVAL      { 0 }
    ::= { vRtrIfLinkDelayEntry 4 }

vRtrIfLinkDelayMeasureTemplName  OBJECT-TYPE
    SYNTAX      TLNamedItemOrEmpty
    MAX-ACCESS  read-create
    STATUS      current
    DESCRIPTION
        "The value of vRtrIfLinkDelayMeasureTemplName specifies the link delay
         measurement template associated with this interface and it should
         match one of the TIMETRA-OAM-TEST-MIB::tmnxOamLnkMeasTmplCtlName
         values. This object is mutually exclusive with
         vRtrIfLinkDelayLagMeasTemplName. Only one of the two objects can be
         set at a time."
    DEFVAL      { ''H }
    ::= { vRtrIfLinkDelayEntry 5 }

vRtrIfLnkDlyTwampIpv4AdminState  OBJECT-TYPE
    SYNTAX      TmnxAdminState
    MAX-ACCESS  read-create
    STATUS      current
    DESCRIPTION
        "The value of vRtrIfLnkDlyTwampIpv4AdminState enables the transmission
         of TWAMP-LIGHT IPv4 measurement packets. Only one of
         vRtrIfLnkDlyTwampIpv4AdminState and vRtrIfLnkDlyTwampIpv6AdminState
         can be enabled."
    DEFVAL      { outOfService }
    ::= { vRtrIfLinkDelayEntry 6 }

vRtrIfLnkDlyTwampIpv4DstAddrType OBJECT-TYPE
    SYNTAX      InetAddressType
    MAX-ACCESS  read-create
    STATUS      current
    DESCRIPTION
        "The value of vRtrIfLnkDlyTwampIpv4DstAddrType specifies the type of
         vRtrIfLnkDlyTwampIpv4DstAddr, the TWAMP-LIGHT IPv4 destination
         address."
    DEFVAL      { ipv4 }
    ::= { vRtrIfLinkDelayEntry 7 }

vRtrIfLnkDlyTwampIpv4DstAddr     OBJECT-TYPE
    SYNTAX      InetAddress (SIZE (0|4))
    MAX-ACCESS  read-create
    STATUS      current
    DESCRIPTION
        "The value of vRtrIfLnkDlyTwampIpv4DstAddr specifies the unicast IPv4
         destination address used on TWAMP-LIGHT measurement packets sent from
         this interface.

         When vRtrIfLnkDlyTwampIpv4DstAddr is not configured, an address will
         be derived from the IPv4 interface address if the prefix length is
         either 30 or 31. A destination address must be configured for prefix
         lengths other than 30 or 31.

         The destination address must be reachable from this interface.

         The type of this address is specified by the value of
         vRtrIfLnkDlyTwampIpv4DstAddrType."
    DEFVAL      { '00000000'H }
    ::= { vRtrIfLinkDelayEntry 8 }

vRtrIfLnkDlyTwampIpv4SrcAddrType OBJECT-TYPE
    SYNTAX      InetAddressType
    MAX-ACCESS  read-create
    STATUS      current
    DESCRIPTION
        "The value of vRtrIfLnkDlyTwampIpv4SrcAddrType specifies the type of
         vRtrIfLnkDlyTwampIpv4SrcAddr, the TWAMP-LIGHT IPv4 source address."
    DEFVAL      { ipv4 }
    ::= { vRtrIfLinkDelayEntry 9 }

vRtrIfLnkDlyTwampIpv4SrcAddr     OBJECT-TYPE
    SYNTAX      InetAddress (SIZE (0|4))
    MAX-ACCESS  read-create
    STATUS      current
    DESCRIPTION
        "The value of vRtrIfLnkDlyTwampIpv4SrcAddr specifies the unicast IPv4
         source address used on TWAMP-LIGHT measurement packets sent from this
         interface.

         When this value is not configured, the source address of the
         TWAMP-LIGHT measurement packet will be derived from the IPv4 address
         of the interface.

         The type of this address is specified by the value of
         vRtrIfLnkDlyTwampIpv4SrcAddrType."
    DEFVAL      { '00000000'H }
    ::= { vRtrIfLinkDelayEntry 10 }

vRtrIfLnkDlyTwampIpv6AdminState  OBJECT-TYPE
    SYNTAX      TmnxAdminState
    MAX-ACCESS  read-create
    STATUS      current
    DESCRIPTION
        "The value of vRtrIfLnkDlyTwampIpv6AdminState enables the transmission
         of TWAMP-LIGHT IPv6 measurement packets. Only one of
         vRtrIfLnkDlyTwampIpv4AdminState and vRtrIfLnkDlyTwampIpv6AdminState
         can be enabled."
    DEFVAL      { outOfService }
    ::= { vRtrIfLinkDelayEntry 11 }

vRtrIfLnkDlyTwampIpv6DstAddrType OBJECT-TYPE
    SYNTAX      InetAddressType
    MAX-ACCESS  read-create
    STATUS      current
    DESCRIPTION
        "The value of vRtrIfLnkDlyTwampIpv6DstAddrType specifies the type of
         vRtrIfLnkDlyTwampIpv6DstAddr, the TWAMP-LIGHT IPv6 destination
         address."
    DEFVAL      { ipv6 }
    ::= { vRtrIfLinkDelayEntry 12 }

vRtrIfLnkDlyTwampIpv6DstAddr     OBJECT-TYPE
    SYNTAX      InetAddress (SIZE (0|16))
    MAX-ACCESS  read-create
    STATUS      current
    DESCRIPTION
        "The value of vRtrIfLnkDlyTwampIpv6DstAddr specifies the IPv6
         destination address used on TWAMP-LIGHT measurement packets sent from
         this interface.

         The destination address must be reachable from this interface.

         The type of this address is specified by the value of
         vRtrIfLnkDlyTwampIpv6DstAddrType."
    DEFVAL      { '00000000000000000000000000000000'H }
    ::= { vRtrIfLinkDelayEntry 13 }

vRtrIfLnkDlyTwampIpv6SrcAddrType OBJECT-TYPE
    SYNTAX      InetAddressType
    MAX-ACCESS  read-create
    STATUS      current
    DESCRIPTION
        "The value of vRtrIfLnkDlyTwampIpv6SrcAddrType specifies the type of
         vRtrIfLnkDlyTwampIpv6SrcAddr, the TWAMP-LIGHT IPv6 source address."
    DEFVAL      { ipv6 }
    ::= { vRtrIfLinkDelayEntry 14 }

vRtrIfLnkDlyTwampIpv6SrcAddr     OBJECT-TYPE
    SYNTAX      InetAddress (SIZE (0|16))
    MAX-ACCESS  read-create
    STATUS      current
    DESCRIPTION
        "The value of vRtrIfLnkDlyTwampIpv6SrcAddr specifies the IPv6 source
         address used on the TWAMP-LIGHT measurement packets sent from this
         interface.

         When vRtrIfLnkDlyTwampIpv6SrcAddr is not configured, the source
         address of the TWAMP-LIGHT measurement packet will be derived from the
         IPv6 address of the interface.

         The type of this address is specified by the value of
         vRtrIfLnkDlyTwampIpv6SrcAddrType."
    DEFVAL      { '00000000000000000000000000000000'H }
    ::= { vRtrIfLinkDelayEntry 15 }

vRtrIfLinkDelayLagMeasTemplName  OBJECT-TYPE
    SYNTAX      TLNamedItemOrEmpty
    MAX-ACCESS  read-create
    STATUS      current
    DESCRIPTION
        "The value of vRtrIfLinkDelayLagMeasTemplName specifies the LAG
         measurement template associated with this interface and it should
         match one of the TIMETRA-OAM-TEST-MIB::tmnxOamLagMeasTmplCtlName
         values.

         This object is mutually exclusive with
         vRtrIfLinkDelayMeasureTemplName. Only one of the two objects can be
         set at a time."
    DEFVAL      { ''H }
    ::= { vRtrIfLinkDelayEntry 16 }

vRtrDPathAttrTable               OBJECT-TYPE
    SYNTAX      SEQUENCE OF VRtrDPathAttrEntry
    MAX-ACCESS  not-accessible
    STATUS      current
    DESCRIPTION
        "The vRtrDPathAttrTable contains the configuration for d-path
         attributes for VPRN services."
    ::= { tmnxVRtrObjs 220 }

vRtrDPathAttrEntry               OBJECT-TYPE
    SYNTAX      VRtrDPathAttrEntry
    MAX-ACCESS  not-accessible
    STATUS      current
    DESCRIPTION
        "Each row entry represents configuration for d-path attributes for
         particular VPRN services."
    AUGMENTS    { vRtrConfEntry }
    ::= { vRtrDPathAttrTable 1 }

VRtrDPathAttrEntry               ::= SEQUENCE
{
    vRtrBgpIpVpnMplsDomainId         TmnxDPathDomainId,
    vRtrLocalRoutesDomainId          TmnxDPathDomainId,
    vRtrDpathLengthIgnore            TruthValue,
    vRtrDPathAttrLastChanged         TimeStamp
}

vRtrBgpIpVpnMplsDomainId         OBJECT-TYPE
    SYNTAX      TmnxDPathDomainId
    MAX-ACCESS  read-create
    STATUS      current
    DESCRIPTION
        "The value of vRtrBgpIpVpnMplsDomainId specifies the Domain ID used in
         D-Path  for routes advertisement for BGP IP VPN MPLS service."
    DEFVAL      { '000000000000'H }
    ::= { vRtrDPathAttrEntry 1 }

vRtrLocalRoutesDomainId          OBJECT-TYPE
    SYNTAX      TmnxDPathDomainId
    MAX-ACCESS  read-create
    STATUS      current
    DESCRIPTION
        "The value of vRtrLocalRoutesDomainId specifies the Domain ID used in
         D-Path for local-routes advertisement."
    DEFVAL      { '000000000000'H }
    ::= { vRtrDPathAttrEntry 2 }

vRtrDpathLengthIgnore            OBJECT-TYPE
    SYNTAX      TruthValue
    MAX-ACCESS  read-create
    STATUS      current
    DESCRIPTION
        "The value of vRtrDpathLengthIgnore specifies if VPRN RTM ignores  the
         D-PATH domain segment length for best path selection."
    DEFVAL      { false }
    ::= { vRtrDPathAttrEntry 3 }

vRtrDPathAttrLastChanged         OBJECT-TYPE
    SYNTAX      TimeStamp
    MAX-ACCESS  read-only
    STATUS      current
    DESCRIPTION
        "Time stamp of last change of any object for this entry."
    ::= { vRtrDPathAttrEntry 4 }

vRtrSubDhcp4Table                OBJECT-TYPE
    SYNTAX      SEQUENCE OF VRtrSubDhcp4Entry
    MAX-ACCESS  not-accessible
    STATUS      current
    DESCRIPTION
        "The vRtrSubDhcp4Table contains DHCP configuration per virtual router."
    ::= { tmnxVRtrObjs 221 }

vRtrSubDhcp4Entry                OBJECT-TYPE
    SYNTAX      VRtrSubDhcp4Entry
    MAX-ACCESS  not-accessible
    STATUS      current
    DESCRIPTION
        "Each row entry contains information for DHCP in IPv4.

         Entries cannot be created and deleted via SNMP SET operations."
    AUGMENTS    { vRtrConfEntry }
    ::= { vRtrSubDhcp4Table 1 }

VRtrSubDhcp4Entry                ::= SEQUENCE
{
    vRtrSubDhcp4LastChanged          TimeStamp,
    vRtrSubDhcp4TransparentForward   TruthValue,
    vRtrSubDhcp4TranspFwdClntPkts    Counter64,
    vRtrSubDhcp4TranspFwdServPkts    Counter64,
    vRtrSubDhcp4TranspFwdOtherPkts   Counter64
}

vRtrSubDhcp4LastChanged          OBJECT-TYPE
    SYNTAX      TimeStamp
    MAX-ACCESS  read-only
    STATUS      current
    DESCRIPTION
        "The value of vRtrSubDhcp4LastChanged indicates the sysUpTime when an
         object in this table was last modified."
    ::= { vRtrSubDhcp4Entry 1 }

vRtrSubDhcp4TransparentForward   OBJECT-TYPE
    SYNTAX      TruthValue
    MAX-ACCESS  read-create
    STATUS      current
    DESCRIPTION
        "The value of vRtrSubDhcp4TransparentForward specifies the transparent
         forwarding of DHCPv4 over IPoE sessions."
    DEFVAL      { false }
    ::= { vRtrSubDhcp4Entry 2 }

vRtrSubDhcp4TranspFwdClntPkts    OBJECT-TYPE
    SYNTAX      Counter64
    MAX-ACCESS  read-only
    STATUS      current
    DESCRIPTION
        "The value of vRtrSubDhcp4TranspFwdClntPkts indicates the number of
         client packets forwarded using transparent forwarding of DHCPv4 over
         IPoE sessions, where the 'op' opcode matches BOOTREQUEST."
    ::= { vRtrSubDhcp4Entry 3 }

vRtrSubDhcp4TranspFwdServPkts    OBJECT-TYPE
    SYNTAX      Counter64
    MAX-ACCESS  read-only
    STATUS      current
    DESCRIPTION
        "The value of vRtrSubDhcp4TranspFwdServPkts indicates the number of
         server packets forwarded using transparent forwarding of DHCPv4 over
         IPoE sessions, where the 'op' opcode matches BOOTREPLY."
    ::= { vRtrSubDhcp4Entry 4 }

vRtrSubDhcp4TranspFwdOtherPkts   OBJECT-TYPE
    SYNTAX      Counter64
    MAX-ACCESS  read-only
    STATUS      current
    DESCRIPTION
        "The value of vRtrSubDhcp4TranspFwdOtherPkts indicates the number of
         packets forwarded using transparent forwarding of DHCPv4 over IPoE
         sessions, where the 'op' opcode is different from either BOOTREQUEST
         or BOOTREPLY."
    ::= { vRtrSubDhcp4Entry 5 }

vRtrConfExt2Table                OBJECT-TYPE
    SYNTAX      SEQUENCE OF VRtrConfExt2Entry
    MAX-ACCESS  not-accessible
    STATUS      current
    DESCRIPTION
        "The vRtrConfExt2Table provides an extension of the vRtrConfTable."
    ::= { tmnxVRtrObjs 222 }

vRtrConfExt2Entry                OBJECT-TYPE
    SYNTAX      VRtrConfExt2Entry
    MAX-ACCESS  not-accessible
    STATUS      current
    DESCRIPTION
        "Each row entry in the vRtrConfExt2Table represents additional columns
         for attributes specific to the Nokia SROS series implementation for
         the router configuration table."
    AUGMENTS    { vRtrConfEntry }
    ::= { vRtrConfExt2Table 1 }

VRtrConfExt2Entry                ::= SEQUENCE
{
    vRtrAllowBgpToIgpExport          TruthValue,
    vRtrBgpIpVpnAttrSetImport        TmnxAttrSetImport,
    vRtrBgpIpVpnAttrSetExport        TruthValue,
    vRtrBgpExportInactiveBgpEnhanced TruthValue,
    vRtrMvpnWldCrdSpmsiSuppressIpmsi TruthValue,
    vRtrMvpnIpmsiP2mpPolicySrv6      TNamedItemOrEmpty,
    vRtrMvpnSpmsiP2mpPolicySrv6      TNamedItemOrEmpty,
    vRtrMvpnServiceReservedLabel     TmnxMplsLabelOrZero,
    vRtrMvpnBierPtaLabelInMsb        TruthValue,
    vRtrBgpIpVpnAnySecEncGrp         TNamedItemOrEmpty
}

vRtrAllowBgpToIgpExport          OBJECT-TYPE
    SYNTAX      TruthValue
    MAX-ACCESS  read-create
    STATUS      current
    DESCRIPTION
        "The value of the object vRtrAllowBgpToIgpExport specifies  whether the
         export of BGP into IGP within the base router is enabled.  It applies
         to newly received BGP prefixes."
    DEFVAL      { true }
    ::= { vRtrConfExt2Entry 1 }

vRtrBgpIpVpnAttrSetImport        OBJECT-TYPE
    SYNTAX      TmnxAttrSetImport
    MAX-ACCESS  read-create
    STATUS      current
    DESCRIPTION
        "The value of the object vRtrBgpIpVpnAttrSetImport specifies the
         reception behaviors of attribute-set. The default value is 'ignore'
         for backwards compatibility."
    DEFVAL      { ignore }
    ::= { vRtrConfExt2Entry 2 }

vRtrBgpIpVpnAttrSetExport        OBJECT-TYPE
    SYNTAX      TruthValue
    MAX-ACCESS  read-create
    STATUS      current
    DESCRIPTION
        "The value of the object vRtrBgpIpVpnAttrSetExport specifies the
         origination behaviors of attribute-set.

         When it is set to 'true', it instructs BGP to add ATTR_SET to  all
         exported routes from this VPRN, regardless of whether they  are MPLS
         or SRv6. When it is set to 'false', it instructs BGP to not add
         ATTR_SET  to exported routes from this VPRN (default for backwards
         compatibility)."
    DEFVAL      { false }
    ::= { vRtrConfExt2Entry 3 }

vRtrBgpExportInactiveBgpEnhanced OBJECT-TYPE
    SYNTAX      TruthValue
    MAX-ACCESS  read-create
    STATUS      current
    DESCRIPTION
        "The value of the object vRtrBgpExportInactiveBgpEnhanced specifies
         whether or not inactive BGP routes in the VPRN BGP instance are
         exported to the MP-BGP  domain when the best route is any other route.

         If the value of vRtrBgpExportInactiveBgpEnhanced is 'true', inactive
         BGP routes  will be exported to the MP-BGP domain. If the value of
         vRtrBgpExportInactiveBgpEnhanced  is 'false', inactive BGP routes are
         not exported to the MP-BGP domain.

         If the value of vRtrBgpExportInactiveBgpEnhanced is 'true', this
         overrides any setting of vRtrBgpExportInactive."
    DEFVAL      { false }
    ::= { vRtrConfExt2Entry 4 }

vRtrMvpnWldCrdSpmsiSuppressIpmsi OBJECT-TYPE
    SYNTAX      TruthValue
    MAX-ACCESS  read-create
    STATUS      current
    DESCRIPTION
        "The value of vRtrMvpnWldCrdSpmsiSuppressIpmsi determines whether to
         suppress IPMSI being  advertised."
    DEFVAL      { false }
    ::= { vRtrConfExt2Entry 5 }

vRtrMvpnIpmsiP2mpPolicySrv6      OBJECT-TYPE
    SYNTAX      TNamedItemOrEmpty
    MAX-ACCESS  read-create
    STATUS      current
    DESCRIPTION
        "The value of vRtrMvpnIpmsiP2mpPolicySrv6 specifies the name of SRv6
         p2mp policy whose parameters are configured in
         TIMETRA-TREE-SID-MIB::vRtrTreeSidPolicyEntry table and are signaled to
         the automatically created P2MP LSP for the inclusive provider tunnel.

         If the corresponding index does not exist in
         TIMETRA-TREE-SID-MIB::vRtrTreeSidPolicyEntry table, an
         'inconsistentValue' error will be returned."
    DEFVAL      { ''H }
    ::= { vRtrConfExt2Entry 6 }

vRtrMvpnSpmsiP2mpPolicySrv6      OBJECT-TYPE
    SYNTAX      TNamedItemOrEmpty
    MAX-ACCESS  read-create
    STATUS      current
    DESCRIPTION
        "The value of vRtrMvpnSpmsiP2mpPolicySrv6 specifies the name of SRv6
         p2mp policy whose parameters are configured in
         TIMETRA-TREE-SID-MIB::vRtrTreeSidPolicyEntry table and are signaled to
         the automatically created P2MP LSP for the selective provider tunnel.

         If the corresponding index does not exist in
         TIMETRA-TREE-SID-MIB::vRtrTreeSidPolicyEntry table, an
         'inconsistentValue' error will be returned."
    DEFVAL      { ''H }
    ::= { vRtrConfExt2Entry 7 }

vRtrMvpnServiceReservedLabel     OBJECT-TYPE
    SYNTAX      TmnxMplsLabelOrZero
    MAX-ACCESS  read-create
    STATUS      current
    DESCRIPTION
        "The value of vRtrMvpnServiceReservedLabel indicates the service label
         for the leaf PE to be allocated and advertised by root PE."
    DEFVAL      { 0 }
    ::= { vRtrConfExt2Entry 8 }

vRtrMvpnBierPtaLabelInMsb        OBJECT-TYPE
    SYNTAX      TruthValue
    MAX-ACCESS  read-create
    STATUS      current
    DESCRIPTION
        "The value of vRtrMvpnBierPtaLabelInMsb if set to true, enables
         encoding of BIER PTA label in the higher order 20-bits of the 24-bit
         MPLS label field."
    DEFVAL      { false }
    ::= { vRtrConfExt2Entry 9 }

vRtrBgpIpVpnAnySecEncGrp         OBJECT-TYPE
    SYNTAX      TNamedItemOrEmpty
    MAX-ACCESS  read-create
    STATUS      current
    DESCRIPTION
        "The vRtrBgpIpVpnAnySecEncGrp specifies the name of ANY-SEC encryption
         group for this service."
    DEFVAL      { "" }
    ::= { vRtrConfExt2Entry 10 }

vRtrInetCidrUpaRouteTable        OBJECT-TYPE
    SYNTAX      SEQUENCE OF VRtrInetCidrUpaRouteEntry
    MAX-ACCESS  not-accessible
    STATUS      current
    DESCRIPTION
        "The vRtrInetCidrUpaRouteTable is the Unreachable Prefix Announcement
         routes route table."
    ::= { tmnxVRtrObjs 223 }

vRtrInetCidrUpaRouteEntry        OBJECT-TYPE
    SYNTAX      VRtrInetCidrUpaRouteEntry
    MAX-ACCESS  not-accessible
    STATUS      current
    DESCRIPTION
        "Each row entry in the vRtrInetCidrUpaRouteTable represents columns for
         attributes specific to the Nokia SROS series implementation for the IP
         Unreachable Prefix Announcement route-table."
    INDEX       {
        vRtrID,
        vRtrInetCidrUpaRouteType,
        vRtrInetCidrUpaRoutePfx,
        vRtrInetCidrUpaRoutePfxLen,
        vRtrInetCidrUpaRoutePfxIndex
    }
    ::= { vRtrInetCidrUpaRouteTable 1 }

VRtrInetCidrUpaRouteEntry        ::= SEQUENCE
{
    vRtrInetCidrUpaRouteType         InetAddressType,
    vRtrInetCidrUpaRoutePfx          InetAddress,
    vRtrInetCidrUpaRoutePfxLen       InetAddressPrefixLength,
    vRtrInetCidrUpaRoutePfxIndex     Unsigned32,
    vRtrInetCidrUpaRouteAge          Gauge32,
    vRtrInetCidrUpaRouteProto        IANAipRouteProtocol,
    vRtrInetCidrUpaRouteProtoInst    Unsigned32,
    vRtrInetCidrUpaRoutePreference   Unsigned32,
    vRtrInetCidrUpaRouteMetric       Unsigned32
}

vRtrInetCidrUpaRouteType         OBJECT-TYPE
    SYNTAX      InetAddressType
    MAX-ACCESS  not-accessible
    STATUS      current
    DESCRIPTION
        "The value of vRtrInetCidrUpaRouteType indicates the type of
         vRtrInetCidrUpaRoutePfx address, as defined in the InetAddress MIB.

         Only those address types that may appear in an actual routing table
         are allowed as values of this object."
    ::= { vRtrInetCidrUpaRouteEntry 1 }

vRtrInetCidrUpaRoutePfx          OBJECT-TYPE
    SYNTAX      InetAddress (SIZE (0|4|16))
    MAX-ACCESS  not-accessible
    STATUS      current
    DESCRIPTION
        "The value of vRtrInetCidrUpaRoutePfx indicates the route prefix.

         The type of this address is determined by the value of the
         vRtrInetCidrUpaRouteType object.

         The values for the index objects vRtrInetCidrUpaRoutePfx and
         vRtrInetCidrUpaRoutePfxLen must be consistent."
    ::= { vRtrInetCidrUpaRouteEntry 2 }

vRtrInetCidrUpaRoutePfxLen       OBJECT-TYPE
    SYNTAX      InetAddressPrefixLength
    MAX-ACCESS  not-accessible
    STATUS      current
    DESCRIPTION
        "The value of vRtrInetCidrUpaRoutePfxLen indicates the number of
         leading bits in the vRtrInetCidrUpaRoutePfx that represents the prefix
         value. The remaining bits of the prefix will be 0.

         The values for the index objects vRtrInetCidrUpaRoutePfx and
         vRtrInetCidrUpaRoutePfxLen must be consistent."
    ::= { vRtrInetCidrUpaRouteEntry 3 }

vRtrInetCidrUpaRoutePfxIndex     OBJECT-TYPE
    SYNTAX      Unsigned32
    MAX-ACCESS  not-accessible
    STATUS      current
    DESCRIPTION
        "The value of vRtrInetCidrUpaRoutePfxIndex indicates the index of the
         entry for a given prefix when there are multiple entries per prefix
         from different routing protocols. There will be at least one entry for
         a given prefix with index 0. The entry with index 0 is the best-route
         for the given prefix."
    ::= { vRtrInetCidrUpaRouteEntry 4 }

vRtrInetCidrUpaRouteAge          OBJECT-TYPE
    SYNTAX      Gauge32
    MAX-ACCESS  read-only
    STATUS      current
    DESCRIPTION
        "The number of seconds since this route was last updated."
    ::= { vRtrInetCidrUpaRouteEntry 5 }

vRtrInetCidrUpaRouteProto        OBJECT-TYPE
    SYNTAX      IANAipRouteProtocol
    MAX-ACCESS  read-only
    STATUS      current
    DESCRIPTION
        "The value of vRtrInetCidrUpaRouteProto indicates the routing protocol
         via which this route was learned."
    ::= { vRtrInetCidrUpaRouteEntry 6 }

vRtrInetCidrUpaRouteProtoInst    OBJECT-TYPE
    SYNTAX      Unsigned32
    MAX-ACCESS  read-only
    STATUS      current
    DESCRIPTION
        "The value of vRtrInetCidrUpaRouteProtoInst indicates the instance of
         the routing protocol via which this route was learned."
    ::= { vRtrInetCidrUpaRouteEntry 7 }

vRtrInetCidrUpaRoutePreference   OBJECT-TYPE
    SYNTAX      Unsigned32 (0..255)
    MAX-ACCESS  read-only
    STATUS      current
    DESCRIPTION
        "The value of vRtrInetCidrUpaRoutePreference indicates the priority of
         this route versus the routes from different protocol sources. Smaller
         values have higher priority."
    ::= { vRtrInetCidrUpaRouteEntry 8 }

vRtrInetCidrUpaRouteMetric       OBJECT-TYPE
    SYNTAX      Unsigned32
    MAX-ACCESS  read-only
    STATUS      current
    DESCRIPTION
        "This value of vRtrInetCidrUpaRouteMetric indicates the routing metric
         for this route. The semantics of this metric are determined by the
         routing protocol."
    ::= { vRtrInetCidrUpaRouteEntry 9 }

vRtrInetStaticRtLeakDestTblLstCh OBJECT-TYPE
    SYNTAX      TimeStamp
    MAX-ACCESS  read-only
    STATUS      current
    DESCRIPTION
        "Timestamp of the last change to the vRtrInetStaticRouteLeakDestTable
         either from adding a row or removing a row."
    ::= { tmnxVRtrObjs 224 }

vRtrInetStaticRouteLeakDestTable OBJECT-TYPE
    SYNTAX      SEQUENCE OF VRtrInetStaticRouteLeakDestEntry
    MAX-ACCESS  not-accessible
    STATUS      current
    DESCRIPTION
        "The table vRtrInetStaticRouteLeakDestTable provides the list of
         destinations to which a static route is leaked to."
    ::= { tmnxVRtrObjs 225 }

vRtrInetStaticRouteLeakDestEntry OBJECT-TYPE
    SYNTAX      VRtrInetStaticRouteLeakDestEntry
    MAX-ACCESS  not-accessible
    STATUS      current
    DESCRIPTION
        "Each entry of vRtrInetStaticRouteLeakDestEntry is for a particular
         destination service identifier that the static route is leaked to."
    INDEX       {
        vRtrID,
        vRtrInetStaticRouteDestType,
        vRtrInetStaticRouteDest,
        vRtrInetStaticRouteDestPfxLen,
        vRtrInetStaticRouteLeakVRtrID
    }
    ::= { vRtrInetStaticRouteLeakDestTable 1 }

VRtrInetStaticRouteLeakDestEntry ::= SEQUENCE
{
    vRtrInetStaticRouteLeakVRtrID    TmnxVRtrID,
    vRtrInetStaticRtLeakDestRowStat  RowStatus
}

vRtrInetStaticRouteLeakVRtrID    OBJECT-TYPE
    SYNTAX      TmnxVRtrID
    MAX-ACCESS  not-accessible
    STATUS      current
    DESCRIPTION
        "The vRtrInetStaticRouteLeakVRtrID specifies the virtual router id
         which the static route is leaked to."
    ::= { vRtrInetStaticRouteLeakDestEntry 1 }

vRtrInetStaticRtLeakDestRowStat  OBJECT-TYPE
    SYNTAX      RowStatus
    MAX-ACCESS  read-create
    STATUS      current
    DESCRIPTION
        "vRtrInetStaticRtLeakDestRowStat controls the creation and deletion of
         rows in the table."
    ::= { vRtrInetStaticRouteLeakDestEntry 2 }

tmnxVRtrConformance              OBJECT IDENTIFIER ::= { tmnxSRConfs 3 }

tmnxVRtrCompliances              OBJECT IDENTIFIER ::= { tmnxVRtrConformance 1 }

tmnxVRtr7450V4v0Compliance       MODULE-COMPLIANCE
    STATUS      obsolete
    DESCRIPTION
        "The compliance statement for management of VRTR instances on Nokia
         7450 ESS series systems release R4.0."
    MODULE
        MANDATORY-GROUPS {
            tmnxVRtrGlobalR2r1Group,
            tmnxVRtrV4v0Group,
            tmnxVRtrIfV4v0Group,
            tmnxVRtrIpV4v0Group,
            tmnxVRtrNotificationV4v0Group,
            tmnxVRtrIfSubscrAuthV3v0Group,
            tmnxVRtrBfdV4v0Group
        }
    ::= { tmnxVRtrCompliances 4 }

tmnxVRtr7750V4v0Compliance       MODULE-COMPLIANCE
    STATUS      obsolete
    DESCRIPTION
        "The compliance statement for management of VRTR instances on Nokia
         7750 SR series systems release R4.0."
    MODULE
        MANDATORY-GROUPS {
            tmnxVRtrGlobalR2r1Group,
            tmnxVRtrV4v0Group,
            tmnxVRtrIfV4v0Group,
            tmnxVRtrIpV4v0Group,
            tmnxVRtrIPv6V4v0Group,
            tmnxVRtrIPv6IpV4v0Group,
            tmnxVRtrIPv6IfV4v0Group,
            tmnxVRtrNotificationV4v0Group,
            tmnxVRtrIfSubscrAuthV3v0Group,
            tmnxVRtrBfdV4v0Group
        }
    ::= { tmnxVRtrCompliances 5 }

tmnxVRtr7450V5v0Compliance       MODULE-COMPLIANCE
    STATUS      obsolete
    DESCRIPTION
        "The compliance statement for management of VRTR instances on Nokia
         7450 ESS series systems release R5.0."
    MODULE
        MANDATORY-GROUPS {
            tmnxVRtrGlobalR2r1Group,
            tmnxVRtrV5v0Group,
            tmnxVRtrIfV5v0Group,
            tmnxVRtrIpV5v0Group,
            tmnxVRtrNotificationV5v0Group,
            tmnxVRtrIfSubscrAuthV3v0Group,
            tmnxVRtrBfdV4v0Group
        }
    ::= { tmnxVRtrCompliances 6 }

tmnxVRtr7750V5v0Compliance       MODULE-COMPLIANCE
    STATUS      obsolete
    DESCRIPTION
        "The compliance statement for management of VRTR instances on Nokia
         7750 SR series systems release R5.0."
    MODULE
        MANDATORY-GROUPS {
            tmnxVRtrGlobalR2r1Group,
            tmnxVRtrV5v0Group,
            tmnxVRtrIfV5v0Group,
            tmnxVRtrIpV5v0Group,
            tmnxVRtrIPv6V4v0Group,
            tmnxVRtrIPv6IpV5v0Group,
            tmnxVRtrIPv6IfV4v0Group,
            tmnxVRtrNotificationV5v0Group,
            tmnxVRtrIfSubscrAuthV3v0Group,
            tmnxVRtrBfdV4v0Group
        }
    ::= { tmnxVRtrCompliances 7 }

tmnxVRtr7450V6v0Compliance       MODULE-COMPLIANCE
    STATUS      obsolete
    DESCRIPTION
        "The compliance statement for management of VRTR instances on Nokia
         7450 ESS series systems release R6.0."
    MODULE
        MANDATORY-GROUPS {
            tmnxVRtrGlobalV6v0Group,
            tmnxVRtrV6v0Group,
            tmnxVRtrIfV5v0Group,
            tmnxVRtrIpV5v0Group,
            tmnxVRtrNotificationV6v0Group,
            tmnxVRtrIfSubscrAuthV3v0Group,
            tmnxVRtrBfdV6v0Group,
            tmnxVRtrStaticRteCPEChkV6v0Group,
            tmnxDscpAppV6v0Group,
            tmnxVRtrIfDHCPRelayGroup,
            tmnxVRtrFibStatsV6v0Group
        }
    ::= { tmnxVRtrCompliances 8 }

tmnxVRtr77x0V6v0Compliance       MODULE-COMPLIANCE
    STATUS      obsolete
    DESCRIPTION
        "The compliance statement for management of VRTR instances on Nokia
         SROS series systems release R6.0."
    MODULE
        MANDATORY-GROUPS {
            tmnxVRtrGlobalV6v0Group,
            tmnxVRtrV6v0Group,
            tmnxVRtrIfV5v0Group,
            tmnxVRtrIpV5v0Group,
            tmnxVRtrIPv6V4v0Group,
            tmnxVRtrIPv6IpV5v0Group,
            tmnxVRtrIPv6IfV4v0Group,
            tmnxVRtrIfDhcpServerGroup,
            tmnxVRtrNotificationV6v0Group,
            tmnxVRtrIfSubscrAuthV3v0Group,
            tmnxVRtrBfdV6v0Group,
            tmnxVRtrStaticRteCPEChkV6v0Group,
            tmnxVRtrIfIpcpV6v0Group,
            tmnxVRtrIfCpmProtectGroup,
            tmnxDscpAppV6v0Group,
            tmnxVRtrIfDHCPRelayGroup,
            tmnxVRtrFibStatsV6v0Group
        }
    ::= { tmnxVRtrCompliances 9 }

tmnxVRtr7450V6v1Compliance       MODULE-COMPLIANCE
    STATUS      obsolete
    DESCRIPTION
        "The compliance statement for management of VRTR instances on Nokia
         7450 ESS series systems release R6.1."
    MODULE
        MANDATORY-GROUPS {
            tmnxVRtrGlobalV6v0Group,
            tmnxVRtrV6v0Group,
            tmnxVRtrIfV5v0Group,
            tmnxVRtrIpV5v0Group,
            tmnxVRtrNotificationV6v1Group,
            tmnxVRtrIfSubscrAuthV3v0Group,
            tmnxVRtrBfdV6v0Group,
            tmnxVRtrStaticRteCPEChkV6v0Group,
            tmnxDscpAppV6v0Group,
            tmnxVRtrIfDHCPRelayV6v1Group,
            tmnxVRtrV6v1Group,
            tmnxVRtrFibStatsV6v1Group
        }
    ::= { tmnxVRtrCompliances 10 }

tmnxVRtr77x0V6v1Compliance       MODULE-COMPLIANCE
    STATUS      obsolete
    DESCRIPTION
        "The compliance statement for management of VRTR instances on Nokia
         SROS series systems release R6.1."
    MODULE
        MANDATORY-GROUPS {
            tmnxVRtrGlobalV6v0Group,
            tmnxVRtrV6v0Group,
            tmnxVRtrIfV5v0Group,
            tmnxVRtrIpV5v0Group,
            tmnxVRtrIPv6V4v0Group,
            tmnxVRtrIPv6IpV5v0Group,
            tmnxVRtrIPv6IfV4v0Group,
            tmnxVRtrIfDhcpServerGroup,
            tmnxVRtrNotificationV6v1Group,
            tmnxVRtrIfSubscrAuthV3v0Group,
            tmnxVRtrBfdV6v0Group,
            tmnxVRtrStaticRteCPEChkV6v0Group,
            tmnxVRtrIfIpcpV6v0Group,
            tmnxVRtrIfCpmProtectGroup,
            tmnxDscpAppV6v0Group,
            tmnxVRtrIfDHCPRelayV6v1Group,
            tmnxVRtrV6v1Group,
            tmnxVRtrFibStatsV6v1Group
        }
    ::= { tmnxVRtrCompliances 11 }

tmnxVRtr7450V7v0Compliance       MODULE-COMPLIANCE
    STATUS      obsolete
    DESCRIPTION
        "The compliance statement for management of VRTR instances on Nokia
         7450 ESS series systems release R7.0."
    MODULE
        MANDATORY-GROUPS {
            tmnxVRtrGlobalV6v0Group,
            tmnxVRtrIfV5v0Group,
            tmnxVRtrIPv6MgtIfV7v0Group,
            tmnxVRtrIfSubscrAuthV3v0Group,
            tmnxVRtrBfdV6v0Group,
            tmnxVRtrStaticRteCPEChkV6v0Group,
            tmnxDscpAppV6v0Group,
            tmnxVRtrIfDHCPRelayV7v0Group,
            tmnxVRtrV6v1Group,
            tmnxVRtrFibStatsV6v1Group,
            tmnxVRtrInetAllCidrRouteV7v0Group,
            tmnxVRtrInetStaticRouteV7v0Group,
            tmnxVRtruRPFV7v0Group,
            tmnxVRtrMvpnV7v0Group,
            tmnxVRtrIfV7v0Group,
            tmnxVRtrV7v0Group,
            tmnxVRtrIpV7v0Group,
            tmnxVRtrBfdV7v0Group,
            tmnxVRtrNotificationV7v0Group
        }
    ::= { tmnxVRtrCompliances 12 }

tmnxVRtr77x0V7v0Compliance       MODULE-COMPLIANCE
    STATUS      obsolete
    DESCRIPTION
        "The compliance statement for management of VRTR instances on Nokia
         SROS series systems release R7.0."
    MODULE
        MANDATORY-GROUPS {
            tmnxVRtrGlobalV6v0Group,
            tmnxVRtrIfV5v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrBfdV6v0Group,
            tmnxVRtrStaticRteCPEChkV6v0Group,
            tmnxVRtrIfIpcpV6v0Group,
            tmnxVRtrIfCpmProtectGroup,
            tmnxDscpAppV6v0Group,
            tmnxVRtrIfDHCPRelayV7v0Group,
            tmnxVRtrV6v1Group,
            tmnxVRtrFibStatsV6v1Group,
            tmnxVRtrInetAllCidrRouteV7v0Group,
            tmnxVRtrInetStaticRouteV7v0Group,
            tmnxVRtruRPFV7v0Group,
            tmnxVRtrMvpnV7v0Group,
            tmnxVRtrIfV7v0Group,
            tmnxVRtrV7v0Group,
            tmnxVRtrIpV7v0Group,
            tmnxVRtrBfdV7v0Group,
            tmnxVRtrNotificationV7v0Group
        }
    ::= { tmnxVRtrCompliances 13 }

tmnxVRtr7450V8v0Compliance       MODULE-COMPLIANCE
    STATUS      obsolete
    DESCRIPTION
        "The compliance statement for management of VRTR instances on Nokia
         7450 ESS series systems release R8.0."
    MODULE
        MANDATORY-GROUPS {
            tmnxVRtrGlobalV6v0Group,
            tmnxVRtrIfV5v0Group,
            tmnxVRtrIPv6MgtIfV7v0Group,
            tmnxVRtrIfSubscrAuthV3v0Group,
            tmnxVRtrBfdV6v0Group,
            tmnxVRtrStaticRteCPEChkV6v0Group,
            tmnxDscpAppV6v0Group,
            tmnxVRtrIfDHCPRelayV8v0Group,
            tmnxVRtrV6v1Group,
            tmnxVRtrInetAllCidrRouteV7v0Group,
            tmnxVRtrInetStaticRouteV7v0Group,
            tmnxVRtruRPFV7v0Group,
            tmnxVRtrMvpnV7v0Group,
            tmnxVRtrIfV7v0Group,
            tmnxVRtrV8v0Group,
            tmnxVRtrBfdV7v0Group,
            tmnxVRtrNotificationV8v0Group,
            tmnxVRtrNetDomainGroup,
            tmnxVRtrBfdV8v0Group,
            tmnxVRtrIpV7v0Group,
            tmnxVRtrFibStatsV8v0Group,
            tmnxVRtrMvpnPmsiV8v0Group,
            tmnxVRtrIfDHCPRelayV6v1Group
        }
    ::= { tmnxVRtrCompliances 14 }

tmnxVRtr77x0V8v0Compliance       MODULE-COMPLIANCE
    STATUS      obsolete
    DESCRIPTION
        "The compliance statement for management of VRTR instances on Nokia
         SROS series systems release R8.0."
    MODULE
        MANDATORY-GROUPS {
            tmnxVRtrGlobalV6v0Group,
            tmnxVRtrIfV5v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrBfdV6v0Group,
            tmnxVRtrStaticRteCPEChkV6v0Group,
            tmnxVRtrIfIpcpV6v0Group,
            tmnxVRtrIfCpmProtectGroup,
            tmnxDscpAppV6v0Group,
            tmnxVRtrIfDHCPRelayV8v0Group,
            tmnxVRtrV6v1Group,
            tmnxVRtrInetAllCidrRouteV7v0Group,
            tmnxVRtrInetStaticRouteV7v0Group,
            tmnxVRtruRPFV7v0Group,
            tmnxVRtrMvpnV7v0Group,
            tmnxVRtrIfV7v0Group,
            tmnxVRtrV8v0Group,
            tmnxVRtrBfdV7v0Group,
            tmnxVRtrNotificationV8v0Group,
            tmnxVRtrNetDomainGroup,
            tmnxVRtrTunIntV8v0Group,
            tmnxVRtrBfdV8v0Group,
            tmnxVRtrIpV7v0Group,
            tmnxVRtrFibStatsV8v0Group,
            tmnxVRtrMvpnPmsiV8v0Group,
            tmnxVRtrIfDHCPRelayV6v1Group
        }
    ::= { tmnxVRtrCompliances 15 }

tmnxVRtr7450V9v0Compliance       MODULE-COMPLIANCE
    STATUS      obsolete
    DESCRIPTION
        "The compliance statement for management of VRTR instances on Nokia
         7450 ESS series systems release R9.0."
    MODULE
        MANDATORY-GROUPS {
            tmnxVRtrGlobalV6v0Group,
            tmnxVRtrIfV5v0Group,
            tmnxVRtrIPv6MgtIfV7v0Group,
            tmnxVRtrIfSubscrAuthV3v0Group,
            tmnxVRtrStaticRteCPEChkV6v0Group,
            tmnxDscpAppV6v0Group,
            tmnxVRtrIfDHCPRelayV9v0Group,
            tmnxVRtrV6v1Group,
            tmnxVRtrInetAllCidrRouteV7v0Group,
            tmnxVRtrInetStaticRouteV7v0Group,
            tmnxVRtruRPFV7v0Group,
            tmnxVRtrMvpnV7v0Group,
            tmnxVRtrIfV7v0Group,
            tmnxVRtrV8v0Group,
            tmnxVRtrV9v0Group,
            tmnxVRtrBfdV7v0Group,
            tmnxVRtrNotificationV8v0Group,
            tmnxVRtrNetDomainGroup,
            tmnxVRtrIpV7v0Group,
            tmnxVRtrFibStatsV8v0Group,
            tmnxVRtrMvpnPmsiV8v0Group,
            tmnxVRtrIfDHCPRelayV6v1Group,
            tmnxVRtrQPPBV9v0R4Group,
            tmnxVRtrIfStatsV9v0Group,
            tmnxVRtrMSPwV9v0Group,
            tmnxVRtrBfdV9v0Group,
            tmnxVRtrMvpnSrcRedV9v0R4Group,
            tmnxVRtrStatV9v0Group
        }
    ::= { tmnxVRtrCompliances 16 }

tmnxVRtr77x0V9v0Compliance       MODULE-COMPLIANCE
    STATUS      obsolete
    DESCRIPTION
        "The compliance statement for management of VRTR instances on Nokia
         SROS series systems release R9.0."
    MODULE
        MANDATORY-GROUPS {
            tmnxVRtrGlobalV6v0Group,
            tmnxVRtrIfV5v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrV6v1Group,
            tmnxVRtrInetAllCidrRouteV7v0Group,
            tmnxVRtrInetStaticRouteV7v0Group,
            tmnxVRtruRPFV7v0Group,
            tmnxVRtrMvpnV7v0Group,
            tmnxVRtrIfV7v0Group,
            tmnxVRtrV8v0Group,
            tmnxVRtrV9v0Group,
            tmnxVRtrBfdV7v0Group,
            tmnxVRtrNotificationV8v0Group,
            tmnxVRtrNetDomainGroup,
            tmnxVRtrTunIntV8v0Group,
            tmnxVRtrIpV7v0Group,
            tmnxVRtrFibStatsV8v0Group,
            tmnxVRtrMvpnPmsiV8v0Group,
            tmnxVRtrIfDHCPRelayV6v1Group,
            tmnxVRtrQPPBV9v0R4Group,
            tmnxVRtrBfdV9v0Group,
            tmnxVRtrIfDHCP6V9v0Group,
            tmnxVRtrIfStatsV9v0Group,
            tmnxVRtrIfIpReasV9v0Group,
            tmnxVRtrIfV9v0Group,
            tmnxVRtrMSPwV9v0Group,
            tmnxVRtrNatRedGroup,
            tmnxVRtrMvpnSrcRedV9v0R4Group,
            tmnxVRtrStatV9v0Group
        }
    ::= { tmnxVRtrCompliances 17 }

tmnxVRtr77x0V10v0Compliance      MODULE-COMPLIANCE
    STATUS      obsolete
    DESCRIPTION
        "The compliance statement for management of VRTR instances on Nokia
         SROS series systems release R10.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrV6v1Group,
            tmnxVRtrInetAllCidrRouteV7v0Group,
            tmnxVRtrInetStaticRouteV7v0Group,
            tmnxVRtruRPFV7v0Group,
            tmnxVRtrV9v0Group,
            tmnxVRtrV10v0Group,
            tmnxVRtrPolicyGroup,
            tmnxVRtrBfdV7v0Group,
            tmnxVRtrNotificationV8v0Group,
            tmnxVRtrNetDomainGroup,
            tmnxVRtrTunIntV8v0Group,
            tmnxVRtrIpV7v0Group,
            tmnxVRtrFibStatsV8v0Group,
            tmnxVRtrMvpnPmsiV8v0Group,
            tmnxVRtrIfDHCPRelayV6v1Group,
            tmnxVRtrQPPBV9v0R4Group,
            tmnxVRtrBfdV9v0Group,
            tmnxVRtrIfDHCP6V9v0Group,
            tmnxVRtrIfDHCP6V10v0Group,
            tmnxVRtrIfStatsV9v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrGlobalV10v0Group,
            tmnxVRtrQosQGrplV10v0Group,
            tmnxVRtrStatV10v0Group,
            tmnxVRtrIPv6MgtIfV7v0Group,
            tmnxMGVRtrIfV4v0Group,
            tmnxVRtrIfV10v0Group,
            tmnxVRtrNotificationV10v0Group
        }
    ::= { tmnxVRtrCompliances 18 }

tmnxVRtr77x0V11v0Compliance      MODULE-COMPLIANCE
    STATUS      obsolete
    DESCRIPTION
        "The compliance statement for management of VRTR instances on Nokia
         SROS series systems release R11.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrV10v0Group,
            tmnxVRtrPolicyGroup,
            tmnxVRtrNetDomainGroup,
            tmnxVRtrTunIntV8v0Group,
            tmnxVRtrIpV7v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrGlobalV10v0Group,
            tmnxVRtrQosQGrplV10v0Group,
            tmnxVRtrStatV10v0Group,
            tmnxVRtrStatV11v0Group,
            tmnxVRtrIPv6MgtIfV7v0Group,
            tmnxMGVRtrIfV4v0Group,
            tmnxVRtrIfV10v0Group,
            tmnxVRtrNotificationV10v0Group,
            tmnxVRtrFlowSpecV11v0Group,
            tmnxVRtrIfExtV11v0Group,
            tmnxVRtrGrtLocalMgmtV10v0Group,
            tmnxVRtrV11v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrNotificationV11v0Group,
            tmnxVRtrIfExtIfArpRetryTimerGrp
        }
    ::= { tmnxVRtrCompliances 19 }

tmnxVRtr7xx0V12v0Compliance      MODULE-COMPLIANCE
    STATUS      obsolete
    DESCRIPTION
        "The compliance statement for management of VRTR instances on Nokia
         SROS series systems release R12.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrV10v0Group,
            tmnxVRtrPolicyGroup,
            tmnxVRtrNetDomainGroup,
            tmnxVRtrTunIntV8v0Group,
            tmnxVRtrIpV7v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrGlobalV10v0Group,
            tmnxVRtrQosQGrplV10v0Group,
            tmnxVRtrStatV10v0Group,
            tmnxVRtrStatV11v0Group,
            tmnxVRtrIPv6MgtIfV7v0Group,
            tmnxMGVRtrIfV4v0Group,
            tmnxVRtrIfV10v0Group,
            tmnxVRtrNotificationV10v0Group,
            tmnxVRtrFlowSpecV11v0Group,
            tmnxVRtrIfExtV12v0Group,
            tmnxVRtrGrtLocalMgmtV10v0Group,
            tmnxVRtrV11v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrNotificationV11v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrBgpEvpnIpRoutes12v0Group,
            tmnxVRtrConfExtV12v0Group,
            tmnxVRtrStickyHashEcmp12v0Group,
            tmnxVRtrV13v0Group,
            tmnxVRtrNotifyObjsNHRvplsArpGrp,
            tmnxVRtrNotificationNHRvplsArpGr,
            tmnxVRtrHoldDownTimeV12v0Group,
            tmnxVRtrIfExtIfArpRetryTimerGrp
        }
    ::= { tmnxVRtrCompliances 20 }

tmnxVRtr7xx0V13v0Compliance      MODULE-COMPLIANCE
    STATUS      obsolete
    DESCRIPTION
        "The compliance statement for management of VRTR instances on Nokia
         SROS series systems release R13.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrPolicyGroup,
            tmnxVRtrNetDomainGroup,
            tmnxVRtrTunIntV8v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrGlobalV10v0Group,
            tmnxVRtrQosQGrplV10v0Group,
            tmnxVRtrStatV10v0Group,
            tmnxVRtrStatV11v0Group,
            tmnxVRtrIPv6MgtIfV7v0Group,
            tmnxMGVRtrIfV4v0Group,
            tmnxVRtrIfV10v0Group,
            tmnxVRtrNotificationV10v0Group,
            tmnxVRtrFlowSpecV11v0Group,
            tmnxVRtrIfExtV12v0Group,
            tmnxVRtrGrtLocalMgmtV10v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrNotificationV11v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrBgpEvpnIpRoutes12v0Group,
            tmnxVRtrConfExtV12v0Group,
            tmnxVRtrStickyHashEcmp12v0Group,
            tmnxVRtrV13v0Group,
            tmnxVRtrNotifyObjsNHRvplsArpGrp,
            tmnxVRtrNotificationNHRvplsArpGr,
            tmnxVRtrTunnelExtTableV13v0Group,
            tmnxVRtrMcastSpmsiEnhV13v0Group,
            tmnxVRtrHoldDownTimeV12v0Group,
            tmnxVRtrLoadBalEnhV13v0Group,
            tmnxVRtrInetSRIndirectV13v0Group,
            tmnxVRtrIfExtIfArpRetryTimerGrp,
            tmnxVRtrBgpAutoRDGroup,
            tmnxVRtrTunnelTableStatGroup,
            tmnxVRtrIfDHCPRelayV13v0Group,
            tmnxVRtrLdpIpv613v0Group,
            tmnxVRtrIfLagPerLinkHashGroup,
            tmnxVRtrCidrNextHopOwnInstGroup,
            tmnxVRtrIpV13v0Group,
            tmnxVRtrIpV13v0ObsoletedGroup,
            tmnxVRtrV13v0GenObsoletedGroup,
            tmnxVRtrIfArpNbrLimitGroup,
            tmnxVRtrIfExtV13v0Group,
            tmnxVRtrV13v0IfStatsGroup,
            tmnxVRtrIfArpNbrNotifGroup,
            tmnxVRtrTunnelTableCBFV13v0Group,
            tmnxVRtrIPv6IPsecStatGroup,
            tmnxVRtrUniqueIfIndexGroup
        }
    ::= { tmnxVRtrCompliances 21 }

tmnxVRtr7xx0V14v0Compliance      MODULE-COMPLIANCE
    STATUS      obsolete
    DESCRIPTION
        "The compliance statement for management of VRTR instances on Nokia
         SROS series systems release R14.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrPolicyGroup,
            tmnxVRtrNetDomainGroup,
            tmnxVRtrTunIntV8v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrGlobalV10v0Group,
            tmnxVRtrQosQGrplV10v0Group,
            tmnxVRtrStatV10v0Group,
            tmnxVRtrStatV11v0Group,
            tmnxVRtrIPv6MgtIfV7v0Group,
            tmnxMGVRtrIfV4v0Group,
            tmnxVRtrIfV10v0Group,
            tmnxVRtrNotificationV10v0Group,
            tmnxVRtrFlowSpecV11v0Group,
            tmnxVRtrIfExtV12v0Group,
            tmnxVRtrGrtLocalMgmtV10v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrNotificationV14v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrBgpEvpnIpRoutes12v0Group,
            tmnxVRtrConfExtV12v0Group,
            tmnxVRtrStickyHashEcmp12v0Group,
            tmnxVRtrV14v0Group,
            tmnxVRtrNotifyObjsNHRvplsArpGrp,
            tmnxVRtrNotificationNHRvplsArpGr,
            tmnxVRtrTunnelExtTableV13v0Group,
            tmnxVRtrMcastSpmsiEnhV13v0Group,
            tmnxVRtrHoldDownTimeV12v0Group,
            tmnxVRtrLoadBalEnhV13v0Group,
            tmnxVRtrInetSRIndirectV13v0Group,
            tmnxVRtrIfExtIfArpRetryTimerGrp,
            tmnxVRtrBgpAutoRDGroup,
            tmnxVRtrTunnelTableStatGroup,
            tmnxVRtrIfDHCPRelayV13v0Group,
            tmnxVRtrLdpIpv613v0Group,
            tmnxVRtrIfLagPerLinkHashGroup,
            tmnxVRtrCidrNextHopOwnInstGroup,
            tmnxVRtrIpV13v0Group,
            tmnxVRtrIpV13v0ObsoletedGroup,
            tmnxVRtrV13v0GenObsoletedGroup,
            tmnxVRtrIfArpNbrLimitGroup,
            tmnxVRtrIfExtV13v0Group,
            tmnxVRtrV13v0IfStatsGroup,
            tmnxVRtrIfArpNbrNotifGroup,
            tmnxVRtrTunnelTableCBFV13v0Group,
            tmnxVRtrIPv6IPsecStatGroup,
            tmnxVRtrUniqueIfIndexGroup,
            tmnxVRtrStaticRoutePrefixGroup,
            tmnxVRtrEntropyLabelGroup,
            tmnxVRtrLspBfdGroup,
            tmnxVRtrConfFlowspecV14v0Group,
            tmnxVRtrIfV14v0Group,
            tmnxVRtrInetSRIndirectV14v0Group,
            tmnxVRtrFibStatsV14v0Group,
            tmnxVRtrIfDHCPRelayV14v0Group,
            tmnxVRtrBgpLblIpRoutes14v0Group,
            tmnxVRtrV6TunnelTableStatGroup,
            tmnxVRtrSrTeV14v0Group,
            tmnxVRtrIfExtV14v0Group,
            tmnxVRtrLoopbackNotifGroup,
            tmnxVRtrV14v0NotifyObjsGroup,
            tmnxVRtrTunnelTableLSCV14v0Group,
            tmnxVRtrIcmpV4StatsV14v0Group,
            tmnxVRtrIcmpV4ParamV14v0Group,
            tmnxVRtrTunnelTableNhTV14v0Group,
            tmnxVRtrFpeV14v0Group
        }
    ::= { tmnxVRtrCompliances 22 }

tmnxVRtr7xx0V15v0Compliance      MODULE-COMPLIANCE
    STATUS      obsolete
    DESCRIPTION
        "The compliance statement for management of VRTR instances on Nokia
         SROS series systems release R15.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrPolicyGroup,
            tmnxVRtrNetDomainGroup,
            tmnxVRtrTunIntV8v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrQosQGrplV10v0Group,
            tmnxVRtrStatV10v0Group,
            tmnxVRtrStatV11v0Group,
            tmnxVRtrIPv6MgtIfV7v0Group,
            tmnxMGVRtrIfV4v0Group,
            tmnxVRtrIfV10v0Group,
            tmnxVRtrNotificationV10v0Group,
            tmnxVRtrFlowSpecV11v0Group,
            tmnxVRtrGrtLocalMgmtV10v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrNotificationV14v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrBgpEvpnIpRoutes12v0Group,
            tmnxVRtrConfExtV12v0Group,
            tmnxVRtrStickyHashEcmp12v0Group,
            tmnxVRtrV14v0Group,
            tmnxVRtrNotifyObjsNHRvplsArpGrp,
            tmnxVRtrNotificationNHRvplsArpGr,
            tmnxVRtrTunnelExtTableV13v0Group,
            tmnxVRtrMcastSpmsiEnhV13v0Group,
            tmnxVRtrHoldDownTimeV12v0Group,
            tmnxVRtrLoadBalEnhV13v0Group,
            tmnxVRtrInetSRIndirectV13v0Group,
            tmnxVRtrIfExtIfArpRetryTimerGrp,
            tmnxVRtrBgpAutoRDGroup,
            tmnxVRtrTunnelTableStatGroup,
            tmnxVRtrIfDHCPRelayV13v0Group,
            tmnxVRtrLdpIpv613v0Group,
            tmnxVRtrIfLagPerLinkHashGroup,
            tmnxVRtrCidrNextHopOwnInstGroup,
            tmnxVRtrIpV13v0ObsoletedGroup,
            tmnxVRtrV13v0GenObsoletedGroup,
            tmnxVRtrIfArpNbrLimitGroup,
            tmnxVRtrIfExtV13v0Group,
            tmnxVRtrV13v0IfStatsGroup,
            tmnxVRtrIfArpNbrNotifGroup,
            tmnxVRtrTunnelTableCBFV13v0Group,
            tmnxVRtrIPv6IPsecStatGroup,
            tmnxVRtrUniqueIfIndexGroup,
            tmnxVRtrStaticRoutePrefixGroup,
            tmnxVRtrEntropyLabelGroup,
            tmnxVRtrLspBfdGroup,
            tmnxVRtrConfFlowspecV14v0Group,
            tmnxVRtrIfV14v0Group,
            tmnxVRtrInetSRIndirectV14v0Group,
            tmnxVRtrFibStatsV14v0Group,
            tmnxVRtrIfDHCPRelayV14v0Group,
            tmnxVRtrBgpLblIpRoutes14v0Group,
            tmnxVRtrV6TunnelTableStatGroup,
            tmnxVRtrSrTeV14v0Group,
            tmnxVRtrIfExtV14v0Group,
            tmnxVRtrLoopbackNotifGroup,
            tmnxVRtrV14v0NotifyObjsGroup,
            tmnxVRtrTunnelTableLSCV14v0Group,
            tmnxVRtrIcmpV4StatsV14v0Group,
            tmnxVRtrIcmpV4ParamV14v0Group,
            tmnxVRtrTunnelTableNhTV14v0Group,
            tmnxVRtrFpeV14v0Group,
            tmnxVRtrV15v0Group,
            tmnxVrtrDDosDCpuProtPolicyGrp,
            tmnxVRtrIfExtV15v0Group,
            tmnxVRtrUdpTunnelGroup,
            tmnxVRtrIpV15v0Group,
            tmnxVRtrQinQNetworkIntfGroup,
            tmnxVRtrGlobalV15v0Group,
            tmnxVRtrIfExtV15v0ObjectGroup,
            tmnxVRtrClassFwdingV15v0Group,
            tmnxVRtrNotificationV15v0Group,
            tmnxVRtrIfExtHostRteV15v0Group,
            tmnxVRtrIfNgeStatsGroup
        }
    ::= { tmnxVRtrCompliances 23 }

tmnxVRtr7xx0V16v0Compliance      MODULE-COMPLIANCE
    STATUS      obsolete
    DESCRIPTION
        "The compliance statement for management of virtual router instances on
         Nokia SROS series systems release R16.0."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrPolicyGroup,
            tmnxVRtrNetDomainGroup,
            tmnxVRtrTunIntV8v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrQosQGrplV10v0Group,
            tmnxVRtrStatV10v0Group,
            tmnxVRtrStatV11v0Group,
            tmnxVRtrIPv6MgtIfV7v0Group,
            tmnxMGVRtrIfV4v0Group,
            tmnxVRtrNotificationV10v0Group,
            tmnxVRtrFlowSpecV11v0Group,
            tmnxVRtrGrtLocalMgmtV10v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrNotificationV14v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrBgpEvpnIpRoutes12v0Group,
            tmnxVRtrConfExtV12v0Group,
            tmnxVRtrStickyHashEcmp12v0Group,
            tmnxVRtrV14v0Group,
            tmnxVRtrNotifyObjsNHRvplsArpGrp,
            tmnxVRtrNotificationNHRvplsArpGr,
            tmnxVRtrMcastSpmsiEnhV13v0Group,
            tmnxVRtrHoldDownTimeV12v0Group,
            tmnxVRtrLoadBalEnhV13v0Group,
            tmnxVRtrInetSRIndirectV13v0Group,
            tmnxVRtrIfExtIfArpRetryTimerGrp,
            tmnxVRtrBgpAutoRDGroup,
            tmnxVRtrTunnelTableStatGroup,
            tmnxVRtrIfDHCPRelayV13v0Group,
            tmnxVRtrLdpIpv613v0Group,
            tmnxVRtrIfLagPerLinkHashGroup,
            tmnxVRtrCidrNextHopOwnInstGroup,
            tmnxVRtrIpV13v0ObsoletedGroup,
            tmnxVRtrV13v0GenObsoletedGroup,
            tmnxVRtrIfArpNbrLimitGroup,
            tmnxVRtrIfExtV13v0Group,
            tmnxVRtrV13v0IfStatsGroup,
            tmnxVRtrIfArpNbrNotifGroup,
            tmnxVRtrIPv6IPsecStatGroup,
            tmnxVRtrUniqueIfIndexGroup,
            tmnxVRtrStaticRoutePrefixGroup,
            tmnxVRtrEntropyLabelGroup,
            tmnxVRtrLspBfdGroup,
            tmnxVRtrConfFlowspecV14v0Group,
            tmnxVRtrInetSRIndirectV14v0Group,
            tmnxVRtrFibStatsV14v0Group,
            tmnxVRtrIfDHCPRelayV14v0Group,
            tmnxVRtrBgpLblIpRoutes14v0Group,
            tmnxVRtrV6TunnelTableStatGroup,
            tmnxVRtrSrTeV14v0Group,
            tmnxVRtrIfExtV14v0Group,
            tmnxVRtrLoopbackNotifGroup,
            tmnxVRtrV14v0NotifyObjsGroup,
            tmnxVRtrIcmpV4StatsV14v0Group,
            tmnxVRtrIcmpV4ParamV14v0Group,
            tmnxVRtrFpeV14v0Group,
            tmnxVRtrV15v0Group,
            tmnxVrtrDDosDCpuProtPolicyGrp,
            tmnxVRtrIfExtV15v0Group,
            tmnxVRtrUdpTunnelGroup,
            tmnxVRtrIpV15v0Group,
            tmnxVRtrQinQNetworkIntfGroup,
            tmnxVRtrIfExtV15v0ObjectGroup,
            tmnxVRtrClassFwdingV15v0Group,
            tmnxVRtrNotificationV15v0Group,
            tmnxVRtrIfExtHostRteV15v0Group,
            tmnxVRtrIfStatsV16v0Group,
            tmnxVRtrIfNgeStatsGroup,
            tmnxVRtrAdminTagsV16v0Group,
            tmnxVRtrLargeCommValV16v0Group,
            tmnxVRtrIfStatsDBCastV16v0Group,
            tmnxVRtrIfV16v0Group,
            tmnxVRtrLocalPrefV16v0Group,
            tmnxVRtrIpV16v0Group,
            tmnxVRtrLoadBalWeightV16v0Group,
            tmnxVRtrInetExtTunnelV16v0Group,
            tmnxVRtrGrtLeakImpPolV16v0Group,
            tmnxVRtrInetTunnStatV16v0Group,
            tmnxVRtrGlobalV16v0Group,
            tmnxVRtrInetRouteV16v0Group,
            tmnxVRtrSrTnlStatV16v0Group,
            tmnxVRtrBierV16v0Group,
            tmnxVRtrRibApiV16v0Group,
            tmnxVRtrRibTelemetryV16v0Group,
            tmnxVRtrMplsFwdPlcyV16v0Group,
            tmnxVRtrLeakExportLimNotifGroup,
            tmnxVRtrInetSRIndirectV16v0Group,
            tmnxVRtrNeInfoGroup,
            tmnxVRtrNeNotifGroup
        }
    ::= { tmnxVRtrCompliances 25 }

tmnxVRtr7xx0V19v0Compliance      MODULE-COMPLIANCE
    STATUS      obsolete
    DESCRIPTION
        "The compliance statement for management of virtual router instances on
         Nokia SROS series systems release R19."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrPolicyGroup,
            tmnxVRtrNetDomainGroup,
            tmnxVRtrTunIntV8v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrQosQGrplV10v0Group,
            tmnxVRtrStatV10v0Group,
            tmnxVRtrStatV11v0Group,
            tmnxVRtrIPv6MgtIfV7v0Group,
            tmnxMGVRtrIfV4v0Group,
            tmnxVRtrFlowSpecV11v0Group,
            tmnxVRtrGrtLocalMgmtV10v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrConfExtV12v0Group,
            tmnxVRtrStickyHashEcmp12v0Group,
            tmnxVRtrV14v0Group,
            tmnxVRtrNotifyObjsNHRvplsArpGrp,
            tmnxVRtrNotificationNHRvplsArpGr,
            tmnxVRtrMcastSpmsiEnhV13v0Group,
            tmnxVRtrHoldDownTimeV12v0Group,
            tmnxVRtrLoadBalEnhV13v0Group,
            tmnxVRtrInetSRIndirectV13v0Group,
            tmnxVRtrIfExtIfArpRetryTimerGrp,
            tmnxVRtrBgpAutoRDGroup,
            tmnxVRtrTunnelTableStatGroup,
            tmnxVRtrIfDHCPRelayV13v0Group,
            tmnxVRtrLdpIpv613v0Group,
            tmnxVRtrIfLagPerLinkHashGroup,
            tmnxVRtrCidrNextHopOwnInstGroup,
            tmnxVRtrIpV13v0ObsoletedGroup,
            tmnxVRtrV13v0GenObsoletedGroup,
            tmnxVRtrIfArpNbrLimitGroup,
            tmnxVRtrIfExtV13v0Group,
            tmnxVRtrV13v0IfStatsGroup,
            tmnxVRtrIfArpNbrNotifGroup,
            tmnxVRtrIPv6IPsecStatGroup,
            tmnxVRtrUniqueIfIndexGroup,
            tmnxVRtrStaticRoutePrefixGroup,
            tmnxVRtrEntropyLabelGroup,
            tmnxVRtrLspBfdGroup,
            tmnxVRtrConfFlowspecV14v0Group,
            tmnxVRtrInetSRIndirectV14v0Group,
            tmnxVRtrFibStatsV14v0Group,
            tmnxVRtrIfDHCPRelayV14v0Group,
            tmnxVRtrBgpLblIpRoutes14v0Group,
            tmnxVRtrV6TunnelTableStatGroup,
            tmnxVRtrSrTeV14v0Group,
            tmnxVRtrIfExtV14v0Group,
            tmnxVRtrLoopbackNotifGroup,
            tmnxVRtrV14v0NotifyObjsGroup,
            tmnxVRtrIcmpV4StatsV14v0Group,
            tmnxVRtrIcmpV4ParamV14v0Group,
            tmnxVRtrFpeV14v0Group,
            tmnxVRtrV15v0Group,
            tmnxVrtrDDosDCpuProtPolicyGrp,
            tmnxVRtrIfExtV15v0Group,
            tmnxVRtrUdpTunnelGroup,
            tmnxVRtrIpV15v0Group,
            tmnxVRtrQinQNetworkIntfGroup,
            tmnxVRtrIfExtV15v0ObjectGroup,
            tmnxVRtrClassFwdingV15v0Group,
            tmnxVRtrIfExtHostRteV20v0Group,
            tmnxVRtrIfStatsV16v0Group,
            tmnxVRtrIfNgeStatsGroup,
            tmnxVRtrAdminTagsV16v0Group,
            tmnxVRtrLargeCommValV16v0Group,
            tmnxVRtrIfStatsDBCastV16v0Group,
            tmnxVRtrIfV16v0Group,
            tmnxVRtrLocalPrefV16v0Group,
            tmnxVRtrIpV16v0Group,
            tmnxVRtrLoadBalWeightV16v0Group,
            tmnxVRtrInetExtTunnelV16v0Group,
            tmnxVRtrGrtLeakImpPolV16v0Group,
            tmnxVRtrInetTunnStatV16v0Group,
            tmnxVRtrGlobalV16v0Group,
            tmnxVRtrInetRouteV16v0Group,
            tmnxVRtrSrTnlStatV16v0Group,
            tmnxVRtrBierV16v0Group,
            tmnxVRtrDhcpClientGroup,
            tmnxVRtrRibApiV16v0Group,
            tmnxVRtrRibTelemetryV16v0Group,
            tmnxVRtrMplsFwdPlcyV16v0Group,
            tmnxVRtrIcmpV4StatsV19v0Group,
            tmnxVRtrLeakExportLimNotifGroup,
            tmnxVRtrInetSRIndirectV16v0Group,
            tmnxVRtrDhcpRoutesV19v0Group,
            tmnxVRtrV19v0Group,
            tmnxVRtrIfV19v0Group,
            tmnxVRtrNotificationV19v0Group,
            vRtrIfEgressQueueV19v0Group,
            tmnxVRtrIfQosV19v0Group,
            vRtrIfIngressPolicerV19v0Group,
            vRtrMplsTunnelModeV19v0Group,
            tmnxVRtrDiscardCV19v0Group,
            vRtrMplsTunnelModeV19v0Group,
            tmnxVRtrConfFlowspecV19v0Group,
            tmnxVRtrIfHostRouteGroup,
            tmnxVRtrTunTerminationV19v0Group,
            tmnxVRtrIfPhysStatsV19v0Group,
            tmnxVRtrSrTnlStatV19v10Group,
            vRtrIfEgressQueueV19v01Group,
            tmnxVRtrSrTeV6Group
        }
    ::= { tmnxVRtrCompliances 26 }

tmnxVRtr7xx0V20v0Compliance      MODULE-COMPLIANCE
    STATUS      current
    DESCRIPTION
        "The compliance statement for management of virtual router instances on
         Nokia SROS series systems release R20."
    MODULE
        MANDATORY-GROUPS {
            tmnxVRtrGlobalV6v0Group,
            tmnxVRtrIPv6V4v0Group,
            tmnxVRtrIPv6IpV5v0Group,
            tmnxVRtrIPv6IfV4v0Group,
            tmnxVRtrIfDhcpServerGroup,
            tmnxVRtrIfSubscrAuthV3v0Group,
            tmnxVRtrStaticRteCPEChkV6v0Group,
            tmnxVRtrIfIpcpV6v0Group,
            tmnxVRtrIfCpmProtectGroup,
            tmnxDscpAppV6v0Group,
            tmnxVRtrIfDHCPRelayV9v0Group,
            tmnxVRtrIfDHCPRelayV11v0Group,
            tmnxVRtrV6v1Group,
            tmnxVRtrInetAllCidrRouteV7v0Group,
            tmnxVRtrInetStaticRouteV7v0Group,
            tmnxVRtruRPFV7v0Group,
            tmnxVRtrV9v0Group,
            tmnxVRtrPolicyGroup,
            tmnxVRtrNetDomainGroup,
            tmnxVRtrTunIntV8v0Group,
            tmnxVRtrFibStatsV8v0Group,
            tmnxVRtrMvpnPmsiV8v0Group,
            tmnxVRtrIfDHCPRelayV6v1Group,
            tmnxVRtrQPPBV9v0R4Group,
            tmnxVRtrIfDHCP6V9v0Group,
            tmnxVRtrIfDHCP6V10v0Group,
            tmnxVRtrIfDHCP6V11v0Group,
            tmnxVRtrIfDHCP6V12v0Group,
            tmnxVrtrIfDHCP6ProxyDuidGroup,
            tmnxVRtrIfStatsV9v0Group,
            tmnxVRtrIfStatsV11v0Group,
            tmnxVRtrIfIpReasV9v0Group,
            tmnxVRtrMSPwV9v0Group,
            tmnxVRtrNatRedGroup,
            tmnxVRtrMvpnSrcRedV9v0R4Group,
            tmnxVRtrStatV9v0Group,
            tmnxVRtruRPFV10v0Group,
            tmnxVRtrIpPoolGroup,
            tmnxVRtrQosQGrplV10v0Group,
            tmnxVRtrStatV10v0Group,
            tmnxVRtrStatV11v0Group,
            tmnxVRtrIPv6MgtIfV7v0Group,
            tmnxMGVRtrIfV4v0Group,
            tmnxVRtrFlowSpecV11v0Group,
            tmnxVRtrGrtLocalMgmtV10v0Group,
            tmnxVRtrMcastV11v0Group,
            tmnxVrtrIfDCpuProtV11v0Group,
            tmnxVrtrDcpNotifyObjsV11v0Group,
            tmnxVrtrIfDcpNotifyV11v0Group,
            tmnxVRtrIfMacStatsV11v0Group,
            tmnxVRtrIpv6RtrAdvertV11v0Group,
            tmnxVRtrBfdV11v0Group,
            tmnxVRtrV12v0Group,
            tmnxVRtrRAV12v0Group,
            tmnxVRtrExportBgpVpnV11v0Group,
            tmnxVRtrGenerateICMPV12v0Group,
            tmnxVRtrIfSendV12v0Group,
            tmnxvRtrIfAttributeGroup,
            tmnxVRtrCreation12v0Group,
            tmnxVRtrIPsecStatGroup,
            tmnxVRtrVirtualCPE12v0Group,
            tmnxVRtrBgpEvpn12v0Group,
            tmnxVRtrLagHashLoadBal12v0Group,
            tmnxVRtrPlcyAcctTempl12v0Group,
            tmnxVRtrLagEgrLoadBal12v0Group,
            tmnxVRtrVccvBfd12v0Group,
            tmnxVRtrIcmpTunnelingGroup,
            tmnxVRtrAggrRouteV12v0Group,
            tmnxVRtrConfExtV12v0Group,
            tmnxVRtrStickyHashEcmp12v0Group,
            tmnxVRtrV14v0Group,
            tmnxVRtrNotifyObjsNHRvplsArpGrp,
            tmnxVRtrNotificationNHRvplsArpGr,
            tmnxVRtrMcastSpmsiEnhV13v0Group,
            tmnxVRtrHoldDownTimeV12v0Group,
            tmnxVRtrLoadBalEnhV13v0Group,
            tmnxVRtrInetSRIndirectV13v0Group,
            tmnxVRtrIfExtIfArpRetryTimerGrp,
            tmnxVRtrBgpAutoRDGroup,
            tmnxVRtrTunnelTableStatGroup,
            tmnxVRtrIfDHCPRelayV13v0Group,
            tmnxVRtrLdpIpv613v0Group,
            tmnxVRtrIfLagPerLinkHashGroup,
            tmnxVRtrCidrNextHopOwnInstGroup,
            tmnxVRtrIpV13v0ObsoletedGroup,
            tmnxVRtrV13v0GenObsoletedGroup,
            tmnxVRtrIfArpNbrLimitGroup,
            tmnxVRtrIfExtV13v0Group,
            tmnxVRtrV13v0IfStatsGroup,
            tmnxVRtrIfArpNbrNotifGroup,
            tmnxVRtrIPv6IPsecStatGroup,
            tmnxVRtrUniqueIfIndexGroup,
            tmnxVRtrStaticRoutePrefixGroup,
            tmnxVRtrEntropyLabelGroup,
            tmnxVRtrLspBfdGroup,
            tmnxVRtrConfFlowspecV14v0Group,
            tmnxVRtrInetSRIndirectV14v0Group,
            tmnxVRtrFibStatsV14v0Group,
            tmnxVRtrIfDHCPRelayV14v0Group,
            tmnxVRtrBgpLblIpRoutes14v0Group,
            tmnxVRtrV6TunnelTableStatGroup,
            tmnxVRtrSrTeV14v0Group,
            tmnxVRtrIfExtV14v0Group,
            tmnxVRtrLoopbackNotifGroup,
            tmnxVRtrV14v0NotifyObjsGroup,
            tmnxVRtrIcmpV4StatsV14v0Group,
            tmnxVRtrIcmpV4ParamV14v0Group,
            tmnxVRtrFpeV14v0Group,
            tmnxVRtrV15v0Group,
            tmnxVrtrDDosDCpuProtPolicyGrp,
            tmnxVRtrUdpTunnelGroup,
            tmnxVRtrIpV15v0Group,
            tmnxVRtrQinQNetworkIntfGroup,
            tmnxVRtrIfExtV15v0ObjectGroup,
            tmnxVRtrClassFwdingV15v0Group,
            tmnxVRtrIfExtHostRteV20v0Group,
            tmnxVRtrIfStatsV16v0Group,
            tmnxVRtrIfNgeStatsGroup,
            tmnxVRtrAdminTagsV16v0Group,
            tmnxVRtrLargeCommValV16v0Group,
            tmnxVRtrIfStatsDBCastV16v0Group,
            tmnxVRtrIfV16v0Group,
            tmnxVRtrLocalPrefV16v0Group,
            tmnxVRtrIpV16v0Group,
            tmnxVRtrLoadBalWeightV16v0Group,
            tmnxVRtrInetExtTunnelV16v0Group,
            tmnxVRtrGrtLeakImpPolV16v0Group,
            tmnxVRtrInetTunnStatV16v0Group,
            tmnxVRtrGlobalV16v0Group,
            tmnxVRtrInetRouteV16v0Group,
            tmnxVRtrSrTnlStatV16v0Group,
            tmnxVRtrBierV16v0Group,
            tmnxVRtrDhcpClientGroup,
            tmnxVRtrRibApiV16v0Group,
            tmnxVRtrRibTelemetryV16v0Group,
            tmnxVRtrMplsFwdPlcyV16v0Group,
            tmnxVRtrIcmpV4StatsV19v0Group,
            tmnxVRtrLeakExportLimNotifGroup,
            tmnxVRtrInetSRIndirectV16v0Group,
            tmnxVRtrDhcpRoutesV19v0Group,
            tmnxVRtrV19v0Group,
            tmnxVRtrIfV19v0Group,
            tmnxVRtrNotificationV19v0Group,
            vRtrIfEgressQueueV19v0Group,
            tmnxVRtrIfQosV19v0Group,
            vRtrIfIngressPolicerV19v0Group,
            vRtrMplsTunnelModeV19v0Group,
            tmnxVRtrDiscardCV19v0Group,
            vRtrMplsTunnelModeV19v0Group,
            tmnxVRtrConfFlowspecV19v0Group,
            tmnxVRtrIfHostRouteGroup,
            tmnxVRtrTunTerminationV19v0Group,
            tmnxVRtrIfPhysStatsV19v0Group,
            tmnxVRtrSrTnlStatV19v10Group,
            vRtrIfEgressQueueV19v01Group,
            tmnxVRtrSrTeV6Group,
            tmnxVRtrIfNdHostRouteGroup,
            tmnxVRtrDnsV20v0Group,
            tmnxVRtrHelperRedirectPkts,
            tmnxVRtrIPEHV20v0Group,
            tmnxVRtrIfExtParmsV20v0Group,
            tmnxVRtrAggtIPPrefixV20v0Group,
            tmnxvRtrInetAggrPolicyV20Group,
            tmnxFlexAlgoV20v0Group,
            tmnxVRtrBgpEpe20v0Group,
            tmnxVrtrSRPolicyV20v0Group,
            tmnxVRtrInetSRIndirectV20v0Group,
            tmnxVRtrIPV20v0Group,
            tmnxVRtrV20v0Group,
            tmnxVRtrBgpEvpnV20v0Group,
            tmnxVRtrLspBfdV20v0Group,
            tmnxVRtrIcmpRedirectV20v0Group,
            vRtrIfEthLoopbackV20v0Group,
            tmnxVRtrBgpLabelIpv620v0Group,
            vRtrIfEthLoopbackNotifGroup,
            tmnxVRtrNotificationV20v0Group,
            tmnxVRtrHelperMplsStatsPktsGroup,
            tmnxVRtrPlcyAcctQPPB20v0Group
        }
    ::= { tmnxVRtrCompliances 27 }

tmnxVRtr7xx0V21v0Compliance      MODULE-COMPLIANCE
    STATUS      current
    DESCRIPTION
        "The compliance statement for management of virtual router instances on
         Nokia SROS series systems release R21."
    MODULE
        MANDATORY-GROUPS {
            tmnxVRtrStaticRtBackupNHGroup,
            vRtrBgpIpVpnMplsGroup,
            tmnxVRtrMtrace2V21Group,
            tmnxVRtrBgpEvpnV21v0Grp,
            tmnxVRtrV21v0Group,
            tmnxVRtrSrV6Isis21v0Group,
            tmnxVRtrBgpSrv6V21v0Group,
            tmnxVRtrFlexAlgoDelayV21v0Group,
            tmnxVRtrFlexAlgoDlyDynV21v0Group,
            tmnxVRtrSrV621v0Group,
            tmnxVRtrFibStatObj21Group,
            tmnxVRtrNotificationObj21Group,
            tmnxVRtrDPathAttrObj21Group,
            tmnxVRtrIfHQosOnLagV21v0Group,
            tmnxVRtrNotifyObjsV21v0Group,
            tmnxVRtrNotificationV21v0Group,
            tmnxVRtrV21Group,
            tmnxVRtrBgpIpVpnV21Group
        }
    ::= { tmnxVRtrCompliances 28 }

tmnxVRtr7xx0V22v0Compliance      MODULE-COMPLIANCE
    STATUS      current
    DESCRIPTION
        "The compliance statement for management of virtual router instances on
         Nokia SROS series systems release R22."
    MODULE
        MANDATORY-GROUPS {
            tmnxVRtrDynEgLblLmtObj22Group,
            tmnxVRtrIfV22v0Group,
            tmnxVRtrIfExtParmsV22v0Group,
            tmnxVRtrBgpEvpnEviGroup,
            tmnxVRtrIfDcpFpCountV22v0Group,
            vRtrSrV6PolicyGroup,
            vRtrBgpEvpnSrv6EviGroup,
            vRtrBgpEvpnUneqalEcmpV22v0Group,
            tmnxVRtrIfQosV22v0Group,
            tmnxvRtrEsaVideoRoutesGroup,
            tmnxVRtrNdRaRoutesGroup
        }
    ::= { tmnxVRtrCompliances 29 }

tmnxVRtr7xx0V23v0Compliance      MODULE-COMPLIANCE
    STATUS      current
    DESCRIPTION
        "The incremental compliance statement for management of virtual router
         instances on Nokia SROS series systems release R23."
    MODULE
        MANDATORY-GROUPS {
            tmnxVRtrNotifyObjsV23v0Group,
            tmnxVRtrNotificationV23v0Group,
            tmnxVRtrSubDhcp4V23v0Group,
            tmnxVRtrV23Group,
            tmnxVRtrBgpIpVpnAttrSetGroup,
            tmnxVrtrBgpSrv6UqlEcmpV23v0Group,
            tmnxVRtrSrMplsTTLPropagateGroup,
            tmnxVRtrBgpExpInactiveAllGroup,
            tmnxVRtrStaticRtVprnCondRtGroup,
            tmnxVRtrBgpNhResGroup,
            tmnxVRtrEsmBcastGroup,
            tmnxVRtrUpaRouteGroup
        }
    ::= { tmnxVRtrCompliances 30 }

tmnxVRtr7xx0V24v0Compliance      MODULE-COMPLIANCE
    STATUS      current
    DESCRIPTION
        "The incremental compliance statement for management of virtual router
         instances on Nokia SROS series systems release R24."
    MODULE
        MANDATORY-GROUPS {
            tmnxVRtrSysMacAddrRangeGroup,
            tmnxVRtrSysCommonMacAddrGroup,
            tmnxVRtrIfQosV24v0Group,
            vRtrVprnVxlanV24Group,
            tmnxVRtrMvpnPmsiV24v0Group,
            tmnxVRtrOamLagMeasV24v0Group,
            tmnxVRtrIPV24v0Group,
            tmnxVRtrMvpnP2mp24v0Group,
            vRtrIfIpTunnelV24v0Group,
            vRtrStaticRtLeakDestGroup,
            vRtrEvpnIflHostRouteGroup,
            tmnxVRtrNotificationV24v0Group
        }
    ::= { tmnxVRtrCompliances 31 }

tmnxVRtr7xx0V25v0Compliance      MODULE-COMPLIANCE
    STATUS      current
    DESCRIPTION
        "The incremental compliance statement for management of virtual router
         instances on Nokia SROS series systems release R25."
    MODULE
        MANDATORY-GROUPS {
            tmnxVRtrMvpnP2mp25v0Group,
            tmnxVRtrRedIfOverIpv6Group,
            tmnxVRtrBgpEvpnGwIpV25v0Group,
            tmnxVRtrIfNatGroup,
            tmnxVRtrMvpnGroup,
            tmnxVRtrIPV25v0Group,
            tmnxVRtrBgpEvpnAnySecGroup,
            tmnxVRtrBgpIpVpnAnySecGroup,
            tmnxVRtrIfDHCPRelayFRGroup,
            tmnxVRtrQosSinkExcessBWV25v0Grp
        }
    ::= { tmnxVRtrCompliances 32 }

tmnxVRtrGroups                   OBJECT IDENTIFIER ::= { tmnxVRtrConformance 2 }

tmnxVRtrGlobalR2r1Group          OBJECT-GROUP
    OBJECTS     {
        vRtrNextVRtrID,
        vRtrConfiguredVRtrs,
        vRtrActiveVRtrs,
        vRtrRouteThresholdSoakTime,
        vRtrMaxARPEntries
    }
    STATUS      obsolete
    DESCRIPTION
        "The group of objects supporting management of general capabilities for
         transport and virtual routers on version 2.1 Nokia SROS series
         systems."
    ::= { tmnxVRtrGroups 10 }

tmnxVRtrIfSubscrAuthV3v0Group    OBJECT-GROUP
    OBJECTS     {
        vRtrIfDHCPAuthPolicy,
        vRtrIfDHCPRelayAuthPktsDiscarded,
        vRtrIfDHCPRelayAuthPktsSuccess
    }
    STATUS      current
    DESCRIPTION
        "The  group  of  objects  supporting management of DHCP
         authentication  on  version  3.0 Nokia SROS series
         systems."
    ::= { tmnxVRtrGroups 11 }

tmnxVRtrV4v0Group                OBJECT-GROUP
    OBJECTS     {
        vRtrRowStatus,
        vRtrAdminState,
        vRtrName,
        vRtrMaxNumRoutes,
        vRtrBgpStatus,
        vRtrMplsStatus,
        vRtrOspfStatus,
        vRtrRipStatus,
        vRtrRsvpStatus,
        vRtrEcmpMaxRoutes,
        vRtrAS,
        vRtrNewIfIndex,
        vRtrLdpStatus,
        vRtrIsIsStatus,
        vRtrRouterId,
        vRtrTriggeredPolicy,
        vRtrConfederationAS,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrOspfv3Status,
        vRtrImportPolicy1,
        vRtrImportPolicy2,
        vRtrImportPolicy3,
        vRtrImportPolicy4,
        vRtrImportPolicy5,
        vRtrExportPolicy1,
        vRtrExportPolicy2,
        vRtrExportPolicy3,
        vRtrExportPolicy4,
        vRtrExportPolicy5,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes
    }
    STATUS      obsolete
    DESCRIPTION
        "The group of objects supporting management of transport and virtual
         routers on version 4.0 Nokia SROS series systems."
    ::= { tmnxVRtrGroups 14 }

tmnxVRtrIfV4v0Group              OBJECT-GROUP
    OBJECTS     {
        vRtrIfTotalNumber,
        vRtrIfRowStatus,
        vRtrIfType,
        vRtrIfName,
        vRtrIfPortID,
        vRtrIfChannelID,
        vRtrIfEncapValue,
        vRtrIfAdminState,
        vRtrIfOperState,
        vRtrIfAlias,
        vRtrIfPhysicalAddress,
        vRtrIfArpTimeout,
        vRtrIfIcmpMaskReply,
        vRtrIfIcmpRedirects,
        vRtrIfIcmpNumRedirects,
        vRtrIfIcmpRedirectsTime,
        vRtrIfIcmpUnreachables,
        vRtrIfIcmpNumUnreachables,
        vRtrIfIcmpUnreachablesTime,
        vRtrIfIcmpTtlExpired,
        vRtrIfIcmpNumTtlExpired,
        vRtrIfIcmpTtlExpiredTime,
        vRtrIfNtpBroadcast,
        vRtrIfUnnumbered,
        vRtrIfMtu,
        vRtrIfQosPolicyId,
        vRtrIfIngressFilterId,
        vRtrIfEgressFilterId,
        vRtrIfDirectedBroadcast,
        vRtrIfMplsStatus,
        vRtrIfUnnumberedIf,
        vRtrIfCflowd,
        vRtrIfVPNClass,
        vRtrIfDescription,
        vRtrIfProtocol,
        vRtrIfTosMarkingTrusted,
        vRtrIfServiceId,
        vRtrIfArpPopulate,
        vRtrIfProxyArp,
        vRtrIfProxyArpLocal,
        vRtrIfProxyArpPolicy1,
        vRtrIfProxyArpPolicy2,
        vRtrIfProxyArpPolicy3,
        vRtrIfProxyArpPolicy4,
        vRtrIfProxyArpPolicy5,
        vRtrIfNameIndex,
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPLeasePopulate,
        vRtrIfDHCPOperLeasePopulate,
        vRtrIfDHCPGiAddressType,
        vRtrIfDHCPGiAddress,
        vRtrIfDHCPGiAddressAsSrc,
        vRtrIfDHCPMatchOption82
    }
    STATUS      obsolete
    DESCRIPTION
        "The group of objects supporting management of virtual interfaces on
         version 4.0 Nokia SROS series systems."
    ::= { tmnxVRtrGroups 15 }

tmnxVRtrIpV4v0Group              OBJECT-GROUP
    OBJECTS     {
        vRiaRowStatus,
        vRiaIpAddress,
        vRiaNetMask,
        vRiaBcastAddrFormat,
        vRiaReasmMaxSize,
        vRiaIgpInhibit,
        vRiaInetAddressType,
        vRiaInetAddress,
        vRiaInetPrefixLen,
        vRiaInetAddrState,
        vRiaInetEui64,
        vRiaInetOperAddress,
        vRtrIpCidrRouteLastEnabledTime,
        vRtrIpCidrRoutePreference,
        vRtrIpCidrRouteMetric,
        vRtrStaticRouteDest,
        vRtrStaticRouteMask,
        vRtrStaticRouteIndex,
        vRtrStaticRouteNumber,
        vRtrStaticRouteRowStatus,
        vRtrStaticRouteLastEnabledTime,
        vRtrStaticRouteStatus,
        vRtrStaticRouteStaticType,
        vRtrStaticRoutePreference,
        vRtrStaticRouteMetric,
        vRtrStaticRouteEgressIfIndex,
        vRtrStaticRouteNextHop,
        vRtrStaticRouteNextHopUnnumberedIf,
        vRtrStaticRouteAdminState,
        vRtrStaticRouteIgpShortcut,
        vRtrStaticRouteDisallowIgp,
        vRtrStaticRouteTag,
        vRtrStaticRouteIndexDest,
        vRtrStaticRouteIndexMask,
        vRtrStaticRouteAvailableIndex,
        vRtrInetStaticRouteRowStatus,
        vRtrInetStaticRouteLastEnabledTime,
        vRtrInetStaticRouteStatus,
        vRtrInetStaticRouteStaticType,
        vRtrInetStaticRoutePreference,
        vRtrInetStaticRouteMetric,
        vRtrInetStaticRouteEgressIfIndex,
        vRtrInetStaticRouteNextHopType,
        vRtrInetStaticRouteNextHop,
        vRtrInetStaticRouteNextHopIf,
        vRtrInetStaticRouteAdminState,
        vRtrInetStaticRouteIgpShortcut,
        vRtrInetStaticRouteDisallowIgp,
        vRtrInetStaticRouteTag,
        vRtrInetStaticRouteEnableBfd,
        vRtrInetStaticRouteAvailIndex,
        vRtrSvcIpRangeAddress,
        vRtrSvcIpRangeMask,
        vRtrSvcIpRangeRowStatus,
        vRtrSvcIpRangeExclusive,
        vRtrIpNetToMediaTimer,
        vRtrIpNetToMediaOperState,
        vRtrInstanceAggregationTableLastChanged,
        vRtrAggregationRowStatus,
        vRtrAggregationLastChanged,
        vRtrAggregationSummaryOnly,
        vRtrAggregationASSet,
        vRtrAggregationAggregatorAS,
        vRtrAggregationAggregatorIPAddr,
        vRtrAggregationOperState,
        vRtrTunnelMetric,
        vRtrTunnelAge,
        vRtrAdvPrefixOnLinkFlag,
        vRtrAdvPrefixAutonomousFlag,
        vRtrAdvPrefixPreferredLifetime,
        vRtrAdvPrefixValidLifetime,
        vRtrAdvPrefixRowStatus,
        vRtrInetInstAggrTblLastChged,
        vRtrInetAggrRowStatus,
        vRtrInetAggrLastChanged,
        vRtrInetAggrSummaryOnly,
        vRtrInetAggrASSet,
        vRtrInetAggrAggregatorAS,
        vRtrInetAggrAggregatorIPAddr,
        vRtrInetAggrOperState,
        vRtrInetSvcIpRangeRowStatus,
        vRtrInetSvcIpRangeExclusive,
        vRtrIpNetToPhysicalTimer,
        vRtrIpNetToPhysicalOperState,
        vRtrIpNetToPhysicalIsRouter,
        vRtrIpNetToPhysicalMTU,
        vRtrIpNetToPhysicalPort,
        vRtrIpNetToPhysicalEncap,
        vRtrInetCidrRouteLastEnabledTime,
        vRtrInetCidrRoutePreference,
        vRtrInetCidrRouteMetric
    }
    STATUS      obsolete
    DESCRIPTION
        "The group of objects supporting management of IP capabilities for
         transport and virtual routers on version 4.0 Nokia SROS series
         systems."
    ::= { tmnxVRtrGroups 16 }

tmnxVRtrObsoletedObjectsV4v0Group OBJECT-GROUP
    OBJECTS     {
        vRtrIfDHCPLseStateChAddr,
        vRtrIfDHCPLseStateRemainLseTime,
        vRtrIfDHCPLseStateOption82,
        vRtrIfDHCPLseStatePersistKey,
        vRtrDHCPClientLease,
        vRtrDhcpLseStateOldCiAddr,
        vRtrDhcpLseStateOldChAddr,
        vRtrDhcpLseStateNewCiAddr,
        vRtrDhcpLseStateNewChAddr,
        vRtrDhcpRestoreLseStateCiAddr,
        vRtrDhcpRestoreLseStateVRtrId,
        vRtrDhcpRestoreLseStateIfIndex,
        vRtrDhcpRestoreLseStateProblem,
        vRtrDhcpLseStatePopulateError,
        vRtrIfDHCPRelayInfoOption,
        vRtrIfDHCPAutoFilter,
        vRtrIfDHCPSnooping,
        vRtrIfDHCPAutoFilterId,
        vRtrIfDHCPOperAutoFilter,
        vRtrAutoFilterDHCPClientAddress,
        vRtrAutoFilterDHCPClientLease
    }
    STATUS      current
    DESCRIPTION
        "The group of objects no longer supported in version 4.0
         of Nokia SROS  series systems."
    ::= { tmnxVRtrGroups 17 }

tmnxVRtrBfdV4v0Group             OBJECT-GROUP
    OBJECTS     {
        vRtrIfBfdAdminState,
        vRtrIfBfdTransmitInterval,
        vRtrIfBfdReceiveInterval,
        vRtrIfBfdMultiplier,
        vRtrIfBfdSessionOperState,
        vRtrIfBfdSessionState,
        vRtrIfBfdSessionOperFlags,
        vRtrIfBfdSessionMesgRecv,
        vRtrIfBfdSessionMesgSent,
        vRtrIfBfdSessionLastDownTime,
        vRtrIfBfdSessionLastUpTime,
        vRtrIfBfdSessionUpCount,
        vRtrIfBfdSessionDownCount,
        vRtrIfBfdSessionLclDisc,
        vRtrIfBfdSessionRemDisc,
        vRtrIfBfdSessionProtocols,
        vRtrIfBfdSessionTxInterval,
        vRtrIfBfdSessionRxInterval
    }
    STATUS      obsolete
    DESCRIPTION
        "The group of objects supporting Bi-directional Forwarding Detection on
         version 4.0 Nokia 7x50 series systems."
    ::= { tmnxVRtrGroups 18 }

tmnxVRtrNotificationV4v0Group    NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported
    }
    STATUS      obsolete
    DESCRIPTION
        "The group of notifications supporting the transport and virtual router
         capabilities on version 4.0 Nokia SROS series systems."
    ::= { tmnxVRtrGroups 19 }

tmnxVRtrIPv6IfV4v0Group          OBJECT-GROUP
    OBJECTS     {
        vRtrIfIPv6ConfigAllowed,
        vRtrIfIPv6OperState,
        vRtrIfIPv6IngressFilterId,
        vRtrIfIPv6EgressFilterId,
        vRtrIfIcmpV6Redirects,
        vRtrIfIcmpV6NumRedirects,
        vRtrIfIcmpV6RedirectsTime,
        vRtrIfIcmpV6Unreachables,
        vRtrIfIcmpV6NumUnreachables,
        vRtrIfIcmpV6UnreachablesTime,
        vRtrIfIcmpV6TimeExceeded,
        vRtrIfIcmpV6NumTimeExceeded,
        vRtrIfIcmpV6TimeExceededTime,
        vRtrIfIcmpV6PktTooBig,
        vRtrIfIcmpV6NumPktTooBig,
        vRtrIfIcmpV6PktTooBigTime,
        vRtrIfIcmpV6ParamProblem,
        vRtrIfIcmpV6NumParamProblem,
        vRtrIfIcmpV6ParamProblemTime,
        vRtrIfLinkLocalAddressType,
        vRtrIfLinkLocalAddressState,
        vRtrIfLinkLocalAddress,
        vRtrIfIcmp6InMsgs,
        vRtrIfIcmp6InErrors,
        vRtrIfIcmp6InDestUnreachs,
        vRtrIfIcmp6InAdminProhibs,
        vRtrIfIcmp6InTimeExcds,
        vRtrIfIcmp6InParmProblems,
        vRtrIfIcmp6InPktTooBigs,
        vRtrIfIcmp6InEchos,
        vRtrIfIcmp6InEchoReplies,
        vRtrIfIcmp6InRtrSolicits,
        vRtrIfIcmp6InRtrAdvertisements,
        vRtrIfIcmp6InNbrSolicits,
        vRtrIfIcmp6InNbrAdvertisements,
        vRtrIfIcmp6InRedirects,
        vRtrIfIcmp6InGrpMembQueries,
        vRtrIfIcmp6InGrpMembResponses,
        vRtrIfIcmp6InGrpMembReductions,
        vRtrIfIcmp6OutMsgs,
        vRtrIfIcmp6OutErrors,
        vRtrIfIcmp6OutDestUnreachs,
        vRtrIfIcmp6OutAdminProhibs,
        vRtrIfIcmp6OutTimeExcds,
        vRtrIfIcmp6OutParmProblems,
        vRtrIfIcmp6OutPktTooBigs,
        vRtrIfIcmp6OutEchos,
        vRtrIfIcmp6OutEchoReplies,
        vRtrIfIcmp6OutRtrSolicits,
        vRtrIfIcmp6OutRtrSolicitsTime,
        vRtrIfIcmp6OutRtrAdvertisements,
        vRtrIfIcmp6OutRtrAdvTime,
        vRtrIfIcmp6OutNbrSolicits,
        vRtrIfIcmp6OutNbrSolicitsTime,
        vRtrIfIcmp6OutNbrAdvertisements,
        vRtrIfIcmp6OutNbrAdvTime,
        vRtrIfIcmp6OutRedirects,
        vRtrIfIcmp6OutGrpMembQueries,
        vRtrIfIcmp6OutGrpMembResponses,
        vRtrIfIcmp6OutGrpMembReductions,
        vRtrIfIcmp6OutDiscards,
        vRtrIcmp6InMsgs,
        vRtrIcmp6InErrors,
        vRtrIcmp6InDestUnreachs,
        vRtrIcmp6InAdminProhibs,
        vRtrIcmp6InTimeExcds,
        vRtrIcmp6InParmProblems,
        vRtrIcmp6InPktTooBigs,
        vRtrIcmp6InEchos,
        vRtrIcmp6InEchoReplies,
        vRtrIcmp6InRtrSolicits,
        vRtrIcmp6InRtrAdvertisements,
        vRtrIcmp6InNbrSolicits,
        vRtrIcmp6InNbrAdvertisements,
        vRtrIcmp6InRedirects,
        vRtrIcmp6InGrpMembQueries,
        vRtrIcmp6InGrpMembResponses,
        vRtrIcmp6InGrpMembReductions,
        vRtrIcmp6OutMsgs,
        vRtrIcmp6OutErrors,
        vRtrIcmp6OutDestUnreachs,
        vRtrIcmp6OutAdminProhibs,
        vRtrIcmp6OutTimeExcds,
        vRtrIcmp6OutParmProblems,
        vRtrIcmp6OutPktTooBigs,
        vRtrIcmp6OutEchos,
        vRtrIcmp6OutEchoReplies,
        vRtrIcmp6OutRtrSolicits,
        vRtrIcmp6OutRtrAdvertisements,
        vRtrIcmp6OutNbrSolicits,
        vRtrIcmp6OutNbrAdvertisements,
        vRtrIcmp6OutRedirects,
        vRtrIcmp6OutGrpMembQueries,
        vRtrIcmp6OutGrpMembResponses,
        vRtrIcmp6OutGrpMembReductions,
        vRtrIcmp6OutDiscards
    }
    STATUS      current
    DESCRIPTION
        "The group of objects supporting management of IPv6 virtual interfaces
         on version 4.0 Nokia SROS series systems."
    ::= { tmnxVRtrGroups 20 }

tmnxVRtrIPv6V4v0Group            OBJECT-GROUP
    OBJECTS     {
        vRtrV6DirectRoutes,
        vRtrV6DirectActiveRoutes,
        vRtrV6StaticRoutes,
        vRtrV6StaticActiveRoutes,
        vRtrV6OSPFRoutes,
        vRtrV6OSPFActiveRoutes,
        vRtrV6BGPRoutes,
        vRtrV6BGPActiveRoutes,
        vRtrV6ISISRoutes,
        vRtrV6ISISActiveRoutes,
        vRtrV6RIPRoutes,
        vRtrV6RIPActiveRoutes,
        vRtrV6AggregateRoutes,
        vRtrV6AggregateActiveRoutes,
        vRtrV6StatConfiguredIfs,
        vRtrV6StatActiveIfs,
        vRtrV6StatIllegalLabels,
        vRtrV6StatCurrNumRoutes,
        vRtrV6StatBGPVpnRoutes,
        vRtrV6StatBGPVpnActiveRoutes,
        vRtrV6StatTotalLdpTunnels,
        vRtrV6StatTotalSdpTunnels,
        vRtrV6StatActiveLdpTunnels,
        vRtrV6StatActiveSdpTunnels,
        vRtrV6MulticastRoutes,
        vRtrV6StatActiveNbrEntries,
        vRtrV6StatTotalNbrEntries
    }
    STATUS      current
    DESCRIPTION
        "The group of objects supporting management of IPv6 transport and
         virtual routers on version 4.0 Nokia SROS series systems."
    ::= { tmnxVRtrGroups 21 }

tmnxVRtrIPv6IpV4v0Group          OBJECT-GROUP
    OBJECTS     {
        vRtrAdvPrefixOnLinkFlag,
        vRtrAdvPrefixAutonomousFlag,
        vRtrAdvPrefixPreferredLifetime,
        vRtrAdvPrefixValidLifetime,
        vRtrAdvPrefixRowStatus
    }
    STATUS      obsolete
    DESCRIPTION
        "The group of objects supporting management of IPv6 IP capabilities for
         transport and virtual routers on version 4.0 Nokia SROS series
         systems."
    ::= { tmnxVRtrGroups 22 }

tmnxVRtrObsoleteNotificationGroup NOTIFICATION-GROUP
    NOTIFICATIONS {
        tmnxVRtrDHCPAFEntriesExceeded,
        tmnxVRtrDHCPLseStsExceeded,
        tmnxVRtrDHCPLeaseStateOverride,
        tmnxVRtrDHCPLseStRestoreProblem,
        tmnxVRtrDHCPLseStatePopulateErr
    }
    STATUS      current
    DESCRIPTION
        "The group of obsolete notifications for the transport and virtual
         router capabilities on Nokia SROS series systems."
    ::= { tmnxVRtrGroups 23 }

tmnxVRtrIPv6IpV5v0Group          OBJECT-GROUP
    OBJECTS     {
        vRtrAdvPrefixOnLinkFlag,
        vRtrAdvPrefixAutonomousFlag,
        vRtrAdvPrefixPreferredLifetime,
        vRtrAdvPrefixValidLifetime,
        vRtrAdvPrefixRowStatus,
        vRtrIfDHCP6TableLastChanged,
        vRtrIfDHCP6LastChanged,
        vRtrIfDHCP6AdminState,
        vRtrIfDHCP6OperState,
        vRtrIfDHCP6Description,
        vRtrIfDHCP6RelayServer1,
        vRtrIfDHCP6RelayServer2,
        vRtrIfDHCP6RelayServer3,
        vRtrIfDHCP6RelayServer4,
        vRtrIfDHCP6RelayServer5,
        vRtrIfDHCP6RelayServer6,
        vRtrIfDHCP6RelayServer7,
        vRtrIfDHCP6RelayServer8,
        vRtrIfDHCP6RelayItfIdOption,
        vRtrIfDHCP6LeasePopulate,
        vRtrIfDHCP6CurrLeasePopulate,
        vRtrIfDHCP6SourceAddress,
        vRtrIfDHCP6EnableNgbrResolution,
        vRtrIfDHCP6RemoteIdOption,
        vRtrIfDHCP6PfxdAdminState,
        vRtrIfDHCP6ServerMaxLeaseStates,
        vRtrIfDHCP6CurrServerLeaseStates,
        vRtrIfDHCP6ItfIdString,
        vRtrIfProxyNDLocal,
        vRtrIfProxyNDPolicy1,
        vRtrIfProxyNDPolicy2,
        vRtrIfProxyNDPolicy3,
        vRtrIfProxyNDPolicy4,
        vRtrIfProxyNDPolicy5,
        vRtrIfDHCP6PfxdRowStatus,
        vRtrIfDHCP6PfxdLastChanged,
        vRtrIfDHCP6PfxdDUID,
        vRtrIfDHCP6PfxdIAID,
        vRtrIfDHCP6PfxdPrefLifetime,
        vRtrIfDHCP6PfxdValidLifetime,
        vRtrIfDHCP6PfxDelegationLstChgd
    }
    STATUS      current
    DESCRIPTION
        "The group of objects supporting management of IPv6 IP capabilities for
         transport and virtual routers on version 5.0 Nokia SROS series
         systems."
    ::= { tmnxVRtrGroups 24 }

tmnxVRtrIfV5v0Group              OBJECT-GROUP
    OBJECTS     {
        vRtrIfTotalNumber,
        vRtrIfRowStatus,
        vRtrIfType,
        vRtrIfName,
        vRtrIfPortID,
        vRtrIfEncapValue,
        vRtrIfAdminState,
        vRtrIfOperState,
        vRtrIfAlias,
        vRtrIfPhysicalAddress,
        vRtrIfArpTimeout,
        vRtrIfIcmpMaskReply,
        vRtrIfIcmpRedirects,
        vRtrIfIcmpNumRedirects,
        vRtrIfIcmpRedirectsTime,
        vRtrIfIcmpUnreachables,
        vRtrIfIcmpNumUnreachables,
        vRtrIfIcmpUnreachablesTime,
        vRtrIfIcmpTtlExpired,
        vRtrIfIcmpNumTtlExpired,
        vRtrIfIcmpTtlExpiredTime,
        vRtrIfNtpBroadcast,
        vRtrIfUnnumbered,
        vRtrIfMtu,
        vRtrIfQosPolicyId,
        vRtrIfIngressFilterId,
        vRtrIfEgressFilterId,
        vRtrIfDirectedBroadcast,
        vRtrIfMplsStatus,
        vRtrIfUnnumberedIf,
        vRtrIfCflowd,
        vRtrIfVPNClass,
        vRtrIfDescription,
        vRtrIfProtocol,
        vRtrIfTosMarkingTrusted,
        vRtrIfServiceId,
        vRtrIfArpPopulate,
        vRtrIfLastOperStateChange,
        vRtrIfOperMtu,
        vRtrIfGlobalIndex,
        vRtrIfProxyArp,
        vRtrIfProxyArpLocal,
        vRtrIfProxyArpPolicy1,
        vRtrIfProxyArpPolicy2,
        vRtrIfProxyArpPolicy3,
        vRtrIfProxyArpPolicy4,
        vRtrIfProxyArpPolicy5,
        vRtrIfNameIndex,
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfGlobalIndexvRtrID,
        vRtrIfGlobalIndexvRtrIfIndex,
        vRtrIfDelaySeconds,
        vRtrIfDelayUpTimer,
        vRtrIfInitDelayEnable
    }
    STATUS      obsolete
    DESCRIPTION
        "The group of objects supporting management of virtual interfaces on
         version 5.0 Nokia SROS series systems."
    ::= { tmnxVRtrGroups 25 }

tmnxVRtrIpV5v0Group              OBJECT-GROUP
    OBJECTS     {
        vRiaRowStatus,
        vRiaIpAddress,
        vRiaNetMask,
        vRiaBcastAddrFormat,
        vRiaReasmMaxSize,
        vRiaIgpInhibit,
        vRiaInetAddressType,
        vRiaInetAddress,
        vRiaInetPrefixLen,
        vRiaInetAddrState,
        vRiaInetEui64,
        vRiaInetOperAddress,
        vRiaInetGwAddressType,
        vRiaInetGwAddress,
        vRiaInetRemoteIpType,
        vRiaInetRemoteIp,
        vRtrIpCidrRouteLastEnabledTime,
        vRtrIpCidrRoutePreference,
        vRtrIpCidrRouteMetric,
        vRtrStaticRouteDest,
        vRtrStaticRouteMask,
        vRtrStaticRouteIndex,
        vRtrStaticRouteNumber,
        vRtrStaticRouteRowStatus,
        vRtrStaticRouteLastEnabledTime,
        vRtrStaticRouteStatus,
        vRtrStaticRouteStaticType,
        vRtrStaticRoutePreference,
        vRtrStaticRouteMetric,
        vRtrStaticRouteEgressIfIndex,
        vRtrStaticRouteNextHop,
        vRtrStaticRouteNextHopUnnumberedIf,
        vRtrStaticRouteAdminState,
        vRtrStaticRouteIgpShortcut,
        vRtrStaticRouteDisallowIgp,
        vRtrStaticRouteTag,
        vRtrStaticRouteIndexDest,
        vRtrStaticRouteIndexMask,
        vRtrStaticRouteAvailableIndex,
        vRtrInetStaticRouteRowStatus,
        vRtrInetStaticRouteLastEnabledTime,
        vRtrInetStaticRouteStatus,
        vRtrInetStaticRouteStaticType,
        vRtrInetStaticRoutePreference,
        vRtrInetStaticRouteMetric,
        vRtrInetStaticRouteEgressIfIndex,
        vRtrInetStaticRouteNextHopType,
        vRtrInetStaticRouteNextHop,
        vRtrInetStaticRouteNextHopIf,
        vRtrInetStaticRouteAdminState,
        vRtrInetStaticRouteIgpShortcut,
        vRtrInetStaticRouteDisallowIgp,
        vRtrInetStaticRouteTag,
        vRtrInetStaticRouteEnableBfd,
        vRtrInetStaticRouteAvailIndex,
        vRtrSvcIpRangeAddress,
        vRtrSvcIpRangeMask,
        vRtrSvcIpRangeRowStatus,
        vRtrSvcIpRangeExclusive,
        vRtrIpNetToMediaTimer,
        vRtrIpNetToMediaOperState,
        vRtrInstanceAggregationTableLastChanged,
        vRtrAggregationRowStatus,
        vRtrAggregationLastChanged,
        vRtrAggregationSummaryOnly,
        vRtrAggregationASSet,
        vRtrAggregationAggregatorAS,
        vRtrAggregationAggregatorIPAddr,
        vRtrAggregationOperState,
        vRtrTunnelMetric,
        vRtrTunnelAge,
        vRtrAdvPrefixOnLinkFlag,
        vRtrAdvPrefixAutonomousFlag,
        vRtrAdvPrefixPreferredLifetime,
        vRtrAdvPrefixValidLifetime,
        vRtrAdvPrefixRowStatus,
        vRtrInetInstAggrTblLastChged,
        vRtrInetAggrRowStatus,
        vRtrInetAggrLastChanged,
        vRtrInetAggrSummaryOnly,
        vRtrInetAggrASSet,
        vRtrInetAggrAggregatorAS,
        vRtrInetAggrAggregatorIPAddr,
        vRtrInetAggrOperState,
        vRtrInetSvcIpRangeRowStatus,
        vRtrInetSvcIpRangeExclusive,
        vRtrIpNetToPhysicalTimer,
        vRtrIpNetToPhysicalOperState,
        vRtrIpNetToPhysicalIsRouter,
        vRtrIpNetToPhysicalMTU,
        vRtrIpNetToPhysicalPort,
        vRtrIpNetToPhysicalEncap,
        vRtrInetCidrRouteLastEnabledTime,
        vRtrInetCidrRoutePreference,
        vRtrInetCidrRouteMetric,
        vRtrInetCidrRouteIfVRtrId
    }
    STATUS      obsolete
    DESCRIPTION
        "The group of objects supporting management of IP capabilities for
         transport and virtual routers on version 4.0 Nokia SROS series
         systems."
    ::= { tmnxVRtrGroups 26 }

tmnxVRtrV5v0Group                OBJECT-GROUP
    OBJECTS     {
        vRtrRowStatus,
        vRtrAdminState,
        vRtrName,
        vRtrMaxNumRoutes,
        vRtrBgpStatus,
        vRtrMplsStatus,
        vRtrRipStatus,
        vRtrRsvpStatus,
        vRtrEcmpMaxRoutes,
        vRtrAS,
        vRtrNewIfIndex,
        vRtrLdpStatus,
        vRtrIsIsStatus,
        vRtrRouterId,
        vRtrTriggeredPolicy,
        vRtrConfederationAS,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrImportPolicy1,
        vRtrImportPolicy2,
        vRtrImportPolicy3,
        vRtrImportPolicy4,
        vRtrImportPolicy5,
        vRtrExportPolicy1,
        vRtrExportPolicy2,
        vRtrExportPolicy3,
        vRtrExportPolicy4,
        vRtrExportPolicy5,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped
    }
    STATUS      obsolete
    DESCRIPTION
        "The group of objects supporting management of transport and virtual
         routers on version 5.0 Nokia SROS series systems."
    ::= { tmnxVRtrGroups 27 }

tmnxVRtrNotificationV5v0Group    NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrBfdSessionUp
    }
    STATUS      obsolete
    DESCRIPTION
        "The group of notifications supporting the transport and virtual router
         capabilities on version 5.0 Nokia 7xx0 SR series systems."
    ::= { tmnxVRtrGroups 28 }

tmnxVRtrObsoleteV5v0Group        OBJECT-GROUP
    OBJECTS     {
        vRtrOspfStatus,
        vRtrOspfv3Status,
        vRtrIfChannelID
    }
    STATUS      current
    DESCRIPTION
        "The group of objects in TIMETRA-VRTR-MIB which are obsoleted in Nokia
         SROS 5.0 series systems."
    ::= { tmnxVRtrGroups 29 }

tmnxVRtrNotificationObjV5v0Group OBJECT-GROUP
    OBJECTS     {
        vRtrID,
        vRtrIfIndex,
        vRtrDhcpPacketProblem,
        vRtrBfdSlotNumber,
        vRtrNumberOfBfdSessionsOnSlot,
        vRtrBfdMaxSessionReason,
        vRtrDHCP6ServerNetAddrType,
        vRtrDHCP6ServerNetAddr,
        vRtrDHCP6ClientNetAddrType,
        vRtrDHCP6ClientNetAddr,
        vRtrDHCP6AssignedNetAddrType,
        vRtrDHCP6AssignedNetAddr,
        vRtrDHCP6AssignedPrefixLen,
        vRtrDHCP6OldAssignedNetAddrType,
        vRtrDHCP6OldAssignedNetAddr,
        vRtrDHCP6OldAssignedPrefixLen,
        vRtrDHCP6NewClientId,
        vRtrDHCP6OldClientId,
        vRtrDHCP6LeaseOverrideResult
    }
    STATUS      obsolete
    DESCRIPTION
        "The group of objects supporting management of notification objects on
         Nokia SROS 5.0 series systems."
    ::= { tmnxVRtrGroups 30 }

tmnxVRtrIfDhcpServerGroup        OBJECT-GROUP
    OBJECTS     {
        vRtrIfLocalDhcpServerName
    }
    STATUS      current
    DESCRIPTION
        "The group of objects supporting the DHCP server capabilities on
         version 6.0 Nokia SROS series systems."
    ::= { tmnxVRtrGroups 31 }

tmnxVRtrV6v0Group                OBJECT-GROUP
    OBJECTS     {
        vRtrRowStatus,
        vRtrAdminState,
        vRtrName,
        vRtrMaxNumRoutes,
        vRtrBgpStatus,
        vRtrMplsStatus,
        vRtrRipStatus,
        vRtrRsvpStatus,
        vRtrEcmpMaxRoutes,
        vRtrAS,
        vRtrNewIfIndex,
        vRtrLdpStatus,
        vRtrIsIsStatus,
        vRtrRouterId,
        vRtrTriggeredPolicy,
        vRtrConfederationAS,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrIPv6MaxNumRoutes,
        vRtrIPv6MidRouteThreshold,
        vRtrIPv6HighRouteThreshold,
        vRtrIPv6MaxNumRoutesLogOnly,
        vRtrIPv6IgnoreIcmpRedirect,
        vRtrMcPathMgmtPlcyName,
        vRtrImportPolicy1,
        vRtrImportPolicy2,
        vRtrImportPolicy3,
        vRtrImportPolicy4,
        vRtrImportPolicy5,
        vRtrExportPolicy1,
        vRtrExportPolicy2,
        vRtrExportPolicy3,
        vRtrExportPolicy4,
        vRtrExportPolicy5,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrHostRoutes,
        vRtrHostActiveRoutes,
        vRtrV6HostRoutes,
        vRtrV6HostActiveRoutes,
        vRtrStatLocalARPEntries,
        vRtrStatStaticARPEntries,
        vRtrStatDynamicARPEntries,
        vRtrStatManagedARPEntries,
        vRtrStatInternalARPEntries,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped,
        vRtrInetStaticRouteNHTunnelName,
        vRtrManagedRoutes,
        vRtrManagedActiveRoutes
    }
    STATUS      obsolete
    DESCRIPTION
        "The group of objects supporting management of transport and virtual
         routers on version 6.0 Nokia SROS series systems."
    ::= { tmnxVRtrGroups 32 }

tmnxVRtrStaticRteCPEChkV6v0Group OBJECT-GROUP
    OBJECTS     {
        vRtrInetStaticRouteCpeAddrType,
        vRtrInetStaticRouteCpeAddr,
        vRtrInetStaticRouteCpeInterval,
        vRtrInetStaticRouteCpeDropCnt,
        vRtrInetStaticRouteCpeEnableLog,
        vRtrInetStatRteCpeChkUpTime,
        vRtrInetStatRteCpeChkInPktCnt,
        vRtrInetStatRteCpeChkOutPktCnt,
        vRtrInetStatRteCpeChkUpTrans,
        vRtrInetStatRteCpeChkDownTrans,
        vRtrInetStatRteCpeChkTTL
    }
    STATUS      current
    DESCRIPTION
        "The group of objects supporting the Static Route CPE Check capability
         on version 6.0 Nokia SROS series systems."
    ::= { tmnxVRtrGroups 33 }

tmnxVRtrIfIpcpV6v0Group          OBJECT-GROUP
    OBJECTS     {
        vRtrIfIpcpPeerAddrType,
        vRtrIfIpcpPeerAddr,
        vRtrIfIpcpPriDnsAddrType,
        vRtrIfIpcpPriDnsAddr,
        vRtrIfIpcpSecDnsAddrType,
        vRtrIfIpcpSecDnsAddr
    }
    STATUS      current
    DESCRIPTION
        "The group of objects supporting management of IPCP extensions for
         virtual interfaces on version 6.0 Nokia 7x50 SR series systems"
    ::= { tmnxVRtrGroups 34 }

tmnxVRtrIfCpmProtectGroup        OBJECT-GROUP
    OBJECTS     {
        vRtrIfCpmProtPolicyId,
        vRtrIfCpmProtUncfgdProtoDropCnt
    }
    STATUS      current
    DESCRIPTION
        "The group of objects supporting management of CPM Protection for
         virtual interfaces on Nokia SROS series systems."
    ::= { tmnxVRtrGroups 35 }

tmnxDscpAppV6v0Group             OBJECT-GROUP
    OBJECTS     {
        tmnxDscpAppLastChanged,
        tmnxDscpAppDscpValue,
        tmnxDscpFCLastChanged,
        tmnxDscpFCValue,
        tmnxDscpAppTableLastChanged,
        tmnxDscpFCTableLastChanged,
        tmnxDot1pAppTableLastChanged,
        tmnxDot1pAppLastChanged,
        tmnxDot1pAppValue
    }
    STATUS      current
    DESCRIPTION
        "The group of objects supporting management of DSCP marking for
         self-generated protocol control traffic on Nokia SROS series systems
         release 6.0."
    ::= { tmnxVRtrGroups 36 }

tmnxVRtrIfDHCPRelayGroup         OBJECT-GROUP
    OBJECTS     {
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfDHCPLayer2Header,
        vRtrIfDHCPAntiSpoofMacAddr,
        vRtrIfDHCPClientApplications,
        vRtrIfLdpSyncTimer
    }
    STATUS      obsolete
    DESCRIPTION
        "The group of objects supporting management of DHCP Relay on virtual
         interfaces on version 6.0 Nokia SROS series systems"
    ::= { tmnxVRtrGroups 37 }

tmnxVRtrGlobalV6v0Group          OBJECT-GROUP
    OBJECTS     {
        vRtrNextVRtrID,
        vRtrConfiguredVRtrs,
        vRtrActiveVRtrs,
        vRtrRouteThresholdSoakTime,
        vRtrMaxARPEntries,
        vRtrIPv6RouteThresholdSoakTime
    }
    STATUS      current
    DESCRIPTION
        "The group of objects supporting management of general capabilities for
         transport and virtual routers on version 6.0 Nokia SROS series
         systems."
    ::= { tmnxVRtrGroups 38 }

tmnxVRtrNotificationObjV6v0Group OBJECT-GROUP
    OBJECTS     {
        vRtrID,
        vRtrIfIndex,
        vRtrDhcpPacketProblem,
        vRtrBfdSlotNumber,
        vRtrNumberOfBfdSessionsOnSlot,
        vRtrBfdMaxSessionReason,
        vRtrDHCP6ServerNetAddrType,
        vRtrDHCP6ServerNetAddr,
        vRtrDHCP6ClientNetAddrType,
        vRtrDHCP6ClientNetAddr,
        vRtrDHCP6AssignedNetAddrType,
        vRtrDHCP6AssignedNetAddr,
        vRtrDHCP6AssignedPrefixLen,
        vRtrDHCP6OldAssignedNetAddrType,
        vRtrDHCP6OldAssignedNetAddr,
        vRtrDHCP6OldAssignedPrefixLen,
        vRtrDHCP6NewClientId,
        vRtrDHCP6OldClientId,
        vRtrDHCP6LeaseOverrideResult,
        vRtrInetStatRteCpeNotifyAddrType,
        vRtrInetStatRteCpeNotifyAddr,
        vRtrInetStaticRouteCpeStatus,
        vRtrManagedRouteInetAddrType,
        vRtrManagedRouteInetAddr,
        vRtrManagedRoutePrefixLen,
        vRtrFailureDescription,
        vRtrMaxRoutesType,
        vRtrSlotOrCpmFlag
    }
    STATUS      obsolete
    DESCRIPTION
        "The group of objects supporting management of notification objects on
         Nokia SROS 6.0 series systems."
    ::= { tmnxVRtrGroups 39 }

tmnxVRtrNotificationV6v0Group    NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrBfdSessionUp,
        tmnxVRtrIPv6MidRouteTCA,
        tmnxVRtrIPv6HighRouteTCA,
        tmnxVRtrIPv6HighRouteCleared,
        tmnxVRtrStaticRouteCPEStatus,
        tmnxVRtrBfdSessionDeleted,
        tmnxVRtrBfdSessionProtChange,
        tmnxVRtrManagedRouteAddFailed
    }
    STATUS      obsolete
    DESCRIPTION
        "The group of notifications supporting the transport and virtual router
         capabilities on version 6.0 Nokia SROS series systems."
    ::= { tmnxVRtrGroups 40 }

tmnxVRtrBfdV6v0Group             OBJECT-GROUP
    OBJECTS     {
        vRtrIfBfdAdminState,
        vRtrIfBfdTransmitInterval,
        vRtrIfBfdReceiveInterval,
        vRtrIfBfdMultiplier,
        vRtrIfBfdSessionOperState,
        vRtrIfBfdSessionState,
        vRtrIfBfdSessionOperFlags,
        vRtrIfBfdSessionMesgRecv,
        vRtrIfBfdSessionMesgSent,
        vRtrIfBfdSessionLastDownTime,
        vRtrIfBfdSessionLastUpTime,
        vRtrIfBfdSessionUpCount,
        vRtrIfBfdSessionDownCount,
        vRtrIfBfdSessionLclDisc,
        vRtrIfBfdSessionRemDisc,
        vRtrIfBfdSessionProtocols,
        vRtrIfBfdSessionTxInterval,
        vRtrIfBfdSessionRxInterval,
        vRtrIfBfdEchoInterval,
        vRtrIfBfdSessionType
    }
    STATUS      obsolete
    DESCRIPTION
        "The group of objects supporting Bi-directional Forwarding Detection on
         version 6.0 Nokia SROS series systems."
    ::= { tmnxVRtrGroups 41 }

tmnxVRtrV6v1Group                OBJECT-GROUP
    OBJECTS     {
        vRtrIgnoreNextHopMetric,
        vRtrIfStripLabel
    }
    STATUS      current
    DESCRIPTION
        "The group of objects supporting new functionality on version 6.1 Nokia
         SROS series systems."
    ::= { tmnxVRtrGroups 42 }

tmnxVRtrIPv6MgtIfV7v0Group       OBJECT-GROUP
    OBJECTS     {
        vRtrIfIPv6ConfigAllowed
    }
    STATUS      current
    DESCRIPTION
        "The group of objects supporting management of IPv6 on the the
         management interface on version 7.0 Nokia SROS series systems."
    ::= { tmnxVRtrGroups 43 }

tmnxVRtrFibStatsV6v0Group        OBJECT-GROUP
    OBJECTS     {
        vRtrFibStatStaticRoutes,
        vRtrFibStatDirectRoutes,
        vRtrFibStatHostRoutes,
        vRtrFibStatBGPRoutes,
        vRtrFibStatBGPVpnRoutes,
        vRtrFibStatOSPFRoutes,
        vRtrFibStatISISRoutes,
        vRtrFibStatRIPRoutes,
        vRtrFibStatAggrRoutes,
        vRtrFibStatSubMgmtRoutes,
        vRtrFibStatManagedRoutes,
        vRtrFibStatV6StaticRoutes,
        vRtrFibStatV6DirectRoutes,
        vRtrFibStatV6HostRoutes,
        vRtrFibStatV6BGPRoutes,
        vRtrFibStatV6BGPVpnRoutes,
        vRtrFibStatV6OSPFRoutes,
        vRtrFibStatV6ISISRoutes,
        vRtrFibStatV6RIPRoutes,
        vRtrFibStatV6AggrRoutes,
        vRtrFibStatV6SubMgmtRoutes,
        vRtrFibStatV6ManagedRoutes,
        vRtrFibStatOverflows,
        vRtrFibStatNextHopIPActive,
        vRtrFibStatNextHopIPAvailable,
        vRtrFibStatNextHopTunnelActive,
        vRtrFibStatNextHopTunnelAvailable
    }
    STATUS      obsolete
    DESCRIPTION
        "The group of objects supporting FIB summary counts on version 6.0
         Nokia SROS series systems."
    ::= { tmnxVRtrGroups 44 }

tmnxVRtrInetAllCidrRouteV7v0Group OBJECT-GROUP
    OBJECTS     {
        vRtrInetAllCidrRouteIfIndex,
        vRtrInetAllCidrRouteType,
        vRtrInetAllCidrRouteAge,
        vRtrInetAllCidrRouteNextHopAS,
        vRtrInetAllCidrRouteMetric1,
        vRtrInetAllCidrRouteMetric2,
        vRtrInetAllCidrRouteMetric3,
        vRtrInetAllCidrRouteMetric4,
        vRtrInetAllCidrRouteMetric5,
        vRtrInetAllCidrRoutePreference,
        vRtrInetAllCidrRouteMetric,
        vRtrInetAllCidrRouteIfVRtrId,
        vRtrInetAllCidrRouteIsActive
    }
    STATUS      current
    DESCRIPTION
        "The group of objects supporting FIB summary counts on version 7.0
         Nokia SROS series systems."
    ::= { tmnxVRtrGroups 45 }

tmnxVRtrInetStaticRouteV7v0Group OBJECT-GROUP
    OBJECTS     {
        vRtrInetStaticRoutePrefixListName,
        vRtrInetStaticRoutePrefixListFlag
    }
    STATUS      current
    DESCRIPTION
        "The group of objects supporting the Conditional Route Policy
         capability on version 7.0 Nokia SROS series systems."
    ::= { tmnxVRtrGroups 46 }

tmnxVRtrFibStatsV6v1Group        OBJECT-GROUP
    OBJECTS     {
        vRtrFibStatStaticRoutes,
        vRtrFibStatDirectRoutes,
        vRtrFibStatHostRoutes,
        vRtrFibStatBGPRoutes,
        vRtrFibStatBGPVpnRoutes,
        vRtrFibStatOSPFRoutes,
        vRtrFibStatISISRoutes,
        vRtrFibStatRIPRoutes,
        vRtrFibStatAggrRoutes,
        vRtrFibStatSubMgmtRoutes,
        vRtrFibStatManagedRoutes,
        vRtrFibStatV6StaticRoutes,
        vRtrFibStatV6DirectRoutes,
        vRtrFibStatV6HostRoutes,
        vRtrFibStatV6BGPRoutes,
        vRtrFibStatV6BGPVpnRoutes,
        vRtrFibStatV6OSPFRoutes,
        vRtrFibStatV6ISISRoutes,
        vRtrFibStatV6RIPRoutes,
        vRtrFibStatV6AggrRoutes,
        vRtrFibStatV6SubMgmtRoutes,
        vRtrFibStatV6ManagedRoutes,
        vRtrFibStatOverflows,
        vRtrFibStatAlarmCount,
        vRtrFibStatLastAlarmTime,
        vRtrFibStatHighUtilization,
        vRtrFibStatNextHopIPActive,
        vRtrFibStatNextHopIPAvailable,
        vRtrFibStatNextHopTunnelActive,
        vRtrFibStatNextHopTunnelAvailable
    }
    STATUS      obsolete
    DESCRIPTION
        "The group of objects supporting FIB summary counts on version 6.1
         Nokia SROS series systems."
    ::= { tmnxVRtrGroups 47 }

tmnxVRtrNotificationV6v1Group    NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrBfdSessionUp,
        tmnxVRtrIPv6MidRouteTCA,
        tmnxVRtrIPv6HighRouteTCA,
        tmnxVRtrIPv6HighRouteCleared,
        tmnxVRtrStaticRouteCPEStatus,
        tmnxVRtrBfdSessionDeleted,
        tmnxVRtrBfdSessionProtChange,
        tmnxVRtrManagedRouteAddFailed,
        tmnxVRtrFibOccupancyThreshold
    }
    STATUS      obsolete
    DESCRIPTION
        "The group of notifications supporting the transport and virtual router
         capabilities on version 6.1 Nokia SROS series systems."
    ::= { tmnxVRtrGroups 48 }

tmnxVRtruRPFV7v0Group            OBJECT-GROUP
    OBJECTS     {
        vRtrIfuRPFCheckState,
        vRtrIfuRPFCheckMode,
        vRtrIfuRPFCheckFailPkts,
        vRtrIfuRPFCheckFailPktsLow32,
        vRtrIfuRPFCheckFailPktsHigh32,
        vRtrIfuRPFCheckFailBytes,
        vRtrIfuRPFCheckFailBytesLow32,
        vRtrIfuRPFCheckFailBytesHigh32
    }
    STATUS      current
    DESCRIPTION
        "The group of objects supporting unicast RPF feature on version 7.0
         Nokia SROS series systems."
    ::= { tmnxVRtrGroups 49 }

tmnxVRtrMvpnV7v0Group            OBJECT-GROUP
    OBJECTS     {
        vRtrMvpnVrfTarget,
        vRtrMvpnVrfExportTarget,
        vRtrMvpnVrfImportTarget,
        vRtrMvpnVrfTargetUnicast,
        vRtrMvpnVrfExportTargetUnicast,
        vRtrMvpnVrfImportTargetUnicast,
        vRtrMvpnImportPolicy1,
        vRtrMvpnImportPolicy2,
        vRtrMvpnImportPolicy3,
        vRtrMvpnImportPolicy4,
        vRtrMvpnImportPolicy5,
        vRtrMvpnExportPolicy1,
        vRtrMvpnExportPolicy2,
        vRtrMvpnExportPolicy3,
        vRtrMvpnExportPolicy4,
        vRtrMvpnExportPolicy5,
        vRtrMvpnImportPolicyUnicast,
        vRtrMvpnExportPolicyUnicast,
        vRtrMvpnCMcastImportRT
    }
    STATUS      obsolete
    DESCRIPTION
        "The group of objects supporting Multicast VPN (MVPN) on version 7.0
         Nokia SROS series systems."
    ::= { tmnxVRtrGroups 50 }

tmnxVRtrIfV7v0Group              OBJECT-GROUP
    OBJECTS     {
        vRtrIfQosQGrp
    }
    STATUS      obsolete
    DESCRIPTION
        "The group of additional router interface objects supported on version
         7.0 Nokia SROS series systems."
    ::= { tmnxVRtrGroups 51 }

tmnxVRtrIpV7v0Group              OBJECT-GROUP
    OBJECTS     {
        vRiaRowStatus,
        vRiaIpAddress,
        vRiaNetMask,
        vRiaBcastAddrFormat,
        vRiaReasmMaxSize,
        vRiaIgpInhibit,
        vRiaInetAddressType,
        vRiaInetAddress,
        vRiaInetPrefixLen,
        vRiaInetAddrState,
        vRiaInetEui64,
        vRiaInetOperAddress,
        vRiaInetGwAddressType,
        vRiaInetGwAddress,
        vRiaInetRemoteIpType,
        vRiaInetRemoteIp,
        vRtrIpCidrRouteLastEnabledTime,
        vRtrIpCidrRoutePreference,
        vRtrIpCidrRouteMetric,
        vRtrStaticRouteDest,
        vRtrStaticRouteMask,
        vRtrStaticRouteIndex,
        vRtrStaticRouteNumber,
        vRtrStaticRouteRowStatus,
        vRtrStaticRouteLastEnabledTime,
        vRtrStaticRouteStatus,
        vRtrStaticRouteStaticType,
        vRtrStaticRoutePreference,
        vRtrStaticRouteMetric,
        vRtrStaticRouteEgressIfIndex,
        vRtrStaticRouteNextHop,
        vRtrStaticRouteNextHopUnnumberedIf,
        vRtrStaticRouteAdminState,
        vRtrStaticRouteIgpShortcut,
        vRtrStaticRouteDisallowIgp,
        vRtrStaticRouteTag,
        vRtrStaticRouteIndexDest,
        vRtrStaticRouteIndexMask,
        vRtrStaticRouteAvailableIndex,
        vRtrInetStaticRouteRowStatus,
        vRtrInetStaticRouteLastEnabledTime,
        vRtrInetStaticRouteStatus,
        vRtrInetStaticRouteStaticType,
        vRtrInetStaticRoutePreference,
        vRtrInetStaticRouteMetric,
        vRtrInetStaticRouteEgressIfIndex,
        vRtrInetStaticRouteNextHopType,
        vRtrInetStaticRouteNextHop,
        vRtrInetStaticRouteNextHopIf,
        vRtrInetStaticRouteAdminState,
        vRtrInetStaticRouteIgpShortcut,
        vRtrInetStaticRouteDisallowIgp,
        vRtrInetStaticRouteTag,
        vRtrInetStaticRouteEnableBfd,
        vRtrInetStaticRouteAvailIndex,
        vRtrSvcIpRangeAddress,
        vRtrSvcIpRangeMask,
        vRtrSvcIpRangeRowStatus,
        vRtrSvcIpRangeExclusive,
        vRtrIpNetToMediaTimer,
        vRtrIpNetToMediaOperState,
        vRtrTunnelMetric,
        vRtrTunnelAge,
        vRtrAdvPrefixOnLinkFlag,
        vRtrAdvPrefixAutonomousFlag,
        vRtrAdvPrefixPreferredLifetime,
        vRtrAdvPrefixValidLifetime,
        vRtrAdvPrefixRowStatus,
        vRtrInetInstAggrTblLastChged,
        vRtrInetAggrRowStatus,
        vRtrInetAggrLastChanged,
        vRtrInetAggrSummaryOnly,
        vRtrInetAggrASSet,
        vRtrInetAggrAggregatorIPAddr,
        vRtrInetAggrOperState,
        vRtrInetSvcIpRangeRowStatus,
        vRtrInetSvcIpRangeExclusive,
        vRtrIpNetToPhysicalTimer,
        vRtrIpNetToPhysicalOperState,
        vRtrIpNetToPhysicalIsRouter,
        vRtrIpNetToPhysicalMTU,
        vRtrIpNetToPhysicalPort,
        vRtrIpNetToPhysicalEncap,
        vRtrInetCidrRouteLastEnabledTime,
        vRtrInetCidrRoutePreference,
        vRtrInetCidrRouteMetric,
        vRtrInetCidrRouteIfVRtrId,
        vRtrInetAggrAggregatorAS4Byte,
        vRtrInetCidrRouteTunnEndpntInfo,
        vRtrInetCidrProtocolInstance,
        vRtrInetStaticRouteLdpSync
    }
    STATUS      obsolete
    DESCRIPTION
        "The group of objects supporting management of IP capabilities for
         transport and virtual routers on version 7.0 Nokia SROS series
         systems. This group was obsoleted in release 13.0."
    ::= { tmnxVRtrGroups 52 }

tmnxVRtrV7v0Group                OBJECT-GROUP
    OBJECTS     {
        vRtrRowStatus,
        vRtrAdminState,
        vRtrName,
        vRtrMaxNumRoutes,
        vRtrBgpStatus,
        vRtrMplsStatus,
        vRtrRipStatus,
        vRtrRsvpStatus,
        vRtrEcmpMaxRoutes,
        vRtrNewIfIndex,
        vRtrLdpStatus,
        vRtrIsIsStatus,
        vRtrRouterId,
        vRtrTriggeredPolicy,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrIPv6MaxNumRoutes,
        vRtrIPv6MidRouteThreshold,
        vRtrIPv6HighRouteThreshold,
        vRtrIPv6MaxNumRoutesLogOnly,
        vRtrIPv6IgnoreIcmpRedirect,
        vRtrMcPathMgmtPlcyName,
        vRtrImportPolicy1,
        vRtrImportPolicy2,
        vRtrImportPolicy3,
        vRtrImportPolicy4,
        vRtrImportPolicy5,
        vRtrExportPolicy1,
        vRtrExportPolicy2,
        vRtrExportPolicy3,
        vRtrExportPolicy4,
        vRtrExportPolicy5,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrHostRoutes,
        vRtrHostActiveRoutes,
        vRtrV6HostRoutes,
        vRtrV6HostActiveRoutes,
        vRtrStatLocalARPEntries,
        vRtrStatStaticARPEntries,
        vRtrStatDynamicARPEntries,
        vRtrStatManagedARPEntries,
        vRtrStatInternalARPEntries,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped,
        vRtrInetStaticRouteNHTunnelName,
        vRtrManagedRoutes,
        vRtrManagedActiveRoutes,
        vRtrAS4Byte,
        vRtrConfederationAS4Byte,
        vRiaInetAddrPreferred,
        vRtrIfAdmLnkLclAddrPreferred,
        vRtrIfAdminLinkLocalAddr,
        vRtrIfAdminLinkLocalAddrType
    }
    STATUS      obsolete
    DESCRIPTION
        "The group of objects supporting management of transport and virtual
         routers on version 7.0 Nokia SROS series systems."
    ::= { tmnxVRtrGroups 53 }

tmnxVRtrObsoleteV7v0Group        OBJECT-GROUP
    OBJECTS     {
        vRtrAS,
        vRtrConfederationAS,
        vRtrInetAggrAggregatorAS,
        vRtrInstanceAggregationTableLastChanged,
        vRtrAggregationRowStatus,
        vRtrAggregationLastChanged,
        vRtrAggregationSummaryOnly,
        vRtrAggregationASSet,
        vRtrAggregationAggregatorAS,
        vRtrAggregationAggregatorIPAddr,
        vRtrAggregationOperState
    }
    STATUS      current
    DESCRIPTION
        "The group of objects in TIMETRA-VRTR-MIB which are obsoleted in Nokia
         SROS 7.0 series systems."
    ::= { tmnxVRtrGroups 54 }

tmnxVRtrIfDHCPRelayV7v0Group     OBJECT-GROUP
    OBJECTS     {
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfDHCPLayer2Header,
        vRtrIfDHCPAntiSpoofMacAddr,
        vRtrIfDHCPClientApplications,
        vRtrIfLdpSyncTimer,
        vRtrIfDHCPUseArpForReply,
        vRtrIfDHCPRelayPlainBootp,
        vRtrIfDHCPUserDb
    }
    STATUS      obsolete
    DESCRIPTION
        "The group of objects supporting management of DHCP Relay on virtual
         interfaces on version 7.0 Nokia SROS series systems"
    ::= { tmnxVRtrGroups 55 }

tmnxVRtrBfdV7v0Group             OBJECT-GROUP
    OBJECTS     {
        vRtrIfBfdSessionVerMismatch
    }
    STATUS      obsolete
    DESCRIPTION
        "The group of objects supporting Bi-directional Forwarding Detection
         add in version 7.0 Nokia SROS series systems."
    ::= { tmnxVRtrGroups 56 }

tmnxVRtrIfDHCPRelayV6v1Group     OBJECT-GROUP
    OBJECTS     {
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfDHCPLayer2Header,
        vRtrIfDHCPAntiSpoofMacAddr,
        vRtrIfDHCPClientApplications,
        vRtrIfDHCPUseArpForReply,
        vRtrIfLdpSyncTimer
    }
    STATUS      current
    DESCRIPTION
        "The group of objects supporting management of DHCP Relay on virtual
         interfaces on version 6.1 Nokia SROS series systems"
    ::= { tmnxVRtrGroups 57 }

tmnxVRtrNotificationObjV7v0Group OBJECT-GROUP
    OBJECTS     {
        vRtrID,
        vRtrIfIndex,
        vRtrDhcpPacketProblem,
        vRtrBfdSlotNumber,
        vRtrNumberOfBfdSessionsOnSlot,
        vRtrBfdMaxSessionReason,
        vRtrDHCP6ServerNetAddrType,
        vRtrDHCP6ServerNetAddr,
        vRtrDHCP6ClientNetAddrType,
        vRtrDHCP6ClientNetAddr,
        vRtrDHCP6AssignedNetAddrType,
        vRtrDHCP6AssignedNetAddr,
        vRtrDHCP6AssignedPrefixLen,
        vRtrDHCP6OldAssignedNetAddrType,
        vRtrDHCP6OldAssignedNetAddr,
        vRtrDHCP6OldAssignedPrefixLen,
        vRtrDHCP6NewClientId,
        vRtrDHCP6OldClientId,
        vRtrDHCP6LeaseOverrideResult,
        vRtrInetStatRteCpeNotifyAddrType,
        vRtrInetStatRteCpeNotifyAddr,
        vRtrInetStaticRouteCpeStatus,
        vRtrManagedRouteInetAddrType,
        vRtrManagedRouteInetAddr,
        vRtrManagedRoutePrefixLen,
        vRtrFailureDescription,
        vRtrMaxRoutesType,
        vRtrSlotOrCpmFlag,
        vRtrNotifInetAddrType,
        vRtrNotifInetAddr
    }
    STATUS      obsolete
    DESCRIPTION
        "The group of objects supporting management of notification objects on
         Nokia SROS 7.0 series systems."
    ::= { tmnxVRtrGroups 58 }

tmnxVRtrNotificationV7v0Group    NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrBfdSessionUp,
        tmnxVRtrIPv6MidRouteTCA,
        tmnxVRtrIPv6HighRouteTCA,
        tmnxVRtrIPv6HighRouteCleared,
        tmnxVRtrStaticRouteCPEStatus,
        tmnxVRtrBfdSessionDeleted,
        tmnxVRtrBfdSessionProtChange,
        tmnxVRtrManagedRouteAddFailed,
        tmnxVRtrFibOccupancyThreshold,
        tmnxVRtrInetAddressAttachFailed
    }
    STATUS      obsolete
    DESCRIPTION
        "The group of notifications supporting the transport and virtual router
         capabilities on version 7.0 Nokia SROS series systems."
    ::= { tmnxVRtrGroups 59 }

tmnxVRtrV8v0Group                OBJECT-GROUP
    OBJECTS     {
        vRtrRowStatus,
        vRtrAdminState,
        vRtrName,
        vRtrMaxNumRoutes,
        vRtrBgpStatus,
        vRtrMplsStatus,
        vRtrRipStatus,
        vRtrRsvpStatus,
        vRtrEcmpMaxRoutes,
        vRtrNewIfIndex,
        vRtrLdpStatus,
        vRtrRouterId,
        vRtrTriggeredPolicy,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrIPv6MaxNumRoutes,
        vRtrIPv6MidRouteThreshold,
        vRtrIPv6HighRouteThreshold,
        vRtrIPv6MaxNumRoutesLogOnly,
        vRtrIPv6IgnoreIcmpRedirect,
        vRtrMcPathMgmtPlcyName,
        vRtrImportPolicy1,
        vRtrImportPolicy2,
        vRtrImportPolicy3,
        vRtrImportPolicy4,
        vRtrImportPolicy5,
        vRtrExportPolicy1,
        vRtrExportPolicy2,
        vRtrExportPolicy3,
        vRtrExportPolicy4,
        vRtrExportPolicy5,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrHostRoutes,
        vRtrHostActiveRoutes,
        vRtrV6HostRoutes,
        vRtrV6HostActiveRoutes,
        vRtrStatLocalARPEntries,
        vRtrStatStaticARPEntries,
        vRtrStatDynamicARPEntries,
        vRtrStatManagedARPEntries,
        vRtrStatInternalARPEntries,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped,
        vRtrInetStaticRouteNHTunnelName,
        vRtrManagedRoutes,
        vRtrManagedActiveRoutes,
        vRtrAS4Byte,
        vRtrConfederationAS4Byte,
        vRiaInetAddrPreferred,
        vRiaSubscrPrefix,
        vRiaSubscrPrefixType,
        vRiaSubscrHostRoutePopulate,
        vRtrIfAdmLnkLclAddrPreferred,
        vRtrIfAdminLinkLocalAddr,
        vRtrIfAdminLinkLocalAddrType,
        vRtrIfLsrIpLoadBalancing,
        vRtrIfDHCP6ProxyAdminState,
        vRtrIfDHCP6ProxyRenewTimer,
        vRtrIfDHCP6ProxyRebindTimer,
        vRtrIfDHCP6ProxyValidLifetime,
        vRtrIfDHCP6ProxyPrefLifetime,
        vRtrIfDHCP6ProxyApplications,
        vRtrIfDHCP6UserDb,
        vRtrSingleSfmOverloadAdminState,
        vRtrSingleSfmOverloadHldOffTime,
        vRtrSingleSfmOverloadState,
        vRtrSingleSfmOverloadStart,
        vRtrSingleSfmOverloadTime,
        vRtrLdpShortcut,
        vRtrLDPRoutes,
        vRtrLDPActiveRoutes,
        vRtrGrtState,
        vRtrGrtMaxExportRoutes,
        vRtrGrtExportPolicy1,
        vRtrGrtExportPolicy2,
        vRtrGrtExportPolicy3,
        vRtrGrtExportPolicy4,
        vRtrGrtExportPolicy5,
        vRtrVPNLeakRoutes,
        vRtrVPNLeakActiveRoutes,
        vRtrV6VPNLeakRoutes,
        vRtrV6VPNLeakActiveRoutes,
        vRtrInetCidrRouteNextHopType,
        vRtrInetCidrRouteNextHopOwner,
        vRtrInetCidrRouteNHOwnerAuxInfo,
        vRtrInetCidrRteTnlEnabledTime,
        vRtrV6SubMgmtRoutes,
        vRtrV6SubMgmtActiveRoutes,
        vRtrMvpnIpmsiType,
        vRtrMvpnSpmsiType,
        vRtrMobileHostRoutes,
        vRtrMobileHostActiveRoutes,
        vRtrV6MobileHostRoutes,
        vRtrV6MobileHostActiveRoutes,
        vRtrStatTotalBgpTunnels,
        vRtrStatActiveBgpTunnels
    }
    STATUS      obsolete
    DESCRIPTION
        "The group of objects supporting management of transport and virtual
         routers new on version 8.0 Nokia SROS series systems."
    ::= { tmnxVRtrGroups 60 }

tmnxVRtrIfDHCPRelayV8v0Group     OBJECT-GROUP
    OBJECTS     {
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfDHCPLayer2Header,
        vRtrIfDHCPAntiSpoofMacAddr,
        vRtrIfDHCPClientApplications,
        vRtrIfLdpSyncTimer,
        vRtrIfDHCPUseArpForReply,
        vRtrIfDHCPRelayPlainBootp,
        vRtrIfDHCPUserDb
    }
    STATUS      obsolete
    DESCRIPTION
        "The group of objects supporting management of DHCP Relay on virtual
         interfaces on version 8.0 Nokia SROS series systems"
    ::= { tmnxVRtrGroups 61 }

tmnxVRtrNetDomainGroup           OBJECT-GROUP
    OBJECTS     {
        vRtrNetDomainRowStatus,
        vRtrNetDomainLastChanged,
        vRtrNetDomainDesc,
        vRtrNetDomainIfAssociationCnt,
        vRtrNetDomainSdpAssociationCnt,
        vRtrIfNetDomainRowStatus,
        vRtrIfNetDomainLastChanged,
        vRtrIfNetDomainTblLastChanged,
        vRtrNetDomainTblLastChanged
    }
    STATUS      current
    DESCRIPTION
        "The group of objects supporting network-domain optimization for
         Ingress SAP Queue allocation in version 8.0 Nokia SROS series systems."
    ::= { tmnxVRtrGroups 62 }

tmnxVRtrNotificationV8v0Group    NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported,
        tmnxVRtrBfdNoCpmNpResources,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrBfdSessionUp,
        tmnxVRtrIPv6MidRouteTCA,
        tmnxVRtrIPv6HighRouteTCA,
        tmnxVRtrIPv6HighRouteCleared,
        tmnxVRtrStaticRouteCPEStatus,
        tmnxVRtrBfdSessionDeleted,
        tmnxVRtrBfdSessionProtChange,
        tmnxVRtrManagedRouteAddFailed,
        tmnxVRtrFibOccupancyThreshold,
        tmnxVRtrInetAddressAttachFailed,
        tmnxVRtrSingleSfmOverloadStateCh,
        tmnxVRtrGrtExportLimitReached,
        tmnxVRtrGrtRoutesExpLimitDropped,
        tmnxVRtrIfLdpSyncTimerStart,
        tmnxVRtrIfLdpSyncTimerStop
    }
    STATUS      obsolete
    DESCRIPTION
        "The group of notifications supporting the transport and virtual router
         capabilities on version 8.0 Nokia SROS series systems."
    ::= { tmnxVRtrGroups 63 }

tmnxVRtrObsoleteV8v0Group        OBJECT-GROUP
    OBJECTS     {
        vRtrIsIsStatus
    }
    STATUS      current
    DESCRIPTION
        "The group of objects in TIMETRA-VRTR-MIB which are obsoleted in Nokia
         SROS 8.0 series systems."
    ::= { tmnxVRtrGroups 64 }

tmnxVRtrTunIntV8v0Group          OBJECT-GROUP
    OBJECTS     {
        vRtrRsvpTunIfTableLastChanged,
        vRtrRsvpTunIfRowStatus,
        vRtrRsvpTunIfLastChanged,
        vRtrRsvpTunIfSessionId,
        vRtrRsvpTunIfTransmitInt,
        vRtrRsvpTunIfMultiplier,
        vRtrRsvpTunIfStandbyLspName,
        vRtrRsvpTunIfStandbyAddrType,
        vRtrRsvpTunIfStandbyAddr,
        vRtrRsvpTunIfIfIndex,
        vRtrRsvpTunIfHoldTimer,
        vRtrRsvpTunIfStandbySessionId,
        vRtrRsvpTunIfStandbyIfIndex,
        vRtrRsvpTunIfDescription,
        vRtrRsvpTunIfSrcTableLastChanged,
        vRtrRsvpTunIfSrcRowStatus,
        vRtrRsvpTunIfSrcLastChanged,
        vRtrRsvpTunIfSrcBfdEnable,
        vRtrRsvpTunIfSrcSessionId,
        vRtrRsvpTunIfSrcTransmitInt,
        vRtrRsvpTunIfSrcMultiplier,
        vRtrRsvpTunIfSrcStandbySessionId,
        vRtrLdpTunIfTableLastChanged,
        vRtrLdpTunIfRowStatus,
        vRtrLdpTunIfLastChanged,
        vRtrLdpTunIfIfIndex,
        vRtrLdpTunIfDescription,
        vRtrLdpTunIfRootNode
    }
    STATUS      current
    DESCRIPTION
        "The group of objects supporting management of tunnel interface for
         implementation of P2MP-LSP on Nokia SROS 8.0 series systems."
    ::= { tmnxVRtrGroups 65 }

tmnxVRtrBfdV8v0Group             OBJECT-GROUP
    OBJECTS     {
        vRtrIfBfdType,
        vRtrIfBfdSessionTimeSinceLastRx,
        vRtrIfBfdSessionTimeSinceLastTx
    }
    STATUS      obsolete
    DESCRIPTION
        "The group of objects supporting Bi-directional Forwarding Detection
         added in release 8.0 Nokia SROS series systems."
    ::= { tmnxVRtrGroups 66 }

tmnxVRtrMvpnPmsiV8v0Group        OBJECT-GROUP
    OBJECTS     {
        vRtrMvpnIpmsiP2MPAdmin,
        vRtrMvpnSpmsiP2MPAdmin,
        vRtrMvpnIpmsiLspTemplate,
        vRtrMvpnSpmsiLspTemplate,
        vRtrMvpnSpmsiMaxLimit,
        vRtrInterASMvpn
    }
    STATUS      current
    DESCRIPTION
        "The group of objects supporting management of Mvpn added in release
         8.0 Nokia SROS series systems."
    ::= { tmnxVRtrGroups 67 }

tmnxVRtrFibStatsV8v0Group        OBJECT-GROUP
    OBJECTS     {
        vRtrFibStatStaticRoutes,
        vRtrFibStatDirectRoutes,
        vRtrFibStatHostRoutes,
        vRtrFibStatBGPRoutes,
        vRtrFibStatBGPVpnRoutes,
        vRtrFibStatOSPFRoutes,
        vRtrFibStatISISRoutes,
        vRtrFibStatRIPRoutes,
        vRtrFibStatAggrRoutes,
        vRtrFibStatSubMgmtRoutes,
        vRtrFibStatManagedRoutes,
        vRtrFibStatV6StaticRoutes,
        vRtrFibStatV6DirectRoutes,
        vRtrFibStatV6HostRoutes,
        vRtrFibStatV6BGPRoutes,
        vRtrFibStatV6BGPVpnRoutes,
        vRtrFibStatV6OSPFRoutes,
        vRtrFibStatV6ISISRoutes,
        vRtrFibStatV6RIPRoutes,
        vRtrFibStatV6AggrRoutes,
        vRtrFibStatV6SubMgmtRoutes,
        vRtrFibStatV6ManagedRoutes,
        vRtrFibStatOverflows,
        vRtrFibStatAlarmCount,
        vRtrFibStatLastAlarmTime,
        vRtrFibStatHighUtilization,
        vRtrFibStatNextHopIPActive,
        vRtrFibStatNextHopIPAvailable,
        vRtrFibStatNextHopTunnelActive,
        vRtrFibStatNextHopTunnelAvailable,
        vRtrFibStatMobileHostRoutes,
        vRtrFibStatV6MobileHostRoutes,
        vRtrFibStatVPNLeakRoutes,
        vRtrFibStatV6VPNLeakRoutes
    }
    STATUS      current
    DESCRIPTION
        "The group of objects supporting FIB summary counts on version 8.0
         Nokia SROS series systems."
    ::= { tmnxVRtrGroups 68 }

tmnxVRtrV9v0Group                OBJECT-GROUP
    OBJECTS     {
        vRtrIfIngressIpv4Flowspec,
        vRtrFibPriority,
        vRtrCarrierCarrierVpn,
        vRtrLabelMode,
        vRtrBgpSharedQueue,
        vRtrBgpSharedQueueCIR,
        vRtrBgpSharedQueuePIR,
        vRiaHoldUpTime,
        vRiaTrackSrrpInstance,
        vRtrMvpnMdtSafi,
        vRtrMvpnMdtDefGrpAddrType,
        vRtrMvpnMdtDefGrpAddress,
        vRtrInetCidrRouteBkupFlags,
        vRtrInetCidrRouteBkupNextHopType,
        vRtrInetCidrRouteBkupNextHop,
        vRtrInetCidrRouteBkupMetric,
        vRtrInetCidrRouteNextHopRepCount,
        vRtrInetAllCidrRouteBkupFlags,
        vRtrInetAllCidrRouteBkupNHopType,
        vRtrInetAllCidrRouteBkupNextHop,
        vRtrInetAllCidrRouteBkupMetric,
        vRtrInetAllCidrRouteNHopRepCount,
        vRtrBgpExportInactive
    }
    STATUS      current
    DESCRIPTION
        "The group of new objects supporting management of transport and
         virtual routers new on version 9.0 Nokia SROS series systems."
    ::= { tmnxVRtrGroups 69 }

tmnxVRtrIfDHCP6V9v0Group         OBJECT-GROUP
    OBJECTS     {
        vRtrIfDHCP6LocalDhcpServerName,
        vRtrIfDHCP6RelayApplications
    }
    STATUS      current
    DESCRIPTION
        "The group of new objects supporting management of DHCPv6 on version
         9.0 Nokia SROS series systems."
    ::= { tmnxVRtrGroups 70 }

tmnxVRtrQPPBV9v0R4Group          OBJECT-GROUP
    OBJECTS     {
        vRtrInetStaticRouteFC,
        vRtrInetStaticRouteFCPriority,
        vRtrIfQosRouteLookup,
        vRtrIfIpv6QosRouteLookup,
        vRtrInetCidrRouteNHFC,
        vRtrInetCidrRouteNHPriority
    }
    STATUS      current
    DESCRIPTION
        "The group of objects supporting QoS policy propagation using BGP in
         release 9.0 R4 Nokia SROS series systems."
    ::= { tmnxVRtrGroups 71 }

tmnxVRtrBfdV9v0Group             OBJECT-GROUP
    OBJECTS     {
        vRtrIfBfdExtTableLastChanged,
        vRtrIfBfdExtAdminState,
        vRtrIfBfdExtTransmitInterval,
        vRtrIfBfdExtReceiveInterval,
        vRtrIfBfdExtMultiplier,
        vRtrIfBfdExtEchoInterval,
        vRtrIfBfdExtType,
        vRtrIfBfdSessionOperState,
        vRtrIfBfdSessionState,
        vRtrIfBfdSessionOperFlags,
        vRtrIfBfdSessionMesgRecv,
        vRtrIfBfdSessionMesgSent,
        vRtrIfBfdSessionLastDownTime,
        vRtrIfBfdSessionLastUpTime,
        vRtrIfBfdSessionUpCount,
        vRtrIfBfdSessionDownCount,
        vRtrIfBfdSessionLclDisc,
        vRtrIfBfdSessionRemDisc,
        vRtrIfBfdSessionProtocols,
        vRtrIfBfdSessionTxInterval,
        vRtrIfBfdSessionRxInterval,
        vRtrIfBfdSessionType,
        vRtrIfBfdSessionTimeSinceLastRx,
        vRtrIfBfdSessionTimeSinceLastTx
    }
    STATUS      obsolete
    DESCRIPTION
        "The group of objects supporting Bi-directional Forwarding Detection on
         version 9.0 Nokia SROS series systems."
    ::= { tmnxVRtrGroups 72 }

tmnxVRtrIfIpReasV9v0Group        OBJECT-GROUP
    OBJECTS     {
        vRtrIfIpReasPortID,
        vRtrIfIpReasContextValue,
        vRtrIfIpReasFragPktsRcvd,
        vRtrIfIpReasFragPktsRcvdLow32,
        vRtrIfIpReasFragPktsRcvdHigh32,
        vRtrIfIpReasFragBytesRcvd,
        vRtrIfIpReasFragBytesRcvdLow32,
        vRtrIfIpReasFragBytesRcvdHigh32,
        vRtrIfIpReasFragPktsReas,
        vRtrIfIpReasFragPktsReasLow32,
        vRtrIfIpReasFragPktsReasHigh32,
        vRtrIfIpReasFragBytesReas,
        vRtrIfIpReasFragBytesReasLow32,
        vRtrIfIpReasFragBytesReasHigh32,
        vRtrIfIpReasFragReasErrors,
        vRtrIfIpReasFragReasErrorsLow32,
        vRtrIfIpReasFragReasErrorsHigh32,
        vRtrIfIpReasFragDisc,
        vRtrIfIpReasFragDiscLow32,
        vRtrIfIpReasFragDiscHigh32,
        vRtrIfIpReasOutBufRes,
        vRtrIfIpReasOutBufResLow32,
        vRtrIfIpReasOutBufResHigh32,
        vRtrIfIpReasPktsRx,
        vRtrIfIpReasPktsRxLow32,
        vRtrIfIpReasPktsRxHigh32,
        vRtrIfIpReasBytesRx,
        vRtrIfIpReasBytesRxLow32,
        vRtrIfIpReasBytesRxHigh32,
        vRtrIfIpReasPktsTx,
        vRtrIfIpReasPktsTxLow32,
        vRtrIfIpReasPktsTxHigh32,
        vRtrIfIpReasBytesTx,
        vRtrIfIpReasBytesTxLow32,
        vRtrIfIpReasBytesTxHigh32,
        vRtrIfIpReasV6FragPktsRcvd,
        vRtrIfIpReasV6FragPktsRcvdLow32,
        vRtrIfIpReasV6FragPktsRcvdHigh32,
        vRtrIfIpReasV6FragBytesRcvd,
        vRtrIfIpReasV6FragBytesRcvdL32,
        vRtrIfIpReasV6FragBytesRcvdH32,
        vRtrIfIpReasV6FragPktsReas,
        vRtrIfIpReasV6FragPktsReasLow32,
        vRtrIfIpReasV6FragPktsReasHigh32,
        vRtrIfIpReasV6FragBytesReas,
        vRtrIfIpReasV6FragBytesReasL32,
        vRtrIfIpReasV6FragBytesReasH32,
        vRtrIfIpReasV6FragReasErrors,
        vRtrIfIpReasV6FragReasErrorsL32,
        vRtrIfIpReasV6FragReasErrorsH32,
        vRtrIfIpReasV6FragDisc,
        vRtrIfIpReasV6FragDiscLow32,
        vRtrIfIpReasV6FragDiscHigh32,
        vRtrIfIpReasV6OutBufRes,
        vRtrIfIpReasV6OutBufResLow32,
        vRtrIfIpReasV6OutBufResHigh32,
        vRtrIfIpReasV6PktsRx,
        vRtrIfIpReasV6PktsRxLow32,
        vRtrIfIpReasV6PktsRxHigh32,
        vRtrIfIpReasV6BytesRx,
        vRtrIfIpReasV6BytesRxLow32,
        vRtrIfIpReasV6BytesRxHigh32,
        vRtrIfIpReasV6PktsTx,
        vRtrIfIpReasV6PktsTxLow32,
        vRtrIfIpReasV6PktsTxHigh32,
        vRtrIfIpReasV6BytesTx,
        vRtrIfIpReasV6BytesTxLow32,
        vRtrIfIpReasV6BytesTxHigh32,
        vRtrIfSpeed
    }
    STATUS      current
    DESCRIPTION
        "The group of objects supporting IP Reassembly on version 9.0 Nokia
         SROS series systems."
    ::= { tmnxVRtrGroups 73 }

tmnxVRtrIfStatsV9v0Group         OBJECT-GROUP
    OBJECTS     {
        vRtrIfRxBytes,
        vRtrIfRxBytesHigh32,
        vRtrIfRxBytesLow32,
        vRtrIfRxPkts,
        vRtrIfRxPktsHigh32,
        vRtrIfRxPktsLow32,
        vRtrIfTxV4Bytes,
        vRtrIfTxV4BytesHigh32,
        vRtrIfTxV4BytesLow32,
        vRtrIfTxV4DiscardBytes,
        vRtrIfTxV4DiscardBytesHigh32,
        vRtrIfTxV4DiscardBytesLow32,
        vRtrIfTxV4DiscardPkts,
        vRtrIfTxV4DiscardPktsHigh32,
        vRtrIfTxV4DiscardPktsLow32,
        vRtrIfTxV4Pkts,
        vRtrIfTxV4PktsHigh32,
        vRtrIfTxV4PktsLow32,
        vRtrIfTxV6Bytes,
        vRtrIfTxV6BytesHigh32,
        vRtrIfTxV6BytesLow32,
        vRtrIfTxV6DiscardBytes,
        vRtrIfTxV6DiscardBytesHigh32,
        vRtrIfTxV6DiscardBytesLow32,
        vRtrIfTxV6DiscardPkts,
        vRtrIfTxV6DiscardPktsHigh32,
        vRtrIfTxV6DiscardPktsLow32,
        vRtrIfTxV6Pkts,
        vRtrIfTxV6PktsHigh32,
        vRtrIfTxV6PktsLow32
    }
    STATUS      current
    DESCRIPTION
        "The group of objects supporting IP Reassembly on version 9.0 Nokia
         SROS series systems."
    ::= { tmnxVRtrGroups 74 }

tmnxVRtrNotificationObjV8v0Group OBJECT-GROUP
    OBJECTS     {
        vRtrID,
        vRtrIfIndex,
        vRtrDhcpPacketProblem,
        vRtrBfdSlotNumber,
        vRtrNumberOfBfdSessionsOnSlot,
        vRtrBfdMaxSessionReason,
        vRtrDHCP6ServerNetAddrType,
        vRtrDHCP6ServerNetAddr,
        vRtrDHCP6ClientNetAddrType,
        vRtrDHCP6ClientNetAddr,
        vRtrDHCP6AssignedNetAddrType,
        vRtrDHCP6AssignedNetAddr,
        vRtrDHCP6AssignedPrefixLen,
        vRtrDHCP6OldAssignedNetAddrType,
        vRtrDHCP6OldAssignedNetAddr,
        vRtrDHCP6OldAssignedPrefixLen,
        vRtrDHCP6NewClientId,
        vRtrDHCP6OldClientId,
        vRtrDHCP6LeaseOverrideResult,
        vRtrInetStatRteCpeNotifyAddrType,
        vRtrInetStatRteCpeNotifyAddr,
        vRtrInetStaticRouteCpeStatus,
        vRtrManagedRouteInetAddrType,
        vRtrManagedRouteInetAddr,
        vRtrManagedRoutePrefixLen,
        vRtrFailureDescription,
        vRtrMaxRoutesType,
        vRtrSlotOrCpmFlag,
        vRtrNotifInetAddrType,
        vRtrNotifInetAddr,
        vRtrIfBfdSessChangedProtocol,
        vRtrIfBfdSessProtoChngdState
    }
    STATUS      obsolete
    DESCRIPTION
        "The group of objects supporting management of notification objects on
         Nokia SROS 8.0 series systems."
    ::= { tmnxVRtrGroups 75 }

tmnxVRtrIfDHCPRelayV9v0Group     OBJECT-GROUP
    OBJECTS     {
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfDHCPLayer2Header,
        vRtrIfDHCPAntiSpoofMacAddr,
        vRtrIfDHCPClientApplications,
        vRtrIfLdpSyncTimer,
        vRtrIfDHCPUseArpForReply,
        vRtrIfDHCPRelayPlainBootp,
        vRtrIfDHCPUserDb,
        vRtrIfDHCPFilterId
    }
    STATUS      current
    DESCRIPTION
        "The group of objects supporting management of DHCP Relay on virtual
         interfaces on version 9.0 Nokia SROS series systems"
    ::= { tmnxVRtrGroups 76 }

tmnxVRtrNatRedGroup              OBJECT-GROUP
    OBJECTS     {
        vRtrNatRoutes,
        vRtrNatActiveRoutes,
        vRtrV6NatRoutes,
        vRtrV6NatActiveRoutes,
        vRtrFibStatNatRoutes,
        vRtrFibStatV6NatRoutes
    }
    STATUS      current
    DESCRIPTION
        "The group of objects supporting management of NAT redundancy on Nokia
         SROS series systems."
    ::= { tmnxVRtrGroups 77 }

tmnxVRtrIfV9v0Group              OBJECT-GROUP
    OBJECTS     {
        vRtrIfInfo,
        vRtrIfInfoEncrypted,
        vRtrIfTxBytes,
        vRtrIfTxBytesHigh32,
        vRtrIfTxBytesLow32,
        vRtrIfTxPkts,
        vRtrIfTxPktsHigh32,
        vRtrIfTxPktsLow32,
        vRtrIfStatusString,
        vRtrIfOperDownReason
    }
    STATUS      obsolete
    DESCRIPTION
        "The group of objects supporting management of router interfaces on
         Nokia SROS series systems in 9.0 release."
    ::= { tmnxVRtrGroups 78 }

tmnxVRtrMSPwV9v0Group            OBJECT-GROUP
    OBJECTS     {
        vRtrMsPwL2RtIsBestRoute,
        vRtrMsPwL2RtRDCommunity,
        vRtrMsPwL2RtAge
    }
    STATUS      current
    DESCRIPTION
        "The group of new objects supporting management of virtual router
         dynamic multi-segment pseudo-wire features new on version 9.0 Nokia
         SROS series systems."
    ::= { tmnxVRtrGroups 79 }

tmnxVRtrMvpnSrcRedV9v0R4Group    OBJECT-GROUP
    OBJECTS     {
        vRtrMvpnIpmsiEnableBfdRoot,
        vRtrMvpnIpmsiEnableBfdLeaf,
        vRtrMvpnIpmsiBfdRtTraInt,
        vRtrMvpnIpmsiBfdRootMult
    }
    STATUS      current
    DESCRIPTION
        "The group of objects supporting management of MVPN source redundancy
         on version 9.0R4 Nokia SROS series systems."
    ::= { tmnxVRtrGroups 80 }

tmnxVRtrObsoletedBfdV9v0Group    OBJECT-GROUP
    OBJECTS     {
        vRtrIfBfdAdminState,
        vRtrIfBfdTransmitInterval,
        vRtrIfBfdReceiveInterval,
        vRtrIfBfdMultiplier,
        vRtrIfBfdEchoInterval,
        vRtrIfBfdType
    }
    STATUS      current
    DESCRIPTION
        "The group of objects obsoleted supporting Bi-directional Forwarding
         Detection on version 9.0 Nokia SROS series systems."
    ::= { tmnxVRtrGroups 81 }

tmnxVRtrStatV9v0Group            OBJECT-GROUP
    OBJECTS     {
        vRtrISISAltRoutes,
        vRtrISISActiveAltRoutes,
        vRtrBGPAltRoutes,
        vRtrBGPActiveAltRoutes,
        vRtrStatCurrNumAltRoutes,
        vRtrV6ISISAltRoutes,
        vRtrV6ISISActiveAltRoutes,
        vRtrV6BGPAltRoutes,
        vRtrV6BGPActiveAltRoutes,
        vRtrV6StatCurrNumAltRoutes
    }
    STATUS      current
    DESCRIPTION
        "The group of objects supporting management of statistics on version
         9.0 Nokia SROS series systems."
    ::= { tmnxVRtrGroups 82 }

tmnxVRtruRPFV10v0Group           OBJECT-GROUP
    OBJECTS     {
        vRtrIfIpv6uRPFCheckState,
        vRtrIfIpv6uRPFCheckMode
    }
    STATUS      current
    DESCRIPTION
        "The group of objects supporting management of router interfaces on
         Nokia SROS series systems in 10.0 release."
    ::= { tmnxVRtrGroups 83 }

tmnxVRtrPolicyGroup              OBJECT-GROUP
    OBJECTS     {
        vRtrVrfImportPolicy1,
        vRtrVrfImportPolicy2,
        vRtrVrfImportPolicy3,
        vRtrVrfImportPolicy4,
        vRtrVrfImportPolicy5,
        vRtrVrfImportPolicy6,
        vRtrVrfImportPolicy7,
        vRtrVrfImportPolicy8,
        vRtrVrfImportPolicy9,
        vRtrVrfImportPolicy10,
        vRtrVrfImportPolicy11,
        vRtrVrfImportPolicy12,
        vRtrVrfImportPolicy13,
        vRtrVrfImportPolicy14,
        vRtrVrfImportPolicy15,
        vRtrVrfExportPolicy1,
        vRtrVrfExportPolicy2,
        vRtrVrfExportPolicy3,
        vRtrVrfExportPolicy4,
        vRtrVrfExportPolicy5,
        vRtrVrfExportPolicy6,
        vRtrVrfExportPolicy7,
        vRtrVrfExportPolicy8,
        vRtrVrfExportPolicy9,
        vRtrVrfExportPolicy10,
        vRtrVrfExportPolicy11,
        vRtrVrfExportPolicy12,
        vRtrVrfExportPolicy13,
        vRtrVrfExportPolicy14,
        vRtrVrfExportPolicy15,
        vRtrMvpnVrfImportPolicy1,
        vRtrMvpnVrfImportPolicy2,
        vRtrMvpnVrfImportPolicy3,
        vRtrMvpnVrfImportPolicy4,
        vRtrMvpnVrfImportPolicy5,
        vRtrMvpnVrfImportPolicy6,
        vRtrMvpnVrfImportPolicy7,
        vRtrMvpnVrfImportPolicy8,
        vRtrMvpnVrfImportPolicy9,
        vRtrMvpnVrfImportPolicy10,
        vRtrMvpnVrfImportPolicy11,
        vRtrMvpnVrfImportPolicy12,
        vRtrMvpnVrfImportPolicy13,
        vRtrMvpnVrfImportPolicy14,
        vRtrMvpnVrfImportPolicy15,
        vRtrMvpnVrfExportPolicy1,
        vRtrMvpnVrfExportPolicy2,
        vRtrMvpnVrfExportPolicy3,
        vRtrMvpnVrfExportPolicy4,
        vRtrMvpnVrfExportPolicy5,
        vRtrMvpnVrfExportPolicy6,
        vRtrMvpnVrfExportPolicy7,
        vRtrMvpnVrfExportPolicy8,
        vRtrMvpnVrfExportPolicy9,
        vRtrMvpnVrfExportPolicy10,
        vRtrMvpnVrfExportPolicy11,
        vRtrMvpnVrfExportPolicy12,
        vRtrMvpnVrfExportPolicy13,
        vRtrMvpnVrfExportPolicy14,
        vRtrMvpnVrfExportPolicy15
    }
    STATUS      current
    DESCRIPTION
        "The group of objects supporting management of transport and virtual
         routers on Nokia SROS series systems in 10.0 release."
    ::= { tmnxVRtrGroups 84 }

tmnxVRtrIfDHCP6V10v0Group        OBJECT-GROUP
    OBJECTS     {
        vRtrIfDHCP6LinkAddress
    }
    STATUS      current
    DESCRIPTION
        "The group of new objects supporting management of DHCPv6 since version
         10.0 Nokia SROS series systems."
    ::= { tmnxVRtrGroups 85 }

tmnxVRtrGlobalV10v0Group         OBJECT-GROUP
    OBJECTS     {
        vRtrIfTmsOffRampVprn,
        vRtrIfTmsMgmtVprn,
        vRtrVpnBackupPath,
        vRtrIpFastReroute,
        vRtrDnsTableLastCh,
        vRtrDnsLastCh,
        vRtrDnsRowStatus,
        vRtrDnsAdminState,
        vRtrDnsPrimaryAddrType,
        vRtrDnsPrimaryAddr,
        vRtrDnsSecondaryAddrType,
        vRtrDnsSecondaryAddr,
        vRtrDnsTertiaryAddrType,
        vRtrDnsTertiaryAddr,
        vRtrDnsIpv4SourceAddr,
        vRtrDnsIpv6SourceAddr,
        vRtrIfInfo,
        vRtrIfTxBytes,
        vRtrIfTxBytesHigh32,
        vRtrIfTxBytesLow32,
        vRtrIfTxPkts,
        vRtrIfTxPktsHigh32,
        vRtrIfTxPktsLow32,
        vRtrIfStatusString,
        vRtrIfOperDownReason
    }
    STATUS      obsolete
    DESCRIPTION
        "The group of objects supporting management of additional features on
         Nokia SROS series systems release 10.0."
    ::= { tmnxVRtrGroups 86 }

tmnxVRtrQosQGrplV10v0Group       OBJECT-GROUP
    OBJECTS     {
        vRtrIfQosNetworkPolicyId,
        vRtrIfQosEgrPortRedirectQGrp,
        vRtrIfQosEgrQGrpInstanceId,
        vRtrIfQosIngFpRedirectQGrp,
        vRtrIfQosIngQGrpInstanceId
    }
    STATUS      current
    DESCRIPTION
        "The group of objects supporting management of QoS queue groups on
         Nokia SROS series systems release 10.0."
    ::= { tmnxVRtrGroups 87 }

tmnxVRtrStatV10v0Group           OBJECT-GROUP
    OBJECTS     {
        vRtrBGPVPNAltRoutes,
        vRtrBGPVPNActiveAltRoutes,
        vRtrV6BGPVPNAltRoutes,
        vRtrV6BGPVPNActiveAltRoutes,
        vRtrOSPFAltRoutes,
        vRtrOSPFActiveAltRoutes,
        vRtrV6OSPFAltRoutes,
        vRtrV6OSPFActiveAltRoutes,
        vRtrPeriodicRoutes,
        vRtrPeriodicActiveRoutes,
        vRtrV6PeriodicRoutes,
        vRtrV6PeriodicActiveRoutes
    }
    STATUS      current
    DESCRIPTION
        "The group of objects supporting management of statistics on version
         10.0 Nokia SROS series systems."
    ::= { tmnxVRtrGroups 88 }

tmnxVRtrIfObsoletedV10v0Group    OBJECT-GROUP
    OBJECTS     {
        vRtrImportPolicy1,
        vRtrImportPolicy2,
        vRtrImportPolicy3,
        vRtrImportPolicy4,
        vRtrImportPolicy5,
        vRtrExportPolicy1,
        vRtrExportPolicy2,
        vRtrExportPolicy3,
        vRtrExportPolicy4,
        vRtrExportPolicy5,
        vRtrMvpnExportPolicy1,
        vRtrMvpnExportPolicy2,
        vRtrMvpnExportPolicy3,
        vRtrMvpnExportPolicy4,
        vRtrMvpnExportPolicy5,
        vRtrMvpnImportPolicy1,
        vRtrMvpnImportPolicy2,
        vRtrMvpnImportPolicy3,
        vRtrMvpnImportPolicy4,
        vRtrMvpnImportPolicy5,
        vRtrIfInfoEncrypted,
        vRtrIfQosPolicyId,
        vRtrIfQosQGrp
    }
    STATUS      current
    DESCRIPTION
        "The group of objects obsoleted in version 10.0 of Nokia SROS series
         systems."
    ::= { tmnxVRtrGroups 89 }

tmnxVRtrV10v0Group               OBJECT-GROUP
    OBJECTS     {
        vRtrRowStatus,
        vRtrAdminState,
        vRtrName,
        vRtrMaxNumRoutes,
        vRtrBgpStatus,
        vRtrMplsStatus,
        vRtrRipStatus,
        vRtrRsvpStatus,
        vRtrEcmpMaxRoutes,
        vRtrNewIfIndex,
        vRtrLdpStatus,
        vRtrRouterId,
        vRtrTriggeredPolicy,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrIPv6MaxNumRoutes,
        vRtrIPv6MidRouteThreshold,
        vRtrIPv6HighRouteThreshold,
        vRtrIPv6MaxNumRoutesLogOnly,
        vRtrIPv6IgnoreIcmpRedirect,
        vRtrMcPathMgmtPlcyName,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrHostRoutes,
        vRtrHostActiveRoutes,
        vRtrV6HostRoutes,
        vRtrV6HostActiveRoutes,
        vRtrStatLocalARPEntries,
        vRtrStatStaticARPEntries,
        vRtrStatDynamicARPEntries,
        vRtrStatManagedARPEntries,
        vRtrStatInternalARPEntries,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped,
        vRtrInetStaticRouteNHTunnelName,
        vRtrManagedRoutes,
        vRtrManagedActiveRoutes,
        vRtrAS4Byte,
        vRtrConfederationAS4Byte,
        vRiaInetAddrPreferred,
        vRiaSubscrPrefix,
        vRiaSubscrPrefixType,
        vRiaSubscrHostRoutePopulate,
        vRtrIfAdmLnkLclAddrPreferred,
        vRtrIfAdminLinkLocalAddr,
        vRtrIfAdminLinkLocalAddrType,
        vRtrIfLsrIpLoadBalancing,
        vRtrIfDHCP6ProxyAdminState,
        vRtrIfDHCP6ProxyRenewTimer,
        vRtrIfDHCP6ProxyRebindTimer,
        vRtrIfDHCP6ProxyValidLifetime,
        vRtrIfDHCP6ProxyPrefLifetime,
        vRtrIfDHCP6ProxyApplications,
        vRtrIfDHCP6UserDb,
        vRtrSingleSfmOverloadAdminState,
        vRtrSingleSfmOverloadHldOffTime,
        vRtrSingleSfmOverloadState,
        vRtrSingleSfmOverloadStart,
        vRtrSingleSfmOverloadTime,
        vRtrLdpShortcut,
        vRtrLDPRoutes,
        vRtrLDPActiveRoutes,
        vRtrGrtState,
        vRtrGrtMaxExportRoutes,
        vRtrGrtExportPolicy1,
        vRtrGrtExportPolicy2,
        vRtrGrtExportPolicy3,
        vRtrGrtExportPolicy4,
        vRtrGrtExportPolicy5,
        vRtrVPNLeakRoutes,
        vRtrVPNLeakActiveRoutes,
        vRtrV6VPNLeakRoutes,
        vRtrV6VPNLeakActiveRoutes,
        vRtrInetCidrRouteNextHopType,
        vRtrInetCidrRouteNextHopOwner,
        vRtrInetCidrRouteNHOwnerAuxInfo,
        vRtrInetCidrRteTnlEnabledTime,
        vRtrV6SubMgmtRoutes,
        vRtrV6SubMgmtActiveRoutes,
        vRtrMvpnIpmsiType,
        vRtrMvpnSpmsiType,
        vRtrMobileHostRoutes,
        vRtrMobileHostActiveRoutes,
        vRtrV6MobileHostRoutes,
        vRtrV6MobileHostActiveRoutes,
        vRtrStatTotalBgpTunnels,
        vRtrStatActiveBgpTunnels,
        vRtrMvpnVrfTarget,
        vRtrMvpnVrfExportTarget,
        vRtrMvpnVrfImportTarget,
        vRtrMvpnVrfTargetUnicast,
        vRtrMvpnVrfExportTargetUnicast,
        vRtrMvpnVrfImportTargetUnicast,
        vRtrMvpnImportPolicyUnicast,
        vRtrMvpnExportPolicyUnicast,
        vRtrMvpnCMcastImportRT,
        vRtrGrtMaxIpv6ExportRoutes,
        vRtrInetAggrNextHopType,
        vRtrInetAllCidrRteTnlEnabledTime,
        vRtrInetAllCidrRtNextHopType,
        vRtrInetAllCidrRtNextHopOwner,
        vRtrInetAllCidrRtNHOwnerAuxInfo,
        vRtrInetAllCidrRtBkupNHType,
        vRtrInetAllCidrRtBkupNHOwner,
        vRtrInetAllCidrRtBkupNHOwnAxInfo,
        vRtrInetStaticRouteDescription,
        vRtrInetStaticRoutePaddingSize
    }
    STATUS      obsolete
    DESCRIPTION
        "The group of objects supporting management of transport and virtual
         routers in Nokia SROS series systems."
    ::= { tmnxVRtrGroups 90 }

tmnxVRtrIfV10v0Group             OBJECT-GROUP
    OBJECTS     {
        vRtrIfTotalNumber,
        vRtrIfRowStatus,
        vRtrIfType,
        vRtrIfName,
        vRtrIfPortID,
        vRtrIfEncapValue,
        vRtrIfAdminState,
        vRtrIfOperState,
        vRtrIfAlias,
        vRtrIfPhysicalAddress,
        vRtrIfArpTimeout,
        vRtrIfIcmpMaskReply,
        vRtrIfIcmpRedirects,
        vRtrIfIcmpNumRedirects,
        vRtrIfIcmpRedirectsTime,
        vRtrIfIcmpUnreachables,
        vRtrIfIcmpNumUnreachables,
        vRtrIfIcmpUnreachablesTime,
        vRtrIfIcmpTtlExpired,
        vRtrIfIcmpNumTtlExpired,
        vRtrIfIcmpTtlExpiredTime,
        vRtrIfNtpBroadcast,
        vRtrIfUnnumbered,
        vRtrIfMtu,
        vRtrIfIngressFilterId,
        vRtrIfEgressFilterId,
        vRtrIfDirectedBroadcast,
        vRtrIfMplsStatus,
        vRtrIfUnnumberedIf,
        vRtrIfCflowd,
        vRtrIfVPNClass,
        vRtrIfDescription,
        vRtrIfProtocol,
        vRtrIfTosMarkingTrusted,
        vRtrIfServiceId,
        vRtrIfArpPopulate,
        vRtrIfLastOperStateChange,
        vRtrIfOperMtu,
        vRtrIfGlobalIndex,
        vRtrIfProxyArp,
        vRtrIfProxyArpLocal,
        vRtrIfProxyArpPolicy1,
        vRtrIfProxyArpPolicy2,
        vRtrIfProxyArpPolicy3,
        vRtrIfProxyArpPolicy4,
        vRtrIfProxyArpPolicy5,
        vRtrIfNameIndex,
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfGlobalIndexvRtrID,
        vRtrIfGlobalIndexvRtrIfIndex,
        vRtrIfDelaySeconds,
        vRtrIfDelayUpTimer,
        vRtrIfInitDelayEnable,
        vRtrInetCidrRouteBkupNHType,
        vRtrInetCidrRouteBkupNHOwner,
        vRtrInetCidrRouteBkupNHOwnAxInfo
    }
    STATUS      obsolete
    DESCRIPTION
        "The group of objects supporting management of virtual interfaces on
         version 10.0 Nokia SROS series systems."
    ::= { tmnxVRtrGroups 91 }

tmnxVRtrNotificationV10v0Group   NOTIFICATION-GROUP
    NOTIFICATIONS {
        tmnxVRtrGrtV6ExportLimitReached,
        tmnxVRtrGrtV6RoutesExpLimDropped,
        tmnxVRtrStaticRouteStatusChanged
    }
    STATUS      obsolete
    DESCRIPTION
        "The group of notifications supporting the transport and virtual router
         capabilities on version 10.0 Nokia SROS series systems."
    ::= { tmnxVRtrGroups 92 }

tmnxVRtrFlowSpecV11v0Group       OBJECT-GROUP
    OBJECTS     {
        vRtrIfIngressIpv4Flowspec,
        vRtrIfIngressIpv6Flowspec
    }
    STATUS      current
    DESCRIPTION
        "The group of objects supporting management BGP flowspec on router
         interfaces on version 11.0 Nokia SROS series systems."
    ::= { tmnxVRtrGroups 93 }

tmnxVRtrIfExtV11v0Group          OBJECT-GROUP
    OBJECTS     {
        vRtrIfLagLinkMapProfile,
        vRtrIfLagActivePort,
        vRtrIfIngressStatsEnabled,
        vRtrIfIpv6ReachableTime,
        vRtrIfEnableMacAccounting
    }
    STATUS      obsolete
    DESCRIPTION
        "The group of objects supporting management of transport and virtual
         routers in Nokia SROS series systems."
    ::= { tmnxVRtrGroups 94 }

tmnxVRtrGrtLocalMgmtV10v0Group   OBJECT-GROUP
    OBJECTS     {
        vRtrGrtLocalMgmtState
    }
    STATUS      current
    DESCRIPTION
        "The group of objects supporting management of virtual interfaces on
         version 10.0 Nokia SROS series systems."
    ::= { tmnxVRtrGroups 95 }

tmnxVRtrV11v0Group               OBJECT-GROUP
    OBJECTS     {
        vRtrInetStaticRouteCommunityVal,
        vRtrInetStaticRouteCreationOrig,
        vRtrInetAggrCommunityVal,
        vRtrInetAggrIndirectAddrType,
        vRtrInetAggrIndirectAddr,
        vRtrIpv6ReachableTime,
        vRtrIfLocalPoolAdminState,
        vRtrIfLocalPoolServerName,
        vRtrIfLocalPoolClientApps,
        vRtrIfLocalPoolDefPoolName,
        vRtrIfLocalPoolSecPoolName,
        vRtrRsmTableLastCh,
        vRtrRsmLastCh,
        vRtrRsmRowStatus,
        vRtrRsmGroup,
        vRtrInetStaticRouteDynamicBgp,
        vRtrTunnelNextHopFlags,
        vRtrIfLocalPoolV6ServerName,
        vRtrIfLocalPoolV6ClientApps,
        vRtrInetStaticRouteDynBgpNHType,
        vRtrInetStaticRouteDynBgpNH
    }
    STATUS      obsolete
    DESCRIPTION
        "The group of objects supporting management of transport and virtual
         routers in Nokia SROS series systems."
    ::= { tmnxVRtrGroups 96 }

tmnxVRtrStatV11v0Group           OBJECT-GROUP
    OBJECTS     {
        vRtrOSPFv3Routes,
        vRtrOSPFv3ActiveRoutes,
        vRtrOSPFv3AltRoutes,
        vRtrOSPFv3ActiveAltRoutes,
        vRtrV6ManagedRoutes,
        vRtrV6ManagedActiveRoutes,
        vRtrStatTotalMplsTpTunnels,
        vRtrStatActiveMplsTpTunnels,
        vRtrV6Dhcpv6PdRoutes,
        vRtrV6Dhcpv6PdActiveRoutes,
        vRtrV6Dhcpv6NaRoutes,
        vRtrV6Dhcpv6NaActiveRoutes,
        vRtrV6Dhcpv6TaRoutes,
        vRtrV6Dhcpv6TaActiveRoutes,
        vRtrV6Dhcpv6PdExclRoutes,
        vRtrV6Dhcpv6PdExclActiveRoutes
    }
    STATUS      current
    DESCRIPTION
        "The group of objects supporting management of statistics on version
         11.0 Nokia SROS series systems."
    ::= { tmnxVRtrGroups 97 }

tmnxVRtrMcastV11v0Group          OBJECT-GROUP
    OBJECTS     {
        vRtrIfMcastNetworkDomainName,
        vRtrNetDomainMcastAssociationCnt
    }
    STATUS      current
    DESCRIPTION
        "The group of objects supporting management of virtual interfaces on
         version 11.0 Nokia SROS series systems."
    ::= { tmnxVRtrGroups 98 }

tmnxVRtrIfStatsV11v0Group        OBJECT-GROUP
    OBJECTS     {
        vRtrIfRxV6Pkts,
        vRtrIfRxV6PktsLow32,
        vRtrIfRxV6PktsHigh32,
        vRtrIfRxV6Bytes,
        vRtrIfRxV6BytesLow32,
        vRtrIfRxV6BytesHigh32,
        vRtrIfV6uRPFCheckFailPkts,
        vRtrIfV6uRPFCheckFailPktsLow32,
        vRtrIfV6uRPFCheckFailPktsHigh32,
        vRtrIfV6uRPFCheckFailBytes,
        vRtrIfV6uRPFCheckFailBytesLow32,
        vRtrIfV6uRPFCheckFailBytesHigh32,
        vRtrIfRxV4Pkts,
        vRtrIfRxV4Bytes,
        vRtrIfV4uRPFCheckFailPkts,
        vRtrIfV4uRPFCheckFailBytes
    }
    STATUS      current
    DESCRIPTION
        "The group of objects supporting IP interface statistics added in
         release 11.0 of Nokia SROS series systems."
    ::= { tmnxVRtrGroups 99 }

tmnxVRtrIfDHCPRelayV11v0Group    OBJECT-GROUP
    OBJECTS     {
        vRtrIfDHCPRelayUnicastMsg,
        vRtrIfDHCPRelayClientPktsProxUDB
    }
    STATUS      current
    DESCRIPTION
        "The group of objects supporting management of DHCP Relay on virtual
         interfaces on version 11.0 Nokia SROS series systems"
    ::= { tmnxVRtrGroups 100 }

tmnxVrtrIfDCpuProtV11v0Group     OBJECT-GROUP
    OBJECTS     {
        vRtrIfDCpuProtPolicy,
        vRtrIfDcpFpStaticState,
        vRtrIfDcpFpStaticExcdCount,
        vRtrIfDcpFpStaticExcdCountHi,
        vRtrIfDcpFpStaticExcdCountLo,
        vRtrIfDcpFpStaticHoldDown,
        vRtrIfDcpFpStaticDetectionTime,
        vRtrIfDcpFpDynState,
        vRtrIfDcpFpDynExcdCount,
        vRtrIfDcpFpDynExcdCountHi,
        vRtrIfDcpFpDynExcdCountLo,
        vRtrIfDcpFpDynHoldDown,
        vRtrIfDcpFpDynDetectionTime,
        vRtrIfDcpFpDynAllocated,
        vRtrIfDcpFpLocMonState,
        vRtrIfDcpFpLocMonExcdCount,
        vRtrIfDcpFpLocMonExcdCountHi,
        vRtrIfDcpFpLocMonExcdCountLo,
        vRtrIfDcpFpLocMonAllDynAlloc
    }
    STATUS      current
    DESCRIPTION
        "The group of additional objects supporting Distributed CPU Protection
         feature for virtual interfaces on Nokia SROS series release 11.0
         systems."
    ::= { tmnxVRtrGroups 102 }

tmnxVrtrIfDHCP6ProxyDuidGroup    OBJECT-GROUP
    OBJECTS     {
        vRtrIfDHCP6ProxyDuidTableLastCh,
        vRtrIfDHCP6ProxyDuidLastChanged,
        vRtrIfDHCP6ProxyDuidTypeCode,
        vRtrIfDHCP6ProxyDuidEnNumber,
        vRtrIfDHCP6ProxyDuidEnIdData,
        vRtrIfDHCP6ProxyDuidEnIdDataType
    }
    STATUS      current
    DESCRIPTION
        "The group of objects supporting DHCP Unique Identifier (DUID) feature
         for virtual interfaces on Nokia SROS series."
    ::= { tmnxVRtrGroups 103 }

tmnxVrtrDcpNotifyObjsV11v0Group  OBJECT-GROUP
    OBJECTS     {
        vRtrIfDcpTimeEventOccured
    }
    STATUS      current
    DESCRIPTION
        "The group of objects supporting management of Distributed CPU
         Protection feature for virtual interfaces on version 11.0 Nokia SROS
         series systems."
    ::= { tmnxVRtrGroups 104 }

tmnxVrtrIfDcpNotifyV11v0Group    NOTIFICATION-GROUP
    NOTIFICATIONS {
        vRtrIfDcpStaticExcd,
        vRtrIfDcpDynamicExcd,
        vRtrIfDcpStaticHoldDownStart,
        vRtrIfDcpDynamicHoldDownStart,
        vRtrIfDcpStaticHoldDownEnd,
        vRtrIfDcpDynamicHoldDownEnd,
        vRtrIfDcpStaticConform,
        vRtrIfDcpDynamicConform,
        vRtrIfDcpLocMonExcd,
        vRtrIfDcpLocMonExcdDynResource,
        vRtrIfDcpLocMonExcdAllDynAlloc,
        vRtrIfDcpLocMonExcdAllDynFreed,
        vRtrIfDcpDynamicEnforceAlloc,
        vRtrIfDcpDynamicEnforceFreed
    }
    STATUS      current
    DESCRIPTION
        "The group of notifications supporting management of Distributed CPU
         Protection feature for virtual interfaces on version 11.0 Nokia SROS
         series systems."
    ::= { tmnxVRtrGroups 105 }

tmnxVRtrIfMacStatsV11v0Group     OBJECT-GROUP
    OBJECTS     {
        vRtrIfMacAccountingInOctets,
        vRtrIfMacAccountingInOctetsL,
        vRtrIfMacAccountingInOctetsH,
        vRtrIfMacAccountingInFrames,
        vRtrIfMacAccountingInFramesL,
        vRtrIfMacAccountingInFramesH,
        vRtrIfMacAccountingOutOctets,
        vRtrIfMacAccountingOutOctetsL,
        vRtrIfMacAccountingOutOctetsH,
        vRtrIfMacAccountingOutFrames,
        vRtrIfMacAccountingOutFramesL,
        vRtrIfMacAccountingOutFramesH
    }
    STATUS      current
    DESCRIPTION
        "The group of objects supporting IP interface MAC statistics added in
         release 11.0 of Nokia SROS series systems."
    ::= { tmnxVRtrGroups 106 }

tmnxVRtrIpv6RtrAdvertV11v0Group  OBJECT-GROUP
    OBJECTS     {
        vRtrIpv6RtrAdvertCreationOrigin
    }
    STATUS      current
    DESCRIPTION
        "The group of objects supporting management of extended Router
         Advertisement features for IPv6 on Nokia SROS series systems."
    ::= { tmnxVRtrGroups 107 }

tmnxVRtrBfdV11v0Group            OBJECT-GROUP
    OBJECTS     {
        vRtrIfBfdExtTableLastChanged,
        vRtrIfBfdExtAdminState,
        vRtrIfBfdExtTransmitInterval,
        vRtrIfBfdExtReceiveInterval,
        vRtrIfBfdExtMultiplier,
        vRtrIfBfdExtEchoInterval,
        vRtrIfBfdExtType,
        vRtrIfBfdSessExtOperState,
        vRtrIfBfdSessExtState,
        vRtrIfBfdSessExtOperFlags,
        vRtrIfBfdSessExtMesgRecv,
        vRtrIfBfdSessExtMesgSent,
        vRtrIfBfdSessExtLastDownTime,
        vRtrIfBfdSessExtLastUpTime,
        vRtrIfBfdSessExtUpCount,
        vRtrIfBfdSessExtDownCount,
        vRtrIfBfdSessExtLclDisc,
        vRtrIfBfdSessExtRemDisc,
        vRtrIfBfdSessExtProtocols,
        vRtrIfBfdSessExtTxInterval,
        vRtrIfBfdSessExtRxInterval,
        vRtrIfBfdSessExtType,
        vRtrIfBfdSessExtVerMismatch,
        vRtrIfBfdSessExtTimeSinceLastRx,
        vRtrIfBfdSessExtTimeSinceLastTx,
        vRtrIfBfdSessExtRemoteLspNum,
        vRtrIfBfdSessExtRemoteTunnelNum,
        vRtrIfBfdSessExtRemoteNodeId,
        vRtrIfBfdSessExtRemoteGlobalId,
        vRtrIfBfdSessExtLspPathTunnelId,
        vRtrIfBfdSessExtLspPathId
    }
    STATUS      current
    DESCRIPTION
        "The group of objects supporting Bi-directional Forwarding Detection on
         version 11.0 Nokia SROS series systems."
    ::= { tmnxVRtrGroups 108 }

tmnxVRtrBfdSessionObsoletedGroup OBJECT-GROUP
    OBJECTS     {
        vRtrIfBfdSessionOperState,
        vRtrIfBfdSessionState,
        vRtrIfBfdSessionOperFlags,
        vRtrIfBfdSessionMesgRecv,
        vRtrIfBfdSessionMesgSent,
        vRtrIfBfdSessionLastDownTime,
        vRtrIfBfdSessionLastUpTime,
        vRtrIfBfdSessionUpCount,
        vRtrIfBfdSessionDownCount,
        vRtrIfBfdSessionLclDisc,
        vRtrIfBfdSessionRemDisc,
        vRtrIfBfdSessionProtocols,
        vRtrIfBfdSessionTxInterval,
        vRtrIfBfdSessionRxInterval,
        vRtrIfBfdSessionType,
        vRtrIfBfdSessionVerMismatch,
        vRtrIfBfdSessionTimeSinceLastRx,
        vRtrIfBfdSessionTimeSinceLastTx
    }
    STATUS      current
    DESCRIPTION
        "The group of obsolete objects for Bi-directional Forwarding Detection
         on Nokia SROS series systems 11.0 Release."
    ::= { tmnxVRtrGroups 109 }

tmnxVRtrObsoleteNotifV11v0Group  NOTIFICATION-GROUP
    NOTIFICATIONS {
        tmnxVRtrBfdSessionDown,
        tmnxVRtrBfdSessionUp,
        tmnxVRtrBfdSessionDeleted,
        tmnxVRtrBfdSessionProtChange,
        tmnxVRtrBfdNoCpmNpResources
    }
    STATUS      current
    DESCRIPTION
        "The group of obsolete notifications for the transport and virtual
         router capabilities on Nokia SROS series systems 11.0 Release."
    ::= { tmnxVRtrGroups 110 }

tmnxVRtrNotificationV11v0Group   NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrIPv6MidRouteTCA,
        tmnxVRtrIPv6HighRouteTCA,
        tmnxVRtrIPv6HighRouteCleared,
        tmnxVRtrStaticRouteCPEStatus,
        tmnxVRtrManagedRouteAddFailed,
        tmnxVRtrFibOccupancyThreshold,
        tmnxVRtrInetAddressAttachFailed,
        tmnxVRtrSingleSfmOverloadStateCh,
        tmnxVRtrGrtExportLimitReached,
        tmnxVRtrGrtRoutesExpLimitDropped,
        tmnxVRtrIfLdpSyncTimerStart,
        tmnxVRtrIfLdpSyncTimerStop,
        tmnxVRtrBfdSessExtDown,
        tmnxVRtrBfdSessExtUp,
        tmnxVRtrBfdSessExtDeleted,
        tmnxVRtrBfdSessExtProtChange,
        tmnxVRtrBfdExtNoCpmNpResources,
        tmnxVRtrDnsFault,
        tmnxVRtrMacAcctLimitReached,
        tmnxVRtrMacAcctLimitCleared,
        tmnxVRtrNgBfdSessDown,
        tmnxVRtrNgBfdSessUp,
        tmnxVRtrNgBfdSessDeleted,
        tmnxVRtrNgBfdSessProtChange,
        tmnxVRtrNgBfdNoCpmNpResources
    }
    STATUS      obsolete
    DESCRIPTION
        "The group of notifications supporting the transport and virtual router
         capabilities on version 11.0 Nokia SROS series systems."
    ::= { tmnxVRtrGroups 111 }

tmnxVRtrIfDHCP6V11v0Group        OBJECT-GROUP
    OBJECTS     {
        vRtrIfDHCP6RoutePopulatePd,
        vRtrIfDHCP6RoutePopulateNa,
        vRtrIfDHCP6RoutePopulateTa
    }
    STATUS      current
    DESCRIPTION
        "The group of new objects supporting management of DHCPv6 since version
         11.0 Nokia SROS series systems."
    ::= { tmnxVRtrGroups 112 }

tmnxVRtrNotifyObjsV11v0Group     OBJECT-GROUP
    OBJECTS     {
        vRtrNotifTruthValue
    }
    STATUS      current
    DESCRIPTION
        "The group of notification objects supporting virtual router instances
         added in release 11.0 of Nokia SROS series systems."
    ::= { tmnxVRtrGroups 113 }

tmnxVRtrV12v0Group               OBJECT-GROUP
    OBJECTS     {
        vRtrRipNgStatus,
        vRtrIfTcpMss,
        vRtrIfIpv6TcpMss,
        vRtrIfuRPFIgnoreDefault,
        vRtrIfIpv6uRPFIgnoreDefault,
        tmnxVrtrIfAdminGrpTableLastCh,
        tmnxVrtrIfAdminGroupRowStatus,
        tmnxVrtrIfAdminGroupLastCh,
        tmnxVrtrIfSrlgGrpTableLastCh,
        tmnxVrtrIfSrlgGroupRowStatus,
        tmnxVrtrIfSrlgGroupLastCh,
        vRtrInetStaticRouteValidateNH,
        vRtrIfDHCPPythonPolicy,
        vRtrIfDHCPVirtualSubnet,
        vRtrInetStaticRouteSrcClassIndex,
        vRtrInetStaticRouteDstClassIndex,
        vRtrIpv6NdCacheStaleTime,
        vRtrInetCidrRouteSrcClassIndex,
        vRtrInetCidrRouteDstClassIndex,
        vRtrInetAllCidrRtSrcClassIndex,
        vRtrInetAllCidrRtDstClassIndex,
        vRiaInetAddressSendCgaModifier
    }
    STATUS      current
    DESCRIPTION
        "The group of objects supporting management of transport and virtual
         routers in Nokia SROS series systems."
    ::= { tmnxVRtrGroups 114 }

tmnxVRtrIfDHCP6V12v0Group        OBJECT-GROUP
    OBJECTS     {
        vRtrIfDHCP6RoutePopulateExcl,
        vRtrIfDHCP6PythonPolicy
    }
    STATUS      current
    DESCRIPTION
        "The group of new objects supporting management of DHCPv6 since version
         12.0 Nokia SROS series systems."
    ::= { tmnxVRtrGroups 115 }

tmnxVRtrExportBgpVpnV11v0Group   OBJECT-GROUP
    OBJECTS     {
        vRtrAllowExportBgpVpn
    }
    STATUS      current
    DESCRIPTION
        "The group of new objects supporting DC Inter connect feature in Nokia
         SROS series systems."
    ::= { tmnxVRtrGroups 116 }

tmnxVRtrGenerateICMPV12v0Group   OBJECT-GROUP
    OBJECTS     {
        vRtrInetStaticRouteGenerateIcmp,
        vRtrInetAggrGenerateIcmp
    }
    STATUS      current
    DESCRIPTION
        "The group of new objects supporting ICMP Unreachable Option for Static
         or Aggregate Black-Hole Routes in Nokia SROS series systems."
    ::= { tmnxVRtrGroups 117 }

tmnxVRtrIfSendV12v0Group         OBJECT-GROUP
    OBJECTS     {
        vRtrSendKeyRollover,
        vRtrIfSendAdminState,
        vRtrIfSendAllowUnsecuredMsgs,
        vRtrIfSendCgaSecurityParameter,
        vRtrIfSendCgaVerificationMinbits,
        vRtrIfSendLinkLocalCgaModifier,
        vRtrIfSendLastChanged,
        vRtrIfSendTableLastChanged,
        vRtrIpNetToPhysicalSecureNd
    }
    STATUS      current
    DESCRIPTION
        "The group of new objects supporting SEcure Neighbor Discovery (SEND)
         in Nokia SROS series systems."
    ::= { tmnxVRtrGroups 118 }

tmnxvRtrIfAttributeGroup         OBJECT-GROUP
    OBJECTS     {
        tmnxAdminGroupTblLastCh,
        tmnxAdminGrpRowStatus,
        tmnxAdminGrpRowLstChng,
        tmnxAdminGrpValue,
        tmnxSrlgGroupTblLastCh,
        tmnxSrlgGrpRowStatus,
        tmnxSrlgGrpRowLstChng,
        tmnxSrlgGrpValue
    }
    STATUS      current
    DESCRIPTION
        "The group of objects providing configuration of interface attributes
         on Nokia SROS series systems."
    ::= { tmnxVRtrGroups 119 }

tmnxVRtrIfExtV12v0Group          OBJECT-GROUP
    OBJECTS     {
        vRtrIfLagLinkMapProfile,
        vRtrIfLagActivePort,
        vRtrIfIngressStatsEnabled,
        vRtrIfIpv6ReachableTime,
        vRtrIfIpv6DadDisable,
        vRtrIfEnableMacAccounting,
        vRtrIfIpv6NdCacheStaleTime,
        vRtrIfTmsOffRampIgrVrf
    }
    STATUS      obsolete
    DESCRIPTION
        "A group of objects supporting management of virtual router instance
         interfaces in version 12.0 of the Nokia SROS series systems."
    ::= { tmnxVRtrGroups 121 }

tmnxVRtrCreation12v0Group        OBJECT-GROUP
    OBJECTS     {
        vRiaCreationOrigin,
        vRtrVrfPlcyCreationOrigin
    }
    STATUS      current
    DESCRIPTION
        "The group of objects supporting management of service creation
         entities for release 12.0 on Nokia SROS series systems."
    ::= { tmnxVRtrGroups 122 }

tmnxVRtrIPsecStatGroup           OBJECT-GROUP
    OBJECTS     {
        vRtrIPsecRoutes,
        vRtrIPsecActiveRoutes
    }
    STATUS      current
    DESCRIPTION
        "The group of objects supporting management of statistics for IPsec
         routes in Nokia SROS series systems."
    ::= { tmnxVRtrGroups 123 }

tmnxVRtrVirtualCPE12v0Group      OBJECT-GROUP
    OBJECTS     {
        vRtrAllowSnmpAccess
    }
    STATUS      current
    DESCRIPTION
        "The group of objects supporting management of service creation
         entities for release 12.0 on Nokia SROS series systems."
    ::= { tmnxVRtrGroups 124 }

tmnxVRtrBgpEvpn12v0Group         OBJECT-GROUP
    OBJECTS     {
        vRtrStatBGPEVPNARPEntries
    }
    STATUS      current
    DESCRIPTION
        "The group of objects supporting management of service creation
         entities for release 12.0 on Nokia SROS series systems."
    ::= { tmnxVRtrGroups 125 }

tmnxVRtrLagHashLoadBal12v0Group  OBJECT-GROUP
    OBJECTS     {
        vRtrIfTeidLoadBalancing
    }
    STATUS      current
    DESCRIPTION
        "The group of objects supporting management of virtual interfaces on
         version 12.0 Nokia SROS series systems."
    ::= { tmnxVRtrGroups 126 }

tmnxVRtrPlcyAcctTempl12v0Group   OBJECT-GROUP
    OBJECTS     {
        vRtrPlcyAcctTemplTblLastChanged,
        vRtrPlcyAcctTemplateRowStatus,
        vRtrPlcyAcctTemplateLastChgd,
        vRtrPlcyAcctSrcClassTblLstChgd,
        vRtrPlcyAcctSrcClassRowStatus,
        vRtrPlcyAcctSrcClassLastChgd,
        vRtrPlcyAcctDestClassTblLstChgd,
        vRtrPlcyAcctDestClassRowStatus,
        vRtrPlcyAcctDestClassLastChgd,
        vRtrIfPlcyAcctTemplateName,
        vRtrPlcyAcctIfStatsTblLstChgd,
        vRtrPlcyAcctRxFwdPkts,
        vRtrPlcyAcctRxFwdBytes,
        vRtrPlcyAcctRxIncompleteCnt
    }
    STATUS      current
    DESCRIPTION
        "The group of objects supporting management of bgp policy accounting
         for release 12.0 on Nokia SROS series systems."
    ::= { tmnxVRtrGroups 127 }

tmnxVRtrLagEgrLoadBal12v0Group   OBJECT-GROUP
    OBJECTS     {
        vRtrIfEgrIpLoadBalancing
    }
    STATUS      current
    DESCRIPTION
        "The group of objects supporting management of virtual interfaces on
         version 12.0 Nokia SROS series systems."
    ::= { tmnxVRtrGroups 128 }

tmnxVRtrVccvBfd12v0Group         OBJECT-GROUP
    OBJECTS     {
        vRtrIfBfdSessSdpBindIndex,
        vRtrIfBfdSessExtSvcId,
        vRtrIfBfdSessExtSdpBindId
    }
    STATUS      current
    DESCRIPTION
        "The group of objects supporting management of BFD sessions on virtual
         interfaces on version 12.0 Nokia SROS series systems."
    ::= { tmnxVRtrGroups 129 }

tmnxVRtrRAV12v0Group             OBJECT-GROUP
    OBJECTS     {
        vRtrRARowStatus,
        vRtrRADnsOptServer1,
        vRtrRADnsOptServer2,
        vRtrRADnsOptServer3,
        vRtrRADnsOptServer4,
        vRtrRADnsOptRdnssLtime,
        vRtrRAIfRowStatus,
        vRtrRAIfDnsOptServer1,
        vRtrRAIfDnsOptServer2,
        vRtrRAIfDnsOptServer3,
        vRtrRAIfDnsOptServer4,
        vRtrRAIfDnsOptRdnssLtime,
        vRtrRAIfDnsOptInclDns
    }
    STATUS      current
    DESCRIPTION
        "The group of objects supporting management of router advertisement
         entities for release 12.0 on Nokia SROS series systems."
    ::= { tmnxVRtrGroups 130 }

tmnxVRtrIcmpTunnelingGroup       OBJECT-GROUP
    OBJECTS     {
        vRtrIcmpTunneling,
        vRtrTTLPropVprnLocal,
        vRtrTTLPropVprnTransit,
        vRtrTTLPropLabelRouteLocal,
        vRtrTTLPropLabelRouteTransit,
        vRtrTTLPropLsrLabelRoute,
        vRtrSvcTTLPropVprnLocal,
        vRtrSvcTTLPropVprnTransit,
        vRtrTTLPropTblLstChgd,
        vRtrSvcTTLPropTblLstChgd
    }
    STATUS      current
    DESCRIPTION
        "The group of objects supporting ICMP tunneling feature for release
         12.0 on Nokia SROS series systems."
    ::= { tmnxVRtrGroups 132 }

tmnxVRtrAggrRouteV12v0Group      OBJECT-GROUP
    OBJECTS     {
        vRtrInetAggrDescription
    }
    STATUS      current
    DESCRIPTION
        "The group of new objects supporting the ability to add text
         description to aggregate routes in version 12.0 of Nokia SROS series
         systems."
    ::= { tmnxVRtrGroups 133 }

tmnxVRtrBgpEvpnIpRoutes12v0Group OBJECT-GROUP
    OBJECTS     {
        vRtrStatBGPEvpnRoutes,
        vRtrStatBGPEvpnActiveRoutes,
        vRtrV6StatBGPEvpnRoutes,
        vRtrV6StatBGPEvpnActiveRoutes,
        vRtrFibStatBGPEvpnRoutes,
        vRtrFibStatV6BGPEvpnRoutes
    }
    STATUS      obsolete
    DESCRIPTION
        "The group of objects supporting management of BGP EVPN IP route
         entities for release 12.0 on Nokia SROS series systems."
    ::= { tmnxVRtrGroups 134 }

tmnxVRtrConfExtV12v0Group        OBJECT-GROUP
    OBJECTS     {
        vRtrMvpnMdSourceAddrType,
        vRtrMvpnMdSourceAddress
    }
    STATUS      current
    DESCRIPTION
        "The group of new objects supporting management of transport and
         virtual routers new on version 12.0 Nokia SROS series systems."
    ::= { tmnxVRtrGroups 135 }

tmnxVRtrStickyHashEcmp12v0Group  OBJECT-GROUP
    OBJECTS     {
        vRtrInetCidrRouteOperFlags,
        vRtrInetAllCidrRtOperFlags
    }
    STATUS      current
    DESCRIPTION
        "The group of objects supporting Sticky Hash Ecmp feature for release
         12.0 on Nokia SROS series systems."
    ::= { tmnxVRtrGroups 136 }

tmnxVRtrV13v0Group               OBJECT-GROUP
    OBJECTS     {
        tmnxSrlgGrpPenaltyWeight,
        vRtrDisableSelectiveFib,
        vRtrWeightedEcmp,
        vRtrIfDHCPRelaySiaddrOvrAddrType,
        vRtrIfDHCPRelaySiaddrOvrAddr,
        vRtrInetCidrRouteNextHopWeight,
        vRtrInetCidrRteTnlNextHopWeight,
        vRtrRowStatus,
        vRtrAdminState,
        vRtrName,
        vRtrMaxNumRoutes,
        vRtrBgpStatus,
        vRtrMplsStatus,
        vRtrRipStatus,
        vRtrRsvpStatus,
        vRtrEcmpMaxRoutes,
        vRtrNewIfIndex,
        vRtrLdpStatus,
        vRtrRouterId,
        vRtrTriggeredPolicy,
        vRtrRouteDistinguisher,
        vRtrMidRouteThreshold,
        vRtrHighRouteThreshold,
        vRtrIllegalLabelThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrIPv6MaxNumRoutes,
        vRtrIPv6MidRouteThreshold,
        vRtrIPv6HighRouteThreshold,
        vRtrIPv6MaxNumRoutesLogOnly,
        vRtrIPv6IgnoreIcmpRedirect,
        vRtrMcPathMgmtPlcyName,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrHostRoutes,
        vRtrHostActiveRoutes,
        vRtrV6HostRoutes,
        vRtrV6HostActiveRoutes,
        vRtrStatLocalARPEntries,
        vRtrStatStaticARPEntries,
        vRtrStatDynamicARPEntries,
        vRtrStatManagedARPEntries,
        vRtrStatInternalARPEntries,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped,
        vRtrInetStaticRouteNHTunnelName,
        vRtrManagedRoutes,
        vRtrManagedActiveRoutes,
        vRtrAS4Byte,
        vRtrConfederationAS4Byte,
        vRiaInetAddrPreferred,
        vRiaSubscrPrefix,
        vRiaSubscrPrefixType,
        vRiaSubscrHostRoutePopulate,
        vRtrIfAdmLnkLclAddrPreferred,
        vRtrIfAdminLinkLocalAddr,
        vRtrIfAdminLinkLocalAddrType,
        vRtrIfLsrIpLoadBalancing,
        vRtrIfDHCP6ProxyAdminState,
        vRtrIfDHCP6ProxyRenewTimer,
        vRtrIfDHCP6ProxyRebindTimer,
        vRtrIfDHCP6ProxyValidLifetime,
        vRtrIfDHCP6ProxyPrefLifetime,
        vRtrIfDHCP6ProxyApplications,
        vRtrIfDHCP6UserDb,
        vRtrSingleSfmOverloadAdminState,
        vRtrSingleSfmOverloadHldOffTime,
        vRtrSingleSfmOverloadState,
        vRtrSingleSfmOverloadStart,
        vRtrSingleSfmOverloadTime,
        vRtrLDPRoutes,
        vRtrLDPActiveRoutes,
        vRtrGrtState,
        vRtrGrtMaxExportRoutes,
        vRtrGrtExportPolicy1,
        vRtrGrtExportPolicy2,
        vRtrGrtExportPolicy3,
        vRtrGrtExportPolicy4,
        vRtrGrtExportPolicy5,
        vRtrVPNLeakRoutes,
        vRtrVPNLeakActiveRoutes,
        vRtrV6VPNLeakRoutes,
        vRtrV6VPNLeakActiveRoutes,
        vRtrInetCidrRouteNextHopType,
        vRtrInetCidrRouteNextHopOwner,
        vRtrInetCidrRouteNHOwnerAuxInfo,
        vRtrInetCidrRteTnlEnabledTime,
        vRtrV6SubMgmtRoutes,
        vRtrV6SubMgmtActiveRoutes,
        vRtrMvpnIpmsiType,
        vRtrMvpnSpmsiType,
        vRtrMobileHostRoutes,
        vRtrMobileHostActiveRoutes,
        vRtrV6MobileHostRoutes,
        vRtrV6MobileHostActiveRoutes,
        vRtrStatTotalBgpTunnels,
        vRtrStatActiveBgpTunnels,
        vRtrMvpnVrfTarget,
        vRtrMvpnVrfExportTarget,
        vRtrMvpnVrfImportTarget,
        vRtrMvpnVrfTargetUnicast,
        vRtrMvpnVrfExportTargetUnicast,
        vRtrMvpnVrfImportTargetUnicast,
        vRtrMvpnImportPolicyUnicast,
        vRtrMvpnExportPolicyUnicast,
        vRtrMvpnCMcastImportRT,
        vRtrGrtMaxIpv6ExportRoutes,
        vRtrInetAggrNextHopType,
        vRtrInetAllCidrRteTnlEnabledTime,
        vRtrInetAllCidrRtNextHopType,
        vRtrInetAllCidrRtNextHopOwner,
        vRtrInetAllCidrRtNHOwnerAuxInfo,
        vRtrInetAllCidrRtBkupNHType,
        vRtrInetAllCidrRtBkupNHOwner,
        vRtrInetAllCidrRtBkupNHOwnAxInfo,
        vRtrInetStaticRouteDescription,
        vRtrInetStaticRoutePaddingSize,
        vRtrV6LDPRoutes,
        vRtrV6LDPActiveRoutes
    }
    STATUS      obsolete
    DESCRIPTION
        "The group of objects supporting management of transport and virtual
         Routers new on release 13.0 in Nokia SROS series systems."
    ::= { tmnxVRtrGroups 137 }

tmnxVRtrNotifyObjsNHRvplsArpGrp  OBJECT-GROUP
    OBJECTS     {
        tmnxVRtrMaxNHRvplsARPEntries
    }
    STATUS      current
    DESCRIPTION
        "The group of notification objects supporting virtual router instances
         added for Next Hop Rvpls ARP in Nokia SROS series systems."
    ::= { tmnxVRtrGroups 138 }

tmnxVRtrNotificationNHRvplsArpGr NOTIFICATION-GROUP
    NOTIFICATIONS {
        tmnxVRtrNHRvplsARPHighUsage,
        tmnxVRtrNHRvplsARPExhaust,
        tmnxVRtrNHRvplsARPHighUsageClr
    }
    STATUS      current
    DESCRIPTION
        "The group of notifications added for supporting virtual router
         instances added for Next Hop Rvpls ARP in Nokia SROS series systems."
    ::= { tmnxVRtrGroups 139 }

tmnxVRtrTunnelExtTableV13v0Group OBJECT-GROUP
    OBJECTS     {
        vRtrInetTunnelMetric,
        vRtrInetTunnelAge,
        vRtrInetTunnelNextHopFlags,
        vRtrInetTunnelLspBandwidth,
        vRtrInetTunnelMTU,
        vRtrInetTunnelLspWeight,
        vRtrInetTunnelLspId,
        vRtrInetTunnelRelativeMetric,
        vRtrInetTunnelFlags,
        vRtrInetTunnelLabel,
        vRtrInetTunnelBypassLabel
    }
    STATUS      obsolete
    DESCRIPTION
        "The group of objects supporting management of transport and virtual
         Routers new on release 13.0 in Nokia SROS series systems."
    ::= { tmnxVRtrGroups 141 }

tmnxVRtrMcastSpmsiEnhV13v0Group  OBJECT-GROUP
    OBJECTS     {
        vRtrMvpnWildcardSpmsi,
        vRtrMvpnWildcardSpmsiBsrSig
    }
    STATUS      current
    DESCRIPTION
        "The group of objects supporting management of transport and virtual
         Routers new on release 13.0 in Nokia SROS series systems."
    ::= { tmnxVRtrGroups 142 }

tmnxVRtrHoldDownTimeV12v0Group   OBJECT-GROUP
    OBJECTS     {
        vRtrStaticRouteHoldDownEnable,
        vRtrStaticRouteHoldDownInitial,
        vRtrStaticRouteHoldDownMultiplr,
        vRtrStaticRouteHoldDownMaxValue,
        vRtrInetStaticRouteHoldTimeLeft
    }
    STATUS      current
    DESCRIPTION
        "The group of objects supporting Hold Down Time for static routes on
         Nokia SROS series systems."
    ::= { tmnxVRtrGroups 143 }

tmnxVRtrLoadBalEnhV13v0Group     OBJECT-GROUP
    OBJECTS     {
        vRtrIfSpiLoadBalancing
    }
    STATUS      current
    DESCRIPTION
        "The group of objects supporting management of virtual interfaces on
         version 13.0 Nokia SROS series systems."
    ::= { tmnxVRtrGroups 144 }

tmnxVRtrInetSRIndirectV13v0Group OBJECT-GROUP
    OBJECTS     {
        vRtrInetSRIndirectTunnelLdp,
        vRtrInetSRIndirectTunnelRsvpTe,
        vRtrInetSRIndirectTunnelDisalIgp,
        vRtrInetSRIndirectLspRowStatus,
        vRtrInetSRIndirectTunResStatus
    }
    STATUS      current
    DESCRIPTION
        "The group of objects supporting management of transport and virtual
         Routers new on release 13.0 in Nokia SROS series systems."
    ::= { tmnxVRtrGroups 145 }

tmnxVRtrIfExtIfArpRetryTimerGrp  OBJECT-GROUP
    OBJECTS     {
        vRtrIfArpRetryTimer
    }
    STATUS      current
    DESCRIPTION
        "The group of objects supporting the virtual interfaces in Nokia SROS
         series systems."
    ::= { tmnxVRtrGroups 146 }

tmnxVRtrBgpAutoRDGroup           OBJECT-GROUP
    OBJECTS     {
        vRtrBgpAutoRD,
        vRtrBgpOperRD,
        vRtrBgpOperRDType
    }
    STATUS      current
    DESCRIPTION
        "The group of objects supporting BGP auto route-distinguisher feature
         in Nokia SROS series systems."
    ::= { tmnxVRtrGroups 147 }

tmnxVRtrTunnelTableStatGroup     OBJECT-GROUP
    OBJECTS     {
        vRtrStatTotalIsisTunnels,
        vRtrStatActiveIsisTunnels,
        vRtrStatTotalOspfTunnels,
        vRtrStatActiveOspfTunnels
    }
    STATUS      current
    DESCRIPTION
        "The group of objects supporting the virtual interfaces in Nokia SROS
         series systems."
    ::= { tmnxVRtrGroups 148 }

tmnxVRtrIfDHCPRelayV13v0Group    OBJECT-GROUP
    OBJECTS     {
        vRtrIfDHCPRelayClientPktsProxNq,
        vRtrIfDHCP6FilterId,
        vRtrIfDHCP6SnpgAdminState
    }
    STATUS      current
    DESCRIPTION
        "The group of objects supporting management of DHCP Relay on virtual
         interfaces added in version 13.0 of Nokia SROS series systems."
    ::= { tmnxVRtrGroups 149 }

tmnxVRtrLdpIpv613v0Group         OBJECT-GROUP
    OBJECTS     {
        vRtrLdpShortcutType
    }
    STATUS      current
    DESCRIPTION
        "The group of objects supporting management of LDP IPv6 in Nokia SROS
         series systems."
    ::= { tmnxVRtrGroups 150 }

tmnxVRtrIfLagPerLinkHashGroup    OBJECT-GROUP
    OBJECTS     {
        vRtrIfLagPerLinkHashLastChgd,
        vRtrIfLagPerLinkHashClass,
        vRtrIfLagPerLinkHashWeight
    }
    STATUS      current
    DESCRIPTION
        "The group of objects supporting management of per link hash on lag
         feature on Nokia SROS series systems."
    ::= { tmnxVRtrGroups 151 }

tmnxVRtrCidrNextHopOwnInstGroup  OBJECT-GROUP
    OBJECTS     {
        vRtrInetCidrRouteNextHopOwnInst,
        vRtrInetCidrRouteBkupNHOwnInst,
        vRtrInetAllCidrRtNextHopOwnInst,
        vRtrInetAllCidrRtBkupNHOwnInst
    }
    STATUS      current
    DESCRIPTION
        "The group of objects supporting the route table next hop instances on
         Nokia SROS series systems."
    ::= { tmnxVRtrGroups 152 }

tmnxVRtrIpV13v0Group             OBJECT-GROUP
    OBJECTS     {
        vRiaRowStatus,
        vRiaIpAddress,
        vRiaNetMask,
        vRiaBcastAddrFormat,
        vRiaReasmMaxSize,
        vRiaIgpInhibit,
        vRiaInetAddressType,
        vRiaInetAddress,
        vRiaInetPrefixLen,
        vRiaInetAddrState,
        vRiaInetEui64,
        vRiaInetOperAddress,
        vRiaInetGwAddressType,
        vRiaInetGwAddress,
        vRiaInetRemoteIpType,
        vRiaInetRemoteIp,
        vRtrIpCidrRouteLastEnabledTime,
        vRtrIpCidrRoutePreference,
        vRtrIpCidrRouteMetric,
        vRtrStaticRouteDest,
        vRtrStaticRouteMask,
        vRtrStaticRouteIndex,
        vRtrStaticRouteNumber,
        vRtrStaticRouteRowStatus,
        vRtrStaticRouteLastEnabledTime,
        vRtrStaticRouteStatus,
        vRtrStaticRouteStaticType,
        vRtrStaticRoutePreference,
        vRtrStaticRouteMetric,
        vRtrStaticRouteEgressIfIndex,
        vRtrStaticRouteNextHop,
        vRtrStaticRouteNextHopUnnumberedIf,
        vRtrStaticRouteAdminState,
        vRtrStaticRouteTag,
        vRtrStaticRouteIndexDest,
        vRtrStaticRouteIndexMask,
        vRtrStaticRouteAvailableIndex,
        vRtrInetStaticRouteRowStatus,
        vRtrInetStaticRouteLastEnabledTime,
        vRtrInetStaticRouteStatus,
        vRtrInetStaticRouteStaticType,
        vRtrInetStaticRoutePreference,
        vRtrInetStaticRouteMetric,
        vRtrInetStaticRouteEgressIfIndex,
        vRtrInetStaticRouteNextHopType,
        vRtrInetStaticRouteNextHop,
        vRtrInetStaticRouteNextHopIf,
        vRtrInetStaticRouteAdminState,
        vRtrInetStaticRouteTag,
        vRtrInetStaticRouteEnableBfd,
        vRtrInetStaticRouteAvailIndex,
        vRtrSvcIpRangeAddress,
        vRtrSvcIpRangeMask,
        vRtrSvcIpRangeRowStatus,
        vRtrSvcIpRangeExclusive,
        vRtrIpNetToMediaTimer,
        vRtrIpNetToMediaOperState,
        vRtrAdvPrefixOnLinkFlag,
        vRtrAdvPrefixAutonomousFlag,
        vRtrAdvPrefixPreferredLifetime,
        vRtrAdvPrefixValidLifetime,
        vRtrAdvPrefixRowStatus,
        vRtrInetInstAggrTblLastChged,
        vRtrInetAggrRowStatus,
        vRtrInetAggrLastChanged,
        vRtrInetAggrSummaryOnly,
        vRtrInetAggrASSet,
        vRtrInetAggrAggregatorIPAddr,
        vRtrInetAggrOperState,
        vRtrInetSvcIpRangeRowStatus,
        vRtrInetSvcIpRangeExclusive,
        vRtrIpNetToPhysicalTimer,
        vRtrIpNetToPhysicalOperState,
        vRtrIpNetToPhysicalIsRouter,
        vRtrIpNetToPhysicalMTU,
        vRtrIpNetToPhysicalPort,
        vRtrIpNetToPhysicalEncap,
        vRtrInetCidrRouteLastEnabledTime,
        vRtrInetCidrRoutePreference,
        vRtrInetCidrRouteMetric,
        vRtrInetCidrRouteIfVRtrId,
        vRtrInetAggrAggregatorAS4Byte,
        vRtrInetCidrRouteTunnEndpntInfo,
        vRtrInetCidrProtocolInstance,
        vRtrInetStaticRouteLdpSync,
        vRtrInetStaticRouteCommunityVal,
        vRtrInetStaticRouteCreationOrig,
        vRtrInetAggrCommunityVal,
        vRtrInetAggrIndirectAddrType,
        vRtrInetAggrIndirectAddr,
        vRtrIpv6ReachableTime,
        vRtrIfLocalPoolAdminState,
        vRtrIfLocalPoolServerName,
        vRtrIfLocalPoolClientApps,
        vRtrIfLocalPoolDefPoolName,
        vRtrIfLocalPoolSecPoolName,
        vRtrRsmTableLastCh,
        vRtrRsmLastCh,
        vRtrRsmRowStatus,
        vRtrRsmGroup,
        vRtrInetStaticRouteDynamicBgp,
        vRtrIfLocalPoolV6ServerName,
        vRtrIfLocalPoolV6ClientApps,
        vRtrInetStaticRouteDynBgpNHType,
        vRtrInetStaticRouteDynBgpNH
    }
    STATUS      obsolete
    DESCRIPTION
        "The group of objects supporting management of IP capabilities for
         transport and virtual routers on version 13.0 Nokia SROS series
         systems."
    ::= { tmnxVRtrGroups 153 }

tmnxVRtrIpV13v0ObsoletedGroup    OBJECT-GROUP
    OBJECTS     {
        vRtrStaticRouteIgpShortcut,
        vRtrStaticRouteDisallowIgp,
        vRtrInetStaticRouteIgpShortcut,
        vRtrInetStaticRouteDisallowIgp
    }
    STATUS      current
    DESCRIPTION
        "The group of obsolete objects for static route on Nokia SROS series
         systems 13.0 Release."
    ::= { tmnxVRtrGroups 154 }

tmnxVRtrIfObsoletedV13v0Group    OBJECT-GROUP
    OBJECTS     {
        vRtrIfCflowd
    }
    STATUS      current
    DESCRIPTION
        "The group of objects obsoleted for virtual router interfaces in
         version 13.0 of Nokia SROS series systems."
    ::= { tmnxVRtrGroups 155 }

tmnxVRtrV13v0GenObsoletedGroup   OBJECT-GROUP
    OBJECTS     {
        vRtrTunnelMetric,
        vRtrTunnelAge,
        vRtrTunnelNextHopFlags,
        vRtrLdpShortcut
    }
    STATUS      current
    DESCRIPTION
        "The group of obsolete objects on Nokia SROS series systems 13.0
         Release."
    ::= { tmnxVRtrGroups 156 }

tmnxVRtrIfArpNbrLimitGroup       OBJECT-GROUP
    OBJECTS     {
        vRtrIfArpLimit,
        vRtrIfArpLogOnly,
        vRtrIfArpThreshold,
        vRtrIfIpv6NbrLimit,
        vRtrIfIpv6NbrLogOnly,
        vRtrIfIpv6NbrThreshold
    }
    STATUS      current
    DESCRIPTION
        "The group of objects supporting management of ARP Limit and Neighbor
         Limit on virtual interfaces in Nokia SROS series systems."
    ::= { tmnxVRtrGroups 157 }

tmnxVRtrIfExtV13v0Group          OBJECT-GROUP
    OBJECTS     {
        vRtrIfVasIfType
    }
    STATUS      current
    DESCRIPTION
        "The group of objects supporting management of virtual router instance
         interfaces in version 13.0 of the Nokia SROS series systems."
    ::= { tmnxVRtrGroups 158 }

tmnxVRtrV13v0IfStatsGroup        OBJECT-GROUP
    OBJECTS     {
        vRtrIfRxMplsPkts,
        vRtrIfTxMplsPkts,
        vRtrIfRxMplsBytes,
        vRtrIfTxMplsBytes
    }
    STATUS      current
    DESCRIPTION
        "The group of objects supporting IF stats for transport and virtual
         routers on version 13.0 Nokia SROS series systems."
    ::= { tmnxVRtrGroups 159 }

tmnxVRtrIfArpNbrNotifGroup       NOTIFICATION-GROUP
    NOTIFICATIONS {
        tmnxVRtrArpLmt,
        tmnxVRtrArpThresholdExceeded,
        tmnxVRtrIpv6NbrLmt,
        tmnxVRtrIpv6NbrThresholdExceeded
    }
    STATUS      current
    DESCRIPTION
        "The group of objects supporting management of ARP Limit and Neighbor
         Limit notifications on virtual interfaces in Nokia SROS series
         systems."
    ::= { tmnxVRtrGroups 160 }

tmnxVRtrTunnelTableCBFV13v0Group OBJECT-GROUP
    OBJECTS     {
        vRtrInetTunnelLspFC
    }
    STATUS      obsolete
    DESCRIPTION
        "The group of objects supporting management of transport and virtual
         Routers new on release 13.0 in Nokia SROS series systems."
    ::= { tmnxVRtrGroups 161 }

tmnxVRtrIPv6IPsecStatGroup       OBJECT-GROUP
    OBJECTS     {
        vRtrV6IPsecRoutes,
        vRtrV6IPsecActiveRoutes
    }
    STATUS      current
    DESCRIPTION
        "The group of objects supporting management of statistics for IPv6
         IPsec routes in version 13.0 Nokia SROS series systems."
    ::= { tmnxVRtrGroups 162 }

tmnxVRtrUniqueIfIndexGroup       OBJECT-GROUP
    OBJECTS     {
        tmnxVrtrIfIndexVrtrIfName,
        tmnxVrtrSysEnforceUniqueIfIndex
    }
    STATUS      current
    DESCRIPTION
        "The group of objects supporting management of IP interfaces on Nokia
         SROS series systems while the system assigns unique identifiers to
         each IP interface."
    ::= { tmnxVRtrGroups 163 }

tmnxVRtrStaticRoutePrefixGroup   OBJECT-GROUP
    OBJECTS     {
        vRtrInetStaticRoutePfxRowStatus,
        vRtrInetStaticRoutePfxCreateOrig,
        vRtrInetStaticRoutePfxCfgNHCount
    }
    STATUS      current
    DESCRIPTION
        "The group of objects supporting management of Static Route
         capabilities for transport and virtual routers on version 14.0 Nokia
         SROS series systems."
    ::= { tmnxVRtrGroups 164 }

tmnxVRtrV14v0ObsoletedGroup      OBJECT-GROUP
    OBJECTS     {
        vRtrIllegalLabelThreshold,
        vRtrIfIngressIpv4Flowspec,
        vRtrIfIngressIpv6Flowspec
    }
    STATUS      current
    DESCRIPTION
        "The group of obsolete objects on Nokia SROS series systems 14.0
         Release."
    ::= { tmnxVRtrGroups 165 }

tmnxVRtrV14v0Group               OBJECT-GROUP
    OBJECTS     {
        tmnxSrlgGrpPenaltyWeight,
        vRtrDisableSelectiveFib,
        vRtrWeightedEcmp,
        vRtrIfDHCPRelaySiaddrOvrAddrType,
        vRtrIfDHCPRelaySiaddrOvrAddr,
        vRtrInetCidrRouteNextHopWeight,
        vRtrInetCidrRteTnlNextHopWeight,
        vRtrRowStatus,
        vRtrAdminState,
        vRtrName,
        vRtrMaxNumRoutes,
        vRtrBgpStatus,
        vRtrMplsStatus,
        vRtrRipStatus,
        vRtrRsvpStatus,
        vRtrEcmpMaxRoutes,
        vRtrNewIfIndex,
        vRtrLdpStatus,
        vRtrRouterId,
        vRtrTriggeredPolicy,
        vRtrRouteDistinguisher,
        vRtrMidRouteThreshold,
        vRtrHighRouteThreshold,
        vRtrVpnId,
        vRtrDescription,
        vRtrGracefulRestart,
        vRtrGracefulRestartType,
        vRtrType,
        vRtrServiceId,
        vRtrCustId,
        vRtrIgmpStatus,
        vRtrMaxNumRoutesLogOnly,
        vRtrVrfTarget,
        vRtrVrfExportTarget,
        vRtrVrfImportTarget,
        vRtrPimStatus,
        vRtrMaxMcastNumRoutes,
        vRtrMaxMcastNumRoutesLogOnly,
        vRtrMcastMidRouteThreshold,
        vRtrIgnoreIcmpRedirect,
        vRtrMsdpStatus,
        vRtrVprnType,
        vRtrSecondaryVrfId,
        vRtrMldStatus,
        vRtrIPv6MaxNumRoutes,
        vRtrIPv6MidRouteThreshold,
        vRtrIPv6HighRouteThreshold,
        vRtrIPv6MaxNumRoutesLogOnly,
        vRtrIPv6IgnoreIcmpRedirect,
        vRtrMcPathMgmtPlcyName,
        vRtrOperState,
        vRtrDirectRoutes,
        vRtrDirectActiveRoutes,
        vRtrStaticRoutes,
        vRtrStaticActiveRoutes,
        vRtrOSPFRoutes,
        vRtrOSPFActiveRoutes,
        vRtrBGPRoutes,
        vRtrBGPActiveRoutes,
        vRtrISISRoutes,
        vRtrISISActiveRoutes,
        vRtrRIPRoutes,
        vRtrRIPActiveRoutes,
        vRtrAggregateRoutes,
        vRtrAggregateActiveRoutes,
        vRtrStatConfiguredIfs,
        vRtrStatActiveIfs,
        vRtrStatIllegalLabels,
        vRtrStatCurrNumRoutes,
        vRtrStatBGPVpnRoutes,
        vRtrStatBGPVpnActiveRoutes,
        vRtrStatTotalLdpTunnels,
        vRtrStatTotalSdpTunnels,
        vRtrStatActiveLdpTunnels,
        vRtrStatActiveSdpTunnels,
        vRtrMulticastRoutes,
        vRtrStatActiveARPEntries,
        vRtrStatTotalARPEntries,
        vRtrSubMgmtRoutes,
        vRtrSubMgmtActiveRoutes,
        vRtrStatTotalRsvpTunnels,
        vRtrStatActiveRsvpTunnels,
        vRtrV6StatTotalRsvpTunnels,
        vRtrV6StatActiveRsvpTunnels,
        vRtrHostRoutes,
        vRtrHostActiveRoutes,
        vRtrV6HostRoutes,
        vRtrV6HostActiveRoutes,
        vRtrStatLocalARPEntries,
        vRtrStatStaticARPEntries,
        vRtrStatDynamicARPEntries,
        vRtrStatManagedARPEntries,
        vRtrStatInternalARPEntries,
        vRtrDHCP6DropStatLastCleared,
        vRtrDHCP6DropStatPktsDropped,
        vRtrDHCP6MsgStatsLstClrd,
        vRtrDHCP6MsgStatsRcvd,
        vRtrDHCP6MsgStatsSent,
        vRtrDHCP6MsgStatsDropped,
        vRtrInetStaticRouteNHTunnelName,
        vRtrManagedRoutes,
        vRtrManagedActiveRoutes,
        vRtrAS4Byte,
        vRtrConfederationAS4Byte,
        vRiaInetAddrPreferred,
        vRiaSubscrPrefix,
        vRiaSubscrPrefixType,
        vRiaSubscrHostRoutePopulate,
        vRtrIfAdmLnkLclAddrPreferred,
        vRtrIfAdminLinkLocalAddr,
        vRtrIfAdminLinkLocalAddrType,
        vRtrIfLsrIpLoadBalancing,
        vRtrIfDHCP6ProxyAdminState,
        vRtrIfDHCP6ProxyRenewTimer,
        vRtrIfDHCP6ProxyRebindTimer,
        vRtrIfDHCP6ProxyValidLifetime,
        vRtrIfDHCP6ProxyPrefLifetime,
        vRtrIfDHCP6ProxyApplications,
        vRtrIfDHCP6UserDb,
        vRtrSingleSfmOverloadAdminState,
        vRtrSingleSfmOverloadHldOffTime,
        vRtrSingleSfmOverloadState,
        vRtrSingleSfmOverloadStart,
        vRtrSingleSfmOverloadTime,
        vRtrLDPRoutes,
        vRtrLDPActiveRoutes,
        vRtrGrtState,
        vRtrGrtMaxExportRoutes,
        vRtrGrtExportPolicy1,
        vRtrGrtExportPolicy2,
        vRtrGrtExportPolicy3,
        vRtrGrtExportPolicy4,
        vRtrGrtExportPolicy5,
        vRtrVPNLeakRoutes,
        vRtrVPNLeakActiveRoutes,
        vRtrV6VPNLeakRoutes,
        vRtrV6VPNLeakActiveRoutes,
        vRtrInetCidrRouteNextHopType,
        vRtrInetCidrRouteNextHopOwner,
        vRtrInetCidrRouteNHOwnerAuxInfo,
        vRtrInetCidrRteTnlEnabledTime,
        vRtrV6SubMgmtRoutes,
        vRtrV6SubMgmtActiveRoutes,
        vRtrMvpnIpmsiType,
        vRtrMvpnSpmsiType,
        vRtrMobileHostRoutes,
        vRtrMobileHostActiveRoutes,
        vRtrV6MobileHostRoutes,
        vRtrV6MobileHostActiveRoutes,
        vRtrStatTotalBgpTunnels,
        vRtrStatActiveBgpTunnels,
        vRtrMvpnVrfTarget,
        vRtrMvpnVrfExportTarget,
        vRtrMvpnVrfImportTarget,
        vRtrMvpnVrfTargetUnicast,
        vRtrMvpnVrfExportTargetUnicast,
        vRtrMvpnVrfImportTargetUnicast,
        vRtrMvpnImportPolicyUnicast,
        vRtrMvpnExportPolicyUnicast,
        vRtrMvpnCMcastImportRT,
        vRtrGrtMaxIpv6ExportRoutes,
        vRtrInetAggrNextHopType,
        vRtrInetAllCidrRteTnlEnabledTime,
        vRtrInetAllCidrRtNextHopType,
        vRtrInetAllCidrRtNextHopOwner,
        vRtrInetAllCidrRtNHOwnerAuxInfo,
        vRtrInetAllCidrRtBkupNHType,
        vRtrInetAllCidrRtBkupNHOwner,
        vRtrInetAllCidrRtBkupNHOwnAxInfo,
        vRtrInetStaticRouteDescription,
        vRtrInetStaticRoutePaddingSize,
        vRtrV6LDPRoutes,
        vRtrV6LDPActiveRoutes,
        tmnxVrtrMssAdjTableLastCh,
        tmnxVrtrMssAdjLastCh,
        tmnxVrtrMssAdjRowStatus,
        tmnxVrtrMssAdjGroup,
        tmnxVrtrMssAdjSegmentSize
    }
    STATUS      current
    DESCRIPTION
        "The group of objects supporting management of transport and virtual
         Routers new on release 14.0 in Nokia SROS series systems."
    ::= { tmnxVRtrGroups 166 }

tmnxVRtrObsoleteNotifV14v0Group  NOTIFICATION-GROUP
    NOTIFICATIONS {
        tmnxVRtrIllegalLabelTCA
    }
    STATUS      current
    DESCRIPTION
        "The group of obsolete notifications for the transport and virtual
         router capabilities on Nokia SROS series systems 14.0 Release."
    ::= { tmnxVRtrGroups 167 }

tmnxVRtrNotificationV14v0Group   NOTIFICATION-GROUP
    NOTIFICATIONS {
        tmnxVRtrMidRouteTCA,
        tmnxVRtrHighRouteTCA,
        tmnxVRtrHighRouteCleared,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrIPv6MidRouteTCA,
        tmnxVRtrIPv6HighRouteTCA,
        tmnxVRtrIPv6HighRouteCleared,
        tmnxVRtrStaticRouteCPEStatus,
        tmnxVRtrManagedRouteAddFailed,
        tmnxVRtrFibOccupancyThreshold,
        tmnxVRtrInetAddressAttachFailed,
        tmnxVRtrSingleSfmOverloadStateCh,
        tmnxVRtrGrtExportLimitReached,
        tmnxVRtrGrtRoutesExpLimitDropped,
        tmnxVRtrIfLdpSyncTimerStart,
        tmnxVRtrIfLdpSyncTimerStop,
        tmnxVRtrBfdSessExtDown,
        tmnxVRtrBfdSessExtUp,
        tmnxVRtrBfdSessExtDeleted,
        tmnxVRtrBfdSessExtProtChange,
        tmnxVRtrBfdExtNoCpmNpResources,
        tmnxVRtrDnsFault,
        tmnxVRtrMacAcctLimitReached,
        tmnxVRtrMacAcctLimitCleared,
        tmnxVRtrNgBfdSessDown,
        tmnxVRtrNgBfdSessUp,
        tmnxVRtrNgBfdSessDeleted,
        tmnxVRtrNgBfdSessProtChange,
        tmnxVRtrNgBfdNoCpmNpResources
    }
    STATUS      obsolete
    DESCRIPTION
        "The group of notifications supporting the transport and virtual router
         capabilities on version 14.0 Nokia SROS series systems."
    ::= { tmnxVRtrGroups 168 }

tmnxVRtrEntropyLabelGroup        OBJECT-GROUP
    OBJECTS     {
        vRtrEntropyLabel
    }
    STATUS      current
    DESCRIPTION
        "The group of objects supporting management of Entropy Label on version
         14.0 Nokia SROS series systems."
    ::= { tmnxVRtrGroups 169 }

tmnxVRtrLspBfdGroup              OBJECT-GROUP
    OBJECTS     {
        vRtrLspBfdSession,
        vRtrLspBfdMaxSessions
    }
    STATUS      current
    DESCRIPTION
        "The group of objects supporting management of BFD on LSP feature for
         transport and virtual routers on version 14.0 Nokia SROS series
         systems."
    ::= { tmnxVRtrGroups 170 }

tmnxVRtrIfV14v0Group             OBJECT-GROUP
    OBJECTS     {
        vRtrIfDelayV4UpSeconds,
        vRtrIfDelayV4DownSeconds,
        vRtrIfDelayV6UpSeconds,
        vRtrIfDelayV6DownSeconds,
        vRtrIfDelayV4Timer,
        vRtrIfDelayV6Timer,
        vRtrIfInitDelayV4Enable,
        vRtrIfInitDelayV6Enable,
        vRtrIfOperV4DownReason,
        vRtrIfOperV6DownReason,
        vRtrIfLdpEolib
    }
    STATUS      obsolete
    DESCRIPTION
        "The group of objects supporting management of virtual interfaces on
         version 14.0 Nokia SROS series systems."
    ::= { tmnxVRtrGroups 171 }

tmnxVRtrConfFlowspecV14v0Group   OBJECT-GROUP
    OBJECTS     {
        vRtrConfFlowspecTableLstChg,
        vRtrConfFlowspecLastChanged,
        vRtrIpEmbeddedFlowspecMaxSize,
        vRtrIpv6EmbeddedFlowspecMaxSize
    }
    STATUS      current
    DESCRIPTION
        "The group of objects supporting management of transport and virtual
         Routers new on release 14.0 in Nokia SROS series systems."
    ::= { tmnxVRtrGroups 172 }

tmnxVRtrInetSRIndirectV14v0Group OBJECT-GROUP
    OBJECTS     {
        vRtrInetSRIndirectTunnelSrIsis,
        vRtrInetSRIndirectTunnelSrOspf,
        vRtrInetSRIndirectTunnelSrTe,
        vRtrInetSRIndSrTeLspRowStatus
    }
    STATUS      current
    DESCRIPTION
        "The group of objects supporting management of transport and virtual
         Routers new on release 14.0 in Nokia SROS series systems."
    ::= { tmnxVRtrGroups 173 }

tmnxVRtrFibStatsV14v0Group       OBJECT-GROUP
    OBJECTS     {
        vRtrFibStatTotalInstalledRoutes,
        vRtrFibStatCurrentUtilization,
        vRtrFibStatFilteredRoutes,
        vRtrFibStatV6TotalInstalledRt,
        vRtrFibStatV6CurrentUtilization,
        vRtrFibStatV6FilteredRoutes,
        vRtrFibStatV6Overflows
    }
    STATUS      current
    DESCRIPTION
        "The group of objects supporting FIB summary counts on version 14.0
         Nokia SROS series systems."
    ::= { tmnxVRtrGroups 174 }

tmnxVRtrIfDHCPRelayV14v0Group    OBJECT-GROUP
    OBJECTS     {
        vRtrIfDHCPRelayClientPktsStream
    }
    STATUS      current
    DESCRIPTION
        "The group of objects supporting management of DHCP Relay on virtual
         interfaces added in version 14.0 of Nokia SROS series systems."
    ::= { tmnxVRtrGroups 175 }

tmnxVRtrBgpLblIpRoutes14v0Group  OBJECT-GROUP
    OBJECTS     {
        vRtrStatBGPLabelV4Routes,
        vRtrStatBGPLabelV4ActiveRoutes,
        vRtrStatBGPLabelV6Routes,
        vRtrStatBGPLabelV6ActiveRoutes,
        vRtrFibStatBGPLabelV4Routes,
        vRtrFibStatBGPLabelV6Routes
    }
    STATUS      current
    DESCRIPTION
        "The group of objects supporting management of BGP labeled route
         entities for release 14.0 on Nokia SROS series systems."
    ::= { tmnxVRtrGroups 176 }

tmnxVRtrV6TunnelTableStatGroup   OBJECT-GROUP
    OBJECTS     {
        vRtrStatTotalIsisV6Tunnels,
        vRtrStatActiveIsisV6Tunnels
    }
    STATUS      current
    DESCRIPTION
        "The group of additional objects enhancing the virtual interface
         statistics for IPv6 tunnels for release 14.0 on Nokia SROS series
         systems."
    ::= { tmnxVRtrGroups 177 }

tmnxVRtrSrTeV14v0Group           OBJECT-GROUP
    OBJECTS     {
        vRtrStatTotalSrTeTunnels,
        vRtrStatActiveSrTeTunnels
    }
    STATUS      current
    DESCRIPTION
        "The group of additional objects enhancing the virtual interface
         statistics for SR-TE tunnels for release 14.0 on Nokia SROS series
         systems."
    ::= { tmnxVRtrGroups 178 }

tmnxVRtrIfExtV14v0Group          OBJECT-GROUP
    OBJECTS     {
        vRtrIfCreationOrigin
    }
    STATUS      current
    DESCRIPTION
        "The group of basic router interface specific additional objects
         associated for release 14.0 on Nokia SROS series systems."
    ::= { tmnxVRtrGroups 179 }

tmnxVRtrLoopbackNotifGroup       NOTIFICATION-GROUP
    NOTIFICATIONS {
        tmnxVRtrIfIgnorePortState
    }
    STATUS      current
    DESCRIPTION
        "The group notifications supporting SAP L3 Loopback feature on Nokia
         SROS series systems release 14.0."
    ::= { tmnxVRtrGroups 180 }

tmnxVRtrV14v0NotifyObjsGroup     OBJECT-GROUP
    OBJECTS     {
        vRtrNotifIgnorePortState
    }
    STATUS      current
    DESCRIPTION
        "A group of notification objects added in release 14.0 for ignoring
         port state associated with IP interface in Nokia SROS series systems."
    ::= { tmnxVRtrGroups 181 }

tmnxVRtrTunnelTableLSCV14v0Group OBJECT-GROUP
    OBJECTS     {
        vRtrInetTunnelMaxLabels
    }
    STATUS      obsolete
    DESCRIPTION
        "The group of objects supporting management of transport and virtual
         Routers new on release 14.0 in Nokia SROS series systems."
    ::= { tmnxVRtrGroups 182 }

tmnxVRtrIcmpV4StatsV14v0Group    OBJECT-GROUP
    OBJECTS     {
        vRtrIcmpInMsgs,
        vRtrIcmpInErrors,
        vRtrIcmpInDestUnreachs,
        vRtrIcmpInRedirects,
        vRtrIcmpInEchos,
        vRtrIcmpInEchoReplies,
        vRtrIcmpInTimeExcds,
        vRtrIcmpInSrcQuenchs,
        vRtrIcmpInTimestamps,
        vRtrIcmpInTimestampReps,
        vRtrIcmpInAddrMasks,
        vRtrIcmpInAddrMaskReps,
        vRtrIcmpInParmProblems,
        vRtrIcmpOutMsgs,
        vRtrIcmpOutErrors,
        vRtrIcmpOutDestUnreachs,
        vRtrIcmpOutRedirects,
        vRtrIcmpOutEchos,
        vRtrIcmpOutEchoReplies,
        vRtrIcmpOutTimeExcds,
        vRtrIcmpOutSrcQuenchs,
        vRtrIcmpOutTimestamps,
        vRtrIcmpOutTimestampReps,
        vRtrIcmpOutAddrMasks,
        vRtrIcmpOutAddrMaskReps,
        vRtrIcmpOutParmProblems,
        vRtrIfIcmpInMsgs,
        vRtrIfIcmpInErrors,
        vRtrIfIcmpInDestUnreachs,
        vRtrIfIcmpInRedirects,
        vRtrIfIcmpInEchos,
        vRtrIfIcmpInEchoReplies,
        vRtrIfIcmpInTimeExcds,
        vRtrIfIcmpInSrcQuenchs,
        vRtrIfIcmpInTimestamps,
        vRtrIfIcmpInTimestampReps,
        vRtrIfIcmpInAddrMasks,
        vRtrIfIcmpInAddrMaskReps,
        vRtrIfIcmpInParmProblems,
        vRtrIfIcmpOutMsgs,
        vRtrIfIcmpOutErrors,
        vRtrIfIcmpOutDestUnreachs,
        vRtrIfIcmpOutRedirects,
        vRtrIfIcmpOutEchos,
        vRtrIfIcmpOutEchoReplies,
        vRtrIfIcmpOutTimeExcds,
        vRtrIfIcmpOutSrcQuenchs,
        vRtrIfIcmpOutTimestamps,
        vRtrIfIcmpOutTimestampReps,
        vRtrIfIcmpOutAddrMasks,
        vRtrIfIcmpOutAddrMaskReps,
        vRtrIfIcmpOutParmProblems
    }
    STATUS      current
    DESCRIPTION
        "The group of objects supporting management of IPv4 virtual interfaces
         on version 4.0 Nokia SROS series systems."
    ::= { tmnxVRtrGroups 183 }

tmnxVRtrIcmpV4ParamV14v0Group    OBJECT-GROUP
    OBJECTS     {
        vRtrIfIcmpV4ParamProblem,
        vRtrIfIcmpV4NumParamProblem,
        vRtrIfIcmpV4ParamProblemTime
    }
    STATUS      current
    DESCRIPTION
        "The group of additional objects enhancing the virtual interface
         statistics for parameter-problem ICMPv4 messages for release 14.0 on
         Nokia SROS series systems."
    ::= { tmnxVRtrGroups 184 }

tmnxVRtrTunnelTableNhTV14v0Group OBJECT-GROUP
    OBJECTS     {
        vRtrInetTunnelNhTunnelId,
        vRtrInetTunnelNhTunnelType,
        vRtrInetTunnelNhTunnelInst
    }
    STATUS      obsolete
    DESCRIPTION
        "The group of objects supporting management of transport and virtual
         Routers new on release 14.0 in Nokia SROS series systems."
    ::= { tmnxVRtrGroups 185 }

tmnxVRtrFpeV14v0Group            OBJECT-GROUP
    OBJECTS     {
        vRtrStatTotalFpeTunnels,
        vRtrStatActiveFpeTunnels
    }
    STATUS      current
    DESCRIPTION
        "The group of additional objects enhancing the virtual interface
         statistics for SR-TE tunnels for release 14.0 on Nokia SROS series
         systems."
    ::= { tmnxVRtrGroups 186 }

tmnxVRtrV15v0Group               OBJECT-GROUP
    OBJECTS     {
        vRtrMtrace2AdminState,
        vRtrMtrace2UdpPort,
        vRtrOperRouterId
    }
    STATUS      current
    DESCRIPTION
        "The group of objects supporting management of transport and virtual
         Routers new on release 15.0 in Nokia SROS series systems."
    ::= { tmnxVRtrGroups 187 }

tmnxVrtrDDosDCpuProtPolicyGrp    OBJECT-GROUP
    OBJECTS     {
        vRtrIfOperDCpuProtPolicy
    }
    STATUS      current
    DESCRIPTION
        "The group of objects supporting management of DDos Protection
         Enhancement feature on Nokia SROS series systems."
    ::= { tmnxVRtrGroups 188 }

tmnxVRtrIfExtV15v0Group          OBJECT-GROUP
    OBJECTS     {
        vRtrIfUrpfSelectedVprnsOnly,
        vRtrIfIpTunnelRemoteIpAddrType,
        vRtrIfIpTunnelRemoteIpAddr
    }
    STATUS      obsolete
    DESCRIPTION
        "The group of basic router interface specific additional objects added
         for release 15.0 on Nokia SROS series systems."
    ::= { tmnxVRtrGroups 189 }

tmnxVRtrUdpTunnelGroup           OBJECT-GROUP
    OBJECTS     {
        vRtrStatTotalUdpTunnels,
        vRtrStatActiveUdpTunnels
    }
    STATUS      current
    DESCRIPTION
        "The group of additional objects enhancing the virtual interface
         statistics for UDP tunnels for release 15.0 on Nokia SROS series
         systems."
    ::= { tmnxVRtrGroups 191 }

tmnxVRtrIpV15v0Group             OBJECT-GROUP
    OBJECTS     {
        vRiaRowStatus,
        vRiaIpAddress,
        vRiaNetMask,
        vRiaBcastAddrFormat,
        vRiaReasmMaxSize,
        vRiaIgpInhibit,
        vRiaInetAddressType,
        vRiaInetAddress,
        vRiaInetPrefixLen,
        vRiaInetAddrState,
        vRiaInetEui64,
        vRiaInetOperAddress,
        vRiaInetGwAddressType,
        vRiaInetGwAddress,
        vRiaInetRemoteIpType,
        vRiaInetRemoteIp,
        vRtrIpCidrRouteLastEnabledTime,
        vRtrIpCidrRoutePreference,
        vRtrIpCidrRouteMetric,
        vRtrStaticRouteNumber,
        vRtrInetStaticRouteRowStatus,
        vRtrInetStaticRouteLastEnabledTime,
        vRtrInetStaticRouteStatus,
        vRtrInetStaticRouteStaticType,
        vRtrInetStaticRoutePreference,
        vRtrInetStaticRouteMetric,
        vRtrInetStaticRouteEgressIfIndex,
        vRtrInetStaticRouteNextHopType,
        vRtrInetStaticRouteNextHop,
        vRtrInetStaticRouteNextHopIf,
        vRtrInetStaticRouteAdminState,
        vRtrInetStaticRouteTag,
        vRtrInetStaticRouteEnableBfd,
        vRtrInetStaticRouteAvailIndex,
        vRtrSvcIpRangeAddress,
        vRtrSvcIpRangeMask,
        vRtrSvcIpRangeRowStatus,
        vRtrSvcIpRangeExclusive,
        vRtrIpNetToMediaTimer,
        vRtrIpNetToMediaOperState,
        vRtrAdvPrefixOnLinkFlag,
        vRtrAdvPrefixAutonomousFlag,
        vRtrAdvPrefixPreferredLifetime,
        vRtrAdvPrefixValidLifetime,
        vRtrAdvPrefixRowStatus,
        vRtrInetInstAggrTblLastChged,
        vRtrInetAggrRowStatus,
        vRtrInetAggrLastChanged,
        vRtrInetAggrSummaryOnly,
        vRtrInetAggrASSet,
        vRtrInetAggrAggregatorIPAddr,
        vRtrInetAggrOperState,
        vRtrInetSvcIpRangeRowStatus,
        vRtrInetSvcIpRangeExclusive,
        vRtrIpNetToPhysicalTimer,
        vRtrIpNetToPhysicalOperState,
        vRtrIpNetToPhysicalIsRouter,
        vRtrIpNetToPhysicalMTU,
        vRtrIpNetToPhysicalPort,
        vRtrIpNetToPhysicalEncap,
        vRtrInetCidrRouteLastEnabledTime,
        vRtrInetCidrRoutePreference,
        vRtrInetCidrRouteMetric,
        vRtrInetCidrRouteIfVRtrId,
        vRtrInetAggrAggregatorAS4Byte,
        vRtrInetCidrRouteTunnEndpntInfo,
        vRtrInetCidrProtocolInstance,
        vRtrInetStaticRouteLdpSync,
        vRtrInetStaticRouteCommunityVal,
        vRtrInetStaticRouteCreationOrig,
        vRtrInetAggrCommunityVal,
        vRtrInetAggrIndirectAddrType,
        vRtrInetAggrIndirectAddr,
        vRtrIpv6ReachableTime,
        vRtrIfLocalPoolAdminState,
        vRtrIfLocalPoolServerName,
        vRtrIfLocalPoolClientApps,
        vRtrIfLocalPoolDefPoolName,
        vRtrIfLocalPoolSecPoolName,
        vRtrRsmTableLastCh,
        vRtrRsmLastCh,
        vRtrRsmRowStatus,
        vRtrRsmGroup,
        vRtrInetStaticRouteDynamicBgp,
        vRtrIfLocalPoolV6ServerName,
        vRtrIfLocalPoolV6ClientApps,
        vRtrInetStaticRouteDynBgpNHType,
        vRtrInetStaticRouteDynBgpNH
    }
    STATUS      current
    DESCRIPTION
        "The group of objects supporting management of IP capabilities for
         transport and virtual routers on version 15.0 Nokia SROS series
         systems."
    ::= { tmnxVRtrGroups 192 }

tmnxVRtrIpV15v0ObsoletedGroup    OBJECT-GROUP
    OBJECTS     {
        vRtrStaticRouteDest,
        vRtrStaticRouteMask,
        vRtrStaticRouteIndex,
        vRtrStaticRouteRowStatus,
        vRtrStaticRouteLastEnabledTime,
        vRtrStaticRouteStatus,
        vRtrStaticRouteStaticType,
        vRtrStaticRoutePreference,
        vRtrStaticRouteMetric,
        vRtrStaticRouteEgressIfIndex,
        vRtrStaticRouteNextHop,
        vRtrStaticRouteNextHopUnnumberedIf,
        vRtrStaticRouteAdminState,
        vRtrStaticRouteTag,
        vRtrStaticRouteIndexDest,
        vRtrStaticRouteIndexMask,
        vRtrStaticRouteAvailableIndex
    }
    STATUS      current
    DESCRIPTION
        "The group of obsolete objects for static route on Nokia SROS series
         systems 15.0 Release."
    ::= { tmnxVRtrGroups 193 }

tmnxVRtrQinQNetworkIntfGroup     OBJECT-GROUP
    OBJECTS     {
        tmnxVrtrSysAllowQinQNetworkIntf
    }
    STATUS      current
    DESCRIPTION
        "The group of objects supporting QinQ encapsulation on network
         interfaces."
    ::= { tmnxVRtrGroups 194 }

tmnxVRtrIfV15v0ObsoletedGroup    OBJECT-GROUP
    OBJECTS     {
        vRtrIfDelaySeconds,
        vRtrIfDelayUpTimer,
        vRtrIfInitDelayEnable,
        vRtrIfOperDownReason
    }
    STATUS      current
    DESCRIPTION
        "The group of obsolete objects on Nokia SROS series systems 15.0
         Release."
    ::= { tmnxVRtrGroups 195 }

tmnxVRtrGlobalV15v0Group         OBJECT-GROUP
    OBJECTS     {
        vRtrVpnBackupPath,
        vRtrIpFastReroute,
        vRtrDnsTableLastCh,
        vRtrDnsLastCh,
        vRtrDnsRowStatus,
        vRtrDnsAdminState,
        vRtrDnsPrimaryAddrType,
        vRtrDnsPrimaryAddr,
        vRtrDnsSecondaryAddrType,
        vRtrDnsSecondaryAddr,
        vRtrDnsTertiaryAddrType,
        vRtrDnsTertiaryAddr,
        vRtrDnsIpv4SourceAddr,
        vRtrDnsIpv6SourceAddr,
        vRtrIfInfo,
        vRtrIfTxBytes,
        vRtrIfTxBytesHigh32,
        vRtrIfTxBytesLow32,
        vRtrIfTxPkts,
        vRtrIfTxPktsHigh32,
        vRtrIfTxPktsLow32,
        vRtrIfStatusString,
        vRtrIfOperDownReason
    }
    STATUS      obsolete
    DESCRIPTION
        "The group of objects supporting management of additional features on
         Nokia SROS series systems release 15.0."
    ::= { tmnxVRtrGroups 196 }

tmnxVRtrGlobalObsoletedGroup     OBJECT-GROUP
    OBJECTS     {
        vRtrIfTmsOffRampVprn,
        vRtrIfTmsMgmtVprn,
        vRtrIfInfo,
        vRtrIfNtpBroadcast,
        vRtrIfAlias,
        vRtrIfStatusString,
        vRtrMcastIpv4StatBGPEvpnRoutes,
        vRtrMcastIpv4StatBGPEvpnActvRts,
        vRtrMcastIpv6StatBGPEvpnRoutes,
        vRtrMcastIpv6StatBGPEvpnActvRts
    }
    STATUS      current
    DESCRIPTION
        "A group of obsoleted objects on Nokia SROS series systems."
    ::= { tmnxVRtrGroups 197 }

tmnxVRtrIfExtV15v0ObjectGroup    OBJECT-GROUP
    OBJECTS     {
        vRtrIfLagLinkMapProfile,
        vRtrIfLagActivePort,
        vRtrIfIngressStatsEnabled,
        vRtrIfIpv6ReachableTime,
        vRtrIfIpv6DadDisable,
        vRtrIfEnableMacAccounting,
        vRtrIfIpv6NdCacheStaleTime
    }
    STATUS      current
    DESCRIPTION
        "A group of objects supporting management of virtual router instance
         interfaces in version 15.0 of the Nokia SROS series systems."
    ::= { tmnxVRtrGroups 198 }

tmnxVRtrIfExtObsoletedGroup      OBJECT-GROUP
    OBJECTS     {
        vRtrIfTmsOffRampIgrVrf
    }
    STATUS      current
    DESCRIPTION
        "A group of obsoleted objects supporting management of virtual router
         instance interfaces in version 15.0 of the Nokia SROS series systems."
    ::= { tmnxVRtrGroups 199 }

tmnxVRtrClassFwdingV15v0Group    OBJECT-GROUP
    OBJECTS     {
        vRtrClassForwarding
    }
    STATUS      current
    DESCRIPTION
        "The group of objects supporting management of class forwarding policy
         for release 15.0 in Nokia SROS series systems. "
    ::= { tmnxVRtrGroups 200 }

tmnxVRtrNotificationV15v0Group   NOTIFICATION-GROUP
    NOTIFICATIONS {
        tmnxVRtrPdnAddrMismatch,
        tmnxVRtrPdnAddrMismatchCleared
    }
    STATUS      obsolete
    DESCRIPTION
        "The group of notifications supporting the transport and virtual router
         capabilities on version 15.0 Nokia SROS series systems."
    ::= { tmnxVRtrGroups 201 }

tmnxVRtrIfExtHostRteV15v0Group   OBJECT-GROUP
    OBJECTS     {
        vRtrIfIpv4ArpLearnUnsol,
        vRtrIfIpv4ArpProRef,
        vRtrIfIpv6NdLearnUnsol,
        vRtrIfIpv6NdProRef,
        vRtrIfIpv4ArpPopulateHost,
        vRtrIfIpv4ArpRouteTag,
        vRtrIfIpv6NdPopulateHost,
        vRtrIfIpv6NdRouteTag,
        vRtrStatArpRoutes,
        vRtrStatArpActiveRoutes,
        vRtrStatNdRoutes,
        vRtrStatNdActiveRoutes
    }
    STATUS      obsolete
    DESCRIPTION
        "The group of basic router interface specific additional objects for
         release 15.0 on Nokia SROS series systems."
    ::= { tmnxVRtrGroups 202 }

tmnxVRtrIfNgeStatsGroup          OBJECT-GROUP
    OBJECTS     {
        vRtrIfTxNgeEncryptPkts,
        vRtrIfTxNgeEncryptBytes,
        vRtrIfRxNgeDecryptPkts,
        vRtrIfRxNgeDecryptBytes,
        vRtrIfRxNgeInvSpiDropPkts,
        vRtrIfRxNgeInvSpiDropBytes,
        vRtrIfRxNgeOthDropPkts,
        vRtrIfRxNgeOthDropBytes,
        vRtrIfRxNgeIcmpDropPkts,
        vRtrIfRxNgeIcmpDropBytes
    }
    STATUS      current
    DESCRIPTION
        "The group of interface statistics for management of NGE on Nokia SROS
         series systems."
    ::= { tmnxVRtrGroups 203 }

tmnxVRtrIfStatsV16v0Group        OBJECT-GROUP
    OBJECTS     {
        vRtrIfAltRxMplsPkts,
        vRtrIfAltTxMplsPkts,
        vRtrIfAltRxMplsBytes,
        vRtrIfAltTxMplsBytes
    }
    STATUS      current
    DESCRIPTION
        "The group of objects supporting IF stats for transport and virtual
         routers on version 16.0 Nokia SROS series systems."
    ::= { tmnxVRtrGroups 205 }

tmnxVRtrAdminTagsV16v0Group      OBJECT-GROUP
    OBJECTS     {
        vRtrAdminTagsRowStatus,
        vRtrAdminTagsPolicyRowStatus,
        vRtrATPolicyIncludeRowStatus,
        vRtrATPolicyExcludeRowStatus
    }
    STATUS      current
    DESCRIPTION
        "A group of objects supporting management of virtual router instance
         admin-tags in version 16.0 of the Nokia SROS series systems."
    ::= { tmnxVRtrGroups 206 }

tmnxVRtrLargeCommValV16v0Group   OBJECT-GROUP
    OBJECTS     {
        vRtrInetAggrCommunityVal2,
        vRtrInetAggrCommunityVal3,
        vRtrInetAggrCommunityVal4,
        vRtrInetAggrCommunityVal5,
        vRtrInetAggrCommunityVal6,
        vRtrInetAggrCommunityVal7,
        vRtrInetAggrCommunityVal8,
        vRtrInetAggrCommunityVal9,
        vRtrInetAggrCommunityVal10,
        vRtrInetAggrCommunityVal11,
        vRtrInetAggrCommunityVal12,
        vRtrInetStaticRoutePfxCommVal1,
        vRtrInetStaticRoutePfxCommVal2,
        vRtrInetStaticRoutePfxCommVal3,
        vRtrInetStaticRoutePfxCommVal4,
        vRtrInetStaticRoutePfxCommVal5,
        vRtrInetStaticRoutePfxCommVal6,
        vRtrInetStaticRoutePfxCommVal7,
        vRtrInetStaticRoutePfxCommVal8,
        vRtrInetStaticRoutePfxCommVal9,
        vRtrInetStaticRoutePfxCommVal10,
        vRtrInetStaticRoutePfxCommVal11,
        vRtrInetStaticRoutePfxCommVal12,
        vRtrInetStaticRoutePfxTag
    }
    STATUS      current
    DESCRIPTION
        "The group of objects supporting Large communities for aggregate routes
         for virtual routers on version 16.0 Nokia SROS series systems."
    ::= { tmnxVRtrGroups 207 }

tmnxVRtrIfStatsDBCastV16v0Group  OBJECT-GROUP
    OBJECTS     {
        vRtrIfTxV4DirectedBcastPktDrop,
        vRtrIfTxV4DirectedBcastByteDrop
    }
    STATUS      current
    DESCRIPTION
        "The group of objects supporting IF stats for transport and virtual
         routers on version 16.0 Nokia SROS series systems."
    ::= { tmnxVRtrGroups 208 }

tmnxVRtrIfV16v0Group             OBJECT-GROUP
    OBJECTS     {
        vRtrIfTotalNumber,
        vRtrIfRowStatus,
        vRtrIfType,
        vRtrIfName,
        vRtrIfPortID,
        vRtrIfEncapValue,
        vRtrIfAdminState,
        vRtrIfOperState,
        vRtrIfPhysicalAddress,
        vRtrIfArpTimeout,
        vRtrIfIcmpMaskReply,
        vRtrIfIcmpRedirects,
        vRtrIfIcmpNumRedirects,
        vRtrIfIcmpRedirectsTime,
        vRtrIfIcmpUnreachables,
        vRtrIfIcmpNumUnreachables,
        vRtrIfIcmpUnreachablesTime,
        vRtrIfIcmpTtlExpired,
        vRtrIfIcmpNumTtlExpired,
        vRtrIfIcmpTtlExpiredTime,
        vRtrIfUnnumbered,
        vRtrIfMtu,
        vRtrIfIngressFilterId,
        vRtrIfEgressFilterId,
        vRtrIfDirectedBroadcast,
        vRtrIfMplsStatus,
        vRtrIfUnnumberedIf,
        vRtrIfCflowd,
        vRtrIfVPNClass,
        vRtrIfDescription,
        vRtrIfProtocol,
        vRtrIfTosMarkingTrusted,
        vRtrIfServiceId,
        vRtrIfArpPopulate,
        vRtrIfLastOperStateChange,
        vRtrIfOperMtu,
        vRtrIfGlobalIndex,
        vRtrIfProxyArp,
        vRtrIfProxyArpLocal,
        vRtrIfProxyArpPolicy1,
        vRtrIfProxyArpPolicy2,
        vRtrIfProxyArpPolicy3,
        vRtrIfProxyArpPolicy4,
        vRtrIfProxyArpPolicy5,
        vRtrIfNameIndex,
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfGlobalIndexvRtrID,
        vRtrIfGlobalIndexvRtrIfIndex,
        vRtrIfDelaySeconds,
        vRtrIfDelayUpTimer,
        vRtrIfInitDelayEnable,
        vRtrInetCidrRouteBkupNHType,
        vRtrInetCidrRouteBkupNHOwner,
        vRtrInetCidrRouteBkupNHOwnAxInfo,
        vRtrIfDelayV4UpSeconds,
        vRtrIfDelayV4DownSeconds,
        vRtrIfDelayV6UpSeconds,
        vRtrIfDelayV6DownSeconds,
        vRtrIfDelayV4Timer,
        vRtrIfDelayV6Timer,
        vRtrIfInitDelayV4Enable,
        vRtrIfInitDelayV6Enable,
        vRtrIfOperV4DownReason,
        vRtrIfOperV6DownReason,
        vRtrIfLdpEolib,
        vRtrIfIpHelperGatewayAddress,
        vRtrIfGreTermination,
        vRtrIfIlmUntrusted,
        vRtrIfIlmDefaultForwarding
    }
    STATUS      current
    DESCRIPTION
        "The group of basic router interface specific objects in release 16.0
         on Nokia SROS series systems."
    ::= { tmnxVRtrGroups 209 }

tmnxVRtrLocalPrefV16v0Group      OBJECT-GROUP
    OBJECTS     {
        vRtrInetAggrFlags,
        vRtrInetAggrLocalPreference
    }
    STATUS      current
    DESCRIPTION
        "The group of objects supporting local preferences for aggregate routes
         for virtual routers on version 16.0 Nokia SROS series systems."
    ::= { tmnxVRtrGroups 210 }

tmnxVRtrIpV16v0Group             OBJECT-GROUP
    OBJECTS     {
        vRiaInetAddressPrimaryPreference,
        vRiaInetAddressPrimaryPreferred
    }
    STATUS      current
    DESCRIPTION
        "The group of objects supporting management of IP capabilities for
         transport and virtual routers on version 16.0 Nokia SROS series
         systems."
    ::= { tmnxVRtrGroups 211 }

tmnxVRtrLoadBalWeightV16v0Group  OBJECT-GROUP
    OBJECTS     {
        vRtrInetStaticRouteLoadBalWeight
    }
    STATUS      current
    DESCRIPTION
        "The group of objects supporting load balancing weight for static
         routes for virtual routers on version 16.0 Nokia SROS series systems."
    ::= { tmnxVRtrGroups 212 }

tmnxVRtrInetExtTunnelV16v0Group  OBJECT-GROUP
    OBJECTS     {
        vRtrInetExtTunnelPreference,
        vRtrInetExtTunnelType,
        vRtrInetExtTunnelTypeInstance,
        vRtrInetExtTunnelID,
        vRtrInetExtTunnelNextHopAddrType,
        vRtrInetExtTunnelNextHopAddr,
        vRtrInetExtTunnelMetric,
        vRtrInetExtTunnelAge,
        vRtrInetExtTunnelNextHopFlags,
        vRtrInetExtTunnelLspBandwidth,
        vRtrInetExtTunnelMTU,
        vRtrInetExtTunnelLspWeight,
        vRtrInetExtTunnelLspId,
        vRtrInetExtTunnelFlags,
        vRtrInetExtTunnelRelativeMetric,
        vRtrInetExtTunnelLabel,
        vRtrInetExtTunnelBypassLabel,
        vRtrInetExtTunnelLspFC,
        vRtrInetExtTunnelMaxLabels,
        vRtrInetExtTunnelNhTunnelId,
        vRtrInetExtTunnelNhTunnelType,
        vRtrInetExtTunnelNhTunnelInst,
        vRtrInetExtTunnelColor,
        vRtrInetExtTunnelNhWeight
    }
    STATUS      current
    DESCRIPTION
        "The group of objects supporting management of transport and virtual
         Routers new on release 16.0 in Nokia SROS series systems."
    ::= { tmnxVRtrGroups 213 }

tmnxVRtrGrtLeakImpPolV16v0Group  OBJECT-GROUP
    OBJECTS     {
        vRtrLeakExportPolicy1,
        vRtrLeakExportPolicy2,
        vRtrLeakExportPolicy3,
        vRtrLeakExportPolicy4,
        vRtrLeakExportPolicy5,
        vRtrLeakExportLimit,
        vRtrGrtImportPolicy1,
        vRtrGrtImportPolicy2,
        vRtrGrtImportPolicy3,
        vRtrGrtImportPolicy4,
        vRtrGrtImportPolicy5
    }
    STATUS      current
    DESCRIPTION
        "The group of objects supporting GRT Leak feature virtual routers on
         version 16.0 Nokia SROS series systems."
    ::= { tmnxVRtrGroups 214 }

tmnxVRtrInetTunnStatV16v0Group   OBJECT-GROUP
    OBJECTS     {
        vRtrStatTotalOspfv3Tunnels,
        vRtrStatActiveOspfv3Tunnels,
        vRtrStatTotalOspfv3IPv6Tunnels,
        vRtrStatActiveOspfv3IPv6Tunnels
    }
    STATUS      current
    DESCRIPTION
        "The group of objects supporting management of transport and virtual
         Routers new on release 16.0 in Nokia SROS series systems."
    ::= { tmnxVRtrGroups 215 }

tmnxVRtrGlobalV16v0Group         OBJECT-GROUP
    OBJECTS     {
        vRtrVpnBackupPath,
        vRtrIpFastReroute,
        vRtrDnsTableLastCh,
        vRtrDnsLastCh,
        vRtrDnsRowStatus,
        vRtrDnsAdminState,
        vRtrDnsPrimaryAddrType,
        vRtrDnsPrimaryAddr,
        vRtrDnsSecondaryAddrType,
        vRtrDnsSecondaryAddr,
        vRtrDnsTertiaryAddrType,
        vRtrDnsTertiaryAddr,
        vRtrDnsIpv4SourceAddr,
        vRtrDnsIpv6SourceAddr,
        vRtrIfInfo,
        vRtrIfTxBytes,
        vRtrIfTxBytesHigh32,
        vRtrIfTxBytesLow32,
        vRtrIfTxPkts,
        vRtrIfTxPktsHigh32,
        vRtrIfTxPktsLow32,
        vRtrIfOperDownReason,
        vRtrPolicyReferenceChecks
    }
    STATUS      current
    DESCRIPTION
        "The group of objects supporting management of additional features on
         Nokia SROS series systems release 16.0."
    ::= { tmnxVRtrGroups 216 }

tmnxVRtrInetRouteV16v0Group      OBJECT-GROUP
    OBJECTS     {
        vRtrInetCidrRouteNHIsFec,
        vRtrInetCidrRouteNHFecPfxLen,
        vRtrInetAllCidrRouteNHIsFec,
        vRtrInetAllCidrRouteNHFecPfxLen
    }
    STATUS      current
    DESCRIPTION
        "The group of objects supporting route next-hop being a FEC in the
         vRtrInetCidrRouteTable and the vRtrInetAllCidrRouteTable tables on
         Nokia SROS series systems 16.0 release."
    ::= { tmnxVRtrGroups 217 }

tmnxVRtrSrTnlStatV16v0Group      OBJECT-GROUP
    OBJECTS     {
        vRtrStatTotalSrPolicyTunnels,
        vRtrStatActiveSrPolicyTunnels
    }
    STATUS      current
    DESCRIPTION
        "The group of objects supporting SR Policy tunnel statistics on release
         16.0 Nokia SROS series systems."
    ::= { tmnxVRtrGroups 218 }

tmnxTunnelTableObsoleteV16v0Grp  OBJECT-GROUP
    OBJECTS     {
        vRtrInetTunnelMetric,
        vRtrInetTunnelAge,
        vRtrInetTunnelNextHopFlags,
        vRtrInetTunnelLspBandwidth,
        vRtrInetTunnelMTU,
        vRtrInetTunnelLspWeight,
        vRtrInetTunnelLspId,
        vRtrInetTunnelRelativeMetric,
        vRtrInetTunnelFlags,
        vRtrInetTunnelLabel,
        vRtrInetTunnelBypassLabel,
        vRtrInetTunnelLspFC,
        vRtrInetTunnelMaxLabels,
        vRtrInetTunnelNhTunnelId,
        vRtrInetTunnelNhTunnelType,
        vRtrInetTunnelNhTunnelInst
    }
    STATUS      current
    DESCRIPTION
        "The group of tunnel table objects which are obsoleted in Nokia SROS
         16.0 series systems."
    ::= { tmnxVRtrGroups 219 }

tmnxVRtrBierV16v0Group           OBJECT-GROUP
    OBJECTS     {
        vRtrMvpnIpmsiBierSubDomain,
        vRtrMvpnSpmsiBierSubDomain
    }
    STATUS      current
    DESCRIPTION
        "The group of objects supporting the BIER protocol on Nokia SROS series
         systems 16.0 release."
    ::= { tmnxVRtrGroups 220 }

tmnxVRtrDhcpClientGroup          OBJECT-GROUP
    OBJECTS     {
        vRtrIfDhcpClLastChanged,
        vRtrIfDhcpClRowStatus,
        vRtrIfDhcpClAdminState,
        vRtrIfDhcpClVendorClassIdFmt,
        vRtrIfDhcpClVendorClassId,
        vRtrIfDhcpClClientIdOrigin,
        vRtrIfDhcpClClientIdFmt,
        vRtrIfDhcpClClientId,
        vRtrIfDhcpClLeaseTime,
        vRtrIfDhcpClRequestOptions,
        vRtrIfDhcpClStatsClearedTime,
        vRtrIfDhcpClStatsTxDiscovers,
        vRtrIfDhcpClStatsTxRequests,
        vRtrIfDhcpClStatsTxReleases,
        vRtrIfDhcpClStatsTxDeclines,
        vRtrIfDhcpClStatsRxOffers,
        vRtrIfDhcpClStatsRxAcks,
        vRtrIfDhcpClStatsRxNaks,
        vRtrIfDhcpClStatsRxDrops,
        vRtrIfDhcpClStateCiAddrType,
        vRtrIfDhcpClStateCiAddr,
        vRtrIfDhcpClStateCiAddrMaskLen,
        vRtrIfDhcpClStateChAddr,
        vRtrIfDhcpClStateSiAddrType,
        vRtrIfDhcpClStateSiAddr,
        vRtrIfDhcpClStateRtAddrType,
        vRtrIfDhcpClStateRtAddr,
        vRtrIfDhcpClStateDnsPriAddrType,
        vRtrIfDhcpClStateDnsPriAddr,
        vRtrIfDhcpClStateDnsSecAddrType,
        vRtrIfDhcpClStateDnsSecAddr,
        vRtrIfDhcpClStateDnsTerAddrType,
        vRtrIfDhcpClStateDnsTerAddr,
        vRtrIfDhcpClStateLeaseAcquired,
        vRtrIfDhcpClStateLeaseRenew,
        vRtrIfDhcpClStateLeaseRebind,
        vRtrIfDhcpClStateLeaseEnd,
        vRtrIfDhcpClDhcpState,
        vRtrIfDhcpClStateStatus,
        vRtrIfDhcpClStateDescription,
        vRtrIfDhcpClRtStatus,
        vRtrAutoCfgRaRtStatus,
        vRtrAutoCfgRaRtTimer,
        vRtrAutoCfgRaRouterIfIndex,
        vRtrAutoCfgRaRouterCurHopLimit,
        vRtrAutoCfgRaRouterManagedFlag,
        vRtrAutoCfgRaRouterOtherCfgFlag,
        vRtrAutoCfgRaRouterPreference,
        vRtrAutoCfgRaRouterLifetime,
        vRtrAutoCfgRaRouterReachableTime,
        vRtrAutoCfgRaRouterRetransTimer,
        vRtrAutoCfgRaPrefixIfIndex,
        vRtrAutoCfgRaPrefixOnLinkFlag,
        vRtrAutoCfgRaPrefixAutonomFlag,
        vRtrAutoCfgRaPrefixPrefLftm,
        vRtrAutoCfgRaPrefixValidLftm,
        vRtrAutoCfgRaSpecRtIfIndex,
        vRtrAutoCfgRaSpecRtPreference,
        vRtrAutoCfgRaSpecRtLifetime,
        vRtrIfAutoCfgRaStatsClearedTime,
        vRtrIfAutoCfgRaStatsOutRtrSol,
        vRtrIfAutoCfgRaStatsRtrSolTime,
        vRtrIfAutoCfgRaStatsOutRtrSolErr,
        vRtrIfAutoCfgRaStatsInRtrAdv,
        vRtrIfAutoCfgRaStatsRtrAdvTime,
        vRtrIfAutoCfgRaStatsInRtrAdvErr,
        vRtrIfDhcp6ClStatsClearedTime,
        vRtrIfDhcp6ClStatsTxSolicits,
        vRtrIfDhcp6ClStatsRxAdvertises,
        vRtrIfDhcp6ClStatsTxRequests,
        vRtrIfDhcp6ClStatsTxConfirms,
        vRtrIfDhcp6ClStatsTxRenews,
        vRtrIfDhcp6ClStatsTxRebinds,
        vRtrIfDhcp6ClStatsRxReplies,
        vRtrIfDhcp6ClStatsTxReleases,
        vRtrIfDhcp6ClStatsTxDeclines,
        vRtrIfDhcp6ClStatsRxReconfigures,
        vRtrIfDhcp6ClStatsTxInfRequests,
        vRtrIfDhcp6ClStatsRxDrops,
        vRtrIfDhcp6ClStateCiAddrType,
        vRtrIfDhcp6ClStateCiAddr,
        vRtrIfDhcp6ClStateCiAddrMaskLen,
        vRtrIfDhcp6ClStateClientDuid,
        vRtrIfDhcp6ClStateSiAddrType,
        vRtrIfDhcp6ClStateSiAddr,
        vRtrIfDhcp6ClStateServerDuid,
        vRtrIfDhcp6ClStateDnsPriAddrType,
        vRtrIfDhcp6ClStateDnsPriAddr,
        vRtrIfDhcp6ClStateDnsSecAddrType,
        vRtrIfDhcp6ClStateDnsSecAddr,
        vRtrIfDhcp6ClStateDnsTerAddrType,
        vRtrIfDhcp6ClStateDnsTerAddr,
        vRtrIfDhcp6ClStateLeaseCreated,
        vRtrIfDhcp6ClStateLeaseAcquired,
        vRtrIfDhcp6ClStateLeaseRenew,
        vRtrIfDhcp6ClStateLeaseRebind,
        vRtrIfDhcp6ClStateLeasePrefLftm,
        vRtrIfDhcp6ClStateLeaseValidLftm,
        vRtrIfDhcp6ClStateStatus,
        vRtrIfDhcp6ClStateDescription
    }
    STATUS      current
    DESCRIPTION
        "The group of objects supporting the DHCP client on Nokia SROS series
         systems."
    ::= { tmnxVRtrGroups 230 }

tmnxVRtrRibApiV16v0Group         OBJECT-GROUP
    OBJECTS     {
        vRtrRibApiMplsLastChanged,
        vRtrRibApiMplsAdminState,
        vRtrRibApiMplsReservedLblBlk,
        vRtrInetSRIndirectTunnelRibApi,
        vRtrInetExtTunnelNhBitFlags,
        vRtrInetExtTunnelNhGroupId,
        vRtrInetSRIndirectTnlMplsFwdPlcy,
        vRtrStatTotalRibApiV4Routes,
        vRtrStatActiveRibApiV4Routes,
        vRtrStatTotalRibApiV6Routes,
        vRtrStatActiveRibApiV6Routes,
        vRtrStatTotalRibApiV4Tunnels,
        vRtrStatActiveRibApiV4Tunnels,
        vRtrStatTotalRibApiV6Tunnels,
        vRtrStatActiveRibApiV6Tunnels,
        vRtrStatTotMplsFwdPlcyV4Tunnels
    }
    STATUS      current
    DESCRIPTION
        "The group of objects supporting the RIB-API on Nokia SROS series
         systems."
    ::= { tmnxVRtrGroups 231 }

tmnxVRtrRibTelemetryV16v0Group   OBJECT-GROUP
    OBJECTS     {
        vRtrFibTelemetry
    }
    STATUS      current
    DESCRIPTION
        "The group of objects supporting the RIB-API on Nokia SROS series
         systems."
    ::= { tmnxVRtrGroups 232 }

tmnxVRtrMplsFwdPlcyV16v0Group    OBJECT-GROUP
    OBJECTS     {
        vRtrStatTotMplsFwdPlcyV4Tunnels,
        vRtrStatActMplsFwdPlcyV4Tunnels,
        vRtrStatTotMplsFwdPlcyV6Tunnels,
        vRtrStatActMplsFwdPlcyV6Tunnels
    }
    STATUS      current
    DESCRIPTION
        "The group of objects supporting the Mpls Forward Policy on Nokia SROS
         series systems."
    ::= { tmnxVRtrGroups 233 }

tmnxVRtrIcmpV4StatsV19v0Group    OBJECT-GROUP
    OBJECTS     {
        vRtrIfIcmpOutDiscards,
        vRtrIcmpOutDiscards
    }
    STATUS      current
    DESCRIPTION
        "The group of objects supporting ICMP counters on version 19 Nokia SROS
         series systems."
    ::= { tmnxVRtrGroups 234 }

tmnxVRtrLeakExportLimNotifGroup  NOTIFICATION-GROUP
    NOTIFICATIONS {
        tmnxVRtrLeakExportLimitReached,
        tmnxVRtrLeakExportLimitDropped
    }
    STATUS      current
    DESCRIPTION
        "The group of objects supporting GRT Leak feature notifications on
         virtual routers for version 16.0 Nokia SROS series systems."
    ::= { tmnxVRtrGroups 235 }

tmnxVRtrInetSRIndirectV16v0Group OBJECT-GROUP
    OBJECTS     {
        vRtrInetSRIndirectTunnelSrOspf3
    }
    STATUS      current
    DESCRIPTION
        "The group of objects supporting management of transport and virtual
         Routers new on release 16.0 in Nokia SROS series systems."
    ::= { tmnxVRtrGroups 236 }

tmnxVRtrDhcpRoutesV19v0Group     OBJECT-GROUP
    OBJECTS     {
        vRtrDHCPRoutes,
        vRtrDHCPActiveRoutes,
        vRtrV6DHCPRoutes,
        vRtrV6DHCPActiveRoutes
    }
    STATUS      current
    DESCRIPTION
        "The group of objects introduced for DHCP routes for version 19.0 Nokia
         SROS series systems."
    ::= { tmnxVRtrGroups 237 }

tmnxVRtrV19v0Group               OBJECT-GROUP
    OBJECTS     {
        vRtrWeightedEcmpStrict,
        vRtrIpv6TeRouterIdIfName,
        tmnxVRtrNeInfoNeidHex,
        tmnxVRtrNeInfoNeipV4Type,
        tmnxVRtrNeInfoNeipV4,
        tmnxVRtrNeInfoNeipV4PrefixLen,
        tmnxVRtrNeInfoNeipV6Type,
        tmnxVRtrNeInfoNeipV6,
        tmnxVRtrNeInfoNeipV6PrefixLen,
        tmnxVRtrNeInfoSystemMac,
        tmnxVRtrNeInfoPlatformType,
        tmnxVRtrNeInfoVendorId,
        vRtrEcmpUnequalCost,
        vRtrRsmToBaseNetwork,
        tmnxVrtrSysMplsLblStackStatCount,
        vRtrMvpnIpmsiP2mpPolicy,
        vRtrMvpnSpmsiP2mpPolicy
    }
    STATUS      current
    DESCRIPTION
        "The group of objects supporting management of transport and virtual
         Routers new on release 19.0 in Nokia SROS series systems."
    ::= { tmnxVRtrGroups 238 }

tmnxVRtrIfV19v0Group             OBJECT-GROUP
    OBJECTS     {
        vRtrIfIpv6ForwardIpv4,
        vRiaInetAddressGreTermination
    }
    STATUS      current
    DESCRIPTION
        "The group of basic router interface specific objects in release 19.0
         on Nokia SROS series systems."
    ::= { tmnxVRtrGroups 239 }

tmnxVRtrNotificationV19v0Group   NOTIFICATION-GROUP
    NOTIFICATIONS {
        tmnxVRtrGrtV6ExportLimitReached,
        tmnxVRtrGrtV6RoutesExpLimDropped,
        tmnxVRtrStaticRouteStatusChanged,
        tmnxVRtrMidRouteTCA,
        tmnxVRtrHighRouteTCA,
        tmnxVRtrHighRouteCleared,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrIPv6MidRouteTCA,
        tmnxVRtrIPv6HighRouteTCA,
        tmnxVRtrIPv6HighRouteCleared,
        tmnxVRtrStaticRouteCPEStatus,
        tmnxVRtrManagedRouteAddFailed,
        tmnxVRtrFibOccupancyThreshold,
        tmnxVRtrInetAddressAttachFailed,
        tmnxVRtrSingleSfmOverloadStateCh,
        tmnxVRtrGrtExportLimitReached,
        tmnxVRtrGrtRoutesExpLimitDropped,
        tmnxVRtrIfLdpSyncTimerStart,
        tmnxVRtrIfLdpSyncTimerStop,
        tmnxVRtrBfdSessExtDown,
        tmnxVRtrBfdSessExtUp,
        tmnxVRtrBfdSessExtDeleted,
        tmnxVRtrBfdSessExtProtChange,
        tmnxVRtrBfdExtNoCpmNpResources,
        tmnxVRtrDnsFault,
        tmnxVRtrMacAcctLimitReached,
        tmnxVRtrMacAcctLimitCleared,
        tmnxVRtrNgBfdSessDown,
        tmnxVRtrNgBfdSessUp,
        tmnxVRtrNgBfdSessDeleted,
        tmnxVRtrNgBfdSessProtChange,
        tmnxVRtrNgBfdNoCpmNpResources,
        tmnxVRtrPdnAddrMismatch,
        tmnxVRtrPdnAddrMismatchCleared,
        tmnxVRtrDhcpClientStatusChanged,
        tmnxVRtrDhcp6ClientStatusChanged,
        vRtrIfDhcpClRtStatusChanged,
        vRtrIfDhcpClStateDnsChanged,
        tmnxVRtrNeDiscovered,
        tmnxVRtrNeRemoved,
        tmnxVRtrNeModified,
        vRtrAutoCfgRaRtStatusChanged,
        vRtrIfDhcp6ClStateDnsChanged
    }
    STATUS      current
    DESCRIPTION
        "The group of notifications supporting the transport and virtual router
         capabilities on release 19 Nokia SROS series systems."
    ::= { tmnxVRtrGroups 240 }

vRtrIfEgressQueueV19v0Group      OBJECT-GROUP
    OBJECTS     {
        vRtrIfEgressQueueFwdPkts,
        vRtrIfEgressQueueFwdOcts,
        vRtrIfEgressQueueDrpPkts,
        vRtrIfEgressQueueDrpOcts
    }
    STATUS      current
    DESCRIPTION
        "The group of basic router interface egress queue specific objects in
         release 19.0 on Nokia SROS series systems."
    ::= { tmnxVRtrGroups 241 }

tmnxVRtrIfQosV19v0Group          OBJECT-GROUP
    OBJECTS     {
        vRtrIfQosEgrVlanQosPlcy,
        vRtrIfQosEgrRemarkPlcy,
        vRtrIfQosNetworkIngressPolicy,
        vRtrIfQosEgrAggRatePIRLmt,
        vRtrIfQosEgrAggRateCIRLmt,
        vRtrIfQosEgrOperVlanQosPlcy
    }
    STATUS      current
    DESCRIPTION
        "The group of basic router interface specific objects in release 19.0
         on Nokia SROS series systems."
    ::= { tmnxVRtrGroups 242 }

vRtrIfIngressPolicerV19v0Group   OBJECT-GROUP
    OBJECTS     {
        vRtrIfIngPolicerFwdInProfPkts,
        vRtrIfIngPolicerFwdOutProfPkts,
        vRtrIfIngPolicerFwdInProfOcts,
        vRtrIfIngPolicerFwdOutProfOcts,
        vRtrIfIngPolicerDrpExdProfPkts,
        vRtrIfIngPolicerDrpExdProfOcts
    }
    STATUS      current
    DESCRIPTION
        "The group of basic router interface ingress policer statistics
         specific objects in release 19.0 on Nokia SROS series systems."
    ::= { tmnxVRtrGroups 243 }

vRtrMplsTunnelModeV19v0Group     OBJECT-GROUP
    OBJECTS     {
        tmnxVrtrSysMplsTunnelMode
    }
    STATUS      current
    DESCRIPTION
        "The group of MPLS tunnel mode mib objects in release 19.0 on Nokia
         SROS series systems."
    ::= { tmnxVRtrGroups 244 }

tmnxVRtrDiscardCV19v0Group       OBJECT-GROUP
    OBJECTS     {
        vRtrInetAggrDiscardComponent
    }
    STATUS      current
    DESCRIPTION
        "The group of objects supporting BGP discard component for aggregate
         routes for virtual routers on version 19.0 Nokia SROS series systems."
    ::= { tmnxVRtrGroups 245 }

tmnxVRtrConfFlowspecV19v0Group   OBJECT-GROUP
    OBJECTS     {
        vRtrFlowspecFltrCamType
    }
    STATUS      current
    DESCRIPTION
        "The group of objects enhancing flowspec in release 19.0  on Nokia SROS
         series systems."
    ::= { tmnxVRtrGroups 246 }

tmnxVRtrIfHostRouteGroup         OBJECT-GROUP
    OBJECTS     {
        vRtrIfArpHostRtRowStatus,
        vRtrIfArpHostRtLastChgd,
        vRtrIfArpHostRtRouteTag,
        vRtrIfArpHostRtTblLstChg
    }
    STATUS      current
    DESCRIPTION
        "The group of objects supporting management of host-routes on router
         interfaces on Nokia mobile gateway systems in 4.0 release."
    ::= { tmnxVRtrGroups 247 }

tmnxVRtrNeInfoGroup              OBJECT-GROUP
    OBJECTS     {
        tmnxVRtrNeInfoNeidHex,
        tmnxVRtrNeInfoNeipV4Type,
        tmnxVRtrNeInfoNeipV4,
        tmnxVRtrNeInfoNeipV4PrefixLen,
        tmnxVRtrNeInfoNeipV6Type,
        tmnxVRtrNeInfoNeipV6,
        tmnxVRtrNeInfoNeipV6PrefixLen,
        tmnxVRtrNeInfoSystemMac,
        tmnxVRtrNeInfoPlatformType,
        tmnxVRtrNeInfoVendorId
    }
    STATUS      obsolete
    DESCRIPTION
        "The group of objects supporting management of Network Element on
         version 16.0 Nokia SROS series systems."
    ::= { tmnxVRtrGroups 248 }

tmnxVRtrNeNotifGroup             NOTIFICATION-GROUP
    NOTIFICATIONS {
        tmnxVRtrNeDiscovered,
        tmnxVRtrNeRemoved,
        tmnxVRtrNeModified
    }
    STATUS      obsolete
    DESCRIPTION
        "The group of objects supporting Network Element notifications on
         virtual routers for version 16.0 Nokia SROS series systems."
    ::= { tmnxVRtrGroups 249 }

tmnxVRtrTunTerminationV19v0Group OBJECT-GROUP
    OBJECTS     {
        tmnxVrtrFwdIPoverIPv6,
        tmnxVrtrFwdIPoverGre
    }
    STATUS      current
    DESCRIPTION
        "The group of objects to disable tunnel termination for IOM  in release
         19.0 on Nokia SROS series systems."
    ::= { tmnxVRtrGroups 250 }

tmnxVRtrIfNdHostRouteGroup       OBJECT-GROUP
    OBJECTS     {
        vRtrIfNdHostRtRowStatus,
        vRtrIfNdHostRtLastChgd,
        vRtrIfNdHostRtRouteTag,
        vRtrIfNdHostRtTblLstChg
    }
    STATUS      current
    DESCRIPTION
        "The group of objects supporting management of host-routes on router
         interfaces on Nokia mobile gateway systems in 4.0 release."
    ::= { tmnxVRtrGroups 251 }

tmnxVRtrIfPhysStatsV19v0Group    OBJECT-GROUP
    OBJECTS     {
        vRtrIfAcctPolicyId,
        vRtrIfCollectStats
    }
    STATUS      current
    DESCRIPTION
        "The group of objects supporting Physical Layer Router interface
         statistics collection in Nokia SROS release 19.0 systems."
    ::= { tmnxVRtrGroups 252 }

tmnxVRtrSrTnlStatV19v10Group     OBJECT-GROUP
    OBJECTS     {
        vRtrStatActiveSrPolicyV6Tunnels,
        vRtrStatTotalSrPolicyV6Tunnels
    }
    STATUS      current
    DESCRIPTION
        "The group of objects supporting SR Policy tunnel statistics on release
         19.10 Nokia SROS series systems."
    ::= { tmnxVRtrGroups 253 }

tmnxVRtrDnsV20v0Group            OBJECT-GROUP
    OBJECTS     {
        vRtrDnsDefaultDomainName,
        vRtrDnsRedirectPreference,
        vRtrDnsRedirectRowStatus,
        vRtrDnsRedirectLastChanged,
        vRtrDnsRedirectTableLastChanged
    }
    STATUS      current
    DESCRIPTION
        "The group of objects supporting management of DNS servers on release
         20.0 Nokia SROS series systems."
    ::= { tmnxVRtrGroups 254 }

tmnxVRtrHelperRedirectPkts       OBJECT-GROUP
    OBJECTS     {
        vRtrIfRxV4IpHelperRedirectPkts,
        vRtrIfRxV4IpHelperRedirectBytes
    }
    STATUS      current
    DESCRIPTION
        ""
    ::= { tmnxVRtrGroups 256 }

tmnxVRtrIPEHV20v0Group           OBJECT-GROUP
    OBJECTS     {
        tmnxVrtrIPEHPerform
    }
    STATUS      current
    DESCRIPTION
        "The group of objects supporting SR Policy IP EH Performance on release
         20.5 Nokia SROS series systems."
    ::= { tmnxVRtrGroups 257 }

tmnxVRtrIfExtParmsV20v0Group     OBJECT-GROUP
    OBJECTS     {
        vRtrIfUnidirectionalLinkDelay,
        vRtrIfIngrDestinationClassLookup
    }
    STATUS      current
    DESCRIPTION
        ""
    ::= { tmnxVRtrGroups 258 }

vRtrIfEgressQueueV19v01Group     OBJECT-GROUP
    OBJECTS     {
        vRtrIfEgrQFwdInProfPkts,
        vRtrIfEgrQFwdInProfOcts,
        vRtrIfEgrQDrpInProfPkts,
        vRtrIfEgrQDrpInProfOcts,
        vRtrIfEgrQFwdOutProfPkts,
        vRtrIfEgrQFwdOutProfOcts,
        vRtrIfEgrQDrpOutProfPkts,
        vRtrIfEgrQDrpOutProfOcts,
        vRtrIfEgrQFwdExdProfPkts,
        vRtrIfEgrQFwdExdProfOcts,
        vRtrIfEgrQDrpExdProfPkts,
        vRtrIfEgrQDrpExdProfOcts,
        vRtrIfEgrQFwdInPlusProfPkts,
        vRtrIfEgrQFwdInPlusProfOcts,
        vRtrIfEgrQDrpInPlusProfPkts,
        vRtrIfEgrQDrpInPlusProfOcts
    }
    STATUS      current
    DESCRIPTION
        "The group of basic router interface egress queue specific objects in
         release 19.0 on Nokia SROS series systems."
    ::= { tmnxVRtrGroups 259 }

tmnxVRtrAggtIPPrefixV20v0Group   OBJECT-GROUP
    OBJECTS     {
        vRtrInetAggrTunnelGroup
    }
    STATUS      current
    DESCRIPTION
        "The group of objects supporting for aggregate routes for virtual
         routers on version 20.0 Nokia SROS series systems."
    ::= { tmnxVRtrGroups 260 }

tmnxFlexAlgoV20v0Group           OBJECT-GROUP
    OBJECTS     {
        tmnxFlexAlgoDefTblLastCh,
        tmnxFlexAlgoAdminGrpTblLstCh,
        tmnxFlexAlgoRowLstChng,
        tmnxFlexAlgoRowStatus,
        tmnxFlexAlgoAdminState,
        tmnxFlexAlgoDescription,
        tmnxFlexAlgoMetricType,
        tmnxFlexAlgoPriority,
        tmnxFlexAlgoAdminGrpRowLstCh,
        tmnxFlexAlgoAdminGrpRowStatus,
        vRtrInetExtTunnelAlgorithm,
        tmnxFlexAlgoFlagsTlv
    }
    STATUS      current
    DESCRIPTION
        "The group of objects providing configuration of Flexible Algorithms on
         Nokia SROS series systems."
    ::= { tmnxVRtrGroups 261 }

tmnxVRtrBgpEpe20v0Group          OBJECT-GROUP
    OBJECTS     {
        vRtrStatTotalBgpEpeTunnels,
        vRtrStatActiveBgpEpeTunnels,
        vRtrStatTotalBgpEpeV6Tunnels,
        vRtrStatActiveBgpEpeV6Tunnels
    }
    STATUS      current
    DESCRIPTION
        "The group of objects supporting management of BGP EPE entities for
         release 20.0 on Nokia SROS series systems."
    ::= { tmnxVRtrGroups 262 }

tmnxVrtrSRPolicyV20v0Group       OBJECT-GROUP
    OBJECTS     {
        vRtrMvpnIpmsiSRPolicy,
        vRtrMvpnSpmsiSRPolicy
    }
    STATUS      current
    DESCRIPTION
        "The group of objects .. "
    ::= { tmnxVRtrGroups 263 }

tmnxVRtrIfExtHostRteV20v0Group   OBJECT-GROUP
    OBJECTS     {
        vRtrIfIpv4ArpLearnUnsol,
        vRtrIfIpv4ArpProRef,
        vRtrIfIpv6NdLearnUnsol,
        vRtrIfIpv6NdProRef,
        vRtrStatArpRoutes,
        vRtrStatArpActiveRoutes,
        vRtrStatNdRoutes,
        vRtrStatNdActiveRoutes
    }
    STATUS      current
    DESCRIPTION
        "The group of basic router interface specific additional objects for
         release 20.0 on Nokia SROS series systems."
    ::= { tmnxVRtrGroups 264 }

tmnxVRtrIfTableObsoleteV20v0Grp  OBJECT-GROUP
    OBJECTS     {
        vRtrIfIpv4ArpPopulateHost,
        vRtrIfIpv4ArpRouteTag,
        vRtrIfIpv6NdPopulateHost,
        vRtrIfIpv6NdRouteTag
    }
    STATUS      current
    DESCRIPTION
        "The group of basic router interface specific objects obsoleted for
         release 20.0 on Nokia SROS series systems."
    ::= { tmnxVRtrGroups 265 }

tmnxVRtrInetSRIndirectV20v0Group OBJECT-GROUP
    OBJECTS     {
        vRtrInetSRIndirectTunFlexAlgoId
    }
    STATUS      current
    DESCRIPTION
        "The group of objects supporting management of transport and virtual
         Routers new on release 20.0 in Nokia SROS series systems."
    ::= { tmnxVRtrGroups 266 }

tmnxvRtrInetAggrPolicyV20Group   OBJECT-GROUP
    OBJECTS     {
        vRtrInetAggrPolicy
    }
    STATUS      current
    DESCRIPTION
        ""
    ::= { tmnxVRtrGroups 267 }

tmnxVRtrSrTeV6Group              OBJECT-GROUP
    OBJECTS     {
        vRtrStatTotalSrTeV6Tunnels,
        vRtrStatActiveSrTeV6Tunnels
    }
    STATUS      current
    DESCRIPTION
        "The group of objects supporting management of SR TE IPv6 entities for
         release 19.0 on Nokia SROS series systems."
    ::= { tmnxVRtrGroups 268 }

tmnxVRtrIPV20v0Group             OBJECT-GROUP
    OBJECTS     {
        tmnxVrtrIPAllowCPUFragmentation
    }
    STATUS      current
    DESCRIPTION
        "The group of object supporting management of IP MTU packets for
         release 20.7 on Nokia SROS series systems."
    ::= { tmnxVRtrGroups 269 }

tmnxVRtrV20v0Group               OBJECT-GROUP
    OBJECTS     {
        vRtrIfDHCPOSelDiscoDly,
        vRtrIfDHCPOSelClntMac,
        vRtrIfDHCPOSelClntMacDiscoDly,
        vRtrIfDHCP6ASelSlctDly,
        vRtrIfDHCP6ASelPref,
        vRtrIfDHCP6ASelClntMac,
        vRtrIfDHCP6ASelClntMacSlctDly,
        vRtrIfDHCP6ASelClntMacPref,
        vRtrIfDHCPOSelSrvrRowStatus,
        vRtrIfDHCPOSelSrvrDiscoDly,
        vRtrIfDHCP6ASelSrvrRowStatus,
        vRtrIfDHCP6ASelSrvrSolDly,
        vRtrIfDHCP6ASelSrvrPref
    }
    STATUS      current
    DESCRIPTION
        "The group of objects supporting management of transport and virtual
         Routers new on release 20.0 in Nokia SROS series systems."
    ::= { tmnxVRtrGroups 270 }

tmnxVRtrBgpEvpnV20v0Group        OBJECT-GROUP
    OBJECTS     {
        vRtrBgpEvpnVrfPolicyLastChg,
        vRtrBgpEvpnVrfPolicyImp1,
        vRtrBgpEvpnVrfPolicyImp2,
        vRtrBgpEvpnVrfPolicyImp3,
        vRtrBgpEvpnVrfPolicyImp4,
        vRtrBgpEvpnVrfPolicyImp5,
        vRtrBgpEvpnVrfPolicyImp6,
        vRtrBgpEvpnVrfPolicyImp7,
        vRtrBgpEvpnVrfPolicyImp8,
        vRtrBgpEvpnVrfPolicyImp9,
        vRtrBgpEvpnVrfPolicyImp10,
        vRtrBgpEvpnVrfPolicyImp11,
        vRtrBgpEvpnVrfPolicyImp12,
        vRtrBgpEvpnVrfPolicyImp13,
        vRtrBgpEvpnVrfPolicyImp14,
        vRtrBgpEvpnVrfPolicyImp15,
        vRtrBgpEvpnVrfPolicyExp1,
        vRtrBgpEvpnVrfPolicyExp2,
        vRtrBgpEvpnVrfPolicyExp3,
        vRtrBgpEvpnVrfPolicyExp4,
        vRtrBgpEvpnVrfPolicyExp5,
        vRtrBgpEvpnVrfPolicyExp6,
        vRtrBgpEvpnVrfPolicyExp7,
        vRtrBgpEvpnVrfPolicyExp8,
        vRtrBgpEvpnVrfPolicyExp9,
        vRtrBgpEvpnVrfPolicyExp10,
        vRtrBgpEvpnVrfPolicyExp11,
        vRtrBgpEvpnVrfPolicyExp12,
        vRtrBgpEvpnVrfPolicyExp13,
        vRtrBgpEvpnVrfPolicyExp14,
        vRtrBgpEvpnVrfPolicyExp15,
        vRtrBgpEvpnVrfRD,
        vRtrBgpEvpnVrfPolicyTblLastCh,
        vRtrBgpEvpnMplsTnlEncapMoUdp,
        vRtrBgpEvpnAutoRD,
        vRtrBgpEvpnExportRteTarget,
        vRtrBgpEvpnImportRteTarget,
        vRtrBgpEvpnABTTblLastCh,
        vRtrBgpEvpnAdminState,
        vRtrBgpEvpnAutoBndTnlBgp,
        vRtrBgpEvpnAutoBndTnlEcmp,
        vRtrBgpEvpnAutoBndTnlLastChg,
        vRtrBgpEvpnAutoBndTnlLdp,
        vRtrBgpEvpnAutoBndTnlRsvpTe,
        vRtrBgpEvpnAutoBndTnlSrIsis,
        vRtrBgpEvpnAutoBndTnlSrOspf,
        vRtrBgpEvpnAutoBndTnlSrOspf3,
        vRtrBgpEvpnAutoBndTnlSrPlcy,
        vRtrBgpEvpnAutoBndTnlSrTe,
        vRtrBgpEvpnAutoBndTnlStatus,
        vRtrBgpEvpnAutoBndTnlTag,
        vRtrBgpEvpnAutoBndTnlUdp,
        vRtrBgpEvpnBndTnlMplsFwdPlcy,
        vRtrBgpEvpnBndTnlRibApi,
        vRtrBgpEvpnDefRtTag,
        vRtrBgpEvpnMplsTnlEncapMpls,
        vRtrBgpEvpnMplsLastChanged,
        vRtrBgpEvpnMplsTblLastCh,
        vRtrBgpEvpnRowStatus,
        vRtrBgpEvpnTblLastCh,
        vRtrBgpEvpnLastChanged,
        vRtrBgpEvpnOperRD,
        vRtrBgpEvpnOperRDType,
        vRtrBgpEvpnVrfPolicyCreateOrig,
        vRtrBgpEvpnVrfTarget,
        vRtrBgpEvpnIflRoutes,
        vRtrBgpEvpnIflActRoutes,
        vRtrBgpEvpnIflAltRoutes,
        vRtrBgpEvpnIflActAltRoutes,
        vRtrV6BgpEvpnIflRoutes,
        vRtrV6BgpEvpnIflActRoutes,
        vRtrV6BgpEvpnIflAltRoutes,
        vRtrV6BgpEvpnIflActAltRoutes,
        vRtrBgpEvpnIffRoutes,
        vRtrBgpEvpnIffActRoutes,
        vRtrV6BgpEvpnIffRoutes,
        vRtrV6BgpEvpnIffActRoutes,
        vRtrFibStatBGPEvpnIflRoutes,
        vRtrFibStatV6BGPEvpnIflRoutes,
        vRtrFibStatBGPEvpnIffRoutes,
        vRtrFibStatV6BGPEvpnIffRoutes
    }
    STATUS      current
    DESCRIPTION
        "The group of objects supporting management of layer-3 BGP-EVPN on
         release 20.0 in Nokia SROS series systems."
    ::= { tmnxVRtrGroups 271 }

tmnxVRtrLspBfdV20v0Group         OBJECT-GROUP
    OBJECTS     {
        vRtrLspBfdTableLastChanged,
        vRtrLspBfdLastChanged,
        vRtrLspBfdTailEndTxInterval,
        vRtrLspBfdTailEndRxInterval,
        vRtrLspBfdTailEndMultiplier
    }
    STATUS      current
    DESCRIPTION
        "The group of objects supporting management of BFD on LSP feature for
         transport and virtual routers on version 20.0 Nokia SROS series
         systems."
    ::= { tmnxVRtrGroups 272 }

tmnxVRtrIcmpRedirectV20v0Group   OBJECT-GROUP
    OBJECTS     {
        tmnxVrtrIPAllowICMPRedirect
    }
    STATUS      current
    DESCRIPTION
        "The group of objects supporting management of IP ICMP  Redirect
         message for release 20 on Nokia SROS series systems."
    ::= { tmnxVRtrGroups 273 }

vRtrIfEthLoopbackV20v0Group      OBJECT-GROUP
    OBJECTS     {
        vRtrIfEthLoopbackTblLastCh,
        vRtrIfEthLoopbackRowStatus,
        vRtrIfEthLoopbackMacSwap,
        vRtrIfEthLoopbackOperState
    }
    STATUS      current
    DESCRIPTION
        "The group of objects supporting management of router interface
         loopback for release 20 on Nokia SROS series systems."
    ::= { tmnxVRtrGroups 274 }

tmnxVRtrBgpLabelIpv620v0Group    OBJECT-GROUP
    OBJECTS     {
        vRtrStatTotalBgpV6Tunnels,
        vRtrStatActiveBgpV6Tunnels
    }
    STATUS      current
    DESCRIPTION
        "The group of objects supporting management of BGP label-ipv6 entities
         for release 20.0 on Nokia SROS series systems."
    ::= { tmnxVRtrGroups 275 }

vRtrIfEthLoopbackNotifGroup      NOTIFICATION-GROUP
    NOTIFICATIONS {
        vRtrIfEthLoopbackStarted,
        vRtrIfEthLoopbackStopped
    }
    STATUS      current
    DESCRIPTION
        "The group of objects supporting ethernet loopback notifications on
         virtual routers for version 20.0 Nokia SROS series systems."
    ::= { tmnxVRtrGroups 276 }

tmnxVRtrNotificationV20v0Group   NOTIFICATION-GROUP
    NOTIFICATIONS {
        tmnxVRtrBfdExtNoFreeTxIntrvlSlot
    }
    STATUS      current
    DESCRIPTION
        "The group of notifications supporting the transport and virtual router
         capabilities on release 20 Nokia SROS series systems."
    ::= { tmnxVRtrGroups 277 }

tmnxVRtrHelperMplsStatsPktsGroup OBJECT-GROUP
    OBJECTS     {
        vRtrIfRxIpMplsBytes,
        vRtrIfRxIpMplsPkts,
        vRtrIfTxIpMplsBytes,
        vRtrIfTxIpMplsPkts
    }
    STATUS      current
    DESCRIPTION
        "The group of objects "
    ::= { tmnxVRtrGroups 278 }

tmnxVRtrPlcyAcctQPPB20v0Group    OBJECT-GROUP
    OBJECTS     {
        vRtrPlcyAcctPolicerTblLstChgd,
        vRtrPlcyAcctPolicerRowStatus,
        vRtrPlcyAcctPolicerLastChgd,
        vRtrPlcyAcctPolicerPeakRateHi,
        vRtrPlcyAcctPolicerPeakRateLo,
        vRtrPlcyAcctPolicerMaxBurstSize,
        vRtrPlcyAcctDestClassPolicerId,
        vRtrPlcyAcctIfPolStatsTblLstChgd,
        vRtrPlcyAcctPolicerDropPkts,
        vRtrPlcyAcctPolicerDropBytes,
        vRtrPlcyAcctPolicerFwdPkts,
        vRtrPlcyAcctPolicerFwdBytes,
        vRtrPlcyAcctPolicerIncompleteCnt
    }
    STATUS      current
    DESCRIPTION
        "The group of objects supporting management of router policy-accounting
         template entries for release 20.0 on Nokia SROS series systems."
    ::= { tmnxVRtrGroups 279 }

tmnxVRtrStaticRtBackupNHGroup    OBJECT-GROUP
    OBJECTS     {
        vRtrInetStaticRoutePfxBackupTag,
        vRtrInetStaticRouteBackupNHType,
        vRtrInetStaticRouteBackupNHAddr,
        vRtrInetStaticRouteBackupStatus
    }
    STATUS      current
    DESCRIPTION
        "The group of objects supporting management of static route  backup
         next hop tag for release 21 on Nokia SROS series systems."
    ::= { tmnxVRtrGroups 280 }

vRtrBgpIpVpnMplsGroup            OBJECT-GROUP
    OBJECTS     {
        vRtrBgpIpVpnMplsAdminState
    }
    STATUS      current
    DESCRIPTION
        "The group of objects supporting management of BGP IP VPN MPLS features
         for release 21 on Nokia SROS series systems."
    ::= { tmnxVRtrGroups 281 }

tmnxVRtrMtrace2V21Group          OBJECT-GROUP
    OBJECTS     {
        vRtrMtrace2OperState
    }
    STATUS      current
    DESCRIPTION
        "The group of objects supporting management of Multicast Trace Route V2
         tests for Release 21 on Nokia SROS series systems."
    ::= { tmnxVRtrGroups 282 }

tmnxVRtrBgpEvpnV21v0Grp          OBJECT-GROUP
    OBJECTS     {
        vRtrBgpEvpnAutoBndTnlFlexAlgoFb
    }
    STATUS      current
    DESCRIPTION
        "The group of objects supporting management of layer-3 BGP-EVPN on
         release 21.0 in Nokia SROS series systems."
    ::= { tmnxVRtrGroups 284 }

tmnxVRtrV21v0Group               OBJECT-GROUP
    OBJECTS     {
        vRtrIfDHCP6LseSplitAdminState,
        vRtrIfDHCP6LseSplitValidLifetime,
        vRtrIfIpv6FlowLabelHashing,
        vRtrIfDHCPReleaseIncludeGiaddr
    }
    STATUS      current
    DESCRIPTION
        "The group of objects supporting management of transport and virtual
         Routers new on release 21.0 in Nokia SROS series systems."
    ::= { tmnxVRtrGroups 285 }

tmnxVRtrSrV6Isis21v0Group        OBJECT-GROUP
    OBJECTS     {
        vRtrStatActiveSrV6IsisTunnels,
        vRtrStatTotalSrV6IsisTunnels
    }
    STATUS      current
    DESCRIPTION
        "The group of objects supporting management of SR V6 ISIS entities for
         release 21.0 on Nokia SROS series systems."
    ::= { tmnxVRtrGroups 286 }

tmnxVRtrBgpSrv6V21v0Group        OBJECT-GROUP
    OBJECTS     {
        vRtrBgpSrv6VrfPolicyLastChg,
        vRtrBgpSrv6VrfPolicyImp1,
        vRtrBgpSrv6VrfPolicyImp2,
        vRtrBgpSrv6VrfPolicyImp3,
        vRtrBgpSrv6VrfPolicyImp4,
        vRtrBgpSrv6VrfPolicyImp5,
        vRtrBgpSrv6VrfPolicyImp6,
        vRtrBgpSrv6VrfPolicyImp7,
        vRtrBgpSrv6VrfPolicyImp8,
        vRtrBgpSrv6VrfPolicyImp9,
        vRtrBgpSrv6VrfPolicyImp10,
        vRtrBgpSrv6VrfPolicyImp11,
        vRtrBgpSrv6VrfPolicyImp12,
        vRtrBgpSrv6VrfPolicyImp13,
        vRtrBgpSrv6VrfPolicyImp14,
        vRtrBgpSrv6VrfPolicyImp15,
        vRtrBgpSrv6VrfPolicyExp1,
        vRtrBgpSrv6VrfPolicyExp2,
        vRtrBgpSrv6VrfPolicyExp3,
        vRtrBgpSrv6VrfPolicyExp4,
        vRtrBgpSrv6VrfPolicyExp5,
        vRtrBgpSrv6VrfPolicyExp6,
        vRtrBgpSrv6VrfPolicyExp7,
        vRtrBgpSrv6VrfPolicyExp8,
        vRtrBgpSrv6VrfPolicyExp9,
        vRtrBgpSrv6VrfPolicyExp10,
        vRtrBgpSrv6VrfPolicyExp11,
        vRtrBgpSrv6VrfPolicyExp12,
        vRtrBgpSrv6VrfPolicyExp13,
        vRtrBgpSrv6VrfPolicyExp14,
        vRtrBgpSrv6VrfPolicyExp15,
        vRtrBgpSrv6VrfRD,
        vRtrBgpSrv6VrfPolicyTblLastCh,
        vRtrBgpSrv6AutoRD,
        vRtrBgpSrv6ExportVrfTarget,
        vRtrBgpSrv6ImportVrfTarget,
        vRtrBgpSrv6AdminState,
        vRtrBgpSrv6RowStatus,
        vRtrBgpSrv6DefRtTag,
        vRtrBgpSrv6TblLastCh,
        vRtrBgpSrv6LastChanged,
        vRtrBgpSrv6OperRD,
        vRtrBgpSrv6OperRDType,
        vRtrBgpSrv6VrfPolicyCreateOrig,
        vRtrBgpSrv6VrfTarget,
        vRtrBgpSrv6Instance,
        vRtrBgpSrv6DefLocator,
        vRtrBgpSrv6SrcAddr,
        vRtrBgpSrv6SrcAddrType
    }
    STATUS      current
    DESCRIPTION
        "The group of objects supporting management of layer-3 BGP-EVPN on
         release 21.0 in Nokia SROS series systems."
    ::= { tmnxVRtrGroups 287 }

tmnxVRtrFlexAlgoDelayV21v0Group  OBJECT-GROUP
    OBJECTS     {
        vRtrIfLinkDelayStatic
    }
    STATUS      current
    DESCRIPTION
        "The group of objects supporting management of transport and virtual
         routers new on release 21.0 in Nokia SROS series systems."
    ::= { tmnxVRtrGroups 289 }

tmnxVRtrFlexAlgoDlyDynV21v0Group OBJECT-GROUP
    OBJECTS     {
        vRtrIfLinkDelaySelection,
        vRtrIfLinkDelayOper,
        vRtrIfLinkDelayDynamic,
        vRtrIfLinkDelayMeasureTemplName,
        vRtrIfLnkDlyTwampIpv4AdminState,
        vRtrIfLnkDlyTwampIpv4DstAddrType,
        vRtrIfLnkDlyTwampIpv4DstAddr,
        vRtrIfLnkDlyTwampIpv4SrcAddrType,
        vRtrIfLnkDlyTwampIpv4SrcAddr,
        vRtrIfLnkDlyTwampIpv6AdminState,
        vRtrIfLnkDlyTwampIpv6DstAddrType,
        vRtrIfLnkDlyTwampIpv6DstAddr,
        vRtrIfLnkDlyTwampIpv6SrcAddrType,
        vRtrIfLnkDlyTwampIpv6SrcAddr
    }
    STATUS      current
    DESCRIPTION
        "The group of objects supporting management of transport and virtual
         routers new on release 21.0 in Nokia SROS series systems."
    ::= { tmnxVRtrGroups 290 }

tmnxVRtrGlobalObsoleteV21v0Grp   OBJECT-GROUP
    OBJECTS     {
        vRtrStatBGPEvpnRoutes,
        vRtrStatBGPEvpnActiveRoutes,
        vRtrV6StatBGPEvpnRoutes,
        vRtrV6StatBGPEvpnActiveRoutes,
        vRtrFibStatBGPEvpnRoutes,
        vRtrFibStatV6BGPEvpnRoutes
    }
    STATUS      current
    DESCRIPTION
        "The group of router objects obsoleted for release 21.0 on  Nokia SROS
         series systems."
    ::= { tmnxVRtrGroups 291 }

tmnxVRtrSrV621v0Group            OBJECT-GROUP
    OBJECTS     {
        vRtrInetExtTunnelSidAddrType,
        vRtrInetExtTunnelSidAddr,
        vRtrFibStatSrV6Routes,
        vRtrStatSrV6ActiveRoutes,
        vRtrStatSrV6TotalRoutes
    }
    STATUS      current
    DESCRIPTION
        "The group of objects supporting management of SR V6 entities for
         release 21.0 on Nokia SROS series systems."
    ::= { tmnxVRtrGroups 292 }

tmnxVRtrNotificationObjV21v0Grp  OBJECT-GROUP
    OBJECTS     {
        vRtrID,
        vRtrIfIndex,
        vRtrDhcpPacketProblem,
        vRtrBfdSlotNumber,
        vRtrNumberOfBfdSessionsOnSlot,
        vRtrBfdMaxSessionReason,
        vRtrDHCP6ServerNetAddrType,
        vRtrDHCP6ServerNetAddr,
        vRtrDHCP6ClientNetAddrType,
        vRtrDHCP6ClientNetAddr,
        vRtrDHCP6AssignedNetAddrType,
        vRtrDHCP6AssignedNetAddr,
        vRtrDHCP6AssignedPrefixLen,
        vRtrDHCP6OldAssignedNetAddrType,
        vRtrDHCP6OldAssignedNetAddr,
        vRtrDHCP6OldAssignedPrefixLen,
        vRtrDHCP6NewClientId,
        vRtrDHCP6OldClientId,
        vRtrDHCP6LeaseOverrideResult,
        vRtrInetStatRteCpeNotifyAddrType,
        vRtrInetStatRteCpeNotifyAddr,
        vRtrInetStaticRouteCpeStatus,
        vRtrManagedRouteInetAddrType,
        vRtrManagedRouteInetAddr,
        vRtrManagedRoutePrefixLen,
        vRtrFailureDescription,
        vRtrMaxRoutesType,
        vRtrSlotOrCpmFlag,
        vRtrNotifInetAddrType,
        vRtrNotifInetAddr,
        vRtrIfBfdSessChangedProtocol,
        vRtrIfBfdSessProtoChngdState
    }
    STATUS      current
    DESCRIPTION
        "The group of objects supporting management of notification objects on
         Nokia SROS 21.0 series systems."
    ::= { tmnxVRtrGroups 293 }

tmnxVRtrFibStatObj21Group        OBJECT-GROUP
    OBJECTS     {
        vRtrFibStatIpVpnCurrUtilization
    }
    STATUS      current
    DESCRIPTION
        "The group of objects fib occupancy for Release 21 on Nokia SROS series
         systems."
    ::= { tmnxVRtrGroups 294 }

tmnxVRtrNotificationObj21Group   NOTIFICATION-GROUP
    NOTIFICATIONS {
        tmnxVRtrFibVPNOccupancyThreshold
    }
    STATUS      current
    DESCRIPTION
        "The group of objects fib occupancy for Release 21 on Nokia SROS series
         systems."
    ::= { tmnxVRtrGroups 295 }

tmnxVRtrDPathAttrObj21Group      OBJECT-GROUP
    OBJECTS     {
        vRtrBgpEvpnDomainId,
        vRtrBgpSrv6DomainId,
        vRtrBgpIpVpnMplsDomainId,
        vRtrLocalRoutesDomainId,
        vRtrDpathLengthIgnore,
        vRtrDPathAttrLastChanged
    }
    STATUS      current
    DESCRIPTION
        "The group of objects supporting D-Path Attribute for routes
         advertisement for Release 21 on Nokia SROS series systems."
    ::= { tmnxVRtrGroups 297 }

tmnxVRtrIfHQosOnLagV21v0Group    OBJECT-GROUP
    OBJECTS     {
        vRtrIfQosEgrVlanPlcyPortRedirect
    }
    STATUS      current
    DESCRIPTION
        "The group of router interface HQos on LAG specific objects in release
         21.0 on Nokia SROS series systems."
    ::= { tmnxVRtrGroups 298 }

tmnxVRtrDynEgLblLmtObj22Group    OBJECT-GROUP
    OBJECTS     {
        vRtrBgpEvpnDynEgrLblLmt,
        vRtrBgpIpVpnMplsDynEgrLblLmt
    }
    STATUS      current
    DESCRIPTION
        "The group of objects supporting for extending Egress Label Limit for
         Release 22 on Nokia SROS series systems."
    ::= { tmnxVRtrGroups 299 }

tmnxVRtrIfV22v0Group             OBJECT-GROUP
    OBJECTS     {
        vRtrIfIngressIPFilterPair
    }
    STATUS      current
    DESCRIPTION
        "The group of objects supporting management of IP filter pair on the
         router interface on release 22.0 in Nokia SROS series systems."
    ::= { tmnxVRtrGroups 300 }

tmnxVRtrObsoleteV22v0Group       OBJECT-GROUP
    OBJECTS     {
        vRtrSvcIpRangeAddress,
        vRtrSvcIpRangeMask,
        vRtrSvcIpRangeRowStatus,
        vRtrSvcIpRangeExclusive,
        vRtrInetSvcIpRangeRowStatus,
        vRtrInetSvcIpRangeExclusive
    }
    STATUS      current
    DESCRIPTION
        "The group of objects supporting management of IP capabilities for
         transport and virtual routers on version 4.0 Nokia SROS series
         systems."
    ::= { tmnxVRtrGroups 301 }

tmnxVRtrBgpEvpnEviGroup          OBJECT-GROUP
    OBJECTS     {
        vRtrBgpEvpnEvi
    }
    STATUS      current
    DESCRIPTION
        "The group of objects supporting management of VPRN BGP EVPN
         capabilities on version 4.0 Nokia SROS series systems."
    ::= { tmnxVRtrGroups 302 }

tmnxVRtrIfExtParmsV22v0Group     OBJECT-GROUP
    OBJECTS     {
        vRtrIfIcmpTtlExpiredMatchingAddr,
        vRtrIfExtRefOcSubIfPresence,
        vRtrIfExtRefOcSubIf
    }
    STATUS      current
    DESCRIPTION
        "The group of basic router interface specific additional objects
         associated for release 22.0 on Nokia SROS series systems."
    ::= { tmnxVRtrGroups 303 }

tmnxVRtrIfDcpFpCountV22v0Group   OBJECT-GROUP
    OBJECTS     {
        vRtrIfDcpFpStaticTotalExcdCount,
        vRtrIfDcpFpStaticExtCnfrmStCount,
        vRtrIfDcpFpDynTotalExcdCount,
        vRtrIfDcpFpDynExtCnfrmStateCount,
        vRtrIfDcpFpLocMonTotalExcdCount,
        vRtrIfDcpFpLocMonExtCnfrmStCount
    }
    STATUS      current
    DESCRIPTION
        "The group of DCPU objects for which exceed counter will not reset for
         release 22.0 on Nokia SROS series systems."
    ::= { tmnxVRtrGroups 304 }

vRtrSrV6PolicyGroup              OBJECT-GROUP
    OBJECTS     {
        vRtrStatActiveSrV6PolicyTunnels,
        vRtrStatTotalSrV6PolicyTunnels,
        vRtrStatActiveSrV6PolicyRoutes,
        vRtrStatTotalSrV6PolicyRoutes,
        vRtrBgpSrv6Resolution
    }
    STATUS      current
    DESCRIPTION
        "The group of objects supporting segment routing v6 policies on Nokia
         SROS series systems."
    ::= { tmnxVRtrGroups 306 }

vRtrBgpEvpnSrv6EviGroup          OBJECT-GROUP
    OBJECTS     {
        vRtrBgpSrv6Evi
    }
    STATUS      current
    DESCRIPTION
        "The group of objects supporting management of VPRN BGP EVPN  SRv6
         capabilities on version 4.0 Nokia SROS series systems."
    ::= { tmnxVRtrGroups 307 }

vRtrBgpEvpnUneqalEcmpV22v0Group  OBJECT-GROUP
    OBJECTS     {
        vRtrBgpEvpnAdLinkBw,
        vRtrBgpEvpnAdLinkBwWeight,
        vRtrBgpEvpnAdLinkBwMaxWeight,
        vRtrBgpEvpnWeightedEcmp
    }
    STATUS      current
    DESCRIPTION
        "The group of objects supporting management of unequal ecmp for
         evpn-ifl routes on Nokia SROS series systems in release 22.0."
    ::= { tmnxVRtrGroups 308 }

tmnxVRtrIfQosV22v0Group          OBJECT-GROUP
    OBJECTS     {
        vRtrIfQosEgrAggRatePIRPercent,
        vRtrIfQosEgrAggRateCIRPercent,
        vRtrIfQosEgrAggRateType
    }
    STATUS      current
    DESCRIPTION
        "The group of basic router interface specific objects in release 22.0
         on Nokia SROS series systems."
    ::= { tmnxVRtrGroups 309 }

tmnxvRtrEsaVideoRoutesGroup      OBJECT-GROUP
    OBJECTS     {
        vRtrStatActiveV4VideoRoutes,
        vRtrStatTotalV4VideoRoutes,
        vRtrStatActiveV6VideoRoutes,
        vRtrStatTotalV6VideoRoutes,
        vRtrMcastIpv4ActiveVideoRoutes,
        vRtrMcastIpv4TotalVideoRoutes,
        vRtrMcastIpv6ActiveVideoRoutes,
        vRtrMcastIpv6TotalVideoRoutes
    }
    STATUS      current
    DESCRIPTION
        "The group of objects supporting video routes in release 22.0 on Nokia
         SROS series systems."
    ::= { tmnxVRtrGroups 310 }

tmnxVRtrNdRaRoutesGroup          OBJECT-GROUP
    OBJECTS     {
        vRtrStatV6NdRaRoutes,
        vRtrStatV6NdRaActiveRoutes
    }
    STATUS      current
    DESCRIPTION
        "The group of objects supporting ND-RA routes in release 22.0 on Nokia
         SROS series systems."
    ::= { tmnxVRtrGroups 311 }

tmnxVRtrNotificationV23v0Group   NOTIFICATION-GROUP
    NOTIFICATIONS {
        tmnxVRtrBfdMultiHopFpMismatch
    }
    STATUS      current
    DESCRIPTION
        "The group of notifications supporting the transport and virtual router
         capabilities added in release 23 Nokia SROS series systems."
    ::= { tmnxVRtrGroups 312 }

tmnxVRtrNotifyObjsV23v0Group     OBJECT-GROUP
    OBJECTS     {
        vRtrNotifyFpNum
    }
    STATUS      current
    DESCRIPTION
        "The group of objects supporting notifications added in Release 23 on
         Nokia SROS series systems."
    ::= { tmnxVRtrGroups 313 }

tmnxVRtrSubDhcp4V23v0Group       OBJECT-GROUP
    OBJECTS     {
        vRtrSubDhcp4LastChanged,
        vRtrSubDhcp4TransparentForward,
        vRtrSubDhcp4TranspFwdClntPkts,
        vRtrSubDhcp4TranspFwdServPkts,
        vRtrSubDhcp4TranspFwdOtherPkts
    }
    STATUS      current
    DESCRIPTION
        "The group of objects supporting DHCPv4 settings per virtual router on
         Nokia SROS series systems since release 23.0."
    ::= { tmnxVRtrGroups 314 }

tmnxVRtrObsoleteV23v0Group       OBJECT-GROUP
    OBJECTS     {
        vRtrIfIpTunnelRemoteIpAddrType,
        vRtrIfIpTunnelRemoteIpAddr
    }
    STATUS      current
    DESCRIPTION
        "The group of objects supporting management of IP capabilities for
         transport and virtual routers on version 23.3.0 Nokia SROS series
         systems."
    ::= { tmnxVRtrGroups 315 }

tmnxVRtrV23Group                 OBJECT-GROUP
    OBJECTS     {
        vRtrIfUrpfSelectedVprnsOnly,
        vRtrAllowBgpToIgpExport,
        vRtrBgpEvpnOperState,
        vRtrBgpSrv6OperState,
        vRtrIpv6RtrAdvertNdRtrPreference,
        vRtrIfMtuProfile,
        vRtrIfOperMtuProfile,
        vRtrIfAllocMtuProfile,
        vRtrIfDHCP6AllowClntIdChng
    }
    STATUS      current
    DESCRIPTION
        "The group of basic router interface specific additional objects added
         for release 23.0 on Nokia SROS series systems."
    ::= { tmnxVRtrGroups 316 }

tmnxVRtrBgpIpVpnV21Group         OBJECT-GROUP
    OBJECTS     {
        vRtrBgpIpVpnMplsOperState
    }
    STATUS      current
    DESCRIPTION
        "The group of BGP IP-VPN specific additional objects added for release
         21.0 on Nokia SROS series systems."
    ::= { tmnxVRtrGroups 317 }

tmnxVRtrNotificationV21v0Group   NOTIFICATION-GROUP
    NOTIFICATIONS {
        vRtrBgpInstanceError
    }
    STATUS      current
    DESCRIPTION
        "The group of notifications supporting the transport and virtual router
         capabilities added in release 21 Nokia SROS series systems."
    ::= { tmnxVRtrGroups 318 }

tmnxVRtrNotifyObjsV21v0Group     OBJECT-GROUP
    OBJECTS     {
        vRtrNotifyBgpInstType,
        vRtrNotifyBgpInstance
    }
    STATUS      current
    DESCRIPTION
        "The group of objects supporting notifications added in Release 21 on
         Nokia SROS series systems."
    ::= { tmnxVRtrGroups 319 }

tmnxVRtrV21Group                 OBJECT-GROUP
    OBJECTS     {
        vRtrBgpEvpnOperState,
        vRtrBgpSrv6OperState
    }
    STATUS      current
    DESCRIPTION
        "The group of basic router interface specific additional objects added
         for release 21.0 on Nokia SROS series systems."
    ::= { tmnxVRtrGroups 320 }

tmnxVRtrBgpIpVpnAttrSetGroup     OBJECT-GROUP
    OBJECTS     {
        vRtrBgpIpVpnAttrSetImport,
        vRtrBgpIpVpnAttrSetExport
    }
    STATUS      current
    DESCRIPTION
        "The group of objects supporting BGP IP-VPN ATTR_SET on Nokia SROS
         series system."
    ::= { tmnxVRtrGroups 321 }

tmnxVrtrBgpSrv6UqlEcmpV23v0Group OBJECT-GROUP
    OBJECTS     {
        vRtrBgpSrv6AdLinkBw,
        vRtrBgpSrv6AdLinkBwWeight,
        vRtrBgpSrv6AdLinkBwMaxWeight,
        vRtrBgpSrv6WeightedEcmp
    }
    STATUS      current
    DESCRIPTION
        "The group of objects supporting BGP SRv6 evpn unequal ecmp for
         evpn-ifl routes on Nokia SROS series system."
    ::= { tmnxVRtrGroups 322 }

tmnxVRtrSrMplsTTLPropagateGroup  OBJECT-GROUP
    OBJECTS     {
        vRtrTTLPropSrMplsLocal,
        vRtrTTLPropSrMplsTransit
    }
    STATUS      current
    DESCRIPTION
        "The group of objects supporting SR MPLS TTL propagation  on Nokia SROS
         series system."
    ::= { tmnxVRtrGroups 323 }

tmnxVRtrBgpExpInactiveAllGroup   OBJECT-GROUP
    OBJECTS     {
        vRtrBgpExportInactiveBgpEnhanced
    }
    STATUS      current
    DESCRIPTION
        "The group of objects supporting extended scope for exporting inactive
         routes in a VPRN BGP instance on Nokia SROS series system."
    ::= { tmnxVRtrGroups 324 }

tmnxVRtrStaticRtVprnCondRtGroup  OBJECT-GROUP
    OBJECTS     {
        vRtrInetStaticRoutePfxLstRtrInst
    }
    STATUS      current
    DESCRIPTION
        "The group of objects supporting static route VPRN conditional routes
         on Nokia SROS series system."
    ::= { tmnxVRtrGroups 325 }

tmnxVRtrBgpNhResGroup            OBJECT-GROUP
    OBJECTS     {
        vRtrBgpEvpnAutoBndTnlUntagRt
    }
    STATUS      current
    DESCRIPTION
        "The group of objects supporting BGP NHRES VPRN  routes on Nokia SROS
         series system."
    ::= { tmnxVRtrGroups 326 }

tmnxVRtrEsmBcastGroup            OBJECT-GROUP
    OBJECTS     {
        vRtrStatActiveV4EsmBcastRoutes,
        vRtrStatTotalV4EsmBcastRoutes
    }
    STATUS      current
    DESCRIPTION
        "The group of objects supporting ESM Broadcast routes  on Nokia SROS
         series system."
    ::= { tmnxVRtrGroups 327 }

tmnxVRtrUpaRouteGroup            OBJECT-GROUP
    OBJECTS     {
        vRtrInetCidrUpaRouteAge,
        vRtrInetCidrUpaRouteProto,
        vRtrInetCidrUpaRouteProtoInst,
        vRtrInetCidrUpaRoutePreference,
        vRtrInetCidrUpaRouteMetric,
        vRtrBgpSrv6UpaTriggerNextHop
    }
    STATUS      current
    DESCRIPTION
        "The group of objects supporting unreachable prefix announcement routes
         on Nokia SROS series system."
    ::= { tmnxVRtrGroups 328 }

tmnxVRtrSysMacAddrRangeGroup     OBJECT-GROUP
    OBJECTS     {
        tmnxVrtrIPStartMacAddress,
        tmnxVrtrIPEndMacAddress
    }
    STATUS      current
    DESCRIPTION
        "The group of objects that indicate the usable IP interface MAC address
         range."
    ::= { tmnxVRtrGroups 329 }

tmnxVRtrSysCommonMacAddrGroup    OBJECT-GROUP
    OBJECTS     {
        tmnxVrtrIPCommonMacAddress
    }
    STATUS      current
    DESCRIPTION
        "The group of objects that indicate the usable IP interface common MAC
         address."
    ::= { tmnxVRtrGroups 330 }

tmnxVRtrIfQosV24v0Group          OBJECT-GROUP
    OBJECTS     {
        vRtrIfQosEgrAggRateBurstLmt
    }
    STATUS      current
    DESCRIPTION
        "The group of basic router interface specific objects in release 24.0
         on Nokia SROS series systems."
    ::= { tmnxVRtrGroups 331 }

vRtrVprnVxlanV24Group            OBJECT-GROUP
    OBJECTS     {
        vRtrBgpEvpnVxTblLastCh,
        vRtrBgpEvpnVxRowStatus,
        vRtrBgpEvpnVxLastChanged,
        vRtrBgpEvpnVxAdminState,
        vRtrBgpEvpnVxDefRtTag,
        vRtrBgpEvpnVxVrfRD,
        vRtrBgpEvpnVxExportRteTarget,
        vRtrBgpEvpnVxImportRteTarget,
        vRtrBgpEvpnVxAutoRD,
        vRtrBgpEvpnVxOperRD,
        vRtrBgpEvpnVxOperRDType,
        vRtrBgpEvpnVxVrfTarget,
        vRtrBgpEvpnVxDomainId,
        vRtrBgpEvpnVxEvi,
        vRtrBgpEvpnVxAdLinkBw,
        vRtrBgpEvpnVxAdLinkBwWeight,
        vRtrBgpEvpnVxAdLinkBwMaxWeight,
        vRtrBgpEvpnVxWeightedEcmp,
        vRtrBgpEvpnVxOperState,
        vRtrBgpEvpnVxInstance,
        vRtrBgpEvpnVxVrfPlcyTblLastCh,
        vRtrBgpEvpnVxVrfPolicyLastChg,
        vRtrBgpEvpnVxVrfPolicyImp1,
        vRtrBgpEvpnVxVrfPolicyImp2,
        vRtrBgpEvpnVxVrfPolicyImp3,
        vRtrBgpEvpnVxVrfPolicyImp4,
        vRtrBgpEvpnVxVrfPolicyImp5,
        vRtrBgpEvpnVxVrfPolicyImp6,
        vRtrBgpEvpnVxVrfPolicyImp7,
        vRtrBgpEvpnVxVrfPolicyImp8,
        vRtrBgpEvpnVxVrfPolicyImp9,
        vRtrBgpEvpnVxVrfPolicyImp10,
        vRtrBgpEvpnVxVrfPolicyImp11,
        vRtrBgpEvpnVxVrfPolicyImp12,
        vRtrBgpEvpnVxVrfPolicyImp13,
        vRtrBgpEvpnVxVrfPolicyImp14,
        vRtrBgpEvpnVxVrfPolicyImp15,
        vRtrBgpEvpnVxVrfPolicyExp1,
        vRtrBgpEvpnVxVrfPolicyExp2,
        vRtrBgpEvpnVxVrfPolicyExp3,
        vRtrBgpEvpnVxVrfPolicyExp4,
        vRtrBgpEvpnVxVrfPolicyExp5,
        vRtrBgpEvpnVxVrfPolicyExp6,
        vRtrBgpEvpnVxVrfPolicyExp7,
        vRtrBgpEvpnVxVrfPolicyExp8,
        vRtrBgpEvpnVxVrfPolicyExp9,
        vRtrBgpEvpnVxVrfPolicyExp10,
        vRtrBgpEvpnVxVrfPolicyExp11,
        vRtrBgpEvpnVxVrfPolicyExp12,
        vRtrBgpEvpnVxVrfPolicyExp13,
        vRtrBgpEvpnVxVrfPolicyExp14,
        vRtrBgpEvpnVxVrfPolicyExp15,
        vRtrBgpEvpnVxVrfPolicyCreateOrig,
        vRtrInetCidrRouteEgrVni,
        vRtrInetAllCidrRouteEgrVni
    }
    STATUS      current
    DESCRIPTION
        "The group of VPRN VXLAN  specific objects
         in release 24.0 on Nokia SROS series systems."
    ::= { tmnxVRtrGroups 332 }

tmnxVRtrMvpnPmsiV24v0Group       OBJECT-GROUP
    OBJECTS     {
        vRtrMvpnWldCrdSpmsiSuppressIpmsi
    }
    STATUS      current
    DESCRIPTION
        "The group of objects supporting management of Mvpn added in release
         24.0 Nokia SROS series systems."
    ::= { tmnxVRtrGroups 333 }

tmnxVRtrOamLagMeasV24v0Group     OBJECT-GROUP
    OBJECTS     {
        vRtrIfLinkDelayLagMeasTemplName
    }
    STATUS      current
    DESCRIPTION
        "The group of objects supporting LAG Measurement added in release 24.0
         Nokia SROS series systems."
    ::= { tmnxVRtrGroups 334 }

tmnxVRtrIPV24v0Group             OBJECT-GROUP
    OBJECTS     {
        tmnxVrtrIPBufferUnresolvedPkts
    }
    STATUS      current
    DESCRIPTION
        "The group of object supporting management of IP MTU packets for
         release 24 on Nokia SROS series systems."
    ::= { tmnxVRtrGroups 335 }

tmnxVRtrMvpnP2mp24v0Group        OBJECT-GROUP
    OBJECTS     {
        vRtrMvpnIpmsiP2mpPolicySrv6,
        vRtrMvpnSpmsiP2mpPolicySrv6
    }
    STATUS      current
    DESCRIPTION
        "The group of object supporting management of SRv6 p2mp policy  for
         release 24 on Nokia SROS series systems."
    ::= { tmnxVRtrGroups 336 }

vRtrIfIpTunnelV24v0Group         OBJECT-GROUP
    OBJECTS     {
        vRtrIfIpTunnelTableLastChanged,
        vRtrIfIpTunnelRowStatus,
        vRtrIfIpTunnelLastChanged,
        vRtrIfIpTunnelGreHeader,
        vRtrIfIpTunnelDescription,
        vRtrIfIpTunnelLclIpAddrType,
        vRtrIfIpTunnelLclIpAddr,
        vRtrIfIpTunnelRemIpAddrType,
        vRtrIfIpTunnelRemIpAddr,
        vRtrIfIpTunnelOperRemIpAddrType,
        vRtrIfIpTunnelOperRemIpAddr,
        vRtrIfIpTunnelDlvryRtrId,
        vRtrIfIpTunnelAdminState,
        vRtrIfIpTunnelOperState,
        vRtrIfIpTunnelOperFlags,
        vRtrIfIpTunnelOperChanged,
        vRtrIfIpTunnelIngStatsEnabled,
        vRtrIfIpTunnelEgrStatsEnabled,
        vRtrIfIpTunnelEncapsulatedMtu
    }
    STATUS      current
    DESCRIPTION
        "The group of IP tunnel objects for which ... for release 24.0 on Nokia
         SROS series systems."
    ::= { tmnxVRtrGroups 337 }

vRtrStaticRtLeakDestGroup        OBJECT-GROUP
    OBJECTS     {
        vRtrInetStaticRtLeakDestTblLstCh,
        vRtrInetStaticRtLeakDestRowStat
    }
    STATUS      current
    DESCRIPTION
        "The group of objects used for static route leak to destination
         services in release 24.0 on Nokia SROS series systems."
    ::= { tmnxVRtrGroups 338 }

vRtrEvpnIflHostRouteGroup        OBJECT-GROUP
    OBJECTS     {
        vRtrBgpEvpnIflHostActRoutes,
        vRtrBgpEvpnIflHostRoutes,
        vRtrV6BgpEvpnIflHostActRoutes,
        vRtrV6BgpEvpnIflHostRoutes,
        vRtrFibStatBGPEvpnIflHostRoutes,
        vRtrFibStatV6BGPEvpnIflHostRts
    }
    STATUS      current
    DESCRIPTION
        "The group of objects used for BGP EVPN IFL HOST routes  in release
         24.0 on Nokia SROS series systems."
    ::= { tmnxVRtrGroups 339 }

tmnxVRtrNotificationV24v0Group   NOTIFICATION-GROUP
    NOTIFICATIONS {
        vrtrIfIpTunnelOperStateChange
    }
    STATUS      current
    DESCRIPTION
        "The group of notifications supporting the transport and virtual router
         capabilities added in release 24 Nokia SROS series systems."
    ::= { tmnxVRtrGroups 340 }

tmnxVRtrNotifyObjsV24v0Group     OBJECT-GROUP
    OBJECTS     {
        vRtrIfIpTunnelName
    }
    STATUS      current
    DESCRIPTION
        "The group of objects supporting notifications added in Release 24 on
         Nokia SROS series systems."
    ::= { tmnxVRtrGroups 341 }

tmnxVRtrMvpnP2mp25v0Group        OBJECT-GROUP
    OBJECTS     {
        vRtrMvpnServiceReservedLabel
    }
    STATUS      current
    DESCRIPTION
        "The group of object supporting management of mvpn service reserved
         label for release 25 on Nokia SROS series systems."
    ::= { tmnxVRtrGroups 342 }

tmnxVRtrRedIfOverIpv6Group       OBJECT-GROUP
    OBJECTS     {
        vRtrIfIpv6GreTermination
    }
    STATUS      current
    DESCRIPTION
        "The group of object supporting management of redundant-interface over
         IPv6 feature for release 25 on Nokia SROS series systems."
    ::= { tmnxVRtrGroups 343 }

tmnxVRtrBgpEvpnGwIpV25v0Group    OBJECT-GROUP
    OBJECTS     {
        vRtrBgpEvpnGwIpAdvertise,
        vRtrBgpEvpnGwIpResolve,
        vRtrBgpEvpnVxGwIpAdvertise,
        vRtrBgpEvpnVxGwIpResolve
    }
    STATUS      current
    DESCRIPTION
        "The group of objects supporting management of the GW IP addresses of
         evpn ifl routes for release 25 on Nokia SROS series systems"
    ::= { tmnxVRtrGroups 344 }

tmnxVRtrIfNatGroup               OBJECT-GROUP
    OBJECTS     {
        vRtrIfNatTableLastChanged,
        vRtrIfNatRowStatus,
        vRtrIfNatLastChanged,
        vRtrIfNatCpmPolicy,
        vRtrIfNatCpmSpfPolicy
    }
    STATUS      current
    DESCRIPTION
        "The group of objects supporting management of NAT  on an interface on
         Nokia SROS series systems."
    ::= { tmnxVRtrGroups 345 }

tmnxVRtrMvpnGroup                OBJECT-GROUP
    OBJECTS     {
        vRtrMvpnBierPtaLabelInMsb
    }
    STATUS      current
    DESCRIPTION
        "The group of objects supporting management of MVPN on Nokia SROS
         series systems."
    ::= { tmnxVRtrGroups 346 }

tmnxVRtrIPV25v0Group             OBJECT-GROUP
    OBJECTS     {
        tmnxVrtrSysuRPFIgnoreDefault
    }
    STATUS      current
    DESCRIPTION
        "The group of object supporting management of uRPF for release 25 on
         Nokia SROS series systems."
    ::= { tmnxVRtrGroups 347 }

tmnxVRtrBgpEvpnAnySecGroup       OBJECT-GROUP
    OBJECTS     {
        vRtrBgpEvpnAnySecEncGrp
    }
    STATUS      current
    DESCRIPTION
        "The group of objects supporting management of layer-3 BGP-EVPN ANYsec
         encryption Nokia SROS series systems."
    ::= { tmnxVRtrGroups 348 }

tmnxVRtrBgpIpVpnAnySecGroup      OBJECT-GROUP
    OBJECTS     {
        vRtrBgpIpVpnAnySecEncGrp
    }
    STATUS      current
    DESCRIPTION
        "The group of objects supporting management of layer-3 BGP-IPVPN ANYsec
         encryption Nokia SROS series systems."
    ::= { tmnxVRtrGroups 349 }

tmnxVRtrIfDHCPRelayFRGroup       OBJECT-GROUP
    OBJECTS     {
        vRtrIfDHCPRelayForceRenewWoLease,
        vRtrIfDHCP6RelayReconfigureWoLse
    }
    STATUS      current
    DESCRIPTION
        "The group of object supporting management of DHCP Relay FORCERENEW and
         Reconfigure without lease for release 25 on Nokia SROS series systems."
    ::= { tmnxVRtrGroups 350 }

tmnxVRtrQosSinkExcessBWV25v0Grp  OBJECT-GROUP
    OBJECTS     {
        vRtrIfQosEgrSinkExcessBW
    }
    STATUS      current
    DESCRIPTION
        "The group of objects supporting management of SAP egress sink excess
         bandwidth"
    ::= { tmnxVRtrGroups 353 }

tmnxVRtrMobGatewayCompliances    OBJECT IDENTIFIER ::= { tmnxVRtrConformance 3 }

tmnxVRtrMobGatewayGroups         OBJECT IDENTIFIER ::= { tmnxVRtrConformance 4 }

tmnxVRtrIpPoolGroup              OBJECT-GROUP
    OBJECTS     {
        vRtrIpPoolTableLastChanged,
        vRtrIpPoolRowStatus,
        vRtrIpPoolLastChanged,
        vRtrIpPoolDescription,
        vRtrIpPoolExclusive,
        vRtrIpPoolStatFree,
        vRtrIpPoolStatHeld,
        vRtrIpPoolStatAllocated,
        vRtrIpPoolAddressHoldTimer,
        vRtrIpPoolAddrTableLastChanged,
        vRtrIpPoolAddrRowStatus,
        vRtrIpPoolAddrLastChanged,
        vRtrIpPoolAddrBlock,
        vRtrIpPoolAddrIpv6AssignedLen,
        vRtrIpPoolSuppress0and255,
        vRtrConfMobGwTableLastChanged
    }
    STATUS      current
    DESCRIPTION
        "The group of objects supporting management of IP pools on Nokia 7x50
         SR series systems."
    ::= { tmnxVRtrMobGatewayGroups 1 }

tmnxMGVRtrIfV4v0Group            OBJECT-GROUP
    OBJECTS     {
        vRtrIfTrackMobile,
        vRtrIfIpv6TrackMobile,
        vRtrIpPoolIsRemote
    }
    STATUS      current
    DESCRIPTION
        "The group of objects supporting management of router interfaces on
         Nokia mobile gateway systems in 4.0 release."
    ::= { tmnxVRtrMobGatewayGroups 2 }

tmnxDCVRtrCompliances            OBJECT IDENTIFIER ::= { tmnxVRtrConformance 5 }

tmnxDCVRtrGroups                 OBJECT IDENTIFIER ::= { tmnxVRtrConformance 6 }

tmnxVRtrNotifyPrefix             OBJECT IDENTIFIER ::= { tmnxSRNotifyPrefix 3 }

tmnxVRtrNotifications            OBJECT IDENTIFIER ::= { tmnxVRtrNotifyPrefix 0 }

tmnxVRtrMidRouteTCA              NOTIFICATION-TYPE
    OBJECTS     {
        vRtrStatCurrNumRoutes,
        vRtrMidRouteThreshold
    }
    STATUS      current
    DESCRIPTION
        "The tmnxVRtrMidRouteTCA notification is generated when the number
         of routes contained in a VPRN exceeds the value specified by
         vRtrMidRouteThreshold.  No other notifications of this type
         are generated until after the soak period specified by
         vRtrRouteThresholdSoakTime has expired."
    ::= { tmnxVRtrNotifications 1 }

tmnxVRtrHighRouteTCA             NOTIFICATION-TYPE
    OBJECTS     {
        vRtrStatCurrNumRoutes,
        vRtrHighRouteThreshold
    }
    STATUS      current
    DESCRIPTION
        "The tmnxVRtrHighRouteTCA notification is generated when the number
         of routes contained in a VPRN exceeds the value specified by
         vRtrHighRouteThreshold.  No other notifications of this type
         are generated until after the soak period specified by
         vRtrRouteThresholdSoakTime has expired."
    ::= { tmnxVRtrNotifications 2 }

tmnxVRtrHighRouteCleared         NOTIFICATION-TYPE
    OBJECTS     {
        vRtrStatCurrNumRoutes,
        vRtrHighRouteThreshold
    }
    STATUS      current
    DESCRIPTION
        "The tmnxVRtrHighRouteCleared notification is generated when the number
         of routes contained in a VPRN has dropped below the
         vRtrHighRouteThreshold value following the generation of a
         tmnxVRtrHighRouteTCA notification."
    ::= { tmnxVRtrNotifications 3 }

tmnxVRtrIllegalLabelTCA          NOTIFICATION-TYPE
    OBJECTS     {
        vRtrStatIllegalLabels,
        vRtrIllegalLabelThreshold
    }
    STATUS      obsolete
    DESCRIPTION
        "The tmnxVRtrIllegalLabelTCA notification is generated when the number
         of illegal label violations on a VRF has exceeded the value specified
         by vRtrIllegalLabelThreshold.

         This notification is made obsolete in release 14.0."
    ::= { tmnxVRtrNotifications 4 }

tmnxVRtrMcastMidRouteTCA         NOTIFICATION-TYPE
    OBJECTS     {
        vRtrMulticastRoutes,
        vRtrMcastMidRouteThreshold
    }
    STATUS      current
    DESCRIPTION
        "The tmnxVRtrMcastMidRouteTCA notification is generated when the number
         of multicast routes contained in a VPRN exceeds the value specified by
         vRtrMcastMidRouteThreshold.  No other notifications of this type
         are generated until after the soak period specified by
         vRtrRouteThresholdSoakTime has expired."
    ::= { tmnxVRtrNotifications 5 }

tmnxVRtrMcastMaxRoutesTCA        NOTIFICATION-TYPE
    OBJECTS     {
        vRtrMulticastRoutes,
        vRtrMaxMcastNumRoutes
    }
    STATUS      current
    DESCRIPTION
        "The tmnxVRtrMcastMaxRoutesTCA notification is generated when the number
         of multicast routes contained in a VPRN exceeds the value specified by
         vRtrMaxMcastNumRoutes.  No other notifications of this type
         are generated until after the soak period specified by
         vRtrRouteThresholdSoakTime has expired."
    ::= { tmnxVRtrNotifications 6 }

tmnxVRtrMcastMaxRoutesCleared    NOTIFICATION-TYPE
    OBJECTS     {
        vRtrMulticastRoutes,
        vRtrMaxMcastNumRoutes
    }
    STATUS      current
    DESCRIPTION
        "The tmnxVRtrMcastMaxRoutesCleared notification is generated when the
         number of multicast routes contained in a VPRN has dropped below the
         vRtrMaxMcastNumRoutes value following the generation of a
         tmnxVRtrMcastMaxRoutesTCA notification."
    ::= { tmnxVRtrNotifications 7 }

tmnxVRtrMaxArpEntriesTCA         NOTIFICATION-TYPE
    OBJECTS     {
        vRtrStatActiveARPEntries,
        vRtrStatTotalARPEntries,
        vRtrMaxARPEntries
    }
    STATUS      current
    DESCRIPTION
        "The tmnxVRtrMaxArpEntriesTCA notification is generated when the number
         of ARP entries in a VPRN exceeds the maximum supported."
    ::= { tmnxVRtrNotifications 8 }

tmnxVRtrMaxArpEntriesCleared     NOTIFICATION-TYPE
    OBJECTS     {
        vRtrStatActiveARPEntries,
        vRtrStatTotalARPEntries,
        vRtrMaxARPEntries
    }
    STATUS      current
    DESCRIPTION
        "The tmnxVRtrMaxArpEntriesCleared notification is generated when the
         number of ARP entries contained in a VPRN has dropped below the
         maximum value following the generation of a tmnxVRtrMaxArpEntriesTCA
         notification."
    ::= { tmnxVRtrNotifications 9 }

tmnxVRtrDHCPAFEntriesExceeded    NOTIFICATION-TYPE
    OBJECTS     {
        vRtrIfDHCPOperAutoFilter,
        vRtrIfIndex,
        vRtrAutoFilterDHCPClientAddress,
        vRtrAutoFilterDHCPClientLease
    }
    STATUS      obsolete
    DESCRIPTION
        "The tmnxVRtrDHCPAFEntriesExceeded notification is generated when the
         number of DHCP 'AutoFilter' entries on a given interface reaches a
         user configurable upper limit given by vRtrIfDHCPAutoFilter."
    ::= { tmnxVRtrNotifications 10 }

tmnxVRtrMaxRoutes                NOTIFICATION-TYPE
    OBJECTS     {
        vRtrStatCurrNumRoutes,
        vRtrMaxNumRoutes,
        vRtrMaxRoutesType
    }
    STATUS      current
    DESCRIPTION
        "The tmnxVRtrMaxRoutes notification is generated when the number of
         routes of type vRtrMaxRoutesType contained in a VPRN reaches the value
         specified by vRtrMaxNumRoutes."
    ::= { tmnxVRtrNotifications 11 }

tmnxVRtrDHCPLseStsExceeded       NOTIFICATION-TYPE
    OBJECTS     {
        vRtrID,
        vRtrServiceId,
        vRtrIfIndex,
        vRtrDhcpLseStateNewCiAddr,
        vRtrDhcpLseStateNewChAddr,
        vRtrDHCPClientLease
    }
    STATUS      obsolete
    DESCRIPTION
        "The tmnxVRtrDHCPLseStsExceeded notification is
         generated when the number  of  DHCP  lease states
         entries on a given interface reaches a user configurable
         upper limit."
    ::= { tmnxVRtrNotifications 12 }

tmnxVRtrDHCPLeaseStateOverride   NOTIFICATION-TYPE
    OBJECTS     {
        vRtrID,
        vRtrServiceId,
        vRtrIfIndex,
        vRtrDhcpLseStateNewCiAddr,
        vRtrDhcpLseStateNewChAddr,
        vRtrDhcpLseStateOldCiAddr,
        vRtrDhcpLseStateOldChAddr
    }
    STATUS      obsolete
    DESCRIPTION
        "The tmnxVRtrDHCPLeaseStateOverride notification is generated when an
         existing DHCP lease state is overridden by a new lease state which has
         the same IP address but a different MAC address."
    ::= { tmnxVRtrNotifications 13 }

tmnxVRtrDHCPSuspiciousPcktRcvd   NOTIFICATION-TYPE
    OBJECTS     {
        vRtrID,
        vRtrServiceId,
        vRtrIfIndex,
        vRtrDhcpPacketProblem
    }
    STATUS      current
    DESCRIPTION
        "The tmnxVRtrDHCPSuspiciousPcktRcvd notification is generated when a
         DHCP packet is received with suspicious content."
    ::= { tmnxVRtrNotifications 14 }

tmnxVRtrDHCPLseStRestoreProblem  NOTIFICATION-TYPE
    OBJECTS     {
        vRtrDhcpRestoreLseStateVRtrId,
        vRtrDhcpRestoreLseStateIfIndex,
        vRtrDhcpRestoreLseStateCiAddr,
        vRtrDhcpRestoreLseStateProblem
    }
    STATUS      obsolete
    DESCRIPTION
        "The tmnxVRtrDHCPLseStRestoreProblem notification is generated when an
         an error is detected while processing a persistency record."
    ::= { tmnxVRtrNotifications 15 }

tmnxVRtrDHCPLseStatePopulateErr  NOTIFICATION-TYPE
    OBJECTS     {
        vRtrID,
        vRtrServiceId,
        vRtrIfIndex,
        vRtrDhcpLseStatePopulateError
    }
    STATUS      obsolete
    DESCRIPTION
        "The tmnxVRtrDHCPLseStatePopulateErr notification indicates that the
         system was unable to update the Lease State Table with the information
         contained in the DHCP ACK message. The DHCP ACK message has been
         discarded."
    ::= { tmnxVRtrNotifications 16 }

tmnxVRtrBfdSessionDown           NOTIFICATION-TYPE
    OBJECTS     {
        vRtrIfBfdSessionLclDisc,
        vRtrIfBfdSessionOperFlags
    }
    STATUS      obsolete
    DESCRIPTION
        "The tmnxVRtrBfdSessionDown notification is generated when a BFD
         session goes down."
    ::= { tmnxVRtrNotifications 17 }

tmnxVRtrBfdMaxSessionOnSlot      NOTIFICATION-TYPE
    OBJECTS     {
        vRtrBfdSlotNumber,
        vRtrNumberOfBfdSessionsOnSlot,
        vRtrBfdMaxSessionReason,
        vRtrSlotOrCpmFlag
    }
    STATUS      current
    DESCRIPTION
        "    The tmnxVRtrBfdMaxSessionOnSlot notification is generated
             when the maximum number of BFD sessions has been reached
             on the slot indicated in 'vRtrBfdSlotNumber'. When we have
             IOM based sessions, vRtrSlotOrCpmFlag is set to 'slot' and
             when the sessions are centralized it is set to 'cpm'."
    ::= { tmnxVRtrNotifications 18 }

tmnxVRtrBfdPortTypeNotSupported  NOTIFICATION-TYPE
    OBJECTS     {
        tmnxPortNotifyPortId,
        tmnxPortType
    }
    STATUS      current
    DESCRIPTION
        "The tmnxVRtrBfdPortTypeNotSupported notification is generated when BFD
         is not supported on the port specified in 'tmnxPortNotifyPortId'."
    ::= { tmnxVRtrNotifications 19 }

tmnxVRtrDHCPIfLseStatesExceeded  NOTIFICATION-TYPE
    OBJECTS     {
        vRtrID,
        vRtrServiceId,
        vRtrIfIndex,
        sapPortId,
        sapEncapValue,
        vRtrIfDHCPLeasePopulate,
        svcDhcpLseStateNewCiAddr,
        svcDhcpLseStateNewChAddr,
        svcDhcpClientLease
    }
    STATUS      current
    DESCRIPTION
        "The tmnxVRtrDHCPIfLseStatesExceeded notification is generated when the
         number of lease states on an interface exceeds
         vRtrIfDHCPLeasePopulate."
    ::= { tmnxVRtrNotifications 20 }

tmnxVRtrDHCP6RelayLseStExceeded  NOTIFICATION-TYPE
    OBJECTS     {
        vRtrID,
        vRtrServiceId,
        vRtrIfIndex,
        vRtrIfDHCP6LeasePopulate,
        vRtrDHCP6AssignedNetAddrType,
        vRtrDHCP6AssignedNetAddr,
        vRtrDHCP6AssignedPrefixLen,
        vRtrDHCP6NewClientId,
        svcDhcpClientLease
    }
    STATUS      current
    DESCRIPTION
        "The tmnxVRtrDHCP6RelayLseStExceeded notification is generated when the
         number of lease states populated by dhcp6 relay on an interface
         exceeds vRtrIfDHCP6LeasePopulate."
    ::= { tmnxVRtrNotifications 21 }

tmnxVRtrDHCP6ServerLseStExceeded NOTIFICATION-TYPE
    OBJECTS     {
        vRtrID,
        vRtrServiceId,
        vRtrIfIndex,
        vRtrIfDHCP6ServerMaxLeaseStates,
        vRtrDHCP6AssignedNetAddrType,
        vRtrDHCP6AssignedNetAddr,
        vRtrDHCP6AssignedPrefixLen,
        vRtrDHCP6NewClientId,
        svcDhcpClientLease
    }
    STATUS      current
    DESCRIPTION
        "The tmnxVRtrDHCP6ServerLseStExceeded notification is generated when
         the number of lease states populated by dhcp6 server on an interface
         exceeds vRtrIfDHCP6ServerMaxLeaseStates."
    ::= { tmnxVRtrNotifications 22 }

tmnxVRtrDHCP6LseStateOverride    NOTIFICATION-TYPE
    OBJECTS     {
        vRtrID,
        vRtrServiceId,
        vRtrIfIndex,
        vRtrDHCP6OldAssignedNetAddrType,
        vRtrDHCP6OldAssignedNetAddr,
        vRtrDHCP6OldAssignedPrefixLen,
        vRtrDhcpLseStateOldChAddr,
        vRtrDHCP6OldClientId,
        vRtrDHCP6AssignedNetAddrType,
        vRtrDHCP6AssignedNetAddr,
        vRtrDHCP6AssignedPrefixLen,
        vRtrDhcpLseStateNewChAddr,
        vRtrDHCP6NewClientId,
        vRtrDHCP6LeaseOverrideResult
    }
    STATUS      current
    DESCRIPTION
        "The tmnxVRtrDHCP6LseStateOverride notification is generated when an
         existing DHCP6 lease state can be overridden by a new lease state.

         This is allowed if the new lease state has the same IP address but a
         different client id or mac address. This is not allowed if the new
         lease state has the same IP address but a different prefix length."
    ::= { tmnxVRtrNotifications 23 }

tmnxVRtrDHCP6RelayReplyStripUni  NOTIFICATION-TYPE
    OBJECTS     {
        vRtrID,
        vRtrServiceId,
        vRtrIfIndex,
        vRtrDHCP6ServerNetAddrType,
        vRtrDHCP6ServerNetAddr
    }
    STATUS      current
    DESCRIPTION
        "The tmnxVRtrDHCP6RelayReplyStripUni notification is generated when a
         unicast option is stripped from a message relayed from a server to a
         client in a relay reply message."
    ::= { tmnxVRtrNotifications 24 }

tmnxVRtrDHCP6IllegalClientAddr   NOTIFICATION-TYPE
    OBJECTS     {
        vRtrID,
        vRtrServiceId,
        vRtrIfIndex,
        vRtrDHCP6ClientNetAddrType,
        vRtrDHCP6ClientNetAddr
    }
    STATUS      current
    DESCRIPTION
        "The tmnxVRtrDHCP6IllegalClientAddr notification is generated when an
         incoming message is dropped because the client's source IP does not
         match the subnet of the incoming interface."
    ::= { tmnxVRtrNotifications 25 }

tmnxVRtrDHCP6AssignedIllegSubnet NOTIFICATION-TYPE
    OBJECTS     {
        vRtrID,
        vRtrServiceId,
        vRtrIfIndex,
        vRtrDHCP6ClientNetAddrType,
        vRtrDHCP6ClientNetAddr,
        vRtrDHCP6AssignedNetAddrType,
        vRtrDHCP6AssignedNetAddr,
        vRtrDHCP6AssignedPrefixLen
    }
    STATUS      current
    DESCRIPTION
        "The tmnxVRtrDHCP6AssignedIllegSubnet notification is generated when an
         IP address assigned to the client does not match the subnet of the
         interface."
    ::= { tmnxVRtrNotifications 26 }

tmnxVRtrDHCP6ClientMacUnresolved NOTIFICATION-TYPE
    OBJECTS     {
        vRtrID,
        vRtrServiceId,
        vRtrIfIndex,
        vRtrDHCP6ClientNetAddrType,
        vRtrDHCP6ClientNetAddr
    }
    STATUS      current
    DESCRIPTION
        "The tmnxVRtrDHCP6ClientMacUnresolved notification is generated when we
         receive a relay reply for a client, and the client's MAC address has
         not been resolved yet."
    ::= { tmnxVRtrNotifications 27 }

tmnxVRtrBfdSessionUp             NOTIFICATION-TYPE
    OBJECTS     {
        vRtrIfBfdSessionLclDisc
    }
    STATUS      obsolete
    DESCRIPTION
        "The tmnxVRtrBfdSessionUp notification is generated when a BFD session
         goes up."
    ::= { tmnxVRtrNotifications 28 }

tmnxVRtrIPv6MidRouteTCA          NOTIFICATION-TYPE
    OBJECTS     {
        vRtrV6StatCurrNumRoutes,
        vRtrIPv6MidRouteThreshold
    }
    STATUS      current
    DESCRIPTION
        "The tmnxVRtrIPv6MidRouteTCA notification is generated when the number
         of IPv6 routes contained in a VPRN exceeds the value specified by
         vRtrIPv6MidRouteThreshold. No other notifications of this type are
         generated until after the soak period specified by
         vRtrIPv6RouteThresholdSoakTime has expired."
    ::= { tmnxVRtrNotifications 29 }

tmnxVRtrIPv6HighRouteTCA         NOTIFICATION-TYPE
    OBJECTS     {
        vRtrV6StatCurrNumRoutes,
        vRtrIPv6HighRouteThreshold
    }
    STATUS      current
    DESCRIPTION
        "The tmnxVRtrIPv6HighRouteTCA notification is generated when the number
         of IPv6 routes contained in a VPRN exceeds the value specified by
         vRtrIPv6HighRouteThreshold. No other notifications of this type are
         generated until after the soak period specified by
         vRtrIPv6RouteThresholdSoakTime has expired."
    ::= { tmnxVRtrNotifications 30 }

tmnxVRtrIPv6HighRouteCleared     NOTIFICATION-TYPE
    OBJECTS     {
        vRtrV6StatCurrNumRoutes,
        vRtrIPv6HighRouteThreshold
    }
    STATUS      current
    DESCRIPTION
        "The tmnxVRtrIPv6HighRouteCleared notification is generated when the
         number of IPv6 routes contained in a VPRN has dropped below the
         vRtrIPv6HighRouteThreshold value following the generation of a
         tmnxVRtrIPv6HighRouteTCA notification."
    ::= { tmnxVRtrNotifications 31 }

tmnxVRtrStaticRouteCPEStatus     NOTIFICATION-TYPE
    OBJECTS     {
        vRtrID,
        vRtrInetStatRteCpeNotifyAddrType,
        vRtrInetStatRteCpeNotifyAddr,
        vRtrInetStaticRouteCpeStatus
    }
    STATUS      current
    DESCRIPTION
        "The tmnxVRtrStaticRouteCPEStatus notification is generated when a CPE
         associated with a static route, as specified by the
         vRtrInetStatRteCpeNotifyAddr object, becomes reachable or unreachable."
    ::= { tmnxVRtrNotifications 32 }

tmnxVRtrBfdSessionDeleted        NOTIFICATION-TYPE
    OBJECTS     {
        vRtrIfBfdSessionLclDisc,
        vRtrIfBfdSessionOperFlags
    }
    STATUS      obsolete
    DESCRIPTION
        "The tmnxVRtrBfdSessionDeleted notification is generated when a BFD
         session is deleted."
    ::= { tmnxVRtrNotifications 33 }

tmnxVRtrBfdSessionProtChange     NOTIFICATION-TYPE
    OBJECTS     {
        vRtrIfBfdSessionLclDisc,
        vRtrIfBfdSessionProtocols,
        vRtrIfBfdSessChangedProtocol,
        vRtrIfBfdSessProtoChngdState
    }
    STATUS      obsolete
    DESCRIPTION
        "The tmnxVRtrBfdSessionProtChange notification is generated when there
         is a change in the list of protocols using the BFD session."
    ::= { tmnxVRtrNotifications 34 }

tmnxVRtrManagedRouteAddFailed    NOTIFICATION-TYPE
    OBJECTS     {
        vRtrID,
        vRtrManagedRouteInetAddrType,
        vRtrManagedRouteInetAddr,
        vRtrManagedRoutePrefixLen,
        vRtrFailureDescription
    }
    STATUS      current
    DESCRIPTION
        "The tmnxVRtrManagedRouteAddFailed notification is generated when a
         managed route could not be installed."
    ::= { tmnxVRtrNotifications 35 }

tmnxVRtrFibOccupancyThreshold    NOTIFICATION-TYPE
    OBJECTS     {
        vRtrFibStatHighUtilization
    }
    STATUS      current
    DESCRIPTION
        "The tmnxVRtrFibOccupancyThreshold notification is generated when the
         FIB on an IOM card transitions between experiencing persistent normal
         and high occupancy."
    ::= { tmnxVRtrNotifications 36 }

tmnxVRtrInetAddressAttachFailed  NOTIFICATION-TYPE
    OBJECTS     {
        vRtrID,
        vRtrIfIndex,
        vRtrNotifInetAddrType,
        vRtrNotifInetAddr,
        vRtrFailureDescription
    }
    STATUS      current
    DESCRIPTION
        "The tmnxVRtrInetAddressAttachFailed notification is generated when an
         IP address could not be attached to an interface.

         The reason is indicated in the failure description.

         A possible cause is that a duplicate address is detected.

         If the IP address is a link-local address, the
         vRtrIfLinkLocalAddressState of the corresponding entry in the
         vRtrIfTable does not reach the state 'preferred'.

         If the IP address was configured by the user, the vRiaInetAddrState of
         the corresponding entry in the vRtrIpAddrTable does not reach the
         state 'preferred'.

         The IP address can also be a subnet router anycast address related to
         an IP address configured by the user (refer to RFC 4291 IPv6
         Addressing Architecture, section 2.6.1 Anycast Addresses)."
    ::= { tmnxVRtrNotifications 37 }

tmnxVRtrSingleSfmOverloadStateCh NOTIFICATION-TYPE
    OBJECTS     {
        vRtrSingleSfmOverloadState
    }
    STATUS      current
    DESCRIPTION
        "The notification tmnxVRtrSingleSfmOverloadStateCh is sent when IGP
         single-SFM-overload state of a virtual router instance changes."
    ::= { tmnxVRtrNotifications 38 }

tmnxVRtrGrtExportLimitReached    NOTIFICATION-TYPE
    OBJECTS     {
        vRtrID,
        vRtrGrtMaxExportRoutes
    }
    STATUS      current
    DESCRIPTION
        "A tmnxVRtrGrtExportLimitReached notification is generated when the
         configured value of exported routes, vRtrGrtMaxExportRoutes, is
         reached. Additional routes would not be exported into the GRT from the
         route table."
    ::= { tmnxVRtrNotifications 39 }

tmnxVRtrGrtRoutesExpLimitDropped NOTIFICATION-TYPE
    OBJECTS     {
        vRtrID,
        vRtrGrtMaxExportRoutes
    }
    STATUS      current
    DESCRIPTION
        "A tmnxVRtrGrtRoutesExpLimitDropped notification is generated when the
         number of exported routes drops below the export limit,
         vRtrGrtMaxExportRoutes."
    ::= { tmnxVRtrNotifications 40 }

tmnxVRtrIfLdpSyncTimerStart      NOTIFICATION-TYPE
    OBJECTS     {
        vRtrIfIndex,
        vRtrIfName,
        vRtrIfLdpSyncTimer
    }
    STATUS      current
    DESCRIPTION
        "A tmnxVRtrIfLdpSyncTimerStart notification is generated when the LDP
         sync timer, vRtrIfLdpSyncTimer starts for this interface."
    ::= { tmnxVRtrNotifications 41 }

tmnxVRtrIfLdpSyncTimerStop       NOTIFICATION-TYPE
    OBJECTS     {
        vRtrIfIndex,
        vRtrIfName,
        vRtrIfLdpSyncTimer
    }
    STATUS      current
    DESCRIPTION
        "A tmnxVRtrIfLdpSyncTimerStart notification is generated when the LDP
         sync timer, vRtrIfLdpSyncTimer stops for this interface."
    ::= { tmnxVRtrNotifications 42 }

tmnxVRtrBfdNoCpmNpResources      NOTIFICATION-TYPE
    OBJECTS     {
        vRtrIfBfdSessionLclDisc
    }
    STATUS      obsolete
    DESCRIPTION
        "The tmnxVRtrBfdNoCpmNpResources notification is generated when a BFD
         session could not be established because the session requires a cpmNp
         or fp session termination resource (see vRtrIfBfdExtType), and no
         cpmNp or fp session termination resources are available."
    ::= { tmnxVRtrNotifications 43 }

tmnxVRtrGrtV6ExportLimitReached  NOTIFICATION-TYPE
    OBJECTS     {
        vRtrID,
        vRtrGrtMaxIpv6ExportRoutes
    }
    STATUS      current
    DESCRIPTION
        "[CAUSE] A tmnxVRtrGrtV6ExportLimitReached notification is generated
         when the configured value of exported routes,
         vRtrGrtMaxIpv6ExportRoutes, is reached.

         [EFFECT] Additional routes would not be exported into the GRT from the
         route table.

         [RECOVERY] The export policy and the value of
         vRtrGrtMaxIpv6ExportRoutes need to be changed."
    ::= { tmnxVRtrNotifications 44 }

tmnxVRtrGrtV6RoutesExpLimDropped NOTIFICATION-TYPE
    OBJECTS     {
        vRtrID,
        vRtrGrtMaxIpv6ExportRoutes
    }
    STATUS      current
    DESCRIPTION
        "[CAUSE] A tmnxVRtrGrtV6RoutesExpLimDropped notification is generated
         when the number of exported routes drops below the export limit,
         vRtrGrtMaxIpv6ExportRoutes.

         [EFFECT] There is no effect of this notification.

         [RECOVERY] There is no recovery required for this notification."
    ::= { tmnxVRtrNotifications 45 }

tmnxVRtrStaticRouteStatusChanged NOTIFICATION-TYPE
    OBJECTS     {
        vRtrInetStaticRouteStatus,
        vRtrInetStaticRouteStaticType,
        vRtrInetStaticRouteNextHopType,
        vRtrInetStaticRouteNextHop,
        vRtrInetStaticRouteNextHopIf
    }
    STATUS      current
    DESCRIPTION
        "[CAUSE] A tmnxVRtrStaticRouteStatusChanged notification is generated
         when the status of a static route, vRtrInetStaticRouteStatus changes
         from active to inactive or from inactive to active.

         [EFFECT] There is no effect of this notification.

         [RECOVERY] There is no recovery required for this notification."
    ::= { tmnxVRtrNotifications 46 }

vRtrIfDcpStaticExcd              NOTIFICATION-TYPE
    OBJECTS     {
        vRtrIfDcpFpStaticExcdCountHi,
        vRtrIfDcpFpStaticExcdCountLo,
        vRtrIfDCpuProtPolicy,
        vRtrIfDcpTimeEventOccured
    }
    STATUS      current
    DESCRIPTION
        "[CAUSE] The vRtrIfDcpStaticExcd notification is generated when the
         static-policer on a particular network-interface has been detected as
         non-conformant to the associated distributed CPU protection policy
         parameters. This notification is generated when
         TIMETRA-SECURITY-MIB.mib::tmnxDCpuProtStaticPlcrLogEvent is configured
         to 'enable' or 'verbose'.

         [EFFECT] The affected network-interface may be using more resources
         than expected and cause the system to under perform. This notification
         may indicate a Denial of Service attack or a misconfiguration in the
         network.

         [RECOVERY] Appropriate configuration changes to the distributed CPU
         protection policy or to the affected network-interface may be
         required."
    ::= { tmnxVRtrNotifications 47 }

vRtrIfDcpDynamicExcd             NOTIFICATION-TYPE
    OBJECTS     {
        vRtrIfDcpFpDynExcdCountHi,
        vRtrIfDcpFpDynExcdCountLo,
        vRtrIfDCpuProtPolicy,
        vRtrIfDcpTimeEventOccured
    }
    STATUS      current
    DESCRIPTION
        "[CAUSE] The vRtrIfDcpDynamicExcd notification is generated when the
         protocol on a particular network-interface has been detected as
         non-conformant to the associated distributed CPU protection policy
         parameters. This notification is generated when
         TIMETRA-SECURITY-MIB.mib::tmnxDCpuProtProtocolDynLogEvent is
         configured to 'enable' or 'verbose'.

         [EFFECT] The affected network-interface may be using more resources
         than expected and cause the system to under perform. This notification
         may indicate a Denial of Service attack or a misconfiguration in the
         network.

         [RECOVERY] Appropriate configuration changes to the distributed CPU
         protection policy or to the affected network-interface may be
         required."
    ::= { tmnxVRtrNotifications 48 }

vRtrIfDcpStaticHoldDownStart     NOTIFICATION-TYPE
    OBJECTS     {
        vRtrIfDcpFpStaticExcdCountHi,
        vRtrIfDcpFpStaticExcdCountLo,
        vRtrIfDCpuProtPolicy,
        vRtrIfDcpTimeEventOccured
    }
    STATUS      current
    DESCRIPTION
        "[CAUSE] The vRtrIfDcpStaticHoldDownStart notification is generated
         when a particular network-interface starts hold-down period for an
         exceeding static-policer. This notification is generated when
         TIMETRA-SECURITY-MIB.mib::tmnxDCpuProtStaticPlcrLogEvent is configured
         to 'verbose'.

         [EFFECT] The static-policer will treat all packets as non-conformant
         during the hold-down period.

         [RECOVERY] There is no recovery required for this notification."
    ::= { tmnxVRtrNotifications 49 }

vRtrIfDcpDynamicHoldDownStart    NOTIFICATION-TYPE
    OBJECTS     {
        vRtrIfDcpFpDynExcdCountHi,
        vRtrIfDcpFpDynExcdCountLo,
        vRtrIfDCpuProtPolicy,
        vRtrIfDcpTimeEventOccured
    }
    STATUS      current
    DESCRIPTION
        "[CAUSE] The vRtrIfDcpDynamicHoldDownStart notification is generated
         when a particular network-interface starts hold-down period for an
         exceeding protocol. This notification is generated when
         TIMETRA-SECURITY-MIB.mib::tmnxDCpuProtProtocolDynLogEvent is
         configured to 'verbose'.

         [EFFECT] The protocol will treat all packets as non-conformant during
         the hold-down period.

         [RECOVERY] There is no recovery required for this notification."
    ::= { tmnxVRtrNotifications 50 }

vRtrIfDcpStaticHoldDownEnd       NOTIFICATION-TYPE
    OBJECTS     {
        vRtrIfDcpFpStaticExcdCountHi,
        vRtrIfDcpFpStaticExcdCountLo,
        vRtrIfDCpuProtPolicy,
        vRtrIfDcpTimeEventOccured
    }
    STATUS      current
    DESCRIPTION
        "[CAUSE] The vRtrIfDcpStaticHoldDownEnd notification is generated when
         a particular network-interface completes hold-down period for an
         exceeding static-policer. This notification is generated when
         TIMETRA-SECURITY-MIB.mib::tmnxDCpuProtStaticPlcrLogEvent is configured
         to 'verbose'.

         [EFFECT] The static-policer for an affected network-interface will
         transition to a detection-time countdown after the hold-down period is
         complete.

         [RECOVERY] There is no recovery required for this notification."
    ::= { tmnxVRtrNotifications 51 }

vRtrIfDcpDynamicHoldDownEnd      NOTIFICATION-TYPE
    OBJECTS     {
        vRtrIfDcpFpDynExcdCountHi,
        vRtrIfDcpFpDynExcdCountLo,
        vRtrIfDCpuProtPolicy,
        vRtrIfDcpTimeEventOccured
    }
    STATUS      current
    DESCRIPTION
        "[CAUSE]  The vRtrIfDcpDynamicHoldDownEnd notification is generated
         when a particular network-interface completes hold-down period for an
         exceeding protocol. This notification is generated when
         TIMETRA-SECURITY-MIB.mib::tmnxDCpuProtProtocolDynLogEvent is configured
         to 'verbose'.

         [EFFECT] The protocol for an affected network-interface will
         transition to a detection-time countdown after the hold-down period is
         complete.

         [RECOVERY] There is no recovery required for this notification."
    ::= { tmnxVRtrNotifications 52 }

vRtrIfDcpStaticConform           NOTIFICATION-TYPE
    OBJECTS     {
        vRtrIfDcpFpStaticExcdCountHi,
        vRtrIfDcpFpStaticExcdCountLo,
        vRtrIfDCpuProtPolicy,
        vRtrIfDcpTimeEventOccured
    }
    STATUS      current
    DESCRIPTION
        "[CAUSE] The vRtrIfDcpStaticConform notification is generated when the
         static-policer for a particular network-interface has been detected as
         conformant for a period of the configured detection-time after having
         been previously detected as exceeding and completed any hold-down
         period. This notification is generated when
         TIMETRA-SECURITY-MIB.mib::tmnxDCpuProtStaticPlcrLogEvent is configured
         to 'enable' or 'verbose'.

         [EFFECT] The affected network-interface is now in conformance with the
         parameters configured for the associated distributed CPU protection
         policy.

         [RECOVERY] There is no recovery required for this notification."
    ::= { tmnxVRtrNotifications 53 }

vRtrIfDcpDynamicConform          NOTIFICATION-TYPE
    OBJECTS     {
        vRtrIfDcpFpDynExcdCountHi,
        vRtrIfDcpFpDynExcdCountLo,
        vRtrIfDCpuProtPolicy,
        vRtrIfDcpTimeEventOccured
    }
    STATUS      current
    DESCRIPTION
        "[CAUSE] The vRtrIfDcpDynamicConform notification is generated when the
         protocol for a particular network-interface has been detected as
         conformant for a period of the configured detection-time after having
         been previously detected as exceeding and completed any hold-down
         period. This notification is generated when
         TIMETRA-SECURITY-MIB.mib::tmnxDCpuProtStaticPlcrLogEvent is configured
         to 'enable' or 'verbose'.

         [EFFECT] The affected network-interface is now in conformance with the
         parameters configured for the associated distributed CPU protection
         policy.

         [RECOVERY] There is no recovery required for this notification."
    ::= { tmnxVRtrNotifications 54 }

vRtrIfDcpLocMonExcd              NOTIFICATION-TYPE
    OBJECTS     {
        vRtrIfDcpFpLocMonExcdCountHi,
        vRtrIfDcpFpLocMonExcdCountLo,
        vRtrIfDCpuProtPolicy,
        vRtrIfDcpTimeEventOccured
    }
    STATUS      current
    DESCRIPTION
        "[CAUSE] The vRtrIfDcpLocMonExcd notification is generated when the
         local-monitoring-policer for a particular network-interface has
         transitioned from a conformant state to a non-conformant state and the
         system will attempt to allocate dynamic enforcement policers. This
         notification is generated when
         TIMETRA-SECURITY-MIB.mib::tmnxDCpuProtLocMonPlcrLogEvent is configured
         to 'verbose'.

         [EFFECT] The affected network-interface may be using more resources
         than expected and cause the system to under perform. This notification
         may indicate a Denial of Service attack or a misconfiguration in the
         network.

         [RECOVERY] Appropriate configuration changes to the distributed CPU
         protection policy or to the affected network-interface may be
         required."
    ::= { tmnxVRtrNotifications 55 }

vRtrIfDcpLocMonExcdDynResource   NOTIFICATION-TYPE
    OBJECTS     {
        vRtrIfDcpFpLocMonExcdCountHi,
        vRtrIfDcpFpLocMonExcdCountLo,
        vRtrIfDCpuProtPolicy,
        vRtrIfDcpTimeEventOccured
    }
    STATUS      current
    DESCRIPTION
        "[CAUSE] The vRtrIfDcpLocMonExcdDynResource notification is generated
         when the local-monitoring-policer for a particular network-interface
         has transitioned from a conformant state to a non-conformant state and
         the system cannot allocate all the dynamic enforcements policers
         associated with the distributed CPU protection policy . This
         notification is generated when
         TIMETRA-SECURITY-MIB.mib::tmnxDCpuProtLocMonPlcrLogEvent is configured
         to 'enable' or 'verbose'.

         [EFFECT] The affected network-interface may be using more resources
         than expected and cause the system to under perform. This notification
         may indicate a Denial of Service attack or a misconfiguration in the
         network.

         [RECOVERY] Appropriate configuration changes to the distributed CPU
         protection policy or to the affected network-interface or to the
         dynamic enforcement policer pool
         (TIMETRA-CHASSIS-MIB.mib::tmnxFPDCpuProtDynEnfrcPlcrPool)."
    ::= { tmnxVRtrNotifications 56 }

vRtrIfDcpLocMonExcdAllDynAlloc   NOTIFICATION-TYPE
    OBJECTS     {
        vRtrIfDcpFpLocMonExcdCountHi,
        vRtrIfDcpFpLocMonExcdCountLo,
        vRtrIfDCpuProtPolicy,
        vRtrIfDcpTimeEventOccured
    }
    STATUS      current
    DESCRIPTION
        "[CAUSE] The vRtrIfDcpLocMonExcdAllDynAlloc notification is generated
         when all dynamic enforcement policers associated with a non-conformant
         local-monitoring-policer have been successfully allocated for a
         particular network-interface. This notification is generated when
         TIMETRA-SECURITY-MIB.mib::tmnxDCpuProtLocMonPlcrLogEvent is configure
         to 'verbose'.

         [EFFECT] The affected network-interface may be using more resources
         than expected and cause the system to under perform.

         [RECOVERY] Appropriate configuration changes to the distributed CPU
         protection policy or to the affected network-interface may be
         required."
    ::= { tmnxVRtrNotifications 57 }

vRtrIfDcpLocMonExcdAllDynFreed   NOTIFICATION-TYPE
    OBJECTS     {
        vRtrIfDcpFpLocMonState,
        vRtrIfDCpuProtPolicy,
        vRtrIfDcpTimeEventOccured
    }
    STATUS      current
    DESCRIPTION
        "[CAUSE] The vRtrIfDcpLocMonExcdAllDynFreed notification is generated
         for a particular network-interface when all the previously allocated
         dynamic enforcement policers for a particular local-monitoring-policer
         on the associated distributed CPU protection policy have been freed up
         and all the protocols are once again being monitored by local-monitor.
         This notification is generated when
         TIMETRA-SECURITY-MIB.mib::tmnxDCpuProtLocMonPlcrLogEvent is configured
         to 'verbose'.

         [EFFECT] The affected network-interface may be using more resources
         than expected and cause the system to under perform.

         [RECOVERY] There is no recovery required for this notification."
    ::= { tmnxVRtrNotifications 58 }

vRtrIfDcpDynamicEnforceAlloc     NOTIFICATION-TYPE
    OBJECTS     {
        vRtrIfDcpFpDynAllocated,
        vRtrIfDCpuProtPolicy,
        vRtrIfDcpTimeEventOccured
    }
    STATUS      current
    DESCRIPTION
        "[CAUSE] The vRtrIfDcpDynamicEnforceAlloc notification is generated
         when a dynamic enforcement policer is allocated on a particular
         network-interface. This notification is generated when
         TIMETRA-SECURITY-MIB.mib::tmnxDCpuProtProtocolDynLogEvent is
         configured to 'verbose'.

         [EFFECT] The affected network-interface is not in conformance with the
         configured parameters of the associated distributed CPU protection
         policy and may be using more resources than expected and cause the
         system to under perform.

         [RECOVERY] Appropriate configuration changes to the distributed CPU
         protection policy or to the affected network-interface may be
         required."
    ::= { tmnxVRtrNotifications 59 }

vRtrIfDcpDynamicEnforceFreed     NOTIFICATION-TYPE
    OBJECTS     {
        vRtrIfDcpFpDynExcdCountHi,
        vRtrIfDcpFpDynExcdCountLo,
        vRtrIfDCpuProtPolicy,
        vRtrIfDcpTimeEventOccured
    }
    STATUS      current
    DESCRIPTION
        "[CAUSE] The vRtrIfDcpDynamicEnforceFreed notification is generated
         when a dynamic enforcement policer is freed on a particular
         network-interface. This notification is generated when
         TIMETRA-SECURITY-MIB.mib::tmnxDCpuProtProtocolDynLogEvent is
         configured to 'verbose'.

         [EFFECT] The affected network-interface is now in conformance with the
         configured parameters of the associated distributed CPU protection
         policy.

         [RECOVERY] There is no recovery required for this notification."
    ::= { tmnxVRtrNotifications 60 }

tmnxVRtrBfdSessExtDown           NOTIFICATION-TYPE
    OBJECTS     {
        vRtrIfBfdSessExtLclDisc,
        vRtrIfBfdSessExtOperFlags
    }
    STATUS      current
    DESCRIPTION
        "[CAUSE] The tmnxVRtrBfdSessExtDown notification is generated when a
         BFD session goes down.

         [EFFECT] The effect of this session going down is that it either takes
                  down any protocol that is riding over top of it or it notifies
                  them that the session has gone down.

         [RECOVERY] The session will automatically attempt to re-establish on
                    its own."
    ::= { tmnxVRtrNotifications 61 }

tmnxVRtrBfdSessExtUp             NOTIFICATION-TYPE
    OBJECTS     {
        vRtrIfBfdSessExtLclDisc
    }
    STATUS      current
    DESCRIPTION
        "[CAUSE] The tmnxVRtrBfdSessExtUp notification is generated when a BFD
         session goes up.

         [EFFECT] There is no effect of this notification.

         [RECOVERY] There is no recovery required for this notification."
    ::= { tmnxVRtrNotifications 62 }

tmnxVRtrBfdSessExtDeleted        NOTIFICATION-TYPE
    OBJECTS     {
        vRtrIfBfdSessExtLclDisc,
        vRtrIfBfdSessExtOperFlags
    }
    STATUS      current
    DESCRIPTION
        "[CAUSE] The tmnxVRtrBfdSessExtDeleted notification is generated when a
         BFD session is deleted.

         [EFFECT] There is no effect of this notification.

         [RECOVERY] There is no recovery required for this notification."
    ::= { tmnxVRtrNotifications 63 }

tmnxVRtrBfdSessExtProtChange     NOTIFICATION-TYPE
    OBJECTS     {
        vRtrIfBfdSessExtLclDisc,
        vRtrIfBfdSessExtProtocols,
        vRtrIfBfdSessChangedProtocol,
        vRtrIfBfdSessProtoChngdState
    }
    STATUS      current
    DESCRIPTION
        "[CAUSE] The tmnxVRtrBfdSessExtProtChange notification is generated
         when there is a change in the list of protocols using the BFD session.

         [EFFECT] There is no effect of this notification.

         [RECOVERY] There is no recovery required for this notification."
    ::= { tmnxVRtrNotifications 64 }

tmnxVRtrBfdExtNoCpmNpResources   NOTIFICATION-TYPE
    OBJECTS     {
        vRtrIfBfdSessExtLclDisc
    }
    STATUS      current
    DESCRIPTION
        "[CAUSE] The tmnxVRtrBfdExtNoCpmNpResources notification is generated
         when a BFD session could not be established because the session
         requires a cpmNp or fp session termination resource (see
         vRtrIfBfdExtType), and no cpmNp or fp session termination resources
         are available.

         [EFFECT] There is no effect of this notification.

         [RECOVERY] There is no recovery required for this notification."
    ::= { tmnxVRtrNotifications 65 }

tmnxVRtrDnsFault                 NOTIFICATION-TYPE
    OBJECTS     {
        vRtrID,
        vRtrNotifInetAddrType,
        vRtrNotifInetAddr,
        vRtrFailureDescription,
        vRtrNotifTruthValue
    }
    STATUS      current
    DESCRIPTION
        "[CAUSE] The tmnxVRtrDnsFault notification is generated when this
         system detects a fault with a DNS server, or when it detects that the
         fault has disappeared.

         The virtual router instance and DNS server address are indicated with
         vRtrID, vRtrNotifInetAddrType, and vRtrNotifInetAddr.

         More details of the fault may be indicated with
         vRtrFailureDescription.

         [EFFECT] If another DNS server is available in the same virtual router
         instance, that DNS server may be used instead.

         Otherwise, any application in this virtual router instance that relies
         on DNS may be affected.

         [RECOVERY] A modification of the conceptual row in the vRtrDnsTable
         with the same value for vRtrID, may repair the problem."
    ::= { tmnxVRtrNotifications 66 }

tmnxVRtrMacAcctLimitReached      NOTIFICATION-TYPE
    OBJECTS     {
        vRtrID,
        vRtrIfName,
        vRtrIfIndex
    }
    STATUS      current
    DESCRIPTION
        "[CAUSE] The tmnxVRtrMacAcctLimitReached notification is generated when
         the system detects that the MAC accounting table is full.

         [EFFECT] The MAC accounting table is full and further allocations of
         accounting indices will fail.

         [RECOVERY] The failure  can  be cleared when the used MAC entries are
         deleted by disabling MAC accounting  on a particular interface
         or through manual intervention with a user command such as clear
         router interface mac."
    ::= { tmnxVRtrNotifications 67 }

tmnxVRtrMacAcctLimitCleared      NOTIFICATION-TYPE
    OBJECTS     {
        vRtrID,
        vRtrIfName,
        vRtrIfIndex
    }
    STATUS      current
    DESCRIPTION
        "[CAUSE] The tmnxVRtrMacAcctLimitCleared notification is generated when
         one or more MAC entries are deleted following the generation of a
         tmnxVRtrMacAcctLimitReached notification.

         [EFFECT] Allocation of further MAC entries will be successful up to
         the number of entries cleared.

         [RECOVERY] No recovery is needed for this notification."
    ::= { tmnxVRtrNotifications 68 }

tmnxVRtrNgBfdSessDown            NOTIFICATION-TYPE
    OBJECTS     {
        vRtrIfBfdSessExtLclDisc,
        vRtrIfBfdSessExtOperFlags,
        vRtrIfBfdSessExtLspPathId,
        vRtrIfBfdSessExtLspPathTunnelId,
        vRtrIfBfdSessExtSvcId,
        vRtrIfBfdSessExtSdpBindId
    }
    STATUS      current
    DESCRIPTION
        "[CAUSE] The tmnxVRtrNgBfdSessDown notification is generated when a BFD
         session goes down.

         [EFFECT] The effect of this session going down is that it either takes
         down any protocol that is riding over top of it or it notifies them
         that the session has gone down.

         [RECOVERY] The session will automatically attempt to re-establish on
         it's own."
    ::= { tmnxVRtrNotifications 69 }

tmnxVRtrNgBfdSessUp              NOTIFICATION-TYPE
    OBJECTS     {
        vRtrIfBfdSessExtLclDisc,
        vRtrIfBfdSessExtLspPathId,
        vRtrIfBfdSessExtLspPathTunnelId,
        vRtrIfBfdSessExtSvcId,
        vRtrIfBfdSessExtSdpBindId
    }
    STATUS      current
    DESCRIPTION
        "[CAUSE] The tmnxVRtrNgBfdSessUp notification is generated when a BFD
         session goes up.

         [EFFECT] The BFD session will be active.

         [RECOVERY] There is no recovery required for this notification."
    ::= { tmnxVRtrNotifications 70 }

tmnxVRtrNgBfdSessDeleted         NOTIFICATION-TYPE
    OBJECTS     {
        vRtrIfBfdSessExtLclDisc,
        vRtrIfBfdSessExtOperFlags,
        vRtrIfBfdSessExtLspPathId,
        vRtrIfBfdSessExtLspPathTunnelId,
        vRtrIfBfdSessExtSvcId,
        vRtrIfBfdSessExtSdpBindId
    }
    STATUS      current
    DESCRIPTION
        "[CAUSE] The tmnxVRtrNgBfdSessDeleted notification is generated when a
         BFD session is deleted.

         [EFFECT] The deletion of this session will either take down any
         protocol that is riding over top of it or notifies them that the
         session has been deleted.

         [RECOVERY] There is no recovery required for this notification."
    ::= { tmnxVRtrNotifications 71 }

tmnxVRtrNgBfdSessProtChange      NOTIFICATION-TYPE
    OBJECTS     {
        vRtrIfBfdSessExtLclDisc,
        vRtrIfBfdSessExtProtocols,
        vRtrIfBfdSessChangedProtocol,
        vRtrIfBfdSessProtoChngdState,
        vRtrIfBfdSessExtLspPathId,
        vRtrIfBfdSessExtLspPathTunnelId,
        vRtrIfBfdSessExtSvcId,
        vRtrIfBfdSessExtSdpBindId
    }
    STATUS      current
    DESCRIPTION
        "[CAUSE] The tmnxVRtrNgBfdSessProtChange notification is generated when
         there is a change in the list of protocols using the BFD session.

         [EFFECT] The list of protocols using this session are modified.

         [RECOVERY] There is no recovery required for this notification."
    ::= { tmnxVRtrNotifications 72 }

tmnxVRtrNgBfdNoCpmNpResources    NOTIFICATION-TYPE
    OBJECTS     {
        vRtrIfBfdSessExtLclDisc,
        vRtrIfBfdSessExtLspPathId,
        vRtrIfBfdSessExtLspPathTunnelId,
        vRtrIfBfdSessExtSvcId,
        vRtrIfBfdSessExtSdpBindId
    }
    STATUS      current
    DESCRIPTION
        "[CAUSE] The tmnxVRtrNgBfdNoCpmNpResources notification is generated
         when a BFD session could not be established because the session
         requires a cpmNp or fp session termination resource (see
         vRtrIfBfdExtType), and no cpmNp or fp session termination resources
         are available.

         [EFFECT] The BFD session cannot be established until a cpmNp or fp
         session termination resource is available

         [RECOVERY] There is no recovery required for this notification."
    ::= { tmnxVRtrNotifications 73 }

tmnxVRtrNHRvplsARPHighUsage      NOTIFICATION-TYPE
    OBJECTS     {
        tmnxVRtrMaxNHRvplsARPEntries
    }
    STATUS      current
    DESCRIPTION
        "[CAUSE] The tmnxVRtrNHRvplsARPHighUsage notification is generated when
         Nexthop RVPLS ARP entries reaches 95% of its limit as indicated by the
         value of tmnxVRtrMaxNHRvplsARPEntries.

         [EFFECT] ARP table reaches high usage limit and further addition of
         Nexthop RVPLS ARP may fail.

         [RECOVERY] Reduce the number of ARPs."
    ::= { tmnxVRtrNotifications 74 }

tmnxVRtrNHRvplsARPExhaust        NOTIFICATION-TYPE
    OBJECTS     {
        tmnxVRtrMaxNHRvplsARPEntries
    }
    STATUS      current
    DESCRIPTION
        "[CAUSE] The tmnxVRtrNHRvplsARPExhaust notification is generated when
         Nexthop RVPLS ARP entries reaches 100% of its limit as indicated by
         the value of tmnxVRtrMaxNHRvplsARPEntries.

         [EFFECT] ARP table reaches high usage limit and further addition of
         Nexthop RVPLS ARP will fail.

         [RECOVERY] Reduce the number of ARPs."
    ::= { tmnxVRtrNotifications 75 }

tmnxVRtrNHRvplsARPHighUsageClr   NOTIFICATION-TYPE
    OBJECTS     {
        tmnxVRtrMaxNHRvplsARPEntries
    }
    STATUS      current
    DESCRIPTION
        "[CAUSE] The tmnxVRtrNHRvplsARPHighUsageClr notification is generated
         when Nexthop RVPLS ARP entries falls below 90% of its limit following
         the generation of tmnxVRtrNHRvplsARPHighUsage notification as
         indicated by the value of tmnxVRtrMaxNHRvplsARPEntries.

         [EFFECT] Addition of further Nexthop RVPLS ARP entries will be
         successful.

         [RECOVERY] No recovery is needed for this notification."
    ::= { tmnxVRtrNotifications 76 }

tmnxVRtrArpLmt                   NOTIFICATION-TYPE
    OBJECTS     {
        vRtrIfName,
        vRtrIfArpLimit
    }
    STATUS      current
    DESCRIPTION
        "[CAUSE] A tmnxVRtrArpLmt notification is generated when the number of
         IPv4 ARP entries learned on an IP interface has exceeded the
         configured maximum.

         [EFFECT] The number of entries have exceeded the configured limit as
         specified by vRtrIfArpLimit. No new entries are learned until an entry
         expires.

         [RECOVERY] Increase the arp-limit."
    ::= { tmnxVRtrNotifications 77 }

tmnxVRtrArpThresholdExceeded     NOTIFICATION-TYPE
    OBJECTS     {
        vRtrIfName,
        vRtrIfArpLimit,
        vRtrIfArpThreshold
    }
    STATUS      current
    DESCRIPTION
        "[CAUSE] A tmnxVRtrArpThresholdExceeded notification is generated when
         the number of IPv4 ARP entries learned on an IP interface has exceeded
         vRtrIfArpThreshold percent of the configured maximum as specified by
         vRtrIfArpLimit.

         [EFFECT] No direct effect but if the interface continues to learn more
         entries then the number of entries may exceed the configured limit as
         specified by vRtrIfArpLimit. In that case, no new entries are learned
         until an entry expires and traffic to these destinations will be
         dropped.

         [RECOVERY] Increase the arp-limit."
    ::= { tmnxVRtrNotifications 78 }

tmnxVRtrIpv6NbrLmt               NOTIFICATION-TYPE
    OBJECTS     {
        vRtrIfName,
        vRtrIfIpv6NbrLimit
    }
    STATUS      current
    DESCRIPTION
        "[CAUSE] A tmnxVRtrIpv6NbrLmt notification is generated when the
         maximum amount of IPv6 neighbor entries learned on an IP interface has
         exceeded the configured maximum.

         [EFFECT] The number of entries have exceeded the configured limit as
         specified by vRtrIfIpv6NbrLimit. No new entries are learned until an
         entry expires.

         [RECOVERY] Increase the neighbor limit."
    ::= { tmnxVRtrNotifications 79 }

tmnxVRtrIpv6NbrThresholdExceeded NOTIFICATION-TYPE
    OBJECTS     {
        vRtrIfName,
        vRtrIfIpv6NbrLimit,
        vRtrIfIpv6NbrThreshold
    }
    STATUS      current
    DESCRIPTION
        "[CAUSE] A tmnxVRtrIpv6NbrThresholdExceeded notification is generated
         when the number of IPv6 neighbor entries learned on an IP interface
         has exceeded vRtrIfIpv6NbrThreshold percent of the configured maximum
         as specified by vRtrIfIpv6NbrLimit.

         [EFFECT] No direct effect but if the interface continues to learn more
         entries then the number of entries may exceed the configured limit as
         specified by vRtrIfIpv6NbrLimit. In that case, no new entries are
         learned until an entry expires and traffic to these destinations will
         be dropped.

         [RECOVERY] Increase the neighbor limit."
    ::= { tmnxVRtrNotifications 80 }

tmnxVRtrIfIgnorePortState        NOTIFICATION-TYPE
    OBJECTS     {
        vRtrServiceId,
        vRtrIfName,
        vRtrNotifIgnorePortState
    }
    STATUS      current
    DESCRIPTION
        "[CAUSE] The tmnxVRtrIfIgnorePortState notification is generated when
         ignoring non-operational state of the port associated with the IP
         interface is changing state.

         [EFFECT] This notification is informational only.

         [RECOVERY] Set TIMETRA-SAP-MIB::sapL3LoopbackRowStatus to 'destroy' to
         stop this."
    ::= { tmnxVRtrNotifications 81 }

tmnxVRtrPdnAddrMismatch          NOTIFICATION-TYPE
    OBJECTS     {
        vRtrID,
        vRtrIfName,
        vRtrNotifInetAddrType,
        vRtrNotifInetAddr,
        vRtrFailureDescription
    }
    STATUS      current
    DESCRIPTION
        "[CAUSE] The tmnxVRtrPdnAddrMismatch notification is generated when the
         IP address learned by the PDN interface through the cellular network
         could not be installed on the PDN router interface.

         For IPv4, this occurs when the parent interface has a mismatching
         configured IP address or when the learned PDN IP address overlaps
         another IP address in the router instance. The notification will only
         be generated when the PDN interface is set unnumbered to the system
         interface or any other existing loopback interface.

         For IPv6 operation, this occurs when the IPv6 address has a
         mismatching subnet to the address configured for the PDN router
         interface or if the exact same IPv6 address is configured on the PDN
         interface as the address received by the network.

         [EFFECT] The PDN Interface will be operationally down.

         [RECOVERY] Check the configured IP address for the PDN interface or
         parent interface, check the other IP addresses in the router instance,
         and/or check the state of the cellular network."
    ::= { tmnxVRtrNotifications 82 }

tmnxVRtrPdnAddrMismatchCleared   NOTIFICATION-TYPE
    OBJECTS     {
        vRtrID,
        vRtrIfName
    }
    STATUS      current
    DESCRIPTION
        "[CAUSE] The tmnxVRtrPdnAddrMismatchCleared notification is generated
         when the conditions that caused the PDN address mismatch no longer
         exist.

         [EFFECT] The PDN interface will go operationally up.

         [RECOVERY] Not applicable."
    ::= { tmnxVRtrNotifications 83 }

tmnxVRtrLeakExportLimitReached   NOTIFICATION-TYPE
    OBJECTS     {
        vRtrLeakExportLimit
    }
    STATUS      current
    DESCRIPTION
        "[CAUSE] The tmnxVRtrLeakExportLimitReached notification is generated
         when the leak-export-limit <limit> has been exceeded.

         [EFFECT]  Some routes allowed by the leak-export policies
         may not have been leaked to the target VPRNs.

         [RECOVERY] Not applicable."
    ::= { tmnxVRtrNotifications 84 }

tmnxVRtrLeakExportLimitDropped   NOTIFICATION-TYPE
    OBJECTS     {
        vRtrLeakExportLimit
    }
    STATUS      current
    DESCRIPTION
        "[CAUSE] The tmnxVRtrLeakExportLimitDropped  notification
         is generated when the number of leaked routes drops below
         the leak-export-limit <limit>.

         [EFFECT]  Some routes allowed by the leak-export policies
         may not have been leaked to the target VPRNs.

         [RECOVERY] Not applicable."
    ::= { tmnxVRtrNotifications 85 }

tmnxVRtrDhcpClientStatusChanged  NOTIFICATION-TYPE
    OBJECTS     {
        vRtrIfDhcpClStateStatus,
        vRtrIfDhcpClStateDescription
    }
    STATUS      current
    DESCRIPTION
        "[CAUSE] The tmnxVRtrDhcpClientStatusChanged notification is sent when
         the value of the object vRtrIfDhcpClStateStatus changes.

         [EFFECT] While the value of the object vRtrIfDhcpClStateDescription is
         not equal to 'established', the DHCP client is not operational.

         [RECOVERY] The recovery action, if necessary, depends on the actual
         state. When the value is 'failed', details about the failure cause are
         specified in the vRtrIfDhcpClStateDescription."
    ::= { tmnxVRtrNotifications 86 }

tmnxVRtrDhcp6ClientStatusChanged NOTIFICATION-TYPE
    OBJECTS     {
        vRtrIfDhcp6ClStateStatus,
        vRtrIfDhcp6ClStateDescription
    }
    STATUS      current
    DESCRIPTION
        "[CAUSE] The tmnxVRtrDhcp6ClientStatusChanged notification is sent when
         the value of the object vRtrIfDhcp6ClStateStatus changes.

         [EFFECT] While the value of the object vRtrIfDhcp6ClStateDescription
         is not equal to 'established', the DHCPv6 client is not operational.

         [RECOVERY] The recovery action, if necessary, depends on the actual
         state. When the value is 'failed', details about the failure cause are
         specified in the vRtrIfDhcp6ClStateDescription."
    ::= { tmnxVRtrNotifications 87 }

tmnxVRtrNeDiscovered             NOTIFICATION-TYPE
    OBJECTS     {
        tmnxVRtrNeInfoNeidHex,
        tmnxVRtrNeInfoNeipV4Type,
        tmnxVRtrNeInfoNeipV4,
        tmnxVRtrNeInfoNeipV4PrefixLen,
        tmnxVRtrNeInfoNeipV6Type,
        tmnxVRtrNeInfoNeipV6,
        tmnxVRtrNeInfoNeipV6PrefixLen,
        tmnxVRtrNeInfoSystemMac,
        tmnxVRtrNeInfoPlatformType,
        tmnxVRtrNeInfoVendorId
    }
    STATUS      current
    DESCRIPTION
        "[CAUSE] The tmnxVRtrNeDiscovered notification is sent when a new
         Network Element is discovered.

         [EFFECT] No effect.

         [RECOVERY] No recovery is necessary."
    ::= { tmnxVRtrNotifications 88 }

tmnxVRtrNeRemoved                NOTIFICATION-TYPE
    OBJECTS     {
        tmnxVRtrNeInfoNeidHex,
        tmnxVRtrNeInfoNeipV4Type,
        tmnxVRtrNeInfoNeipV4,
        tmnxVRtrNeInfoNeipV4PrefixLen,
        tmnxVRtrNeInfoNeipV6Type,
        tmnxVRtrNeInfoNeipV6,
        tmnxVRtrNeInfoNeipV6PrefixLen,
        tmnxVRtrNeInfoSystemMac,
        tmnxVRtrNeInfoPlatformType,
        tmnxVRtrNeInfoVendorId
    }
    STATUS      current
    DESCRIPTION
        "[CAUSE] The tmnxVRtrNeRemoved notification is sent when a Network
         Element is removed.

         [EFFECT] No effect.

         [RECOVERY] No recovery is necessary."
    ::= { tmnxVRtrNotifications 89 }

tmnxVRtrNeModified               NOTIFICATION-TYPE
    OBJECTS     {
        tmnxVRtrNeInfoNeidHex,
        tmnxVRtrNeInfoNeipV4Type,
        tmnxVRtrNeInfoNeipV4,
        tmnxVRtrNeInfoNeipV4PrefixLen,
        tmnxVRtrNeInfoNeipV6Type,
        tmnxVRtrNeInfoNeipV6,
        tmnxVRtrNeInfoNeipV6PrefixLen,
        tmnxVRtrNeInfoSystemMac,
        tmnxVRtrNeInfoPlatformType,
        tmnxVRtrNeInfoVendorId
    }
    STATUS      current
    DESCRIPTION
        "[CAUSE] The tmnxVRtrNeModified notification is sent when a Network
         Element is modified.

         [EFFECT] No effect.

         [RECOVERY] No recovery is necessary."
    ::= { tmnxVRtrNotifications 90 }

vRtrIfDhcpClRtStatusChanged      NOTIFICATION-TYPE
    OBJECTS     {
        vRtrIfDhcpClRtStatus
    }
    STATUS      current
    DESCRIPTION
        "[CAUSE] The vRtrIfDhcpClRtStatusChanged notification is sent when the
         value of the object vRtrIfDhcpClRtStatus changes; that includes when a
         row in the vRtrIfDhcpClRtTable is created or destroyed.

         [EFFECT] A value of 'installed' indicates the received route is valid,
                  and is successfully installed in the route table.

         [RECOVERY] The recovery action, if necessary, depends on the actual
         state."
    ::= { tmnxVRtrNotifications 91 }

vRtrIfDhcpClStateDnsChanged      NOTIFICATION-TYPE
    OBJECTS     {
        vRtrIfDhcpClStateDnsPriAddrType,
        vRtrIfDhcpClStateDnsPriAddr,
        vRtrIfDhcpClStateDnsSecAddrType,
        vRtrIfDhcpClStateDnsSecAddr,
        vRtrIfDhcpClStateDnsTerAddrType,
        vRtrIfDhcpClStateDnsTerAddr
    }
    STATUS      current
    DESCRIPTION
        "[CAUSE] The vRtrIfDhcpClStateDnsChanged notification is sent when the
         value of any of the DNS addresses of the DHCP client changes.

         [EFFECT]

         [RECOVERY] "
    ::= { tmnxVRtrNotifications 92 }

vRtrAutoCfgRaRtStatusChanged     NOTIFICATION-TYPE
    OBJECTS     {
        vRtrAutoCfgRaRtStatus
    }
    STATUS      current
    DESCRIPTION
        "[CAUSE] The vRtrAutoCfgRaRtStatusChanged notification is sent when the
         value of the object vRtrAutoCfgRaRtStatus changes; that includes when
         a row in the vRtrAutoCfgRaRtTable is created or destroyed.

         [EFFECT] A value of 'installed' indicates the received route is valid,
                  and is successfully installed in the route table.

         [RECOVERY] The recovery action, if necessary, depends on the actual
         state."
    ::= { tmnxVRtrNotifications 93 }

vRtrIfDhcp6ClStateDnsChanged     NOTIFICATION-TYPE
    OBJECTS     {
        vRtrIfDhcp6ClStateDnsPriAddrType,
        vRtrIfDhcp6ClStateDnsPriAddr,
        vRtrIfDhcp6ClStateDnsSecAddrType,
        vRtrIfDhcp6ClStateDnsSecAddr,
        vRtrIfDhcp6ClStateDnsTerAddrType,
        vRtrIfDhcp6ClStateDnsTerAddr
    }
    STATUS      current
    DESCRIPTION
        "[CAUSE] The vRtrIfDhcp6ClStateDnsChanged notification is sent when the
         value of any of the DNS addresses of the DHCP client changes.

         [EFFECT]

         [RECOVERY] "
    ::= { tmnxVRtrNotifications 94 }

vRtrIfEthLoopbackStarted         NOTIFICATION-TYPE
    OBJECTS     {
        vRtrIfEthLoopbackMacSwap
    }
    STATUS      current
    DESCRIPTION
        "[CAUSE] The vRtrIfEthLoopbackStarted notification is generated when
         the router interface is placed into loopback.

         [EFFECT] This notification is informational only."
    ::= { tmnxVRtrNotifications 96 }

vRtrIfEthLoopbackStopped         NOTIFICATION-TYPE
    OBJECTS     {
        vRtrIfEthLoopbackMacSwap
    }
    STATUS      current
    DESCRIPTION
        "[CAUSE] The vRtrIfEthLoopbackStopped notification is generated when
         the router interface is removed from loopback.

         [EFFECT] This notification is informational only."
    ::= { tmnxVRtrNotifications 97 }

tmnxVRtrBfdExtNoFreeTxIntrvlSlot NOTIFICATION-TYPE
    OBJECTS     {
        vRtrIfBfdSessExtLclDisc
    }
    STATUS      current
    DESCRIPTION
        "[CAUSE] The tmnxVRtrBfdExtNoFreeTxIntrvlSlot is generated when a BFD
         session of type fp must use another transmit interval than negotiated
         with the peer because all transmit interval slots available in
         hardware (8) are already in use.

         [EFFECT] There is no effect of this notification.

         [RECOVERY] The problem can be mitigated by changing the configuration
         on this node and its peer nodes to use maximum 8 combinations of local
         multiplier, local transmit interval and remote receive interval."
    ::= { tmnxVRtrNotifications 98 }

tmnxVRtrFibVPNOccupancyThreshold NOTIFICATION-TYPE
    OBJECTS     {
        vRtrFibStatIpVpnCurrUtilization
    }
    STATUS      current
    DESCRIPTION
        "The tmnxVRtrFibVPNOccupancyThreshold notification is generated when
         the VPN FIB on an IOM card transitions between experiencing persistent
         normal and high occupancy."
    ::= { tmnxVRtrNotifications 99 }

tmnxVRtrBfdMultiHopFpMismatch    NOTIFICATION-TYPE
    OBJECTS     {
        vRtrIfBfdSessExtLclDisc,
        vRtrBfdSlotNumber,
        vRtrNotifyFpNum
    }
    STATUS      current
    DESCRIPTION
        "[CAUSE] The tmnxVRtrBfdMultiHopFpMismatch is generated on certain
         platforms when a BFD session is created where:
         - the stream of the BFD packets that this system transmits
           could change from one FP to another, or
         - this system could receive the BFD packets on another FP
           than the one that transmits them.
         [EFFECT] BFD packets could be dropped and the BFD session could report a loss.

         [RECOVERY] Design the network such that this system always transmits and receives
          the streams of packets for any given BFD session using the same FP."
    ::= { tmnxVRtrNotifications 100 }

vRtrBgpInstanceError             NOTIFICATION-TYPE
    OBJECTS     {
        vRtrID,
        vRtrNotifyBgpInstType,
        vRtrNotifyBgpInstance,
        vRtrFailureDescription
    }
    STATUS      current
    DESCRIPTION
        "[CAUSE] The vRtrBgpInstanceError is generated on certain platforms
         when BGP instance generates an error.

         [EFFECT] Associated BGP instance may be operationally down.

         [RECOVERY] Design the network such that this system uses resources
         properly."
    ::= { tmnxVRtrNotifications 101 }

vrtrIfIpTunnelOperStateChange    NOTIFICATION-TYPE
    OBJECTS     {
        vRtrID,
        vRtrIfIndex,
        vRtrIfIpTunnelName,
        vRtrIfIpTunnelAdminState,
        vRtrIfIpTunnelOperState,
        vRtrIfIpTunnelOperFlags
    }
    STATUS      current
    DESCRIPTION
        "[CAUSE] The vrtrIfIpTunnelOperStateChange notification is generated
         when there is a change in state for an IP tunnel.

         [EFFECT] When the tunnel is operationally down, traffic arriving at
         the tunnel endpoints will not be encapsulated and transported."
    ::= { tmnxVRtrNotifications 102 }

END
