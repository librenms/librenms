TIMETRA-WLAN-MIB DEFINITIONS ::= BEGIN

IMPORTS
    MODULE-COMPLIANCE, NOTIFICATION-GROUP,
    OBJECT-GROUP
                                                         FROM SNMPv2-CONF
    Counter64, Integer32, MODULE-IDENTITY,
    NOTIFICATION-TYPE, OBJECT-TYPE,
    Unsigned32
                                                         FROM SNMPv2-SMI
    DateAndTime, DisplayString, MacAddress,
    RowStatus, TEXTUAL-CONVENTION,
    TimeStamp, TruthValue
                                                         FROM SNMPv2-TC
    tmnxCardSlotNum, tmnxChassisIndex,
    tmnxMDASlotNum
                                                         FROM TIMETRA-CHASSIS-MIB
    timetraSRMIBModules, tmnxSRConfs,
    tmnxSRNotifyPrefix, tmnxSRObjs
                                                         FROM TIMETRA-GLOBAL-MIB
    tmnxPortNotifyPortId, tmnxPortPortID
                                                         FROM TIMETRA-PORT-MIB
    TPolicyStatementNameOrEmpty,
    TmnxAdminState, TmnxAuthPassword
                                                         FROM TIMETRA-TC-MIB
    ;

timetraWlanMIBModule             MODULE-IDENTITY
    LAST-UPDATED "201707180000Z"
    ORGANIZATION "Nokia"
    CONTACT-INFO
        "Nokia SROS Support
         Web: http://www.nokia.com"
    DESCRIPTION
        "This document is the SNMP MIB module for the Nokia SROS implementation
         of wireless lan ports.

         Copyright 2017-2018 Nokia. All rights reserved. Reproduction of this
         document is authorized on the condition that the foregoing copyright
         notice is included.

         This SNMP MIB module (Specification) embodies Nokia's
         proprietary intellectual property.  Nokia retains all
         title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201707180000Z"
    DESCRIPTION
        "Rev 1.0               18 Jul 2017 00:00
         Initial version of the TIMETRA-WLAN-MIB."

    ::= { timetraSRMIBModules 117 }

TmnxWlanNetworkId                ::= TEXTUAL-CONVENTION
    STATUS      current
    DESCRIPTION
        "TmnxWlanNetworkId identifies a specific WLAN Network definition in the
         system."
    SYNTAX      Unsigned32 (1..10)

TmnxWlanSSID                     ::= TEXTUAL-CONVENTION
    STATUS      current
    DESCRIPTION
        "The data type TmnxWlanSSID represents the WLAN service set identifier
         Access Point Name (APN)."
    SYNTAX      DisplayString (SIZE (1..32))

TmnxWlanWpaPassphrase            ::= TEXTUAL-CONVENTION
    STATUS      current
    DESCRIPTION
        "The data type TmnxWlanWpaPassphrase represents the WLAN WPA/WPA2
         passphrase to access the network."
    SYNTAX      DisplayString (SIZE (0|8..63))

TmnxWlanRadioType                ::= TEXTUAL-CONVENTION
    STATUS      current
    DESCRIPTION
        "The type of WLAN radio."
    SYNTAX      INTEGER {
        unknown      (0),
        dualbandWifi (1)
    }

TmnxWlanRadioAdminStatus         ::= TEXTUAL-CONVENTION
    STATUS      current
    DESCRIPTION
        "The desired administrative status of this radio."
    SYNTAX      INTEGER {
        inService    (1),
        outOfService (2)
    }

TmnxWlanRadioOperStatus          ::= TEXTUAL-CONVENTION
    STATUS      current
    DESCRIPTION
        "The desired operational status of this radio."
    SYNTAX      INTEGER {
        unknown  (0),
        down     (1),
        scanning (2),
        up       (3)
    }

TmnxWlanRadioFreqBand            ::= TEXTUAL-CONVENTION
    STATUS      current
    DESCRIPTION
        "The frequency band of the radio.
             band24GHz : 2.4 GHz
             band50Ghz : 5.0 GHz"
    SYNTAX      INTEGER {
        unknown   (0),
        band24Ghz (1),
        band50Ghz (2)
    }

TmnxWlanRadioChBandwidth         ::= TEXTUAL-CONVENTION
    STATUS      current
    DESCRIPTION
        "The value of channel size (bandwidth)."
    SYNTAX      INTEGER {
        unknown    (0),
        width20mhz (1),
        width40mhz (2)
    }

tmnxWlanObjs                     OBJECT IDENTIFIER ::= { tmnxSRObjs 117 }

tmnxWlanConfigObjs               OBJECT IDENTIFIER ::= { tmnxWlanObjs 2 }

tmnxWlanPortConfigObjs           OBJECT IDENTIFIER ::= { tmnxWlanConfigObjs 1 }

tmnxWlanPortTable                OBJECT-TYPE
    SYNTAX      SEQUENCE OF TmnxWlanPortEntry
    MAX-ACCESS  not-accessible
    STATUS      current
    DESCRIPTION
        "The tmnxWlanPortTable has an entry for each WLAN Port known to the
         system."
    ::= { tmnxWlanPortConfigObjs 1 }

tmnxWlanPortEntry                OBJECT-TYPE
    SYNTAX      TmnxWlanPortEntry
    MAX-ACCESS  not-accessible
    STATUS      current
    DESCRIPTION
        "Each row entry represents a network description for a WLAN in the
         system."
    INDEX       { tmnxPortPortID }
    ::= { tmnxWlanPortTable 1 }

TmnxWlanPortEntry                ::= SEQUENCE
{
    tmnxWlanPortMode                 INTEGER,
    tmnxWlanPortRadio                Unsigned32,
    tmnxWlanPortOperFlags            BITS
}

tmnxWlanPortMode                 OBJECT-TYPE
    SYNTAX      INTEGER {
        unknown      (0),
        access-point (1),
        station      (2)
    }
    MAX-ACCESS  read-only
    STATUS      current
    DESCRIPTION
        "The value of tmnxWlanPortMode specifies the type of WLAN access this
         port privides."
    ::= { tmnxWlanPortEntry 1 }

tmnxWlanPortRadio                OBJECT-TYPE
    SYNTAX      Unsigned32
    MAX-ACCESS  read-only
    STATUS      current
    DESCRIPTION
        "The value of tmnxWlanPortRadio specifies the radio on this MDA that
         this port belongs to."
    ::= { tmnxWlanPortEntry 2 }

tmnxWlanPortOperFlags            OBJECT-TYPE
    SYNTAX      BITS {
        adminDown          (0),
        rfAdminDown        (1),
        rfChNotLocked      (2),
        noRadiusPlcyCfg    (3),
        dot1xDisabled      (4),
        radiusPlcyDisabled (5),
        noRadiusAuthSvr    (6),
        noNasIpAddr        (7)
    }
    MAX-ACCESS  read-only
    STATUS      current
    DESCRIPTION
        "The value of tmnxWlanPortOperFlags indicates the reasons that this port is
         not in service.
           adminDown         | Port is admin down
           rfAdminDown       | Radio is admin down
           rfChNotLocked     | No channel has been selected (scanning)
           noRadiusPlcyCfg   | Security requires a radius policy, but none configured
           dot1xDisabled     | Dot1x authentication is disabled
           radiusPlcyDisabled| Assigned radius policy is disabled
           noRadiusAuthSvr   | Assigned radius policy contains no authentication server
           noNasIpAddr       | No NAS Ip address found,"
    ::= { tmnxWlanPortEntry 3 }

tmnxWlanNetworkTable             OBJECT-TYPE
    SYNTAX      SEQUENCE OF TmnxWlanNetworkEntry
    MAX-ACCESS  not-accessible
    STATUS      current
    DESCRIPTION
        "The tmnxWlanNetworkTable has an entry for each WLAN Network known to
         the system."
    ::= { tmnxWlanPortConfigObjs 2 }

tmnxWlanNetworkEntry             OBJECT-TYPE
    SYNTAX      TmnxWlanNetworkEntry
    MAX-ACCESS  not-accessible
    STATUS      current
    DESCRIPTION
        "Each row entry represents a network description for a WLAN in the
         system."
    INDEX       {
        tmnxPortPortID,
        tmnxWlanNetworkId
    }
    ::= { tmnxWlanNetworkTable 1 }

TmnxWlanNetworkEntry             ::= SEQUENCE
{
    tmnxWlanNetworkId                TmnxWlanNetworkId,
    tmnxWlanNetworkRowStatus         RowStatus,
    tmnxWlanNetworkSSID              TmnxWlanSSID
}

tmnxWlanNetworkId                OBJECT-TYPE
    SYNTAX      TmnxWlanNetworkId
    MAX-ACCESS  not-accessible
    STATUS      current
    DESCRIPTION
        "The value of tmnxWlanNetworkId specifies a wireless network."
    ::= { tmnxWlanNetworkEntry 1 }

tmnxWlanNetworkRowStatus         OBJECT-TYPE
    SYNTAX      RowStatus
    MAX-ACCESS  read-create
    STATUS      current
    DESCRIPTION
        "The value of tmnxWlanNetworkRowStatus specifies the row status of the
         WLAN Network entry.  It is used to control the creation and deletion of
         WLAN Network description.

         Only one row entry with index tmnxWlanNetworkId 1 can be created on
         WLAN ports with tmnxWlanPortMode set to 'access-point'."
    ::= { tmnxWlanNetworkEntry 2 }

tmnxWlanNetworkSSID              OBJECT-TYPE
    SYNTAX      TmnxWlanSSID
    MAX-ACCESS  read-create
    STATUS      current
    DESCRIPTION
        "The value of tmnxWlanNetworkSSID specifies the Service Set Identifier
         (SSID) for the network."
    ::= { tmnxWlanNetworkEntry 3 }

tmnxWlanNetworkSecurityTable     OBJECT-TYPE
    SYNTAX      SEQUENCE OF TmnxWlanNetworkSecurityEntry
    MAX-ACCESS  not-accessible
    STATUS      current
    DESCRIPTION
        "The tmnxWlanNetworkSecurityTable has an entry for each WLAN Network
         known to the system."
    ::= { tmnxWlanPortConfigObjs 3 }

tmnxWlanNetworkSecurityEntry     OBJECT-TYPE
    SYNTAX      TmnxWlanNetworkSecurityEntry
    MAX-ACCESS  not-accessible
    STATUS      current
    DESCRIPTION
        "Each row entry represents a network description for a WLAN in the
         system."
    AUGMENTS    { tmnxWlanNetworkEntry }
    ::= { tmnxWlanNetworkSecurityTable 1 }

TmnxWlanNetworkSecurityEntry     ::= SEQUENCE
{
    tmnxWlanNetworkSecurity          INTEGER,
    tmnxWlanNetworkWpaEncryption     INTEGER,
    tmnxWlanNetworkWpaPassphrase     TmnxWlanWpaPassphrase,
    tmnxWlanNetworkAuthType          INTEGER,
    tmnxWlanNetworkAuthUsername      DisplayString,
    tmnxWlanNetworkAuthPassword      TmnxAuthPassword
}

tmnxWlanNetworkSecurity          OBJECT-TYPE
    SYNTAX      INTEGER {
        none            (0),
        wpa2-psk        (1),
        wpa2-enterprise (2)
    }
    MAX-ACCESS  read-write
    STATUS      current
    DESCRIPTION
        "The value of tmnxWlanNetworkSecurity specifies the type of security to
         access this network."
    DEFVAL      { none }
    ::= { tmnxWlanNetworkSecurityEntry 1 }

tmnxWlanNetworkWpaEncryption     OBJECT-TYPE
    SYNTAX      INTEGER {
        none (0),
        aes  (1),
        tkip (2)
    }
    MAX-ACCESS  read-write
    STATUS      current
    DESCRIPTION
        "The value of tmnxWlanNetworkWpaEncryption specifies the type of
         encryption permitted on this network."
    DEFVAL      { none }
    ::= { tmnxWlanNetworkSecurityEntry 2 }

tmnxWlanNetworkWpaPassphrase     OBJECT-TYPE
    SYNTAX      TmnxWlanWpaPassphrase
    MAX-ACCESS  read-write
    STATUS      current
    DESCRIPTION
        "The value of tmnxWlanNetworkWpaPassphrase specifies the WPA/WPA2
         Pre-Shared Passphrase for the network."
    DEFVAL      { "" }
    ::= { tmnxWlanNetworkSecurityEntry 3 }

tmnxWlanNetworkAuthType          OBJECT-TYPE
    SYNTAX      INTEGER {
        not-applicable (0),
        none           (1),
        eap-ttls       (2),
        eap-peap       (3),
        eap-fast       (4)
    }
    MAX-ACCESS  read-write
    STATUS      current
    DESCRIPTION
        "The value of tmnxWlanNetworkAuthType specifies the type of
         authentication used by the WLAN network.

         For WLAN networks configured on ports with tmnxWlanPortMode set to
         'access-point', the value of tmnxWlanNetworkAuthType is set to
         'not-applicable', and cannot be changed.  WLAN Access Points
         on SROS series systems use the radius policy configured with
         tmnxWlanAPDot1xRadiusPlcy to authenticate WLAN clients.

         For WLAN networks configured on ports with tmnxWlanPortMode set to
         'station', and tmnxWlanNetworkSecurity set to 'none' or 'wpa2-psk',
         the value of tmnxWlanNetworkAuthType is set to 'none', and cannot be
         changed.  When tmnxWlanNetworkAuthType is set to 'wpa2-enterprise',
         tmnxWlanNetworkSecurity must be configured to one of the EAP
         authentication types for the WLAN port to become operationally in
         service."
    ::= { tmnxWlanNetworkSecurityEntry 4 }

tmnxWlanNetworkAuthUsername      OBJECT-TYPE
    SYNTAX      DisplayString (SIZE (0..64))
    MAX-ACCESS  read-write
    STATUS      current
    DESCRIPTION
        "The value of tmnxWlanNetworkAuthUsername specifies the username to use
         for authenticating the SROS series system on the WLAN network."
    DEFVAL      { ''H }
    ::= { tmnxWlanNetworkSecurityEntry 5 }

tmnxWlanNetworkAuthPassword      OBJECT-TYPE
    SYNTAX      TmnxAuthPassword
    MAX-ACCESS  read-write
    STATUS      current
    DESCRIPTION
        "The value of tmnxWlanNetworkAuthPassword specifies the password to use
         for authenticating the SROS series system on the WLAN network.

         A get request on this object always returns an empty string."
    DEFVAL      { ''H }
    ::= { tmnxWlanNetworkSecurityEntry 6 }

tmnxWlanAPTable                  OBJECT-TYPE
    SYNTAX      SEQUENCE OF TmnxWlanAPEntry
    MAX-ACCESS  not-accessible
    STATUS      current
    DESCRIPTION
        "The tmnxWlanAPTable contains configuration for each WLAN Access Point
         on the system."
    ::= { tmnxWlanPortConfigObjs 4 }

tmnxWlanAPEntry                  OBJECT-TYPE
    SYNTAX      TmnxWlanAPEntry
    MAX-ACCESS  not-accessible
    STATUS      current
    DESCRIPTION
        "Each row entry contains configuration information for a specific WLAN
         Access Point on the system."
    INDEX       { tmnxPortPortID }
    ::= { tmnxWlanAPTable 1 }

TmnxWlanAPEntry                  ::= SEQUENCE
{
    tmnxWlanAPBroadcastSSID          TruthValue,
    tmnxWlanAPClientLimit            Unsigned32,
    tmnxWlanAPClientTimeout          Unsigned32,
    tmnxWlanAPDot1xRadiusPlcy        TPolicyStatementNameOrEmpty,
    tmnxWlanAPDot1xReauthPeriod      Unsigned32,
    tmnxWlanAPDhcpAdminState         TmnxAdminState
}

tmnxWlanAPBroadcastSSID          OBJECT-TYPE
    SYNTAX      TruthValue
    MAX-ACCESS  read-write
    STATUS      current
    DESCRIPTION
        "The value of tmnxWlanAPBroadcastSSID specifies whether the access
         point should return the Service Set Identifier (SSID) to probes that
         do not contain the SSID."
    DEFVAL      { true }
    ::= { tmnxWlanAPEntry 1 }

tmnxWlanAPClientLimit            OBJECT-TYPE
    SYNTAX      Unsigned32 (1..24)
    MAX-ACCESS  read-write
    STATUS      current
    DESCRIPTION
        "The value of tmnxWlanAPClientLimit specifies the maximum number of
         stations that can be connected at one time."
    DEFVAL      { 24 }
    ::= { tmnxWlanAPEntry 2 }

tmnxWlanAPClientTimeout          OBJECT-TYPE
    SYNTAX      Unsigned32 (60..86400)
    UNITS       "seconds"
    MAX-ACCESS  read-write
    STATUS      current
    DESCRIPTION
        "The value of tmnxWlanAPClientTimeout specifies the amount of time a
         station may be idle before it is disconnected from the access point."
    DEFVAL      { 300 }
    ::= { tmnxWlanAPEntry 3 }

tmnxWlanAPDot1xRadiusPlcy        OBJECT-TYPE
    SYNTAX      TPolicyStatementNameOrEmpty
    MAX-ACCESS  read-write
    STATUS      current
    DESCRIPTION
        "tmnxWlanAPDot1xRadiusPlcy specifies  the  name  of  the
         Radius   Policy.   The   Radius  Policy  specifies  the
         parameters that control the Radius Protocol. If no Policy is
         specified (empty string) no Radius authentication will be
         possible. This object can only be set to a policy that is defined
         in the alxdot1xRadiusServerPlcyTable."
    DEFVAL      { "" }
    ::= { tmnxWlanAPEntry 4 }

tmnxWlanAPDot1xReauthPeriod      OBJECT-TYPE
    SYNTAX      Unsigned32 (1..9000)
    UNITS       "seconds"
    MAX-ACCESS  read-write
    STATUS      current
    DESCRIPTION
        "The value of tmnxWlanAPDot1xReauthPeriod specifies the amount of time
         before a station must reauthorize when using EAP security."
    DEFVAL      { 3600 }
    ::= { tmnxWlanAPEntry 5 }

tmnxWlanAPDhcpAdminState         OBJECT-TYPE
    SYNTAX      TmnxAdminState
    MAX-ACCESS  read-write
    STATUS      current
    DESCRIPTION
        "The value of tmnxWlanAPDhcpAdminState specifies the administrative
         state of DHCP snooping on the access point."
    DEFVAL      { outOfService }
    ::= { tmnxWlanAPEntry 6 }

tmnxWlanCardConfigObjs           OBJECT IDENTIFIER ::= { tmnxWlanConfigObjs 2 }

tmnxWlanRadioTable               OBJECT-TYPE
    SYNTAX      SEQUENCE OF TmnxWlanRadioEntry
    MAX-ACCESS  not-accessible
    STATUS      current
    DESCRIPTION
        "The tmnxWlanRadioTable has an entry for each WLAN Radio known to the
         system."
    ::= { tmnxWlanCardConfigObjs 1 }

tmnxWlanRadioEntry               OBJECT-TYPE
    SYNTAX      TmnxWlanRadioEntry
    MAX-ACCESS  not-accessible
    STATUS      current
    DESCRIPTION
        "Each row entry represents a radio on an MDA card in a
         chassis in the system.  Entries cannot be created and
         deleted via SNMP SET operations."
    INDEX       {
        tmnxChassisIndex,
        tmnxCardSlotNum,
        tmnxMDASlotNum,
        tmnxMDARadioNum
    }
    ::= { tmnxWlanRadioTable 1 }

TmnxWlanRadioEntry               ::= SEQUENCE
{
    tmnxMDARadioNum                  Unsigned32,
    tmnxWlanRadioType                TmnxWlanRadioType,
    tmnxWlanRadioAdminStatus         TmnxWlanRadioAdminStatus,
    tmnxWlanRadioCountry             INTEGER,
    tmnxWlanRadioCfgFreqBand         TmnxWlanRadioFreqBand,
    tmnxWlanRadioCfgChannel          Unsigned32,
    tmnxWlanRadioCfgChBandwidth      TmnxWlanRadioChBandwidth,
    tmnxWlanRadioApBeaconInterval    Unsigned32
}

tmnxMDARadioNum                  OBJECT-TYPE
    SYNTAX      Unsigned32
    MAX-ACCESS  not-accessible
    STATUS      current
    DESCRIPTION
        "The unique value which identifies this radio within a specific MDA in
         the system."
    ::= { tmnxWlanRadioEntry 1 }

tmnxWlanRadioType                OBJECT-TYPE
    SYNTAX      TmnxWlanRadioType
    MAX-ACCESS  read-only
    STATUS      current
    DESCRIPTION
        "The value of tmnxWlanRadioType specifies the type of radio (antenna)
         is equipped."
    ::= { tmnxWlanRadioEntry 2 }

tmnxWlanRadioAdminStatus         OBJECT-TYPE
    SYNTAX      TmnxWlanRadioAdminStatus
    MAX-ACCESS  read-write
    STATUS      current
    DESCRIPTION
        "The value of tmnxWlanRadioAdminStatus indicates the administrative
         status of the radio."
    DEFVAL      { outOfService }
    ::= { tmnxWlanRadioEntry 3 }

tmnxWlanRadioCountry             OBJECT-TYPE
    SYNTAX      INTEGER {
        none        (0),
        australia   (1),
        belgium     (2),
        bolivia     (3),
        brazil      (4),
        canada      (5),
        chile       (6),
        colombia    (7),
        france      (8),
        germany     (9),
        india       (10),
        iran        (11),
        italy       (12),
        japan       (13),
        malaysia    (14),
        mexico      (15),
        newZealand  (16),
        peru        (17),
        russia      (18),
        singapore   (19),
        southAfrica (20),
        usa         (21),
        venezuela   (22)
    }
    MAX-ACCESS  read-write
    STATUS      current
    DESCRIPTION
        "The value of tmnxWlanRadioCountry specifies the country this radio is
         operating in."
    DEFVAL      { none }
    ::= { tmnxWlanRadioEntry 4 }

tmnxWlanRadioCfgFreqBand         OBJECT-TYPE
    SYNTAX      TmnxWlanRadioFreqBand
    MAX-ACCESS  read-write
    STATUS      current
    DESCRIPTION
        "The value of tmnxWlanRadioCfgFreqBand specifies the preferred band
         this radio operates in."
    DEFVAL      { band24Ghz }
    ::= { tmnxWlanRadioEntry 5 }

tmnxWlanRadioCfgChannel          OBJECT-TYPE
    SYNTAX      Unsigned32
    MAX-ACCESS  read-write
    STATUS      current
    DESCRIPTION
        "The value of tmnxWlanRadioCfgChannel specifies the preferred channel
         number within the frequency band this radio operates at.

         A value of (0) indicates the channel should be automatically selected
         to minimize interference from other WLAN networks in the area."
    DEFVAL      { 0 }
    ::= { tmnxWlanRadioEntry 6 }

tmnxWlanRadioCfgChBandwidth      OBJECT-TYPE
    SYNTAX      TmnxWlanRadioChBandwidth
    MAX-ACCESS  read-write
    STATUS      current
    DESCRIPTION
        "The value of tmnxWlanRadioCfgChBandwidth specifies the width of the
         selected channel."
    DEFVAL      { width20mhz }
    ::= { tmnxWlanRadioEntry 7 }

tmnxWlanRadioApBeaconInterval    OBJECT-TYPE
    SYNTAX      Unsigned32 (75..999)
    UNITS       "msecs"
    MAX-ACCESS  read-write
    STATUS      current
    DESCRIPTION
        "The value of tmnxWlanRadioApBeaconInterval specifies the beacon
         transmission interval for radio access points."
    DEFVAL      { 200 }
    ::= { tmnxWlanRadioEntry 8 }

tmnxWlanOperObjs                 OBJECT IDENTIFIER ::= { tmnxWlanObjs 3 }

tmnxWlanRadioOperTable           OBJECT-TYPE
    SYNTAX      SEQUENCE OF TmnxWlanRadioOperEntry
    MAX-ACCESS  not-accessible
    STATUS      current
    DESCRIPTION
        "The tmnxWlanRadioOperTable has an entry for each WLAN Radio known to
         the system."
    ::= { tmnxWlanOperObjs 2 }

tmnxWlanRadioOperEntry           OBJECT-TYPE
    SYNTAX      TmnxWlanRadioOperEntry
    MAX-ACCESS  not-accessible
    STATUS      current
    DESCRIPTION
        "Each row entry represents a radio on an MDA card in a
         chassis in the system.  Entries cannot be created and
         deleted via SNMP SET operations."
    INDEX       {
        tmnxChassisIndex,
        tmnxCardSlotNum,
        tmnxMDASlotNum,
        tmnxMDARadioNum
    }
    ::= { tmnxWlanRadioOperTable 1 }

TmnxWlanRadioOperEntry           ::= SEQUENCE
{
    tmnxWlanRadioOperStatus          TmnxWlanRadioOperStatus,
    tmnxWlanRadioOperFreqBand        TmnxWlanRadioFreqBand,
    tmnxWlanRadioOperChannel         Unsigned32,
    tmnxWlanRadioOperChBandwidth     TmnxWlanRadioChBandwidth,
    tmnxWlanRadioOperCentreFreq      Unsigned32
}

tmnxWlanRadioOperStatus          OBJECT-TYPE
    SYNTAX      TmnxWlanRadioOperStatus
    MAX-ACCESS  read-only
    STATUS      current
    DESCRIPTION
        "The value of tmnxWlanRadioOperStatus indicates the operational status
         of the radio."
    ::= { tmnxWlanRadioOperEntry 1 }

tmnxWlanRadioOperFreqBand        OBJECT-TYPE
    SYNTAX      TmnxWlanRadioFreqBand
    MAX-ACCESS  read-only
    STATUS      current
    DESCRIPTION
        "The value of tmnxWlanRadioOperFreqBand specifies the band this radio
         is operating in."
    ::= { tmnxWlanRadioOperEntry 2 }

tmnxWlanRadioOperChannel         OBJECT-TYPE
    SYNTAX      Unsigned32
    MAX-ACCESS  read-only
    STATUS      current
    DESCRIPTION
        "The value of tmnxWlanRadioOperChannel indicates the channel number
         within the frequency band this radio operates at.

         A value of (0) indicates the channel is not selected."
    ::= { tmnxWlanRadioOperEntry 3 }

tmnxWlanRadioOperChBandwidth     OBJECT-TYPE
    SYNTAX      TmnxWlanRadioChBandwidth
    MAX-ACCESS  read-only
    STATUS      current
    DESCRIPTION
        "The value of tmnxWlanRadioOperChBandwidth indicates the width of the
         selected channel."
    ::= { tmnxWlanRadioOperEntry 4 }

tmnxWlanRadioOperCentreFreq      OBJECT-TYPE
    SYNTAX      Unsigned32
    UNITS       "MHz"
    MAX-ACCESS  read-only
    STATUS      current
    DESCRIPTION
        "The value of tmnxWlanRadioOperCentreFreq indicates the centre
         frequency this radio is operating in."
    ::= { tmnxWlanRadioOperEntry 5 }

tmnxWlanAPOperTable              OBJECT-TYPE
    SYNTAX      SEQUENCE OF TmnxWlanAPOperEntry
    MAX-ACCESS  not-accessible
    STATUS      current
    DESCRIPTION
        "The tmnxWlanAPOperTable contains operational information for each WLAN
         Access Point configured on the system."
    ::= { tmnxWlanOperObjs 3 }

tmnxWlanAPOperEntry              OBJECT-TYPE
    SYNTAX      TmnxWlanAPOperEntry
    MAX-ACCESS  not-accessible
    STATUS      current
    DESCRIPTION
        "Each row entry contains operational information for a WLAN Access
         Point configured on the system."
    INDEX       { tmnxPortPortID }
    ::= { tmnxWlanAPOperTable 1 }

TmnxWlanAPOperEntry              ::= SEQUENCE
{
    tmnxWlanAPConnectedClients       Unsigned32,
    tmnxWlanAPTotalAttaches          Counter64,
    tmnxWlanAPTotalDetaches          Counter64,
    tmnxWlanAPTotalAuthSuccess       Counter64,
    tmnxWlanAPTotalAuthFails         Counter64
}

tmnxWlanAPConnectedClients       OBJECT-TYPE
    SYNTAX      Unsigned32
    MAX-ACCESS  read-only
    STATUS      current
    DESCRIPTION
        "The value of tmnxWlanAPConnectedClients specifies the number of
         clients currently connected."
    ::= { tmnxWlanAPOperEntry 1 }

tmnxWlanAPTotalAttaches          OBJECT-TYPE
    SYNTAX      Counter64
    MAX-ACCESS  read-only
    STATUS      current
    DESCRIPTION
        "The value of tmnxWlanAPTotalAttaches specifies the total number of
         clients that have attached to this access point."
    ::= { tmnxWlanAPOperEntry 2 }

tmnxWlanAPTotalDetaches          OBJECT-TYPE
    SYNTAX      Counter64
    MAX-ACCESS  read-only
    STATUS      current
    DESCRIPTION
        "The value of tmnxWlanAPTotalDetaches specifies the total number of
         clients that have detached from this access point."
    ::= { tmnxWlanAPOperEntry 3 }

tmnxWlanAPTotalAuthSuccess       OBJECT-TYPE
    SYNTAX      Counter64
    MAX-ACCESS  read-only
    STATUS      current
    DESCRIPTION
        "The value of tmnxWlanAPTotalAuthSuccess specifies the total number of
         clients that have successfully authenticated on this access point."
    ::= { tmnxWlanAPOperEntry 4 }

tmnxWlanAPTotalAuthFails         OBJECT-TYPE
    SYNTAX      Counter64
    MAX-ACCESS  read-only
    STATUS      current
    DESCRIPTION
        "The value of tmnxWlanAPTotalAuthFails specifies the total number of
         client attempts that have failed to authenticate on this access point."
    ::= { tmnxWlanAPOperEntry 5 }

tmnxWlanAPClientTable            OBJECT-TYPE
    SYNTAX      SEQUENCE OF TmnxWlanAPClientEntry
    MAX-ACCESS  not-accessible
    STATUS      current
    DESCRIPTION
        "The tmnxWlanAPClientTable has an entry for each WLAN Access Point
         client connected to the system."
    ::= { tmnxWlanOperObjs 4 }

tmnxWlanAPClientEntry            OBJECT-TYPE
    SYNTAX      TmnxWlanAPClientEntry
    MAX-ACCESS  not-accessible
    STATUS      current
    DESCRIPTION
        "Each row entry represents a network description for a WLAN AP in the
         system."
    INDEX       {
        tmnxPortPortID,
        tmnxWlanAPClientMacAddress
    }
    ::= { tmnxWlanAPClientTable 1 }

TmnxWlanAPClientEntry            ::= SEQUENCE
{
    tmnxWlanAPClientMacAddress       MacAddress,
    tmnxWlanAPClientConnectTime      TimeStamp,
    tmnxWlanAPClientAuthorized       TruthValue
}

tmnxWlanAPClientMacAddress       OBJECT-TYPE
    SYNTAX      MacAddress
    MAX-ACCESS  not-accessible
    STATUS      current
    DESCRIPTION
        "The value of the object tmnxWlanAPClientMacAddress indicates the MAC
         address of this client."
    ::= { tmnxWlanAPClientEntry 1 }

tmnxWlanAPClientConnectTime      OBJECT-TYPE
    SYNTAX      TimeStamp
    MAX-ACCESS  read-only
    STATUS      current
    DESCRIPTION
        "The value of tmnxWlanAPClientConnectTime indicates the sysUpTime at
         the time of this client connected."
    ::= { tmnxWlanAPClientEntry 2 }

tmnxWlanAPClientAuthorized       OBJECT-TYPE
    SYNTAX      TruthValue
    MAX-ACCESS  read-only
    STATUS      current
    DESCRIPTION
        "The value of tmnxWlanAPClientAuthorized indicates whether this client
         has successfully authenticated."
    ::= { tmnxWlanAPClientEntry 3 }

tmnxWlanClientNetworkOperTable   OBJECT-TYPE
    SYNTAX      SEQUENCE OF TmnxWlanClientNetworkOperEntry
    MAX-ACCESS  not-accessible
    STATUS      current
    DESCRIPTION
        "The tmnxWlanClientNetworkOperTable contains operational information
         for WLAN networks known by the WLAN station on the system."
    ::= { tmnxWlanOperObjs 5 }

tmnxWlanClientNetworkOperEntry   OBJECT-TYPE
    SYNTAX      TmnxWlanClientNetworkOperEntry
    MAX-ACCESS  not-accessible
    STATUS      current
    DESCRIPTION
        "Each row entry contains operational information for a WLAN network
         known by the WLAN station on the system."
    INDEX       {
        tmnxPortPortID,
        tmnxWlanNetworkId
    }
    ::= { tmnxWlanClientNetworkOperTable 1 }

TmnxWlanClientNetworkOperEntry   ::= SEQUENCE
{
    tmnxWlanNetworkIsConnected       TruthValue,
    tmnxWlanNetworkConnectTime       DateAndTime,
    tmnxWlanNetworkBssid             MacAddress,
    tmnxWlanNetworkChannel           Unsigned32,
    tmnxWlanNetworkFrequency         Unsigned32,
    tmnxWlanNetworkBandwidth         TmnxWlanRadioChBandwidth,
    tmnxWlanNetworkRxSignalLevel     Integer32
}

tmnxWlanNetworkIsConnected       OBJECT-TYPE
    SYNTAX      TruthValue
    MAX-ACCESS  read-only
    STATUS      current
    DESCRIPTION
        "The value of tmnxWlanNetworkIsConnected indicates the whether the WLAN
         station is currently connected to this WLAN network."
    ::= { tmnxWlanClientNetworkOperEntry 1 }

tmnxWlanNetworkConnectTime       OBJECT-TYPE
    SYNTAX      DateAndTime
    MAX-ACCESS  read-only
    STATUS      current
    DESCRIPTION
        "The value of tmnxWlanNetworkConnectTime indicates when the system last
         established a connection to this WLAN network.

         A value of '0000000000000000000000' indicates that the system has
         never established a connection to this network."
    ::= { tmnxWlanClientNetworkOperEntry 2 }

tmnxWlanNetworkBssid             OBJECT-TYPE
    SYNTAX      MacAddress
    MAX-ACCESS  read-only
    STATUS      current
    DESCRIPTION
        "The value of tmnxWlanNetworkBssid indicates the basic service set id
         of the access point for this WLAN network.

         The value of all zeroes indicates that the system does not know the
         BSSID of the access point for this WLAN network."
    ::= { tmnxWlanClientNetworkOperEntry 3 }

tmnxWlanNetworkChannel           OBJECT-TYPE
    SYNTAX      Unsigned32
    MAX-ACCESS  read-only
    STATUS      current
    DESCRIPTION
        "The value of tmnxWlanNetworkChannel indicates the channel number in
         use by the access point for this WLAN network.

         A value of 0 indicates that the system does not know the channel
         number of the access point for this WLAN network."
    ::= { tmnxWlanClientNetworkOperEntry 4 }

tmnxWlanNetworkFrequency         OBJECT-TYPE
    SYNTAX      Unsigned32
    UNITS       "MHz"
    MAX-ACCESS  read-only
    STATUS      current
    DESCRIPTION
        "The value of tmnxWlanNetworkFrequency indicates the centre frequency
         of the channel in use by the access point for this WLAN network.

         A value of 0 indicates that the system does not know the channel of
         the access point for this WLAN network."
    ::= { tmnxWlanClientNetworkOperEntry 5 }

tmnxWlanNetworkBandwidth         OBJECT-TYPE
    SYNTAX      TmnxWlanRadioChBandwidth
    MAX-ACCESS  read-only
    STATUS      current
    DESCRIPTION
        "The value of tmnxWlanNetworkBandwidth specifies the width of the
         selected channel."
    ::= { tmnxWlanClientNetworkOperEntry 6 }

tmnxWlanNetworkRxSignalLevel     OBJECT-TYPE
    SYNTAX      Integer32
    UNITS       "dBm"
    MAX-ACCESS  read-only
    STATUS      current
    DESCRIPTION
        "The value of tmnxWlanNetworkRxSignalLevel indicates the level of the
         signal of the access point, as received on the station, in dBm.

         A value of -100 dBm indicates that the station is not receiving a
         signal from the access point."
    ::= { tmnxWlanClientNetworkOperEntry 7 }

tmnxWlanNotificationObjs         OBJECT IDENTIFIER ::= { tmnxWlanObjs 4 }

tmnxWlanNotifyWlanNetworkId      OBJECT-TYPE
    SYNTAX      TmnxWlanNetworkId
    MAX-ACCESS  accessible-for-notify
    STATUS      current
    DESCRIPTION
        "WLAN notifications use tmnxWlanNotifyWlanNetworkId to indicate the
         WLAN network associated with the notification."
    ::= { tmnxWlanNotificationObjs 1 }

tmnxWlanConformance              OBJECT IDENTIFIER ::= { tmnxSRConfs 117 }

tmnxWlanCompliances              OBJECT IDENTIFIER ::= { tmnxWlanConformance 1 }

tmnxWlanrCompliance              MODULE-COMPLIANCE
    STATUS      current
    DESCRIPTION
        "The compliance statement for the management of the WLAN feature-set
         for Release 15.0 on Nokia SROS series systems."
    MODULE
        MANDATORY-GROUPS {
            tmnxWlanConfigGroup,
            tmnxWlanOperGroup
        }
    ::= { tmnxWlanCompliances 1 }

tmnxWlanComplianceV20            MODULE-COMPLIANCE
    STATUS      current
    DESCRIPTION
        "The compliance statement for the management of the WLAN feature-set
         for Release 20 on Nokia SROS series systems."
    MODULE
        MANDATORY-GROUPS {
            tmnxWlanV20ConfigGroup,
            tmnxWlanV20OperGroup,
            tmnxWlanV20NotificationGroup
        }
    ::= { tmnxWlanCompliances 2 }

tmnxWlanGroups                   OBJECT IDENTIFIER ::= { tmnxWlanConformance 2 }

tmnxWlanV15v0Groups              OBJECT IDENTIFIER ::= { tmnxWlanGroups 1 }

tmnxWlanConfigGroup              OBJECT-GROUP
    OBJECTS     {
        tmnxWlanPortMode,
        tmnxWlanPortRadio,
        tmnxWlanPortOperFlags,
        tmnxWlanNetworkRowStatus,
        tmnxWlanNetworkSSID,
        tmnxWlanNetworkSecurity,
        tmnxWlanNetworkWpaEncryption,
        tmnxWlanNetworkWpaPassphrase,
        tmnxWlanAPBroadcastSSID,
        tmnxWlanAPClientLimit,
        tmnxWlanAPClientTimeout,
        tmnxWlanAPDot1xRadiusPlcy,
        tmnxWlanAPDot1xReauthPeriod,
        tmnxWlanAPDhcpAdminState,
        tmnxWlanRadioType,
        tmnxWlanRadioAdminStatus,
        tmnxWlanRadioCfgChBandwidth,
        tmnxWlanRadioCfgChannel,
        tmnxWlanRadioCountry,
        tmnxWlanRadioCfgFreqBand,
        tmnxWlanRadioApBeaconInterval
    }
    STATUS      current
    DESCRIPTION
        "The group of objects maintaining WLAN port configuration on Nokia
         SROS series systems.  This group was introduced in Release 15.0."
    ::= { tmnxWlanV15v0Groups 1 }

tmnxWlanOperGroup                OBJECT-GROUP
    OBJECTS     {
        tmnxWlanAPConnectedClients,
        tmnxWlanAPTotalAttaches,
        tmnxWlanAPTotalDetaches,
        tmnxWlanAPTotalAuthSuccess,
        tmnxWlanAPTotalAuthFails,
        tmnxWlanRadioOperStatus,
        tmnxWlanRadioOperChBandwidth,
        tmnxWlanRadioOperChannel,
        tmnxWlanRadioOperFreqBand,
        tmnxWlanAPClientConnectTime,
        tmnxWlanAPClientAuthorized,
        tmnxWlanRadioOperCentreFreq
    }
    STATUS      current
    DESCRIPTION
        "The group of objects maintaining WLAN port operations on Nokia
         SROS series systems.  This group was introduced in Release 15.0."
    ::= { tmnxWlanV15v0Groups 2 }

tmnxWlanV20Groups                OBJECT IDENTIFIER ::= { tmnxWlanGroups 2 }

tmnxWlanV20ConfigGroup           OBJECT-GROUP
    OBJECTS     {
        tmnxWlanNetworkAuthType,
        tmnxWlanNetworkAuthUsername,
        tmnxWlanNetworkAuthPassword
    }
    STATUS      current
    DESCRIPTION
        "The group of objects maintaining WLAN configuration for Release 20 on
         Nokia SROS series systems."
    ::= { tmnxWlanV20Groups 1 }

tmnxWlanV20OperGroup             OBJECT-GROUP
    OBJECTS     {
        tmnxWlanNetworkIsConnected,
        tmnxWlanNetworkConnectTime,
        tmnxWlanNetworkBssid,
        tmnxWlanNetworkChannel,
        tmnxWlanNetworkFrequency,
        tmnxWlanNetworkBandwidth,
        tmnxWlanNetworkRxSignalLevel
    }
    STATUS      current
    DESCRIPTION
        "The group of objects maintaining WLAN operational information for
         Release 20 on Nokia SROS series systems."
    ::= { tmnxWlanV20Groups 2 }

tmnxWlanV20NotifyObjsGroup       OBJECT-GROUP
    OBJECTS     {
        tmnxWlanNotifyWlanNetworkId
    }
    STATUS      current
    DESCRIPTION
        "The group of objects supporting WLAN notifications for Release 20 on
         Nokia SROS series systems."
    ::= { tmnxWlanV20Groups 3 }

tmnxWlanV20NotificationGroup     NOTIFICATION-GROUP
    NOTIFICATIONS {
        tmnxWlanNetworkConnected,
        tmnxWlanNetworkDisconnected
    }
    STATUS      current
    DESCRIPTION
        "The group of notifications for WLAN ports on Nokia SROS series
         systems, introduced in Release 20."
    ::= { tmnxWlanV20Groups 4 }

tmnxWlanNotifyPrefix             OBJECT IDENTIFIER ::= { tmnxSRNotifyPrefix 117 }

tmnxWlanNotifications            OBJECT IDENTIFIER ::= { tmnxWlanNotifyPrefix 0 }

tmnxWlanNetworkConnected         NOTIFICATION-TYPE
    OBJECTS     {
        tmnxPortNotifyPortId,
        tmnxWlanNotifyWlanNetworkId,
        tmnxWlanNetworkSSID
    }
    STATUS      current
    DESCRIPTION
        "The system generates a tmnxWlanNetworkConnected notification when the
         system establishes a WLAN connection to the specified network."
    ::= { tmnxWlanNotifications 1 }

tmnxWlanNetworkDisconnected      NOTIFICATION-TYPE
    OBJECTS     {
        tmnxPortNotifyPortId,
        tmnxWlanNotifyWlanNetworkId,
        tmnxWlanNetworkSSID
    }
    STATUS      current
    DESCRIPTION
        "The system generates a tmnxWlanNetworkDisconnected notification when
         the system loses the WLAN connection to the specified network."
    ::= { tmnxWlanNotifications 2 }

END
