TIMETRA-WLAN-GW-MIB DEFINITIONS ::= BEGIN

IMPORTS
    InterfaceIndex, InterfaceIndexOrZero
                                                         FROM IF-MIB
    InetAddress, InetAddressIPv4,
    InetAddressIPv6,
    InetAddressPrefixLength,
    InetAddressType, InetPortNumber
                                                         FROM INET-ADDRESS-MIB
    MplsLabel
                                                         FROM MPLS-LSR-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, DisplayString, MacAddress,
    RowStatus, TEXTUAL-CONVENTION,
    TimeStamp, TruthValue
                                                         FROM SNMPv2-TC
    TmnxChassisIndex,
    TmnxChassisIndexOrZero, TmnxSlotNum,
    TmnxSlotNumOrZero, tmnxCardSlotNum,
    tmnxChassisIndex, tmnxMDASlotNum
                                                         FROM TIMETRA-CHASSIS-MIB
    timetraSRMIBModules, tmnxSRConfs,
    tmnxSRNotifyPrefix, tmnxSRObjs
                                                         FROM TIMETRA-GLOBAL-MIB
    sapEncapValue, sapPortId
                                                         FROM TIMETRA-SAP-MIB
    iesIfIndex, svcId, svcTlsInfoEntry
                                                         FROM TIMETRA-SERV-MIB
    TmnxMobApn, TmnxMobApnDomainName,
    TmnxMobApnOrZero, TmnxMobArp,
    TmnxMobArpValue, TmnxMobBearerId,
    TmnxMobExtQci, TmnxMobImsiStr,
    TmnxMobMccOrEmpty, TmnxMobMncOrEmpty,
    TmnxMobPathMgmtState,
    TmnxMobProfGbrRate, TmnxMobProfIpTtl,
    TmnxMobProfKeepAliveResponse,
    TmnxMobProfKeepAliveRetryCount,
    TmnxMobProfKeepAliveTimeout,
    TmnxMobProfMbrRate,
    TmnxMobProfMsgReTxRetryCount,
    TmnxMobProfMsgReTxTimeout, TmnxMobQci,
    TmnxMobQciValue, TmnxMobService
                                                         FROM TIMETRA-TC-MG-MIB
    QTagFullRange, QTagFullRangeOrNone,
    SvcISID, TAdaptationRule, TCIRRate,
    TDirectionIngEgr, TIpProtocol,
    TItemDescription, TLNamedItemOrEmpty,
    TNamedItem, TNamedItemOrEmpty, TPIRRate,
    TPolicyID, TPortSchedulerPIR,
    TQosOverrideType,
    TQosQueueCIRRateOverride,
    TQosQueuePIRRateOverride,
    TmnxActionType, TmnxAdminState,
    TmnxBsxAaSubHttpUrlParam,
    TmnxBsxIsaAaGroupIndexOrZero,
    TmnxEnabledDisabled,
    TmnxEnabledDisabledAdminState,
    TmnxEnabledDisabledOrNA, TmnxEncapVal,
    TmnxEsaNum, TmnxEsaVappNum, TmnxFpeId,
    TmnxHttpRedirectUrl,
    TmnxIsaScalingProfile,
    TmnxMacSpecification, TmnxNatWaterMark,
    TmnxOperState, TmnxPortID, TmnxServId,
    TmnxVPNRouteDistinguisher, TmnxVRtrID,
    TmnxVRtrIDOrZero, TmnxWlanGwIsaGrpId,
    TmnxWlanGwIsaGrpIdOrZero
                                                         FROM TIMETRA-TC-MIB
    vRtrID
                                                         FROM TIMETRA-VRTR-MIB
    ;

timetraWlanGwMIBModule           MODULE-IDENTITY
    LAST-UPDATED "201904010000Z"
    ORGANIZATION "Nokia"
    CONTACT-INFO
        "Nokia 7xxx Support
         Web: http://www.nokia.com"
    DESCRIPTION
        "This document is the SNMP MIB module to manage and provision the
         Wireless Local Access Network Gateway function for the Nokia 7xxx
         device.

         Copyright 2011-2018 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201904010000Z"
    DESCRIPTION
        "Rev 19.0                 1 April 2019 12:00
         19.0 release of the TIMETRA-WLAN-GW-MIB."

    REVISION    "201701010000Z"
    DESCRIPTION
        "Rev 15.0                 1 Jan 2017 12:00
         15.0 release of the TIMETRA-WLAN-GW-MIB."

    REVISION    "201601010000Z"
    DESCRIPTION
        "Rev 14.0                 1 Jan 2016 12:00
         14.0 release of the TIMETRA-WLAN-GW-MIB."

    REVISION    "201501010000Z"
    DESCRIPTION
        "Rev 13.0                 1 Jan 2015 12:00
         13.0 release of the TIMETRA-WLAN-GW-MIB."

    REVISION    "201401010000Z"
    DESCRIPTION
        "Rev 12.0                 1 Jan 2014 12:00
         12.0 release of the TIMETRA-WLAN-GW-MIB."

    REVISION    "201202280000Z"
    DESCRIPTION
        "Rev 10.0                28 Feb 2012 12:00
         10.0 release of the TIMETRA-WLAN-GW-MIB."

    ::= { timetraSRMIBModules 81 }

TmnxWlanGwAmbr                   ::= TEXTUAL-CONVENTION
    STATUS      current
    DESCRIPTION
        "The data type TmnxWlanGwAmbr is an Aggregated Maximum Bit Rate (AMBR)
         value in kbps per second(kbps).

         The value minus two specifies 'no AMBR'."
    SYNTAX      Integer32 (-2 | 0..10000000)

TmnxWlanGwBurstSize              ::= TEXTUAL-CONVENTION
    STATUS      current
    DESCRIPTION
        "The amount of burst capacity (in kbytes) assigned to a policer."
    SYNTAX      Integer32 (0..131071)

TmnxWlanGwIsaIomOperState        ::= TEXTUAL-CONVENTION
    STATUS      current
    DESCRIPTION
        "TmnxWlanGwIsaIomOperState is an enumerated integer that indicates the
         operational state of a WLAN Gateway ISA IOM within a WLAN Gateway ISA
         group."
    SYNTAX      INTEGER {
        unavail (0),
        primary (1),
        backup  (2),
        busy    (3)
    }

TmnxWlanGwMgwInterfaceType       ::= TEXTUAL-CONVENTION
    STATUS      current
    DESCRIPTION
        "TmnxWlanGwMgwInterfaceType is an enumerated integer that identifies
         the interface type of the connection between WLAN Gateway and Mobile
         Gateway.

         The possible values are: 'gn' for the Gn interface, 's2a' for the S2a
         interface, 's2b' for the S2b interface, 's11' for the S11 interface."
    SYNTAX      INTEGER {
        gn  (1),
        s2a (2),
        s2b (3),
        s11 (4)
    }

TmnxWlanGwDsmFilterDefaultAction ::= TEXTUAL-CONVENTION
    STATUS      current
    DESCRIPTION
        "TmnxWlanGwDsmFilterDefaultAction is an enumerated integer that
         indicates the default action to take for packets matching
         distributed-sub-mgmt filter criteria.

         - drop        : packets matching the filter entry are dropped.
         - forward     : packets matching the filter entry are forwarded."
    SYNTAX      INTEGER {
        drop    (1),
        forward (2)
    }

TmnxWlanGwDsmFilterAction        ::= TEXTUAL-CONVENTION
    STATUS      current
    DESCRIPTION
        "TmnxWlanGwDsmFilterAction is an enumerated integer that indicates the
         action to take for packets matching distributed-sub-mgmt filter
         criteria.

         - drop        : packets matching the filter entry are dropped.
         - forward     : packets matching the filter entry are forwarded.
         - httpRedirect: packets matching the filter entry are redirected."
    SYNTAX      INTEGER {
        none         (0),
        drop         (1),
        forward      (2),
        httpRedirect (3),
        reserved4    (4)
    }

TmnxWlanGwQoSOperState           ::= TEXTUAL-CONVENTION
    STATUS      current
    DESCRIPTION
        "TmnxWlanGwQoSOperState is an enumerated integer that indicates the
         operational state of a WLAN Gateway User Equipment (UE)."
    SYNTAX      INTEGER {
        adminDown (0),
        active    (1),
        pending   (2),
        problem   (3)
    }

TmnxWlanGwGtpSeIdentifier        ::= TEXTUAL-CONVENTION
    STATUS      current
    DESCRIPTION
        "The distributed GTP session identifier."
    SYNTAX      OCTET STRING (SIZE (8))

TmnxWlanGwUeAddressFamily        ::= TEXTUAL-CONVENTION
    STATUS      current
    DESCRIPTION
        "TmnxWlanGwUeAddressFamily is an enumerated integer that indicates the
         User Equipment address family.

         The meaning of the values is 'ipv4': any IPv4 address 'ipv6': any IPv6
         address 'ipv4-only': only an IPv4 address 'ipv6-only': only an IPv6
         address 'ipv4v6': both an IPv4 and an IPv6 address"
    SYNTAX      INTEGER {
        notSpecified (0),
        ipv4         (1),
        ipv6         (2),
        ipv4-only    (3),
        ipv6-only    (4),
        ipv4v6       (5)
    }

TmnxWlanGwUeEncapsulation        ::= TEXTUAL-CONVENTION
    STATUS      current
    DESCRIPTION
        "TmnxWlanGwUeEncapsulation is an enumerated integer that indicates the
         type of encapsulation of User Equipment traffic.

         The meaning of the values is
         'gre' : Soft GRE
         'l2tp': Soft L2TPv3
         'l2'  : IEEE 802.1Q or IEEE 802.1ad
         'vxlan': vxlan endpoint"
    SYNTAX      INTEGER {
        notSpecified (0),
        gre          (1),
        l2tp         (2),
        l2           (3),
        vxlan        (4)
    }

TmnxWlanGwUeIdentifier           ::= TEXTUAL-CONVENTION
    STATUS      current
    DESCRIPTION
        "The User Equipment identifier."
    SYNTAX      OCTET STRING (SIZE (8))

TmnxWlanGwChargingCharBits       ::= TEXTUAL-CONVENTION
    STATUS      current
    DESCRIPTION
        "TmnxWlanGwChargingCharBits is a BITS construct that specifies Charging
         Characteristics bits.

         The meaning of the bits is opaque to this system."
    SYNTAX      BITS {
        bit0  (0),
        bit1  (1),
        bit2  (2),
        bit3  (3),
        bit4  (4),
        bit5  (5),
        bit6  (6),
        bit7  (7),
        bit8  (8),
        bit9  (9),
        bit10 (10),
        bit11 (11),
        bit12 (12),
        bit13 (13),
        bit14 (14),
        bit15 (15)
    }

TmnxWlanGwSubIfIpsAddrFamily     ::= TEXTUAL-CONVENTION
    STATUS      current
    DESCRIPTION
        "TmnxWlanGwSubIfIpsAddrFamily is an enumerated integer that indicates
         the address family of the pool"
    SYNTAX      INTEGER {
        dhcpv6 (0),
        slaac  (1),
        dhcpv4 (2)
    }

TmnxWlanGwVlanIdleTimeoutAction  ::= TEXTUAL-CONVENTION
    STATUS      current
    DESCRIPTION
        "TmnxWlanGwVlanIdleTimeoutAction is an enumerated integer that
         indicates the action to be performed when the idle-timeout timer goes
         off."
    SYNTAX      INTEGER {
        remove (0),
        shcv   (1)
    }

TmnxWlanGwWatermarkEntity        ::= TEXTUAL-CONVENTION
    STATUS      current
    DESCRIPTION
        "TmnxWlanGwWatermarkEntity is an enumerated integer that identifies the
         entities whose quantity is monitored."
    SYNTAX      INTEGER {
        userEquipment     (1),
        bridgeDomain      (2),
        radiusProxyClient (3)
    }

TmnxGtpInterfaceType             ::= TEXTUAL-CONVENTION
    STATUS      current
    DESCRIPTION
        "TmnxGtpInterfaceType is an enumerated integer that indicates the type
         of the GTP interface.

         The possible values are: 'mgw' for a Mobile Gateway interface, 'mme'
         for a Mobility Management Entity interface"
    SYNTAX      INTEGER {
        uplink (0),
        s11    (1)
    }

tmnxWlanGw                       OBJECT IDENTIFIER ::= { tmnxSRObjs 81 }

tmnxWlanGwObjs                   OBJECT IDENTIFIER ::= { tmnxWlanGw 1 }

tmnxWlanGwIsaObjs                OBJECT IDENTIFIER ::= { tmnxWlanGwObjs 1 }

tmnxWlanGwGrpTable               OBJECT-TYPE
    SYNTAX      SEQUENCE OF TmnxWlanGwGrpEntry
    MAX-ACCESS  not-accessible
    STATUS      current
    DESCRIPTION
        "The tmnxWlanGwGrpTable contains objects to configure WLAN Gateway
         Integrated Service Adaptor (ISA) Groups.

         A WLAN Gateway ISA group is used to represent multiple hardware
         adaptors as a single entity, allowing for warm redundancy between
         multiple WLAN Gateway ISAs."
    ::= { tmnxWlanGwIsaObjs 1 }

tmnxWlanGwGrpEntry               OBJECT-TYPE
    SYNTAX      TmnxWlanGwGrpEntry
    MAX-ACCESS  not-accessible
    STATUS      current
    DESCRIPTION
        "Each conceptual row represents a WLAN Gateway Integrated Service
         Adaptor Group.

         Entries in this table can be created or deleted via SNMP operations."
    INDEX       { tmnxWlanGwGrpId }
    ::= { tmnxWlanGwGrpTable 1 }

TmnxWlanGwGrpEntry               ::= SEQUENCE
{
    tmnxWlanGwGrpId                  TmnxWlanGwIsaGrpId,
    tmnxWlanGwGrpRowStatus           RowStatus,
    tmnxWlanGwGrpLastMgmtChange      TimeStamp,
    tmnxWlanGwGrpDescription         TItemDescription,
    tmnxWlanGwGrpAdminState          TmnxAdminState,
    tmnxWlanGwGrpActiveIomLimit      Unsigned32,
    tmnxWlanGwGrpPortPlcy            TNamedItemOrEmpty,
    tmnxWlanGwGrpTunnelPortPlcy      TNamedItemOrEmpty,
    tmnxWlanGwGrpIsaAaGroup          TmnxBsxIsaAaGroupIndexOrZero,
    tmnxWlanGwGrpOperState           TmnxOperState,
    tmnxWlanGwGrpDegraded            TruthValue,
    tmnxWlanGwGrpRedundancyUnit      INTEGER,
    tmnxWlanGwGrpActiveMdaLimit      Unsigned32,
    tmnxWlanGwGrpScalingProfile      TmnxIsaScalingProfile,
    tmnxWlanGwGrpIsaAaOversub        Unsigned32
}

tmnxWlanGwGrpId                  OBJECT-TYPE
    SYNTAX      TmnxWlanGwIsaGrpId
    MAX-ACCESS  not-accessible
    STATUS      current
    DESCRIPTION
        "The value of the object tmnxWlanGwGrpId specifies the identifier of
         the WLAN Gateway Integrated Service Adaptor group."
    ::= { tmnxWlanGwGrpEntry 1 }

tmnxWlanGwGrpRowStatus           OBJECT-TYPE
    SYNTAX      RowStatus
    MAX-ACCESS  read-create
    STATUS      current
    DESCRIPTION
        "The value of tmnxWlanGwGrpRowStatus specifies the row status of this
         row."
    ::= { tmnxWlanGwGrpEntry 2 }

tmnxWlanGwGrpLastMgmtChange      OBJECT-TYPE
    SYNTAX      TimeStamp
    MAX-ACCESS  read-only
    STATUS      current
    DESCRIPTION
        "The value of tmnxWlanGwGrpLastMgmtChange indicates the sysUpTime at
         the time of the most recent management-initiated change to this table
         row."
    ::= { tmnxWlanGwGrpEntry 3 }

tmnxWlanGwGrpDescription         OBJECT-TYPE
    SYNTAX      TItemDescription
    MAX-ACCESS  read-create
    STATUS      current
    DESCRIPTION
        "The value of tmnxWlanGwGrpDescription specifies the description of
         this WLAN Gateway ISA group."
    DEFVAL      { "" }
    ::= { tmnxWlanGwGrpEntry 4 }

tmnxWlanGwGrpAdminState          OBJECT-TYPE
    SYNTAX      TmnxAdminState
    MAX-ACCESS  read-create
    STATUS      current
    DESCRIPTION
        "The value of tmnxWlanGwGrpAdminState specifies the administrative
         state of this WLAN Gateway ISA group."
    DEFVAL      { outOfService }
    ::= { tmnxWlanGwGrpEntry 5 }

tmnxWlanGwGrpActiveIomLimit      OBJECT-TYPE
    SYNTAX      Unsigned32 (0..7 | 8..14)
    MAX-ACCESS  read-create
    STATUS      current
    DESCRIPTION
        "The value of tmnxWlanGwGrpActiveIomLimit specifies the number of IOMs
         in this WLAN Gateway ISA group that are intended for active use.

         The values above seven are only available in a virtual machine
         implementation.

         A non-zero value is only accepted if the value of
         tmnxWlanGwGrpRedundancyUnit is equal to 'iom'.

         A non-zero value must be specified before setting the value of
         tmnxWlanGwGrpAdminState to 'inService'."
    DEFVAL      { 0 }
    ::= { tmnxWlanGwGrpEntry 6 }

tmnxWlanGwGrpPortPlcy            OBJECT-TYPE
    SYNTAX      TNamedItemOrEmpty
    MAX-ACCESS  read-create
    STATUS      current
    DESCRIPTION
        "The value of tmnxWlanGwGrpPortPlcy specifies the port policy of this
         WLAN Gateway ISA group.

         This object refers to a row in the
         TIMETRA-PORT-MIB::tmnxPortPlcyTable.

         If a port policy is associated with a WLAN Gateway ISA group, ports
         created for this group can take applicable configuration from that
         port policy.

         This port policy is applicable to those ports that take part in the
         per-UE QoS processing."
    DEFVAL      { "" }
    ::= { tmnxWlanGwGrpEntry 7 }

tmnxWlanGwGrpTunnelPortPlcy      OBJECT-TYPE
    SYNTAX      TNamedItemOrEmpty
    MAX-ACCESS  read-create
    STATUS      current
    DESCRIPTION
        "The value of tmnxWlanGwGrpTunnelPortPlcy specifies a port policy of
         this WLAN Gateway ISA group.

         This object refers to a row in the
         TIMETRA-PORT-MIB::tmnxPortPlcyTable.

         If a port policy is associated with a WLAN Gateway ISA group, ports
         created for this group can take applicable configuration from that
         port policy.

         This port policy is applicable to those ports that take part in the
         per-tunnel QoS processing."
    DEFVAL      { "" }
    ::= { tmnxWlanGwGrpEntry 8 }

tmnxWlanGwGrpIsaAaGroup          OBJECT-TYPE
    SYNTAX      TmnxBsxIsaAaGroupIndexOrZero
    MAX-ACCESS  read-create
    STATUS      current
    DESCRIPTION
        "The value of tmnxWlanGwGrpIsaAaGroup specifies an Application
         Assurance ISA group associated with this WLAN Gateway ISA group.

         This object refers to a row in the
         TIMETRA-BSX-NG-MIB::tmnxBsxIsaAaGrpTable."
    DEFVAL      { 0 }
    ::= { tmnxWlanGwGrpEntry 9 }

tmnxWlanGwGrpOperState           OBJECT-TYPE
    SYNTAX      TmnxOperState
    MAX-ACCESS  read-only
    STATUS      current
    DESCRIPTION
        "The value of tmnxWlanGwGrpOperState indicates the operational status
         of this WLAN Gateway ISA group."
    ::= { tmnxWlanGwGrpEntry 50 }

tmnxWlanGwGrpDegraded            OBJECT-TYPE
    SYNTAX      TruthValue
    MAX-ACCESS  read-only
    STATUS      current
    DESCRIPTION
        "The value of tmnxWlanGwGrpDegraded indicates if this WLAN Gateway ISA
         group is degraded, while operationally still in service."
    ::= { tmnxWlanGwGrpEntry 51 }

tmnxWlanGwGrpRedundancyUnit      OBJECT-TYPE
    SYNTAX      INTEGER {
        iom (1),
        mda (2)
    }
    MAX-ACCESS  read-create
    STATUS      current
    DESCRIPTION
        "The value of tmnxWlanGwGrpRedundancyUnit specifies the hardware unit
         subject to redundancy.

         Any value other than 'iom' must be set while the conceptual row is
         being created.

         The value of this object can not be modified after the conceptual row
         was created."
    DEFVAL      { iom }
    ::= { tmnxWlanGwGrpEntry 54 }

tmnxWlanGwGrpActiveMdaLimit      OBJECT-TYPE
    SYNTAX      Unsigned32 (0..14)
    MAX-ACCESS  read-create
    STATUS      current
    DESCRIPTION
        "The value of tmnxWlanGwGrpActiveMdaLimit specifies the number of MDA's
         in this WLAN Gateway ISA group that are intended for active use.

         A non-zero value must be specified before setting the value of
         tmnxWlanGwGrpAdminState to 'inService', and is only accepted if the
         value of tmnxWlanGwGrpRedundancyUnit is equal to 'mda'."
    DEFVAL      { 0 }
    ::= { tmnxWlanGwGrpEntry 55 }

tmnxWlanGwGrpScalingProfile      OBJECT-TYPE
    SYNTAX      TmnxIsaScalingProfile
    MAX-ACCESS  read-create
    STATUS      current
    DESCRIPTION
        "The value of tmnxWlanGwGrpScalingProfile specifies the scaling profile
         of this WLAN Gateway ISA group.

         ISA scaling profiles are only used in a virtual machine
         implementation."
    DEFVAL      { profile1 }
    ::= { tmnxWlanGwGrpEntry 56 }

tmnxWlanGwGrpIsaAaOversub        OBJECT-TYPE
    SYNTAX      Unsigned32 (1..10)
    MAX-ACCESS  read-create
    STATUS      current
    DESCRIPTION
        "The value of tmnxWlanGwGrpIsaAaOversub specifies the oversubscription
         of the number of WLAN-GW ISA MDA modules in this WLAN-GW ISA group
         with respect to the number of AA ISA MDA modules in the AA ISA group
         specified by the object tmnxWlanGwGrpIsaAaGroup.

         While the value of tmnxWlanGwGrpIsaAaGroup is equal to zero, it is not
         allowed to modify the value of this object."
    DEFVAL      { 1 }
    ::= { tmnxWlanGwGrpEntry 57 }

tmnxWlanGwIomTable               OBJECT-TYPE
    SYNTAX      SEQUENCE OF TmnxWlanGwIomEntry
    MAX-ACCESS  not-accessible
    STATUS      current
    DESCRIPTION
        "The tmnxWlanGwIomTable contains objects to configure the WLAN Gateway
         ISA Group Input/Output Modules (IOM)."
    ::= { tmnxWlanGwIsaObjs 2 }

tmnxWlanGwIomEntry               OBJECT-TYPE
    SYNTAX      TmnxWlanGwIomEntry
    MAX-ACCESS  not-accessible
    STATUS      current
    DESCRIPTION
        "Each conceptual row represents a WLAN Gateway ISA Input/Output Module
         (IOM) of a WLAN Gateway ISA Group.

         Entries in this table can be created or deleted via SNMP operations."
    INDEX       {
        tmnxWlanGwGrpId,
        tmnxChassisIndex,
        tmnxCardSlotNum
    }
    ::= { tmnxWlanGwIomTable 1 }

TmnxWlanGwIomEntry               ::= SEQUENCE
{
    tmnxWlanGwIomRowStatus           RowStatus,
    tmnxWlanGwIomLastMgmtChange      TimeStamp,
    tmnxWlanGwIomOperState           TmnxWlanGwIsaIomOperState,
    tmnxWlanGwIomApplication         BITS
}

tmnxWlanGwIomRowStatus           OBJECT-TYPE
    SYNTAX      RowStatus
    MAX-ACCESS  read-create
    STATUS      current
    DESCRIPTION
        "The value of tmnxWlanGwIomRowStatus specifies the row status of this
         row.

         For a given value of tmnxWlanGwGrpId, it is only allowed to create a
         conceptual row in this table if the value of the
         tmnxWlanGwGrpRedundancyUnit object in the corresponding row in the
         tmnxWlanGwGrpTable is equal to 'iom'."
    ::= { tmnxWlanGwIomEntry 1 }

tmnxWlanGwIomLastMgmtChange      OBJECT-TYPE
    SYNTAX      TimeStamp
    MAX-ACCESS  read-only
    STATUS      current
    DESCRIPTION
        "The value of tmnxWlanGwIomLastMgmtChange indicates the sysUpTime at
         the time of the most recent management-initiated change to this table
         row."
    ::= { tmnxWlanGwIomEntry 2 }

tmnxWlanGwIomOperState           OBJECT-TYPE
    SYNTAX      TmnxWlanGwIsaIomOperState
    MAX-ACCESS  read-only
    STATUS      current
    DESCRIPTION
        "The value of tmnxWlanGwIomOperState indicates the operational state of
         this WLAN Gateway ISA IOM."
    ::= { tmnxWlanGwIomEntry 3 }

tmnxWlanGwIomApplication         OBJECT-TYPE
    SYNTAX      BITS {
        loadBalancing (0),
        ueAnchoring   (1)
    }
    MAX-ACCESS  read-create
    STATUS      current
    DESCRIPTION
        "The value of tmnxWlanGwIomApplication specifies the application of
         this WLAN Gateway ISA IOM in a virtual machine implementation.

         A value other than all zeroes can only be specified while creating the
         conceptual row, and it cannot be modified afterwards."
    DEFVAL      { {} }
    ::= { tmnxWlanGwIomEntry 4 }

tmnxWlanGwIsaMemberTable         OBJECT-TYPE
    SYNTAX      SEQUENCE OF TmnxWlanGwIsaMemberEntry
    MAX-ACCESS  not-accessible
    STATUS      current
    DESCRIPTION
        "The tmnxWlanGwIsaMemberTable contains status and statistics
         information about the members of a WLAN Gateway ISA Group.

         A member of a WLAN Gateway ISA Group can be mapped to a physical ISA
         MDA or ESA VM."
    ::= { tmnxWlanGwIsaObjs 3 }

tmnxWlanGwIsaMemberEntry         OBJECT-TYPE
    SYNTAX      TmnxWlanGwIsaMemberEntry
    MAX-ACCESS  not-accessible
    STATUS      current
    DESCRIPTION
        "Each conceptual row contains WLAN Gateway-specific status and basic
         statistics information about a member of a WLAN Gateway ISA Group.

         Entries in this table are created and removed automatically by the
         system."
    INDEX       {
        tmnxWlanGwGrpId,
        tmnxWlanGwIsaMemberId
    }
    ::= { tmnxWlanGwIsaMemberTable 1 }

TmnxWlanGwIsaMemberEntry         ::= SEQUENCE
{
    tmnxWlanGwIsaMemberId            Unsigned32,
    tmnxWlanGwIsaMemberChassisIndex  TmnxChassisIndexOrZero,
    tmnxWlanGwIsaMemberCardSlotNum   TmnxSlotNumOrZero,
    tmnxWlanGwIsaMemberSlotNum       Unsigned32,
    tmnxWlanGwIsaMemberNumSoftGreTu  Gauge32,
    tmnxWlanGwIsaMemberNumUe         Gauge32,
    tmnxWlanGwIsaMemberEegMemberAct  Gauge32,
    tmnxWlanGwIsaMemberEegMemberPend Gauge32,
    tmnxWlanGwIsaMemberTuQosProblem  Gauge32,
    tmnxWlanGwIsaMemberEsaNum        TmnxEsaNum,
    tmnxWlanGwIsaMemberEsaVappNum    TmnxEsaVappNum
}

tmnxWlanGwIsaMemberId            OBJECT-TYPE
    SYNTAX      Unsigned32
    MAX-ACCESS  not-accessible
    STATUS      current
    DESCRIPTION
        "The value of the object tmnxWlanGwIsaMemberId indicates the identifier
         of this WLAN Gateway ISA Group member."
    ::= { tmnxWlanGwIsaMemberEntry 1 }

tmnxWlanGwIsaMemberChassisIndex  OBJECT-TYPE
    SYNTAX      TmnxChassisIndexOrZero
    MAX-ACCESS  read-only
    STATUS      current
    DESCRIPTION
        "The value of tmnxWlanGwIsaMemberChassisIndex indicates the chassis of
         the MDA associated with this member.

         The value zero means that there is currently no MDA associated with
         this member."
    ::= { tmnxWlanGwIsaMemberEntry 2 }

tmnxWlanGwIsaMemberCardSlotNum   OBJECT-TYPE
    SYNTAX      TmnxSlotNumOrZero
    MAX-ACCESS  read-only
    STATUS      current
    DESCRIPTION
        "The value of tmnxWlanGwIsaMemberCardSlotNum indicates the IOM slot of
         the MDA associated with this member.

         The value zero means that there is currently no MDA associated with
         this member."
    ::= { tmnxWlanGwIsaMemberEntry 3 }

tmnxWlanGwIsaMemberSlotNum       OBJECT-TYPE
    SYNTAX      Unsigned32
    MAX-ACCESS  read-only
    STATUS      current
    DESCRIPTION
        "The value of tmnxWlanGwIsaMemberSlotNum indicates the MDA slot within
         the IOM of the MDA associated with this member.

         The value zero means that there is currently no MDA associated with
         this member."
    ::= { tmnxWlanGwIsaMemberEntry 4 }

tmnxWlanGwIsaMemberNumSoftGreTu  OBJECT-TYPE
    SYNTAX      Gauge32
    MAX-ACCESS  read-only
    STATUS      current
    DESCRIPTION
        "The value of tmnxWlanGwIsaMemberNumSoftGreTu indicates the number of
         tunnels processed by the MDA associated with this member."
    ::= { tmnxWlanGwIsaMemberEntry 5 }

tmnxWlanGwIsaMemberNumUe         OBJECT-TYPE
    SYNTAX      Gauge32
    MAX-ACCESS  read-only
    STATUS      current
    DESCRIPTION
        "The value of tmnxWlanGwIsaMemberNumUe indicates the number of UE
         processed by the MDA associated with this member."
    ::= { tmnxWlanGwIsaMemberEntry 6 }

tmnxWlanGwIsaMemberEegMemberAct  OBJECT-TYPE
    SYNTAX      Gauge32
    MAX-ACCESS  read-only
    STATUS      current
    DESCRIPTION
        "The value of tmnxWlanGwIsaMemberEegMemberAct indicates the number of
         activated Egress Encapsulation Group members associated with this ISA
         group member."
    ::= { tmnxWlanGwIsaMemberEntry 7 }

tmnxWlanGwIsaMemberEegMemberPend OBJECT-TYPE
    SYNTAX      Gauge32
    MAX-ACCESS  read-only
    STATUS      current
    DESCRIPTION
        "The value of tmnxWlanGwIsaMemberEegMemberPend indicates the number of
         pending Egress Encapsulation Group members associated with this ISA
         group member."
    ::= { tmnxWlanGwIsaMemberEntry 8 }

tmnxWlanGwIsaMemberTuQosProblem  OBJECT-TYPE
    SYNTAX      Gauge32
    MAX-ACCESS  read-only
    STATUS      current
    DESCRIPTION
        "The value of tmnxWlanGwIsaMemberTuQosProblem indicates the number of
         tunnel Qos infrastructure configuration instances on the MDA
         associated with this ISA group member that have a resource issue."
    ::= { tmnxWlanGwIsaMemberEntry 9 }

tmnxWlanGwIsaMemberEsaNum        OBJECT-TYPE
    SYNTAX      TmnxEsaNum
    MAX-ACCESS  read-only
    STATUS      current
    DESCRIPTION
        "The value of tmnxWlanGwIsaMemberEsaNum indicates the number of the
         Extended Service Appliance where the member is located."
    ::= { tmnxWlanGwIsaMemberEntry 10 }

tmnxWlanGwIsaMemberEsaVappNum    OBJECT-TYPE
    SYNTAX      TmnxEsaVappNum
    MAX-ACCESS  read-only
    STATUS      current
    DESCRIPTION
        "The value of tmnxWlanGwIsaMemberEsaVappNum indicates the number of the
         Virtual Machine within an Extended Service Appliance where the member
         is located."
    ::= { tmnxWlanGwIsaMemberEntry 11 }

tmnxWlanGwIsaMemberStatsTable    OBJECT-TYPE
    SYNTAX      SEQUENCE OF TmnxWlanGwIsaMemberStatsEntry
    MAX-ACCESS  not-accessible
    STATUS      obsolete
    DESCRIPTION
        "The tmnxWlanGwIsaMemberStatsTable contains detailed statistics
         information about the members of a WLAN Gateway ISA ISA Group."
    ::= { tmnxWlanGwIsaObjs 4 }

tmnxWlanGwIsaMemberStatsEntry    OBJECT-TYPE
    SYNTAX      TmnxWlanGwIsaMemberStatsEntry
    MAX-ACCESS  not-accessible
    STATUS      obsolete
    DESCRIPTION
        "Each conceptual row contains detailed statistics information about a
         member of a WLAN Gateway ISA Group.

         Entries in this table are created and removed automatically by the
         system."
    INDEX       {
        tmnxWlanGwGrpId,
        tmnxWlanGwIsaMemberId,
        tmnxWlanGwIsaMemberStatsType
    }
    ::= { tmnxWlanGwIsaMemberStatsTable 1 }

TmnxWlanGwIsaMemberStatsEntry    ::= SEQUENCE
{
    tmnxWlanGwIsaMemberStatsType     Unsigned32,
    tmnxWlanGwIsaMemberStatsName     DisplayString,
    tmnxWlanGwIsaMemberStatsVal      Counter32,
    tmnxWlanGwIsaMemberStatsValHw    Counter32,
    tmnxWlanGwIsaMemberStatsValue    Counter64
}

tmnxWlanGwIsaMemberStatsType     OBJECT-TYPE
    SYNTAX      Unsigned32 (0..199)
    MAX-ACCESS  not-accessible
    STATUS      current
    DESCRIPTION
        "The value of tmnxWlanGwIsaMemberStatsType indicates the type of WLAN
         Gateway statistics contained in this conceptual row."
    ::= { tmnxWlanGwIsaMemberStatsEntry 1 }

tmnxWlanGwIsaMemberStatsName     OBJECT-TYPE
    SYNTAX      DisplayString (SIZE (1..64))
    MAX-ACCESS  read-only
    STATUS      obsolete
    DESCRIPTION
        "The value of the object tmnxWlanGwIsaMemberStatsName indicates the
         human-readable identifier of the statistics contained in this
         conceptual row."
    ::= { tmnxWlanGwIsaMemberStatsEntry 2 }

tmnxWlanGwIsaMemberStatsVal      OBJECT-TYPE
    SYNTAX      Counter32
    MAX-ACCESS  read-only
    STATUS      obsolete
    DESCRIPTION
        "The value of the object tmnxWlanGwIsaMemberStatsVal indicates the
         lower 32-bits word of the statistics contained in this conceptual row."
    ::= { tmnxWlanGwIsaMemberStatsEntry 3 }

tmnxWlanGwIsaMemberStatsValHw    OBJECT-TYPE
    SYNTAX      Counter32
    MAX-ACCESS  read-only
    STATUS      obsolete
    DESCRIPTION
        "The value of the object tmnxWlanGwIsaMemberStatsValHw indicates the
         higher 32-bits word of the statistics contained in this conceptual
         row."
    ::= { tmnxWlanGwIsaMemberStatsEntry 4 }

tmnxWlanGwIsaMemberStatsValue    OBJECT-TYPE
    SYNTAX      Counter64
    MAX-ACCESS  read-only
    STATUS      obsolete
    DESCRIPTION
        "The value of the object tmnxWlanGwIsaMemberStatsValue indicates the
         value of the statistics contained in this conceptual row."
    ::= { tmnxWlanGwIsaMemberStatsEntry 5 }

tmnxWlanGwMdaTable               OBJECT-TYPE
    SYNTAX      SEQUENCE OF TmnxWlanGwMdaEntry
    MAX-ACCESS  not-accessible
    STATUS      current
    DESCRIPTION
        "The tmnxWlanGwMdaTable contains objects to configure the WLAN Gateway
         ISA Group Media Dependent Adapter (MDA)."
    ::= { tmnxWlanGwIsaObjs 7 }

tmnxWlanGwMdaEntry               OBJECT-TYPE
    SYNTAX      TmnxWlanGwMdaEntry
    MAX-ACCESS  not-accessible
    STATUS      current
    DESCRIPTION
        "Each conceptual row represents a WLAN Gateway ISA Media Dependent
         Adapter (MDA) of a WLAN Gateway ISA Group.

         Entries in this table can be created or deleted via SNMP operations."
    INDEX       {
        tmnxWlanGwGrpId,
        tmnxChassisIndex,
        tmnxCardSlotNum,
        tmnxMDASlotNum
    }
    ::= { tmnxWlanGwMdaTable 1 }

TmnxWlanGwMdaEntry               ::= SEQUENCE
{
    tmnxWlanGwMdaRowStatus           RowStatus,
    tmnxWlanGwMdaLastMgmtChange      TimeStamp
}

tmnxWlanGwMdaRowStatus           OBJECT-TYPE
    SYNTAX      RowStatus
    MAX-ACCESS  read-create
    STATUS      current
    DESCRIPTION
        "The value of tmnxWlanGwMdaRowStatus specifies the row status of this
         row.

         For a given value of tmnxWlanGwGrpId, it is only allowed to create a
         conceptual row in this table if the value of the
         tmnxWlanGwGrpRedundancyUnit object in the corresponding row in the
         tmnxWlanGwGrpTable is equal to 'mda'."
    ::= { tmnxWlanGwMdaEntry 1 }

tmnxWlanGwMdaLastMgmtChange      OBJECT-TYPE
    SYNTAX      TimeStamp
    MAX-ACCESS  read-only
    STATUS      current
    DESCRIPTION
        "The value of tmnxWlanGwMdaLastMgmtChange indicates the sysUpTime at
         the time of the most recent management-initiated change to this table
         row."
    ::= { tmnxWlanGwMdaEntry 2 }

tmnxWlanGwIsaStatsTable          OBJECT-TYPE
    SYNTAX      SEQUENCE OF TmnxWlanGwIsaStatsEntry
    MAX-ACCESS  not-accessible
    STATUS      current
    DESCRIPTION
        "The tmnxWlanGwIsaStatsTable contains detailed statistics information
         about the members of a WLAN Gateway ISA ISA Group."
    ::= { tmnxWlanGwIsaObjs 8 }

tmnxWlanGwIsaStatsEntry          OBJECT-TYPE
    SYNTAX      TmnxWlanGwIsaStatsEntry
    MAX-ACCESS  not-accessible
    STATUS      current
    DESCRIPTION
        "Each conceptual row contains detailed statistics information about a
         member of a WLAN Gateway ISA Group.

         Entries in this table are created and removed automatically by the
         system."
    INDEX       {
        tmnxWlanGwGrpId,
        tmnxWlanGwIsaMemberId,
        tmnxWlanGwIsaStatsType,
        tmnxWlanGwIsaStatsId
    }
    ::= { tmnxWlanGwIsaStatsTable 1 }

TmnxWlanGwIsaStatsEntry          ::= SEQUENCE
{
    tmnxWlanGwIsaStatsType           INTEGER,
    tmnxWlanGwIsaStatsId             Unsigned32,
    tmnxWlanGwIsaStatsName           DisplayString,
    tmnxWlanGwIsaStatsValue          Counter64
}

tmnxWlanGwIsaStatsType           OBJECT-TYPE
    SYNTAX      INTEGER {
        packetErrors (0),
        hostErrors   (1),
        bdErrors     (2),
        forwarding   (3),
        reassembly   (4),
        aa           (5),
        radius       (6),
        arp          (7),
        dhcp         (8),
        dhcp6        (9),
        icmp         (10),
        icmp6        (11)
    }
    MAX-ACCESS  not-accessible
    STATUS      current
    DESCRIPTION
        "The value of tmnxWlanGwIsaStatsType indicates the type of WLAN Gateway
         statistics contained in this conceptual row."
    ::= { tmnxWlanGwIsaStatsEntry 1 }

tmnxWlanGwIsaStatsId             OBJECT-TYPE
    SYNTAX      Unsigned32 (0..40)
    MAX-ACCESS  not-accessible
    STATUS      current
    DESCRIPTION
        "The value of tmnxWlanGwIsaStatsId indicates the identifier of WLAN
         Gateway statistics contained in this conceptual row.

         The meaning of an identifier depends on its type and is indicated by
         its name."
    ::= { tmnxWlanGwIsaStatsEntry 2 }

tmnxWlanGwIsaStatsName           OBJECT-TYPE
    SYNTAX      DisplayString (SIZE (1..64))
    MAX-ACCESS  read-only
    STATUS      current
    DESCRIPTION
        "The value of the object tmnxWlanGwIsaStatsName indicates the
         human-readable identifier of the statistics contained in this
         conceptual row."
    ::= { tmnxWlanGwIsaStatsEntry 3 }

tmnxWlanGwIsaStatsValue          OBJECT-TYPE
    SYNTAX      Counter64
    MAX-ACCESS  read-only
    STATUS      current
    DESCRIPTION
        "The value of the object tmnxWlanGwIsaStatsValue indicates the value of
         the statistics contained in this conceptual row."
    ::= { tmnxWlanGwIsaStatsEntry 4 }

tmnxWlanGwGrpWmTable             OBJECT-TYPE
    SYNTAX      SEQUENCE OF TmnxWlanGwGrpWmEntry
    MAX-ACCESS  not-accessible
    STATUS      current
    DESCRIPTION
        "The tmnxWlanGwGrpWmTable contains objects to configure watermarks for
         WLAN Gateway ISA Groups"
    ::= { tmnxWlanGwIsaObjs 9 }

tmnxWlanGwGrpWmEntry             OBJECT-TYPE
    SYNTAX      TmnxWlanGwGrpWmEntry
    MAX-ACCESS  not-accessible
    STATUS      current
    DESCRIPTION
        "Each conceptual row represents a set of high and low watermarks for a
         WLAN Gateway ISA Group.

         Entries in this table can be created or deleted via SNMP operations."
    INDEX       {
        tmnxWlanGwGrpId,
        tmnxWlanGwGrpWmEntity
    }
    ::= { tmnxWlanGwGrpWmTable 1 }

TmnxWlanGwGrpWmEntry             ::= SEQUENCE
{
    tmnxWlanGwGrpWmEntity            TmnxWlanGwWatermarkEntity,
    tmnxWlanGwGrpWmRowStatus         RowStatus,
    tmnxWlanGwGrpWmLastMgmtChange    TimeStamp,
    tmnxWlanGwGrpWmHi                TmnxNatWaterMark,
    tmnxWlanGwGrpWmLo                TmnxNatWaterMark
}

tmnxWlanGwGrpWmEntity            OBJECT-TYPE
    SYNTAX      TmnxWlanGwWatermarkEntity
    MAX-ACCESS  not-accessible
    STATUS      current
    DESCRIPTION
        "The value of the object tmnxWlanGwGrpWmEntity specifies the entity
         whose quantity is monitored."
    ::= { tmnxWlanGwGrpWmEntry 1 }

tmnxWlanGwGrpWmRowStatus         OBJECT-TYPE
    SYNTAX      RowStatus
    MAX-ACCESS  read-create
    STATUS      current
    DESCRIPTION
        "The value of tmnxWlanGwGrpWmRowStatus specifies the row status of this
         row."
    ::= { tmnxWlanGwGrpWmEntry 2 }

tmnxWlanGwGrpWmLastMgmtChange    OBJECT-TYPE
    SYNTAX      TimeStamp
    MAX-ACCESS  read-only
    STATUS      current
    DESCRIPTION
        "The value of tmnxWlanGwGrpWmLastMgmtChange indicates the sysUpTime at
         the time of the most recent management-initiated change to this table
         row."
    ::= { tmnxWlanGwGrpWmEntry 3 }

tmnxWlanGwGrpWmHi                OBJECT-TYPE
    SYNTAX      TmnxNatWaterMark (1..100)
    MAX-ACCESS  read-create
    STATUS      current
    DESCRIPTION
        "The value of tmnxWlanGwGrpWmHi specifies the high watermark of the
         number of entities for each MDA in this ISA group.

         While creating a conceptual row, a value for tmnxWlanGwGrpWmHi must be
         specified.

         The value of this object must be set together with the value of
         tmnxWlanGwGrpWmLo.

         The value of this object must be higher than the value of
         tmnxWlanGwGrpWmLo."
    ::= { tmnxWlanGwGrpWmEntry 4 }

tmnxWlanGwGrpWmLo                OBJECT-TYPE
    SYNTAX      TmnxNatWaterMark (0..99)
    MAX-ACCESS  read-create
    STATUS      current
    DESCRIPTION
        "The value of tmnxWlanGwGrpWmLo specifies the low watermark of the
         number of entities for each MDA in this ISA group.

         While creating a conceptual row, a value for tmnxWlanGwGrpWmLo must be
         specified.

         The value of this object must be set together with the value of
         tmnxWlanGwGrpWmHi.

         The value of this object must be lower than the value of
         tmnxWlanGwGrpWmHi."
    ::= { tmnxWlanGwGrpWmEntry 5 }

tmnxWlanGwIsaResrcStatsTable     OBJECT-TYPE
    SYNTAX      SEQUENCE OF TmnxWlanGwIsaResrcStatsEntry
    MAX-ACCESS  not-accessible
    STATUS      current
    DESCRIPTION
        "The tmnxWlanGwIsaResrcStatsTable contains detailed statistics
         information about the members of a WLAN Gateway ISA ISA Group."
    ::= { tmnxWlanGwIsaObjs 10 }

tmnxWlanGwIsaResrcStatsEntry     OBJECT-TYPE
    SYNTAX      TmnxWlanGwIsaResrcStatsEntry
    MAX-ACCESS  not-accessible
    STATUS      current
    DESCRIPTION
        "Each conceptual row contains detailed resource statistics information
         about a member of a WLAN Gateway ISA Group.

         Entries in this table are created and removed automatically by the
         system."
    INDEX       {
        tmnxWlanGwGrpId,
        tmnxWlanGwIsaMemberId,
        tmnxWlanGwIsaResrcStatsId
    }
    ::= { tmnxWlanGwIsaResrcStatsTable 1 }

TmnxWlanGwIsaResrcStatsEntry     ::= SEQUENCE
{
    tmnxWlanGwIsaResrcStatsId        Unsigned32,
    tmnxWlanGwIsaResrcStatsName      DisplayString,
    tmnxWlanGwIsaResrcStatsMaxValue  Counter64,
    tmnxWlanGwIsaResrcStatsValue     Counter64,
    tmnxWlanGwIsaResrcStatsPeakValue Counter64,
    tmnxWlanGwIsaResrcStatsPeakTime  DateAndTime
}

tmnxWlanGwIsaResrcStatsId        OBJECT-TYPE
    SYNTAX      Unsigned32 (0..40)
    MAX-ACCESS  not-accessible
    STATUS      current
    DESCRIPTION
        "The value of tmnxWlanGwIsaResrcStatsId indicates the identifier of the
         WLAN Gateway resource statistics contained in this conceptual row.

         The meaning of an identifier is indicated by the value of
         tmnxWlanGwIsaResrcStatsName."
    ::= { tmnxWlanGwIsaResrcStatsEntry 1 }

tmnxWlanGwIsaResrcStatsName      OBJECT-TYPE
    SYNTAX      DisplayString (SIZE (1..64))
    MAX-ACCESS  read-only
    STATUS      current
    DESCRIPTION
        "The value of the object tmnxWlanGwIsaResrcStatsName indicates the
         human-readable identifier of the resource statistics contained in this
         conceptual row."
    ::= { tmnxWlanGwIsaResrcStatsEntry 2 }

tmnxWlanGwIsaResrcStatsMaxValue  OBJECT-TYPE
    SYNTAX      Counter64
    MAX-ACCESS  read-only
    STATUS      current
    DESCRIPTION
        "The value of the object tmnxWlanGwIsaResrcStatsMaxValue indicates the
         maximum possible value of the resource statistics contained in this
         conceptual row."
    ::= { tmnxWlanGwIsaResrcStatsEntry 3 }

tmnxWlanGwIsaResrcStatsValue     OBJECT-TYPE
    SYNTAX      Counter64
    MAX-ACCESS  read-only
    STATUS      current
    DESCRIPTION
        "The value of the object tmnxWlanGwIsaResrcStatsValue indicates the
         actual value of the resource statistics contained in this conceptual
         row."
    ::= { tmnxWlanGwIsaResrcStatsEntry 4 }

tmnxWlanGwIsaResrcStatsPeakValue OBJECT-TYPE
    SYNTAX      Counter64
    MAX-ACCESS  read-only
    STATUS      current
    DESCRIPTION
        "The value of the object tmnxWlanGwIsaResrcStatsPeakValue indicates the
         peak value of the resource statistics contained in this conceptual
         row."
    ::= { tmnxWlanGwIsaResrcStatsEntry 5 }

tmnxWlanGwIsaResrcStatsPeakTime  OBJECT-TYPE
    SYNTAX      DateAndTime (SIZE (11))
    MAX-ACCESS  read-only
    STATUS      current
    DESCRIPTION
        "The value of tmnxWlanGwIsaResrcStatsPeakTime indicates the time the
         system reached the peak value of the resource statistics contained in
         this conceptual row."
    ::= { tmnxWlanGwIsaResrcStatsEntry 6 }

tmnxWlanGwEsaObjs                OBJECT IDENTIFIER ::= { tmnxWlanGwIsaObjs 11 }

tmnxWlanGwVappTable              OBJECT-TYPE
    SYNTAX      SEQUENCE OF TmnxWlanGwVappEntry
    MAX-ACCESS  not-accessible
    STATUS      current
    DESCRIPTION
        "The tmnxWlanGwVappTable contains objects to configure the WLAN Gateway
         ISA Group Virtual Application.."
    ::= { tmnxWlanGwEsaObjs 1 }

tmnxWlanGwVappEntry              OBJECT-TYPE
    SYNTAX      TmnxWlanGwVappEntry
    MAX-ACCESS  not-accessible
    STATUS      current
    DESCRIPTION
        "Each conceptual row represents a WLAN Gateway ISA Group Member of a
         WLAN Gateway ISA Group.

         Entries in this table can be created or deleted via SNMP operations."
    INDEX       {
        tmnxWlanGwGrpId,
        tmnxWlanGwEsaNum,
        tmnxWlanGwEsaVappNum
    }
    ::= { tmnxWlanGwVappTable 1 }

TmnxWlanGwVappEntry              ::= SEQUENCE
{
    tmnxWlanGwEsaNum                 TmnxEsaNum,
    tmnxWlanGwEsaVappNum             TmnxEsaVappNum,
    tmnxWlanGwVappRowStatus          RowStatus,
    tmnxWlanGwVappLastMgmtChange     TimeStamp
}

tmnxWlanGwEsaNum                 OBJECT-TYPE
    SYNTAX      TmnxEsaNum (1..16)
    MAX-ACCESS  not-accessible
    STATUS      current
    DESCRIPTION
        "The value of tmnxWlanGwEsaNum indicates the number of the Extended
         Service Appliance where the member is located."
    ::= { tmnxWlanGwVappEntry 1 }

tmnxWlanGwEsaVappNum             OBJECT-TYPE
    SYNTAX      TmnxEsaVappNum (1..4)
    MAX-ACCESS  not-accessible
    STATUS      current
    DESCRIPTION
        "The value of tmnxWlanGwEsaVappNum indicates the number of the Virtual
         Machine within an Extended Service Appliance where the member is
         located"
    ::= { tmnxWlanGwVappEntry 2 }

tmnxWlanGwVappRowStatus          OBJECT-TYPE
    SYNTAX      RowStatus
    MAX-ACCESS  read-create
    STATUS      current
    DESCRIPTION
        "The value of tmnxWlanGwVappRowStatus specifies the row status of this
         row."
    ::= { tmnxWlanGwVappEntry 3 }

tmnxWlanGwVappLastMgmtChange     OBJECT-TYPE
    SYNTAX      TimeStamp
    MAX-ACCESS  read-only
    STATUS      current
    DESCRIPTION
        "The value of tmnxWlanGwVappLastMgmtChange indicates the sysUpTime at
         the time of the most recent management-initiated change to this table
         row."
    ::= { tmnxWlanGwVappEntry 4 }

tmnxWlanGwSoftGreObjs            OBJECT IDENTIFIER ::= { tmnxWlanGwObjs 2 }

tmnxWlanGwSoftGreIfTable         OBJECT-TYPE
    SYNTAX      SEQUENCE OF TmnxWlanGwSoftGreIfEntry
    MAX-ACCESS  not-accessible
    STATUS      current
    DESCRIPTION
        "The tmnxWlanGwSoftGreIfTable contains objects to configure WLAN
         Gateway Group-Interfaces.

         Entries in this table are created and destroyed by the system.

         The system automatically creates an entry in this table for each entry
         in the TIMETRA-SERV-MIB::iesIfTable where the value of iesIfType is
         equal to 'group' and the value of iesIfGroupInterfaceType is equal to
         'softGre'.

         Deletion of such a row in the iesIfTable results in the same fate for
         the corresponding row in this table."
    ::= { tmnxWlanGwSoftGreObjs 1 }

tmnxWlanGwSoftGreIfEntry         OBJECT-TYPE
    SYNTAX      TmnxWlanGwSoftGreIfEntry
    MAX-ACCESS  not-accessible
    STATUS      current
    DESCRIPTION
        "Each conceptual row contains Soft GRE specific information of a
         specific group interface."
    INDEX       {
        svcId,
        iesIfIndex
    }
    ::= { tmnxWlanGwSoftGreIfTable 1 }

TmnxWlanGwSoftGreIfEntry         ::= SEQUENCE
{
    tmnxWlanGwSoftGreIfLastCh        TimeStamp,
    tmnxWlanGwSoftGreIfAdminState    TmnxAdminState,
    tmnxWlanGwSoftGreIfRouter        TmnxVRtrIDOrZero,
    tmnxWlanGwSoftGreIfGwAddrType    InetAddressType,
    tmnxWlanGwSoftGreIfGwAddr        InetAddress,
    tmnxWlanGwSoftGreIfGrpId         TmnxWlanGwIsaGrpIdOrZero,
    tmnxWlanGwSoftGreIfShapingType   INTEGER,
    tmnxWlanGwSoftGreIfShapeMultiUe  TruthValue,
    tmnxWlanGwSoftGreIfEQosPlcy      TPolicyID,
    tmnxWlanGwSoftGreIfESchedPlcy    TNamedItemOrEmpty,
    tmnxWlanGwSoftGreIfEAggRateLimit TPortSchedulerPIR,
    tmnxWlanGwSoftGreIfMobTrigger    BITS,
    tmnxWlanGwSoftGreIfMobHoldTime   Unsigned32,
    tmnxWlanGwSoftGreIfDefRetailSvc  TmnxServId,
    tmnxWlanGwSoftGreIfTcpMssAdjust  Unsigned32,
    tmnxWlanGwSoftGreIfEHoldTime     Unsigned32,
    tmnxWlanGwSoftGreIfDataTrigg     TmnxEnabledDisabled,
    tmnxWlanGwSoftGreIfAuthPlcy      TNamedItemOrEmpty,
    tmnxWlanGwSoftGreIfAuthHoldTime  Unsigned32,
    tmnxWlanGwSoftGreIfRadProxVrtr   TmnxVRtrIDOrZero,
    tmnxWlanGwSoftGreIfRadProxSrv    TNamedItemOrEmpty,
    tmnxWlanGwSoftGreIfRadProxMacFmt TmnxMacSpecification,
    tmnxWlanGwSoftGreIfGwV6AddrType  InetAddressType,
    tmnxWlanGwSoftGreIfGwV6Addr      InetAddress,
    tmnxWlanGwSoftGreIfMobArpAp      TmnxEnabledDisabled,
    tmnxWlanGwSoftGreIfDownIfGrpDeg  TruthValue,
    tmnxWlanGwSoftGreIfL2ApEncapType INTEGER,
    tmnxWlanGwSoftGreIfMultiTuType   TruthValue,
    tmnxWlanGwSoftGreIfL2tpLrnCookie INTEGER,
    tmnxWlanGwSoftGreIfL2tpCookie    OCTET STRING,
    tmnxWlanGwSoftGreIfMaxLanextBd   Unsigned32,
    tmnxWlanGwSoftGreIfNumSoftGreTu  Gauge32,
    tmnxWlanGwSoftGreIfLearnApMac    TmnxEnabledDisabled,
    tmnxWlanGwSoftGreIfLearnApMacDA  TmnxEnabledDisabled,
    tmnxWlanGwSoftGreIfMobInterVlan  TmnxEnabledDisabled,
    tmnxWlanGwSoftGreIfL2ApAutoSubId INTEGER
}

tmnxWlanGwSoftGreIfLastCh        OBJECT-TYPE
    SYNTAX      TimeStamp
    MAX-ACCESS  read-only
    STATUS      current
    DESCRIPTION
        "The value of tmnxWlanGwSoftGreIfLastCh indicates the sysUpTime at the
         time of the most recent management-initiated change to this table row."
    ::= { tmnxWlanGwSoftGreIfEntry 1 }

tmnxWlanGwSoftGreIfAdminState    OBJECT-TYPE
    SYNTAX      TmnxAdminState
    MAX-ACCESS  read-create
    STATUS      current
    DESCRIPTION
        "The value of tmnxWlanGwSoftGreIfAdminState specifies the
         administrative state of Soft GRE on this group interface."
    DEFVAL      { outOfService }
    ::= { tmnxWlanGwSoftGreIfEntry 2 }

tmnxWlanGwSoftGreIfRouter        OBJECT-TYPE
    SYNTAX      TmnxVRtrIDOrZero
    MAX-ACCESS  read-create
    STATUS      current
    DESCRIPTION
        "The value of tmnxWlanGwSoftGreIfRouter specifies the identifier of the
         virtual router instance where the tunneled User Equipment traffic is
         routed.

         The value zero specifies that the router instance corresponding to the
         service containing this interface is used."
    DEFVAL      { 0 }
    ::= { tmnxWlanGwSoftGreIfEntry 3 }

tmnxWlanGwSoftGreIfGwAddrType    OBJECT-TYPE
    SYNTAX      InetAddressType
    MAX-ACCESS  read-create
    STATUS      current
    DESCRIPTION
        "The value of tmnxWlanGwSoftGreIfGwAddrType specifies the type of
         address stored in tmnxWlanGwSoftGreIfGwAddr."
    DEFVAL      { unknown }
    ::= { tmnxWlanGwSoftGreIfEntry 4 }

tmnxWlanGwSoftGreIfGwAddr        OBJECT-TYPE
    SYNTAX      InetAddress (SIZE (0|4|16))
    MAX-ACCESS  read-create
    STATUS      current
    DESCRIPTION
        "The value of tmnxWlanGwSoftGreIfGwAddr specifies the IP address of the
         WLAN Gateway GRE function of this system on this group interface."
    DEFVAL      { ''H }
    ::= { tmnxWlanGwSoftGreIfEntry 5 }

tmnxWlanGwSoftGreIfGrpId         OBJECT-TYPE
    SYNTAX      TmnxWlanGwIsaGrpIdOrZero
    MAX-ACCESS  read-create
    STATUS      current
    DESCRIPTION
        "The value of tmnxWlanGwSoftGreIfGrpId specifies the identifier of the
         WLAN Gateway ISA group that terminates GRE for this group interface."
    DEFVAL      { 0 }
    ::= { tmnxWlanGwSoftGreIfEntry 6 }

tmnxWlanGwSoftGreIfShapingType   OBJECT-TYPE
    SYNTAX      INTEGER {
        none        (0),
        perTunnel   (1),
        perRetailer (2)
    }
    MAX-ACCESS  read-create
    STATUS      current
    DESCRIPTION
        "The value of tmnxWlanGwSoftGreIfShapingType specifies the granularity
         of the egress shaping for Soft GRE on this group interface.

         The value of this object can only be modified while the value of
         tmnxWlanGwSoftGreIfAdminState is equal to 'outOfService'.

         The value 'perTunnel' specifies that a separate shaper is applied to
         each Soft GRE tunnel; the value 'perRetailer' specifies that a
         separate shaper is applied to each retailer Mobile Network Operator's
         fraction of the Soft GRE tunnel payload."
    DEFVAL      { none }
    ::= { tmnxWlanGwSoftGreIfEntry 7 }

tmnxWlanGwSoftGreIfShapeMultiUe  OBJECT-TYPE
    SYNTAX      TruthValue
    MAX-ACCESS  read-create
    STATUS      current
    DESCRIPTION
        "The value of tmnxWlanGwSoftGreIfShapeMultiUe specifies conditional
         egress shaping.

         If the value of tmnxWlanGwSoftGreIfShapeMultiUe is equal to 'true',
         egress shaping is only enabled for a Soft GRE tunnel while there are
         multiple UE (User Equipment) using it.

         If the value of tmnxWlanGwSoftGreIfShapeMultiUe is equal to 'false',
         egress shaping is always enabled for every Soft GRE tunnel, also while
         there is only a single UE using it."
    DEFVAL      { false }
    ::= { tmnxWlanGwSoftGreIfEntry 8 }

tmnxWlanGwSoftGreIfEQosPlcy      OBJECT-TYPE
    SYNTAX      TPolicyID (1..65535)
    MAX-ACCESS  read-create
    STATUS      current
    DESCRIPTION
        "The value of tmnxWlanGwSoftGreIfEQosPlcy specifies the identifier of
         the egress QoS policy associated with each Soft GRE tunnel of this
         interface."
    DEFVAL      { 1 }
    ::= { tmnxWlanGwSoftGreIfEntry 9 }

tmnxWlanGwSoftGreIfESchedPlcy    OBJECT-TYPE
    SYNTAX      TNamedItemOrEmpty
    MAX-ACCESS  read-create
    STATUS      current
    DESCRIPTION
        "The value of tmnxWlanGwSoftGreIfESchedPlcy specifies the identifier of
         the egress scheduler policy associated with each Soft GRE tunnel of
         this interface."
    DEFVAL      { "" }
    ::= { tmnxWlanGwSoftGreIfEntry 10 }

tmnxWlanGwSoftGreIfEAggRateLimit OBJECT-TYPE
    SYNTAX      TPortSchedulerPIR
    UNITS       "kilobps"
    MAX-ACCESS  read-create
    STATUS      current
    DESCRIPTION
        "The value of tmnxWlanGwSoftGreIfEAggRateLimit specifies the aggregate
         rate limit of each shaper associated with this interface.

         The value minus one specifies that there is no limit configured."
    DEFVAL      { -1 }
    ::= { tmnxWlanGwSoftGreIfEntry 11 }

tmnxWlanGwSoftGreIfMobTrigger    OBJECT-TYPE
    SYNTAX      BITS {
        data    (0),
        iapp    (1),
        control (2)
    }
    MAX-ACCESS  read-create
    STATUS      current
    DESCRIPTION
        "The value of tmnxWlanGwSoftGreIfMobTrigger specifies what is used as a
         trigger for mobility detection.

         The value 'data' specifies that data traffic be used as a trigger.

         The value 'iapp' specifies that Inter Access Point Protocol (IAPP)
         messages be used as a trigger.

         The value 'control' specifies that DHCP, DHCPv6 and ICMPv6-RS messages
         be used as a trigger."
    DEFVAL      { {} }
    ::= { tmnxWlanGwSoftGreIfEntry 12 }

tmnxWlanGwSoftGreIfMobHoldTime   OBJECT-TYPE
    SYNTAX      Unsigned32 (0..255)
    UNITS       "seconds"
    MAX-ACCESS  read-create
    STATUS      current
    DESCRIPTION
        "The value of tmnxWlanGwSoftGreIfMobHoldTime specifies the minimum time
         that a User Equipment will be held associated with its current Access
         Point (AP) before being associated with a new AP.

         The hold time is used to prevent overwhelming the system with mobility
         triggers, by limiting the rate at which a UE can move from one AP to
         another while the system is very busy already."
    DEFVAL      { 5 }
    ::= { tmnxWlanGwSoftGreIfEntry 13 }

tmnxWlanGwSoftGreIfDefRetailSvc  OBJECT-TYPE
    SYNTAX      TmnxServId
    MAX-ACCESS  read-create
    STATUS      obsolete
    DESCRIPTION
        "This object is obsolete. Please ue 'tmnxWlanGwVlanRetailService'
         instead."
    DEFVAL      { 0 }
    ::= { tmnxWlanGwSoftGreIfEntry 14 }

tmnxWlanGwSoftGreIfTcpMssAdjust  OBJECT-TYPE
    SYNTAX      Unsigned32 (0 | 160..10240)
    UNITS       "bytes"
    MAX-ACCESS  read-create
    STATUS      current
    DESCRIPTION
        "The value of tmnxWlanGwSoftGreIfTcpMssAdjust specifies the value to
         put into the TCP Maximum Segment Size (MSS) option if not already
         present, or if the present value is higher.

         The value zero means that no MSS option adjustment is done."
    DEFVAL      { 0 }
    ::= { tmnxWlanGwSoftGreIfEntry 15 }

tmnxWlanGwSoftGreIfEHoldTime     OBJECT-TYPE
    SYNTAX      Unsigned32 (0..86400 | 4294967295)
    UNITS       "seconds"
    MAX-ACCESS  read-create
    STATUS      current
    DESCRIPTION
        "The value of tmnxWlanGwSoftGreIfEHoldTime specifies the minimum time
         that the egress QoS resources associated with a Soft GRE tunnel (such
         as a shaper) are held after the last User Equipment of the Soft GRE
         tunnel has disappeared.

         The value all ones specifies an infinite time.

         The value zero specifies that the resources are released immediately."
    DEFVAL      { 0 }
    ::= { tmnxWlanGwSoftGreIfEntry 16 }

tmnxWlanGwSoftGreIfDataTrigg     OBJECT-TYPE
    SYNTAX      TmnxEnabledDisabled
    MAX-ACCESS  read-create
    STATUS      obsolete
    DESCRIPTION
        "The object tmnxWlanGwSoftGreIfDataTrigg is obsolete.

         Please use the object tmnxWlanGwVlanDataTrigg in the
         tmnxWlanGwVlanTable instead, with the default VLAN tag range
         [4096-4096], to configure the default properties for the WLAN Gateway
         interface."
    DEFVAL      { disabled }
    ::= { tmnxWlanGwSoftGreIfEntry 18 }

tmnxWlanGwSoftGreIfAuthPlcy      OBJECT-TYPE
    SYNTAX      TNamedItemOrEmpty
    MAX-ACCESS  read-create
    STATUS      obsolete
    DESCRIPTION
        "The object tmnxWlanGwSoftGreIfAuthPlcy is obsolete.

         Please use the object tmnxWlanGwVlanAuthPlcy in the
         tmnxWlanGwVlanTable instead, with the default VLAN tag range
         [4096-4096], to configure the default properties for the WLAN Gateway
         interface."
    DEFVAL      { "" }
    ::= { tmnxWlanGwSoftGreIfEntry 19 }

tmnxWlanGwSoftGreIfAuthHoldTime  OBJECT-TYPE
    SYNTAX      Unsigned32 (0..3600)
    UNITS       "seconds"
    MAX-ACCESS  read-create
    STATUS      obsolete
    DESCRIPTION
        "The object tmnxWlanGwSoftGreIfAuthHoldTime is obsolete.

         Please use the object tmnxWlanGwVlanAuthHoldTime in the
         tmnxWlanGwVlanTable instead, with the default VLAN tag range
         [4096-4096], to configure the default properties for the WLAN Gateway
         interface."
    DEFVAL      { 5 }
    ::= { tmnxWlanGwSoftGreIfEntry 20 }

tmnxWlanGwSoftGreIfRadProxVrtr   OBJECT-TYPE
    SYNTAX      TmnxVRtrIDOrZero
    MAX-ACCESS  read-create
    STATUS      obsolete
    DESCRIPTION
        "The object tmnxWlanGwSoftGreIfRadProxVrtr is obsolete.

         Please use the object tmnxWlanGwVlanRadProxVrtr in the
         tmnxWlanGwVlanTable instead, with the default VLAN tag range
         [4096-4096], to configure the default properties for the WLAN Gateway
         interface."
    DEFVAL      { 0 }
    ::= { tmnxWlanGwSoftGreIfEntry 21 }

tmnxWlanGwSoftGreIfRadProxSrv    OBJECT-TYPE
    SYNTAX      TNamedItemOrEmpty
    MAX-ACCESS  read-create
    STATUS      obsolete
    DESCRIPTION
        "The object tmnxWlanGwSoftGreIfRadProxSrv is obsolete.

         Please use the object tmnxWlanGwVlanRadProxSrv in the
         tmnxWlanGwVlanTable instead, with the default VLAN tag range
         [4096-4096], to configure the default properties for the WLAN Gateway
         interface."
    DEFVAL      { "" }
    ::= { tmnxWlanGwSoftGreIfEntry 22 }

tmnxWlanGwSoftGreIfRadProxMacFmt OBJECT-TYPE
    SYNTAX      TmnxMacSpecification (SIZE (2..7))
    MAX-ACCESS  read-create
    STATUS      obsolete
    DESCRIPTION
        "The object tmnxWlanGwSoftGreIfRadProxMacFmt is obsolete.

         Please use the object tmnxWlanGwVlanRadProxMacFmt in the
         tmnxWlanGwVlanTable instead, with the default VLAN tag range
         [4096-4096], to configure the default properties for the WLAN Gateway
         interface."
    DEFVAL      { "aa:" }
    ::= { tmnxWlanGwSoftGreIfEntry 23 }

tmnxWlanGwSoftGreIfGwV6AddrType  OBJECT-TYPE
    SYNTAX      InetAddressType
    MAX-ACCESS  read-create
    STATUS      current
    DESCRIPTION
        "The value of tmnxWlanGwSoftGreIfGwV6AddrType specifies the type of
         address stored in tmnxWlanGwSoftGreIfGwV6Addr."
    DEFVAL      { unknown }
    ::= { tmnxWlanGwSoftGreIfEntry 29 }

tmnxWlanGwSoftGreIfGwV6Addr      OBJECT-TYPE
    SYNTAX      InetAddress (SIZE (0|16))
    MAX-ACCESS  read-create
    STATUS      current
    DESCRIPTION
        "The value of tmnxWlanGwSoftGreIfGwV6Addr specifies the IP address of
         the WLAN Gateway GRE function of this system on this group interface."
    DEFVAL      { ''H }
    ::= { tmnxWlanGwSoftGreIfEntry 30 }

tmnxWlanGwSoftGreIfMobArpAp      OBJECT-TYPE
    SYNTAX      TmnxEnabledDisabled
    MAX-ACCESS  read-create
    STATUS      current
    DESCRIPTION
        "The value of tmnxWlanGwSoftGreIfMobArpAp specifies if this system
         sends an ARP Request upon detecting mobility, in order to learn the
         MAC address of the Access Point."
    DEFVAL      { disabled }
    ::= { tmnxWlanGwSoftGreIfEntry 32 }

tmnxWlanGwSoftGreIfDownIfGrpDeg  OBJECT-TYPE
    SYNTAX      TruthValue
    MAX-ACCESS  read-create
    STATUS      current
    DESCRIPTION
        "The value of tmnxWlanGwSoftGreIfDownIfGrpDeg specifies if the system
         will bring this interface operationally down when its ISA WLAN Gateway
         becomes degraded, that means: when the value of the object
         tmnxWlanGwGrpDegraded in the row where the tmnxWlanGwGrpId is equal to
         the value of tmnxWlanGwSoftGreIfGrpId is equal to 'true'."
    DEFVAL      { false }
    ::= { tmnxWlanGwSoftGreIfEntry 35 }

tmnxWlanGwSoftGreIfL2ApEncapType OBJECT-TYPE
    SYNTAX      INTEGER {
        null  (1),
        dot1q (2),
        qinq  (10)
    }
    MAX-ACCESS  read-create
    STATUS      current
    DESCRIPTION
        "The value of tmnxWlanGwSoftGreIfL2ApEncapType specifies the
         encapsulation type of all layer 2 access points where the value of
         tmnxWlanGwL2ApEncapType is equal to 'default'."
    DEFVAL      { null }
    ::= { tmnxWlanGwSoftGreIfEntry 36 }

tmnxWlanGwSoftGreIfMultiTuType   OBJECT-TYPE
    SYNTAX      TruthValue
    MAX-ACCESS  read-create
    STATUS      current
    DESCRIPTION
        "The value of tmnxWlanGwSoftGreIfMultiTuType specifies if this system
         supports multiple tunnel types terminating on this interface."
    DEFVAL      { false }
    ::= { tmnxWlanGwSoftGreIfEntry 37 }

tmnxWlanGwSoftGreIfL2tpLrnCookie OBJECT-TYPE
    SYNTAX      INTEGER {
        ifMatch (1),
        never   (2),
        always  (3)
    }
    MAX-ACCESS  read-create
    STATUS      current
    DESCRIPTION
        "The value of tmnxWlanGwSoftGreIfL2tpLrnCookie specifies when this
         system will learn the cookie from L2TP tunnels terminating on this
         interface.

         Learning the cookie means that the value of the octets 3-8 of the
         cookie is interpreted as an access point's MAC address, and used as
         such, for example in the Called-Station-Id attribute of RADIUS
         Interim-Update messages.

         The value 'ifMatch' means that the cookie will be interpreted only if
         the value of the first two octets of the cookie is equal to the value
         of the object tmnxWlanGwSoftGreIfL2tpCookie."
    REFERENCE
        "RFC 3931 Layer Two Tunneling Protocol - Version 3 (L2TPv3),
         section 4.1 L2TP Over Specific Packet-Switched Networks (PSNs).

         RFC 2865 Remote Authentication Dial In User Service (RADIUS),
         section 5.30 Called-Station-Id.

         RFC 2866 RADIUS Accounting,
         section 5.1.  Acct-Status-Type."
    DEFVAL      { never }
    ::= { tmnxWlanGwSoftGreIfEntry 38 }

tmnxWlanGwSoftGreIfL2tpCookie    OBJECT-TYPE
    SYNTAX      OCTET STRING (SIZE (2))
    MAX-ACCESS  read-create
    STATUS      current
    DESCRIPTION
        "The value of tmnxWlanGwSoftGreIfL2tpCookie specifies the value to
         match with the first two octets of the L2TP cookie.

         A value other than all zeroes is only accepted while the value of the
         object tmnxWlanGwSoftGreIfL2tpLrnCookie is equal to 'ifMatch'.

         If the first two octets of the cookie match, the system learns the
         value of the remainder of the cookie, in octets 3 until and including
         8."
    DEFVAL      { '0000'H }
    ::= { tmnxWlanGwSoftGreIfEntry 39 }

tmnxWlanGwSoftGreIfMaxLanextBd   OBJECT-TYPE
    SYNTAX      Unsigned32 (0..131071)
    MAX-ACCESS  read-create
    STATUS      current
    DESCRIPTION
        "The value of tmnxWlanGwSoftGreIfMaxLanextBd specifies the maximum
         number of bridge domains for this group-interface."
    DEFVAL      { 0 }
    ::= { tmnxWlanGwSoftGreIfEntry 40 }

tmnxWlanGwSoftGreIfNumSoftGreTu  OBJECT-TYPE
    SYNTAX      Gauge32
    MAX-ACCESS  read-only
    STATUS      current
    DESCRIPTION
        "The value of tmnxWlanGwSoftGreIfNumSoftGreTu indicates the number of
         Soft GRE tunnels terminated on this interface."
    ::= { tmnxWlanGwSoftGreIfEntry 100 }

tmnxWlanGwSoftGreIfLearnApMac    OBJECT-TYPE
    SYNTAX      TmnxEnabledDisabled
    MAX-ACCESS  read-create
    STATUS      current
    DESCRIPTION
        "The value of tmnxWlanGwSoftGreIfLearnApMac enables or disables
         the sending of ARP or ND packets on the wlan-gw GRE tunnel
         upon certain events. The target IP address in the ARP/ND packet
         will be the endpoint IP address of the AP. The ARP/ND response
         from the AP should contain the AP MAC, which subsequently can be
         reported in called-station-id. When enabled, this will be sent
         for following events:
         - CPM: Mobility to an AP for which the AP-MAC is not yet known.
         - CPM: RS-triggered authentication on an AP for which the AP-MAC
                is not yet known
         - ISA: Any mobility event
         - ISA: Any authentication where the AP-MAC is not yet known
               (e.g. from radius proxy cache, DHCP circuit-id, ...).

         If the optional keyword 'delay-authentication' is provided, the
         authentication will be delayed until the ARP/ND is answered or timed
         out, after which the AP-MAC can be included in authentication.

         This configuration is ignored for l2-ap and l2tpv3 access.

         The 'no' form of the command disables this mechanism."
    DEFVAL      { disabled }
    ::= { tmnxWlanGwSoftGreIfEntry 110 }

tmnxWlanGwSoftGreIfLearnApMacDA  OBJECT-TYPE
    SYNTAX      TmnxEnabledDisabled
    MAX-ACCESS  read-create
    STATUS      current
    DESCRIPTION
        "The value of tmnxWlanGwSoftGreIfLearnApMacDA specifies the value of
         the optional parameter 'delay-authentication' for the object
         'tmnxWlanGwSoftGreIfLearnApMac'.

         If 'delay-authentication' is provided, the authentication will be
         delayed until the ARP/ND is answered or timed out, after which the
         AP-MAC can be included in authentication."
    DEFVAL      { disabled }
    ::= { tmnxWlanGwSoftGreIfEntry 111 }

tmnxWlanGwSoftGreIfMobInterVlan  OBJECT-TYPE
    SYNTAX      TmnxEnabledDisabled
    MAX-ACCESS  read-create
    STATUS      current
    DESCRIPTION
        "The value of tmnxWlanGwSoftGreIfMobInterVlan specifies if mobility is
         accepted for User Equipment moving from one VLAN to another within the
         same range of VLAN Q-tags."
    DEFVAL      { disabled }
    ::= { tmnxWlanGwSoftGreIfEntry 112 }

tmnxWlanGwSoftGreIfL2ApAutoSubId OBJECT-TYPE
    SYNTAX      INTEGER {
        include-ap-tags (0),
        sap-only        (1)
    }
    MAX-ACCESS  read-create
    STATUS      current
    DESCRIPTION
        "The value of tmnxWlanGwSoftGreIfL2ApAutoSubId specifies what the
         auto-generated subscriber id should look like if the auto-sub-id-key
         is set to sap-id. It is possible to switch between the SAP and SAP +
         AP delimiting tags."
    DEFVAL      { include-ap-tags }
    ::= { tmnxWlanGwSoftGreIfEntry 113 }

tmnxWlanGwSoftGreTuTable         OBJECT-TYPE
    SYNTAX      SEQUENCE OF TmnxWlanGwSoftGreTuEntry
    MAX-ACCESS  not-accessible
    STATUS      current
    DESCRIPTION
        "The tmnxWlanGwSoftGreTuTable contains information about Soft GRE
         tunnels terminated by this system."
    ::= { tmnxWlanGwSoftGreObjs 2 }

tmnxWlanGwSoftGreTuEntry         OBJECT-TYPE
    SYNTAX      TmnxWlanGwSoftGreTuEntry
    MAX-ACCESS  not-accessible
    STATUS      current
    DESCRIPTION
        "Each conceptual row represents a Soft GRE tunnel.

         Entries in this table are created and destroyed by the system."
    INDEX       {
        vRtrID,
        tmnxWlanGwSoftGreTuRemoteAddrTyp,
        tmnxWlanGwSoftGreTuRemoteAddr,
        tmnxWlanGwSoftGreTuLocalAddrType,
        tmnxWlanGwSoftGreTuLocalAddr
    }
    ::= { tmnxWlanGwSoftGreTuTable 1 }

TmnxWlanGwSoftGreTuEntry         ::= SEQUENCE
{
    tmnxWlanGwSoftGreTuRemoteAddrTyp InetAddressType,
    tmnxWlanGwSoftGreTuRemoteAddr    InetAddress,
    tmnxWlanGwSoftGreTuLocalAddrType InetAddressType,
    tmnxWlanGwSoftGreTuLocalAddr     InetAddress,
    tmnxWlanGwSoftGreTuEstabTime     DateAndTime,
    tmnxWlanGwSoftGreTuIsaGroup      TmnxWlanGwIsaGrpIdOrZero,
    tmnxWlanGwSoftGreTuIsaMember     Unsigned32,
    tmnxWlanGwSoftGreTuNumUe         Gauge32,
    tmnxWlanGwSoftGreTuApMacAddress  MacAddress,
    tmnxWlanGwSoftGreTuApLearnFailed TruthValue,
    tmnxWlanGwSoftGreTuEncap         INTEGER,
    tmnxWlanGwSoftGreTuEncapTag1     QTagFullRangeOrNone,
    tmnxWlanGwSoftGreTuEncapTag2     QTagFullRangeOrNone,
    tmnxWlanGwSoftGreTuService       TmnxServId,
    tmnxWlanGwSoftGreTuInterface     InterfaceIndexOrZero,
    tmnxWlanGwSoftGreTuApSapPortId   TmnxPortID,
    tmnxWlanGwSoftGreTuApSapEncapVal TmnxEncapVal
}

tmnxWlanGwSoftGreTuRemoteAddrTyp OBJECT-TYPE
    SYNTAX      InetAddressType
    MAX-ACCESS  not-accessible
    STATUS      current
    DESCRIPTION
        "The value of tmnxWlanGwSoftGreTuRemoteAddrTyp specifies the address
         type of tmnxWlanGwSoftGreTuRemoteAddr.

         The only values allowed are 'ipv4' and 'ipv6'."
    ::= { tmnxWlanGwSoftGreTuEntry 1 }

tmnxWlanGwSoftGreTuRemoteAddr    OBJECT-TYPE
    SYNTAX      InetAddress (SIZE (4|16))
    MAX-ACCESS  not-accessible
    STATUS      current
    DESCRIPTION
        "The value of the object tmnxWlanGwSoftGreTuRemoteAddr specifies the IP
         address of the remote endpoint of this Soft GRE tunnel, that is the
         source IP address in the tunnel header of received packets."
    ::= { tmnxWlanGwSoftGreTuEntry 2 }

tmnxWlanGwSoftGreTuLocalAddrType OBJECT-TYPE
    SYNTAX      InetAddressType
    MAX-ACCESS  not-accessible
    STATUS      current
    DESCRIPTION
        "The value of tmnxWlanGwSoftGreTuLocalAddrType specifies the address
         type of tmnxWlanGwSoftGreTuLocalAddr.

         The only values allowed are 'ipv4' and 'ipv6'."
    ::= { tmnxWlanGwSoftGreTuEntry 3 }

tmnxWlanGwSoftGreTuLocalAddr     OBJECT-TYPE
    SYNTAX      InetAddress (SIZE (4|16))
    MAX-ACCESS  not-accessible
    STATUS      current
    DESCRIPTION
        "The value of the object tmnxWlanGwSoftGreTuLocalAddr specifies the IP
         address of the local endpoint of this Soft GRE tunnel, that is the
         destination IP address in the tunnel header of received packets.

         The value of this object is equal to the value of the
         tmnxWlanGwSoftGreIfGwAddr object in the conceptual row corresponding
         to the Soft GRE Group-Interface where this tunnel is terminated."
    ::= { tmnxWlanGwSoftGreTuEntry 4 }

tmnxWlanGwSoftGreTuEstabTime     OBJECT-TYPE
    SYNTAX      DateAndTime (SIZE (11))
    MAX-ACCESS  read-only
    STATUS      current
    DESCRIPTION
        "The value of the object tmnxWlanGwSoftGreTuEstabTime indicates the
         value of sysUpTime when this Soft GRE tunnel was established."
    ::= { tmnxWlanGwSoftGreTuEntry 5 }

tmnxWlanGwSoftGreTuIsaGroup      OBJECT-TYPE
    SYNTAX      TmnxWlanGwIsaGrpIdOrZero
    MAX-ACCESS  read-only
    STATUS      current
    DESCRIPTION
        "The value of the object tmnxWlanGwSoftGreTuIsaGroup indicates the
         identifier of the WLAN Gateway ISA group that processes this Soft GRE
         tunnel.

         The value of this object is equal to the value of the object
         tmnxWlanGwGrpId in the conceptual row that corresponds to the WLAN
         Gateway ISA group."
    ::= { tmnxWlanGwSoftGreTuEntry 6 }

tmnxWlanGwSoftGreTuIsaMember     OBJECT-TYPE
    SYNTAX      Unsigned32
    MAX-ACCESS  read-only
    STATUS      current
    DESCRIPTION
        "The value of the object tmnxWlanGwSoftGreTuIsaMember indicates the
         identifier of the ISA Group member that processes this Soft GRE
         tunnel.

         The value of this object is equal to the value of the object
         tmnxWlanGwIsaMemberId in the conceptual row in the
         tmnxWlanGwIsaMemberTable that corresponds to this ISA Group member."
    ::= { tmnxWlanGwSoftGreTuEntry 7 }

tmnxWlanGwSoftGreTuNumUe         OBJECT-TYPE
    SYNTAX      Gauge32
    MAX-ACCESS  read-only
    STATUS      current
    DESCRIPTION
        "The value of the object tmnxWlanGwSoftGreTuNumUe indicates the number
         of User Equipment's connected to this system through this Soft GRE
         tunnel."
    ::= { tmnxWlanGwSoftGreTuEntry 8 }

tmnxWlanGwSoftGreTuApMacAddress  OBJECT-TYPE
    SYNTAX      MacAddress
    MAX-ACCESS  read-only
    STATUS      current
    DESCRIPTION
        "The value of the object tmnxWlanGwSoftGreTuApMacAddress indicates the
         MAC address of the Access Point, as learned by this system.

         The value all zeroes indicates that the Access Point MAC is not known,
         either because there was no attempt to learn it, or because an attempt
         failed."
    ::= { tmnxWlanGwSoftGreTuEntry 10 }

tmnxWlanGwSoftGreTuApLearnFailed OBJECT-TYPE
    SYNTAX      TruthValue
    MAX-ACCESS  read-only
    STATUS      current
    DESCRIPTION
        "The value of the object tmnxWlanGwSoftGreTuApLearnFailed indicates if
         the learning of the MAC address of the Access Point failed.

         When the value of tmnxWlanGwSoftGreTuApLearnFailed is equal to 'true',
         the value of tmnxWlanGwSoftGreTuApMacAddress is equal to all zeroes."
    ::= { tmnxWlanGwSoftGreTuEntry 11 }

tmnxWlanGwSoftGreTuEncap         OBJECT-TYPE
    SYNTAX      INTEGER {
        gre   (1),
        l2tp  (2),
        l2    (3),
        vxlan (4)
    }
    MAX-ACCESS  read-only
    STATUS      current
    DESCRIPTION
        "The value of the object tmnxWlanGwSoftGreTuEncap indicates the tunnel
         encapsulation.

         The meaning of the values is
         'gre' : Soft GRE
         'l2tp': Soft L2TPv3
         'l2'  : IEEE 802.1Q or IEEE 802.1ad
         'vxlan': vxlan endpoint

         The value of tmnxWlanGwSoftGreTuEncap is learned from the latest UE
         associated with this tunnel; when a given Access Point changes its
         encapsulation, there may be a transition period where the system
         contexts of some UE of this tunnel already have the new encapsulation,
         while some other UE still seem to have the previous encapsulation."
    ::= { tmnxWlanGwSoftGreTuEntry 12 }

tmnxWlanGwSoftGreTuEncapTag1     OBJECT-TYPE
    SYNTAX      QTagFullRangeOrNone
    MAX-ACCESS  read-only
    STATUS      current
    DESCRIPTION
        "The value of the object tmnxWlanGwSoftGreTuEncapTag1 indicates the
         VLAN tag in case of IEEE 802.1Q encapsulation, or the outer tag
         (service tag, ethertype 0x88a8) in case of IEEE 802.1ad encapsulation.

         If the value of tmnxWlanGwSoftGreTuEncap is not equal to 'vlan', the
         value of tmnxWlanGwSoftGreTuEncapTag1 is minus one."
    ::= { tmnxWlanGwSoftGreTuEntry 13 }

tmnxWlanGwSoftGreTuEncapTag2     OBJECT-TYPE
    SYNTAX      QTagFullRangeOrNone
    MAX-ACCESS  read-only
    STATUS      current
    DESCRIPTION
        "The value of the object tmnxWlanGwSoftGreTuEncapTag2 indicates the
         inner tag (customer tag, ethertype 0x8100) in case of qinq
         encapsulation.

         If the value of tmnxWlanGwSoftGreTuEncap is not equal to 'vlan', the
         value of tmnxWlanGwSoftGreTuEncapTag2 is minus one."
    ::= { tmnxWlanGwSoftGreTuEntry 14 }

tmnxWlanGwSoftGreTuService       OBJECT-TYPE
    SYNTAX      TmnxServId
    MAX-ACCESS  read-only
    STATUS      current
    DESCRIPTION
        "The value of the object tmnxWlanGwSoftGreTuService indicates the
         identifier of the service of the interface associated with this
         tunnel."
    ::= { tmnxWlanGwSoftGreTuEntry 15 }

tmnxWlanGwSoftGreTuInterface     OBJECT-TYPE
    SYNTAX      InterfaceIndexOrZero
    MAX-ACCESS  read-only
    STATUS      current
    DESCRIPTION
        "The value of the object tmnxWlanGwSoftGreTuInterface indicates the
         identifier of the interface associated with this tunnel.

         Together with tmnxWlanGwSoftGreTuService, it identifies a row in the
         tmnxWlanGwSoftGreIfTable."
    ::= { tmnxWlanGwSoftGreTuEntry 16 }

tmnxWlanGwSoftGreTuApSapPortId   OBJECT-TYPE
    SYNTAX      TmnxPortID
    MAX-ACCESS  read-only
    STATUS      current
    DESCRIPTION
        "The value of the object tmnxWlanGwSoftGreTuApSapPortId indicates the
         ID of the access port of the Access Point, as learned by this system.

         The value all zeroes indicates that the Access Point SAP is not known,
         either because there was no attempt to learn it, or because an attempt
         failed."
    ::= { tmnxWlanGwSoftGreTuEntry 17 }

tmnxWlanGwSoftGreTuApSapEncapVal OBJECT-TYPE
    SYNTAX      TmnxEncapVal
    MAX-ACCESS  read-only
    STATUS      current
    DESCRIPTION
        "The value of the object tmnxWlanGwSoftGreTuApSapEncapVal indicates the
         value of the label used to identify the SAP of the Access Point, as
         learned by this system.

         The value all zeroes indicates that the Access Point SAP is not known,
         either because there was no attempt to learn it, or because an attempt
         failed."
    ::= { tmnxWlanGwSoftGreTuEntry 18 }

tmnxWlanGwTuQosTable             OBJECT-TYPE
    SYNTAX      SEQUENCE OF TmnxWlanGwTuQosEntry
    MAX-ACCESS  not-accessible
    STATUS      current
    DESCRIPTION
        "The tmnxWlanGwTuQosTable contains information about Soft GRE tunnels'
         Quality of Service (QoS) infrastructure.

         The QoS infrastructure of a Soft GRE tunnel consists of one or
         multiple Egress Encapsulation Groups."
    ::= { tmnxWlanGwSoftGreObjs 3 }

tmnxWlanGwTuQosEntry             OBJECT-TYPE
    SYNTAX      TmnxWlanGwTuQosEntry
    MAX-ACCESS  not-accessible
    STATUS      current
    DESCRIPTION
        "Each conceptual row represents information about a WLAN Gateway
         tunnel-QoS-infrastructure.

         Entries in this table are created and destroyed by the system."
    INDEX       {
        vRtrID,
        tmnxWlanGwSoftGreTuRemoteAddrTyp,
        tmnxWlanGwSoftGreTuRemoteAddr,
        tmnxWlanGwSoftGreTuLocalAddrType,
        tmnxWlanGwSoftGreTuLocalAddr,
        tmnxWlanGwTuQosRetailService
    }
    ::= { tmnxWlanGwTuQosTable 1 }

TmnxWlanGwTuQosEntry             ::= SEQUENCE
{
    tmnxWlanGwTuQosRetailService     TmnxServId,
    tmnxWlanGwTuQosEegSvcId          TmnxServId,
    tmnxWlanGwTuQosEegPortId         TmnxPortID,
    tmnxWlanGwTuQosEegEncapValue     TmnxEncapVal,
    tmnxWlanGwTuQosEegName           TNamedItemOrEmpty,
    tmnxWlanGwTuQosEegMember         SvcISID,
    tmnxWlanGwTuQosState             TmnxWlanGwQoSOperState,
    tmnxWlanGwTuQosNumUe             Gauge32,
    tmnxWlanGwTuQosRemainingHoldTime Gauge32
}

tmnxWlanGwTuQosRetailService     OBJECT-TYPE
    SYNTAX      TmnxServId
    MAX-ACCESS  not-accessible
    STATUS      current
    DESCRIPTION
        "The value of the object tmnxWlanGwTuQosRetailService indicates the
         identifier of the retail service.

         The value zero indicates that this tunnel has per-tunnel QoS."
    ::= { tmnxWlanGwTuQosEntry 1 }

tmnxWlanGwTuQosEegSvcId          OBJECT-TYPE
    SYNTAX      TmnxServId
    MAX-ACCESS  read-only
    STATUS      current
    DESCRIPTION
        "The value of the object tmnxWlanGwTuQosEegSvcId indicates the service
         identifier of the B-Component instance of the Egress Encapsulation
         Group member of this tunnel-QoS-infrastructure.

         The value zero indicates that there is no egress encapsulation group
         member."
    ::= { tmnxWlanGwTuQosEntry 2 }

tmnxWlanGwTuQosEegPortId         OBJECT-TYPE
    SYNTAX      TmnxPortID
    MAX-ACCESS  read-only
    STATUS      current
    DESCRIPTION
        "The value of the object tmnxWlanGwTuQosEegPortId indicates the ID of
         the access port in the B-Component instance of the Egress
         Encapsulation Group member of this tunnel-QoS-infrastructure.

         The value zero indicates that there is no egress encapsulation group
         member."
    ::= { tmnxWlanGwTuQosEntry 3 }

tmnxWlanGwTuQosEegEncapValue     OBJECT-TYPE
    SYNTAX      TmnxEncapVal
    MAX-ACCESS  read-only
    STATUS      current
    DESCRIPTION
        "The value of the object tmnxWlanGwTuQosEegEncapValue indicates the
         value of the label used to identify this SAP access port in the
         B-Component instance of the Egress Encapsulation Group member of this
         tunnel-QoS-infrastructure.

         The value zero indicates that there is no egress encapsulation group
         member."
    ::= { tmnxWlanGwTuQosEntry 4 }

tmnxWlanGwTuQosEegName           OBJECT-TYPE
    SYNTAX      TNamedItemOrEmpty
    MAX-ACCESS  read-only
    STATUS      current
    DESCRIPTION
        "The value of the object tmnxWlanGwTuQosEegName indicates the name of
         the Egress Encapsulation Group of this tunnel-QoS-infrastructure.

         An empty string indicates that there is no egress encapsulation group
         member."
    ::= { tmnxWlanGwTuQosEntry 5 }

tmnxWlanGwTuQosEegMember         OBJECT-TYPE
    SYNTAX      SvcISID
    MAX-ACCESS  read-only
    STATUS      current
    DESCRIPTION
        "The value of tmnxWlanGwTuQosEegMember indicates the identifier of the
         Egress Encapsulation Group member of this tunnel-QoS-infrastructure.

         The value minus one indicates that there is no egress encapsulation
         group member."
    ::= { tmnxWlanGwTuQosEntry 6 }

tmnxWlanGwTuQosState             OBJECT-TYPE
    SYNTAX      TmnxWlanGwQoSOperState
    MAX-ACCESS  read-only
    STATUS      current
    DESCRIPTION
        "The value of tmnxWlanGwTuQosState indicates the operational state of
         this tunnel-QoS-infrastructure."
    ::= { tmnxWlanGwTuQosEntry 7 }

tmnxWlanGwTuQosNumUe             OBJECT-TYPE
    SYNTAX      Gauge32
    MAX-ACCESS  read-only
    STATUS      current
    DESCRIPTION
        "The value of the object tmnxWlanGwTuQosNumUe indicates the number of
         User Equipment's using this tunnel-QoS-infrastructure."
    ::= { tmnxWlanGwTuQosEntry 8 }

tmnxWlanGwTuQosRemainingHoldTime OBJECT-TYPE
    SYNTAX      Gauge32
    UNITS       "seconds"
    MAX-ACCESS  read-only
    STATUS      current
    DESCRIPTION
        "The value of the object tmnxWlanGwTuQosRemainingHoldTime indicates the
         time remaining before this tunnel-QoS-infrastructure is released
         because there are no UEs using it.

         The value zero indicates that the hold timer is not running because
         there are still UEs using this tunnel-QoS-infrastructure.

         The value all ones indicates that this tunnel-QoS infrastructure is
         held infinitely."
    ::= { tmnxWlanGwTuQosEntry 9 }

tmnxWlanGwSoftGreTuUeTable       OBJECT-TYPE
    SYNTAX      SEQUENCE OF TmnxWlanGwSoftGreTuUeEntry
    MAX-ACCESS  not-accessible
    STATUS      current
    DESCRIPTION
        "The tmnxWlanGwSoftGreTuUeTable contains the WLAN Gateway User
         Equipment's (UE) connected to this system by means of Soft GRE
         tunnels, ordered by tunnel."
    ::= { tmnxWlanGwSoftGreObjs 4 }

tmnxWlanGwSoftGreTuUeEntry       OBJECT-TYPE
    SYNTAX      TmnxWlanGwSoftGreTuUeEntry
    MAX-ACCESS  not-accessible
    STATUS      current
    DESCRIPTION
        "Each conceptual row represents a WLAN Gateway User Equipment.

         Entries in this table are created and destroyed by the system."
    INDEX       {
        vRtrID,
        tmnxWlanGwSoftGreTuRemoteAddrTyp,
        tmnxWlanGwSoftGreTuRemoteAddr,
        tmnxWlanGwSoftGreTuLocalAddrType,
        tmnxWlanGwSoftGreTuLocalAddr,
        tmnxWlanGwUeMacAddress
    }
    ::= { tmnxWlanGwSoftGreTuUeTable 1 }

TmnxWlanGwSoftGreTuUeEntry       ::= SEQUENCE
{ tmnxWlanGwSoftGreTuUeSsid        TNamedItemOrEmpty }

tmnxWlanGwSoftGreTuUeSsid        OBJECT-TYPE
    SYNTAX      TNamedItemOrEmpty
    MAX-ACCESS  read-only
    STATUS      current
    DESCRIPTION
        "The value of tmnxWlanGwSoftGreTuUeSsid indicates the Service Set ID
         (SSID) of this UE.

         This object refers to a conceptual row in the tmnxWlanGwSsidTable."
    ::= { tmnxWlanGwSoftGreTuUeEntry 1 }

tmnxWlanGwSoftGreXtTable         OBJECT-TYPE
    SYNTAX      SEQUENCE OF TmnxWlanGwSoftGreXtEntry
    MAX-ACCESS  not-accessible
    STATUS      obsolete
    DESCRIPTION
        "The tmnxWlanGwSoftGreXtTable is obsolete.

         Please use the tmnxWlanGwVlanTable instead, with the default VLAN tag
         range [4096-4096], to configure the default properties for the WLAN
         Gateway interface."
    ::= { tmnxWlanGwSoftGreObjs 5 }

tmnxWlanGwSoftGreXtEntry         OBJECT-TYPE
    SYNTAX      TmnxWlanGwSoftGreXtEntry
    MAX-ACCESS  not-accessible
    STATUS      obsolete
    DESCRIPTION
        "The tmnxWlanGwSoftGreXtTable is obsolete.

         Please use the tmnxWlanGwVlanTable instead, with the default VLAN tag
         range [4096-4096], to configure the default properties for the WLAN
         Gateway interface."
    AUGMENTS    { tmnxWlanGwSoftGreIfEntry }
    ::= { tmnxWlanGwSoftGreXtTable 1 }

TmnxWlanGwSoftGreXtEntry         ::= SEQUENCE
{
    tmnxWlanGwSoftGreXtLastCh        TimeStamp,
    tmnxWlanGwSoftGreXtDhcp          TmnxEnabledDisabled,
    tmnxWlanGwSoftGreXtAddrType      InetAddressType,
    tmnxWlanGwSoftGreXtAddr          InetAddress,
    tmnxWlanGwSoftGreXtLeaseTime     Unsigned32,
    tmnxWlanGwSoftGreXtActLeaseTime  Unsigned32,
    tmnxWlanGwSoftGreXtDns1AddrType  InetAddressType,
    tmnxWlanGwSoftGreXtDns1Addr      InetAddress,
    tmnxWlanGwSoftGreXtDns2AddrType  InetAddressType,
    tmnxWlanGwSoftGreXtDns2Addr      InetAddress,
    tmnxWlanGwSoftGreXtNb1AddrType   InetAddressType,
    tmnxWlanGwSoftGreXtNb1Addr       InetAddress,
    tmnxWlanGwSoftGreXtNb2AddrType   InetAddressType,
    tmnxWlanGwSoftGreXtNb2Addr       InetAddress,
    tmnxWlanGwSoftGreXtHttpRdrPlcy   TNamedItemOrEmpty,
    tmnxWlanGwSoftGreXtNatPlcy       TNamedItemOrEmpty
}

tmnxWlanGwSoftGreXtLastCh        OBJECT-TYPE
    SYNTAX      TimeStamp
    MAX-ACCESS  read-only
    STATUS      obsolete
    DESCRIPTION
        "The value of tmnxWlanGwSoftGreXtLastCh indicates the sysUpTime at the
         time of the most recent management-initiated change to this table row."
    ::= { tmnxWlanGwSoftGreXtEntry 1 }

tmnxWlanGwSoftGreXtDhcp          OBJECT-TYPE
    SYNTAX      TmnxEnabledDisabled
    MAX-ACCESS  read-create
    STATUS      obsolete
    DESCRIPTION
        "The value of tmnxWlanGwSoftGreXtDhcp specifies the administrative
         state of the DHCP protocol distributed on the ISA cards for the UE.

         While the value of the object tmnxWlanGwSoftGreXtDhcp is equal to
         'enabled', the distributed DHCP will reply to DHCP Request messages
         coming from UE without a corresponding subscriber known to this
         system."
    DEFVAL      { disabled }
    ::= { tmnxWlanGwSoftGreXtEntry 2 }

tmnxWlanGwSoftGreXtAddrType      OBJECT-TYPE
    SYNTAX      InetAddressType
    MAX-ACCESS  read-create
    STATUS      obsolete
    DESCRIPTION
        "The value of tmnxWlanGwSoftGreXtAddrType specifies the type of address
         stored in tmnxWlanGwSoftGreXtAddr."
    DEFVAL      { unknown }
    ::= { tmnxWlanGwSoftGreXtEntry 3 }

tmnxWlanGwSoftGreXtAddr          OBJECT-TYPE
    SYNTAX      InetAddress (SIZE (0|4|16))
    MAX-ACCESS  read-create
    STATUS      obsolete
    DESCRIPTION
        "The value of tmnxWlanGwSoftGreXtAddr specifies the IP address to be
         given to the User Equipment as 'yiaddr' in DHCP OFFER and DHCP ACK
         messages.

         The same IP address can be given to multiple UE because the user
         traffic is tunneled and this WLAN Gateway is layer-2-aware.

         The virtual router instance corresponding to the service with ID
         'svcId' must have a row in the TIMETRA-NAT-MIB::tmnxNatL2AwAddrTable,
         such that the value of tmnxWlanGwVlanAddr matches that address prefix
         but is not equal to the value of TIMETRA-NAT-MIB::tmnxNatL2AwAddr."
    DEFVAL      { ''H }
    ::= { tmnxWlanGwSoftGreXtEntry 4 }

tmnxWlanGwSoftGreXtLeaseTime     OBJECT-TYPE
    SYNTAX      Unsigned32 (300..3600)
    UNITS       "seconds"
    MAX-ACCESS  read-create
    STATUS      obsolete
    DESCRIPTION
        "The value of tmnxWlanGwSoftGreXtLeaseTime specifies the IP address
         lease time to be given to the User Equipment in DHCP OFFER and DHCP
         ACK messages, before authentication."
    DEFVAL      { 600 }
    ::= { tmnxWlanGwSoftGreXtEntry 5 }

tmnxWlanGwSoftGreXtActLeaseTime  OBJECT-TYPE
    SYNTAX      Unsigned32 (300..3600)
    UNITS       "seconds"
    MAX-ACCESS  read-create
    STATUS      obsolete
    DESCRIPTION
        "The value of tmnxWlanGwSoftGreXtActLeaseTime specifies the IP address
         lease time to be given to the User Equipment in DHCP OFFER and DHCP
         ACK messages, while the UE is active."
    DEFVAL      { 600 }
    ::= { tmnxWlanGwSoftGreXtEntry 6 }

tmnxWlanGwSoftGreXtDns1AddrType  OBJECT-TYPE
    SYNTAX      InetAddressType
    MAX-ACCESS  read-create
    STATUS      obsolete
    DESCRIPTION
        "The value of tmnxWlanGwSoftGreXtDns1AddrType specifies the address
         type of tmnxWlanGwSoftGreXtDns1Addr."
    DEFVAL      { unknown }
    ::= { tmnxWlanGwSoftGreXtEntry 7 }

tmnxWlanGwSoftGreXtDns1Addr      OBJECT-TYPE
    SYNTAX      InetAddress (SIZE (0|4|16))
    MAX-ACCESS  read-create
    STATUS      obsolete
    DESCRIPTION
        "The value of tmnxWlanGwSoftGreXtDns1Addr specifies the address of the
         primary DNS server to be given to the User Equipment in Option 6 of
         DHCP OFFER and DHCP ACK messages."
    REFERENCE
        "RFC 2132 DHCP Options and BOOTP Vendor Extensions,
         section 3.8 Domain Name Server Option."
    DEFVAL      { ''H }
    ::= { tmnxWlanGwSoftGreXtEntry 8 }

tmnxWlanGwSoftGreXtDns2AddrType  OBJECT-TYPE
    SYNTAX      InetAddressType
    MAX-ACCESS  read-create
    STATUS      obsolete
    DESCRIPTION
        "The value of tmnxWlanGwSoftGreXtDns2AddrType specifies the address
         type of tmnxWlanGwSoftGreXtDns2Addr."
    DEFVAL      { unknown }
    ::= { tmnxWlanGwSoftGreXtEntry 9 }

tmnxWlanGwSoftGreXtDns2Addr      OBJECT-TYPE
    SYNTAX      InetAddress (SIZE (0|4|16))
    MAX-ACCESS  read-create
    STATUS      obsolete
    DESCRIPTION
        "The value of tmnxWlanGwSoftGreXtDns2Addr specifies
         the address of the secondary DNS server  to be given to the
         User Equipment in Option 6 of DHCP OFFER and DHCP ACK messages."
    REFERENCE
        "RFC 2132 DHCP Options and BOOTP Vendor Extensions,
         section 3.8 Domain Name Server Option."
    DEFVAL      { ''H }
    ::= { tmnxWlanGwSoftGreXtEntry 10 }

tmnxWlanGwSoftGreXtNb1AddrType   OBJECT-TYPE
    SYNTAX      InetAddressType
    MAX-ACCESS  read-create
    STATUS      obsolete
    DESCRIPTION
        "The value of tmnxWlanGwSoftGreXtNb1AddrType specifies the address type
         of tmnxWlanGwSoftGreXtNb1Addr."
    DEFVAL      { unknown }
    ::= { tmnxWlanGwSoftGreXtEntry 11 }

tmnxWlanGwSoftGreXtNb1Addr       OBJECT-TYPE
    SYNTAX      InetAddress (SIZE (0|4|16))
    MAX-ACCESS  read-create
    STATUS      obsolete
    DESCRIPTION
        "The value of tmnxWlanGwSoftGreXtNb1Addr specifies the address of the
         primary NBNS (Netbios Name Server) server to be given to the User
         Equipment in Option 44 of DHCP OFFER and DHCP ACK messages."
    REFERENCE
        "RFC 2132 DHCP Options and BOOTP Vendor Extensions,
         section 8.5. Net BIOS over TCP/IP Name Server Option."
    DEFVAL      { ''H }
    ::= { tmnxWlanGwSoftGreXtEntry 12 }

tmnxWlanGwSoftGreXtNb2AddrType   OBJECT-TYPE
    SYNTAX      InetAddressType
    MAX-ACCESS  read-create
    STATUS      obsolete
    DESCRIPTION
        "The value of tmnxWlanGwSoftGreXtNb2AddrType specifies the address type
         of tmnxWlanGwSoftGreXtNb2Addr."
    DEFVAL      { unknown }
    ::= { tmnxWlanGwSoftGreXtEntry 13 }

tmnxWlanGwSoftGreXtNb2Addr       OBJECT-TYPE
    SYNTAX      InetAddress (SIZE (0|4|16))
    MAX-ACCESS  read-create
    STATUS      obsolete
    DESCRIPTION
        "The value of tmnxWlanGwSoftGreXtNb2Addr specifies the address of the
         secondary NBNS server to be given to the User Equipment in Option 44
         of DHCP OFFER and DHCP ACK messages."
    REFERENCE
        "RFC 2132 DHCP Options and BOOTP Vendor Extensions,
         section 8.5. Net BIOS over TCP/IP Name Server Option."
    DEFVAL      { ''H }
    ::= { tmnxWlanGwSoftGreXtEntry 14 }

tmnxWlanGwSoftGreXtHttpRdrPlcy   OBJECT-TYPE
    SYNTAX      TNamedItemOrEmpty
    MAX-ACCESS  read-create
    STATUS      obsolete
    DESCRIPTION
        "The value of tmnxWlanGwSoftGreXtHttpRdrPlcy specifies the identifier
         of the HTTP redirect policy for UE.

         HTTP redirect is triggered per subscriber during the authentication
         phase, by the presence of certain vendor- specific attributes in the
         RADIUS Access-Accept message (Alc-Wifi-Portal-Redirect or
         Alc-Wifi-Portal-Url).

         A row with the same name must exist in the
         TIMETRA-SUBSCRIBER-MGMT-MIB::tmnxSubHttpRdrPlcyTable."
    DEFVAL      { "" }
    ::= { tmnxWlanGwSoftGreXtEntry 21 }

tmnxWlanGwSoftGreXtNatPlcy       OBJECT-TYPE
    SYNTAX      TNamedItemOrEmpty
    MAX-ACCESS  read-create
    STATUS      obsolete
    DESCRIPTION
        "The value of tmnxWlanGwSoftGreXtNatPlcy specifies the identifier of
         the NAT policy for UE.

         Layer-2-Aware NAT hosts are temporarily created if UE are
         authenticated by a web portal.

         A row with the same name must exist in the
         TIMETRA-NAT-MIB::tmnxNatPlcyTable."
    DEFVAL      { "" }
    ::= { tmnxWlanGwSoftGreXtEntry 22 }

tmnxWlanGwVlanTable              OBJECT-TYPE
    SYNTAX      SEQUENCE OF TmnxWlanGwVlanEntry
    MAX-ACCESS  not-accessible
    STATUS      current
    DESCRIPTION
        "The tmnxWlanGwVlanTable contains objects to configure WLAN Gateway
         behavior for Soft GRE Group-Interfaces and for ranges of IEEE 802.1q
         VLAN tags in Soft GRE Group-Interfaces."
    ::= { tmnxWlanGwSoftGreObjs 6 }

tmnxWlanGwVlanEntry              OBJECT-TYPE
    SYNTAX      TmnxWlanGwVlanEntry
    MAX-ACCESS  not-accessible
    STATUS      current
    DESCRIPTION
        "Each conceptual row represents the set of configuration data for a
         range of VLAN Q-tags on a particular interface.

         Users whose traffic comes in on this interface tagged with a matching
         VLAN Q-tag are to be processed according to the configuration
         specified in this conceptual row; otherwise, the default configuration
         specified in the default range [4096-4096] must be used.

         Rows in this table are created and destroyed by means of SNMP
         operations on the tmnxWlanGwVlanRowStatus object.

         A row with the same values for svcId and iesIfIndex must exist in the
         tmnxWlanGwSoftGreIfTable.

         A single row in this table is always created by the system and cannot
         be destroyed: the default range [4096-4096]."
    INDEX       {
        svcId,
        iesIfIndex,
        tmnxWlanGwVlanTagStart,
        tmnxWlanGwVlanTagEnd
    }
    ::= { tmnxWlanGwVlanTable 1 }

TmnxWlanGwVlanEntry              ::= SEQUENCE
{
    tmnxWlanGwVlanTagStart           Unsigned32,
    tmnxWlanGwVlanTagEnd             Unsigned32,
    tmnxWlanGwVlanRowStatus          RowStatus,
    tmnxWlanGwVlanLastCh             TimeStamp,
    tmnxWlanGwVlanRetailService      TmnxServId,
    tmnxWlanGwVlanDhcp               TmnxEnabledDisabled,
    tmnxWlanGwVlanAddrType           InetAddressType,
    tmnxWlanGwVlanAddr               InetAddress,
    tmnxWlanGwVlanLeaseTime          Unsigned32,
    tmnxWlanGwVlanActLeaseTime       Unsigned32,
    tmnxWlanGwVlanDns1AddrType       InetAddressType,
    tmnxWlanGwVlanDns1Addr           InetAddress,
    tmnxWlanGwVlanDns2AddrType       InetAddressType,
    tmnxWlanGwVlanDns2Addr           InetAddress,
    tmnxWlanGwVlanNb1AddrType        InetAddressType,
    tmnxWlanGwVlanNb1Addr            InetAddress,
    tmnxWlanGwVlanNb2AddrType        InetAddressType,
    tmnxWlanGwVlanNb2Addr            InetAddress,
    tmnxWlanGwVlanHttpRdrPlcy        TNamedItemOrEmpty,
    tmnxWlanGwVlanNatPlcy            TNamedItemOrEmpty,
    tmnxWlanGwVlanDataTrigg          TmnxEnabledDisabled,
    tmnxWlanGwVlanAuthPlcy           TNamedItemOrEmpty,
    tmnxWlanGwVlanAuthHoldTime       Unsigned32,
    tmnxWlanGwVlanRadProxVrtr        TmnxVRtrIDOrZero,
    tmnxWlanGwVlanRadProxSrv         TNamedItemOrEmpty,
    tmnxWlanGwVlanRadProxMacFmt      TmnxMacSpecification,
    tmnxWlanGwVlanAuthOnDhcp         TmnxEnabledDisabled,
    tmnxWlanGwVlanL2Service          TmnxServId,
    tmnxWlanGwVlanL2AdminState       TmnxEnabledDisabled,
    tmnxWlanGwVlanL2Description      TItemDescription,
    tmnxWlanGwVlanIdleTimeoutAction  TmnxWlanGwVlanIdleTimeoutAction,
    tmnxWlanGwVlanAddrFromPool       TruthValue,
    tmnxWlanGwVlanAuthVlanMismatchTo Unsigned32,
    tmnxWlanGwVlanDataTriggArp       TmnxEnabledDisabled,
    tmnxWlanGwVlanLocAuthDefUeState  INTEGER,
    tmnxWlanGwVlanLocAuthCoAPlcy     TNamedItemOrEmpty,
    tmnxWlanGwVlanDynService         TmnxEnabledDisabled
}

tmnxWlanGwVlanTagStart           OBJECT-TYPE
    SYNTAX      Unsigned32 (0..4096)
    MAX-ACCESS  not-accessible
    STATUS      current
    DESCRIPTION
        "The value of the object tmnxWlanGwVlanTagStart specifies the start
         VLAN tag of this range."
    ::= { tmnxWlanGwVlanEntry 1 }

tmnxWlanGwVlanTagEnd             OBJECT-TYPE
    SYNTAX      Unsigned32 (0..4096)
    MAX-ACCESS  not-accessible
    STATUS      current
    DESCRIPTION
        "The value of the object tmnxWlanGwVlanTagEnd specifies the end VLAN
         tag of this range."
    ::= { tmnxWlanGwVlanEntry 2 }

tmnxWlanGwVlanRowStatus          OBJECT-TYPE
    SYNTAX      RowStatus
    MAX-ACCESS  read-create
    STATUS      current
    DESCRIPTION
        "The value of tmnxWlanGwVlanRowStatus specifies the row status of this
         row."
    ::= { tmnxWlanGwVlanEntry 3 }

tmnxWlanGwVlanLastCh             OBJECT-TYPE
    SYNTAX      TimeStamp
    MAX-ACCESS  read-only
    STATUS      current
    DESCRIPTION
        "The value of tmnxWlanGwVlanLastCh indicates the sysUpTime at the time
         of the most recent management-initiated change to this table row."
    ::= { tmnxWlanGwVlanEntry 4 }

tmnxWlanGwVlanRetailService      OBJECT-TYPE
    SYNTAX      TmnxServId
    MAX-ACCESS  read-create
    STATUS      current
    DESCRIPTION
        "The value of tmnxWlanGwVlanRetailService specifies the identifier of
         the retail service associated with this range.

         The value zero means that no retail service is associated with this
         range."
    DEFVAL      { 0 }
    ::= { tmnxWlanGwVlanEntry 5 }

tmnxWlanGwVlanDhcp               OBJECT-TYPE
    SYNTAX      TmnxEnabledDisabled
    MAX-ACCESS  read-create
    STATUS      current
    DESCRIPTION
        "The value of tmnxWlanGwVlanDhcp specifies the administrative state of
         the DHCP protocol distributed on the ISA cards for the matching UE.

         While the value of the object tmnxWlanGwVlanDhcp is equal to
         'enabled', the distributed DHCP will reply to DHCP Request messages
         coming from UE without a corresponding subscriber known to this
         system."
    DEFVAL      { disabled }
    ::= { tmnxWlanGwVlanEntry 6 }

tmnxWlanGwVlanAddrType           OBJECT-TYPE
    SYNTAX      InetAddressType
    MAX-ACCESS  read-create
    STATUS      current
    DESCRIPTION
        "The value of tmnxWlanGwVlanAddrType specifies the type of address
         stored in tmnxWlanGwVlanAddr."
    DEFVAL      { unknown }
    ::= { tmnxWlanGwVlanEntry 7 }

tmnxWlanGwVlanAddr               OBJECT-TYPE
    SYNTAX      InetAddress (SIZE (0|4|16))
    MAX-ACCESS  read-create
    STATUS      current
    DESCRIPTION
        "The value of tmnxWlanGwVlanAddr specifies the IP address to be given
         before authentication to the User Equipment as 'yiaddr' in DHCP OFFER
         and DHCP ACK messages.

         The same IP address can be given to multiple UE because the user
         traffic is tunneled and this WLAN Gateway is layer-2-aware.

         The virtual router instance corresponding to the service with ID
         'svcId' must have a row in the TIMETRA-NAT-MIB::tmnxNatL2AwAddrTable,
         such that the value of tmnxWlanGwVlanAddr matches that address prefix
         but is not equal to the value of TIMETRA-NAT-MIB::tmnxNatL2AwAddr."
    DEFVAL      { ''H }
    ::= { tmnxWlanGwVlanEntry 8 }

tmnxWlanGwVlanLeaseTime          OBJECT-TYPE
    SYNTAX      Unsigned32 (300..3600)
    UNITS       "seconds"
    MAX-ACCESS  read-create
    STATUS      current
    DESCRIPTION
        "The value of tmnxWlanGwVlanLeaseTime specifies the IP address lease
         time to be given before authentication User Equipment in DHCP OFFER
         and DHCP ACK messages."
    DEFVAL      { 600 }
    ::= { tmnxWlanGwVlanEntry 9 }

tmnxWlanGwVlanActLeaseTime       OBJECT-TYPE
    SYNTAX      Unsigned32 (300..3600)
    UNITS       "seconds"
    MAX-ACCESS  read-create
    STATUS      current
    DESCRIPTION
        "The value of tmnxWlanGwVlanActLeaseTime specifies the IP address lease
         time to be given to the User Equipment in DHCP OFFER and DHCP ACK
         messages, while the UE is in active state."
    DEFVAL      { 600 }
    ::= { tmnxWlanGwVlanEntry 10 }

tmnxWlanGwVlanDns1AddrType       OBJECT-TYPE
    SYNTAX      InetAddressType
    MAX-ACCESS  read-create
    STATUS      current
    DESCRIPTION
        "The value of tmnxWlanGwVlanDns1AddrType specifies the address type of
         tmnxWlanGwVlanDns1Addr."
    DEFVAL      { unknown }
    ::= { tmnxWlanGwVlanEntry 11 }

tmnxWlanGwVlanDns1Addr           OBJECT-TYPE
    SYNTAX      InetAddress (SIZE (0|4|16))
    MAX-ACCESS  read-create
    STATUS      current
    DESCRIPTION
        "The value of tmnxWlanGwVlanDns1Addr specifies the address of the
         primary DNS server to be given before authentication to the User
         Equipment in Option 6 of DHCP OFFER and DHCP ACK messages."
    REFERENCE
        "RFC 2132 DHCP Options and BOOTP Vendor Extensions,
         section 3.8 Domain Name Server Option."
    DEFVAL      { ''H }
    ::= { tmnxWlanGwVlanEntry 12 }

tmnxWlanGwVlanDns2AddrType       OBJECT-TYPE
    SYNTAX      InetAddressType
    MAX-ACCESS  read-create
    STATUS      current
    DESCRIPTION
        "The value of tmnxWlanGwVlanDns2AddrType specifies the address type of
         tmnxWlanGwVlanDns2Addr."
    DEFVAL      { unknown }
    ::= { tmnxWlanGwVlanEntry 13 }

tmnxWlanGwVlanDns2Addr           OBJECT-TYPE
    SYNTAX      InetAddress (SIZE (0|4|16))
    MAX-ACCESS  read-create
    STATUS      current
    DESCRIPTION
        "The value of tmnxWlanGwVlanDns2Addr specifies the address of the
         secondary DNS server to be given before authentication to the User
         Equipment in Option 6 of DHCP OFFER and DHCP ACK messages."
    REFERENCE
        "RFC 2132 DHCP Options and BOOTP Vendor Extensions,
         section 3.8 Domain Name Server Option."
    DEFVAL      { ''H }
    ::= { tmnxWlanGwVlanEntry 14 }

tmnxWlanGwVlanNb1AddrType        OBJECT-TYPE
    SYNTAX      InetAddressType
    MAX-ACCESS  read-create
    STATUS      current
    DESCRIPTION
        "The value of tmnxWlanGwVlanNb1AddrType specifies the address type of
         tmnxWlanGwVlanNb1Addr."
    DEFVAL      { unknown }
    ::= { tmnxWlanGwVlanEntry 15 }

tmnxWlanGwVlanNb1Addr            OBJECT-TYPE
    SYNTAX      InetAddress (SIZE (0|4|16))
    MAX-ACCESS  read-create
    STATUS      current
    DESCRIPTION
        "The value of tmnxWlanGwVlanNb1Addr specifies the address of the
         primary NBNS server to be given before authentication to the User
         Equipment in Option 44 of DHCP OFFER and DHCP ACK messages."
    REFERENCE
        "RFC 2132 DHCP Options and BOOTP Vendor Extensions,
         section 8.5. Net BIOS over TCP/IP Name Server Option."
    DEFVAL      { ''H }
    ::= { tmnxWlanGwVlanEntry 16 }

tmnxWlanGwVlanNb2AddrType        OBJECT-TYPE
    SYNTAX      InetAddressType
    MAX-ACCESS  read-create
    STATUS      current
    DESCRIPTION
        "The value of tmnxWlanGwVlanNb2AddrType specifies the address type of
         tmnxWlanGwVlanNb2Addr."
    DEFVAL      { unknown }
    ::= { tmnxWlanGwVlanEntry 17 }

tmnxWlanGwVlanNb2Addr            OBJECT-TYPE
    SYNTAX      InetAddress (SIZE (0|4|16))
    MAX-ACCESS  read-create
    STATUS      current
    DESCRIPTION
        "The value of tmnxWlanGwVlanNb2Addr specifies the address of the
         secondary NBNS server to be given before authentication to the User
         Equipment in Option 44 of DHCP OFFER and DHCP ACK messages."
    REFERENCE
        "RFC 2132 DHCP Options and BOOTP Vendor Extensions,
         section 8.5. Net BIOS over TCP/IP Name Server Option."
    DEFVAL      { ''H }
    ::= { tmnxWlanGwVlanEntry 18 }

tmnxWlanGwVlanHttpRdrPlcy        OBJECT-TYPE
    SYNTAX      TNamedItemOrEmpty
    MAX-ACCESS  read-create
    STATUS      current
    DESCRIPTION
        "The value of tmnxWlanGwVlanHttpRdrPlcy specifies the identifier of the
         HTTP redirect policy for UE before authentication.

         HTTP redirect is triggered per subscriber during the authentication
         phase, by the presence of certain vendor- specific attributes in the
         RADIUS Access-Accept message (Alc-Wifi-Portal-Redirect or
         Alc-Wifi-Portal-Url).

         A row with the same name must exist in the
         TIMETRA-SUBSCRIBER-MGMT-MIB::tmnxSubHttpRdrPlcyTable."
    DEFVAL      { "" }
    ::= { tmnxWlanGwVlanEntry 21 }

tmnxWlanGwVlanNatPlcy            OBJECT-TYPE
    SYNTAX      TNamedItemOrEmpty
    MAX-ACCESS  read-create
    STATUS      current
    DESCRIPTION
        "The value of tmnxWlanGwVlanNatPlcy specifies the identifier of the NAT
         policy for UE before authentication.

         Layer-2-Aware NAT hosts are temporarily created if UE are
         authenticated by a web portal.

         A row with the same name must exist in the
         TIMETRA-NAT-MIB::tmnxNatPolicyTable."
    DEFVAL      { "" }
    ::= { tmnxWlanGwVlanEntry 22 }

tmnxWlanGwVlanDataTrigg          OBJECT-TYPE
    SYNTAX      TmnxEnabledDisabled
    MAX-ACCESS  read-create
    STATUS      current
    DESCRIPTION
        "The value of tmnxWlanGwVlanDataTrigg specifies the administrative
         state of data-triggered authentication for the UE.

         While the value of the object tmnxWlanGwVlanDataTrigg is equal to
         'enabled', the system will start the authentication procedure upon
         receiving Layer 3 messages coming from unknown UE."
    DEFVAL      { disabled }
    ::= { tmnxWlanGwVlanEntry 30 }

tmnxWlanGwVlanAuthPlcy           OBJECT-TYPE
    SYNTAX      TNamedItemOrEmpty
    MAX-ACCESS  read-create
    STATUS      current
    DESCRIPTION
        "The value of tmnxWlanGwVlanAuthPlcy specifies the identifier of the
         authentication policy for UE.

         The authentication procedure is triggered by any Layer 3 packet other
         than a DHCP message.

         An entry with the same name must exist in the
         TIMETRA-RADIUS-MIB::tmnxRadIsaPlcyTable."
    DEFVAL      { "" }
    ::= { tmnxWlanGwVlanEntry 31 }

tmnxWlanGwVlanAuthHoldTime       OBJECT-TYPE
    SYNTAX      Unsigned32 (0..3600)
    UNITS       "seconds"
    MAX-ACCESS  read-create
    STATUS      current
    DESCRIPTION
        "The value of tmnxWlanGwVlanAuthHoldTime specifies the minimum time
         that a User Equipment will be held down after a failed authentication
         attempt.

         The hold time is used to prevent overwhelming the RADIUS servers with
         access request messages."
    DEFVAL      { 5 }
    ::= { tmnxWlanGwVlanEntry 32 }

tmnxWlanGwVlanRadProxVrtr        OBJECT-TYPE
    SYNTAX      TmnxVRtrIDOrZero
    MAX-ACCESS  read-create
    STATUS      current
    DESCRIPTION
        "The value of tmnxWlanGwVlanRadProxVrtr specifies the identifier of the
         virtual router instance of the RADIUS Proxy server.

         The system can learn authentication information about UE that use a
         closed-SSID from the RADIUS Proxy server.

         The value zero specifies that there is no RADIUS Proxy server
         associated with this VLAN range for this purpose.

         Non-zero/non-empty values of tmnxWlanGwVlanRadProxVrtr and
         tmnxWlanGwVlanRadProxSrv must refer to a row in the
         TIMETRA-RADIUS-MIB::tmnxRadProxSrvTable."
    DEFVAL      { 0 }
    ::= { tmnxWlanGwVlanEntry 34 }

tmnxWlanGwVlanRadProxSrv         OBJECT-TYPE
    SYNTAX      TNamedItemOrEmpty
    MAX-ACCESS  read-create
    STATUS      current
    DESCRIPTION
        "The value of tmnxWlanGwVlanRadProxSrv specifies the name of the RADIUS
         Proxy server.

         The system can learn authentication information about UE that use a
         closed-SSID from the RADIUS Proxy server.

         The empty string specifies that there is no RADIUS Proxy server
         associated with this VLAN range for this purpose.

         Non-zero/non-empty values of tmnxWlanGwVlanRadProxVrtr and
         tmnxWlanGwVlanRadProxSrv must refer to a row in the
         TIMETRA-RADIUS-MIB::tmnxRadProxSrvTable."
    DEFVAL      { "" }
    ::= { tmnxWlanGwVlanEntry 35 }

tmnxWlanGwVlanRadProxMacFmt      OBJECT-TYPE
    SYNTAX      TmnxMacSpecification (SIZE (2..7))
    MAX-ACCESS  read-create
    STATUS      current
    DESCRIPTION
        "The value of tmnxWlanGwVlanRadProxMacFmt specifies how a MAC address
         is represented by the RADIUS Proxy server.

         The value of tmnxWlanGwVlanRadProxMacFmt is only relevant while also
         non-zero/non-empty values for tmnxWlanGwVlanRadProxVrtr and
         tmnxWlanGwVlanRadProxSrv are specified.

         Examples:

         'ab:'               00:0c:f1:99:85:b8  Nokia SROS style
         'XY-'               00-0C-F1-99-85-B8  IEEE canonical style
         'mmmm.'             0002.03aa.abff     Cisco style."
    DEFVAL      { "aa:" }
    ::= { tmnxWlanGwVlanEntry 36 }

tmnxWlanGwVlanAuthOnDhcp         OBJECT-TYPE
    SYNTAX      TmnxEnabledDisabled
    MAX-ACCESS  read-create
    STATUS      current
    DESCRIPTION
        "The value of tmnxWlanGwVlanAuthOnDhcp specifies the administrative
         state of DHCP-triggered authentication for the UE.

         While the value of the object tmnxWlanGwVlanAuthOnDhcp is equal to
         'enabled', the system will start the authentication procedure upon
         receiving DHCP messages coming from unknown UE."
    DEFVAL      { disabled }
    ::= { tmnxWlanGwVlanEntry 40 }

tmnxWlanGwVlanL2Service          OBJECT-TYPE
    SYNTAX      TmnxServId
    MAX-ACCESS  read-create
    STATUS      current
    DESCRIPTION
        "The value of tmnxWlanGwVlanL2Service specifies the identifier of the
         layer 2 service associated with this range. All traffic in this vlan
         range will terminate in the associated layer 2 service instead of the
         parent service of this group interface.

         The value zero means that no layer 2 service is associated with this
         range."
    DEFVAL      { 0 }
    ::= { tmnxWlanGwVlanEntry 41 }

tmnxWlanGwVlanL2AdminState       OBJECT-TYPE
    SYNTAX      TmnxEnabledDisabled
    MAX-ACCESS  read-create
    STATUS      current
    DESCRIPTION
        "The value of tmnxWlanGwVlanL2AdminState specifies the administrative
         state of the layer 2 service."
    DEFVAL      { disabled }
    ::= { tmnxWlanGwVlanEntry 42 }

tmnxWlanGwVlanL2Description      OBJECT-TYPE
    SYNTAX      TItemDescription
    MAX-ACCESS  read-create
    STATUS      current
    DESCRIPTION
        "The value of tmnxWlanGwVlanL2Description specifies the user provided
         description of the layer 2 service."
    DEFVAL      { "" }
    ::= { tmnxWlanGwVlanEntry 43 }

tmnxWlanGwVlanIdleTimeoutAction  OBJECT-TYPE
    SYNTAX      TmnxWlanGwVlanIdleTimeoutAction
    MAX-ACCESS  read-create
    STATUS      current
    DESCRIPTION
        "The value of tmnxWlanGwVlanIdleTimeoutAction specifies the action to
         be performed when the idle-timeout timer goes off. Idle-timeout is
         activated by RADIUS and is on by default for SLAAC."
    DEFVAL      { remove }
    ::= { tmnxWlanGwVlanEntry 44 }

tmnxWlanGwVlanAddrFromPool       OBJECT-TYPE
    SYNTAX      TruthValue
    MAX-ACCESS  read-create
    STATUS      current
    DESCRIPTION
        "The value of tmnxWlanGwVlanAddrFromPool specifies when the l2-aware IP
         address should be allocated from a pool. If this parameter is
         specified instead of an IPv4 address, a unique address will be
         allocated for each UE. The pool used is managed by the dhcpv4-nat pool
         manager configured under the same subscriber interface."
    DEFVAL      { false }
    ::= { tmnxWlanGwVlanEntry 45 }

tmnxWlanGwVlanAuthVlanMismatchTo OBJECT-TYPE
    SYNTAX      Unsigned32 (0 | 5..60)
    UNITS       "seconds"
    MAX-ACCESS  read-create
    STATUS      current
    DESCRIPTION
        "The value of tmnxWlanGwVlanAuthVlanMismatchTo specifies the timeout
         for the radius proxy cache if a packet is received with a non-matching
         VLAN tag. The timeout will be the minimum of this value and the
         currently remaining proxy cache timeout value.

         The [no] form of the command disables the behavior. In this case, the
         cache timeout will stay unchanged."
    DEFVAL      { 0 }
    ::= { tmnxWlanGwVlanEntry 46 }

tmnxWlanGwVlanDataTriggArp       OBJECT-TYPE
    SYNTAX      TmnxEnabledDisabled
    MAX-ACCESS  read-create
    STATUS      current
    DESCRIPTION
        "The value of tmnxWlanGwVlanDataTriggArp specifies the value of the
         optional parameter 'arp' for the object 'tmnxWlanGwVlanDataTrigg'.

         If the 'arp' parameter is provided, the system will start the
         authentication procedure upon receiving ARP packets coming from
         unknown UE."
    DEFVAL      { disabled }
    ::= { tmnxWlanGwVlanEntry 47 }

tmnxWlanGwVlanLocAuthDefUeState  OBJECT-TYPE
    SYNTAX      INTEGER {
        none   (0),
        portal (1),
        dsm    (2)
    }
    MAX-ACCESS  read-create
    STATUS      current
    DESCRIPTION
        "The value of tmnxWlanGwVlanLocAuthDefUeState specifies the initial UE
         state in case of local authentication.

         The value 'none' specifies that local authentication is disabled and
         that the policy in tmnxWlanGwVlanAuthPlcy is used for authentication.

         The value 'portal' specifies that UE will be created as
         portal-redirect UE, using the policy in tmnxWlanGwVlanHttpRdrPlcy.

         The value 'dsm' specifies that UE will immediately be created as
         distributed-sub-mgmt UE, using the parameters from the corresponding
         row in the tmnxWlanGwVlanDsmTable."
    DEFVAL      { none }
    ::= { tmnxWlanGwVlanEntry 48 }

tmnxWlanGwVlanLocAuthCoAPlcy     OBJECT-TYPE
    SYNTAX      TNamedItemOrEmpty
    MAX-ACCESS  read-create
    STATUS      current
    DESCRIPTION
        "The value of tmnxWlanGwVlanLocAuthCoAPlcy specifies the ISA RADIUS
         policy to be used for handling Change-of-Authorization or Disconnect
         messages for locally authenticated UE.

         An entry with the same name must exist in the
         TIMETRA-RADIUS-MIB::tmnxRadIsaPlcyTable."
    DEFVAL      { "" }
    ::= { tmnxWlanGwVlanEntry 49 }

tmnxWlanGwVlanDynService         OBJECT-TYPE
    SYNTAX      TmnxEnabledDisabled
    MAX-ACCESS  read-create
    STATUS      current
    DESCRIPTION
        "The value of tmnxWlanGwVlanDynService specifies whether the VLAN range
         supports a combination of both Layer 2 and Layer 3 UE.

         While the value of the object tmnxWlanGwVlanDynService is equal to
         'enabled', either a Layer 2 or Layer 3 UE will be created, depending
         on what is returned in the RADIUS Access-Accept message for the UE.

         While the value of the object tmnxWlanGwVlanDynService is equal to
         'disabled', the VLAN range only exclusively supports Layer 2 (when
         tmnxWlanGwVlanL2AdminState has value 'enabled') or Layer 3 (when
         tmnxWlanGwVlanL2AdminState has value 'disabled') UE."
    DEFVAL      { disabled }
    ::= { tmnxWlanGwVlanEntry 50 }

tmnxWlanGwSubIfTable             OBJECT-TYPE
    SYNTAX      SEQUENCE OF TmnxWlanGwSubIfEntry
    MAX-ACCESS  not-accessible
    STATUS      current
    DESCRIPTION
        "The tmnxWlanGwSubIfTable contains objects to configure WLAN Gateway
         functions for subscriber interfaces.

         These objects are useful only while the subscriber interface has Soft
         GRE Group-Interfaces configured.

         Entries in this table can be created and deleted via SNMP SET
         operations to tmnxWlanGwSubIfRowStatus."
    ::= { tmnxWlanGwSoftGreObjs 7 }

tmnxWlanGwSubIfEntry             OBJECT-TYPE
    SYNTAX      TmnxWlanGwSubIfEntry
    MAX-ACCESS  not-accessible
    STATUS      current
    DESCRIPTION
        "Each conceptual row contains WLAN Gateway information of a specific
         subscriber interface.

         Objects in this row are effective only while this subscriber interface
         has Soft GRE Group-Interfaces configured.

         Entries in this table can be created and deleted via SNMP SET
         operations to tmnxWlanGwSubIfRowStatus.

         A corresponding row in the TIMETRA-SERV-MIB::iesIfTable must exist in
         order to create a row in this table."
    INDEX       {
        svcId,
        iesIfIndex
    }
    ::= { tmnxWlanGwSubIfTable 1 }

TmnxWlanGwSubIfEntry             ::= SEQUENCE
{
    tmnxWlanGwSubIfRowStatus         RowStatus,
    tmnxWlanGwSubIfLastCh            TimeStamp,
    tmnxWlanGwSubIfRedExpPrefixType  InetAddressType,
    tmnxWlanGwSubIfRedExpPrefix      InetAddress,
    tmnxWlanGwSubIfRedExpPrefixLen   InetAddressPrefixLength,
    tmnxWlanGwSubIfRedMonPrefixType  InetAddressType,
    tmnxWlanGwSubIfRedMonPrefix      InetAddress,
    tmnxWlanGwSubIfRedMonPrefixLen   InetAddressPrefixLength,
    tmnxWlanGwSubIfRedAdminState     TmnxEnabledDisabled,
    tmnxWlanGwSubIfRedActive         TruthValue,
    tmnxWlanGwSubIfRedSwitch         TmnxActionType
}

tmnxWlanGwSubIfRowStatus         OBJECT-TYPE
    SYNTAX      RowStatus
    MAX-ACCESS  read-create
    STATUS      current
    DESCRIPTION
        "The value of tmnxWlanGwSubIfRowStatus specifies the row status of this
         row."
    ::= { tmnxWlanGwSubIfEntry 1 }

tmnxWlanGwSubIfLastCh            OBJECT-TYPE
    SYNTAX      TimeStamp
    MAX-ACCESS  read-only
    STATUS      current
    DESCRIPTION
        "The value of tmnxWlanGwSubIfLastCh indicates the sysUpTime at the time
         of the most recent management-initiated change to this table row."
    ::= { tmnxWlanGwSubIfEntry 2 }

tmnxWlanGwSubIfRedExpPrefixType  OBJECT-TYPE
    SYNTAX      InetAddressType
    MAX-ACCESS  read-create
    STATUS      current
    DESCRIPTION
        "The value of tmnxWlanGwSubIfRedExpPrefixType specifies the address
         type of tmnxWlanGwSubIfRedExpPrefix."
    DEFVAL      { unknown }
    ::= { tmnxWlanGwSubIfEntry 3 }

tmnxWlanGwSubIfRedExpPrefix      OBJECT-TYPE
    SYNTAX      InetAddress (SIZE (0|4|16))
    MAX-ACCESS  read-create
    STATUS      current
    DESCRIPTION
        "The value of tmnxWlanGwSubIfRedExpPrefix specifies the IP address of
         the prefix to be exported.

         While the export prefix is configured and the value of the object
         tmnxWlanGwSubIfRedActive is equal to 'true', the system exports this
         prefix in the realm of the virtual router instance associated with
         this service; to the WLAN Gateway redundancy peer, the presence of
         this prefix is an indication that the WLAN Gateway function in this
         virtual router instance is active; hence, the export prefix of this
         system is the monitor prefix of the peer.

         The export prefix must be different from the monitor prefix."
    DEFVAL      { ''H }
    ::= { tmnxWlanGwSubIfEntry 4 }

tmnxWlanGwSubIfRedExpPrefixLen   OBJECT-TYPE
    SYNTAX      InetAddressPrefixLength (0..128)
    MAX-ACCESS  read-create
    STATUS      current
    DESCRIPTION
        "The value of tmnxWlanGwSubIfRedExpPrefixLen specifies the prefix
         length of the prefix to be exported."
    DEFVAL      { 0 }
    ::= { tmnxWlanGwSubIfEntry 5 }

tmnxWlanGwSubIfRedMonPrefixType  OBJECT-TYPE
    SYNTAX      InetAddressType
    MAX-ACCESS  read-create
    STATUS      current
    DESCRIPTION
        "The value of tmnxWlanGwSubIfRedMonPrefixType specifies the address
         type of tmnxWlanGwSubIfRedMonPrefix."
    DEFVAL      { unknown }
    ::= { tmnxWlanGwSubIfEntry 6 }

tmnxWlanGwSubIfRedMonPrefix      OBJECT-TYPE
    SYNTAX      InetAddress (SIZE (0|4|16))
    MAX-ACCESS  read-create
    STATUS      current
    DESCRIPTION
        "The value of tmnxWlanGwSubIfRedMonPrefix specifies the IP address of
         the prefix to be monitored.

         While the monitor prefix is configured, the system monitors the
         presence of this prefix in the routing table of the virtual router
         instance associated with this service; the presence of this prefix is
         an indication that the WLAN Gateway redundancy peer is active; the
         monitor prefix of this system is the export prefix of the peer.

         The monitor prefix must be different from the export prefix."
    DEFVAL      { ''H }
    ::= { tmnxWlanGwSubIfEntry 7 }

tmnxWlanGwSubIfRedMonPrefixLen   OBJECT-TYPE
    SYNTAX      InetAddressPrefixLength (0..128)
    MAX-ACCESS  read-create
    STATUS      current
    DESCRIPTION
        "The value of tmnxWlanGwSubIfRedMonPrefixLen specifies the prefix
         length of the prefix to be monitored."
    DEFVAL      { 0 }
    ::= { tmnxWlanGwSubIfEntry 8 }

tmnxWlanGwSubIfRedAdminState     OBJECT-TYPE
    SYNTAX      TmnxEnabledDisabled
    MAX-ACCESS  read-create
    STATUS      current
    DESCRIPTION
        "The value of tmnxWlanGwSubIfRedAdminState specifies the administrative
         state of dual homing redundancy for this subscriber interface."
    DEFVAL      { disabled }
    ::= { tmnxWlanGwSubIfEntry 9 }

tmnxWlanGwSubIfRedActive         OBJECT-TYPE
    SYNTAX      TruthValue
    MAX-ACCESS  read-only
    STATUS      current
    DESCRIPTION
        "The value of tmnxWlanGwSubIfRedActive indicates if this system is
         actively performing the WLAN Gateway function for this subscriber
         interface."
    ::= { tmnxWlanGwSubIfEntry 10 }

tmnxWlanGwSubIfRedSwitch         OBJECT-TYPE
    SYNTAX      TmnxActionType
    MAX-ACCESS  read-create
    STATUS      current
    DESCRIPTION
        "Setting this object to 'doAction' triggers an attempt to switch WLAN
         Gateway service to the standby system for the UE associated with this
         subscriber interface.

         This is only allowed while the value of tmnxWlanGwSubIfRedActive is
         equal to 'true'.

         An SNMP GET request on this object returns 'notApplicable'."
    DEFVAL      { notApplicable }
    ::= { tmnxWlanGwSubIfEntry 11 }

tmnxWlanGwL2ApTable              OBJECT-TYPE
    SYNTAX      SEQUENCE OF TmnxWlanGwL2ApEntry
    MAX-ACCESS  not-accessible
    STATUS      current
    DESCRIPTION
        "The tmnxWlanGwL2ApTable contains objects to configure Layer 2 Access
         Points in WLAN Gateway Group-Interfaces."
    ::= { tmnxWlanGwSoftGreObjs 8 }

tmnxWlanGwL2ApEntry              OBJECT-TYPE
    SYNTAX      TmnxWlanGwL2ApEntry
    MAX-ACCESS  not-accessible
    STATUS      current
    DESCRIPTION
        "Each conceptual row represents the set of configuration data for a
         Layer 2 Access Point on a particular WLAN Gateway Group-Interface.

         Rows in this table are created and destroyed by means of SNMP
         operations on the tmnxWlanGwVlanRowStatus object.

         A row with the same values for svcId and iesIfIndex must exist in the
         tmnxWlanGwSoftGreIfTable.

         While a conceptual row in this table exists, a row with the same
         values for sapPortId and sapEncapValue can not be created in the
         TIMETRA-SAP-MIB::sapBaseInfoTable."
    INDEX       {
        svcId,
        iesIfIndex,
        sapPortId,
        sapEncapValue
    }
    ::= { tmnxWlanGwL2ApTable 1 }

TmnxWlanGwL2ApEntry              ::= SEQUENCE
{
    tmnxWlanGwL2ApRowStatus          RowStatus,
    tmnxWlanGwL2ApLastCh             TimeStamp,
    tmnxWlanGwL2ApAdminState         TmnxEnabledDisabled,
    tmnxWlanGwL2ApEncapType          INTEGER,
    tmnxWlanGwL2ApEpipeSapTemplate   TNamedItemOrEmpty,
    tmnxWlanGwL2ApId                 Unsigned32
}

tmnxWlanGwL2ApRowStatus          OBJECT-TYPE
    SYNTAX      RowStatus
    MAX-ACCESS  read-create
    STATUS      current
    DESCRIPTION
        "The value of tmnxWlanGwL2ApRowStatus specifies the row status of this
         row."
    ::= { tmnxWlanGwL2ApEntry 1 }

tmnxWlanGwL2ApLastCh             OBJECT-TYPE
    SYNTAX      TimeStamp
    MAX-ACCESS  read-only
    STATUS      current
    DESCRIPTION
        "The value of tmnxWlanGwL2ApLastCh indicates the sysUpTime at the time
         of the most recent management-initiated change to this table row."
    ::= { tmnxWlanGwL2ApEntry 2 }

tmnxWlanGwL2ApAdminState         OBJECT-TYPE
    SYNTAX      TmnxEnabledDisabled
    MAX-ACCESS  read-create
    STATUS      current
    DESCRIPTION
        "The value of tmnxWlanGwL2ApAdminState specifies the administrative
         status of this row.

         While the value of tmnxWlanGwL2ApAdminState is equal to 'enabled', a
         row with the same values for sapPortId and sapEncapValue is present in
         the TIMETRA-SAP-MIB::sapBaseInfoTable."
    DEFVAL      { disabled }
    ::= { tmnxWlanGwL2ApEntry 3 }

tmnxWlanGwL2ApEncapType          OBJECT-TYPE
    SYNTAX      INTEGER {
        default (0),
        null    (1),
        dot1q   (2),
        qinq    (10)
    }
    MAX-ACCESS  read-create
    STATUS      current
    DESCRIPTION
        "The value of tmnxWlanGwL2ApEncapType specifies the service
         encapsulation type of this access point.

         The value 'default' specifies that the default value for this
         interface be used: tmnxWlanGwSoftGreIfL2ApEncapType."
    DEFVAL      { default }
    ::= { tmnxWlanGwL2ApEntry 4 }

tmnxWlanGwL2ApEpipeSapTemplate   OBJECT-TYPE
    SYNTAX      TNamedItemOrEmpty
    MAX-ACCESS  read-create
    STATUS      current
    DESCRIPTION
        "The value of tmnxWlanGwL2ApEpipeSapTemplate specifies the template to
         configure the parameters of the internal connections with the ISA
         cards.

         A non empty value must correspond to a row in the
         TIMETRA-SERV-MIB::sapTmplTable where the value of the object
         sapTmplType is equal to 'epipe'."
    DEFVAL      { "" }
    ::= { tmnxWlanGwL2ApEntry 5 }

tmnxWlanGwL2ApId                 OBJECT-TYPE
    SYNTAX      Unsigned32
    MAX-ACCESS  read-only
    STATUS      current
    DESCRIPTION
        "The value of tmnxWlanGwL2ApId indicates the unique identifier of this
         conceptual row.

         It may be used as NAS-Port-Id."
    ::= { tmnxWlanGwL2ApEntry 6 }

tmnxWlanGwSubIfPmTable           OBJECT-TYPE
    SYNTAX      SEQUENCE OF TmnxWlanGwSubIfPmEntry
    MAX-ACCESS  not-accessible
    STATUS      current
    DESCRIPTION
        "The tmnxWlanGwSubIfPmTable contains objects to configure the pool
         manager for WLAN GW subscriber interfaces."
    ::= { tmnxWlanGwSoftGreObjs 9 }

tmnxWlanGwSubIfPmEntry           OBJECT-TYPE
    SYNTAX      TmnxWlanGwSubIfPmEntry
    MAX-ACCESS  not-accessible
    STATUS      current
    DESCRIPTION
        "Each conceptual row represents the set of pool manager configuration
         data for a WLAN GW subscriber interface."
    AUGMENTS    { tmnxWlanGwSubIfEntry }
    ::= { tmnxWlanGwSubIfPmTable 1 }

TmnxWlanGwSubIfPmEntry           ::= SEQUENCE
{
    tmnxWlanGwSubIfPmLastChanged     TimeStamp,
    tmnxWlanGwSubIfPmWatermarkHigh   Unsigned32,
    tmnxWlanGwSubIfPmWatermarkLow    Unsigned32,
    tmnxWlanGwSubIfPmWlanGwGroup     TmnxWlanGwIsaGrpIdOrZero,
    tmnxWlanGwSubIfPmD6cServer1      InetAddressIPv6,
    tmnxWlanGwSubIfPmD6cServer2      InetAddressIPv6,
    tmnxWlanGwSubIfPmD6cServer3      InetAddressIPv6,
    tmnxWlanGwSubIfPmD6cServer4      InetAddressIPv6,
    tmnxWlanGwSubIfPmD6cServer5      InetAddressIPv6,
    tmnxWlanGwSubIfPmD6cServer6      InetAddressIPv6,
    tmnxWlanGwSubIfPmD6cServer7      InetAddressIPv6,
    tmnxWlanGwSubIfPmD6cServer8      InetAddressIPv6,
    tmnxWlanGwSubIfPmD6cLeaseQuery   TmnxEnabledDisabled,
    tmnxWlanGwSubIfPmD6cLeaseQueryMR Unsigned32,
    tmnxWlanGwSubIfPmD6cSourceIp     InetAddressIPv6,
    tmnxWlanGwSubIfPmD6cSlaacPoolNm  TNamedItemOrEmpty,
    tmnxWlanGwSubIfPmD6cSlaacLinkAdd InetAddressIPv6,
    tmnxWlanGwSubIfPmD6cSlaacAdminSt TmnxAdminState,
    tmnxWlanGwSubIfPmD6cIaNaPoolNm   TNamedItemOrEmpty,
    tmnxWlanGwSubIfPmD6cIaNaLinkAdd  InetAddressIPv6,
    tmnxWlanGwSubIfPmD6cIaNaAdminSt  TmnxAdminState,
    tmnxWlanGwSubIfPmD6cD4natPoolNm  TNamedItemOrEmpty,
    tmnxWlanGwSubIfPmD6cD4natLinkAdd InetAddressIPv6,
    tmnxWlanGwSubIfPmD6cD4natAdminSt TmnxAdminState
}

tmnxWlanGwSubIfPmLastChanged     OBJECT-TYPE
    SYNTAX      TimeStamp
    MAX-ACCESS  read-only
    STATUS      current
    DESCRIPTION
        "The value of tmnxWlanGwSubIfPmLastChanged indicates the time of the
         most recent management-initiated change."
    ::= { tmnxWlanGwSubIfPmEntry 1 }

tmnxWlanGwSubIfPmWatermarkHigh   OBJECT-TYPE
    SYNTAX      Unsigned32 (51..99)
    MAX-ACCESS  read-create
    STATUS      current
    DESCRIPTION
        "The value of tmnxWlanGwSubIfPmWatermarkHigh specifies the high value
         of the watermarks used to determine if a new prefix should be
         allocated or an old prefix should be removed.

         A new prefix will be allocated when the total usage level for the ISA
         reaches the high watermark.

         A prefix will be freed if no addresses are currently in use and the
         usage level without this prefix would be below the low watermark.

         Values allowed for high watermark are [51..99].

         The 'no' form of the corresponding CLI command resets the watermarks
         to its default values of 95% high and 90% low."
    DEFVAL      { 95 }
    ::= { tmnxWlanGwSubIfPmEntry 2 }

tmnxWlanGwSubIfPmWatermarkLow    OBJECT-TYPE
    SYNTAX      Unsigned32 (50..98)
    MAX-ACCESS  read-create
    STATUS      current
    DESCRIPTION
        "The value of tmnxWlanGwSubIfPmWatermarkLow specifies the low value of
         the watermarks used to determine if a new prefix should be allocated
         or an old prefix should be removed.

         A new prefix will be allocated when the total usage level for the ISA
         reaches the high watermark.

         A prefix will be freed if no addresses are currently in use and the
         usage level without this prefix would be below the low watermark.

         Values allowed for low watermark are [50..98].

         The 'no' form of the corresponding CLI command resets the watermarks
         to its default values of 95% high and 90% low."
    DEFVAL      { 90 }
    ::= { tmnxWlanGwSubIfPmEntry 3 }

tmnxWlanGwSubIfPmWlanGwGroup     OBJECT-TYPE
    SYNTAX      TmnxWlanGwIsaGrpIdOrZero
    MAX-ACCESS  read-create
    STATUS      current
    DESCRIPTION
        "The value of tmnxWlanGwSubIfPmWlanGwGroup specifies the identifier of
         the WLAN Gateway ISA group that terminates GRE for this group
         interface."
    DEFVAL      { 0 }
    ::= { tmnxWlanGwSubIfPmEntry 4 }

tmnxWlanGwSubIfPmD6cServer1      OBJECT-TYPE
    SYNTAX      InetAddressIPv6
    MAX-ACCESS  read-create
    STATUS      current
    DESCRIPTION
        "The value of tmnxWlanGwSubIfPmD6cServer1 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 5 }

tmnxWlanGwSubIfPmD6cServer2      OBJECT-TYPE
    SYNTAX      InetAddressIPv6
    MAX-ACCESS  read-create
    STATUS      current
    DESCRIPTION
        "The value of tmnxWlanGwSubIfPmD6cServer2 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 6 }

tmnxWlanGwSubIfPmD6cServer3      OBJECT-TYPE
    SYNTAX      InetAddressIPv6
    MAX-ACCESS  read-create
    STATUS      current
    DESCRIPTION
        "The value of tmnxWlanGwSubIfPmD6cServer3 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 7 }

tmnxWlanGwSubIfPmD6cServer4      OBJECT-TYPE
    SYNTAX      InetAddressIPv6
    MAX-ACCESS  read-create
    STATUS      current
    DESCRIPTION
        "The value of tmnxWlanGwSubIfPmD6cServer4 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 8 }

tmnxWlanGwSubIfPmD6cServer5      OBJECT-TYPE
    SYNTAX      InetAddressIPv6
    MAX-ACCESS  read-create
    STATUS      current
    DESCRIPTION
        "The value of tmnxWlanGwSubIfPmD6cServer5 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 9 }

tmnxWlanGwSubIfPmD6cServer6      OBJECT-TYPE
    SYNTAX      InetAddressIPv6
    MAX-ACCESS  read-create
    STATUS      current
    DESCRIPTION
        "The value of tmnxWlanGwSubIfPmD6cServer6 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 10 }

tmnxWlanGwSubIfPmD6cServer7      OBJECT-TYPE
    SYNTAX      InetAddressIPv6
    MAX-ACCESS  read-create
    STATUS      current
    DESCRIPTION
        "The value of tmnxWlanGwSubIfPmD6cServer7 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 11 }

tmnxWlanGwSubIfPmD6cServer8      OBJECT-TYPE
    SYNTAX      InetAddressIPv6
    MAX-ACCESS  read-create
    STATUS      current
    DESCRIPTION
        "The value of tmnxWlanGwSubIfPmD6cServer8 specifies one of the
         DHCPv6 servers that are used for requesting addresses.  Up to
         8 servers can be used simultaneously.

         The 'no' form of the corresponding CLI command removes the server.
         This cannot be executed while the DHCPv6 server is not shutdown."
    DEFVAL      { '00000000000000000000000000000000'H }
    ::= { tmnxWlanGwSubIfPmEntry 12 }

tmnxWlanGwSubIfPmD6cLeaseQuery   OBJECT-TYPE
    SYNTAX      TmnxEnabledDisabled
    MAX-ACCESS  read-create
    STATUS      current
    DESCRIPTION
        "The value of tmnxWlanGwSubIfPmD6cLeaseQuery enables or
         disables lease-query.  If it is specified, the DHCPv6 client
         will retrieve any existing addresses when becoming active.
         The lease-query is performed for all of the configured servers.

         The 'no' form of the corresponding CLI command disables lease-query."
    DEFVAL      { disabled }
    ::= { tmnxWlanGwSubIfPmEntry 13 }

tmnxWlanGwSubIfPmD6cLeaseQueryMR OBJECT-TYPE
    SYNTAX      Unsigned32 (0..10)
    MAX-ACCESS  read-create
    STATUS      current
    DESCRIPTION
        "The value of tmnxWlanGwSubIfPmD6cLeaseQueryMR specifies the maximum
         number of retries before the lease query assumes no existing subnets
         were allocated.

         The maximum number of retries is 10 and the default value is 2."
    DEFVAL      { 2 }
    ::= { tmnxWlanGwSubIfPmEntry 14 }

tmnxWlanGwSubIfPmD6cSourceIp     OBJECT-TYPE
    SYNTAX      InetAddressIPv6
    MAX-ACCESS  read-create
    STATUS      current
    DESCRIPTION
        "The value of tmnxWlanGwSubIfPmD6cSourceIp specifies the source IP
         address to be used by the DHCPv6 client.

         The 'no' form of the corresponding CLI command removes the specific
         source IP address. In this case, the DHCPv6 client will fall back to
         the IP address configured on the outgoing interface."
    DEFVAL      { '00000000000000000000000000000000'H }
    ::= { tmnxWlanGwSubIfPmEntry 15 }

tmnxWlanGwSubIfPmD6cSlaacPoolNm  OBJECT-TYPE
    SYNTAX      TNamedItemOrEmpty
    MAX-ACCESS  read-create
    STATUS      current
    DESCRIPTION
        "The value of tmnxWlanGwSubIfPmD6cSlaacPoolNm specifies the pool name
         for SLAAC that should be sent in the DHCPv6 messages. This will be
         reflected in the Nokia vendor specific pool option. (vendor-id 6527,
         option-id 0x02).

         The 'no' form of the corresponding CLI command removes the pool-name
         and the option will not be sent in DHCPv6."
    DEFVAL      { "" }
    ::= { tmnxWlanGwSubIfPmEntry 16 }

tmnxWlanGwSubIfPmD6cSlaacLinkAdd OBJECT-TYPE
    SYNTAX      InetAddressIPv6
    MAX-ACCESS  read-create
    STATUS      current
    DESCRIPTION
        "The value of tmnxWlanGwSubIfPmD6cSlaacLinkAdd specifies the IPv6
         address for SLAAC that should be included in the link-address field of
         the relay header. This can be used for pool-selection by the DHCPv6
         server.

         The 'no' form of the corresponding CLI command sets the link-address
         to its default value '0::0'."
    DEFVAL      { '00000000000000000000000000000000'H }
    ::= { tmnxWlanGwSubIfPmEntry 17 }

tmnxWlanGwSubIfPmD6cSlaacAdminSt OBJECT-TYPE
    SYNTAX      TmnxAdminState
    MAX-ACCESS  read-create
    STATUS      current
    DESCRIPTION
        "The value of tmnxWlanGwSubIfPmD6cSlaacAdminSt specifies the
         administrative state of the considered DHCPv6 client for SLAAC."
    DEFVAL      { outOfService }
    ::= { tmnxWlanGwSubIfPmEntry 18 }

tmnxWlanGwSubIfPmD6cIaNaPoolNm   OBJECT-TYPE
    SYNTAX      TNamedItemOrEmpty
    MAX-ACCESS  read-create
    STATUS      current
    DESCRIPTION
        "The value of tmnxWlanGwSubIfPmD6cIaNaPoolNm specifies the pool name
         for IA-NA that should be sent in the DHCPv6 messages. This will be
         reflected in the Nokia vendor specific pool option. (vendor-id 6527,
         option-id 0x02).

         The 'no' form of of the corresponding CLI command removes pool-name
         and the option will not be sent in DHCPv6."
    DEFVAL      { "" }
    ::= { tmnxWlanGwSubIfPmEntry 19 }

tmnxWlanGwSubIfPmD6cIaNaLinkAdd  OBJECT-TYPE
    SYNTAX      InetAddressIPv6
    MAX-ACCESS  read-create
    STATUS      current
    DESCRIPTION
        "The value of tmnxWlanGwSubIfPmD6cIaNaLinkAdd specifies the IPv6
         address for IA-NA that should be included in the link-address field of
         the relay header. This can be used for pool-selection by the DHCPv6
         server.

         The 'no' form of the corresponding CLI command sets the link-address
         to its default value '0::0'."
    DEFVAL      { '00000000000000000000000000000000'H }
    ::= { tmnxWlanGwSubIfPmEntry 20 }

tmnxWlanGwSubIfPmD6cIaNaAdminSt  OBJECT-TYPE
    SYNTAX      TmnxAdminState
    MAX-ACCESS  read-create
    STATUS      current
    DESCRIPTION
        "The value of tmnxWlanGwSubIfPmD6cIaNaAdminSt specifies the
         administrative state of the considered DHCPv6 client for IA-NA."
    DEFVAL      { outOfService }
    ::= { tmnxWlanGwSubIfPmEntry 21 }

tmnxWlanGwSubIfPmD6cD4natPoolNm  OBJECT-TYPE
    SYNTAX      TNamedItemOrEmpty
    MAX-ACCESS  read-create
    STATUS      current
    DESCRIPTION
        "The value of tmnxWlanGwSubIfPmD6cD4natPoolNm specifies the pool name
         for DHCPv4 NAT that should be sent in the DHCPv6 messages. This will
         be reflected in the Nokia vendor specific pool option. (vendor-id
         6527, option-id 0x02).

         The 'no' form of of the corresponding CLI command removes pool-name
         and the option will not be sent in DHCPv6."
    DEFVAL      { "" }
    ::= { tmnxWlanGwSubIfPmEntry 22 }

tmnxWlanGwSubIfPmD6cD4natLinkAdd OBJECT-TYPE
    SYNTAX      InetAddressIPv6
    MAX-ACCESS  read-create
    STATUS      current
    DESCRIPTION
        "The value of tmnxWlanGwSubIfPmD6cD4natLinkAdd specifies the IPv6
         address for DHCPv4 NAT that should be included in the link-address
         field of the relay header. This can be used for pool-selection by the
         DHCPv6 server.

         The 'no' form of the corresponding CLI command sets the link-address
         to its default value '0::0'."
    DEFVAL      { '00000000000000000000000000000000'H }
    ::= { tmnxWlanGwSubIfPmEntry 23 }

tmnxWlanGwSubIfPmD6cD4natAdminSt OBJECT-TYPE
    SYNTAX      TmnxAdminState
    MAX-ACCESS  read-create
    STATUS      current
    DESCRIPTION
        "The value of tmnxWlanGwSubIfPmD6cD4natAdminSt specifies the
         administrative state of the considered DHCPv6 client for DHCPv4 NAT."
    DEFVAL      { outOfService }
    ::= { tmnxWlanGwSubIfPmEntry 24 }

tmnxWlanGwSubIfIpsTable          OBJECT-TYPE
    SYNTAX      SEQUENCE OF TmnxWlanGwSubIfIpsEntry
    MAX-ACCESS  not-accessible
    STATUS      current
    DESCRIPTION
        "The tmnxWlanGwSubIfIpsTable contains objects giving the states of the
         pools on the ISA."
    ::= { tmnxWlanGwSoftGreObjs 10 }

tmnxWlanGwSubIfIpsEntry          OBJECT-TYPE
    SYNTAX      TmnxWlanGwSubIfIpsEntry
    MAX-ACCESS  not-accessible
    STATUS      current
    DESCRIPTION
        "Each conceptual row represents a set of states of a pool on the ISA."
    INDEX       {
        vRtrID,
        tmnxWlanGwSubIfIpsSubnetAddrType,
        tmnxWlanGwSubIfIpsSubnetAddr,
        tmnxWlanGwSubIfIpsSubnetPrefLen
    }
    ::= { tmnxWlanGwSubIfIpsTable 1 }

TmnxWlanGwSubIfIpsEntry          ::= SEQUENCE
{
    tmnxWlanGwSubIfIpsSubIfIndex     InterfaceIndex,
    tmnxWlanGwSubIfIpsSubnetAddrType InetAddressType,
    tmnxWlanGwSubIfIpsSubnetAddr     InetAddress,
    tmnxWlanGwSubIfIpsSubnetPrefLen  InetAddressPrefixLength,
    tmnxWlanGwSubIfIpsAddrFamily     TmnxWlanGwSubIfIpsAddrFamily,
    tmnxWlanGwSubIfIpsPoolIsOld      TruthValue,
    tmnxWlanGwSubIfIpsUsageLevelPct  Unsigned32,
    tmnxWlanGwSubIfIpsDHCPv6Options  OCTET STRING,
    tmnxWlanGwSubIfIpsRemLeaseTime   Unsigned32,
    tmnxWlanGwSubIfIpsIsaGrpId       TmnxWlanGwIsaGrpIdOrZero,
    tmnxWlanGwSubIfIpsIsaMemberId    Unsigned32,
    tmnxWlanGwSubIfIpsServiceId      TmnxServId,
    tmnxWlanGwSubIfIpsIpv4Addr       InetAddressIPv4,
    tmnxWlanGwSubIfIpsIpv4PrefLen    InetAddressPrefixLength,
    tmnxWlanGwSubIfIpsIpv4DefGwAddr  InetAddressIPv4,
    tmnxWlanGwSubIfIpsDnsServer1     InetAddressIPv6,
    tmnxWlanGwSubIfIpsDnsServer2     InetAddressIPv6
}

tmnxWlanGwSubIfIpsSubIfIndex     OBJECT-TYPE
    SYNTAX      InterfaceIndex
    MAX-ACCESS  read-only
    STATUS      current
    DESCRIPTION
        "The value of tmnxWlanGwSubIfIpsSubIfIndex indicates the index of the
         subscriber interface."
    ::= { tmnxWlanGwSubIfIpsEntry 1 }

tmnxWlanGwSubIfIpsSubnetAddrType OBJECT-TYPE
    SYNTAX      InetAddressType
    MAX-ACCESS  read-only
    STATUS      current
    DESCRIPTION
        "The value of tmnxWlanGwSubIfIpsSubnetAddrType indicates the type of
         the address stored in tmnxWlanGwSubIfIpsSubnetAddr."
    ::= { tmnxWlanGwSubIfIpsEntry 2 }

tmnxWlanGwSubIfIpsSubnetAddr     OBJECT-TYPE
    SYNTAX      InetAddress (SIZE (4|16))
    MAX-ACCESS  read-only
    STATUS      current
    DESCRIPTION
        "The value of tmnxWlanGwSubIfIpsSubnetAddr indicates the subnet address
         of the pool."
    ::= { tmnxWlanGwSubIfIpsEntry 3 }

tmnxWlanGwSubIfIpsSubnetPrefLen  OBJECT-TYPE
    SYNTAX      InetAddressPrefixLength
    MAX-ACCESS  read-only
    STATUS      current
    DESCRIPTION
        "The value of tmnxWlanGwSubIfIpsSubnetPrefLen indicates the prefix
         length of the subnet of the pool."
    ::= { tmnxWlanGwSubIfIpsEntry 4 }

tmnxWlanGwSubIfIpsAddrFamily     OBJECT-TYPE
    SYNTAX      TmnxWlanGwSubIfIpsAddrFamily
    MAX-ACCESS  read-only
    STATUS      current
    DESCRIPTION
        "The value of tmnxWlanGwSubIfIpsAddrFamily indicates the address family
         of the pool as defined in the textual convention
         TmnxWlanGwSubIfIpsAddrFamily."
    ::= { tmnxWlanGwSubIfIpsEntry 5 }

tmnxWlanGwSubIfIpsPoolIsOld      OBJECT-TYPE
    SYNTAX      TruthValue
    MAX-ACCESS  read-only
    STATUS      current
    DESCRIPTION
        "The value of tmnxWlanGwSubIfIpsPoolIsOld is 'true' if the data in the
         pool entry is coming from another ISA. The value is 'false' if the
         pool has been requested for the ISA."
    DEFVAL      { false }
    ::= { tmnxWlanGwSubIfIpsEntry 6 }

tmnxWlanGwSubIfIpsUsageLevelPct  OBJECT-TYPE
    SYNTAX      Unsigned32 (0..100)
    MAX-ACCESS  read-only
    STATUS      current
    DESCRIPTION
        "The value of tmnxWlanGwSubIfIpsUsageLevelPct indicates the percentage
         of addresses in use for the prefix."
    DEFVAL      { 0 }
    ::= { tmnxWlanGwSubIfIpsEntry 7 }

tmnxWlanGwSubIfIpsDHCPv6Options  OBJECT-TYPE
    SYNTAX      OCTET STRING (SIZE (512))
    MAX-ACCESS  read-only
    STATUS      current
    DESCRIPTION
        "The value of tmnxWlanGwSubIfIpsDHCPv6Options indicates the DHCPv6
         options as defined in RFC 3315 section 22."
    ::= { tmnxWlanGwSubIfIpsEntry 8 }

tmnxWlanGwSubIfIpsRemLeaseTime   OBJECT-TYPE
    SYNTAX      Unsigned32
    UNITS       "seconds"
    MAX-ACCESS  read-only
    STATUS      current
    DESCRIPTION
        "The value of tmnxWlanGwSubIfIpsRemLeaseTime indicates the remaining
         lease time of the pool."
    DEFVAL      { 0 }
    ::= { tmnxWlanGwSubIfIpsEntry 9 }

tmnxWlanGwSubIfIpsIsaGrpId       OBJECT-TYPE
    SYNTAX      TmnxWlanGwIsaGrpIdOrZero
    MAX-ACCESS  read-only
    STATUS      current
    DESCRIPTION
        "The value of the object tmnxWlanGwSubIfIpsIsaGrpId indicates the group
         identifier of the ISA for the given prefix."
    ::= { tmnxWlanGwSubIfIpsEntry 10 }

tmnxWlanGwSubIfIpsIsaMemberId    OBJECT-TYPE
    SYNTAX      Unsigned32
    MAX-ACCESS  read-only
    STATUS      current
    DESCRIPTION
        "The value of the object tmnxWlanGwSubIfIpsIsaMemberId indicates the
         member identifier of the ISA for the given prefix."
    ::= { tmnxWlanGwSubIfIpsEntry 11 }

tmnxWlanGwSubIfIpsServiceId      OBJECT-TYPE
    SYNTAX      TmnxServId
    MAX-ACCESS  read-only
    STATUS      current
    DESCRIPTION
        "The value of tmnxWlanGwSubIfIpsServiceId indicates the service
         identifier."
    ::= { tmnxWlanGwSubIfIpsEntry 12 }

tmnxWlanGwSubIfIpsIpv4Addr       OBJECT-TYPE
    SYNTAX      InetAddressIPv4
    MAX-ACCESS  read-only
    STATUS      current
    DESCRIPTION
        "The value of tmnxWlanGwSubIfIpsIpv4Addr indicates the IPv4 subnet
         address of the pool. If the value of tmnxWlanGwSubIfIpsAddrFamily is
         not 'dhcpv4' (2), this object will be an empty address."
    ::= { tmnxWlanGwSubIfIpsEntry 13 }

tmnxWlanGwSubIfIpsIpv4PrefLen    OBJECT-TYPE
    SYNTAX      InetAddressPrefixLength
    MAX-ACCESS  read-only
    STATUS      current
    DESCRIPTION
        "The value of tmnxWlanGwSubIfIpsIpv4PrefLen indicates the prefix length
         of the IPv4 subnet of the pool. If the value of
         tmnxWlanGwSubIfIpsAddrFamily is not 'dhcpv4' (2), this field is set to
         0."
    ::= { tmnxWlanGwSubIfIpsEntry 14 }

tmnxWlanGwSubIfIpsIpv4DefGwAddr  OBJECT-TYPE
    SYNTAX      InetAddressIPv4
    MAX-ACCESS  read-only
    STATUS      current
    DESCRIPTION
        "The value of tmnxWlanGwSubIfIpsIpv4DefGwAddr indicates the default
         gateway of the IPv4 subnet of the pool. If the value of
         tmnxWlanGwSubIfIpsAddrFamily is not 'dhcpv4' (2), this object will be
         an empty address."
    ::= { tmnxWlanGwSubIfIpsEntry 15 }

tmnxWlanGwSubIfIpsDnsServer1     OBJECT-TYPE
    SYNTAX      InetAddressIPv6
    MAX-ACCESS  read-only
    STATUS      current
    DESCRIPTION
        "The value of tmnxWlanGwSubIfIpsDnsServer1 indicates the first DNS
         server IPv6 address provided by the DHCPv6 server."
    ::= { tmnxWlanGwSubIfIpsEntry 16 }

tmnxWlanGwSubIfIpsDnsServer2     OBJECT-TYPE
    SYNTAX      InetAddressIPv6
    MAX-ACCESS  read-only
    STATUS      current
    DESCRIPTION
        "The value of tmnxWlanGwSubIfIpsDnsServer2 indicates the second DNS
         server IPv6 address provided by the DHCPv6 server."
    ::= { tmnxWlanGwSubIfIpsEntry 17 }

tmnxWlanGwTuQosOvrTable          OBJECT-TYPE
    SYNTAX      SEQUENCE OF TmnxWlanGwTuQosOvrEntry
    MAX-ACCESS  not-accessible
    STATUS      current
    DESCRIPTION
        "The tmnxWlanGwTuQosOvrTable contains the override information for the
         Soft GRE tunnels' Quality of Service (QoS) infrastructure.

         The QoS infrastructure of a Soft GRE tunnel consists of one or
         multiple Egress Encapsulation Groups."
    ::= { tmnxWlanGwSoftGreObjs 11 }

tmnxWlanGwTuQosOvrEntry          OBJECT-TYPE
    SYNTAX      TmnxWlanGwTuQosOvrEntry
    MAX-ACCESS  not-accessible
    STATUS      current
    DESCRIPTION
        "Each conceptual row represents information about the overrides for a
         WLAN Gateway tunnel-QoS-infrastructure.

         Entries in this table are created and destroyed by the system."
    INDEX       {
        vRtrID,
        tmnxWlanGwSoftGreTuRemoteAddrTyp,
        tmnxWlanGwSoftGreTuRemoteAddr,
        tmnxWlanGwSoftGreTuLocalAddrType,
        tmnxWlanGwSoftGreTuLocalAddr,
        tmnxWlanGwTuQosRetailService,
        tmnxWlanGwTuQosOvrDirection,
        tmnxWlanGwTuQosOvrType,
        tmnxWlanGwTuQosOvrTypeName
    }
    ::= { tmnxWlanGwTuQosOvrTable 1 }

TmnxWlanGwTuQosOvrEntry          ::= SEQUENCE
{
    tmnxWlanGwTuQosOvrDirection      TDirectionIngEgr,
    tmnxWlanGwTuQosOvrType           TQosOverrideType,
    tmnxWlanGwTuQosOvrTypeName       TNamedItemOrEmpty,
    tmnxWlanGwTuQosOvrPIR            TQosQueuePIRRateOverride,
    tmnxWlanGwTuQosOvrCIR            TQosQueueCIRRateOverride,
    tmnxWlanGwTuQosOvrAggRateLimit   TQosQueuePIRRateOverride
}

tmnxWlanGwTuQosOvrDirection      OBJECT-TYPE
    SYNTAX      TDirectionIngEgr
    MAX-ACCESS  not-accessible
    STATUS      current
    DESCRIPTION
        "The value of tmnxWlanGwTuQosOvrDirection indicates whether this row
         specifies ingress or egress qos override parameters. For tunnel-QoS,
         this will always be 'egress'."
    ::= { tmnxWlanGwTuQosOvrEntry 1 }

tmnxWlanGwTuQosOvrType           OBJECT-TYPE
    SYNTAX      TQosOverrideType
    MAX-ACCESS  not-accessible
    STATUS      current
    DESCRIPTION
        "The value of tmnxWlanGwTuQosOvrType indicates what field has been
         overwritten by this row."
    ::= { tmnxWlanGwTuQosOvrEntry 2 }

tmnxWlanGwTuQosOvrTypeName       OBJECT-TYPE
    SYNTAX      TNamedItemOrEmpty
    MAX-ACCESS  not-accessible
    STATUS      current
    DESCRIPTION
        "The value of tmnxWlanGwTuQosOvrTypeName indicates the name of the
         scheduler that has been overwritten by this row.

         If the value of tmnxWlanGwTuQosOvrType is not 'scheduler' (5), this
         object will be an empty string."
    ::= { tmnxWlanGwTuQosOvrEntry 3 }

tmnxWlanGwTuQosOvrPIR            OBJECT-TYPE
    SYNTAX      TQosQueuePIRRateOverride
    MAX-ACCESS  read-only
    STATUS      current
    DESCRIPTION
        "The value of tmnxWlanGwTuQosOvrPIR indicates the PIR rate in kbps
         allowed for the object overwritten by this row.

         If the value of tmnxWlanGwTuQosOvrType is not 'scheduler' (5), this
         field is set to -2 which indicates 'no override'."
    ::= { tmnxWlanGwTuQosOvrEntry 4 }

tmnxWlanGwTuQosOvrCIR            OBJECT-TYPE
    SYNTAX      TQosQueueCIRRateOverride
    MAX-ACCESS  read-only
    STATUS      current
    DESCRIPTION
        "The value of tmnxWlanGwTuQosOvrCIR indicates the CIR rate in kbps
         allowed for the object overwritten by this row.

         If the value of tmnxWlanGwTuQosOvrType is not 'scheduler' (5), this
         field is set to -2 which indicates 'no override'."
    ::= { tmnxWlanGwTuQosOvrEntry 5 }

tmnxWlanGwTuQosOvrAggRateLimit   OBJECT-TYPE
    SYNTAX      TQosQueuePIRRateOverride
    MAX-ACCESS  read-only
    STATUS      current
    DESCRIPTION
        "The value of tmnxWlanGwTuQosOvrAggRateLimit indicates the egress
         aggregate rate limit override received by RADIUS.

         If the value of tmnxWlanGwTuQosOvrType is not 'aggRateLimit' (3), this
         field is set to -2 which indicates 'no override'."
    ::= { tmnxWlanGwTuQosOvrEntry 6 }

tmnxWlanGwGrpIfGwAddrTable       OBJECT-TYPE
    SYNTAX      SEQUENCE OF TmnxWlanGwGrpIfGwAddrEntry
    MAX-ACCESS  not-accessible
    STATUS      current
    DESCRIPTION
        "The tmnxWlanGwGrpIfGwAddrTable contains information about the tunnel
         IP addresses associated with a WLAN Gateway group interface."
    ::= { tmnxWlanGwSoftGreObjs 12 }

tmnxWlanGwGrpIfGwAddrEntry       OBJECT-TYPE
    SYNTAX      TmnxWlanGwGrpIfGwAddrEntry
    MAX-ACCESS  not-accessible
    STATUS      current
    DESCRIPTION
        "Each conceptual row contains a tunnel IP address associated with a
         WLAN Gateway group interface."
    INDEX       {
        svcId,
        iesIfIndex,
        tmnxWlanGwGrpIfGwAddrType,
        tmnxWlanGwGrpIfGwAddr
    }
    ::= { tmnxWlanGwGrpIfGwAddrTable 1 }

TmnxWlanGwGrpIfGwAddrEntry       ::= SEQUENCE
{
    tmnxWlanGwGrpIfGwAddrType        InetAddressType,
    tmnxWlanGwGrpIfGwAddr            InetAddress,
    tmnxWlanGwGrpIfGwAddrRowStatus   RowStatus,
    tmnxWlanGwGrpIfGwAddrPurpose     BITS
}

tmnxWlanGwGrpIfGwAddrType        OBJECT-TYPE
    SYNTAX      InetAddressType
    MAX-ACCESS  not-accessible
    STATUS      current
    DESCRIPTION
        "The value of tmnxWlanGwGrpIfGwAddrType indicates the address type of
         tmnxWlanGwGrpIfGwAddr.

         The only values allowed are 'ipv4' and 'ipv6'."
    ::= { tmnxWlanGwGrpIfGwAddrEntry 1 }

tmnxWlanGwGrpIfGwAddr            OBJECT-TYPE
    SYNTAX      InetAddress (SIZE (4|16))
    MAX-ACCESS  not-accessible
    STATUS      current
    DESCRIPTION
        "The value of tmnxWlanGwGrpIfGwAddr indicates the tunnel IP address of
         the interface."
    ::= { tmnxWlanGwGrpIfGwAddrEntry 2 }

tmnxWlanGwGrpIfGwAddrRowStatus   OBJECT-TYPE
    SYNTAX      RowStatus
    MAX-ACCESS  read-create
    STATUS      current
    DESCRIPTION
        "The value of tmnxWlanGwGrpIfGwAddrRowStatus specifies the row status
         of this row."
    ::= { tmnxWlanGwGrpIfGwAddrEntry 3 }

tmnxWlanGwGrpIfGwAddrPurpose     OBJECT-TYPE
    SYNTAX      BITS {
        xconnect (0)
    }
    MAX-ACCESS  read-create
    STATUS      current
    DESCRIPTION
        "The value of tmnxWlanGwGrpIfGwAddrPurpose specifies for which purpose
         the tunnel IP address is used.

         The value 'xconnect' specifies that the tunnel IP address is used for
         cross-connect traffic. This option can only be set for IPv6 addresses
         and will be reflected in the Radius attribute
         'Alc-Xconnect-Tunnel-Home-Ipv6'."
    DEFVAL      { {} }
    ::= { tmnxWlanGwGrpIfGwAddrEntry 4 }

tmnxWlanGwIfRetailTable          OBJECT-TYPE
    SYNTAX      SEQUENCE OF TmnxWlanGwIfRetailEntry
    MAX-ACCESS  not-accessible
    STATUS      obsolete
    DESCRIPTION
        "The tmnxWlanGwIfRetailTable contains objects to configure the
         association between IEEE 802.1q VLAN tags and retail services for WLAN
         Gateway interfaces.

         This table is replaced with the tmnxWlanGwVlanTable."
    ::= { tmnxWlanGwObjs 3 }

tmnxWlanGwIfRetailEntry          OBJECT-TYPE
    SYNTAX      TmnxWlanGwIfRetailEntry
    MAX-ACCESS  not-accessible
    STATUS      obsolete
    DESCRIPTION
        "Each conceptual row represents a range of VLAN Q-tags on a particular
         interface, and its association with a Retail Service.

         WLAN Gateway traffic on this interface tagged with a matching VLAN
         Q-tag is to be processed in the specified retailer service, unless a
         RADIUS server provided a retail service for the traffic from this User
         Equipment.

         Rows in this table can be created or deleted via SNMP operations.

         A row with the same values for svcId and iesIfIndex must exist in the
         tmnxWlanGwSoftGreIfTable."
    INDEX       {
        svcId,
        iesIfIndex,
        tmnxWlanGwIfRetailTagStart,
        tmnxWlanGwIfRetailTagEnd
    }
    ::= { tmnxWlanGwIfRetailTable 1 }

TmnxWlanGwIfRetailEntry          ::= SEQUENCE
{
    tmnxWlanGwIfRetailTagStart       QTagFullRange,
    tmnxWlanGwIfRetailTagEnd         QTagFullRange,
    tmnxWlanGwIfRetailRowStatus      RowStatus,
    tmnxWlanGwIfRetailLastCh         TimeStamp,
    tmnxWlanGwIfRetailService        TmnxServId
}

tmnxWlanGwIfRetailTagStart       OBJECT-TYPE
    SYNTAX      QTagFullRange
    MAX-ACCESS  not-accessible
    STATUS      obsolete
    DESCRIPTION
        "The value of the object tmnxWlanGwIfRetailTagStart specifies the start
         VLAN tag of this range."
    ::= { tmnxWlanGwIfRetailEntry 1 }

tmnxWlanGwIfRetailTagEnd         OBJECT-TYPE
    SYNTAX      QTagFullRange
    MAX-ACCESS  not-accessible
    STATUS      obsolete
    DESCRIPTION
        "The value of the object tmnxWlanGwIfRetailTagEnd specifies the end
         VLAN tag of this range."
    ::= { tmnxWlanGwIfRetailEntry 2 }

tmnxWlanGwIfRetailRowStatus      OBJECT-TYPE
    SYNTAX      RowStatus
    MAX-ACCESS  read-create
    STATUS      obsolete
    DESCRIPTION
        "The value of tmnxWlanGwIfRetailRowStatus specifies the row status of
         this row."
    ::= { tmnxWlanGwIfRetailEntry 3 }

tmnxWlanGwIfRetailLastCh         OBJECT-TYPE
    SYNTAX      TimeStamp
    MAX-ACCESS  read-only
    STATUS      obsolete
    DESCRIPTION
        "The value of tmnxWlanGwIfRetailLastCh indicates the sysUpTime at the
         time of the most recent management-initiated change to this table row."
    ::= { tmnxWlanGwIfRetailEntry 4 }

tmnxWlanGwIfRetailService        OBJECT-TYPE
    SYNTAX      TmnxServId
    MAX-ACCESS  read-create
    STATUS      obsolete
    DESCRIPTION
        "The value of tmnxWlanGwIfRetailService specifies the identifier of the
         retail service associated with this range.

         A nonzero value for this object must be specified when a row is
         created."
    ::= { tmnxWlanGwIfRetailEntry 5 }

tmnxWlanGwUeTable                OBJECT-TYPE
    SYNTAX      SEQUENCE OF TmnxWlanGwUeEntry
    MAX-ACCESS  not-accessible
    STATUS      current
    DESCRIPTION
        "The tmnxWlanGwUeTable contains information about WLAN Gateway User
         Equipment's (UE)."
    ::= { tmnxWlanGwObjs 4 }

tmnxWlanGwUeEntry                OBJECT-TYPE
    SYNTAX      TmnxWlanGwUeEntry
    MAX-ACCESS  not-accessible
    STATUS      current
    DESCRIPTION
        "Each conceptual row represents information about a WLAN Gateway User
         Equipment.

         Entries in this table are created and destroyed automatically by the
         system."
    INDEX       { tmnxWlanGwUeMacAddress }
    ::= { tmnxWlanGwUeTable 1 }

TmnxWlanGwUeEntry                ::= SEQUENCE
{
    tmnxWlanGwUeMacAddress           MacAddress,
    tmnxWlanGwUeQTag                 QTagFullRangeOrNone,
    tmnxWlanGwUeMplsLabel            MplsLabel,
    tmnxWlanGwUeTuRouter             TmnxVRtrID,
    tmnxWlanGwUeTuAddrType           InetAddressType,
    tmnxWlanGwUeTuRemoteAddr         InetAddress,
    tmnxWlanGwUeTuLocalAddr          InetAddress,
    tmnxWlanGwUeTuQosRetailService   TmnxServId,
    tmnxWlanGwUeSsid                 TNamedItemOrEmpty,
    tmnxWlanGwUePrevApAddrType       InetAddressType,
    tmnxWlanGwUePrevApAddr           InetAddress,
    tmnxWlanGwUeLastMoveTime         DateAndTime,
    tmnxWlanGwUeImsi                 TmnxMobImsiStr,
    tmnxWlanGwUeService              TmnxServId,
    tmnxWlanGwUeSapPortId            TmnxPortID,
    tmnxWlanGwUeSapPortEncapValue    TmnxEncapVal,
    tmnxWlanGwUeEncapsulation        TmnxWlanGwUeEncapsulation
}

tmnxWlanGwUeMacAddress           OBJECT-TYPE
    SYNTAX      MacAddress
    MAX-ACCESS  not-accessible
    STATUS      current
    DESCRIPTION
        "The value of the object tmnxWlanGwUeMacAddress indicates the MAC
         address of this UE."
    ::= { tmnxWlanGwUeEntry 1 }

tmnxWlanGwUeQTag                 OBJECT-TYPE
    SYNTAX      QTagFullRangeOrNone
    MAX-ACCESS  read-only
    STATUS      current
    DESCRIPTION
        "The value of the object tmnxWlanGwUeQTag indicates the VLAN Q-tag
         present in the traffic received from this UE.

         The value of this object can be used to identify the retailer service,
         by means of the tmnxWlanGwIfRetailTable.

         The value minus one indicates that the traffic received from this UE
         does not have a VLAN Q-tag."
    ::= { tmnxWlanGwUeEntry 3 }

tmnxWlanGwUeMplsLabel            OBJECT-TYPE
    SYNTAX      MplsLabel
    MAX-ACCESS  read-only
    STATUS      current
    DESCRIPTION
        "The value of the object tmnxWlanGwUeMplsLabel indicates the MPLS label
         present in the traffic received from this UE.

         The value zero indicates that the traffic received from this UE does
         not have an MPLS label."
    ::= { tmnxWlanGwUeEntry 4 }

tmnxWlanGwUeTuRouter             OBJECT-TYPE
    SYNTAX      TmnxVRtrID
    MAX-ACCESS  read-only
    STATUS      current
    DESCRIPTION
        "The value of tmnxWlanGwUeTuRouter indicates the identifier of the
         virtual router instance where the tunneled User Equipment traffic is
         routed."
    ::= { tmnxWlanGwUeEntry 5 }

tmnxWlanGwUeTuAddrType           OBJECT-TYPE
    SYNTAX      InetAddressType
    MAX-ACCESS  read-only
    STATUS      current
    DESCRIPTION
        "The value of tmnxWlanGwUeTuAddrType indicates the address type of
         tmnxWlanGwUeTuRemoteAddr and tmnxWlanGwUeTuLocalAddr."
    ::= { tmnxWlanGwUeEntry 6 }

tmnxWlanGwUeTuRemoteAddr         OBJECT-TYPE
    SYNTAX      InetAddress (SIZE (4|16))
    MAX-ACCESS  read-only
    STATUS      current
    DESCRIPTION
        "The value of the object tmnxWlanGwUeTuRemoteAddr indicates the IP
         address of the remote endpoint of this UE's tunnel, that is the source
         IP address in the tunnel header of received packets."
    ::= { tmnxWlanGwUeEntry 7 }

tmnxWlanGwUeTuLocalAddr          OBJECT-TYPE
    SYNTAX      InetAddress (SIZE (4|16))
    MAX-ACCESS  read-only
    STATUS      current
    DESCRIPTION
        "The value of the object tmnxWlanGwUeTuLocalAddr indicates the IP
         address of the local endpoint of this UE's tunnel, that is the
         destination IP address in the tunnel header of received packets."
    ::= { tmnxWlanGwUeEntry 8 }

tmnxWlanGwUeTuQosRetailService   OBJECT-TYPE
    SYNTAX      TmnxServId
    MAX-ACCESS  read-only
    STATUS      current
    DESCRIPTION
        "The value of the object tmnxWlanGwUeTuQosRetailService indicates the
         identifier of the retail service.

         The value zero indicates that this UE's tunnel has per-tunnel QoS."
    ::= { tmnxWlanGwUeEntry 9 }

tmnxWlanGwUeSsid                 OBJECT-TYPE
    SYNTAX      TNamedItemOrEmpty
    MAX-ACCESS  read-only
    STATUS      current
    DESCRIPTION
        "The value of tmnxWlanGwUeSsid indicates the Service Set ID (SSID) of
         this UE.

         This object refers to a conceptual row in the tmnxWlanGwSsidTable."
    ::= { tmnxWlanGwUeEntry 10 }

tmnxWlanGwUePrevApAddrType       OBJECT-TYPE
    SYNTAX      InetAddressType
    MAX-ACCESS  read-only
    STATUS      current
    DESCRIPTION
        "The value of tmnxWlanGwUePrevApAddrType indicates the address type of
         tmnxWlanGwUePrevApAddr."
    ::= { tmnxWlanGwUeEntry 11 }

tmnxWlanGwUePrevApAddr           OBJECT-TYPE
    SYNTAX      InetAddress (SIZE (0|4|16))
    MAX-ACCESS  read-only
    STATUS      current
    DESCRIPTION
        "The value of tmnxWlanGwUePrevApAddr indicates the IP address of the
         previous Access Point (AP) of this UE.

         Note that the address of the current AP of this UE is the value of the
         object tmnxWlanGwUeTuRemoteAddr."
    ::= { tmnxWlanGwUeEntry 12 }

tmnxWlanGwUeLastMoveTime         OBJECT-TYPE
    SYNTAX      DateAndTime (SIZE (11))
    MAX-ACCESS  read-only
    STATUS      current
    DESCRIPTION
        "The value of tmnxWlanGwUeLastMoveTime indicates the time of the most
         recent Access Point move of this UE."
    ::= { tmnxWlanGwUeEntry 13 }

tmnxWlanGwUeImsi                 OBJECT-TYPE
    SYNTAX      TmnxMobImsiStr
    MAX-ACCESS  read-only
    STATUS      current
    DESCRIPTION
        "The value of tmnxWlanGwUeImsi indicates the IMSI (International Mobile
         Subscriber Identity) of this UE."
    ::= { tmnxWlanGwUeEntry 15 }

tmnxWlanGwUeService              OBJECT-TYPE
    SYNTAX      TmnxServId
    MAX-ACCESS  read-only
    STATUS      current
    DESCRIPTION
        "The value of the object tmnxWlanGwUeService indicates the service
         identifier of the (internal) SAP associated with this UE.

         While a subscriber is associated with this UE, that SAP is where its
         subscriber hosts can be found in the
         TIMETRA-SUBSCRIBER-MGMT-MIB::tmnxSubHostInfoV2Table.

         While no subscriber is associated with this UE, the value of
         tmnxWlanGwUeService is equal to zero."
    ::= { tmnxWlanGwUeEntry 16 }

tmnxWlanGwUeSapPortId            OBJECT-TYPE
    SYNTAX      TmnxPortID
    MAX-ACCESS  read-only
    STATUS      current
    DESCRIPTION
        "The value of the object tmnxWlanGwUeSapPortId indicates the port ID of
         the (internal) SAP associated with this UE.

         While no subscriber is associated with this UE, the value of
         tmnxWlanGwUeSapPortId is equal to '1E000000'H, the identifier of the
         'invalid port'."
    ::= { tmnxWlanGwUeEntry 17 }

tmnxWlanGwUeSapPortEncapValue    OBJECT-TYPE
    SYNTAX      TmnxEncapVal
    MAX-ACCESS  read-only
    STATUS      current
    DESCRIPTION
        "The value of the object tmnxWlanGwUeSapPortEncapValue indicates the
         value of the encapsulation of the (internal) SAP associated with this
         UE.

         While no subscriber is associated with this UE, the value of
         tmnxWlanGwUeSapPortEncapValue is equal to zero."
    ::= { tmnxWlanGwUeEntry 18 }

tmnxWlanGwUeEncapsulation        OBJECT-TYPE
    SYNTAX      TmnxWlanGwUeEncapsulation
    MAX-ACCESS  read-only
    STATUS      current
    DESCRIPTION
        "The value of the object tmnxWlanGwUeEncapsulation indicates the
         encapsulation used in this UE's tunnel."
    ::= { tmnxWlanGwUeEntry 19 }

tmnxWlanGwSsidTable              OBJECT-TYPE
    SYNTAX      SEQUENCE OF TmnxWlanGwSsidEntry
    MAX-ACCESS  not-accessible
    STATUS      current
    DESCRIPTION
        "The tmnxWlanGwSsidTable contains information about WLAN Gateway
         Service Set IDs (SSID) learned by this system."
    ::= { tmnxWlanGwObjs 5 }

tmnxWlanGwSsidEntry              OBJECT-TYPE
    SYNTAX      TmnxWlanGwSsidEntry
    MAX-ACCESS  not-accessible
    STATUS      current
    DESCRIPTION
        "Each conceptual row represents information about a specific WLAN
         Gateway Service Set ID (SSID).

         Entries in this table are created and destroyed automatically by the
         system."
    INDEX       { IMPLIED tmnxWlanGwSsid }
    ::= { tmnxWlanGwSsidTable 1 }

TmnxWlanGwSsidEntry              ::= SEQUENCE
{
    tmnxWlanGwSsid                   TNamedItem,
    tmnxWlanGwSsidNumUe              Gauge32
}

tmnxWlanGwSsid                   OBJECT-TYPE
    SYNTAX      TNamedItem
    MAX-ACCESS  not-accessible
    STATUS      current
    DESCRIPTION
        "The value of tmnxWlanGwSsid indicates a Service Set ID (SSID) learned
         by this system."
    ::= { tmnxWlanGwSsidEntry 1 }

tmnxWlanGwSsidNumUe              OBJECT-TYPE
    SYNTAX      Gauge32
    MAX-ACCESS  read-only
    STATUS      current
    DESCRIPTION
        "The value of the object tmnxWlanGwSsidNumUe indicates the number of
         User Equipment's connected to this system using this SSID."
    ::= { tmnxWlanGwSsidEntry 2 }

tmnxWlanGwMgwObjs                OBJECT IDENTIFIER ::= { tmnxWlanGwObjs 6 }

tmnxWlanGwMgwProfTable           OBJECT-TYPE
    SYNTAX      SEQUENCE OF TmnxWlanGwMgwProfEntry
    MAX-ACCESS  not-accessible
    STATUS      current
    DESCRIPTION
        "The tmnxWlanGwMgwProfTable allows configuration of how to communicate
         with a Mobile Gateway.

         A Mobile Gateway can be a Packet Data Network Gateway (PGW) or a
         Gateway GPRS Support Node (GGSN)."
    ::= { tmnxWlanGwMgwObjs 1 }

tmnxWlanGwMgwProfEntry           OBJECT-TYPE
    SYNTAX      TmnxWlanGwMgwProfEntry
    MAX-ACCESS  not-accessible
    STATUS      current
    DESCRIPTION
        "Each entry represents the configuration for a specific Mobile Gateway
         Profile.

         Entries in this table can be created and deleted via SNMP SET
         operations to tmnxWlanGwMgwProfRowStatus."
    INDEX       { IMPLIED tmnxWlanGwMgwProfName }
    ::= { tmnxWlanGwMgwProfTable 1 }

TmnxWlanGwMgwProfEntry           ::= SEQUENCE
{
    tmnxWlanGwMgwProfName            TNamedItem,
    tmnxWlanGwMgwProfRowStatus       RowStatus,
    tmnxWlanGwMgwProfLastChanged     TimeStamp,
    tmnxWlanGwMgwProfDescription     TItemDescription,
    tmnxWlanGwMgwProfMsgReTxTimeout  TmnxMobProfMsgReTxTimeout,
    tmnxWlanGwMgwProfMsgReTxRetryCnt TmnxMobProfMsgReTxRetryCount,
    tmnxWlanGwMgwProfKeepAlvTimeout  TmnxMobProfKeepAliveTimeout,
    tmnxWlanGwMgwProfKeepAlvRetryCnt TmnxMobProfKeepAliveRetryCount,
    tmnxWlanGwMgwProfKeepAlvResp     TmnxMobProfKeepAliveResponse,
    tmnxWlanGwMgwProfTtl             TmnxMobProfIpTtl,
    tmnxWlanGwMgwProfInterfaceType   TmnxWlanGwMgwInterfaceType,
    tmnxWlanGwMgwProfChrgCharHome    TmnxWlanGwChargingCharBits,
    tmnxWlanGwMgwProfChrgCharRoam    TmnxWlanGwChargingCharBits,
    tmnxWlanGwMgwProfSeHoldTime      Integer32,
    tmnxWlanGwMgwProfReportWlanLoc   TmnxEnabledDisabled,
    tmnxWlanGwMgwProfProtocolCfgOpt  INTEGER,
    tmnxWlanGwMgwProfPythonPolicy    TNamedItemOrEmpty,
    tmnxWlanGwMgwProfRatType         Unsigned32,
    tmnxWlanGwMgwProfIpv4Mtu         Unsigned32,
    tmnxWlanGwMgwProfEndMarkerCount  Unsigned32,
    tmnxWlanGwMgwProfChangeRepAction Integer32
}

tmnxWlanGwMgwProfName            OBJECT-TYPE
    SYNTAX      TNamedItem
    MAX-ACCESS  not-accessible
    STATUS      current
    DESCRIPTION
        "The value of tmnxWlanGwMgwProfName specifies the name that identifies
         this profile."
    ::= { tmnxWlanGwMgwProfEntry 1 }

tmnxWlanGwMgwProfRowStatus       OBJECT-TYPE
    SYNTAX      RowStatus
    MAX-ACCESS  read-create
    STATUS      current
    DESCRIPTION
        "The value of tmnxWlanGwMgwProfRowStatus controls the creation and
         deletion of rows in the table."
    ::= { tmnxWlanGwMgwProfEntry 2 }

tmnxWlanGwMgwProfLastChanged     OBJECT-TYPE
    SYNTAX      TimeStamp
    MAX-ACCESS  read-only
    STATUS      current
    DESCRIPTION
        "The value of tmnxWlanGwMgwProfLastChanged indicates the sysUpTime at
         the time of the most recent management-initiated change to this
         profile."
    ::= { tmnxWlanGwMgwProfEntry 3 }

tmnxWlanGwMgwProfDescription     OBJECT-TYPE
    SYNTAX      TItemDescription
    MAX-ACCESS  read-create
    STATUS      current
    DESCRIPTION
        "The value of tmnxWlanGwMgwProfDescription specifies the user provided
         description of this profile."
    DEFVAL      { "" }
    ::= { tmnxWlanGwMgwProfEntry 4 }

tmnxWlanGwMgwProfMsgReTxTimeout  OBJECT-TYPE
    SYNTAX      TmnxMobProfMsgReTxTimeout
    UNITS       "seconds"
    MAX-ACCESS  read-create
    STATUS      current
    DESCRIPTION
        "The value of tmnxWlanGwMgwProfMsgReTxTimeout specifies, in seconds,
         the interval between retransmission of signalling request messages
         towards the same peer Mobile Gateway."
    REFERENCE
        "3GPP TS 29.060,
         section 7.6 Reliable Delivery of Signalling Messages."
    DEFVAL      { 5 }
    ::= { tmnxWlanGwMgwProfEntry 5 }

tmnxWlanGwMgwProfMsgReTxRetryCnt OBJECT-TYPE
    SYNTAX      TmnxMobProfMsgReTxRetryCount
    MAX-ACCESS  read-create
    STATUS      current
    DESCRIPTION
        "The value of tmnxWlanGwMgwProfMsgReTxRetryCnt specifies the number of
         times a signalling request message is transmitted towards the same
         peer."
    REFERENCE
        "3GPP TS 29.060,
         section 7.6 Reliable Delivery of Signalling Messages."
    DEFVAL      { 3 }
    ::= { tmnxWlanGwMgwProfEntry 6 }

tmnxWlanGwMgwProfKeepAlvTimeout  OBJECT-TYPE
    SYNTAX      TmnxMobProfKeepAliveTimeout
    UNITS       "seconds"
    MAX-ACCESS  read-create
    STATUS      current
    DESCRIPTION
        "The value of tmnxWlanGwMgwProfKeepAlvTimeout specifies, in seconds,
         the interval between keep-alive Echo-Request messages towards the same
         peer.

         The value zero specifies that no Echo-Request messages be sent."
    REFERENCE
        "3GPP TS 29.060,
         section 7.2.1 Echo Request."
    DEFVAL      { 60 }
    ::= { tmnxWlanGwMgwProfEntry 7 }

tmnxWlanGwMgwProfKeepAlvRetryCnt OBJECT-TYPE
    SYNTAX      TmnxMobProfKeepAliveRetryCount
    MAX-ACCESS  read-create
    STATUS      current
    DESCRIPTION
        "The value of tmnxWlanGwMgwProfKeepAlvRetryCnt specifies the number of
         Echo-Request messages towards the same peer."
    REFERENCE
        "3GPP TS 29.060,
         section 7.2.1 Echo Request."
    DEFVAL      { 4 }
    ::= { tmnxWlanGwMgwProfEntry 8 }

tmnxWlanGwMgwProfKeepAlvResp     OBJECT-TYPE
    SYNTAX      TmnxMobProfKeepAliveResponse
    UNITS       "seconds"
    MAX-ACCESS  read-create
    STATUS      current
    DESCRIPTION
        "The value of tmnxWlanGwMgwProfKeepAlvResp specifies, in seconds, the
         time between Echo-Request message retries towards the same peer."
    REFERENCE
        "3GPP TS 29.060,
         section 7.2.1 Echo Request."
    DEFVAL      { 5 }
    ::= { tmnxWlanGwMgwProfEntry 9 }

tmnxWlanGwMgwProfTtl             OBJECT-TYPE
    SYNTAX      TmnxMobProfIpTtl
    UNITS       "hops"
    MAX-ACCESS  read-create
    STATUS      current
    DESCRIPTION
        "The value of tmnxWlanGwMgwProfTtl specifies the value to put in the IP
         header's TTL field for GTP (GPRS Tunnel Protocol) control messages."
    DEFVAL      { 255 }
    ::= { tmnxWlanGwMgwProfEntry 10 }

tmnxWlanGwMgwProfInterfaceType   OBJECT-TYPE
    SYNTAX      TmnxWlanGwMgwInterfaceType
    MAX-ACCESS  read-create
    STATUS      current
    DESCRIPTION
        "The value of tmnxWlanGwMgwProfInterfaceType specifies the interface
         type."
    DEFVAL      { s2a }
    ::= { tmnxWlanGwMgwProfEntry 12 }

tmnxWlanGwMgwProfChrgCharHome    OBJECT-TYPE
    SYNTAX      TmnxWlanGwChargingCharBits
    MAX-ACCESS  read-create
    STATUS      current
    DESCRIPTION
        "The value of tmnxWlanGwMgwProfChrgCharHome specifies the bits to set
         in the Charging Characteristics Information Element (IE) for 'home
         UE', if not known by other means such as RADIUS."
    REFERENCE
        "3GPP TS 29.060, section 7.7.23 Charging Characteristics

         3GPP TS 29.061 section 16.4.7.2 Coding 3GPP Vendor-Specific RADIUS attributes,
         13 - 3GPP-Charging-Characteristics"
    DEFVAL      { {} }
    ::= { tmnxWlanGwMgwProfEntry 15 }

tmnxWlanGwMgwProfChrgCharRoam    OBJECT-TYPE
    SYNTAX      TmnxWlanGwChargingCharBits
    MAX-ACCESS  read-create
    STATUS      current
    DESCRIPTION
        "The value of tmnxWlanGwMgwProfChrgCharRoam specifies the bits to set
         in the Charging Characteristics Information Element (IE) for roaming
         UE, if not known by other means such as RADIUS."
    REFERENCE
        "3GPP TS 29.060, section 7.7.23 Charging Characteristics

         3GPP TS 29.061 section 16.4.7.2 Coding 3GPP Vendor-Specific RADIUS attributes,
         13 - 3GPP-Charging-Characteristics"
    DEFVAL      { {} }
    ::= { tmnxWlanGwMgwProfEntry 16 }

tmnxWlanGwMgwProfSeHoldTime      OBJECT-TYPE
    SYNTAX      Integer32 (-1..3600)
    UNITS       "seconds"
    MAX-ACCESS  read-create
    STATUS      current
    DESCRIPTION
        "The value of tmnxWlanGwMgwProfSeHoldTime specifies, in seconds, the
         time that a GTP session context is held after the corresponding User
         Equipment is disconnected.

         If the same User Equipment reconnects to this system before this time
         has elapsed, its GTP session context is reused.

         When the timer expires, the GTP session context is cleared.

         The value minus one specifies that the timer is equal to the User
         Equipment's DHCP remaining lease time.

         The value zero specifies that the GTP session context is cleared
         immediately."
    DEFVAL      { 30 }
    ::= { tmnxWlanGwMgwProfEntry 20 }

tmnxWlanGwMgwProfReportWlanLoc   OBJECT-TYPE
    SYNTAX      TmnxEnabledDisabled
    MAX-ACCESS  read-create
    STATUS      current
    DESCRIPTION
        "The value of tmnxWlanGwMgwProfReportWlanLoc specifies if this system
         reports UE Wifi location in the session create request through the GTP
         interface."
    REFERENCE
        "3GPP S2-124852_was_S2-124665: Location Information for 'SaMOG' user."
    DEFVAL      { disabled }
    ::= { tmnxWlanGwMgwProfEntry 21 }

tmnxWlanGwMgwProfProtocolCfgOpt  OBJECT-TYPE
    SYNTAX      INTEGER {
        pco  (1),
        apco (2)
    }
    MAX-ACCESS  read-create
    STATUS      current
    DESCRIPTION
        "The value of tmnxWlanGwMgwProfProtocolCfgOpt specifies if this system
         uses the Protocol Configuration Options Information Element (IE), or
         the Additional Protocol Configuration Options IE."
    REFERENCE
        "3GPP TS 24.008 Section 10.5.6.3 Protocol configuration options
         3GPP TS 29.275 Section 12.1.1.19 Additional Protocol Configuration Options."
    DEFVAL      { pco }
    ::= { tmnxWlanGwMgwProfEntry 22 }

tmnxWlanGwMgwProfPythonPolicy    OBJECT-TYPE
    SYNTAX      TNamedItemOrEmpty
    MAX-ACCESS  read-create
    STATUS      current
    DESCRIPTION
        "The value of tmnxWlanGwMgwProfPythonPolicy specifies the Python policy
         used to process GTP messages.

         A non empty value must correspond to a row in the
         TIMETRA-PYTHON-MIB::tmnxPythonPolicyTable."
    DEFVAL      { "" }
    ::= { tmnxWlanGwMgwProfEntry 23 }

tmnxWlanGwMgwProfRatType         OBJECT-TYPE
    SYNTAX      Unsigned32 (0..255)
    MAX-ACCESS  read-create
    STATUS      current
    DESCRIPTION
        "The value of tmnxWlanGwMgwProfRatType specifies the default Radio
         Access Type signaled during GTP setup.

         3GPP TS 129 274 Table 8.17-1 defines the values 1-7:
              utran   (1),
              geran   (2),
              wlan    (3),
              gan     (4),
              hspa    (5),
              eutran  (6),
              virtual (7)."
    REFERENCE
        "3GPP TS 3GPP 29.061 section 16.4.7.2 Coding 3GPP Vendor-Specific RADIUS attributes, 21 - 3GPP-RAT-Type

         3GPP TS 129 274, section 8.17 RAT Type"
    DEFVAL      { 3 }
    ::= { tmnxWlanGwMgwProfEntry 24 }

tmnxWlanGwMgwProfIpv4Mtu         OBJECT-TYPE
    SYNTAX      Unsigned32 (512..9000)
    UNITS       "bytes"
    MAX-ACCESS  read-create
    STATUS      current
    DESCRIPTION
        "The value of tmnxWlanGwMgwProfIpv4Mtu specifies the IPv4 MTU  signaled
         in the Protocol Configuration Options (PCO)."
    DEFVAL      { 1400 }
    ::= { tmnxWlanGwMgwProfEntry 25 }

tmnxWlanGwMgwProfEndMarkerCount  OBJECT-TYPE
    SYNTAX      Unsigned32 (0..5)
    UNITS       "packets"
    MAX-ACCESS  read-create
    STATUS      current
    DESCRIPTION
        "The value of tmnxWlanGwMgwProfEndMarkerCount specifies the number of
         times the gtp-u end-marker packet is sent to the previous enode-b upon
         enode-b switchover."
    DEFVAL      { 1 }
    ::= { tmnxWlanGwMgwProfEntry 26 }

tmnxWlanGwMgwProfChangeRepAction OBJECT-TYPE
    SYNTAX      Integer32 (-1 | 0..255)
    MAX-ACCESS  read-create
    STATUS      current
    DESCRIPTION
        "The value of tmnxWlanGwMgwProfChangeRepAction specifies the value of
         the Change Reporting Action IE sent to the peer in applicable
         messages. The peer needs to indicate support first using the
         appropriate flag in the Indication IE.

         This is overridden by Gx, if Gx explicitly requests notification
         changes for either ECGI, TAI or both. If Gx does not request any
         notification changes or only the generic location change, the
         configured value is used.

         3GPP TS 29.274 specifies the following action values:
              Stop Reporting                        (0),
              Start Reporting CGI/SAI               (1),
              Start Reporting RAI                   (2),
              Start Reporting TAI                   (3),
              Start Reporting ECGI                  (4),
              Start Reporting CGI/SAI and RAI       (5),
              Start Reporting TAI and ECGI          (6),
              Start Reporting Macro eNodeB ID
                and Extended Macro eNodeB ID        (7),
              Start Reporting TAI, Macro eNodeB ID
                and Extended Macro eNodeB ID        (8)

         The value -1 indicates the IE is not sent."
    REFERENCE
        "3GPP TS 29.274: GTP-C specification - Section 'Change Reporting Action'"
    DEFVAL      { -1 }
    ::= { tmnxWlanGwMgwProfEntry 27 }

tmnxWlanGwMgwAddrTable           OBJECT-TYPE
    SYNTAX      SEQUENCE OF TmnxWlanGwMgwAddrEntry
    MAX-ACCESS  not-accessible
    STATUS      current
    DESCRIPTION
        "The tmnxWlanGwMgwAddrTable associates Mobile Gateways to Mobile
         Gateway Profiles."
    ::= { tmnxWlanGwMgwObjs 2 }

tmnxWlanGwMgwAddrEntry           OBJECT-TYPE
    SYNTAX      TmnxWlanGwMgwAddrEntry
    MAX-ACCESS  not-accessible
    STATUS      current
    DESCRIPTION
        "Each conceptual row represents a prefix for Mobile Gateway addresses,
         associating them to a particular Mobile Gateway Profile.

         Entries in this table can be created or deleted via SNMP operations.

         A corresponding conceptual row in the tmnxNatVrtrTable must exist
         while creating a row in this table."
    INDEX       {
        vRtrID,
        tmnxWlanGwMgwAddrType,
        tmnxWlanGwMgwAddr,
        tmnxWlanGwMgwAddrPrefixLen
    }
    ::= { tmnxWlanGwMgwAddrTable 1 }

TmnxWlanGwMgwAddrEntry           ::= SEQUENCE
{
    tmnxWlanGwMgwAddrType            InetAddressType,
    tmnxWlanGwMgwAddr                InetAddress,
    tmnxWlanGwMgwAddrPrefixLen       InetAddressPrefixLength,
    tmnxWlanGwMgwAddrRowStatus       RowStatus,
    tmnxWlanGwMgwAddrLastMgmtChange  TimeStamp,
    tmnxWlanGwMgwAddrProfile         TNamedItem
}

tmnxWlanGwMgwAddrType            OBJECT-TYPE
    SYNTAX      InetAddressType
    MAX-ACCESS  not-accessible
    STATUS      current
    DESCRIPTION
        "The value of tmnxWlanGwMgwAddrType specifies the address type of
         tmnxWlanGwMgwAddr.

         The only value supported is 'ipv4'."
    ::= { tmnxWlanGwMgwAddrEntry 1 }

tmnxWlanGwMgwAddr                OBJECT-TYPE
    SYNTAX      InetAddress (SIZE (4|16))
    MAX-ACCESS  not-accessible
    STATUS      current
    DESCRIPTION
        "The value of tmnxWlanGwMgwAddrType specifies the IP address of the
         subnet.

         Only IPv4 addresses are supported."
    ::= { tmnxWlanGwMgwAddrEntry 2 }

tmnxWlanGwMgwAddrPrefixLen       OBJECT-TYPE
    SYNTAX      InetAddressPrefixLength (0..128)
    MAX-ACCESS  not-accessible
    STATUS      current
    DESCRIPTION
        "The value of tmnxWlanGwMgwAddrPrefixLen specifies the prefix length of
         the subnet."
    ::= { tmnxWlanGwMgwAddrEntry 3 }

tmnxWlanGwMgwAddrRowStatus       OBJECT-TYPE
    SYNTAX      RowStatus
    MAX-ACCESS  read-create
    STATUS      current
    DESCRIPTION
        "The value of tmnxWlanGwMgwAddrRowStatus specifies the row status of
         this row."
    ::= { tmnxWlanGwMgwAddrEntry 4 }

tmnxWlanGwMgwAddrLastMgmtChange  OBJECT-TYPE
    SYNTAX      TimeStamp
    MAX-ACCESS  read-only
    STATUS      current
    DESCRIPTION
        "The value of tmnxWlanGwMgwAddrLastMgmtChange indicates the sysUpTime
         at the time of the most recent management-initiated change to this
         table row."
    ::= { tmnxWlanGwMgwAddrEntry 5 }

tmnxWlanGwMgwAddrProfile         OBJECT-TYPE
    SYNTAX      TNamedItem
    MAX-ACCESS  read-create
    STATUS      current
    DESCRIPTION
        "The value of tmnxWlanGwMgwAddrProfile specifies the Mobile Gateway
         profile associated with this address prefix.

         This object refers to a row in the tmnxWlanGwMgwProfTable.

         A value for this object must be provided when the conceptual row is
         created."
    ::= { tmnxWlanGwMgwAddrEntry 6 }

tmnxWlanGwMgwTable               OBJECT-TYPE
    SYNTAX      SEQUENCE OF TmnxWlanGwMgwEntry
    MAX-ACCESS  not-accessible
    STATUS      current
    DESCRIPTION
        "The tmnxWlanGwMgwTable contains information about Mobile Gateways
         connected to this system."
    ::= { tmnxWlanGwMgwObjs 3 }

tmnxWlanGwMgwEntry               OBJECT-TYPE
    SYNTAX      TmnxWlanGwMgwEntry
    MAX-ACCESS  not-accessible
    STATUS      current
    DESCRIPTION
        "Each conceptual row represents information about a particular Mobile
         Gateway connected to this system.

         Rows are created or removed automatically by the system."
    INDEX       {
        vRtrID,
        tmnxWlanGwMgwRemoteAddrType,
        tmnxWlanGwMgwRemoteAddr,
        tmnxWlanGwMgwRemotePort
    }
    ::= { tmnxWlanGwMgwTable 1 }

TmnxWlanGwMgwEntry               ::= SEQUENCE
{
    tmnxWlanGwMgwRemoteAddrType      InetAddressType,
    tmnxWlanGwMgwRemoteAddr          InetAddress,
    tmnxWlanGwMgwRemotePort          InetPortNumber,
    tmnxWlanGwMgwLocalAddrType       InetAddressType,
    tmnxWlanGwMgwLocalAddr           InetAddress,
    tmnxWlanGwMgwTime                DateAndTime,
    tmnxWlanGwMgwProfile             TNamedItemOrEmpty,
    tmnxWlanGwMgwControl             INTEGER,
    tmnxWlanGwMgwRestartCnt          Gauge32,
    tmnxWlanGwMgwState               TmnxMobPathMgmtState,
    tmnxWlanGwMgwInterfaceType       TmnxWlanGwMgwInterfaceType
}

tmnxWlanGwMgwRemoteAddrType      OBJECT-TYPE
    SYNTAX      InetAddressType
    MAX-ACCESS  not-accessible
    STATUS      current
    DESCRIPTION
        "The value of tmnxWlanGwMgwRemoteAddrType indicates the address type of
         tmnxWlanGwMgwRemoteAddr.

         The only values allowed are 'ipv4' and 'ipv6'."
    ::= { tmnxWlanGwMgwEntry 1 }

tmnxWlanGwMgwRemoteAddr          OBJECT-TYPE
    SYNTAX      InetAddress (SIZE (4|16))
    MAX-ACCESS  not-accessible
    STATUS      current
    DESCRIPTION
        "The value of the object tmnxWlanGwMgwRemoteAddr indicates the IP
         address of the Mobile Gateway, that is the source IP address in the
         tunnel header of received packets."
    ::= { tmnxWlanGwMgwEntry 2 }

tmnxWlanGwMgwRemotePort          OBJECT-TYPE
    SYNTAX      InetPortNumber
    MAX-ACCESS  not-accessible
    STATUS      current
    DESCRIPTION
        "The value of tmnxWlanGwMgwRemotePort indicates the remote port."
    ::= { tmnxWlanGwMgwEntry 3 }

tmnxWlanGwMgwLocalAddrType       OBJECT-TYPE
    SYNTAX      InetAddressType
    MAX-ACCESS  read-only
    STATUS      current
    DESCRIPTION
        "The value of tmnxWlanGwMgwLocalAddrType indicates the address type of
         tmnxWlanGwMgwLocalAddr.

         The only values allowed are 'ipv4' and 'ipv6'."
    ::= { tmnxWlanGwMgwEntry 4 }

tmnxWlanGwMgwLocalAddr           OBJECT-TYPE
    SYNTAX      InetAddress (SIZE (4|16))
    MAX-ACCESS  read-only
    STATUS      current
    DESCRIPTION
        "The value of the object tmnxWlanGwMgwLocalAddr indicates the IP
         address of this system, that is the destination IP address in the
         tunnel header of received packets."
    ::= { tmnxWlanGwMgwEntry 5 }

tmnxWlanGwMgwTime                OBJECT-TYPE
    SYNTAX      DateAndTime (SIZE (11))
    MAX-ACCESS  read-only
    STATUS      current
    DESCRIPTION
        "The value of the object tmnxWlanGwMgwTime indicates the value of
         sysUpTime when this conceptual row was created."
    ::= { tmnxWlanGwMgwEntry 6 }

tmnxWlanGwMgwProfile             OBJECT-TYPE
    SYNTAX      TNamedItemOrEmpty
    MAX-ACCESS  read-only
    STATUS      current
    DESCRIPTION
        "The value of the object tmnxWlanGwMgwProfile indicates the name of the
         profile used for the connection with this Mobile Gateway.

         A non-empty value of this object corresponds to a value of the object
         tmnxWlanGwMgwProfName in the tmnxWlanGwMgwProfTable."
    ::= { tmnxWlanGwMgwEntry 7 }

tmnxWlanGwMgwControl             OBJECT-TYPE
    SYNTAX      INTEGER {
        gtpv1C (1),
        gtpv2C (2)
    }
    MAX-ACCESS  read-only
    STATUS      current
    DESCRIPTION
        "The value of tmnxWlanGwMgwControl indicates the control plane protocol
         used for the connection with this Mobile Gateway."
    ::= { tmnxWlanGwMgwEntry 8 }

tmnxWlanGwMgwRestartCnt          OBJECT-TYPE
    SYNTAX      Gauge32
    MAX-ACCESS  read-only
    STATUS      current
    DESCRIPTION
        "The value of tmnxWlanGwMgwRestartCnt indicates the number of times
         this Mobile Gateway restarted.

         This value is learned by means of the connection with this Mobile
         Gateway."
    ::= { tmnxWlanGwMgwEntry 9 }

tmnxWlanGwMgwState               OBJECT-TYPE
    SYNTAX      TmnxMobPathMgmtState
    MAX-ACCESS  read-only
    STATUS      current
    DESCRIPTION
        "The value of tmnxWlanGwMgwState indicates the state of the connection
         with this Mobile Gateway."
    ::= { tmnxWlanGwMgwEntry 10 }

tmnxWlanGwMgwInterfaceType       OBJECT-TYPE
    SYNTAX      TmnxWlanGwMgwInterfaceType
    MAX-ACCESS  read-only
    STATUS      current
    DESCRIPTION
        "The value of tmnxWlanGwMgwInterfaceType indicates the interface type
         of the connection with this Mobile Gateway."
    ::= { tmnxWlanGwMgwEntry 11 }

tmnxWlanMgwStatsTable            OBJECT-TYPE
    SYNTAX      SEQUENCE OF TmnxWlanMgwStatsEntry
    MAX-ACCESS  not-accessible
    STATUS      current
    DESCRIPTION
        "The tmnxWlanMgwStatsTable contains detailed statistics information
         about the Mobile Gateways connected to this system.

         The typical usage of this table is to fill in the part of the index
         that identifies a Mobile Gateway, and perform a partial walk to get
         all the statistics applicable to that Mobile Gateway."
    ::= { tmnxWlanGwMgwObjs 4 }

tmnxWlanMgwStatsEntry            OBJECT-TYPE
    SYNTAX      TmnxWlanMgwStatsEntry
    MAX-ACCESS  not-accessible
    STATUS      current
    DESCRIPTION
        "Each conceptual row contains detailed statistics information about a
         Mobile Gateway.

         Entries in this table are created and removed automatically by the
         system."
    INDEX       {
        vRtrID,
        tmnxWlanGwMgwRemoteAddrType,
        tmnxWlanGwMgwRemoteAddr,
        tmnxWlanGwMgwRemotePort,
        tmnxWlanMgwStatsId
    }
    ::= { tmnxWlanMgwStatsTable 1 }

TmnxWlanMgwStatsEntry            ::= SEQUENCE
{
    tmnxWlanMgwStatsId               Unsigned32,
    tmnxWlanMgwStatsName             DisplayString,
    tmnxWlanMgwStatsVal              Counter64,
    tmnxWlanMgwStatsValLw            Counter32,
    tmnxWlanMgwStatsValHw            Counter32
}

tmnxWlanMgwStatsId               OBJECT-TYPE
    SYNTAX      Unsigned32 (0..50)
    MAX-ACCESS  not-accessible
    STATUS      current
    DESCRIPTION
        "The value of tmnxWlanMgwStatsId indicates the identifier of the WLAN
         Gateway statistics contained in this conceptual row.

         It is a meaningless number generated by this system."
    ::= { tmnxWlanMgwStatsEntry 1 }

tmnxWlanMgwStatsName             OBJECT-TYPE
    SYNTAX      DisplayString (SIZE (1..64))
    MAX-ACCESS  read-only
    STATUS      current
    DESCRIPTION
        "The value of the object tmnxWlanMgwStatsName indicates the
         human-readable identifier of the statistics contained in this
         conceptual row."
    ::= { tmnxWlanMgwStatsEntry 2 }

tmnxWlanMgwStatsVal              OBJECT-TYPE
    SYNTAX      Counter64
    MAX-ACCESS  read-only
    STATUS      current
    DESCRIPTION
        "The value of the object tmnxWlanMgwStatsVal indicates the value of the
         statistics contained in this conceptual row."
    ::= { tmnxWlanMgwStatsEntry 3 }

tmnxWlanMgwStatsValLw            OBJECT-TYPE
    SYNTAX      Counter32
    MAX-ACCESS  read-only
    STATUS      current
    DESCRIPTION
        "The value of the object tmnxWlanMgwStatsValLw indicates the lower 32
         bits of the statistics contained in this conceptual row."
    ::= { tmnxWlanMgwStatsEntry 4 }

tmnxWlanMgwStatsValHw            OBJECT-TYPE
    SYNTAX      Counter32
    MAX-ACCESS  read-only
    STATUS      current
    DESCRIPTION
        "The value of the object tmnxWlanMgwStatsValHw indicates the higher 32
         bits of the statistics contained in this conceptual row."
    ::= { tmnxWlanMgwStatsEntry 5 }

tmnxWlanGwGtpSeTable             OBJECT-TYPE
    SYNTAX      SEQUENCE OF TmnxWlanGwGtpSeEntry
    MAX-ACCESS  not-accessible
    STATUS      current
    DESCRIPTION
        "The tmnxWlanGwGtpSeTable contains information about GTP (GPRS Tunnel
         Protocol) sessions."
    ::= { tmnxWlanGwMgwObjs 5 }

tmnxWlanGwGtpSeEntry             OBJECT-TYPE
    SYNTAX      TmnxWlanGwGtpSeEntry
    MAX-ACCESS  not-accessible
    STATUS      current
    DESCRIPTION
        "Each conceptual row represents information about a particular GTP
         session.

         Rows are created or removed automatically by the system."
    INDEX       {
        tmnxWlanGwGtpSeImsi,
        tmnxWlanGwGtpSeApn
    }
    ::= { tmnxWlanGwGtpSeTable 1 }

TmnxWlanGwGtpSeEntry             ::= SEQUENCE
{
    tmnxWlanGwGtpSeImsi              TmnxMobImsiStr,
    tmnxWlanGwGtpSeApn               TmnxMobApn,
    tmnxWlanGwGtpSeMgwRouter         TmnxVRtrIDOrZero,
    tmnxWlanGwGtpSeMgwAddrType       InetAddressType,
    tmnxWlanGwGtpSeMgwAddr           InetAddress,
    tmnxWlanGwGtpSeRemoteCtrlTeid    Unsigned32,
    tmnxWlanGwGtpSeLocalCtrlTeid     Unsigned32,
    tmnxWlanGwGtpSeChrgChar          TmnxWlanGwChargingCharBits,
    tmnxWlanGwGtpSeQosUplinkAmbr     TmnxWlanGwAmbr,
    tmnxWlanGwGtpSeQosDwnlinkAmbr    TmnxWlanGwAmbr
}

tmnxWlanGwGtpSeImsi              OBJECT-TYPE
    SYNTAX      TmnxMobImsiStr (SIZE (9..15))
    MAX-ACCESS  not-accessible
    STATUS      current
    DESCRIPTION
        "The value of tmnxWlanGwGtpSeImsi indicates the IMSI."
    ::= { tmnxWlanGwGtpSeEntry 1 }

tmnxWlanGwGtpSeApn               OBJECT-TYPE
    SYNTAX      TmnxMobApn
    MAX-ACCESS  not-accessible
    STATUS      current
    DESCRIPTION
        "The value of the object tmnxWlanGwGtpSeApn indicates the APN (Access
         Point Name)."
    REFERENCE
        "3GPP TS 23.003 Numbering, addressing and identification,
         section 9 Definition of Access Point Name"
    ::= { tmnxWlanGwGtpSeEntry 2 }

tmnxWlanGwGtpSeMgwRouter         OBJECT-TYPE
    SYNTAX      TmnxVRtrIDOrZero
    MAX-ACCESS  read-only
    STATUS      current
    DESCRIPTION
        "The value of tmnxWlanGwGtpSeMgwRouter indicates the identifier of the
         virtual router instance where the GTP tunnel is terminated."
    ::= { tmnxWlanGwGtpSeEntry 3 }

tmnxWlanGwGtpSeMgwAddrType       OBJECT-TYPE
    SYNTAX      InetAddressType
    MAX-ACCESS  read-only
    STATUS      current
    DESCRIPTION
        "The value of tmnxWlanGwGtpSeMgwAddrType indicates the address type of
         tmnxWlanGwGtpSeMgwAddr."
    ::= { tmnxWlanGwGtpSeEntry 4 }

tmnxWlanGwGtpSeMgwAddr           OBJECT-TYPE
    SYNTAX      InetAddress (SIZE (4|16))
    MAX-ACCESS  read-only
    STATUS      current
    DESCRIPTION
        "The value of the object tmnxWlanGwGtpSeMgwAddr indicates the IP
         address of the Mobile Gateway, that is the source IP address in the
         tunnel header of received packets."
    ::= { tmnxWlanGwGtpSeEntry 5 }

tmnxWlanGwGtpSeRemoteCtrlTeid    OBJECT-TYPE
    SYNTAX      Unsigned32
    MAX-ACCESS  read-only
    STATUS      current
    DESCRIPTION
        "The value of tmnxWlanGwGtpSeRemoteCtrlTeid indicates the remote
         control plane Tunnel Endpoint Identifier (TEID)."
    ::= { tmnxWlanGwGtpSeEntry 6 }

tmnxWlanGwGtpSeLocalCtrlTeid     OBJECT-TYPE
    SYNTAX      Unsigned32
    MAX-ACCESS  read-only
    STATUS      current
    DESCRIPTION
        "The value of tmnxWlanGwGtpSeLocalCtrlTeid indicates the local control
         plane Tunnel Endpoint Identifier (TEID)."
    ::= { tmnxWlanGwGtpSeEntry 7 }

tmnxWlanGwGtpSeChrgChar          OBJECT-TYPE
    SYNTAX      TmnxWlanGwChargingCharBits
    MAX-ACCESS  read-only
    STATUS      current
    DESCRIPTION
        "The value of tmnxWlanGwGtpSeChrgChar indicates the Charging
         Characteristics."
    ::= { tmnxWlanGwGtpSeEntry 10 }

tmnxWlanGwGtpSeQosUplinkAmbr     OBJECT-TYPE
    SYNTAX      TmnxWlanGwAmbr
    UNITS       "kilobps"
    MAX-ACCESS  read-only
    STATUS      current
    DESCRIPTION
        "The value of tmnxWlanGwGtpSeQosUplinkAmbr indicates the uplink
         Aggregated Maximum Bit Rate (AMBR)."
    ::= { tmnxWlanGwGtpSeEntry 11 }

tmnxWlanGwGtpSeQosDwnlinkAmbr    OBJECT-TYPE
    SYNTAX      TmnxWlanGwAmbr
    UNITS       "kilobps"
    MAX-ACCESS  read-only
    STATUS      current
    DESCRIPTION
        "The value of tmnxWlanGwGtpSeQosDwnlinkAmbr indicates the downlink
         Aggregated Maximum Bit Rate (AMBR)."
    ::= { tmnxWlanGwGtpSeEntry 12 }

tmnxWlanGwBcTable                OBJECT-TYPE
    SYNTAX      SEQUENCE OF TmnxWlanGwBcEntry
    MAX-ACCESS  not-accessible
    STATUS      current
    DESCRIPTION
        "The tmnxWlanGwBcTable contains information about GTP (GPRS Tunnel
         Protocol) bearers."
    ::= { tmnxWlanGwMgwObjs 6 }

tmnxWlanGwBcEntry                OBJECT-TYPE
    SYNTAX      TmnxWlanGwBcEntry
    MAX-ACCESS  not-accessible
    STATUS      current
    DESCRIPTION
        "Each conceptual row represents information about a particular bearer
         context.

         Rows are created or removed automatically by the system."
    INDEX       {
        tmnxWlanGwGtpSeImsi,
        tmnxWlanGwGtpSeApn,
        tmnxWlanGwBcId
    }
    ::= { tmnxWlanGwBcTable 1 }

TmnxWlanGwBcEntry                ::= SEQUENCE
{
    tmnxWlanGwBcId                   TmnxMobBearerId,
    tmnxWlanGwBcRemoteTeid           Unsigned32,
    tmnxWlanGwBcLocalTeid            Unsigned32,
    tmnxWlanGwBcQosUlGbr             Unsigned32,
    tmnxWlanGwBcQosUlMbr             Unsigned32,
    tmnxWlanGwBcQosDlGbr             Unsigned32,
    tmnxWlanGwBcQosDlMbr             Unsigned32,
    tmnxWlanGwBcQosQci               TmnxMobQci,
    tmnxWlanGwBcQosArp               TmnxMobArp
}

tmnxWlanGwBcId                   OBJECT-TYPE
    SYNTAX      TmnxMobBearerId
    MAX-ACCESS  not-accessible
    STATUS      current
    DESCRIPTION
        "The value of tmnxWlanGwBcId indicates the identifier of this bearer
         context."
    ::= { tmnxWlanGwBcEntry 1 }

tmnxWlanGwBcRemoteTeid           OBJECT-TYPE
    SYNTAX      Unsigned32
    MAX-ACCESS  read-only
    STATUS      current
    DESCRIPTION
        "The value of tmnxWlanGwBcRemoteTeid indicates the remote Tunnel
         Endpoint Identifier (TEID)."
    ::= { tmnxWlanGwBcEntry 2 }

tmnxWlanGwBcLocalTeid            OBJECT-TYPE
    SYNTAX      Unsigned32
    MAX-ACCESS  read-only
    STATUS      current
    DESCRIPTION
        "The value of tmnxWlanGwBcLocalTeid indicates the local Tunnel Endpoint
         Identifier (TEID)."
    ::= { tmnxWlanGwBcEntry 3 }

tmnxWlanGwBcQosUlGbr             OBJECT-TYPE
    SYNTAX      Unsigned32
    UNITS       "kilobps"
    MAX-ACCESS  read-only
    STATUS      current
    DESCRIPTION
        "The value of tmnxWlanGwBcQosUlGbr indicates the uplink Guaranteed Bit
         Rate (GBR)."
    ::= { tmnxWlanGwBcEntry 10 }

tmnxWlanGwBcQosUlMbr             OBJECT-TYPE
    SYNTAX      Unsigned32
    UNITS       "kilobps"
    MAX-ACCESS  read-only
    STATUS      current
    DESCRIPTION
        "The value of tmnxWlanGwBcQosUlMbr indicates the uplink Maximum Bit
         Rate (MBR)."
    ::= { tmnxWlanGwBcEntry 11 }

tmnxWlanGwBcQosDlGbr             OBJECT-TYPE
    SYNTAX      Unsigned32
    UNITS       "kilobps"
    MAX-ACCESS  read-only
    STATUS      current
    DESCRIPTION
        "The value of tmnxWlanGwBcQosDlGbr indicates the downlink Guaranteed
         Bit Rate (GBR)."
    ::= { tmnxWlanGwBcEntry 12 }

tmnxWlanGwBcQosDlMbr             OBJECT-TYPE
    SYNTAX      Unsigned32
    UNITS       "kilobps"
    MAX-ACCESS  read-only
    STATUS      current
    DESCRIPTION
        "The value of tmnxWlanGwBcQosDlMbr indicates the downlink Maximum Bit
         Rate (MBR)."
    ::= { tmnxWlanGwBcEntry 13 }

tmnxWlanGwBcQosQci               OBJECT-TYPE
    SYNTAX      TmnxMobQci
    MAX-ACCESS  read-only
    STATUS      current
    DESCRIPTION
        "The value of tmnxWlanGwBcQosQci indicates the Qos Class Identifier"
    ::= { tmnxWlanGwBcEntry 14 }

tmnxWlanGwBcQosArp               OBJECT-TYPE
    SYNTAX      TmnxMobArp
    MAX-ACCESS  read-only
    STATUS      current
    DESCRIPTION
        "The value of tmnxWlanGwBcQosArp indicates the Allocation and Retention
         Priority (ARP)."
    ::= { tmnxWlanGwBcEntry 15 }

tmnxWlanGwMgwCacheTable          OBJECT-TYPE
    SYNTAX      SEQUENCE OF TmnxWlanGwMgwCacheEntry
    MAX-ACCESS  not-accessible
    STATUS      obsolete
    DESCRIPTION
        "This table is obsoleted and replaced with the
         tmnxWlanGwMgwArecCacheTable."
    ::= { tmnxWlanGwMgwObjs 7 }

tmnxWlanGwMgwCacheEntry          OBJECT-TYPE
    SYNTAX      TmnxWlanGwMgwCacheEntry
    MAX-ACCESS  not-accessible
    STATUS      obsolete
    DESCRIPTION
        "This table is obsoleted and replaced with the
         tmnxWlanGwMgwArecCacheTable."
    INDEX       {
        vRtrID,
        tmnxWlanGwMgwCacheApn,
        tmnxWlanGwMgwCacheAddrType,
        tmnxWlanGwMgwCacheAddr
    }
    ::= { tmnxWlanGwMgwCacheTable 1 }

TmnxWlanGwMgwCacheEntry          ::= SEQUENCE
{
    tmnxWlanGwMgwCacheApn            TmnxMobApnDomainName,
    tmnxWlanGwMgwCacheAddrType       InetAddressType,
    tmnxWlanGwMgwCacheAddr           InetAddress,
    tmnxWlanGwMgwCacheTtl            Unsigned32
}

tmnxWlanGwMgwCacheApn            OBJECT-TYPE
    SYNTAX      TmnxMobApnDomainName
    MAX-ACCESS  not-accessible
    STATUS      obsolete
    DESCRIPTION
        "The value of the object tmnxWlanGwMgwCacheApn indicates the APN
         (Access Point Name) of this DNS cache entry."
    REFERENCE
        "3GPP TS 23.003 Numbering, addressing and identification,
         section 9 Definition of Access Point Name"
    ::= { tmnxWlanGwMgwCacheEntry 1 }

tmnxWlanGwMgwCacheAddrType       OBJECT-TYPE
    SYNTAX      InetAddressType
    MAX-ACCESS  not-accessible
    STATUS      obsolete
    DESCRIPTION
        "The value of tmnxWlanGwMgwCacheAddrType indicates the address type of
         tmnxWlanGwMgwCacheAddr.

         The only values allowed are 'ipv4' and 'ipv6'."
    ::= { tmnxWlanGwMgwCacheEntry 2 }

tmnxWlanGwMgwCacheAddr           OBJECT-TYPE
    SYNTAX      InetAddress (SIZE (4|16))
    MAX-ACCESS  not-accessible
    STATUS      obsolete
    DESCRIPTION
        "The value of the object tmnxWlanGwMgwCacheAddr indicates the IP
         address of the Mobile Gateway."
    ::= { tmnxWlanGwMgwCacheEntry 3 }

tmnxWlanGwMgwCacheTtl            OBJECT-TYPE
    SYNTAX      Unsigned32
    UNITS       "seconds"
    MAX-ACCESS  read-only
    STATUS      obsolete
    DESCRIPTION
        "The value of tmnxWlanGwMgwCacheTtl indicates the period of time left
         for this cache entry."
    ::= { tmnxWlanGwMgwCacheEntry 4 }

tmnxWlanGwGtpStatsTable          OBJECT-TYPE
    SYNTAX      SEQUENCE OF TmnxWlanGwGtpStatsEntry
    MAX-ACCESS  not-accessible
    STATUS      current
    DESCRIPTION
        "The tmnxWlanGwGtpStatsTable contains detailed statistics information
         about the GTP protocol in this system.

         The typical usage of this table is to perform a walk to get all the
         statistics."
    ::= { tmnxWlanGwMgwObjs 8 }

tmnxWlanGwGtpStatsEntry          OBJECT-TYPE
    SYNTAX      TmnxWlanGwGtpStatsEntry
    MAX-ACCESS  not-accessible
    STATUS      current
    DESCRIPTION
        "Each conceptual row contains detailed information about a GTP
         statistic.

         Entries in this table are created and removed automatically by the
         system."
    INDEX       { tmnxWlanGwGtpStatsId }
    ::= { tmnxWlanGwGtpStatsTable 1 }

TmnxWlanGwGtpStatsEntry          ::= SEQUENCE
{
    tmnxWlanGwGtpStatsId             Unsigned32,
    tmnxWlanGwGtpStatsName           DisplayString,
    tmnxWlanGwGtpStatsVal            Counter64,
    tmnxWlanGwGtpStatsValLw          Counter32,
    tmnxWlanGwGtpStatsValHw          Counter32
}

tmnxWlanGwGtpStatsId             OBJECT-TYPE
    SYNTAX      Unsigned32 (0..71)
    MAX-ACCESS  not-accessible
    STATUS      current
    DESCRIPTION
        "The value of tmnxWlanGwGtpStatsId indicates the identifier of the GTP
         statistics contained in this conceptual row.

         It is a meaningless number generated by this system."
    ::= { tmnxWlanGwGtpStatsEntry 1 }

tmnxWlanGwGtpStatsName           OBJECT-TYPE
    SYNTAX      DisplayString (SIZE (1..56))
    MAX-ACCESS  read-only
    STATUS      current
    DESCRIPTION
        "The value of the object tmnxWlanGwGtpStatsName indicates the
         human-readable identifier of the statistics contained in this
         conceptual row."
    ::= { tmnxWlanGwGtpStatsEntry 2 }

tmnxWlanGwGtpStatsVal            OBJECT-TYPE
    SYNTAX      Counter64
    MAX-ACCESS  read-only
    STATUS      current
    DESCRIPTION
        "The value of the object tmnxWlanGwGtpStatsVal indicates the value of
         the statistics contained in this conceptual row."
    ::= { tmnxWlanGwGtpStatsEntry 3 }

tmnxWlanGwGtpStatsValLw          OBJECT-TYPE
    SYNTAX      Counter32
    MAX-ACCESS  read-only
    STATUS      current
    DESCRIPTION
        "The value of the object tmnxWlanGwGtpStatsValLw indicates the lower 32
         bits of the statistics contained in this conceptual row."
    ::= { tmnxWlanGwGtpStatsEntry 4 }

tmnxWlanGwGtpStatsValHw          OBJECT-TYPE
    SYNTAX      Counter32
    MAX-ACCESS  read-only
    STATUS      current
    DESCRIPTION
        "The value of the object tmnxWlanGwGtpStatsValHw indicates the higher
         32 bits of the statistics contained in this conceptual row."
    ::= { tmnxWlanGwGtpStatsEntry 5 }

tmnxWlanGwMgwArecCacheTable      OBJECT-TYPE
    SYNTAX      SEQUENCE OF TmnxWlanGwMgwArecCacheEntry
    MAX-ACCESS  not-accessible
    STATUS      current
    DESCRIPTION
        "The tmnxWlanGwMgwArecCacheTable contains information about the Mobile
         Gateways DNS cache.

         When a DNS request is done to find a Mobile Gateway for a particular
         APN, the result is cached."
    ::= { tmnxWlanGwMgwObjs 10 }

tmnxWlanGwMgwArecCacheEntry      OBJECT-TYPE
    SYNTAX      TmnxWlanGwMgwArecCacheEntry
    MAX-ACCESS  not-accessible
    STATUS      current
    DESCRIPTION
        "Each conceptual row represents information about a particular Mobile
         Gateway A-record cache instance.

         Each conceptual row associates an APN in a router instance with a
         Mobile Gateway.

         Rows are created or removed automatically by the system."
    INDEX       {
        vRtrID,
        tmnxWlanGwMgwArecCacheApn,
        tmnxWlanGwMgwArecCacheIndex
    }
    ::= { tmnxWlanGwMgwArecCacheTable 1 }

TmnxWlanGwMgwArecCacheEntry      ::= SEQUENCE
{
    tmnxWlanGwMgwArecCacheApn        TmnxMobApnDomainName,
    tmnxWlanGwMgwArecCacheIndex      Unsigned32,
    tmnxWlanGwMgwArecCacheAddrType   InetAddressType,
    tmnxWlanGwMgwArecCacheAddr       InetAddress,
    tmnxWlanGwMgwArecCacheTtl        Unsigned32
}

tmnxWlanGwMgwArecCacheApn        OBJECT-TYPE
    SYNTAX      TmnxMobApnDomainName
    MAX-ACCESS  not-accessible
    STATUS      current
    DESCRIPTION
        "The value of the object tmnxWlanGwMgwArecCacheApn indicates the APN
         (Access Point Name) of this DNS cache entry."
    REFERENCE
        "3GPP TS 23.003 Numbering, addressing and identification,
         section 9 Definition of Access Point Name"
    ::= { tmnxWlanGwMgwArecCacheEntry 1 }

tmnxWlanGwMgwArecCacheIndex      OBJECT-TYPE
    SYNTAX      Unsigned32
    MAX-ACCESS  not-accessible
    STATUS      current
    DESCRIPTION
        "The value of the object tmnxWlanGwMgwArecCacheIndex indicates the
         identifier of this entry within a set of rows that have the same APN.

         It is a number generated by the system."
    ::= { tmnxWlanGwMgwArecCacheEntry 2 }

tmnxWlanGwMgwArecCacheAddrType   OBJECT-TYPE
    SYNTAX      InetAddressType
    MAX-ACCESS  read-only
    STATUS      current
    DESCRIPTION
        "The value of tmnxWlanGwMgwArecCacheAddrType indicates the address type
         of tmnxWlanGwMgwArecCacheAddr.

         The only values allowed are 'ipv4' and 'ipv6'."
    ::= { tmnxWlanGwMgwArecCacheEntry 3 }

tmnxWlanGwMgwArecCacheAddr       OBJECT-TYPE
    SYNTAX      InetAddress (SIZE (4|16))
    MAX-ACCESS  read-only
    STATUS      current
    DESCRIPTION
        "The value of the object tmnxWlanGwMgwArecCacheAddr indicates the IP
         address of the Mobile Gateway."
    ::= { tmnxWlanGwMgwArecCacheEntry 4 }

tmnxWlanGwMgwArecCacheTtl        OBJECT-TYPE
    SYNTAX      Unsigned32
    UNITS       "seconds"
    MAX-ACCESS  read-only
    STATUS      current
    DESCRIPTION
        "The value of tmnxWlanGwMgwArecCacheTtl indicates the period of time
         left for this cache entry."
    ::= { tmnxWlanGwMgwArecCacheEntry 5 }

tmnxWlanGwMgwSnaptrCacheTable    OBJECT-TYPE
    SYNTAX      SEQUENCE OF TmnxWlanGwMgwSnaptrCacheEntry
    MAX-ACCESS  not-accessible
    STATUS      current
    DESCRIPTION
        "The tmnxWlanGwMgwSnaptrCacheTable contains information about the
         Mobile Gateways DNS S-NAPTR (Straightforward Naming Authority Pointer)
         cache.

         When a DNS NAPTR request is done to find a Mobile Gateway for a
         particular APN, the result is cached."
    REFERENCE
        "3GPP TS 29.303 / RFC 3958"
    ::= { tmnxWlanGwMgwObjs 11 }

tmnxWlanGwMgwSnaptrCacheEntry    OBJECT-TYPE
    SYNTAX      TmnxWlanGwMgwSnaptrCacheEntry
    MAX-ACCESS  not-accessible
    STATUS      current
    DESCRIPTION
        "Each conceptual row represents information about a particular Mobile
         Gateway S-NAPTR cache instance.

         Each conceptual row associates an APN and service for a given order
         and preference in a router instance with a Domain Name.

         Rows are created or removed automatically by the system."
    INDEX       {
        vRtrID,
        tmnxWlanGwMgwSnaptrCacheApn,
        tmnxWlanGwMgwSnaptrCacheOrder,
        tmnxWlanGwMgwSnaptrCacheIndex
    }
    ::= { tmnxWlanGwMgwSnaptrCacheTable 1 }

TmnxWlanGwMgwSnaptrCacheEntry    ::= SEQUENCE
{
    tmnxWlanGwMgwSnaptrCacheApn      TmnxMobApnDomainName,
    tmnxWlanGwMgwSnaptrCacheOrder    Unsigned32,
    tmnxWlanGwMgwSnaptrCacheIndex    Unsigned32,
    tmnxWlanGwMgwSnaptrCachePref     Unsigned32,
    tmnxWlanGwMgwSnaptrCacheService  TmnxMobService,
    tmnxWlanGwMgwSnaptrCacheNext     INTEGER,
    tmnxWlanGwMgwSnaptrCacheRepl     TmnxMobApnDomainName,
    tmnxWlanGwMgwSnaptrCacheTtl      Unsigned32
}

tmnxWlanGwMgwSnaptrCacheApn      OBJECT-TYPE
    SYNTAX      TmnxMobApnDomainName
    MAX-ACCESS  not-accessible
    STATUS      current
    DESCRIPTION
        "The value of the object tmnxWlanGwMgwSnaptrCacheApn indicates the APN
         (Access Point Name) of this DNS cache entry."
    REFERENCE
        "3GPP TS 23.003 Numbering, addressing and identification,
         section 9 Definition of Access Point Name"
    ::= { tmnxWlanGwMgwSnaptrCacheEntry 1 }

tmnxWlanGwMgwSnaptrCacheOrder    OBJECT-TYPE
    SYNTAX      Unsigned32
    MAX-ACCESS  not-accessible
    STATUS      current
    DESCRIPTION
        "The value of tmnxWlanGwMgwSnaptrCacheOrder indicates the order of this
         cache entry.

         If more than one NAPTR record matches, they are processed in
         increasing values of tmnxWlanGwMgwSnaptrCacheOrder."
    ::= { tmnxWlanGwMgwSnaptrCacheEntry 2 }

tmnxWlanGwMgwSnaptrCacheIndex    OBJECT-TYPE
    SYNTAX      Unsigned32
    MAX-ACCESS  not-accessible
    STATUS      current
    DESCRIPTION
        "The value of the object tmnxWlanGwMgwSnaptrCacheIndex indicates the
         identifier of this entry within a set of rows that have the same APN
         and order.

         It is a number generated by the system."
    ::= { tmnxWlanGwMgwSnaptrCacheEntry 3 }

tmnxWlanGwMgwSnaptrCachePref     OBJECT-TYPE
    SYNTAX      Unsigned32
    MAX-ACCESS  read-only
    STATUS      current
    DESCRIPTION
        "The value of the object tmnxWlanGwMgwSnaptrCachePref indicates the
         preference of this cache entry.

         A lower value for tmnxWlanGwMgwSnaptrCachePref indicates a higher
         preference."
    ::= { tmnxWlanGwMgwSnaptrCacheEntry 4 }

tmnxWlanGwMgwSnaptrCacheService  OBJECT-TYPE
    SYNTAX      TmnxMobService (SIZE (1..80))
    MAX-ACCESS  read-only
    STATUS      current
    DESCRIPTION
        "The value of the object tmnxWlanGwMgwSnaptrCacheService indicates the
         service associated with this cache entry."
    ::= { tmnxWlanGwMgwSnaptrCacheEntry 5 }

tmnxWlanGwMgwSnaptrCacheNext     OBJECT-TYPE
    SYNTAX      INTEGER {
        dnsSrv   (1),
        dnsA     (2),
        dnsNaptr (3)
    }
    MAX-ACCESS  read-only
    STATUS      current
    DESCRIPTION
        "The value of tmnxWlanGwMgwSnaptrCacheNext indicates the next lookup
         operation for this cache entry.

         For the next lookup operation, the value of
         tmnxWlanGwMgwSnaptrCacheRepl must be used instead of the original APN
         value."
    ::= { tmnxWlanGwMgwSnaptrCacheEntry 6 }

tmnxWlanGwMgwSnaptrCacheRepl     OBJECT-TYPE
    SYNTAX      TmnxMobApnDomainName
    MAX-ACCESS  read-only
    STATUS      current
    DESCRIPTION
        "The value of tmnxWlanGwMgwSnaptrCacheRepl indicates the APN value to
         be substituted for the original APN in the next lookup."
    ::= { tmnxWlanGwMgwSnaptrCacheEntry 7 }

tmnxWlanGwMgwSnaptrCacheTtl      OBJECT-TYPE
    SYNTAX      Unsigned32
    UNITS       "seconds"
    MAX-ACCESS  read-only
    STATUS      current
    DESCRIPTION
        "The value of tmnxWlanGwMgwSnaptrCacheTtl indicates the period of time
         left for this cache entry."
    ::= { tmnxWlanGwMgwSnaptrCacheEntry 8 }

tmnxWlanGwMgwSrvCacheTable       OBJECT-TYPE
    SYNTAX      SEQUENCE OF TmnxWlanGwMgwSrvCacheEntry
    MAX-ACCESS  not-accessible
    STATUS      current
    DESCRIPTION
        "The tmnxWlanGwMgwSrvCacheTable contains information about the Mobile
         Gateways DNS SRV cache.

         When a DNS SRV request is done to find a DNS server for a particular
         APN, the result is cached."
    REFERENCE
        "IETF RFC 2782"
    ::= { tmnxWlanGwMgwObjs 12 }

tmnxWlanGwMgwSrvCacheEntry       OBJECT-TYPE
    SYNTAX      TmnxWlanGwMgwSrvCacheEntry
    MAX-ACCESS  not-accessible
    STATUS      current
    DESCRIPTION
        "Each conceptual row represents information about a particular Mobile
         Gateway SRV cache instance.

         Each conceptual row associates an APN for a given priority and weight
         in a router instance, with a target Domain Name.

         Rows are created or removed automatically by the system."
    INDEX       {
        vRtrID,
        tmnxWlanGwMgwSrvCacheApn,
        tmnxWlanGwMgwSrvCachePriority,
        tmnxWlanGwMgwSrvCacheIndex
    }
    ::= { tmnxWlanGwMgwSrvCacheTable 1 }

TmnxWlanGwMgwSrvCacheEntry       ::= SEQUENCE
{
    tmnxWlanGwMgwSrvCacheApn         TmnxMobApnDomainName,
    tmnxWlanGwMgwSrvCachePriority    Unsigned32,
    tmnxWlanGwMgwSrvCacheIndex       Unsigned32,
    tmnxWlanGwMgwSrvCacheWeight      Unsigned32,
    tmnxWlanGwMgwSrvCachePort        InetPortNumber,
    tmnxWlanGwMgwSrvCacheTarget      TmnxMobApnDomainName,
    tmnxWlanGwMgwSrvCacheTtl         Unsigned32
}

tmnxWlanGwMgwSrvCacheApn         OBJECT-TYPE
    SYNTAX      TmnxMobApnDomainName
    MAX-ACCESS  not-accessible
    STATUS      current
    DESCRIPTION
        "The value of the object tmnxWlanGwMgwSrvCacheApn indicates the APN
         (Access Point Name) of this DNS cache entry."
    REFERENCE
        "3GPP TS 23.003 Numbering, addressing and identification,
         section 9 Definition of Access Point Name"
    ::= { tmnxWlanGwMgwSrvCacheEntry 1 }

tmnxWlanGwMgwSrvCachePriority    OBJECT-TYPE
    SYNTAX      Unsigned32 (0..65535)
    MAX-ACCESS  not-accessible
    STATUS      current
    DESCRIPTION
        "The value of tmnxWlanGwMgwSrvCachePriority indicates the priority of
         this cache entry.

         The lower the number, the higher the priority.

         If more than one SERV record matches, they are processed according to
         their value of tmnxWlanGwMgwSrvCacheWeight."
    ::= { tmnxWlanGwMgwSrvCacheEntry 2 }

tmnxWlanGwMgwSrvCacheIndex       OBJECT-TYPE
    SYNTAX      Unsigned32
    MAX-ACCESS  not-accessible
    STATUS      current
    DESCRIPTION
        "The value of the object tmnxWlanGwMgwSrvCacheIndex indicates the
         identifier of this entry within a set of rows that have the same APN
         and priority.

         It is a number generated by the system."
    ::= { tmnxWlanGwMgwSrvCacheEntry 3 }

tmnxWlanGwMgwSrvCacheWeight      OBJECT-TYPE
    SYNTAX      Unsigned32 (0..65535)
    MAX-ACCESS  read-only
    STATUS      current
    DESCRIPTION
        "The value of the object tmnxWlanGwMgwSrvCacheWeight indicates the
         weight of this cache entry.

         Cache entries with larger weights should have a higher probability of
         being used."
    ::= { tmnxWlanGwMgwSrvCacheEntry 4 }

tmnxWlanGwMgwSrvCachePort        OBJECT-TYPE
    SYNTAX      InetPortNumber
    MAX-ACCESS  read-only
    STATUS      current
    DESCRIPTION
        "The value of the object tmnxWlanGwMgwSrvCachePort indicates the port
         on this target host of this service."
    ::= { tmnxWlanGwMgwSrvCacheEntry 5 }

tmnxWlanGwMgwSrvCacheTarget      OBJECT-TYPE
    SYNTAX      TmnxMobApnDomainName
    MAX-ACCESS  read-only
    STATUS      current
    DESCRIPTION
        "The value of tmnxWlanGwMgwSrvCacheTarget indicates the domain name of
         the target host."
    ::= { tmnxWlanGwMgwSrvCacheEntry 6 }

tmnxWlanGwMgwSrvCacheTtl         OBJECT-TYPE
    SYNTAX      Unsigned32
    UNITS       "seconds"
    MAX-ACCESS  read-only
    STATUS      current
    DESCRIPTION
        "The value of tmnxWlanGwMgwSrvCacheTtl indicates the period of time
         left for this cache entry."
    ::= { tmnxWlanGwMgwSrvCacheEntry 7 }

tmnxWlanGwPgwTable               OBJECT-TYPE
    SYNTAX      SEQUENCE OF TmnxWlanGwPgwEntry
    MAX-ACCESS  not-accessible
    STATUS      current
    DESCRIPTION
        "The tmnxWlanGwPgwTable allows configuration of how to communicate with
         a Packet Data Network Gateway (PGW) Mobile Gateway."
    ::= { tmnxWlanGwMgwObjs 20 }

tmnxWlanGwPgwEntry               OBJECT-TYPE
    SYNTAX      TmnxWlanGwPgwEntry
    MAX-ACCESS  not-accessible
    STATUS      current
    DESCRIPTION
        "Each entry represents the configuration for a specific Mobile Gateway
         Profile, to be used when the Mobile Gateway is a Packet Data Network
         Gateway (PGW).

         Entries in this table are created and destroyed automatically by the
         system."
    AUGMENTS    { tmnxWlanGwMgwProfEntry }
    ::= { tmnxWlanGwPgwTable 1 }

TmnxWlanGwPgwEntry               ::= SEQUENCE
{
    tmnxWlanGwPgwLastChanged         TimeStamp,
    tmnxWlanGwPgwQosUplinkGbrRate    TmnxMobProfGbrRate,
    tmnxWlanGwPgwQosUplinkMbrRate    TmnxMobProfMbrRate,
    tmnxWlanGwPgwQosDwnlinkGbrRate   TmnxMobProfGbrRate,
    tmnxWlanGwPgwQosDwnlinkMbrRate   TmnxMobProfMbrRate,
    tmnxWlanGwPgwQosArpValue         TmnxMobArpValue,
    tmnxWlanGwPgwQosQciValue         TmnxMobQci,
    tmnxWlanGwPgwQosUplinkAmbr       TmnxWlanGwAmbr,
    tmnxWlanGwPgwQosDwnlinkAmbr      TmnxWlanGwAmbr
}

tmnxWlanGwPgwLastChanged         OBJECT-TYPE
    SYNTAX      TimeStamp
    MAX-ACCESS  read-only
    STATUS      current
    DESCRIPTION
        "The value of tmnxWlanGwPgwLastChanged indicates the sysUpTime at the
         time of the most recent management-initiated change to this profile."
    ::= { tmnxWlanGwPgwEntry 1 }

tmnxWlanGwPgwQosUplinkGbrRate    OBJECT-TYPE
    SYNTAX      TmnxMobProfGbrRate
    UNITS       "kilobps"
    MAX-ACCESS  read-create
    STATUS      current
    DESCRIPTION
        "The value of tmnxWlanGwPgwQosUplinkGbrRate specifies the uplink
         Guaranteed Bit Rate (GBR) to be used in the GTP messages as 'QOS IE'
         (for a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 0 }
    ::= { tmnxWlanGwPgwEntry 2 }

tmnxWlanGwPgwQosUplinkMbrRate    OBJECT-TYPE
    SYNTAX      TmnxMobProfMbrRate
    UNITS       "kilobps"
    MAX-ACCESS  read-create
    STATUS      current
    DESCRIPTION
        "The value of tmnxWlanGwPgwQosUplinkMbrRate specifies the uplink
         Maximum Bit Rate (MBR) to be used in the GTP messages as 'QOS IE' (for
         a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 0 }
    ::= { tmnxWlanGwPgwEntry 3 }

tmnxWlanGwPgwQosDwnlinkGbrRate   OBJECT-TYPE
    SYNTAX      TmnxMobProfGbrRate
    UNITS       "kilobps"
    MAX-ACCESS  read-create
    STATUS      current
    DESCRIPTION
        "The value of tmnxWlanGwPgwQosDwnlinkGbrRate specifies the downlink
         Guaranteed Bit Rate (GBR) to be used in the GTP messages as 'QOS IE'
         (for a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 0 }
    ::= { tmnxWlanGwPgwEntry 4 }

tmnxWlanGwPgwQosDwnlinkMbrRate   OBJECT-TYPE
    SYNTAX      TmnxMobProfMbrRate
    UNITS       "kilobps"
    MAX-ACCESS  read-create
    STATUS      current
    DESCRIPTION
        "The value of tmnxWlanGwPgwQosDwnlinkMbrRate specifies the downlink
         Maximum Bit Rate (MBR) to be used in the GTP messages as 'QOS IE' (for
         a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 0 }
    ::= { tmnxWlanGwPgwEntry 5 }

tmnxWlanGwPgwQosArpValue         OBJECT-TYPE
    SYNTAX      TmnxMobArpValue
    MAX-ACCESS  read-create
    STATUS      current
    DESCRIPTION
        "The value of tmnxWlanGwPgwQosArpValue specifies the
         allocation/retention priority to be used in the GTP messages as 'QOS
         IE' (for a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 1 }
    ::= { tmnxWlanGwPgwEntry 6 }

tmnxWlanGwPgwQosQciValue         OBJECT-TYPE
    SYNTAX      TmnxMobQci
    MAX-ACCESS  read-create
    STATUS      current
    DESCRIPTION
        "The value of tmnxWlanGwPgwQosQciValue specifies the QoS Class
         Identifier (QCI) value to be used in the GTP messages as 'QOS IE' (for
         a Gn interface) or 'Bearer QOS' (for an S2a/S2b interface)."
    REFERENCE
        "3GPP TS 29.060, section 7.7.34 Quality of Service (QoS) Profile

         3GPP TS 129.274, section 8.15 Bearer Quality of Service (Bearer QoS)

         3GPP TS 23.203, section 6.5 Quality of Service Control rule"
    DEFVAL      { 8 }
    ::= { tmnxWlanGwPgwEntry 7 }

tmnxWlanGwPgwQosUplinkAmbr       OBJECT-TYPE
    SYNTAX      TmnxWlanGwAmbr
    UNITS       "kilobps"
    MAX-ACCESS  read-create
    STATUS      current
    DESCRIPTION
        "The value of tmnxWlanGwPgwQosUplinkAmbr specifies the uplink
         Aggregated Maximum Bit Rate (AMBR) to be used in the GTP messages as
         'AMBR IE'.

         The value minus two is not allowed."
    DEFVAL      { 10000 }
    ::= { tmnxWlanGwPgwEntry 8 }

tmnxWlanGwPgwQosDwnlinkAmbr      OBJECT-TYPE
    SYNTAX      TmnxWlanGwAmbr
    UNITS       "kilobps"
    MAX-ACCESS  read-create
    STATUS      current
    DESCRIPTION
        "The value of tmnxWlanGwPgwQosDwnlinkAmbr specifies the downlink
         Aggregated Maximum Bit Rate (AMBR) to be used in the GTP messages as
         'AMBR IE'.

         The value minus two is not allowed."
    DEFVAL      { 20000 }
    ::= { tmnxWlanGwPgwEntry 9 }

tmnxWlanGwGgsnTable              OBJECT-TYPE
    SYNTAX      SEQUENCE OF TmnxWlanGwGgsnEntry
    MAX-ACCESS  not-accessible
    STATUS      current
    DESCRIPTION
        "The tmnxWlanGwGgsnTable allows configuration of how to communicate
         with a Gateway GPRS Support Node (GGSN) Mobile Gateway."
    ::= { tmnxWlanGwMgwObjs 21 }

tmnxWlanGwGgsnEntry              OBJECT-TYPE
    SYNTAX      TmnxWlanGwGgsnEntry
    MAX-ACCESS  not-accessible
    STATUS      current
    DESCRIPTION
        "Each entry represents the configuration for a specific Mobile Gateway
         Profile, to be used when the Mobile Gateway is a Gateway GPRS Support
         Node (GGSN).

         Entries in this table are created and destroyed automatically by the
         system."
    AUGMENTS    { tmnxWlanGwMgwProfEntry }
    ::= { tmnxWlanGwGgsnTable 1 }

TmnxWlanGwGgsnEntry              ::= SEQUENCE
{
    tmnxWlanGwGgsnLastChanged        TimeStamp,
    tmnxWlanGwGgsnQosUplinkGbrRate   TmnxMobProfGbrRate,
    tmnxWlanGwGgsnQosUplinkMbrRate   TmnxMobProfMbrRate,
    tmnxWlanGwGgsnQosDwnlinkGbrRate  TmnxMobProfGbrRate,
    tmnxWlanGwGgsnQosDwnlinkMbrRate  TmnxMobProfMbrRate,
    tmnxWlanGwGgsnQosArpValue        TmnxMobArpValue,
    tmnxWlanGwGgsnQosUplinkAmbr      TmnxWlanGwAmbr,
    tmnxWlanGwGgsnQosDwnlinkAmbr     TmnxWlanGwAmbr
}

tmnxWlanGwGgsnLastChanged        OBJECT-TYPE
    SYNTAX      TimeStamp
    MAX-ACCESS  read-only
    STATUS      current
    DESCRIPTION
        "The value of tmnxWlanGwGgsnLastChanged indicates the sysUpTime at the
         time of the most recent management-initiated change to this profile."
    ::= { tmnxWlanGwGgsnEntry 1 }

tmnxWlanGwGgsnQosUplinkGbrRate   OBJECT-TYPE
    SYNTAX      TmnxMobProfGbrRate
    UNITS       "kilobps"
    MAX-ACCESS  read-create
    STATUS      current
    DESCRIPTION
        "The value of tmnxWlanGwGgsnQosUplinkGbrRate specifies the uplink
         Guaranteed Bit Rate (GBR) to be used in the GTP messages as 'QOS IE'
         (for a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 5000 }
    ::= { tmnxWlanGwGgsnEntry 2 }

tmnxWlanGwGgsnQosUplinkMbrRate   OBJECT-TYPE
    SYNTAX      TmnxMobProfMbrRate
    UNITS       "kilobps"
    MAX-ACCESS  read-create
    STATUS      current
    DESCRIPTION
        "The value of tmnxWlanGwGgsnQosUplinkMbrRate specifies the uplink
         Maximum Bit Rate (MBR) to be used in the GTP messages as 'QOS IE' (for
         a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 5000 }
    ::= { tmnxWlanGwGgsnEntry 3 }

tmnxWlanGwGgsnQosDwnlinkGbrRate  OBJECT-TYPE
    SYNTAX      TmnxMobProfGbrRate
    UNITS       "kilobps"
    MAX-ACCESS  read-create
    STATUS      current
    DESCRIPTION
        "The value of tmnxWlanGwGgsnQosDwnlinkGbrRate specifies the downlink
         Guaranteed Bit Rate (GBR) to be used in the GTP messages as 'QOS IE'
         (for a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 2000 }
    ::= { tmnxWlanGwGgsnEntry 4 }

tmnxWlanGwGgsnQosDwnlinkMbrRate  OBJECT-TYPE
    SYNTAX      TmnxMobProfMbrRate
    UNITS       "kilobps"
    MAX-ACCESS  read-create
    STATUS      current
    DESCRIPTION
        "The value of tmnxWlanGwGgsnQosDwnlinkMbrRate specifies the downlink
         Maximum Bit Rate (MBR) to be used in the GTP messages as 'QOS IE' (for
         a Gn interface) or 'Bearer QOS' (for an S2a/S2b interface)."
    REFERENCE
        "3GPP TS 29.060, section 7.7.34 Quality of Service (QoS) Profile

         3GPP TS 129 274, section 8.15 Bearer Quality of Service (Bearer QoS)"
    DEFVAL      { 2000 }
    ::= { tmnxWlanGwGgsnEntry 5 }

tmnxWlanGwGgsnQosArpValue        OBJECT-TYPE
    SYNTAX      TmnxMobArpValue (1..3)
    MAX-ACCESS  read-create
    STATUS      current
    DESCRIPTION
        "The value of tmnxWlanGwGgsnQosArpValue specifies the admission control
         to prioritize allocation and retention for bearer establishment and
         modification."
    REFERENCE
        "3GPP TS 29.060, section 7.7.34 Quality of Service (QoS) Profile

         3GPP TS 129 274, section 8.15 Bearer Quality of Service (Bearer QoS)

         3GPP TS 23.107 Table 5 Note 1"
    DEFVAL      { 1 }
    ::= { tmnxWlanGwGgsnEntry 6 }

tmnxWlanGwGgsnQosUplinkAmbr      OBJECT-TYPE
    SYNTAX      TmnxWlanGwAmbr
    UNITS       "kilobps"
    MAX-ACCESS  read-create
    STATUS      current
    DESCRIPTION
        "The value of tmnxWlanGwGgsnQosUplinkAmbr specifies the uplink
         Aggregated Maximum Bit Rate (AMBR) to be used in the GTP messages as
         'APN-AMBR IE'.

         While the value of tmnxWlanGwGgsnQosUplinkAmbr is equal to minus two,
         this system does not transmit the 'APN-AMBR IE'.

         The values of tmnxWlanGwGgsnQosUplinkAmbr and
         tmnxWlanGwGgsnQosDwnlinkAmbr must be either both equal to minus two,
         or both different from minus two."
    DEFVAL      { -2 }
    ::= { tmnxWlanGwGgsnEntry 7 }

tmnxWlanGwGgsnQosDwnlinkAmbr     OBJECT-TYPE
    SYNTAX      TmnxWlanGwAmbr
    UNITS       "kilobps"
    MAX-ACCESS  read-create
    STATUS      current
    DESCRIPTION
        "The value of tmnxWlanGwGgsnQosDwnlinkAmbr specifies the downlink
         Aggregated Maximum Bit Rate (AMBR) to be used in the GTP messages as
         'APN-AMBR IE'.

         While the value of tmnxWlanGwGgsnQosDwnlinkAmbr is equal to minus two,
         this system does not transmit the 'APN-AMBR IE'.

         The values of tmnxWlanGwGgsnQosUplinkAmbr and
         tmnxWlanGwGgsnQosDwnlinkAmbr must be either both equal to minus two,
         or both different from minus two."
    DEFVAL      { -2 }
    ::= { tmnxWlanGwGgsnEntry 8 }

tmnxWlanGwMmeTable               OBJECT-TYPE
    SYNTAX      SEQUENCE OF TmnxWlanGwMmeEntry
    MAX-ACCESS  not-accessible
    STATUS      current
    DESCRIPTION
        "The tmnxWlanGwMmeTable allows configuration of how to communicate with
         the Mobility Management Entity (MME)."
    ::= { tmnxWlanGwMgwObjs 22 }

tmnxWlanGwMmeEntry               OBJECT-TYPE
    SYNTAX      TmnxWlanGwMmeEntry
    MAX-ACCESS  not-accessible
    STATUS      current
    DESCRIPTION
        "Each entry represents the configuration for a specific Mobility
         Management Entity (MME).

         Entries in this table are created and destroyed automatically by the
         system."
    AUGMENTS    { tmnxWlanGwMgwProfEntry }
    ::= { tmnxWlanGwMmeTable 1 }

TmnxWlanGwMmeEntry               ::= SEQUENCE
{
    tmnxWlanGwMmeLastChanged         TimeStamp,
    tmnxWlanGwMmeQosUplinkGbrRate    TmnxMobProfGbrRate,
    tmnxWlanGwMmeQosUplinkMbrRate    TmnxMobProfMbrRate,
    tmnxWlanGwMmeQosDwnlinkGbrRate   TmnxMobProfGbrRate,
    tmnxWlanGwMmeQosDwnlinkMbrRate   TmnxMobProfMbrRate,
    tmnxWlanGwMmeQosArpValue         TmnxMobArpValue,
    tmnxWlanGwMmeQosQciValue         TmnxMobQciValue,
    tmnxWlanGwMmeQosUplinkAmbr       TmnxWlanGwAmbr,
    tmnxWlanGwMmeQosDwnlinkAmbr      TmnxWlanGwAmbr
}

tmnxWlanGwMmeLastChanged         OBJECT-TYPE
    SYNTAX      TimeStamp
    MAX-ACCESS  read-only
    STATUS      current
    DESCRIPTION
        "The value of tmnxWlanGwMmeLastChanged indicates the sysUpTime at the
         time of the most recent management-initiated change to this profile."
    ::= { tmnxWlanGwMmeEntry 1 }

tmnxWlanGwMmeQosUplinkGbrRate    OBJECT-TYPE
    SYNTAX      TmnxMobProfGbrRate
    UNITS       "kilobps"
    MAX-ACCESS  read-create
    STATUS      current
    DESCRIPTION
        "The value of tmnxWlanGwMmeQosUplinkGbrRate specifies the uplink
         Guaranteed Bit Rate (GBR) to be used in the GTP messages as 'QOS IE'
         or 'Bearer QOS'."
    REFERENCE
        "3GPP TS 29.060, section 7.7.34 Quality of Service (QoS) Profile

         3GPP TS 129 274, section 8.15 Bearer Quality of Service (Bearer QoS)"
    DEFVAL      { 0 }
    ::= { tmnxWlanGwMmeEntry 2 }

tmnxWlanGwMmeQosUplinkMbrRate    OBJECT-TYPE
    SYNTAX      TmnxMobProfMbrRate
    UNITS       "kilobps"
    MAX-ACCESS  read-create
    STATUS      current
    DESCRIPTION
        "The value of tmnxWlanGwMmeQosUplinkMbrRate specifies the uplink
         Maximum Bit Rate (MBR) to be used in the GTP messages as 'QOS IE' or
         'Bearer QOS'."
    REFERENCE
        "3GPP TS 29.060, section 7.7.34 Quality of Service (QoS) Profile

         3GPP TS 129 274, section 8.15 Bearer Quality of Service (Bearer QoS)"
    DEFVAL      { 0 }
    ::= { tmnxWlanGwMmeEntry 3 }

tmnxWlanGwMmeQosDwnlinkGbrRate   OBJECT-TYPE
    SYNTAX      TmnxMobProfGbrRate
    UNITS       "kilobps"
    MAX-ACCESS  read-create
    STATUS      current
    DESCRIPTION
        "The value of tmnxWlanGwMmeQosDwnlinkGbrRate specifies the downlink
         Guaranteed Bit Rate (GBR) to be used in the GTP messages as 'QOS IE'
         or 'Bearer QOS'."
    REFERENCE
        "3GPP TS 29.060, section 7.7.34 Quality of Service (QoS) Profile

         3GPP TS 129 274, section 8.15 Bearer Quality of Service (Bearer QoS)"
    DEFVAL      { 0 }
    ::= { tmnxWlanGwMmeEntry 4 }

tmnxWlanGwMmeQosDwnlinkMbrRate   OBJECT-TYPE
    SYNTAX      TmnxMobProfMbrRate
    UNITS       "kilobps"
    MAX-ACCESS  read-create
    STATUS      current
    DESCRIPTION
        "The value of tmnxWlanGwMmeQosDwnlinkMbrRate specifies the downlink
         Maximum Bit Rate (MBR) to be used in the GTP messages as 'QOS IE' or
         'Bearer QOS'."
    REFERENCE
        "3GPP TS 29.060, section 7.7.34 Quality of Service (QoS) Profile

         3GPP TS 129 274, section 8.15 Bearer Quality of Service (Bearer QoS)"
    DEFVAL      { 0 }
    ::= { tmnxWlanGwMmeEntry 5 }

tmnxWlanGwMmeQosArpValue         OBJECT-TYPE
    SYNTAX      TmnxMobArpValue
    MAX-ACCESS  read-create
    STATUS      current
    DESCRIPTION
        "The value of tmnxWlanGwMmeQosArpValue specifies the
         allocation/retention priority to be used in the GTP messages as 'QOS
         IE' or 'Bearer QOS'."
    REFERENCE
        "3GPP TS 29.060, section 7.7.34 Quality of Service (QoS) Profile

         3GPP TS 129 274, section 8.15 Bearer Quality of Service (Bearer QoS)"
    DEFVAL      { 1 }
    ::= { tmnxWlanGwMmeEntry 6 }

tmnxWlanGwMmeQosQciValue         OBJECT-TYPE
    SYNTAX      TmnxMobQciValue
    MAX-ACCESS  read-create
    STATUS      current
    DESCRIPTION
        "The value of tmnxWlanGwMmeQosQciValue specifies the QoS Class
         Identifier (QCI) value to be used in the GTP messages as 'QOS IE' or
         'Bearer QOS'."
    REFERENCE
        "3GPP TS 29.060, section 7.7.34 Quality of Service (QoS) Profile

         3GPP TS 129.274, section 8.15 Bearer Quality of Service (Bearer QoS)

         3GPP TS 23.203, section 6.5 Quality of Service Control rule"
    DEFVAL      { 8 }
    ::= { tmnxWlanGwMmeEntry 7 }

tmnxWlanGwMmeQosUplinkAmbr       OBJECT-TYPE
    SYNTAX      TmnxWlanGwAmbr
    UNITS       "kilobps"
    MAX-ACCESS  read-create
    STATUS      current
    DESCRIPTION
        "The value of tmnxWlanGwMmeQosUplinkAmbr specifies the uplink
         Aggregated Maximum Bit Rate (AMBR) to be used in the GTP messages as
         'AMBR IE'.

         The value minus two is not allowed."
    DEFVAL      { 10000 }
    ::= { tmnxWlanGwMmeEntry 8 }

tmnxWlanGwMmeQosDwnlinkAmbr      OBJECT-TYPE
    SYNTAX      TmnxWlanGwAmbr
    UNITS       "kilobps"
    MAX-ACCESS  read-create
    STATUS      current
    DESCRIPTION
        "The value of tmnxWlanGwMmeQosDwnlinkAmbr specifies the downlink
         Aggregated Maximum Bit Rate (AMBR) to be used in the GTP messages as
         'AMBR IE'.

         The value minus two is not allowed."
    DEFVAL      { 20000 }
    ::= { tmnxWlanGwMmeEntry 9 }

tmnxWlanGwSysCfgObjs             OBJECT IDENTIFIER ::= { tmnxWlanGwObjs 7 }

tmnxWlanGwSysCfgServingNwMcc     OBJECT-TYPE
    SYNTAX      TmnxMobMccOrEmpty
    MAX-ACCESS  read-write
    STATUS      current
    DESCRIPTION
        "The value of tmnxWlanGwSysCfgServingNwMcc specifies the Mobile Country
         Code (MCC) portion of the Serving Network."
    DEFVAL      { ''H }
    ::= { tmnxWlanGwSysCfgObjs 1 }

tmnxWlanGwSysCfgServingNwMnc     OBJECT-TYPE
    SYNTAX      TmnxMobMncOrEmpty
    MAX-ACCESS  read-write
    STATUS      current
    DESCRIPTION
        "The value of tmnxWlanGwSysCfgServingNwMnc specifies the Mobile Network
         Code (MNC) portion of the Serving Network."
    DEFVAL      { ''H }
    ::= { tmnxWlanGwSysCfgObjs 2 }

tmnxWlanGwSysCfgMgwMaxHeldSe     OBJECT-TYPE
    SYNTAX      Unsigned32 (0..500000)
    MAX-ACCESS  read-write
    STATUS      current
    DESCRIPTION
        "The value of tmnxWlanGwSysCfgMgwMaxHeldSe specifies the maximum number
         of GTP session contexts held in the system while their UEs are
         disconnected.

         Refer also to the object tmnxWlanGwMgwProfSeHoldTime.

         The held session contexts are kept in a First-In-First-Out (FIFO)
         storage: when a new session is added to the storage and the number of
         held sessions reaches the value of tmnxWlanGwSysCfgMgwMaxHeldSe, the
         session context being held the longest time is cleared."
    DEFVAL      { 2000 }
    ::= { tmnxWlanGwSysCfgObjs 5 }

tmnxWlanGwSysCfgVirtChassisId    OBJECT-TYPE
    SYNTAX      DisplayString (SIZE (0..16))
    MAX-ACCESS  read-write
    STATUS      current
    DESCRIPTION
        "The value of tmnxWlanGwSysCfgVirtChassisId specifies the virtual
         chassis identifier or dual homing key which links two WLAN-GWs
         together."
    DEFVAL      { "" }
    ::= { tmnxWlanGwSysCfgObjs 15 }

tmnxWlanGwTable                  OBJECT-TYPE
    SYNTAX      SEQUENCE OF TmnxWlanGwEntry
    MAX-ACCESS  not-accessible
    STATUS      current
    DESCRIPTION
        "The tmnxWlanGwTable allows configuration of WLAN Gateway functions in
         a virtual router instance."
    ::= { tmnxWlanGwObjs 8 }

tmnxWlanGwEntry                  OBJECT-TYPE
    SYNTAX      TmnxWlanGwEntry
    MAX-ACCESS  not-accessible
    STATUS      current
    DESCRIPTION
        "Each entry represents the configuration for WLAN Gateway functions in
         a particular virtual router instance.

         Entries in this table can be created and deleted via SNMP SET
         operations to tmnxWlanGwRowStatus.

         A corresponding row in the TIMETRA-VRTR-MIB::vRtrConfTable must exist
         in order to create a row in this table."
    INDEX       { vRtrID }
    ::= { tmnxWlanGwTable 1 }

TmnxWlanGwEntry                  ::= SEQUENCE
{
    tmnxWlanGwRowStatus              RowStatus,
    tmnxWlanGwLastCh                 TimeStamp,
    tmnxWlanGwApn                    TmnxMobApnOrZero,
    tmnxWlanGwMobAcctInterimUpdate   TmnxEnabledDisabled,
    tmnxWlanGwPdnType                INTEGER,
    tmnxWlanGwMobAcctIntUpdtInclCnts TruthValue,
    tmnxWlanGwMobAcctIntUpdtHoldDown Unsigned32
}

tmnxWlanGwRowStatus              OBJECT-TYPE
    SYNTAX      RowStatus
    MAX-ACCESS  read-create
    STATUS      current
    DESCRIPTION
        "The value of tmnxWlanGwRowStatus controls the creation and deletion of
         rows in the table."
    ::= { tmnxWlanGwEntry 1 }

tmnxWlanGwLastCh                 OBJECT-TYPE
    SYNTAX      TimeStamp
    MAX-ACCESS  read-only
    STATUS      current
    DESCRIPTION
        "The value of tmnxWlanGwLastCh indicates the sysUpTime at the time of
         the most recent management-initiated change to this conceptual row."
    ::= { tmnxWlanGwEntry 2 }

tmnxWlanGwApn                    OBJECT-TYPE
    SYNTAX      TmnxMobApnOrZero (SIZE (0..80))
    MAX-ACCESS  read-create
    STATUS      current
    DESCRIPTION
        "The value of tmnxWlanGwApn specifies the Network Identifier part of
         the Access Point Name (APN) to be used for UE in this virtual router
         instance if the APN cannot be determined by other means."
    REFERENCE
        "3GPP TS 23.003,
         section 9.1.1 Format of APN Network Identifier"
    DEFVAL      { "" }
    ::= { tmnxWlanGwEntry 3 }

tmnxWlanGwMobAcctInterimUpdate   OBJECT-TYPE
    SYNTAX      TmnxEnabledDisabled
    MAX-ACCESS  read-create
    STATUS      current
    DESCRIPTION
        "The value of tmnxWlanGwMobAcctInterimUpdate specifies the
         administrative state of sending mobility-triggered accounting interim
         updates.

         While the value of the object tmnxWlanGwMobAcctInterimUpdate is equal
         to 'enabled', the system will send Interim-Update messages triggered
         by UE mobility."
    DEFVAL      { disabled }
    ::= { tmnxWlanGwEntry 10 }

tmnxWlanGwPdnType                OBJECT-TYPE
    SYNTAX      INTEGER {
        ipv4   (0),
        ipv6   (1),
        ipv4v6 (2)
    }
    MAX-ACCESS  read-create
    STATUS      current
    DESCRIPTION
        "The value of tmnxWlanGwPdnType specifies the default 3GPP-PDN type to
         be used for the UE in this virtual router instance if the 3GPP-PDN
         type could not be determined by other means."
    DEFVAL      { ipv4 }
    ::= { tmnxWlanGwEntry 11 }

tmnxWlanGwMobAcctIntUpdtInclCnts OBJECT-TYPE
    SYNTAX      TruthValue
    MAX-ACCESS  read-create
    STATUS      current
    DESCRIPTION
        "The value of tmnxWlanGwMobAcctIntUpdtInclCnts specifies whether or not
         an Interim-Update message triggered by UE mobility includes counters.

         When the value of this object is 'true (1)', the Interim-Update
         messages, triggered by UE mobility, include counters.

         The value of this object can only be set to 'true(1)' if the value of
         tmnxWlanGwMobAcctInterimUpdate is set to 'enabled (1)'."
    DEFVAL      { false }
    ::= { tmnxWlanGwEntry 12 }

tmnxWlanGwMobAcctIntUpdtHoldDown OBJECT-TYPE
    SYNTAX      Unsigned32 (0 | 60..86400)
    UNITS       "seconds"
    MAX-ACCESS  read-create
    STATUS      current
    DESCRIPTION
        "The value of tmnxWlanGwMobAcctIntUpdtHoldDown specifies the hold-down
         time for including counters in Interim-Update messages triggered by UE
         mobility.

         When the value of this object is set to a non-default value, the
         Interim-Update messages triggered by UE mobility are suppressed if the
         configured hold-time has not elapsed since we last sent Interim-Update
         messages triggered by UE mobility.

         The value of this object can only be set to a non-default value if the
         value of tmnxWlanGwMobAcctIntUpdtInclCnts is set to 'true (1)"
    DEFVAL      { 0 }
    ::= { tmnxWlanGwEntry 13 }

tmnxWlanGwDsmSubObjs             OBJECT IDENTIFIER ::= { tmnxWlanGwObjs 9 }

tmnxWlanGwVlanDsmTable           OBJECT-TYPE
    SYNTAX      SEQUENCE OF TmnxWlanGwVlanDsmEntry
    MAX-ACCESS  not-accessible
    STATUS      current
    DESCRIPTION
        "The tmnxWlanGwVlanDsmTable contains objects to configure Distributed
         Subscriber Management (DSM) for Soft GRE Group-Interfaces and for
         ranges of IEEE 802.1q VLAN tags in Soft GRE Group-Interfaces."
    ::= { tmnxWlanGwDsmSubObjs 1 }

tmnxWlanGwVlanDsmEntry           OBJECT-TYPE
    SYNTAX      TmnxWlanGwVlanDsmEntry
    MAX-ACCESS  not-accessible
    STATUS      current
    DESCRIPTION
        "Each conceptual row represents the set of Distributed subscriber
         management configuration data for a range of VLAN Q-tags on a
         particular interface, or for the interface itself.

         Users whose traffic comes in on this interface tagged with a matching
         VLAN Q-tag are to be processed according to the configuration
         specified in this conceptual row; otherwise, the default configuration
         specified in the default range [4096-4096] must be used.

         Rows in this table are created and destroyed automatically by the
         system.

         A single row in this table is always created by the system and cannot
         be destroyed: the default range [4096-4096]."
    AUGMENTS    { tmnxWlanGwVlanEntry }
    ::= { tmnxWlanGwVlanDsmTable 1 }

TmnxWlanGwVlanDsmEntry           ::= SEQUENCE
{
    tmnxWlanGwVlanDsmLastCh          TimeStamp,
    tmnxWlanGwVlanDsmAdminState      TmnxEnabledDisabled,
    tmnxWlanGwVlanDsmAcctPlcy        TNamedItemOrEmpty,
    tmnxWlanGwVlanDsmEgressPolicer   TNamedItemOrEmpty,
    tmnxWlanGwVlanDsmIngressPolicer  TNamedItemOrEmpty,
    tmnxWlanGwVlanDsmIpFilter        TNamedItemOrEmpty,
    tmnxWlanGwVlanDsmOneTimeRdrUrl   TmnxHttpRedirectUrl,
    tmnxWlanGwVlanDsmOneTimeRdrPort  Unsigned32,
    tmnxWlanGwVlanDsmAcctUpdInterv   Unsigned32,
    tmnxWlanGwVlanDsmDefAppProfile   TNamedItemOrEmpty,
    tmnxWlanGwVlanDsmAaAcctStats     TruthValue,
    tmnxWlanGwVlanDsmQuotaDirection  INTEGER,
    tmnxWlanGwVlanDsmQuotaExhFilter  TNamedItemOrEmpty,
    tmnxWlanGwVlanDsmAaHttpUrlParam  TmnxBsxAaSubHttpUrlParam
}

tmnxWlanGwVlanDsmLastCh          OBJECT-TYPE
    SYNTAX      TimeStamp
    MAX-ACCESS  read-only
    STATUS      current
    DESCRIPTION
        "The value of tmnxWlanGwVlanDsmLastCh indicates the sysUpTime at the
         time of the most recent management-initiated change to this table row."
    ::= { tmnxWlanGwVlanDsmEntry 1 }

tmnxWlanGwVlanDsmAdminState      OBJECT-TYPE
    SYNTAX      TmnxEnabledDisabled
    MAX-ACCESS  read-create
    STATUS      current
    DESCRIPTION
        "The value of tmnxWlanGwVlanDsmAdminState specifies the administrative
         state of Distributed subscriber management."
    DEFVAL      { disabled }
    ::= { tmnxWlanGwVlanDsmEntry 2 }

tmnxWlanGwVlanDsmAcctPlcy        OBJECT-TYPE
    SYNTAX      TNamedItemOrEmpty
    MAX-ACCESS  read-create
    STATUS      current
    DESCRIPTION
        "The value of tmnxWlanGwVlanDsmAcctPlcy specifies the identifier of the
         accounting policy.

         An entry with the same name must exist in the
         TIMETRA-RADIUS-MIB::tmnxRadIsaPlcyTable."
    DEFVAL      { "" }
    ::= { tmnxWlanGwVlanDsmEntry 3 }

tmnxWlanGwVlanDsmEgressPolicer   OBJECT-TYPE
    SYNTAX      TNamedItemOrEmpty
    MAX-ACCESS  read-create
    STATUS      current
    DESCRIPTION
        "The value of tmnxWlanGwVlanDsmEgressPolicer specifies the identifier
         of the distributed-sub-mgmt policer for egress traffic.

         An entry with the same name must exist in the tmnxWlanGwPolicerTable."
    DEFVAL      { "" }
    ::= { tmnxWlanGwVlanDsmEntry 4 }

tmnxWlanGwVlanDsmIngressPolicer  OBJECT-TYPE
    SYNTAX      TNamedItemOrEmpty
    MAX-ACCESS  read-create
    STATUS      current
    DESCRIPTION
        "The value of tmnxWlanGwVlanDsmIngressPolicer specifies the identifier
         of the distributed-sub-mgmt policer for ingress traffic.

         An entry with the same name must exist in the tmnxWlanGwDsmIpFilTable."
    DEFVAL      { "" }
    ::= { tmnxWlanGwVlanDsmEntry 5 }

tmnxWlanGwVlanDsmIpFilter        OBJECT-TYPE
    SYNTAX      TNamedItemOrEmpty
    MAX-ACCESS  read-create
    STATUS      current
    DESCRIPTION
        "The value of tmnxWlanGwVlanDsmIpFilter specifies the identifier of the
         distributed-sub-mgmt IP filter.

         A row with the same name must exist in the tmnxWlanGwDsmIpFilTable."
    DEFVAL      { "" }
    ::= { tmnxWlanGwVlanDsmEntry 6 }

tmnxWlanGwVlanDsmOneTimeRdrUrl   OBJECT-TYPE
    SYNTAX      TmnxHttpRedirectUrl
    MAX-ACCESS  read-create
    STATUS      current
    DESCRIPTION
        "The value of tmnxWlanGwVlanDsmOneTimeRdrUrl specifies the URL to
         redirect to.

         This string may contain a number of substitution macro's:
         - $URL: specifies that '$URL' must be substituted with the content of the
                 Request-URI in the HTTP GET Request received.

         - $MAC: specifies that '$MAC' must be replaced with a string that
                 represents the MAC address of the subscriber host;
                 the MAC address is formatted in Nokia SROS style,
                 like 00:0c:f1:99:85:b8.

         - $IP:  specifies that '$IP' must be replaced with a string that represents
                 the IP address of the subscriber host."
    DEFVAL      { ''H }
    ::= { tmnxWlanGwVlanDsmEntry 7 }

tmnxWlanGwVlanDsmOneTimeRdrPort  OBJECT-TYPE
    SYNTAX      Unsigned32 (1..65535)
    MAX-ACCESS  read-create
    STATUS      current
    DESCRIPTION
        "The value of tmnxWlanGwVlanDsmOneTimeRdrPort specifies the destination
         port for redirected HTTP protocol packets."
    DEFVAL      { 80 }
    ::= { tmnxWlanGwVlanDsmEntry 8 }

tmnxWlanGwVlanDsmAcctUpdInterv   OBJECT-TYPE
    SYNTAX      Unsigned32 (0 | 5..259200)
    UNITS       "minutes"
    MAX-ACCESS  read-create
    STATUS      current
    DESCRIPTION
        "The value of tmnxWlanGwVlanDsmAcctUpdInterv specifies the time
         interval between consecutive Interim Accounting Update messages.

         The value zero specifies that the system does not send Interim
         Accounting Update messages."
    REFERENCE
        "RFC 2866 RADIUS Accounting
         section 5.1 Acct-Status-Type.

         RFC 2869 RADIUS Extensions
         section 2.1.  RADIUS support for Interim Accounting Updates."
    DEFVAL      { 0 }
    ::= { tmnxWlanGwVlanDsmEntry 9 }

tmnxWlanGwVlanDsmDefAppProfile   OBJECT-TYPE
    SYNTAX      TNamedItemOrEmpty
    MAX-ACCESS  read-create
    STATUS      current
    DESCRIPTION
        "The value of tmnxWlanGwVlanDsmDefAppProfile specifies the identifier
         of the default application profile.

         A row with the same name must exist in the
         TIMETRA-BSX-NG-MIB::tmnxBsxAppProfTable."
    DEFVAL      { "" }
    ::= { tmnxWlanGwVlanDsmEntry 10 }

tmnxWlanGwVlanDsmAaAcctStats     OBJECT-TYPE
    SYNTAX      TruthValue
    MAX-ACCESS  read-create
    STATUS      current
    DESCRIPTION
        "The value of tmnxWlanGwVlanDsmAaAcctStats specifies if Application
         Assurance accounting statistics are collected."
    DEFVAL      { false }
    ::= { tmnxWlanGwVlanDsmEntry 11 }

tmnxWlanGwVlanDsmQuotaDirection  OBJECT-TYPE
    SYNTAX      INTEGER {
        both    (0),
        ingress (1),
        egress  (2)
    }
    MAX-ACCESS  read-create
    STATUS      current
    DESCRIPTION
        "The value of tmnxWlanGwVlanDsmQuotaDirection specifies whether volume
         quota are applied in the egress (downstream), ingress (upstream), or
         both direction(s)."
    DEFVAL      { both }
    ::= { tmnxWlanGwVlanDsmEntry 12 }

tmnxWlanGwVlanDsmQuotaExhFilter  OBJECT-TYPE
    SYNTAX      TNamedItemOrEmpty
    MAX-ACCESS  read-create
    STATUS      current
    DESCRIPTION
        "The value of tmnxWlanGwVlanDsmQuotaExhFilter specifies the identifier
         of the distributed-sub-mgmt IP filter to be applied when soft volume
         quota is reached. This filter replaces the currently applied filter
         for the UE upon quota exhaustion. If quota is extended the filter will
         automatically be reverted.

         A row with the same name must exist in the tmnxWlanGwDsmIpFilTable."
    DEFVAL      { "" }
    ::= { tmnxWlanGwVlanDsmEntry 13 }

tmnxWlanGwVlanDsmAaHttpUrlParam  OBJECT-TYPE
    SYNTAX      TmnxBsxAaSubHttpUrlParam
    MAX-ACCESS  read-create
    STATUS      current
    DESCRIPTION
        "The value of tmnxWlanGwVlanDsmAaHttpUrlParam specifies an optional
         text string to customize the URL used for Application Assurance HTTP
         In-Browser Notification."
    DEFVAL      { "" }
    ::= { tmnxWlanGwVlanDsmEntry 14 }

tmnxWlanGwDsmIpFilTable          OBJECT-TYPE
    SYNTAX      SEQUENCE OF TmnxWlanGwDsmIpFilEntry
    MAX-ACCESS  not-accessible
    STATUS      current
    DESCRIPTION
        "The tmnxWlanGwDsmIpFilTable allows configuration of IP filters
         distributed on ISA cards for DSM subscribers."
    ::= { tmnxWlanGwDsmSubObjs 2 }

tmnxWlanGwDsmIpFilEntry          OBJECT-TYPE
    SYNTAX      TmnxWlanGwDsmIpFilEntry
    MAX-ACCESS  not-accessible
    STATUS      current
    DESCRIPTION
        "Each conceptual row represents the configuration for a specific
         distributed-sub-mgmt IP filter.

         Rows in this table can be created and deleted via SNMP SET operations
         to tmnxWlanGwDsmIpFilRowStatus."
    INDEX       { IMPLIED tmnxWlanGwDsmIpFilName }
    ::= { tmnxWlanGwDsmIpFilTable 1 }

TmnxWlanGwDsmIpFilEntry          ::= SEQUENCE
{
    tmnxWlanGwDsmIpFilName           TNamedItem,
    tmnxWlanGwDsmIpFilRowStatus      RowStatus,
    tmnxWlanGwDsmIpFilLastCh         TimeStamp,
    tmnxWlanGwDsmIpFilDescription    TItemDescription,
    tmnxWlanGwDsmIpFilDefaultAction  TmnxWlanGwDsmFilterDefaultAction,
    tmnxWlanGwDsmIpFilDefaultAction6 TmnxWlanGwDsmFilterDefaultAction,
    tmnxWlanGwDsmIpFilType           INTEGER
}

tmnxWlanGwDsmIpFilName           OBJECT-TYPE
    SYNTAX      TNamedItem
    MAX-ACCESS  not-accessible
    STATUS      current
    DESCRIPTION
        "The value of tmnxWlanGwDsmIpFilName specifies the identifier of this
         distributed-sub-mgmt IP filter."
    ::= { tmnxWlanGwDsmIpFilEntry 1 }

tmnxWlanGwDsmIpFilRowStatus      OBJECT-TYPE
    SYNTAX      RowStatus
    MAX-ACCESS  read-create
    STATUS      current
    DESCRIPTION
        "The value of tmnxWlanGwDsmIpFilRowStatus controls the creation and
         deletion of rows in the table."
    ::= { tmnxWlanGwDsmIpFilEntry 2 }

tmnxWlanGwDsmIpFilLastCh         OBJECT-TYPE
    SYNTAX      TimeStamp
    MAX-ACCESS  read-only
    STATUS      current
    DESCRIPTION
        "The value of tmnxWlanGwDsmIpFilLastCh indicates the sysUpTime at the
         time of the most recent management-initiated change to this policy."
    ::= { tmnxWlanGwDsmIpFilEntry 3 }

tmnxWlanGwDsmIpFilDescription    OBJECT-TYPE
    SYNTAX      TItemDescription
    MAX-ACCESS  read-create
    STATUS      current
    DESCRIPTION
        "The value of tmnxWlanGwDsmIpFilDescription specifies the user provided
         description of this subscriber ISA RADIUS policy."
    DEFVAL      { "" }
    ::= { tmnxWlanGwDsmIpFilEntry 4 }

tmnxWlanGwDsmIpFilDefaultAction  OBJECT-TYPE
    SYNTAX      TmnxWlanGwDsmFilterDefaultAction
    MAX-ACCESS  read-create
    STATUS      current
    DESCRIPTION
        "The value of tmnxWlanGwDsmIpFilDefaultAction specifies for IPv4 the
         action to take for a packet that does not match any of the filter
         entries of this filter."
    DEFVAL      { drop }
    ::= { tmnxWlanGwDsmIpFilEntry 5 }

tmnxWlanGwDsmIpFilDefaultAction6 OBJECT-TYPE
    SYNTAX      TmnxWlanGwDsmFilterDefaultAction
    MAX-ACCESS  read-create
    STATUS      current
    DESCRIPTION
        "The value of tmnxWlanGwDsmIpFilDefaultAction6 specifies for IPv6 the
         action to take for a packet that does not match any of the filter
         entries of this filter."
    DEFVAL      { drop }
    ::= { tmnxWlanGwDsmIpFilEntry 6 }

tmnxWlanGwDsmIpFilType           OBJECT-TYPE
    SYNTAX      INTEGER {
        dsm       (0),
        reserved1 (1)
    }
    MAX-ACCESS  read-create
    STATUS      current
    DESCRIPTION
        "The value of tmnxWlanGwDsmIpFilType specifies  the type of ISA filter.

         A value for this object must be specified when the conceptual row is
         created.

         The value of this object can not be modified  while this conceptual
         row exists."
    ::= { tmnxWlanGwDsmIpFilEntry 7 }

tmnxWlanGwDsmIpFilN3Table        OBJECT-TYPE
    SYNTAX      SEQUENCE OF TmnxWlanGwDsmIpFilN3Entry
    MAX-ACCESS  not-accessible
    STATUS      current
    DESCRIPTION
        "The tmnxWlanGwDsmIpFilN3Table allows configuration of
         distributed-sub-mgmt IP filter entries."
    ::= { tmnxWlanGwDsmSubObjs 3 }

tmnxWlanGwDsmIpFilN3Entry        OBJECT-TYPE
    SYNTAX      TmnxWlanGwDsmIpFilN3Entry
    MAX-ACCESS  not-accessible
    STATUS      current
    DESCRIPTION
        "Each row represents the configuration for a particular filter entry of
         a distributed-sub-mgmt IP filter.

         Each row contains match criteria and the action to take for matching
         packets.

         Rows in this table can be created and deleted via SNMP SET operations
         to tmnxWlanGwDsmIpFilN3RowStatus."
    INDEX       {
        tmnxWlanGwDsmIpFilName,
        tmnxWlanGwDsmIpFilN3Index
    }
    ::= { tmnxWlanGwDsmIpFilN3Table 1 }

TmnxWlanGwDsmIpFilN3Entry        ::= SEQUENCE
{
    tmnxWlanGwDsmIpFilN3Index        Unsigned32,
    tmnxWlanGwDsmIpFilN3RowStatus    RowStatus,
    tmnxWlanGwDsmIpFilN3LastCh       TimeStamp,
    tmnxWlanGwDsmIpFilN3Description  TItemDescription,
    tmnxWlanGwDsmIpFilN3Action       TmnxWlanGwDsmFilterAction,
    tmnxWlanGwDsmIpFilN3Protocol     TIpProtocol,
    tmnxWlanGwDsmIpFilN3DestAddrType InetAddressType,
    tmnxWlanGwDsmIpFilN3DestAddr     InetAddress,
    tmnxWlanGwDsmIpFilN3DestPrefLen  InetAddressPrefixLength,
    tmnxWlanGwDsmIpFilN3DestPortOp   INTEGER,
    tmnxWlanGwDsmIpFilN3DestPort1    InetPortNumber,
    tmnxWlanGwDsmIpFilN3IngHitCount  Counter64,
    tmnxWlanGwDsmIpFilN3RedirectURL  TmnxHttpRedirectUrl
}

tmnxWlanGwDsmIpFilN3Index        OBJECT-TYPE
    SYNTAX      Unsigned32 (1..1024)
    MAX-ACCESS  not-accessible
    STATUS      current
    DESCRIPTION
        "The value of tmnxWlanGwDsmIpFilN3Index specifies the index of this
         filter entry."
    ::= { tmnxWlanGwDsmIpFilN3Entry 1 }

tmnxWlanGwDsmIpFilN3RowStatus    OBJECT-TYPE
    SYNTAX      RowStatus
    MAX-ACCESS  read-create
    STATUS      current
    DESCRIPTION
        "The value of tmnxWlanGwDsmIpFilN3RowStatus controls the creation and
         deletion of rows in the table."
    ::= { tmnxWlanGwDsmIpFilN3Entry 2 }

tmnxWlanGwDsmIpFilN3LastCh       OBJECT-TYPE
    SYNTAX      TimeStamp
    MAX-ACCESS  read-only
    STATUS      current
    DESCRIPTION
        "The value tmnxWlanGwDsmIpFilN3LastCh indicates the sysUpTime at the
         time of the most recent management-initiated change to this conceptual
         row."
    ::= { tmnxWlanGwDsmIpFilN3Entry 3 }

tmnxWlanGwDsmIpFilN3Description  OBJECT-TYPE
    SYNTAX      TItemDescription
    MAX-ACCESS  read-create
    STATUS      current
    DESCRIPTION
        "The value of tmnxWlanGwDsmIpFilN3Description specifies the user
         provided description of this IP filter entry."
    DEFVAL      { "" }
    ::= { tmnxWlanGwDsmIpFilN3Entry 4 }

tmnxWlanGwDsmIpFilN3Action       OBJECT-TYPE
    SYNTAX      TmnxWlanGwDsmFilterAction
    MAX-ACCESS  read-create
    STATUS      current
    DESCRIPTION
        "The value of the object tmnxWlanGwDsmIpFilN3Action specifies the
         action to take for packets that match this filter entry."
    DEFVAL      { none }
    ::= { tmnxWlanGwDsmIpFilN3Entry 5 }

tmnxWlanGwDsmIpFilN3Protocol     OBJECT-TYPE
    SYNTAX      TIpProtocol
    MAX-ACCESS  read-create
    STATUS      current
    DESCRIPTION
        "The value of the object tmnxWlanGwDsmIpFilN3Protocol specifies the IP
         protocol to match.

         The value minus one specifies no IP protocol matching."
    DEFVAL      { -1 }
    ::= { tmnxWlanGwDsmIpFilN3Entry 6 }

tmnxWlanGwDsmIpFilN3DestAddrType OBJECT-TYPE
    SYNTAX      InetAddressType
    MAX-ACCESS  read-create
    STATUS      current
    DESCRIPTION
        "The value of tmnxWlanGwDsmIpFilN3DestAddrType specifies the address
         type of tmnxWlanGwDsmIpFilN3DestAddr.

         The values  supported are 'unknown' and 'ipv4'."
    DEFVAL      { unknown }
    ::= { tmnxWlanGwDsmIpFilN3Entry 7 }

tmnxWlanGwDsmIpFilN3DestAddr     OBJECT-TYPE
    SYNTAX      InetAddress (SIZE (0|4))
    MAX-ACCESS  read-create
    STATUS      current
    DESCRIPTION
        "The value of tmnxWlanGwDsmIpFilN3DestAddr specifies the IP address of
         the destination prefix to match."
    DEFVAL      { ''H }
    ::= { tmnxWlanGwDsmIpFilN3Entry 8 }

tmnxWlanGwDsmIpFilN3DestPrefLen  OBJECT-TYPE
    SYNTAX      InetAddressPrefixLength (0..32)
    MAX-ACCESS  read-create
    STATUS      current
    DESCRIPTION
        "The value of tmnxWlanGwDsmIpFilN3DestPrefLen specifies the length of
         the destination prefix to match."
    DEFVAL      { 0 }
    ::= { tmnxWlanGwDsmIpFilN3Entry 9 }

tmnxWlanGwDsmIpFilN3DestPortOp   OBJECT-TYPE
    SYNTAX      INTEGER {
        none (0),
        eq   (1)
    }
    MAX-ACCESS  read-create
    STATUS      current
    DESCRIPTION
        "The value of the object tmnxWlanGwDsmIpFilN3DestPortOp specifies the
         operation to perform on the object tmnxWlanGwDsmIpFilN3DestPort1."
    DEFVAL      { none }
    ::= { tmnxWlanGwDsmIpFilN3Entry 10 }

tmnxWlanGwDsmIpFilN3DestPort1    OBJECT-TYPE
    SYNTAX      InetPortNumber
    MAX-ACCESS  read-create
    STATUS      current
    DESCRIPTION
        "The value of this object specifies the value to compare with the
         destination port in each packet, according to the value of the object
         tmnxWlanGwDsmIpFilN3DestPortOp."
    DEFVAL      { 0 }
    ::= { tmnxWlanGwDsmIpFilN3Entry 11 }

tmnxWlanGwDsmIpFilN3IngHitCount  OBJECT-TYPE
    SYNTAX      Counter64
    MAX-ACCESS  read-only
    STATUS      current
    DESCRIPTION
        "This object indicates the number of times an ingress packet matched
         this entry."
    ::= { tmnxWlanGwDsmIpFilN3Entry 17 }

tmnxWlanGwDsmIpFilN3RedirectURL  OBJECT-TYPE
    SYNTAX      TmnxHttpRedirectUrl
    MAX-ACCESS  read-create
    STATUS      current
    DESCRIPTION
        "The value of tmnxWlanGwDsmIpFilN3RedirectURL specifies the URL to
         redirect to, when the value of tmnxWlanGwDsmIpFilN3Action is
         'httpRedirect'.

         This string may contain a number of substitution macro's:
         - $URL: specifies that '$URL' must be substituted with the content of the
                 Request-URI in the HTTP GET Request received.

         - $MAC: specifies that '$MAC' must be replaced with a string that
                 represents the MAC address of the subscriber host;
                 the MAC address is formatted in Nokia SROS style,
                 like 00:0c:f1:99:85:b8.

         - $IP:  specifies that '$IP' must be replaced with a string that represents
                 the IP address of the subscriber host.

         Note that the value of tmnxWlanGwDsmIpFilN3RedirectURL is silently
         cleared by the system if tmnxWlanGwDsmIpFilN3Action is set to any
         value other than httpRedirect."
    DEFVAL      { ''H }
    ::= { tmnxWlanGwDsmIpFilN3Entry 18 }

tmnxWlanGwPolicerTable           OBJECT-TYPE
    SYNTAX      SEQUENCE OF TmnxWlanGwPolicerEntry
    MAX-ACCESS  not-accessible
    STATUS      current
    DESCRIPTION
        "The tmnxWlanGwPolicerTable allows configuration of traffic policer
         templates distributed on ISA cards for DSM subscribers."
    ::= { tmnxWlanGwDsmSubObjs 4 }

tmnxWlanGwPolicerEntry           OBJECT-TYPE
    SYNTAX      TmnxWlanGwPolicerEntry
    MAX-ACCESS  not-accessible
    STATUS      current
    DESCRIPTION
        "Each conceptual row represents the configuration for a specific
         distributed-sub-mgmt traffic policer template.

         Rows in this table can be created and deleted via SNMP SET operations
         to tmnxWlanGwPolicerRowStatus."
    INDEX       { IMPLIED tmnxWlanGwPolicerName }
    ::= { tmnxWlanGwPolicerTable 1 }

TmnxWlanGwPolicerEntry           ::= SEQUENCE
{
    tmnxWlanGwPolicerName            TNamedItem,
    tmnxWlanGwPolicerRowLastChange   TimeStamp,
    tmnxWlanGwPolicerRowStatus       RowStatus,
    tmnxWlanGwPolicerDescription     TItemDescription,
    tmnxWlanGwPolicerType            INTEGER,
    tmnxWlanGwPolicerAction          INTEGER,
    tmnxWlanGwPolicerAdminPIR        TPIRRate,
    tmnxWlanGwPolicerAdminCIR        TCIRRate,
    tmnxWlanGwPolicerMBS             TmnxWlanGwBurstSize,
    tmnxWlanGwPolicerCBS             TmnxWlanGwBurstSize,
    tmnxWlanGwPolicerPIRAdaptation   TAdaptationRule,
    tmnxWlanGwPolicerCIRAdaptation   TAdaptationRule
}

tmnxWlanGwPolicerName            OBJECT-TYPE
    SYNTAX      TNamedItem
    MAX-ACCESS  not-accessible
    STATUS      current
    DESCRIPTION
        "The value of tmnxWlanGwPolicerName specifies the name defined for the
         policer application."
    ::= { tmnxWlanGwPolicerEntry 1 }

tmnxWlanGwPolicerRowLastChange   OBJECT-TYPE
    SYNTAX      TimeStamp
    MAX-ACCESS  read-only
    STATUS      current
    DESCRIPTION
        "The value of tmnxWlanGwPolicerRowLastChange indicates the last time,
         since system startup, a successful set was performed on this row."
    ::= { tmnxWlanGwPolicerEntry 2 }

tmnxWlanGwPolicerRowStatus       OBJECT-TYPE
    SYNTAX      RowStatus
    MAX-ACCESS  read-create
    STATUS      current
    DESCRIPTION
        "The value of tmnxWlanGwPolicerRowStatus specifies the row status of
         this row."
    ::= { tmnxWlanGwPolicerEntry 3 }

tmnxWlanGwPolicerDescription     OBJECT-TYPE
    SYNTAX      TItemDescription
    MAX-ACCESS  read-create
    STATUS      current
    DESCRIPTION
        "The value of tmnxWlanGwPolicerDescription specifies the description of
         the policer."
    DEFVAL      { "" }
    ::= { tmnxWlanGwPolicerEntry 4 }

tmnxWlanGwPolicerType            OBJECT-TYPE
    SYNTAX      INTEGER {
        singleBucketBandwidth (0),
        dualBucketBandwidth   (1)
    }
    MAX-ACCESS  read-create
    STATUS      current
    DESCRIPTION
        "The value of tmnxWlanGwPolicerType specifies the number of buckets
         used by the policer.

         A value for this object must be specified when the conceptual row is
         created.

         The value of this object can not be modified while this conceptual row
         exists."
    ::= { tmnxWlanGwPolicerEntry 5 }

tmnxWlanGwPolicerAction          OBJECT-TYPE
    SYNTAX      INTEGER {
        permitDeny   (0),
        priorityMark (1)
    }
    MAX-ACCESS  read-create
    STATUS      current
    DESCRIPTION
        "The value of tmnxWlanGwPolicerAction specifies if the action taken by
         the policer is to permit or drop the packet or is to mark the
         packet(s) as in-profile or out-of-profile."
    DEFVAL      { permitDeny }
    ::= { tmnxWlanGwPolicerEntry 6 }

tmnxWlanGwPolicerAdminPIR        OBJECT-TYPE
    SYNTAX      TPIRRate
    UNITS       "kilobps"
    MAX-ACCESS  read-create
    STATUS      current
    DESCRIPTION
        "The value of tmnxWlanGwPolicerAdminPIR specifies the administrative
         PIR (Peak Information Rate)."
    DEFVAL      { -1 }
    ::= { tmnxWlanGwPolicerEntry 7 }

tmnxWlanGwPolicerAdminCIR        OBJECT-TYPE
    SYNTAX      TCIRRate
    UNITS       "kilobps"
    MAX-ACCESS  read-create
    STATUS      current
    DESCRIPTION
        "The value of tmnxWlanGwPolicerAdminCIR specifies the administrative
         CIR specified by the user."
    DEFVAL      { 0 }
    ::= { tmnxWlanGwPolicerEntry 8 }

tmnxWlanGwPolicerMBS             OBJECT-TYPE
    SYNTAX      TmnxWlanGwBurstSize
    UNITS       "kilobytes"
    MAX-ACCESS  read-create
    STATUS      current
    DESCRIPTION
        "The value of tmnxWlanGwPolicerMBS specifies the maximum burst size
         specified by the user to be used in conjunction with the PIR."
    DEFVAL      { 0 }
    ::= { tmnxWlanGwPolicerEntry 9 }

tmnxWlanGwPolicerCBS             OBJECT-TYPE
    SYNTAX      TmnxWlanGwBurstSize
    UNITS       "kilobytes"
    MAX-ACCESS  read-create
    STATUS      current
    DESCRIPTION
        "The value of tmnxWlanGwPolicerCBS specifies the committed burst size
         specified by the user to be used in conjunction with the CIR."
    DEFVAL      { 0 }
    ::= { tmnxWlanGwPolicerEntry 10 }

tmnxWlanGwPolicerPIRAdaptation   OBJECT-TYPE
    SYNTAX      TAdaptationRule
    MAX-ACCESS  read-create
    STATUS      current
    DESCRIPTION
        "The value of tmnxWlanGwPolicerPIRAdaptation specifies the adaptation
         rule to be used while computing the operational PIR value.

         The adaptation rule specifies the rules to compute the operational
         values while maintaining minimum offset."
    DEFVAL      { closest }
    ::= { tmnxWlanGwPolicerEntry 11 }

tmnxWlanGwPolicerCIRAdaptation   OBJECT-TYPE
    SYNTAX      TAdaptationRule
    MAX-ACCESS  read-create
    STATUS      current
    DESCRIPTION
        "The value of tmnxWlanGwPolicerCIRAdaptation specifies the adaptation
         rule to be used while computing the operational CIR value. The
         adaptation rule specifies the rules to compute the operational values
         while maintaining minimum offset."
    DEFVAL      { closest }
    ::= { tmnxWlanGwPolicerEntry 12 }

tmnxWlanGwDsmIpFil6N3Table       OBJECT-TYPE
    SYNTAX      SEQUENCE OF TmnxWlanGwDsmIpFil6N3Entry
    MAX-ACCESS  not-accessible
    STATUS      current
    DESCRIPTION
        "The tmnxWlanGwDsmIpFil6N3Table allows configuration of
         distributed-sub-mgmt IPv6 filter entries."
    ::= { tmnxWlanGwDsmSubObjs 8 }

tmnxWlanGwDsmIpFil6N3Entry       OBJECT-TYPE
    SYNTAX      TmnxWlanGwDsmIpFil6N3Entry
    MAX-ACCESS  not-accessible
    STATUS      current
    DESCRIPTION
        "Each row represents the configuration for a particular filter entry of
         a distributed-sub-mgmt IPv6 filter.

         Each row contains match criteria and the action to take for matching
         packets.

         Rows in this table can be created and deleted via SNMP SET operations
         to tmnxWlanGwDsmIpFil6N3RowStatus."
    INDEX       {
        tmnxWlanGwDsmIpFilName,
        tmnxWlanGwDsmIpFil6N3Index
    }
    ::= { tmnxWlanGwDsmIpFil6N3Table 1 }

TmnxWlanGwDsmIpFil6N3Entry       ::= SEQUENCE
{
    tmnxWlanGwDsmIpFil6N3Index       Unsigned32,
    tmnxWlanGwDsmIpFil6N3RowStatus   RowStatus,
    tmnxWlanGwDsmIpFil6N3LastCh      TimeStamp,
    tmnxWlanGwDsmIpFil6N3Description TItemDescription,
    tmnxWlanGwDsmIpFil6N3Action      TmnxWlanGwDsmFilterAction,
    tmnxWlanGwDsmIpFil6N3Protocol    TIpProtocol,
    tmnxWlanGwDsmIpFil6N3DestAddrTyp InetAddressType,
    tmnxWlanGwDsmIpFil6N3DestAddr    InetAddress,
    tmnxWlanGwDsmIpFil6N3DestPrefLen InetAddressPrefixLength,
    tmnxWlanGwDsmIpFil6N3DestPortOp  INTEGER,
    tmnxWlanGwDsmIpFil6N3DestPort1   InetPortNumber,
    tmnxWlanGwDsmIpFil6N3IngHitCount Counter64,
    tmnxWlanGwDsmIpFil6N3RedirectURL TmnxHttpRedirectUrl
}

tmnxWlanGwDsmIpFil6N3Index       OBJECT-TYPE
    SYNTAX      Unsigned32 (1..1024)
    MAX-ACCESS  not-accessible
    STATUS      current
    DESCRIPTION
        "The value of tmnxWlanGwDsmIpFil6N3Index specifies the index of this
         filter entry."
    ::= { tmnxWlanGwDsmIpFil6N3Entry 1 }

tmnxWlanGwDsmIpFil6N3RowStatus   OBJECT-TYPE
    SYNTAX      RowStatus
    MAX-ACCESS  read-create
    STATUS      current
    DESCRIPTION
        "The value of tmnxWlanGwDsmIpFil6N3RowStatus controls the creation and
         deletion of rows in the table."
    ::= { tmnxWlanGwDsmIpFil6N3Entry 2 }

tmnxWlanGwDsmIpFil6N3LastCh      OBJECT-TYPE
    SYNTAX      TimeStamp
    MAX-ACCESS  read-only
    STATUS      current
    DESCRIPTION
        "The value tmnxWlanGwDsmIpFil6N3LastCh indicates the sysUpTime at the
         time of the most recent management-initiated change to this conceptual
         row."
    ::= { tmnxWlanGwDsmIpFil6N3Entry 3 }

tmnxWlanGwDsmIpFil6N3Description OBJECT-TYPE
    SYNTAX      TItemDescription
    MAX-ACCESS  read-create
    STATUS      current
    DESCRIPTION
        "The value of tmnxWlanGwDsmIpFil6N3Description specifies the user
         provided description of this IPv6 filter entry."
    DEFVAL      { "" }
    ::= { tmnxWlanGwDsmIpFil6N3Entry 4 }

tmnxWlanGwDsmIpFil6N3Action      OBJECT-TYPE
    SYNTAX      TmnxWlanGwDsmFilterAction
    MAX-ACCESS  read-create
    STATUS      current
    DESCRIPTION
        "The value of the object tmnxWlanGwDsmIpFil6N3Action specifies the
         action to take for packets that match this filter entry."
    DEFVAL      { none }
    ::= { tmnxWlanGwDsmIpFil6N3Entry 5 }

tmnxWlanGwDsmIpFil6N3Protocol    OBJECT-TYPE
    SYNTAX      TIpProtocol
    MAX-ACCESS  read-create
    STATUS      current
    DESCRIPTION
        "The value of the object tmnxWlanGwDsmIpFil6N3Protocol specifies the IP
         protocol to match.

         The value minus one specifies no IP protocol matching."
    DEFVAL      { -1 }
    ::= { tmnxWlanGwDsmIpFil6N3Entry 6 }

tmnxWlanGwDsmIpFil6N3DestAddrTyp OBJECT-TYPE
    SYNTAX      InetAddressType
    MAX-ACCESS  read-create
    STATUS      current
    DESCRIPTION
        "The value of tmnxWlanGwDsmIpFil6N3DestAddrTyp specifies the address
         type of tmnxWlanGwDsmIpFil6N3DestAddr.

         The values supported are 'unknown' and 'ipv6'."
    DEFVAL      { unknown }
    ::= { tmnxWlanGwDsmIpFil6N3Entry 7 }

tmnxWlanGwDsmIpFil6N3DestAddr    OBJECT-TYPE
    SYNTAX      InetAddress (SIZE (0|16))
    MAX-ACCESS  read-create
    STATUS      current
    DESCRIPTION
        "The value of tmnxWlanGwDsmIpFil6N3DestAddr specifies the IPv6 address
         of the destination prefix to match."
    DEFVAL      { ''H }
    ::= { tmnxWlanGwDsmIpFil6N3Entry 8 }

tmnxWlanGwDsmIpFil6N3DestPrefLen OBJECT-TYPE
    SYNTAX      InetAddressPrefixLength (0..128)
    MAX-ACCESS  read-create
    STATUS      current
    DESCRIPTION
        "The value of tmnxWlanGwDsmIpFil6N3DestPrefLen specifies the length of
         the destination prefix to match."
    DEFVAL      { 0 }
    ::= { tmnxWlanGwDsmIpFil6N3Entry 9 }

tmnxWlanGwDsmIpFil6N3DestPortOp  OBJECT-TYPE
    SYNTAX      INTEGER {
        none (0),
        eq   (1)
    }
    MAX-ACCESS  read-create
    STATUS      current
    DESCRIPTION
        "The value of the object tmnxWlanGwDsmIpFil6N3DestPortOp specifies the
         operation to perform on the object tmnxWlanGwDsmIpFil6N3DestPort1."
    DEFVAL      { none }
    ::= { tmnxWlanGwDsmIpFil6N3Entry 10 }

tmnxWlanGwDsmIpFil6N3DestPort1   OBJECT-TYPE
    SYNTAX      InetPortNumber
    MAX-ACCESS  read-create
    STATUS      current
    DESCRIPTION
        "The value of this object specifies the value to compare with the
         destination port in each packet, according to the value of the object
         tmnxWlanGwDsmIpFil6N3DestPortOp."
    DEFVAL      { 0 }
    ::= { tmnxWlanGwDsmIpFil6N3Entry 11 }

tmnxWlanGwDsmIpFil6N3IngHitCount OBJECT-TYPE
    SYNTAX      Counter64
    MAX-ACCESS  read-only
    STATUS      current
    DESCRIPTION
        "This object indicates the number of times an ingress packet matched
         this entry."
    ::= { tmnxWlanGwDsmIpFil6N3Entry 17 }

tmnxWlanGwDsmIpFil6N3RedirectURL OBJECT-TYPE
    SYNTAX      TmnxHttpRedirectUrl
    MAX-ACCESS  read-create
    STATUS      current
    DESCRIPTION
        "The value of tmnxWlanGwDsmIpFil6N3RedirectURL specifies the URL to
         redirect to, when the value of tmnxWlanGwDsmIpFil6N3Action is
         'httpRedirect'.

         This string may contain a number of substitution macro's:
         - $URL: specifies that '$URL' must be substituted with the content of the
                 Request-URI in the HTTP GET Request received.

         - $MAC: specifies that '$MAC' must be replaced with a string that
                 represents the MAC address of the subscriber host;
                 the MAC address is formatted in Nokia SROS style,
                 like 00:0c:f1:99:85:b8.

         - $IP:  specifies that '$IP' must be replaced with a string that represents
                 the IP address of the subscriber host.

         Note that the value of tmnxWlanGwDsmIpFil6N3RedirectURL is silently
         cleared by the system if tmnxWlanGwDsmIpFil6N3Action is set to any
         value other than httpRedirect."
    DEFVAL      { ''H }
    ::= { tmnxWlanGwDsmIpFil6N3Entry 18 }

tmnxWlanGwDsmTable               OBJECT-TYPE
    SYNTAX      SEQUENCE OF TmnxWlanGwDsmEntry
    MAX-ACCESS  not-accessible
    STATUS      current
    DESCRIPTION
        "The tmnxWlanGwDsmTable contains objects to configure the Distributed
         Subscriber Management (DSM) for WLAN Gateway interfaces."
    ::= { tmnxWlanGwDsmSubObjs 9 }

tmnxWlanGwDsmEntry               OBJECT-TYPE
    SYNTAX      TmnxWlanGwDsmEntry
    MAX-ACCESS  not-accessible
    STATUS      current
    DESCRIPTION
        "Each conceptual row represents a set of Distributed Subscriber
         Management configuration data for a particular interface."
    AUGMENTS    { tmnxWlanGwEntry }
    ::= { tmnxWlanGwDsmTable 1 }

TmnxWlanGwDsmEntry               ::= SEQUENCE
{
    tmnxWlanGwDsmLastCh              TimeStamp,
    tmnxWlanGwDsmIpv6TcpMssAdjust    Unsigned32
}

tmnxWlanGwDsmLastCh              OBJECT-TYPE
    SYNTAX      TimeStamp
    MAX-ACCESS  read-only
    STATUS      current
    DESCRIPTION
        "The value of tmnxWlanGwDsmLastCh indicates the sysUpTime at the time
         of the most recent management-initiated change to this table row."
    ::= { tmnxWlanGwDsmEntry 1 }

tmnxWlanGwDsmIpv6TcpMssAdjust    OBJECT-TYPE
    SYNTAX      Unsigned32 (0 | 160..10240)
    UNITS       "bytes"
    MAX-ACCESS  read-create
    STATUS      current
    DESCRIPTION
        "The value of tmnxWlanGwDsmIpv6TcpMssAdjust specifies the value to put
         into the TCP Maximum Segment Size (MSS) option if not already present,
         or if the present value is higher.

         The value zero means that no MSS option adjustment is done."
    DEFVAL      { 0 }
    ::= { tmnxWlanGwDsmEntry 2 }

tmnxWlanGwGtpIsaObjs             OBJECT IDENTIFIER ::= { tmnxWlanGwObjs 10 }

tmnxWlanGwUeObjs                 OBJECT IDENTIFIER ::= { tmnxWlanGwObjs 11 }

tmnxWlanGwUeNextQryId            OBJECT-TYPE
    SYNTAX      Unsigned32
    MAX-ACCESS  read-only
    STATUS      current
    DESCRIPTION
        "The value of the object tmnxWlanGwUeNextQryId indicates the next
         available unique query identifier to use in User Equipment queries.

         Multiple concurrent queries are supported; each query and its results
         are identified with a unique query ID supplied by the system."
    ::= { tmnxWlanGwUeObjs 1 }

tmnxWlanGwUeMaxQryId             OBJECT-TYPE
    SYNTAX      Unsigned32
    MAX-ACCESS  read-only
    STATUS      current
    DESCRIPTION
        "The value of the object tmnxWlanGwUeMaxQryId indicates the maximum
         value of a query identifier for use in User Equipment queries.

         Multiple concurrent queries are supported; each query and its results
         are identified with a unique query ID supplied by the system.

         The value of the object tmnxWlanGwUeMaxQryId indicates also the
         maximum number of concurrent queries."
    ::= { tmnxWlanGwUeObjs 2 }

tmnxWlanGwUeQryTable             OBJECT-TYPE
    SYNTAX      SEQUENCE OF TmnxWlanGwUeQryEntry
    MAX-ACCESS  not-accessible
    STATUS      current
    DESCRIPTION
        "The tmnxWlanGwUeQryTable contains queries for User Equipment.

         Conceptual rows in this table are created and destroyed by means of
         SNMP operations on the tmnxWlanGwUeQryRowStatus object.

         Conceptual rows in this table are volatile: they are lost upon reboot
         or switchover."
    ::= { tmnxWlanGwUeObjs 3 }

tmnxWlanGwUeQryEntry             OBJECT-TYPE
    SYNTAX      TmnxWlanGwUeQryEntry
    MAX-ACCESS  not-accessible
    STATUS      current
    DESCRIPTION
        "Each conceptual row represents a query for User Equipment.

         Entries in this table can be created or deleted by means of SNMP
         operations on the tmnxWlanGwUeQryRowStatus object."
    INDEX       { tmnxWlanGwUeQryId }
    ::= { tmnxWlanGwUeQryTable 1 }

TmnxWlanGwUeQryEntry             ::= SEQUENCE
{
    tmnxWlanGwUeQryId                Unsigned32,
    tmnxWlanGwUeQryRowStatus         RowStatus,
    tmnxWlanGwUeQryWhereState        BITS,
    tmnxWlanGwUeQryWhereMacAddress   MacAddress,
    tmnxWlanGwUeQryWhereAddrType     InetAddressType,
    tmnxWlanGwUeQryWhereAddr         InetAddress,
    tmnxWlanGwUeQryWhereIsaGrp       TmnxWlanGwIsaGrpIdOrZero,
    tmnxWlanGwUeQryWhereMemberId     Unsigned32,
    tmnxWlanGwUeQryWhereQTag         QTagFullRangeOrNone,
    tmnxWlanGwUeQryWhereTuRouter     TmnxVRtrIDOrZero,
    tmnxWlanGwUeQryWhereTuRemAddrTyp InetAddressType,
    tmnxWlanGwUeQryWhereTuRemAddr    InetAddress,
    tmnxWlanGwUeQryWhereTuLocAddrTyp InetAddressType,
    tmnxWlanGwUeQryWhereTuLocAddr    InetAddress,
    tmnxWlanGwUeQryWhereEncap        TmnxWlanGwUeEncapsulation,
    tmnxWlanGwUeQryWhereSlaacPrefTyp InetAddressType,
    tmnxWlanGwUeQryWhereSlaacPref    InetAddress,
    tmnxWlanGwUeQryWhereDhcp6AddrTyp InetAddressType,
    tmnxWlanGwUeQryWhereDhcp6Addr    InetAddress,
    tmnxWlanGwUeQryWhereBridgeId     Unsigned32,
    tmnxWlanGwUeQryWhereAddrFamily   TmnxWlanGwUeAddressFamily,
    tmnxWlanGwUeQryName              TNamedItem,
    tmnxWlanGwUeQryWhereSoftQuotaExh TruthValue,
    tmnxWlanGwUeQryNumResults        Gauge32
}

tmnxWlanGwUeQryId                OBJECT-TYPE
    SYNTAX      Unsigned32
    MAX-ACCESS  not-accessible
    STATUS      current
    DESCRIPTION
        "The value of tmnxWlanGwUeQryId specifies the query ID of this User
         Equipment query.

         Get a unique query ID by means of an SNMP get on the
         tmnxWlanGwUeNextQryId object."
    ::= { tmnxWlanGwUeQryEntry 1 }

tmnxWlanGwUeQryRowStatus         OBJECT-TYPE
    SYNTAX      RowStatus
    MAX-ACCESS  read-create
    STATUS      current
    DESCRIPTION
        "The value of tmnxWlanGwUeQryRowStatus specifies the row status of this
         row."
    ::= { tmnxWlanGwUeQryEntry 2 }

tmnxWlanGwUeQryWhereState        OBJECT-TYPE
    SYNTAX      BITS {
        bDataTriggered        (0),
        bDhcpTriggered        (1),
        bIpAssigned           (2),
        bAuthorizedOnly       (3),
        bIpAssignedAuthorized (4),
        bAlreadySignedIn      (5),
        bPortal               (6),
        bDistributedSubMgmt   (7),
        bEsmUser              (8),
        bL2User               (9),
        bGtpAuthorized        (10),
        bDeletePending        (11),
        bXcon                 (12)
    }
    MAX-ACCESS  read-create
    STATUS      current
    DESCRIPTION
        "The value of tmnxWlanGwUeQryWhereState specifies the set of UE state
         values.

         When the value of tmnxWlanGwUeQryWhereState is not all zeroes, the
         tmnxWlanGwUeResTable will contain only rows with this query ID where
         the value of the object tmnxWlanGwUeResState is equal to one of the
         states corresponding to the bits set in tmnxWlanGwUeQryWhereState.

         Setting the value of tmnxWlanGwUeQryWhereState to all zeroes is
         equivalent of setting it to all ones, and specifies that the
         tmnxWlanGwUeResTable may contain rows with this query ID having any
         value of the object tmnxWlanGwUeResState."
    DEFVAL      { {} }
    ::= { tmnxWlanGwUeQryEntry 3 }

tmnxWlanGwUeQryWhereMacAddress   OBJECT-TYPE
    SYNTAX      MacAddress
    MAX-ACCESS  read-create
    STATUS      current
    DESCRIPTION
        "The value of the object tmnxWlanGwUeQryWhereMacAddress specifies the
         MAC address.

         When the value of tmnxWlanGwUeQryWhereMacAddress is not all zeroes,
         the tmnxWlanGwUeResTable will contain only rows with this query ID
         where the value of tmnxWlanGwUeResMacAddress is equal to this value."
    DEFVAL      { '000000000000'H }
    ::= { tmnxWlanGwUeQryEntry 4 }

tmnxWlanGwUeQryWhereAddrType     OBJECT-TYPE
    SYNTAX      InetAddressType
    MAX-ACCESS  read-create
    STATUS      current
    DESCRIPTION
        "The value of tmnxWlanGwUeQryWhereAddrType specifies the type of the
         User Equipment's IP address.

         When the value of tmnxWlanGwUeQryWhereAddrType is not 'unknown', the
         tmnxWlanGwUeResTable will contain only rows with this query ID where
         the value of tmnxWlanGwUeResAddrType is equal to this value."
    DEFVAL      { unknown }
    ::= { tmnxWlanGwUeQryEntry 5 }

tmnxWlanGwUeQryWhereAddr         OBJECT-TYPE
    SYNTAX      InetAddress (SIZE (0|4|16))
    MAX-ACCESS  read-create
    STATUS      current
    DESCRIPTION
        "The value of tmnxWlanGwUeQryWhereAddr specifies the IP address of the
         remote endpoint of the UE tunnel.

         When the value of tmnxWlanGwUeQryWhereAddr is not empty, the
         tmnxWlanGwUeResTable will contain only rows where the value of
         tmnxWlanGwUeResAddr is equal to this value."
    DEFVAL      { ''H }
    ::= { tmnxWlanGwUeQryEntry 6 }

tmnxWlanGwUeQryWhereIsaGrp       OBJECT-TYPE
    SYNTAX      TmnxWlanGwIsaGrpIdOrZero
    MAX-ACCESS  read-create
    STATUS      current
    DESCRIPTION
        "The value of tmnxWlanGwUeQryWhereIsaGrp specifies the identifier of
         the WLAN Gateway Integrated Service Adaptor group.

         When the value of tmnxWlanGwUeQryWhereIsaGrp is non-zero, the
         tmnxWlanGwUeResTable will contain only rows with this query ID where
         the WLAN Gateway ISA group is equal to this value."
    DEFVAL      { 0 }
    ::= { tmnxWlanGwUeQryEntry 7 }

tmnxWlanGwUeQryWhereMemberId     OBJECT-TYPE
    SYNTAX      Unsigned32
    MAX-ACCESS  read-create
    STATUS      current
    DESCRIPTION
        "The value of tmnxWlanGwUeQryWhereMemberId specifies the identifier of
         the WLAN Gateway ISA Group member.

         When the value of tmnxWlanGwUeQryWhereMemberId is non-zero, the
         tmnxWlanGwUeResTable will contain only rows with this query ID where
         the WLAN Gateway ISA Group member is equal to this value."
    DEFVAL      { 0 }
    ::= { tmnxWlanGwUeQryEntry 8 }

tmnxWlanGwUeQryWhereQTag         OBJECT-TYPE
    SYNTAX      QTagFullRangeOrNone
    MAX-ACCESS  read-create
    STATUS      current
    DESCRIPTION
        "The value of tmnxWlanGwUeQryWhereQTag specifies the VLAN Q-tag present
         in the traffic received from a UE.

         When the value of tmnxWlanGwUeQryWhereQTag is non-zero, the
         tmnxWlanGwUeResTable will contain only rows with this query ID where
         the value of tmnxWlanGwUeResQTag is equal to this value."
    DEFVAL      { -1 }
    ::= { tmnxWlanGwUeQryEntry 9 }

tmnxWlanGwUeQryWhereTuRouter     OBJECT-TYPE
    SYNTAX      TmnxVRtrIDOrZero
    MAX-ACCESS  read-create
    STATUS      current
    DESCRIPTION
        "The value of tmnxWlanGwUeQryWhereTuRouter specifies the virtual router
         instance.

         When the value of tmnxWlanGwUeQryWhereTuRouter is non-zero, the
         tmnxWlanGwUeResTable will contain only rows with this query ID where
         the value of tmnxWlanGwUeResTuRouter is equal to this value."
    DEFVAL      { 0 }
    ::= { tmnxWlanGwUeQryEntry 10 }

tmnxWlanGwUeQryWhereTuRemAddrTyp OBJECT-TYPE
    SYNTAX      InetAddressType
    MAX-ACCESS  read-create
    STATUS      current
    DESCRIPTION
        "The value of tmnxWlanGwUeQryWhereTuRemAddrTyp specifies the type of
         tmnxWlanGwUeQryWhereTuRemAddr.

         When the value of tmnxWlanGwUeQryWhereTuRemAddrTyp is not 'unknown',
         the tmnxWlanGwUeResTable will contain only rows with this query ID
         where the value of tmnxWlanGwUeResTuAddrType is equal to this value."
    DEFVAL      { unknown }
    ::= { tmnxWlanGwUeQryEntry 11 }

tmnxWlanGwUeQryWhereTuRemAddr    OBJECT-TYPE
    SYNTAX      InetAddress (SIZE (0|4|16))
    MAX-ACCESS  read-create
    STATUS      current
    DESCRIPTION
        "The value of tmnxWlanGwUeQryWhereTuRemAddr specifies the IP address of
         the remote endpoint of the UE tunnel.

         When the value of tmnxWlanGwUeQryWhereTuRemAddr is not empty, the
         tmnxWlanGwUeResTable will contain only rows where the value of
         tmnxWlanGwUeResTuRemoteAddr is equal to this value."
    DEFVAL      { ''H }
    ::= { tmnxWlanGwUeQryEntry 12 }

tmnxWlanGwUeQryWhereTuLocAddrTyp OBJECT-TYPE
    SYNTAX      InetAddressType
    MAX-ACCESS  read-create
    STATUS      current
    DESCRIPTION
        "The value of tmnxWlanGwUeQryWhereTuLocAddrTyp specifies the type of
         tmnxWlanGwUeQryWhereTuLocAddr.

         When the value of tmnxWlanGwUeQryWhereTuRemAddrTyp is not 'unknown',
         the tmnxWlanGwUeResTable will contain only rows with this query ID
         where the value of tmnxWlanGwUeResTuAddrType is equal to this value."
    DEFVAL      { unknown }
    ::= { tmnxWlanGwUeQryEntry 13 }

tmnxWlanGwUeQryWhereTuLocAddr    OBJECT-TYPE
    SYNTAX      InetAddress (SIZE (0|4|16))
    MAX-ACCESS  read-create
    STATUS      current
    DESCRIPTION
        "The value of tmnxWlanGwUeQryWhereTuLocAddr specifies the IP address of
         the local endpoint of the UE tunnel.

         When the value of tmnxWlanGwUeQryWhereTuLocAddr is not empty, the
         tmnxWlanGwUeResTable will contain only rows with this query ID where
         the value of tmnxWlanGwUeResTuLocalAddr is equal to this value."
    DEFVAL      { ''H }
    ::= { tmnxWlanGwUeQryEntry 14 }

tmnxWlanGwUeQryWhereEncap        OBJECT-TYPE
    SYNTAX      TmnxWlanGwUeEncapsulation
    MAX-ACCESS  read-create
    STATUS      current
    DESCRIPTION
        "The value of tmnxWlanGwUeQryWhereEncap specifies the encapsulation
         type present in the traffic received from a UE.

         When the value of tmnxWlanGwUeQryWhereEncap is non-zero, the
         tmnxWlanGwUeResTable will contain only rows with this query ID where
         the value of tmnxWlanGwUeResEncapsulation is equal to this value."
    DEFVAL      { notSpecified }
    ::= { tmnxWlanGwUeQryEntry 15 }

tmnxWlanGwUeQryWhereSlaacPrefTyp OBJECT-TYPE
    SYNTAX      InetAddressType
    MAX-ACCESS  read-create
    STATUS      current
    DESCRIPTION
        "The value of tmnxWlanGwUeQryWhereSlaacPrefTyp specifies the type of
         tmnxWlanGwUeQryWhereSlaacPref.

         When the value of tmnxWlanGwUeQryWhereSlaacPrefTyp is not 'unknown',
         the tmnxWlanGwUeResTable will contain only rows with this query ID
         where the value of tmnxWlanGwUeQryWhereSlaacPrefTyp is equal to this
         value."
    DEFVAL      { unknown }
    ::= { tmnxWlanGwUeQryEntry 16 }

tmnxWlanGwUeQryWhereSlaacPref    OBJECT-TYPE
    SYNTAX      InetAddress (SIZE (0|16))
    MAX-ACCESS  read-create
    STATUS      current
    DESCRIPTION
        "The value of tmnxWlanGwUeQryWhereSlaacPref specifies the IPv6 prefix
         used to filter on new SLAAC prefixes.

         When the value of tmnxWlanGwUeQryWhereSlaacPref is not empty, the
         tmnxWlanGwUeResTable will contain only rows with this query ID where
         the value of tmnxWlanGwUeQryWhereSlaacPref is equal to this value."
    DEFVAL      { ''H }
    ::= { tmnxWlanGwUeQryEntry 17 }

tmnxWlanGwUeQryWhereDhcp6AddrTyp OBJECT-TYPE
    SYNTAX      InetAddressType
    MAX-ACCESS  read-create
    STATUS      current
    DESCRIPTION
        "The value of tmnxWlanGwUeQryWhereDhcp6AddrTyp specifies the type of
         tmnxWlanGwUeQryWhereDhcp6Addr.

         When the value of tmnxWlanGwUeQryWhereDhcp6AddrTyp is not 'unknown',
         the tmnxWlanGwUeResTable will contain only rows with this query ID
         where the value of tmnxWlanGwUeQryWhereDhcp6AddrTyp is equal to this
         value."
    DEFVAL      { unknown }
    ::= { tmnxWlanGwUeQryEntry 18 }

tmnxWlanGwUeQryWhereDhcp6Addr    OBJECT-TYPE
    SYNTAX      InetAddress (SIZE (0|16))
    MAX-ACCESS  read-create
    STATUS      current
    DESCRIPTION
        "The value of tmnxWlanGwUeQryWhereDhcp6Addr specifies the IPv6 address
         used to filter on new DHCPv6 addresses.

         When the value of tmnxWlanGwUeQryWhereDhcp6Addr is not empty, the
         tmnxWlanGwUeResTable will contain only rows with this query ID where
         the value of tmnxWlanGwUeQryWhereDhcp6Addr is equal to this value."
    DEFVAL      { ''H }
    ::= { tmnxWlanGwUeQryEntry 19 }

tmnxWlanGwUeQryWhereBridgeId     OBJECT-TYPE
    SYNTAX      Unsigned32
    MAX-ACCESS  read-create
    STATUS      current
    DESCRIPTION
        "The value of tmnxWlanGwUeQryWhereBridgeId specifies  the identifier of
         the bridge.

         When the value of tmnxWlanGwUeQryWhereBridgeId is not equal to all
         ones, the tmnxWlanGwUeResTable will contain only rows with this query
         ID where the bridge identifier is equal to this value."
    DEFVAL      { 'ffffffff'H }
    ::= { tmnxWlanGwUeQryEntry 25 }

tmnxWlanGwUeQryWhereAddrFamily   OBJECT-TYPE
    SYNTAX      TmnxWlanGwUeAddressFamily
    MAX-ACCESS  read-create
    STATUS      current
    DESCRIPTION
        "The value of tmnxWlanGwUeQryWhereAddrFamily specifies the UE address
         family used to filter.

         When the value of tmnxWlanGwUeQryWhereAddrFamily is non-zero, the
         tmnxWlanGwUeResTable will contain only rows with this query ID where
         the value of tmnxWlanGwUeQryWhereAddrFamily is equal to this value."
    DEFVAL      { notSpecified }
    ::= { tmnxWlanGwUeQryEntry 26 }

tmnxWlanGwUeQryName              OBJECT-TYPE
    SYNTAX      TNamedItem
    MAX-ACCESS  read-create
    STATUS      current
    DESCRIPTION
        "The value of tmnxWlanGwUeQryName specifies the name of this query.

         If a value for tmnxWlanGwUeQryName is not provided while the
         conceptual row is created, the system will assign one.

         After the conceptual row is created, it is not allowed to change the
         value of tmnxWlanGwUeQryName."
    ::= { tmnxWlanGwUeQryEntry 27 }

tmnxWlanGwUeQryWhereSoftQuotaExh OBJECT-TYPE
    SYNTAX      TruthValue
    MAX-ACCESS  read-create
    STATUS      current
    DESCRIPTION
        "The value of tmnxWlanGwUeQryWhereSoftQuotaExh specifies to query UEs
         for which the soft volume quota is exhausted.

         When the value of tmnxWlanGwUeQryWhereSoftQuotaExh is non-zero, the
         tmnxWlanGwUeResTable will contain only rows with this query ID for
         which the soft volume quota is exhausted"
    DEFVAL      { false }
    ::= { tmnxWlanGwUeQryEntry 28 }

tmnxWlanGwUeQryNumResults        OBJECT-TYPE
    SYNTAX      Gauge32
    MAX-ACCESS  read-only
    STATUS      current
    DESCRIPTION
        "The value of tmnxWlanGwUeQryNumResults indicates the current number of
         User Equipment matching this query.

         It is recommended to examine this value before starting to read the
         tmnxWlanGwUeResTable."
    ::= { tmnxWlanGwUeQryEntry 200 }

tmnxWlanGwUeResTable             OBJECT-TYPE
    SYNTAX      SEQUENCE OF TmnxWlanGwUeResEntry
    MAX-ACCESS  not-accessible
    STATUS      current
    DESCRIPTION
        "The tmnxWlanGwUeResTable contains the results of one or more queries
         for User Equipment."
    ::= { tmnxWlanGwUeObjs 4 }

tmnxWlanGwUeResEntry             OBJECT-TYPE
    SYNTAX      TmnxWlanGwUeResEntry
    MAX-ACCESS  not-accessible
    STATUS      current
    DESCRIPTION
        "Each conceptual row represents a UE.

         Conceptual rows in this table are created and destroyed automatically
         by the system.

         Conceptual rows in this table are volatile: they are lost upon reboot
         or switchover.

         The system creates rows in this table as a result of the creation of a
         row in the query table tmnxWlanGwUeQryTable, and destroys them when
         that row is destroyed."
    INDEX       {
        tmnxWlanGwUeQryId,
        tmnxWlanGwUeResId
    }
    ::= { tmnxWlanGwUeResTable 1 }

TmnxWlanGwUeResEntry             ::= SEQUENCE
{
    tmnxWlanGwUeResId                TmnxWlanGwUeIdentifier,
    tmnxWlanGwUeResMacAddress        MacAddress,
    tmnxWlanGwUeResQTag              QTagFullRangeOrNone,
    tmnxWlanGwUeResAddrType          InetAddressType,
    tmnxWlanGwUeResAddr              InetAddress,
    tmnxWlanGwUeResState             INTEGER,
    tmnxWlanGwUeResIsaGrp            TmnxWlanGwIsaGrpIdOrZero,
    tmnxWlanGwUeResIsaMemberId       Unsigned32,
    tmnxWlanGwUeResTuRouter          TmnxVRtrIDOrZero,
    tmnxWlanGwUeResTuAddrType        InetAddressType,
    tmnxWlanGwUeResTuRemoteAddr      InetAddress,
    tmnxWlanGwUeResTuLocalAddr       InetAddress,
    tmnxWlanGwUeResEncapsulation     TmnxWlanGwUeEncapsulation,
    tmnxWlanGwUeResApMacAddress      MacAddress,
    tmnxWlanGwUeResSsid              TNamedItemOrEmpty,
    tmnxWlanGwUeResMplsLabel         MplsLabel,
    tmnxWlanGwUeResLastMoveTime      DateAndTime,
    tmnxWlanGwUeResExpirationTime    DateAndTime,
    tmnxWlanGwUeResIdleTimeout       Unsigned32,
    tmnxWlanGwUeResSessionTimeout    DateAndTime,
    tmnxWlanGwUeResNatPlcy           TNamedItemOrEmpty,
    tmnxWlanGwUeResHttpRdrPlcy       TNamedItemOrEmpty,
    tmnxWlanGwUeResDsmIpFilter       TNamedItemOrEmpty,
    tmnxWlanGwUeResDsmAcctPlcy       TNamedItemOrEmpty,
    tmnxWlanGwUeResDsmAcctUpdInterv  Unsigned32,
    tmnxWlanGwUeResAcctUpdate        DateAndTime,
    tmnxWlanGwUeResIngOperPir        TPIRRate,
    tmnxWlanGwUeResIngOperCir        TCIRRate,
    tmnxWlanGwUeResEgrOperPir        TPIRRate,
    tmnxWlanGwUeResEgrOperCir        TCIRRate,
    tmnxWlanGwUeResDsmAppProfile     TNamedItemOrEmpty,
    tmnxWlanGwUeResRxPkts            Counter64,
    tmnxWlanGwUeResRxOctets          Counter64,
    tmnxWlanGwUeResTxPkts            Counter64,
    tmnxWlanGwUeResTxOctets          Counter64,
    tmnxWlanGwUeResSlaacAddrType     InetAddressType,
    tmnxWlanGwUeResSlaacPref         InetAddress,
    tmnxWlanGwUeResSlaacAddr1        InetAddress,
    tmnxWlanGwUeResSlaacAddr2        InetAddress,
    tmnxWlanGwUeResSlaacAddr3        InetAddress,
    tmnxWlanGwUeResDhcp6AddrType     InetAddressType,
    tmnxWlanGwUeResDhcp6Addr         InetAddress,
    tmnxWlanGwUeResDhcp6AddrDepr     TruthValue,
    tmnxWlanGwUeResDhcp6IAID         Unsigned32,
    tmnxWlanGwUeResDhcp6IAIDValid    TruthValue,
    tmnxWlanGwUeResSlaacLeaseExpire  DateAndTime,
    tmnxWlanGwUeResDhcp6LeaseExpire  DateAndTime,
    tmnxWlanGwUeResDhcpAddrDepr      TruthValue,
    tmnxWlanGwUeResBridgeId          Unsigned32,
    tmnxWlanGwUeResAddrFamily        TmnxWlanGwUeAddressFamily,
    tmnxWlanGwUeResHardQuotaOctets   Counter64,
    tmnxWlanGwUeResSoftQuotaOctets   Counter64,
    tmnxWlanGwUeResL2Service         TLNamedItemOrEmpty
}

tmnxWlanGwUeResId                OBJECT-TYPE
    SYNTAX      TmnxWlanGwUeIdentifier
    MAX-ACCESS  not-accessible
    STATUS      current
    DESCRIPTION
        "The value of tmnxWlanGwUeResId indicates the identifier of this User
         Equipment."
    ::= { tmnxWlanGwUeResEntry 1 }

tmnxWlanGwUeResMacAddress        OBJECT-TYPE
    SYNTAX      MacAddress
    MAX-ACCESS  read-only
    STATUS      current
    DESCRIPTION
        "The value of the object tmnxWlanGwUeResMacAddress indicates the MAC
         address of this UE."
    ::= { tmnxWlanGwUeResEntry 2 }

tmnxWlanGwUeResQTag              OBJECT-TYPE
    SYNTAX      QTagFullRangeOrNone
    MAX-ACCESS  read-only
    STATUS      current
    DESCRIPTION
        "The value of the object tmnxWlanGwUeResQTag indicates the VLAN Q-tag
         present in the traffic received from this UE.

         The value of this object can be used to identify the retailer service,
         by means of the tmnxWlanGwIfRetailTable.

         The value minus one indicates that the traffic received from this UE
         does not have a VLAN Q-tag."
    ::= { tmnxWlanGwUeResEntry 3 }

tmnxWlanGwUeResAddrType          OBJECT-TYPE
    SYNTAX      InetAddressType
    MAX-ACCESS  read-only
    STATUS      current
    DESCRIPTION
        "The value of tmnxWlanGwUeResAddrType indicates the address type of
         tmnxWlanGwUeResAddr."
    ::= { tmnxWlanGwUeResEntry 4 }

tmnxWlanGwUeResAddr              OBJECT-TYPE
    SYNTAX      InetAddress (SIZE (4|16))
    MAX-ACCESS  read-only
    STATUS      current
    DESCRIPTION
        "The value of the object tmnxWlanGwUeResAddr indicates the IP address
         this UE."
    ::= { tmnxWlanGwUeResEntry 5 }

tmnxWlanGwUeResState             OBJECT-TYPE
    SYNTAX      INTEGER {
        new                  (1),
        dataTriggered        (2),
        dhcpTriggered        (3),
        ipAssigned           (4),
        authorizedOnly       (5),
        ipAssignedAuthorized (6),
        alreadySignedIn      (7),
        portal               (8),
        distributedSubMgmt   (9),
        esmUser              (10),
        l2User               (11),
        gtpAuthorized        (12),
        deletePending        (13),
        xCon                 (14)
    }
    MAX-ACCESS  read-only
    STATUS      current
    DESCRIPTION
        "The value of the object tmnxWlanGwUeResState indicates the state of
         this UE."
    ::= { tmnxWlanGwUeResEntry 6 }

tmnxWlanGwUeResIsaGrp            OBJECT-TYPE
    SYNTAX      TmnxWlanGwIsaGrpIdOrZero
    MAX-ACCESS  read-only
    STATUS      current
    DESCRIPTION
        "The value of the object tmnxWlanGwUeResIsaGrp indicates the identifier
         of the WLAN Gateway Integrated Service Adaptor group associated with
         this UE."
    ::= { tmnxWlanGwUeResEntry 7 }

tmnxWlanGwUeResIsaMemberId       OBJECT-TYPE
    SYNTAX      Unsigned32
    MAX-ACCESS  read-only
    STATUS      current
    DESCRIPTION
        "The value of the object tmnxWlanGwUeResIsaMemberId indicates the
         identifier of the WLAN Gateway ISA Group member associated with this
         UE."
    ::= { tmnxWlanGwUeResEntry 8 }

tmnxWlanGwUeResTuRouter          OBJECT-TYPE
    SYNTAX      TmnxVRtrIDOrZero
    MAX-ACCESS  read-only
    STATUS      current
    DESCRIPTION
        "The object tmnxWlanGwUeResTuRouter indicates the identifier of the
         virtual router instance where the tunneled User Equipment traffic is
         routed."
    ::= { tmnxWlanGwUeResEntry 9 }

tmnxWlanGwUeResTuAddrType        OBJECT-TYPE
    SYNTAX      InetAddressType
    MAX-ACCESS  read-only
    STATUS      current
    DESCRIPTION
        "The value of tmnxWlanGwUeResTuAddrType indicates the address type of
         tmnxWlanGwUeResTuRemoteAddr and tmnxWlanGwUeResTuLocalAddr."
    ::= { tmnxWlanGwUeResEntry 10 }

tmnxWlanGwUeResTuRemoteAddr      OBJECT-TYPE
    SYNTAX      InetAddress (SIZE (0|4|16))
    MAX-ACCESS  read-only
    STATUS      current
    DESCRIPTION
        "The value of the object tmnxWlanGwUeResTuRemoteAddr indicates the IP
         address of the remote endpoint of this UE's tunnel, that is the source
         IP address in the tunnel header of received packets."
    ::= { tmnxWlanGwUeResEntry 11 }

tmnxWlanGwUeResTuLocalAddr       OBJECT-TYPE
    SYNTAX      InetAddress (SIZE (0|4|16))
    MAX-ACCESS  read-only
    STATUS      current
    DESCRIPTION
        "The value of the object tmnxWlanGwUeResTuLocalAddr indicates the IP
         address of the local endpoint of this UE's tunnel, that is the
         destination IP address in the tunnel header of received packets."
    ::= { tmnxWlanGwUeResEntry 12 }

tmnxWlanGwUeResEncapsulation     OBJECT-TYPE
    SYNTAX      TmnxWlanGwUeEncapsulation
    MAX-ACCESS  read-only
    STATUS      current
    DESCRIPTION
        "The value of the object tmnxWlanGwUeResEncapsulation indicates the
         encapsulation used in this UE's tunnel."
    ::= { tmnxWlanGwUeResEntry 13 }

tmnxWlanGwUeResApMacAddress      OBJECT-TYPE
    SYNTAX      MacAddress
    MAX-ACCESS  read-only
    STATUS      current
    DESCRIPTION
        "The value of the object tmnxWlanGwUeResApMacAddress indicates the MAC
         address of the Access Point of this UE."
    ::= { tmnxWlanGwUeResEntry 100 }

tmnxWlanGwUeResSsid              OBJECT-TYPE
    SYNTAX      TNamedItemOrEmpty
    MAX-ACCESS  read-only
    STATUS      current
    DESCRIPTION
        "The value of tmnxWlanGwUeResSsid indicates the Service Set ID (SSID)
         of this UE.

         This object refers to a conceptual row in the tmnxWlanGwSsidTable."
    ::= { tmnxWlanGwUeResEntry 101 }

tmnxWlanGwUeResMplsLabel         OBJECT-TYPE
    SYNTAX      MplsLabel
    MAX-ACCESS  read-only
    STATUS      current
    DESCRIPTION
        "The value of the object tmnxWlanGwUeResMplsLabel indicates the MPLS
         label present in the traffic received from this UE.

         The value zero indicates that the traffic received from this UE does
         not have an MPLS label."
    ::= { tmnxWlanGwUeResEntry 102 }

tmnxWlanGwUeResLastMoveTime      OBJECT-TYPE
    SYNTAX      DateAndTime (SIZE (11))
    MAX-ACCESS  read-only
    STATUS      current
    DESCRIPTION
        "The value of tmnxWlanGwUeResLastMoveTime indicates the time of the
         most recent Access Point move of this UE."
    ::= { tmnxWlanGwUeResEntry 103 }

tmnxWlanGwUeResExpirationTime    OBJECT-TYPE
    SYNTAX      DateAndTime (SIZE (11))
    MAX-ACCESS  read-only
    STATUS      current
    DESCRIPTION
        "The value of tmnxWlanGwUeResExpirationTime indicates the time when the
         system context of this UE will expire and be removed from this system,
         unless it is renewed."
    ::= { tmnxWlanGwUeResEntry 104 }

tmnxWlanGwUeResIdleTimeout       OBJECT-TYPE
    SYNTAX      Unsigned32
    UNITS       "seconds"
    MAX-ACCESS  read-only
    STATUS      current
    DESCRIPTION
        "The value of tmnxWlanGwUeResIdleTimeout indicates the time that this
         UE can remain inactive before its system context will be removed from
         this system.

         An idle timeout can be imposed by an AAA server."
    ::= { tmnxWlanGwUeResEntry 105 }

tmnxWlanGwUeResSessionTimeout    OBJECT-TYPE
    SYNTAX      DateAndTime (SIZE (11))
    MAX-ACCESS  read-only
    STATUS      current
    DESCRIPTION
        "The value of tmnxWlanGwUeResSessionTimeout indicates the time when
         this UE's system context will be removed unconditionally.

         A session timeout can be imposed by an AAA server."
    ::= { tmnxWlanGwUeResEntry 106 }

tmnxWlanGwUeResNatPlcy           OBJECT-TYPE
    SYNTAX      TNamedItemOrEmpty
    MAX-ACCESS  read-only
    STATUS      current
    DESCRIPTION
        "The value of tmnxWlanGwUeResNatPlcy indicates the NAT (Network Address
         Translation) policy of this UE.

         This object refers to a conceptual row in the
         TIMETRA-NAT-MIB::tmnxNatPolicyTable.

         One source for this information is the tmnxWlanGwVlanNatPlcy."
    ::= { tmnxWlanGwUeResEntry 107 }

tmnxWlanGwUeResHttpRdrPlcy       OBJECT-TYPE
    SYNTAX      TNamedItemOrEmpty
    MAX-ACCESS  read-only
    STATUS      current
    DESCRIPTION
        "The value of tmnxWlanGwUeResHttpRdrPlcy indicates the HTTP redirect
         policy of this UE.

         This object refers to a conceptual row in the
         TIMETRA-SUBSCRIBER-MGMT-MIB::tmnxSubHttpRdrPlcyTable.

         One source for this information is the tmnxWlanGwVlanHttpRdrPlcy."
    ::= { tmnxWlanGwUeResEntry 108 }

tmnxWlanGwUeResDsmIpFilter       OBJECT-TYPE
    SYNTAX      TNamedItemOrEmpty
    MAX-ACCESS  read-only
    STATUS      current
    DESCRIPTION
        "The value of tmnxWlanGwUeResDsmIpFilter indicates the DSM IP filter of
         this UE.

         This object refers to a conceptual row in the tmnxWlanGwDsmIpFilTable.

         One source for this information is the tmnxWlanGwVlanDsmIpFilter."
    ::= { tmnxWlanGwUeResEntry 109 }

tmnxWlanGwUeResDsmAcctPlcy       OBJECT-TYPE
    SYNTAX      TNamedItemOrEmpty
    MAX-ACCESS  read-only
    STATUS      current
    DESCRIPTION
        "The value of tmnxWlanGwUeResDsmAcctPlcy indicates the accounting
         policy of this UE.

         This object refers to a conceptual row in the
         TIMETRA-RADIUS-MIB::tmnxRadIsaPlcyTable.

         One source for this information is the tmnxWlanGwVlanDsmAcctPlcy."
    ::= { tmnxWlanGwUeResEntry 110 }

tmnxWlanGwUeResDsmAcctUpdInterv  OBJECT-TYPE
    SYNTAX      Unsigned32
    UNITS       "seconds"
    MAX-ACCESS  read-only
    STATUS      current
    DESCRIPTION
        "The value of tmnxWlanGwUeResDsmAcctUpdInterv indicates the time
         interval between consecutive Interim Accounting Update messages.

         One source for this information is the tmnxWlanGwVlanDsmAcctUpdInterv."
    ::= { tmnxWlanGwUeResEntry 111 }

tmnxWlanGwUeResAcctUpdate        OBJECT-TYPE
    SYNTAX      DateAndTime (SIZE (11))
    MAX-ACCESS  read-only
    STATUS      current
    DESCRIPTION
        "The value of tmnxWlanGwUeResAcctUpdate indicates the time when the
         next accounting update for this UE is going to be transmitted."
    ::= { tmnxWlanGwUeResEntry 112 }

tmnxWlanGwUeResIngOperPir        OBJECT-TYPE
    SYNTAX      TPIRRate
    UNITS       "kilobps"
    MAX-ACCESS  read-only
    STATUS      current
    DESCRIPTION
        "The value of tmnxWlanGwUeResIngOperPir indicates the actual ingress
         PIR (Peak Information Rate).

         One source for this information is the tmnxWlanGwPolicerAdminPIR."
    ::= { tmnxWlanGwUeResEntry 113 }

tmnxWlanGwUeResIngOperCir        OBJECT-TYPE
    SYNTAX      TCIRRate
    UNITS       "kilobps"
    MAX-ACCESS  read-only
    STATUS      current
    DESCRIPTION
        "The value of tmnxWlanGwUeResIngOperCir indicates the actual ingress
         CIR (Committed Information Rate).

         One source for this information is the tmnxWlanGwPolicerAdminCIR."
    ::= { tmnxWlanGwUeResEntry 114 }

tmnxWlanGwUeResEgrOperPir        OBJECT-TYPE
    SYNTAX      TPIRRate
    UNITS       "kilobps"
    MAX-ACCESS  read-only
    STATUS      current
    DESCRIPTION
        "The value of tmnxWlanGwUeResEgrOperPir indicates the actual egress PIR
         (Peak Information Rate).

         One source for this information is the tmnxWlanGwPolicerAdminPIR."
    ::= { tmnxWlanGwUeResEntry 115 }

tmnxWlanGwUeResEgrOperCir        OBJECT-TYPE
    SYNTAX      TCIRRate
    UNITS       "kilobps"
    MAX-ACCESS  read-only
    STATUS      current
    DESCRIPTION
        "The value of tmnxWlanGwUeResEgrOperCir indicates the actual egress CIR
         (Committed Information Rate).

         One source for this information is the tmnxWlanGwPolicerAdminCIR."
    ::= { tmnxWlanGwUeResEntry 116 }

tmnxWlanGwUeResDsmAppProfile     OBJECT-TYPE
    SYNTAX      TNamedItemOrEmpty
    MAX-ACCESS  read-only
    STATUS      current
    DESCRIPTION
        "The value of tmnxWlanGwUeResDsmAppProfile indicates the application
         profile of this UE.

         This object refers to a conceptual row in the
         TIMETRA-BSX-NG-MIB::tmnxBsxAppProfTable.

         One source for this information is the tmnxWlanGwVlanDsmDefAppProfile."
    ::= { tmnxWlanGwUeResEntry 130 }

tmnxWlanGwUeResRxPkts            OBJECT-TYPE
    SYNTAX      Counter64
    MAX-ACCESS  read-only
    STATUS      current
    DESCRIPTION
        "The value of tmnxWlanGwUeResRxPkts indicates the number of packets
         received from this UE."
    ::= { tmnxWlanGwUeResEntry 200 }

tmnxWlanGwUeResRxOctets          OBJECT-TYPE
    SYNTAX      Counter64
    MAX-ACCESS  read-only
    STATUS      current
    DESCRIPTION
        "The value of tmnxWlanGwUeResRxOctets indicates the number of octets
         received from this UE."
    ::= { tmnxWlanGwUeResEntry 201 }

tmnxWlanGwUeResTxPkts            OBJECT-TYPE
    SYNTAX      Counter64
    MAX-ACCESS  read-only
    STATUS      current
    DESCRIPTION
        "The value of tmnxWlanGwUeResTxPkts indicates the number of packets
         transmitted to this UE."
    ::= { tmnxWlanGwUeResEntry 202 }

tmnxWlanGwUeResTxOctets          OBJECT-TYPE
    SYNTAX      Counter64
    MAX-ACCESS  read-only
    STATUS      current
    DESCRIPTION
        "The value of tmnxWlanGwUeResTxOctets indicates the number of octets
         transmitted to this UE."
    ::= { tmnxWlanGwUeResEntry 203 }

tmnxWlanGwUeResSlaacAddrType     OBJECT-TYPE
    SYNTAX      InetAddressType
    MAX-ACCESS  read-only
    STATUS      current
    DESCRIPTION
        "The value of tmnxWlanGwUeResSlaacAddrType indicates the type of
         tmnxWlanGwUeResSlaacPref, tmnxWlanGwUeResSlaacAddr1,
         tmnxWlanGwUeResSlaacAddr2 and tmnxWlanGwUeResSlaacAddr3."
    ::= { tmnxWlanGwUeResEntry 300 }

tmnxWlanGwUeResSlaacPref         OBJECT-TYPE
    SYNTAX      InetAddress (SIZE (0|16))
    MAX-ACCESS  read-only
    STATUS      current
    DESCRIPTION
        "The value of tmnxWlanGwUeResSlaacPref indicates the SLAAC prefix."
    ::= { tmnxWlanGwUeResEntry 301 }

tmnxWlanGwUeResSlaacAddr1        OBJECT-TYPE
    SYNTAX      InetAddress (SIZE (0|16))
    MAX-ACCESS  read-only
    STATUS      current
    DESCRIPTION
        "The value of tmnxWlanGwUeResSlaacAddr1 indicates the SLAAC address (1
         of 3)."
    ::= { tmnxWlanGwUeResEntry 302 }

tmnxWlanGwUeResSlaacAddr2        OBJECT-TYPE
    SYNTAX      InetAddress (SIZE (0|16))
    MAX-ACCESS  read-only
    STATUS      current
    DESCRIPTION
        "The value of tmnxWlanGwUeResSlaacAddr2 indicates the SLAAC address (2
         of 3)."
    ::= { tmnxWlanGwUeResEntry 303 }

tmnxWlanGwUeResSlaacAddr3        OBJECT-TYPE
    SYNTAX      InetAddress (SIZE (0|16))
    MAX-ACCESS  read-only
    STATUS      current
    DESCRIPTION
        "The value of tmnxWlanGwUeResSlaacAddr3 indicates the SLAAC address (3
         of 3)."
    ::= { tmnxWlanGwUeResEntry 304 }

tmnxWlanGwUeResDhcp6AddrType     OBJECT-TYPE
    SYNTAX      InetAddressType
    MAX-ACCESS  read-only
    STATUS      current
    DESCRIPTION
        "The value of tmnxWlanGwUeResDhcp6AddrType indicates the type of
         tmnxWlanGwUeResDhcp6Addr."
    ::= { tmnxWlanGwUeResEntry 305 }

tmnxWlanGwUeResDhcp6Addr         OBJECT-TYPE
    SYNTAX      InetAddress (SIZE (0|16))
    MAX-ACCESS  read-only
    STATUS      current
    DESCRIPTION
        "The value of tmnxWlanGwUeResDhcp6Addr indicates the DHCPv6 address."
    ::= { tmnxWlanGwUeResEntry 306 }

tmnxWlanGwUeResDhcp6AddrDepr     OBJECT-TYPE
    SYNTAX      TruthValue
    MAX-ACCESS  read-only
    STATUS      current
    DESCRIPTION
        "The value of tmnxWlanGwUeResDhcp6AddrDepr indicates whether the DHCPv6
         address is deprecated or not."
    ::= { tmnxWlanGwUeResEntry 307 }

tmnxWlanGwUeResDhcp6IAID         OBJECT-TYPE
    SYNTAX      Unsigned32
    MAX-ACCESS  read-only
    STATUS      current
    DESCRIPTION
        "The value of tmnxWlanGwUeResDhcp6IAID indicates the DHCPv6 Identity
         Association Identifier IAID."
    ::= { tmnxWlanGwUeResEntry 308 }

tmnxWlanGwUeResDhcp6IAIDValid    OBJECT-TYPE
    SYNTAX      TruthValue
    MAX-ACCESS  read-only
    STATUS      current
    DESCRIPTION
        "The value of tmnxWlanGwUeResDhcp6IAIDValid indicates whether the IAID
         available in tmnxWlanGwUeResDhcp6IAID is valid or not."
    ::= { tmnxWlanGwUeResEntry 309 }

tmnxWlanGwUeResSlaacLeaseExpire  OBJECT-TYPE
    SYNTAX      DateAndTime (SIZE (11))
    MAX-ACCESS  read-only
    STATUS      current
    DESCRIPTION
        "The value of tmnxWlanGwUeResSlaacLeaseExpire indicates when the lease
         of the Slaac prefix and addresses will expire."
    ::= { tmnxWlanGwUeResEntry 310 }

tmnxWlanGwUeResDhcp6LeaseExpire  OBJECT-TYPE
    SYNTAX      DateAndTime (SIZE (11))
    MAX-ACCESS  read-only
    STATUS      current
    DESCRIPTION
        "The value of tmnxWlanGwUeResDhcp6LeaseExpire indicates when the lease
         of the DHCPv6 address will expire."
    ::= { tmnxWlanGwUeResEntry 311 }

tmnxWlanGwUeResDhcpAddrDepr      OBJECT-TYPE
    SYNTAX      TruthValue
    MAX-ACCESS  read-only
    STATUS      current
    DESCRIPTION
        "The value of tmnxWlanGwUeResDhcpAddrDepr indicates whether the DHCP
         address is deprecated or not."
    ::= { tmnxWlanGwUeResEntry 400 }

tmnxWlanGwUeResBridgeId          OBJECT-TYPE
    SYNTAX      Unsigned32
    MAX-ACCESS  read-only
    STATUS      current
    DESCRIPTION
        "The value of the object tmnxWlanGwUeResBridgeId indicates  the
         identifier of the bridge associated with this UE."
    ::= { tmnxWlanGwUeResEntry 410 }

tmnxWlanGwUeResAddrFamily        OBJECT-TYPE
    SYNTAX      TmnxWlanGwUeAddressFamily
    MAX-ACCESS  read-only
    STATUS      current
    DESCRIPTION
        "The value of the object tmnxWlanGwUeResAddrFamily indicates the UE's
         address family."
    ::= { tmnxWlanGwUeResEntry 420 }

tmnxWlanGwUeResHardQuotaOctets   OBJECT-TYPE
    SYNTAX      Counter64
    MAX-ACCESS  read-only
    STATUS      current
    DESCRIPTION
        "The value of the object tmnxWlanGwUeResHardQuotaOctets indicates the
         remaining octets that a UE can consume before hitting the hard quota."
    ::= { tmnxWlanGwUeResEntry 430 }

tmnxWlanGwUeResSoftQuotaOctets   OBJECT-TYPE
    SYNTAX      Counter64
    MAX-ACCESS  read-only
    STATUS      current
    DESCRIPTION
        "The value of the object tmnxWlanGwUeResSoftQuotaOctets indicates the
         remaining octets that a UE can consume before hitting the soft quota."
    ::= { tmnxWlanGwUeResEntry 431 }

tmnxWlanGwUeResL2Service         OBJECT-TYPE
    SYNTAX      TLNamedItemOrEmpty
    MAX-ACCESS  read-only
    STATUS      current
    DESCRIPTION
        "The value of tmnxWlanGwUeResL2Service indicates the L2 service of this
         UE.

         This object refers to a conceptual row in the tmnxWlanGwVplsTable."
    ::= { tmnxWlanGwUeResEntry 432 }

tmnxWlanGwVplsTable              OBJECT-TYPE
    SYNTAX      SEQUENCE OF TmnxWlanGwVplsEntry
    MAX-ACCESS  not-accessible
    STATUS      current
    DESCRIPTION
        "The tmnxWlanGwVplsTable has an entry for each TLS Service."
    ::= { tmnxWlanGwObjs 12 }

tmnxWlanGwVplsEntry              OBJECT-TYPE
    SYNTAX      TmnxWlanGwVplsEntry
    MAX-ACCESS  not-accessible
    STATUS      current
    DESCRIPTION
        "Each row entry in the tmnxWlanGwVplsTable represents additional
         columns in the TIMETRA-SERV-MIB::svcTlsInfoTable for attributes needed
         in a multi-chassis operation."
    AUGMENTS    { svcTlsInfoEntry }
    ::= { tmnxWlanGwVplsTable 1 }

TmnxWlanGwVplsEntry              ::= SEQUENCE
{
    tmnxWlanGwVplsLastMgmtChange     TimeStamp,
    tmnxWlanGwVplsAdminState         TmnxEnabledDisabled,
    tmnxWlanGwVplsDescription        TItemDescription,
    tmnxWlanGwVplsSapTemplate        TNamedItemOrEmpty,
    tmnxWlanGwVplsWlanGwGrpId        TmnxWlanGwIsaGrpIdOrZero
}

tmnxWlanGwVplsLastMgmtChange     OBJECT-TYPE
    SYNTAX      TimeStamp
    MAX-ACCESS  read-only
    STATUS      current
    DESCRIPTION
        "The value of tmnxWlanGwVplsLastMgmtChange indicates the sysUpTime at
         the time of the last change of this entry.

         If no changes occurred since the last re-initialization of the local
         network management subsystem, then this object contains a zero value."
    ::= { tmnxWlanGwVplsEntry 1 }

tmnxWlanGwVplsAdminState         OBJECT-TYPE
    SYNTAX      TmnxEnabledDisabled
    MAX-ACCESS  read-write
    STATUS      current
    DESCRIPTION
        "The value of tmnxWlanGwVplsAdminState specifies the administrative
         status of this conceptual row."
    DEFVAL      { disabled }
    ::= { tmnxWlanGwVplsEntry 2 }

tmnxWlanGwVplsDescription        OBJECT-TYPE
    SYNTAX      TItemDescription
    MAX-ACCESS  read-write
    STATUS      current
    DESCRIPTION
        "The value of tmnxWlanGwVplsDescription specifies the description of
         this conceptual row."
    DEFVAL      { ''H }
    ::= { tmnxWlanGwVplsEntry 3 }

tmnxWlanGwVplsSapTemplate        OBJECT-TYPE
    SYNTAX      TNamedItemOrEmpty
    MAX-ACCESS  read-write
    STATUS      current
    DESCRIPTION
        "The value of tmnxWlanGwVplsSapTemplate specifies the name of the VPLS
         SAP template associated with this VPLS service for the purpose of WLAN
         Gateway Layer 2 wholesale.

         While the value of tmnxWlanGwVplsSapTemplate is not empty, a
         conceptual row with the same name must exist in the
         TIMETRA-SAP-MIB::sapTmplTable.

         The configuration in the template is applied to the internal
         connection between the WLAN Gateway service and the Layer 2 service."
    DEFVAL      { ''H }
    ::= { tmnxWlanGwVplsEntry 4 }

tmnxWlanGwVplsWlanGwGrpId        OBJECT-TYPE
    SYNTAX      TmnxWlanGwIsaGrpIdOrZero
    MAX-ACCESS  read-write
    STATUS      current
    DESCRIPTION
        "The value of tmnxWlanGwVplsWlanGwGrpId specifies the identifier of
         the WLAN Gateway group that processes layer 2 traffic in this TLS
         service.

         A non-zero value is only required for TLS services used for layer 2
         wholesale provisioned dynamically via RADIUS. For TLS services that
         are only referred to in tmnxWlanGwVlanL2Service, the value can be
         zero."
    DEFVAL      { 0 }
    ::= { tmnxWlanGwVplsEntry 5 }

tmnxWlanGwVlanSubObjs            OBJECT IDENTIFIER ::= { tmnxWlanGwObjs 13 }

tmnxWlanGwVlanDhcp6Table         OBJECT-TYPE
    SYNTAX      SEQUENCE OF TmnxWlanGwVlanDhcp6Entry
    MAX-ACCESS  not-accessible
    STATUS      current
    DESCRIPTION
        "The tmnxWlanGwVlanDhcp6Table contains objects to configure the DHCPv6
         configuration data for WLAN GW VLAN ranges."
    ::= { tmnxWlanGwVlanSubObjs 2 }

tmnxWlanGwVlanDhcp6Entry         OBJECT-TYPE
    SYNTAX      TmnxWlanGwVlanDhcp6Entry
    MAX-ACCESS  not-accessible
    STATUS      current
    DESCRIPTION
        "Each conceptual row represents the set of DHCPv6 configuration data
         for a range of VLAN Q-tags."
    AUGMENTS    { tmnxWlanGwVlanEntry }
    ::= { tmnxWlanGwVlanDhcp6Table 1 }

TmnxWlanGwVlanDhcp6Entry         ::= SEQUENCE
{
    tmnxWlanGwVlanDhcp6LastChanged   TimeStamp,
    tmnxWlanGwVlanDhcp6InitPrefLt    Unsigned32,
    tmnxWlanGwVlanDhcp6ActPrefLt     Unsigned32,
    tmnxWlanGwVlanDhcp6InitValidLt   Unsigned32,
    tmnxWlanGwVlanDhcp6ActValidLt    Unsigned32,
    tmnxWlanGwVlanDhcp6AdminState    TmnxEnabledDisabled
}

tmnxWlanGwVlanDhcp6LastChanged   OBJECT-TYPE
    SYNTAX      TimeStamp
    MAX-ACCESS  read-only
    STATUS      current
    DESCRIPTION
        "The value of tmnxWlanGwVlanDhcp6LastChanged indicates the time of the
         most recent management-initiated change."
    ::= { tmnxWlanGwVlanDhcp6Entry 1 }

tmnxWlanGwVlanDhcp6InitPrefLt    OBJECT-TYPE
    SYNTAX      Unsigned32 (300..3600)
    UNITS       "seconds"
    MAX-ACCESS  read-create
    STATUS      current
    DESCRIPTION
        "The value of tmnxWlanGwVlanDhcp6InitPrefLt specifies the signaled
         preferred lifetime in DHCPv6 during migrant phase."
    DEFVAL      { 300 }
    ::= { tmnxWlanGwVlanDhcp6Entry 2 }

tmnxWlanGwVlanDhcp6ActPrefLt     OBJECT-TYPE
    SYNTAX      Unsigned32 (300..3600)
    UNITS       "seconds"
    MAX-ACCESS  read-create
    STATUS      current
    DESCRIPTION
        "The value of tmnxWlanGwVlanDhcp6ActPrefLt specifies the signaled
         preferred lifetime in DHCPv6 after full authentication. (DSM and/or
         ESM)"
    DEFVAL      { 600 }
    ::= { tmnxWlanGwVlanDhcp6Entry 3 }

tmnxWlanGwVlanDhcp6InitValidLt   OBJECT-TYPE
    SYNTAX      Unsigned32 (300..3600)
    UNITS       "seconds"
    MAX-ACCESS  read-create
    STATUS      current
    DESCRIPTION
        "The value of tmnxWlanGwVlanDhcp6InitValidLt specifies the signaled
         valid lifetime in DHCPv6 during migrant phase."
    DEFVAL      { 300 }
    ::= { tmnxWlanGwVlanDhcp6Entry 4 }

tmnxWlanGwVlanDhcp6ActValidLt    OBJECT-TYPE
    SYNTAX      Unsigned32 (300..3600)
    UNITS       "seconds"
    MAX-ACCESS  read-create
    STATUS      current
    DESCRIPTION
        "The value of tmnxWlanGwVlanDhcp6ActValidLt specifies the signaled
         valid lifetime in DHCPv6 after full authentication. (DSM and/or ESM)"
    DEFVAL      { 600 }
    ::= { tmnxWlanGwVlanDhcp6Entry 5 }

tmnxWlanGwVlanDhcp6AdminState    OBJECT-TYPE
    SYNTAX      TmnxEnabledDisabled
    MAX-ACCESS  read-create
    STATUS      current
    DESCRIPTION
        "The value of tmnxWlanGwVlanDhcp6AdminState specifies the
         administrative state of the DHCPv6 client."
    DEFVAL      { disabled }
    ::= { tmnxWlanGwVlanDhcp6Entry 6 }

tmnxWlanGwVlanSlaacTable         OBJECT-TYPE
    SYNTAX      SEQUENCE OF TmnxWlanGwVlanSlaacEntry
    MAX-ACCESS  not-accessible
    STATUS      current
    DESCRIPTION
        "The tmnxWlanGwVlanSlaacTable contains objects to configure the SLAAC
         configuration data for WLAN GW VLAN ranges."
    ::= { tmnxWlanGwVlanSubObjs 3 }

tmnxWlanGwVlanSlaacEntry         OBJECT-TYPE
    SYNTAX      TmnxWlanGwVlanSlaacEntry
    MAX-ACCESS  not-accessible
    STATUS      current
    DESCRIPTION
        "Each conceptual row represents the set of SLAAC configuration data for
         a range of VLAN Q-tags."
    AUGMENTS    { tmnxWlanGwVlanEntry }
    ::= { tmnxWlanGwVlanSlaacTable 1 }

TmnxWlanGwVlanSlaacEntry         ::= SEQUENCE
{
    tmnxWlanGwVlanSlaacLastChanged   TimeStamp,
    tmnxWlanGwVlanSlaacInitPrefLt    Unsigned32,
    tmnxWlanGwVlanSlaacActPrefLt     Unsigned32,
    tmnxWlanGwVlanSlaacInitValidLt   Unsigned32,
    tmnxWlanGwVlanSlaacActValidLt    Unsigned32,
    tmnxWlanGwVlanSlaacAdminState    TmnxEnabledDisabled
}

tmnxWlanGwVlanSlaacLastChanged   OBJECT-TYPE
    SYNTAX      TimeStamp
    MAX-ACCESS  read-only
    STATUS      current
    DESCRIPTION
        "The value of tmnxWlanGwVlanSlaacLastChanged indicates the time of the
         most recent management-initiated change."
    ::= { tmnxWlanGwVlanSlaacEntry 1 }

tmnxWlanGwVlanSlaacInitPrefLt    OBJECT-TYPE
    SYNTAX      Unsigned32 (300..3600)
    UNITS       "seconds"
    MAX-ACCESS  read-create
    STATUS      current
    DESCRIPTION
        "The value of tmnxWlanGwVlanSlaacInitPrefLt specifies the signaled
         preferred lifetime in DHCPv6 during migrant phase."
    DEFVAL      { 300 }
    ::= { tmnxWlanGwVlanSlaacEntry 2 }

tmnxWlanGwVlanSlaacActPrefLt     OBJECT-TYPE
    SYNTAX      Unsigned32 (300..3600)
    UNITS       "seconds"
    MAX-ACCESS  read-create
    STATUS      current
    DESCRIPTION
        "The value of tmnxWlanGwVlanSlaacActPrefLt specifies the signaled
         preferred lifetime in DHCPv6 after full authentication. (DSM and/or
         ESM)"
    DEFVAL      { 600 }
    ::= { tmnxWlanGwVlanSlaacEntry 3 }

tmnxWlanGwVlanSlaacInitValidLt   OBJECT-TYPE
    SYNTAX      Unsigned32 (300..3600)
    UNITS       "seconds"
    MAX-ACCESS  read-create
    STATUS      current
    DESCRIPTION
        "The value of tmnxWlanGwVlanSlaacInitValidLt specifies the signaled
         valid lifetime in DHCPv6 during migrant phase."
    DEFVAL      { 300 }
    ::= { tmnxWlanGwVlanSlaacEntry 4 }

tmnxWlanGwVlanSlaacActValidLt    OBJECT-TYPE
    SYNTAX      Unsigned32 (300..3600)
    UNITS       "seconds"
    MAX-ACCESS  read-create
    STATUS      current
    DESCRIPTION
        "The value of tmnxWlanGwVlanSlaacActValidLt specifies the signaled
         valid lifetime in DHCPv6 after full authentication. (DSM and/or ESM)"
    DEFVAL      { 600 }
    ::= { tmnxWlanGwVlanSlaacEntry 5 }

tmnxWlanGwVlanSlaacAdminState    OBJECT-TYPE
    SYNTAX      TmnxEnabledDisabled
    MAX-ACCESS  read-create
    STATUS      current
    DESCRIPTION
        "The value of tmnxWlanGwVlanSlaacAdminState specifies the
         administrative state of the SLAAC client."
    DEFVAL      { disabled }
    ::= { tmnxWlanGwVlanSlaacEntry 6 }

tmnxWlanGwVlanBrgTable           OBJECT-TYPE
    SYNTAX      SEQUENCE OF TmnxWlanGwVlanBrgEntry
    MAX-ACCESS  not-accessible
    STATUS      current
    DESCRIPTION
        "The tmnxWlanGwVlanBrgTable contains objects to configure Bridged
         Residential Gateways (BRG) for WLAN GW VLAN ranges."
    ::= { tmnxWlanGwVlanSubObjs 4 }

tmnxWlanGwVlanBrgEntry           OBJECT-TYPE
    SYNTAX      TmnxWlanGwVlanBrgEntry
    MAX-ACCESS  not-accessible
    STATUS      current
    DESCRIPTION
        "Each conceptual row represents the set of BRG configuration data for a
         range of VLAN Q-tags."
    AUGMENTS    { tmnxWlanGwVlanEntry }
    ::= { tmnxWlanGwVlanBrgTable 1 }

TmnxWlanGwVlanBrgEntry           ::= SEQUENCE
{
    tmnxWlanGwVlanBrgLastChanged     TimeStamp,
    tmnxWlanGwVlanBrgAdminState      TmnxEnabledDisabled,
    tmnxWlanGwVlanBrgDefBrgProfile   TNamedItemOrEmpty,
    tmnxWlanGwVlanBrgAuthedBrgOnly   TruthValue
}

tmnxWlanGwVlanBrgLastChanged     OBJECT-TYPE
    SYNTAX      TimeStamp
    MAX-ACCESS  read-only
    STATUS      current
    DESCRIPTION
        "The value of tmnxWlanGwVlanBrgLastChanged indicates the time of the
         most recent management-initiated change."
    ::= { tmnxWlanGwVlanBrgEntry 1 }

tmnxWlanGwVlanBrgAdminState      OBJECT-TYPE
    SYNTAX      TmnxEnabledDisabled
    MAX-ACCESS  read-create
    STATUS      current
    DESCRIPTION
        "The value of tmnxWlanGwVlanBrgAdminState specifies the administrative
         status of the Bridged Residential Gateway function."
    DEFVAL      { disabled }
    ::= { tmnxWlanGwVlanBrgEntry 2 }

tmnxWlanGwVlanBrgDefBrgProfile   OBJECT-TYPE
    SYNTAX      TNamedItemOrEmpty
    MAX-ACCESS  read-create
    STATUS      current
    DESCRIPTION
        "The value of tmnxWlanGwVlanBrgDefBrgProfile specifies the BRG profile
         to use when no BRG profile is obtained from the AAA server.

         A non empty value must correspond to a conceptual row in the
         TIMETRA-SUBSCRIBER-MGMT-MIB::tmnxSubBrgProfTable."
    DEFVAL      { "" }
    ::= { tmnxWlanGwVlanBrgEntry 3 }

tmnxWlanGwVlanBrgAuthedBrgOnly   OBJECT-TYPE
    SYNTAX      TruthValue
    MAX-ACCESS  read-create
    STATUS      current
    DESCRIPTION
        "The value of tmnxWlanGwVlanBrgAuthedBrgOnly specifies if this system
         only accepts (hosts behind) Bridged Residential Gateway devices
         already authenticated."
    DEFVAL      { false }
    ::= { tmnxWlanGwVlanBrgEntry 4 }

tmnxWlanGwVlanLeTable            OBJECT-TYPE
    SYNTAX      SEQUENCE OF TmnxWlanGwVlanLeEntry
    MAX-ACCESS  not-accessible
    STATUS      current
    DESCRIPTION
        "The tmnxWlanGwVlanLeTable contains objects to configure home LAN
         Extension for WLAN GW VLAN ranges."
    ::= { tmnxWlanGwVlanSubObjs 5 }

tmnxWlanGwVlanLeEntry            OBJECT-TYPE
    SYNTAX      TmnxWlanGwVlanLeEntry
    MAX-ACCESS  not-accessible
    STATUS      current
    DESCRIPTION
        "Each conceptual row represents the set of configuration data for a LAN
         Extension range of VLAN Q-tags on a particular interface.

         Users whose traffic comes in on this interface  tagged with a matching
         VLAN Q-tag are to be processed according to the configuration
         specified in this conceptual row; otherwise, the default configuration
         specified  in the default range [4096-4096] must be used.

         Entries in this table are created and destroyed automatically by the
         system."
    AUGMENTS    { tmnxWlanGwVlanEntry }
    ::= { tmnxWlanGwVlanLeTable 1 }

TmnxWlanGwVlanLeEntry            ::= SEQUENCE
{
    tmnxWlanGwVlanLeLastChanged      TimeStamp,
    tmnxWlanGwVlanLeAdminState       TmnxEnabledDisabledAdminState,
    tmnxWlanGwVlanLeMacTranslation   TmnxEnabledDisabled,
    tmnxWlanGwVlanLeBdMacPrefix      MacAddress,
    tmnxWlanGwVlanLeBdMacPrefixLen   Unsigned32,
    tmnxWlanGwVlanLeAssistAddrRes    TmnxEnabledDisabled,
    tmnxWlanGwVlanLeNetwPolicer      TNamedItemOrEmpty,
    tmnxWlanGwVlanLeNetwMaxMac       Unsigned32,
    tmnxWlanGwVlanLeNetwAdminState   TmnxEnabledDisabledAdminState,
    tmnxWlanGwVlanLeAccsPolicer      TNamedItemOrEmpty,
    tmnxWlanGwVlanLeAccsMaxMac       Unsigned32,
    tmnxWlanGwVlanLeAccsMultiAccess  TruthValue
}

tmnxWlanGwVlanLeLastChanged      OBJECT-TYPE
    SYNTAX      TimeStamp
    MAX-ACCESS  read-only
    STATUS      current
    DESCRIPTION
        "The value of tmnxWlanGwVlanLeLastChanged indicates the sysUpTime at
         the time of the most recent management-initiated change to this table
         row."
    ::= { tmnxWlanGwVlanLeEntry 1 }

tmnxWlanGwVlanLeAdminState       OBJECT-TYPE
    SYNTAX      TmnxEnabledDisabledAdminState
    MAX-ACCESS  read-create
    STATUS      current
    DESCRIPTION
        "The value of tmnxWlanGwVlanLeAdminState specifies the administrative
         state of the home LAN Extension."
    DEFVAL      { disabled }
    ::= { tmnxWlanGwVlanLeEntry 2 }

tmnxWlanGwVlanLeMacTranslation   OBJECT-TYPE
    SYNTAX      TmnxEnabledDisabled
    MAX-ACCESS  read-create
    STATUS      current
    DESCRIPTION
        "The value of tmnxWlanGwVlanLeMacTranslation specifies whether MAC
         translation is enabled in bridge domains or not."
    DEFVAL      { disabled }
    ::= { tmnxWlanGwVlanLeEntry 3 }

tmnxWlanGwVlanLeBdMacPrefix      OBJECT-TYPE
    SYNTAX      MacAddress
    MAX-ACCESS  read-create
    STATUS      current
    DESCRIPTION
        "The value of tmnxWlanGwVlanLeBdMacPrefix specifies the prefix that is
         used to derive the MAC for each bridge domain in case MAC  translation
         is enabled."
    DEFVAL      { 'FFFFFF000000'H }
    ::= { tmnxWlanGwVlanLeEntry 4 }

tmnxWlanGwVlanLeBdMacPrefixLen   OBJECT-TYPE
    SYNTAX      Unsigned32 (3)
    MAX-ACCESS  read-create
    STATUS      current
    DESCRIPTION
        "The value of tmnxWlanGwVlanLeBdMacPrefixLen specifies the number of
         octets in tmnxWlanGwVlanLeBdMacPrefix to use as prefix. Currently only
         3 is supported."
    DEFVAL      { 3 }
    ::= { tmnxWlanGwVlanLeEntry 5 }

tmnxWlanGwVlanLeAssistAddrRes    OBJECT-TYPE
    SYNTAX      TmnxEnabledDisabled
    MAX-ACCESS  read-create
    STATUS      current
    DESCRIPTION
        "The value of tmnxWlanGwVlanLeAssistAddrRes specifies whether the
         assistive address resolution is enabled in bridge domains."
    DEFVAL      { disabled }
    ::= { tmnxWlanGwVlanLeEntry 7 }

tmnxWlanGwVlanLeNetwPolicer      OBJECT-TYPE
    SYNTAX      TNamedItemOrEmpty
    MAX-ACCESS  read-create
    STATUS      current
    DESCRIPTION
        "The value of tmnxWlanGwVlanLeNetwPolicer specifies the identifier of
         the distributed-sub-mgmt policer for ingress data center traffic.

         An entry with the same name must exist in the tmnxWlanGwPolicerTable."
    DEFVAL      { "" }
    ::= { tmnxWlanGwVlanLeEntry 8 }

tmnxWlanGwVlanLeNetwMaxMac       OBJECT-TYPE
    SYNTAX      Unsigned32 (1..64)
    MAX-ACCESS  read-create
    STATUS      current
    DESCRIPTION
        "The value of tmnxWlanGwVlanLeNetwMaxMac specifies the maximum number
         of VM MAC entries in each bridge domain."
    DEFVAL      { 20 }
    ::= { tmnxWlanGwVlanLeEntry 10 }

tmnxWlanGwVlanLeNetwAdminState   OBJECT-TYPE
    SYNTAX      TmnxEnabledDisabledAdminState
    MAX-ACCESS  read-create
    STATUS      current
    DESCRIPTION
        "The value of tmnxWlanGwVlanLeNetwAdminState specifies whether data
         data center connections are allowed."
    DEFVAL      { enabled }
    ::= { tmnxWlanGwVlanLeEntry 11 }

tmnxWlanGwVlanLeAccsPolicer      OBJECT-TYPE
    SYNTAX      TNamedItemOrEmpty
    MAX-ACCESS  read-create
    STATUS      current
    DESCRIPTION
        "The value of tmnxWlanGwVlanLeAccsPolicer specifies the identifier of
         the distributed-sub-mgmt policer for ingress home traffic.

         An entry with the same name must exist in the tmnxWlanGwPolicerTable."
    DEFVAL      { "" }
    ::= { tmnxWlanGwVlanLeEntry 12 }

tmnxWlanGwVlanLeAccsMaxMac       OBJECT-TYPE
    SYNTAX      Unsigned32 (1..256)
    MAX-ACCESS  read-create
    STATUS      current
    DESCRIPTION
        "The value of tmnxWlanGwVlanLeAccsMaxMac specifies the maximum number
         of home MAC entries in each bridge domain."
    DEFVAL      { 20 }
    ::= { tmnxWlanGwVlanLeEntry 14 }

tmnxWlanGwVlanLeAccsMultiAccess  OBJECT-TYPE
    SYNTAX      TruthValue
    MAX-ACCESS  read-create
    STATUS      current
    DESCRIPTION
        "The value of tmnxWlanGwVlanLeAccsMultiAccess specifies if multiple
         access is allowed."
    DEFVAL      { false }
    ::= { tmnxWlanGwVlanLeEntry 20 }

tmnxWlanGwVlanExtTable           OBJECT-TYPE
    SYNTAX      SEQUENCE OF TmnxWlanGwVlanExtEntry
    MAX-ACCESS  not-accessible
    STATUS      current
    DESCRIPTION
        "The tmnxWlanGwVlanExtTable contains objects to configure VLAN
         extensions for WLAN Gateway VLAN ranges."
    ::= { tmnxWlanGwVlanSubObjs 6 }

tmnxWlanGwVlanExtEntry           OBJECT-TYPE
    SYNTAX      TmnxWlanGwVlanExtEntry
    MAX-ACCESS  not-accessible
    STATUS      current
    DESCRIPTION
        "Each conceptual row contains a VLAN extension associated with a WLAN
         Gateway VLAN range.

         Users whose traffic comes in on this interface  tagged with a VLAN
         Q-tag in the range
         [tmnxWlanGwVlanExtTagStart..tmnxWlanGwVlanExtTagEnd] are to be
         processed according to the configuration specified in the row with the
         same values for svcId, iesIfIndex, tmnxWlanGwVlanTagStart and
         tmnxWlanGwVlanTagEnd in the tmnxWlanGwVlanTable.

         Rows in this table are created and destroyed by means of SNMP
         operations on the tmnxWlanGwVlanExtRowStatus object.

         A row with the same values for svcId, iesIfIndex,
         tmnxWlanGwVlanTagStart and tmnxWlanGwVlanTagEnd must exist in the
         tmnxWlanGwVlanTable."
    INDEX       {
        svcId,
        iesIfIndex,
        tmnxWlanGwVlanTagStart,
        tmnxWlanGwVlanTagEnd,
        tmnxWlanGwVlanExtTagStart,
        tmnxWlanGwVlanExtTagEnd
    }
    ::= { tmnxWlanGwVlanExtTable 1 }

TmnxWlanGwVlanExtEntry           ::= SEQUENCE
{
    tmnxWlanGwVlanExtTagStart        Unsigned32,
    tmnxWlanGwVlanExtTagEnd          Unsigned32,
    tmnxWlanGwVlanExtRowStatus       RowStatus
}

tmnxWlanGwVlanExtTagStart        OBJECT-TYPE
    SYNTAX      Unsigned32 (0..4095)
    MAX-ACCESS  not-accessible
    STATUS      current
    DESCRIPTION
        "The value of the object tmnxWlanGwVlanExtTagStart specifies the start
         VLAN Q-tag of this VLAN extension."
    ::= { tmnxWlanGwVlanExtEntry 1 }

tmnxWlanGwVlanExtTagEnd          OBJECT-TYPE
    SYNTAX      Unsigned32 (0..4095)
    MAX-ACCESS  not-accessible
    STATUS      current
    DESCRIPTION
        "The value of the object tmnxWlanGwVlanExtTagEnd specifies the end VLAN
         Q-tag of this VLAN extension."
    ::= { tmnxWlanGwVlanExtEntry 2 }

tmnxWlanGwVlanExtRowStatus       OBJECT-TYPE
    SYNTAX      RowStatus
    MAX-ACCESS  read-create
    STATUS      current
    DESCRIPTION
        "The value of tmnxWlanGwVlanExtRowStatus specifies the row status of
         this row."
    ::= { tmnxWlanGwVlanExtEntry 3 }

tmnxWlanGwTuObjs                 OBJECT IDENTIFIER ::= { tmnxWlanGwObjs 14 }

tmnxWlanGwTuNextQryId            OBJECT-TYPE
    SYNTAX      Unsigned32
    MAX-ACCESS  read-only
    STATUS      current
    DESCRIPTION
        "The value of the object tmnxWlanGwTuNextQryId indicates the next
         available unique query identifier to use in tunnel queries.

         Multiple concurrent queries are supported; each query and its results
         are identified with a unique query ID supplied by the system."
    ::= { tmnxWlanGwTuObjs 1 }

tmnxWlanGwTuMaxQryId             OBJECT-TYPE
    SYNTAX      Unsigned32
    MAX-ACCESS  read-only
    STATUS      current
    DESCRIPTION
        "The value of the object tmnxWlanGwTuMaxQryId indicates the maximum
         value of a query identifier for use in tunnel queries.

         Multiple concurrent queries are supported; each query and its results
         are identified with a unique query ID supplied by the system.

         The value of the object tmnxWlanGwTuMaxQryId indicates also the
         maximum number of concurrent queries."
    ::= { tmnxWlanGwTuObjs 2 }

tmnxWlanGwTuQryTable             OBJECT-TYPE
    SYNTAX      SEQUENCE OF TmnxWlanGwTuQryEntry
    MAX-ACCESS  not-accessible
    STATUS      current
    DESCRIPTION
        "The tmnxWlanGwTuQryTable contains queries for tunnels.

         Conceptual rows in this table are created and destroyed by means of
         SNMP operations on the tmnxWlanGwTuQryRowStatus object.

         Conceptual rows in this table are volatile: they are lost upon reboot
         or switchover."
    ::= { tmnxWlanGwTuObjs 3 }

tmnxWlanGwTuQryEntry             OBJECT-TYPE
    SYNTAX      TmnxWlanGwTuQryEntry
    MAX-ACCESS  not-accessible
    STATUS      current
    DESCRIPTION
        "Each conceptual row represents a query for tunnels.

         Entries in this table can be created or deleted by means of SNMP
         operations on the tmnxWlanGwTuQryRowStatus object."
    INDEX       { tmnxWlanGwTuQryId }
    ::= { tmnxWlanGwTuQryTable 1 }

TmnxWlanGwTuQryEntry             ::= SEQUENCE
{
    tmnxWlanGwTuQryId                Unsigned32,
    tmnxWlanGwTuQryRowStatus         RowStatus,
    tmnxWlanGwTuQryWhereTuRouter     TmnxVRtrIDOrZero,
    tmnxWlanGwTuQryWhereRemAddrType  InetAddressType,
    tmnxWlanGwTuQryWhereRemAddr      InetAddress,
    tmnxWlanGwTuQryWhereLocAddrType  InetAddressType,
    tmnxWlanGwTuQryWhereLocAddr      InetAddress,
    tmnxWlanGwTuQryWhereAddrFamily   InetAddressType,
    tmnxWlanGwTuQryWhereEncap        BITS,
    tmnxWlanGwTuQryWhereEncapTag1    QTagFullRangeOrNone,
    tmnxWlanGwTuQryWhereEncapTag2    QTagFullRangeOrNone,
    tmnxWlanGwTuQryWhereApSapPortId  TmnxPortID,
    tmnxWlanGwTuQryWhereApSapEncap   TmnxEncapVal,
    tmnxWlanGwTuQryWhereNumUeMin     Unsigned32,
    tmnxWlanGwTuQryWhereNumUeMax     Unsigned32,
    tmnxWlanGwTuQryWhereApLearnFail  INTEGER,
    tmnxWlanGwTuQryWhereUeType       BITS,
    tmnxWlanGwTuQryDoGetNumResults   TruthValue,
    tmnxWlanGwTuQryNumResults        Gauge32,
    tmnxWlanGwTuQryName              TNamedItem,
    tmnxWlanGwTuQryVolatile          TruthValue
}

tmnxWlanGwTuQryId                OBJECT-TYPE
    SYNTAX      Unsigned32
    MAX-ACCESS  not-accessible
    STATUS      current
    DESCRIPTION
        "The value of tmnxWlanGwTuQryId specifies the query ID of this tunnel
         query.

         Get a unique query ID by means of an SNMP get on the
         tmnxWlanGwTuNextQryId object."
    ::= { tmnxWlanGwTuQryEntry 1 }

tmnxWlanGwTuQryRowStatus         OBJECT-TYPE
    SYNTAX      RowStatus
    MAX-ACCESS  read-create
    STATUS      current
    DESCRIPTION
        "The value of tmnxWlanGwTuQryRowStatus specifies the row status of this
         row."
    ::= { tmnxWlanGwTuQryEntry 2 }

tmnxWlanGwTuQryWhereTuRouter     OBJECT-TYPE
    SYNTAX      TmnxVRtrIDOrZero
    MAX-ACCESS  read-create
    STATUS      current
    DESCRIPTION
        "The value of tmnxWlanGwTuQryWhereTuRouter specifies the virtual router
         instance.

         When the value of tmnxWlanGwTuQryWhereTuRouter is non-zero, the
         tmnxWlanGwTuTable will contain only rows with this query ID where the
         value of tmnxWlanGwTuRouter is equal to this value."
    DEFVAL      { 0 }
    ::= { tmnxWlanGwTuQryEntry 3 }

tmnxWlanGwTuQryWhereRemAddrType  OBJECT-TYPE
    SYNTAX      InetAddressType
    MAX-ACCESS  read-create
    STATUS      current
    DESCRIPTION
        "The value of tmnxWlanGwTuQryWhereRemAddrType specifies the type of the
         remote IP address.

         When the value of tmnxWlanGwTuQryWhereRemAddrType is not 'unknown',
         the tmnxWlanGwTuTable will contain only rows with this query ID where
         the value of tmnxWlanGwTuRemoteAddrType is equal to this value."
    DEFVAL      { unknown }
    ::= { tmnxWlanGwTuQryEntry 4 }

tmnxWlanGwTuQryWhereRemAddr      OBJECT-TYPE
    SYNTAX      InetAddress (SIZE (0|4|16))
    MAX-ACCESS  read-create
    STATUS      current
    DESCRIPTION
        "The value of tmnxWlanGwTuQryWhereRemAddr specifies the IP address of
         the remote endpoint of the tunnel.

         When the value of tmnxWlanGwTuQryWhereRemAddr is not empty, the
         tmnxWlanGwTuTable will contain only rows where the value of
         tmnxWlanGwTuRemoteAddr is equal to this value."
    DEFVAL      { ''H }
    ::= { tmnxWlanGwTuQryEntry 5 }

tmnxWlanGwTuQryWhereLocAddrType  OBJECT-TYPE
    SYNTAX      InetAddressType
    MAX-ACCESS  read-create
    STATUS      current
    DESCRIPTION
        "The value of tmnxWlanGwTuQryWhereLocAddrType specifies the type of the
         local IP address.

         When the value of tmnxWlanGwTuQryWhereLocAddrType is not 'unknown',
         the tmnxWlanGwTuTable will contain only rows with this query ID where
         the value of tmnxWlanGwTuLocalAddrType is equal to this value."
    DEFVAL      { unknown }
    ::= { tmnxWlanGwTuQryEntry 6 }

tmnxWlanGwTuQryWhereLocAddr      OBJECT-TYPE
    SYNTAX      InetAddress (SIZE (0|4|16))
    MAX-ACCESS  read-create
    STATUS      current
    DESCRIPTION
        "The value of tmnxWlanGwTuQryWhereLocAddr specifies the IP address of
         the local endpoint of the tunnel.

         When the value of tmnxWlanGwTuQryWhereLocAddr is not empty, the
         tmnxWlanGwTuTable will contain only rows where the value of
         tmnxWlanGwTuLocalAddr is equal to this value."
    DEFVAL      { ''H }
    ::= { tmnxWlanGwTuQryEntry 7 }

tmnxWlanGwTuQryWhereAddrFamily   OBJECT-TYPE
    SYNTAX      InetAddressType
    MAX-ACCESS  read-create
    STATUS      current
    DESCRIPTION
        "The value of tmnxWlanGwTuQryWhereAddrFamily specifies the address
         family of the IP layer of the tunnel.

         When the value of tmnxWlanGwTuQryWhereAddrFamily is not 'unknown', the
         tmnxWlanGwTuTable will contain only rows with this query ID where the
         value of tmnxWlanGwTuLocalAddrType  and tmnxWlanGwTuRemoteAddrType are
         equal to this value."
    DEFVAL      { unknown }
    ::= { tmnxWlanGwTuQryEntry 8 }

tmnxWlanGwTuQryWhereEncap        OBJECT-TYPE
    SYNTAX      BITS {
        gre   (0),
        l2tp  (1),
        l2    (2),
        vxlan (3)
    }
    MAX-ACCESS  read-create
    STATUS      current
    DESCRIPTION
        "The value of tmnxWlanGwTuQryWhereEncap specifies  the encapsulation
         types present in the traffic received through a tunnel.

         When the value of tmnxWlanGwTuQryWhereEncap is not all zeroes, the
         tmnxWlanGwTuTable will contain only rows with this query ID where the
         value of tmnxWlanGwTuEncap corresponds to one of the encapsulations
         specified."
    DEFVAL      { {} }
    ::= { tmnxWlanGwTuQryEntry 15 }

tmnxWlanGwTuQryWhereEncapTag1    OBJECT-TYPE
    SYNTAX      QTagFullRangeOrNone
    MAX-ACCESS  read-create
    STATUS      current
    DESCRIPTION
        "The value of the object tmnxWlanGwTuQryWhereEncapTag1 specifies the
         VLAN tag in case of IEEE 802.1Q encapsulation, or the outer tag
         (service tag, ethertype 0x88a8) in case of IEEE 802.1ad encapsulation,
         present in the traffic received through a tunnel.

         If the value of tmnxWlanGwTuQryWhereEncap does not have the 'vlan' bit
         set, the value of tmnxWlanGwTuEncapTag1 must be minus one.

         When the value of tmnxWlanGwTuQryWhereEncapTag1 is not equal to minus
         one, the tmnxWlanGwTuTable will contain only rows with this query ID
         where the value of tmnxWlanGwTuEncapTag1 is equal to this value."
    DEFVAL      { -1 }
    ::= { tmnxWlanGwTuQryEntry 16 }

tmnxWlanGwTuQryWhereEncapTag2    OBJECT-TYPE
    SYNTAX      QTagFullRangeOrNone
    MAX-ACCESS  read-create
    STATUS      current
    DESCRIPTION
        "The value of the object tmnxWlanGwTuQryWhereEncapTag2 specifies the
         inner tag (customer tag, ethertype 0x8100) in case of qinq
         encapsulation, present in the traffic received through a tunnel.

         If the value of tmnxWlanGwTuQryWhereEncap does not have the 'vlan' bit
         set, the value of tmnxWlanGwTuEncapTag2 must be minus one.

         When the value of tmnxWlanGwTuQryWhereEncapTag2 is not equal to minus
         one, the tmnxWlanGwTuTable will contain only rows with this query ID
         where the value of tmnxWlanGwTuEncapTag2 is equal to this value."
    DEFVAL      { -1 }
    ::= { tmnxWlanGwTuQryEntry 17 }

tmnxWlanGwTuQryWhereApSapPortId  OBJECT-TYPE
    SYNTAX      TmnxPortID
    MAX-ACCESS  read-create
    STATUS      current
    DESCRIPTION
        "The value of the object tmnxWlanGwTuQryWhereApSapPortId specifies the
         ID of the access port of the Access Point.

         If the value of tmnxWlanGwTuQryWhereEncap does not have the 'vlan' bit
         set, the value of tmnxWlanGwTuQryWhereApSapPortId must be equal to the
         'invalid portid'.

         When the value of tmnxWlanGwTuQryWhereApSapPortId is not equal to the
         'invalid portid', the tmnxWlanGwTuTable will contain only rows with
         this query ID where the value of tmnxWlanGwTuApSapPortId is equal to
         this value."
    DEFVAL      { '1e000000'H }
    ::= { tmnxWlanGwTuQryEntry 18 }

tmnxWlanGwTuQryWhereApSapEncap   OBJECT-TYPE
    SYNTAX      TmnxEncapVal
    MAX-ACCESS  read-create
    STATUS      current
    DESCRIPTION
        "The value of the object tmnxWlanGwTuQryWhereApSapEncap specifies the
         value of the label used to identify the SAP of the Access Point, as
         learned by this system.

         If the value of tmnxWlanGwTuQryWhereEncap does not have the 'vlan' bit
         set, the value of tmnxWlanGwTuQryWhereApSapEncap must be equal to
         zero.

         When the value of tmnxWlanGwTuQryWhereApSapEncap is not equal to zero,
         the tmnxWlanGwTuTable will contain only rows with this query ID where
         the value of tmnxWlanGwTuApSapEncapVal is equal to this value."
    DEFVAL      { '00000000'H }
    ::= { tmnxWlanGwTuQryEntry 19 }

tmnxWlanGwTuQryWhereNumUeMin     OBJECT-TYPE
    SYNTAX      Unsigned32
    MAX-ACCESS  read-create
    STATUS      current
    DESCRIPTION
        "The value of tmnxWlanGwTuQryWhereNumUeMin specifies the minimum number
         of UEs in the tunnel.

         The tmnxWlanGwTuTable will contain only rows with this query ID where
         the value of tmnxWlanGwTuNumUe is higher than or equal to this value
         at the time of evaluation."
    DEFVAL      { 0 }
    ::= { tmnxWlanGwTuQryEntry 20 }

tmnxWlanGwTuQryWhereNumUeMax     OBJECT-TYPE
    SYNTAX      Unsigned32
    MAX-ACCESS  read-create
    STATUS      current
    DESCRIPTION
        "The value of tmnxWlanGwTuQryWhereNumUeMax specifies the maximum number
         of UEs in the tunnel.

         The tmnxWlanGwTuTable will contain only rows with this query ID where
         the value of tmnxWlanGwTuNumUe is lower than or equal to this value at
         the time of evaluation."
    DEFVAL      { 'ffffffff'H }
    ::= { tmnxWlanGwTuQryEntry 21 }

tmnxWlanGwTuQryWhereApLearnFail  OBJECT-TYPE
    SYNTAX      INTEGER {
        dontCare (0),
        true     (1),
        false    (2)
    }
    MAX-ACCESS  read-create
    STATUS      current
    DESCRIPTION
        "The value of the object tmnxWlanGwTuQryWhereApLearnFail specifies if
         the learning of the MAC address of the Access Point failed.

         When the value of tmnxWlanGwTuQryWhereApLearnFail is not equal to
         'dontCare', the tmnxWlanGwTuTable will contain only rows with this
         query ID where the value of tmnxWlanGwTuApLearnFailed is equal to the
         value of tmnxWlanGwTuQryWhereApLearnFail."
    DEFVAL      { dontCare }
    ::= { tmnxWlanGwTuQryEntry 22 }

tmnxWlanGwTuQryWhereUeType       OBJECT-TYPE
    SYNTAX      BITS {
        migrant (0),
        dsm     (1),
        l2w     (2),
        esm     (3),
        xcon    (4)
    }
    MAX-ACCESS  read-create
    STATUS      current
    DESCRIPTION
        "The value of tmnxWlanGwTuQryWhereUeType specifies the set of UE type
         values.

         When the value of tmnxWlanGwTuQryWhereUeType is not all zeroes, the
         tmnxWlanGwTuTable will contain only rows with this query ID where the
         number of UEs in one of the states corresponding to the bits set in
         tmnxWlanGwTuQryWhereUeType is within the range of
         tmnxWlanGwTuQryWhereNumUeMin and tmnxWlanGwTuQryWhereNumUeMax;
         typically the value of tmnxWlanGwTuQryWhereNumUeMin will have to be
         set to 1 or higher.

         Setting the value of tmnxWlanGwTuQryWhereUeType to all zeroes is
         equivalent of setting it to all ones.

         The per-type UE counts are in the objects tmnxWlanGwTuNumUeMigrant
         until tmnxWlanGwTuNumUeEsm."
    DEFVAL      { {} }
    ::= { tmnxWlanGwTuQryEntry 23 }

tmnxWlanGwTuQryDoGetNumResults   OBJECT-TYPE
    SYNTAX      TruthValue
    MAX-ACCESS  read-create
    STATUS      current
    DESCRIPTION
        "The value of the object tmnxWlanGwTuQryDoGetNumResults specifies if
         the system calculates the current number of tunnels matching this
         query when a client requests the value of tmnxWlanGwTuQryNumResults.

         If the value of the object tmnxWlanGwTuQryDoGetNumResults is equal to
         'true', the current number of matching tunnels is available in the
         object tmnxWlanGwTuQryNumResults.

         While the value of the object tmnxWlanGwTuQryDoGetNumResults is equal
         to 'false', reading the tmnxWlanGwTuQryNumResults will result in the
         value zero."
    DEFVAL      { false }
    ::= { tmnxWlanGwTuQryEntry 199 }

tmnxWlanGwTuQryNumResults        OBJECT-TYPE
    SYNTAX      Gauge32
    MAX-ACCESS  read-only
    STATUS      current
    DESCRIPTION
        "The value of tmnxWlanGwTuQryNumResults indicates the current number of
         tunnels matching this query, while the value of
         tmnxWlanGwTuQryDoGetNumResults is equal to 'true'.

         It is recommended to examine this value before starting to read the
         tmnxWlanGwTuTable."
    ::= { tmnxWlanGwTuQryEntry 200 }

tmnxWlanGwTuQryName              OBJECT-TYPE
    SYNTAX      TNamedItem
    MAX-ACCESS  read-create
    STATUS      current
    DESCRIPTION
        "The value of tmnxWlanGwTuQryName specifies the name of this query.

         If a value for tmnxWlanGwTuQryName is not provided while the
         conceptual row is created, the system will assign one.

         After the conceptual row is created, it is not allowed to change the
         value of tmnxWlanGwTuQryName."
    ::= { tmnxWlanGwTuQryEntry 201 }

tmnxWlanGwTuQryVolatile          OBJECT-TYPE
    SYNTAX      TruthValue
    MAX-ACCESS  read-only
    STATUS      current
    DESCRIPTION
        "The value of tmnxWlanGwTuQryVolatile indicates if this query is
         volatile.

         If the value of tmnxWlanGwTuQryVolatile is equal to 'true', this query
         will not be saved in the configuration file.

         Conceptual rows created by means of SNMP operations or by means of a
         CLI configuration command are not volatile."
    ::= { tmnxWlanGwTuQryEntry 202 }

tmnxWlanGwTuTable                OBJECT-TYPE
    SYNTAX      SEQUENCE OF TmnxWlanGwTuEntry
    MAX-ACCESS  not-accessible
    STATUS      current
    DESCRIPTION
        "The tmnxWlanGwTuTable contains the results of one or more queries for
         tunnels."
    ::= { tmnxWlanGwTuObjs 4 }

tmnxWlanGwTuEntry                OBJECT-TYPE
    SYNTAX      TmnxWlanGwTuEntry
    MAX-ACCESS  not-accessible
    STATUS      current
    DESCRIPTION
        "Each conceptual row represents a tunnel.

         Conceptual rows in this table are created and destroyed automatically
         by the system.

         Conceptual rows in this table are volatile: they are lost upon reboot
         or switchover.

         The system creates rows in this table as a result of the creation of a
         row in the query table tmnxWlanGwTuQryTable, and destroys them when
         that row is destroyed."
    INDEX       {
        tmnxWlanGwTuQryId,
        tmnxWlanGwTuRouter,
        tmnxWlanGwTuEncap,
        tmnxWlanGwTuRemoteAddrType,
        tmnxWlanGwTuRemoteAddr,
        tmnxWlanGwTuLocalAddrType,
        tmnxWlanGwTuLocalAddr
    }
    ::= { tmnxWlanGwTuTable 1 }

TmnxWlanGwTuEntry                ::= SEQUENCE
{
    tmnxWlanGwTuRouter               TmnxVRtrID,
    tmnxWlanGwTuEncap                TmnxWlanGwUeEncapsulation,
    tmnxWlanGwTuRemoteAddrType       InetAddressType,
    tmnxWlanGwTuRemoteAddr           InetAddress,
    tmnxWlanGwTuLocalAddrType        InetAddressType,
    tmnxWlanGwTuLocalAddr            InetAddress,
    tmnxWlanGwTuFirstMoveTime        DateAndTime,
    tmnxWlanGwTuIsaGroup             TmnxWlanGwIsaGrpIdOrZero,
    tmnxWlanGwTuIsaMember            Unsigned32,
    tmnxWlanGwTuService              TmnxServId,
    tmnxWlanGwTuInterface            InterfaceIndexOrZero,
    tmnxWlanGwTuApMacAddress         MacAddress,
    tmnxWlanGwTuApLearnFailed        TruthValue,
    tmnxWlanGwTuEncapTag1            QTagFullRangeOrNone,
    tmnxWlanGwTuEncapTag2            QTagFullRangeOrNone,
    tmnxWlanGwTuApSapPortId          TmnxPortID,
    tmnxWlanGwTuApSapEncapVal        TmnxEncapVal,
    tmnxWlanGwTuRemoteUdpPort        InetPortNumber,
    tmnxWlanGwTuNumUe                Gauge32,
    tmnxWlanGwTuNumUeMigrant         Gauge32,
    tmnxWlanGwTuNumUeDsm             Gauge32,
    tmnxWlanGwTuNumUeL2w             Gauge32,
    tmnxWlanGwTuNumUeEsm             Gauge32,
    tmnxWlanGwTuNumUeXcon            Gauge32
}

tmnxWlanGwTuRouter               OBJECT-TYPE
    SYNTAX      TmnxVRtrID
    MAX-ACCESS  not-accessible
    STATUS      current
    DESCRIPTION
        "The object tmnxWlanGwTuRouter indicates the identifier of the virtual
         router instance where the tunneled traffic is routed."
    ::= { tmnxWlanGwTuEntry 1 }

tmnxWlanGwTuEncap                OBJECT-TYPE
    SYNTAX      TmnxWlanGwUeEncapsulation
    MAX-ACCESS  not-accessible
    STATUS      current
    DESCRIPTION
        "The value of the object tmnxWlanGwTuEncap indicates the tunnel
         encapsulation.

         The value of tmnxWlanGwTuEncap is learned from the latest UE
         associated with this tunnel; when a given Access Point changes its
         encapsulation, there may be a transition period where the system
         contexts of some UE of this tunnel already have the new encapsulation,
         while some other UE still seem to have the previous encapsulation."
    ::= { tmnxWlanGwTuEntry 2 }

tmnxWlanGwTuRemoteAddrType       OBJECT-TYPE
    SYNTAX      InetAddressType
    MAX-ACCESS  not-accessible
    STATUS      current
    DESCRIPTION
        "The value of tmnxWlanGwTuRemoteAddrType specifies the address type of
         tmnxWlanGwTuRemoteAddr.

         The only values allowed are 'ipv4' and 'ipv6'."
    ::= { tmnxWlanGwTuEntry 3 }

tmnxWlanGwTuRemoteAddr           OBJECT-TYPE
    SYNTAX      InetAddress (SIZE (4|16))
    MAX-ACCESS  not-accessible
    STATUS      current
    DESCRIPTION
        "The value of the object tmnxWlanGwTuRemoteAddr specifies the IP
         address of the remote endpoint of this tunnel, that is the source IP
         address in the tunnel header of received packets."
    ::= { tmnxWlanGwTuEntry 4 }

tmnxWlanGwTuLocalAddrType        OBJECT-TYPE
    SYNTAX      InetAddressType
    MAX-ACCESS  not-accessible
    STATUS      current
    DESCRIPTION
        "The value of tmnxWlanGwTuLocalAddrType specifies the address type of
         tmnxWlanGwTuLocalAddr.

         The only values allowed are 'ipv4' and 'ipv6'."
    ::= { tmnxWlanGwTuEntry 5 }

tmnxWlanGwTuLocalAddr            OBJECT-TYPE
    SYNTAX      InetAddress (SIZE (4|16))
    MAX-ACCESS  not-accessible
    STATUS      current
    DESCRIPTION
        "The value of the object tmnxWlanGwTuLocalAddr specifies the IP address
         of the local endpoint of this tunnel, that is the destination IP
         address in the tunnel header of received packets.

         The value of this object is equal to the value of the
         tmnxWlanGwSoftGreIfGwAddr object in the conceptual row corresponding
         to the Group-Interface where this tunnel is terminated."
    ::= { tmnxWlanGwTuEntry 6 }

tmnxWlanGwTuFirstMoveTime        OBJECT-TYPE
    SYNTAX      DateAndTime (SIZE (11))
    MAX-ACCESS  read-only
    STATUS      current
    DESCRIPTION
        "The value of the object tmnxWlanGwTuFirstMoveTime indicates the value
         of sysUpTime when this tunnel moved for the first time."
    ::= { tmnxWlanGwTuEntry 7 }

tmnxWlanGwTuIsaGroup             OBJECT-TYPE
    SYNTAX      TmnxWlanGwIsaGrpIdOrZero
    MAX-ACCESS  read-only
    STATUS      current
    DESCRIPTION
        "The value of the object tmnxWlanGwTuIsaGroup indicates the identifier
         of the WLAN Gateway ISA group that processes this tunnel.

         The value of this object is equal to the value of the object
         tmnxWlanGwGrpId in the conceptual row that corresponds to the WLAN
         Gateway ISA group."
    ::= { tmnxWlanGwTuEntry 8 }

tmnxWlanGwTuIsaMember            OBJECT-TYPE
    SYNTAX      Unsigned32
    MAX-ACCESS  read-only
    STATUS      current
    DESCRIPTION
        "The value of the object tmnxWlanGwTuIsaMember indicates the identifier
         of the ISA Group member that processes this tunnel.

         The value of this object is equal to the value of the object
         tmnxWlanGwIsaMemberId in the conceptual row in the
         tmnxWlanGwIsaMemberTable that corresponds to this ISA Group member."
    ::= { tmnxWlanGwTuEntry 9 }

tmnxWlanGwTuService              OBJECT-TYPE
    SYNTAX      TmnxServId
    MAX-ACCESS  read-only
    STATUS      current
    DESCRIPTION
        "The value of the object tmnxWlanGwTuService indicates the identifier
         of the service of the interface associated with this tunnel."
    ::= { tmnxWlanGwTuEntry 10 }

tmnxWlanGwTuInterface            OBJECT-TYPE
    SYNTAX      InterfaceIndexOrZero
    MAX-ACCESS  read-only
    STATUS      current
    DESCRIPTION
        "The value of the object tmnxWlanGwTuInterface indicates the identifier
         of the interface associated with this tunnel.

         Together with tmnxWlanGwTuService, it identifies a row in the
         tmnxWlanGwSoftGreIfTable."
    ::= { tmnxWlanGwTuEntry 11 }

tmnxWlanGwTuApMacAddress         OBJECT-TYPE
    SYNTAX      MacAddress
    MAX-ACCESS  read-only
    STATUS      current
    DESCRIPTION
        "The value of the object tmnxWlanGwTuApMacAddress indicates the MAC
         address of the Access Point, as learned by this system.

         The value all zeroes indicates that the Access Point MAC is not known,
         either because there was no attempt to learn it, or because an attempt
         failed."
    ::= { tmnxWlanGwTuEntry 12 }

tmnxWlanGwTuApLearnFailed        OBJECT-TYPE
    SYNTAX      TruthValue
    MAX-ACCESS  read-only
    STATUS      current
    DESCRIPTION
        "The value of the object tmnxWlanGwTuApLearnFailed indicates if the
         learning of the MAC address of the Access Point failed.

         When the value of tmnxWlanGwTuApLearnFailed is equal to 'true', the
         value of tmnxWlanGwTuApMacAddress is equal to all zeroes."
    ::= { tmnxWlanGwTuEntry 13 }

tmnxWlanGwTuEncapTag1            OBJECT-TYPE
    SYNTAX      QTagFullRangeOrNone
    MAX-ACCESS  read-only
    STATUS      current
    DESCRIPTION
        "The value of the object tmnxWlanGwTuEncapTag1 indicates the VLAN tag
         in case of IEEE 802.1Q encapsulation, or the outer tag (service tag,
         ethertype 0x88a8) in case of IEEE 802.1ad encapsulation.

         If the value of tmnxWlanGwTuEncap is not equal to 'vlan', the value of
         tmnxWlanGwTuEncapTag1 is minus one."
    ::= { tmnxWlanGwTuEntry 15 }

tmnxWlanGwTuEncapTag2            OBJECT-TYPE
    SYNTAX      QTagFullRangeOrNone
    MAX-ACCESS  read-only
    STATUS      current
    DESCRIPTION
        "The value of the object tmnxWlanGwTuEncapTag2 indicates the inner tag
         (customer tag, ethertype 0x8100) in case of qinq encapsulation.

         If the value of tmnxWlanGwTuEncap is not equal to 'vlan', the value of
         tmnxWlanGwTuEncapTag2 is minus one."
    ::= { tmnxWlanGwTuEntry 16 }

tmnxWlanGwTuApSapPortId          OBJECT-TYPE
    SYNTAX      TmnxPortID
    MAX-ACCESS  read-only
    STATUS      current
    DESCRIPTION
        "The value of the object tmnxWlanGwTuApSapPortId indicates the ID of
         the access port of the Access Point, as learned by this system.

         If the value of tmnxWlanGwTuEncap is not equal to 'vlan', the value of
         tmnxWlanGwTuApSapPortId is all zeroes."
    ::= { tmnxWlanGwTuEntry 17 }

tmnxWlanGwTuApSapEncapVal        OBJECT-TYPE
    SYNTAX      TmnxEncapVal
    MAX-ACCESS  read-only
    STATUS      current
    DESCRIPTION
        "The value of the object tmnxWlanGwTuApSapEncapVal indicates the value
         of the label used to identify the SAP of the Access Point, as learned
         by this system.

         If the value of tmnxWlanGwTuEncap is not equal to 'vlan', the value of
         tmnxWlanGwTuApSapEncapVal is all zeroes."
    ::= { tmnxWlanGwTuEntry 18 }

tmnxWlanGwTuRemoteUdpPort        OBJECT-TYPE
    SYNTAX      InetPortNumber
    MAX-ACCESS  read-only
    STATUS      current
    DESCRIPTION
        "The value of the object tmnxWlanGwTuRemoteUdpPort indicates the UDP
         port of the remote endpoint of this tunnel, that is the source UDP
         port in the tunnel header of received packets.

         The value of this object is only relevant if the value of
         tmnxWlanGwTuEncap is equal to 'l2tp'."
    ::= { tmnxWlanGwTuEntry 19 }

tmnxWlanGwTuNumUe                OBJECT-TYPE
    SYNTAX      Gauge32
    MAX-ACCESS  read-only
    STATUS      current
    DESCRIPTION
        "The value of the object tmnxWlanGwTuNumUe indicates the number of User
         Equipment's connected to this system through this tunnel."
    ::= { tmnxWlanGwTuEntry 50 }

tmnxWlanGwTuNumUeMigrant         OBJECT-TYPE
    SYNTAX      Gauge32
    MAX-ACCESS  read-only
    STATUS      current
    DESCRIPTION
        "The value of the object tmnxWlanGwTuNumUeMigrant indicates the number
         of migrant User Equipment's connected to this system through this
         tunnel."
    ::= { tmnxWlanGwTuEntry 51 }

tmnxWlanGwTuNumUeDsm             OBJECT-TYPE
    SYNTAX      Gauge32
    MAX-ACCESS  read-only
    STATUS      current
    DESCRIPTION
        "The value of the object tmnxWlanGwTuNumUeDsm indicates the number of
         DSM User Equipment's connected to this system through this tunnel."
    ::= { tmnxWlanGwTuEntry 52 }

tmnxWlanGwTuNumUeL2w             OBJECT-TYPE
    SYNTAX      Gauge32
    MAX-ACCESS  read-only
    STATUS      current
    DESCRIPTION
        "The value of the object tmnxWlanGwTuNumUeL2w indicates the number of
         layer-2 wholesale User Equipment's connected to this system through
         this tunnel."
    ::= { tmnxWlanGwTuEntry 53 }

tmnxWlanGwTuNumUeEsm             OBJECT-TYPE
    SYNTAX      Gauge32
    MAX-ACCESS  read-only
    STATUS      current
    DESCRIPTION
        "The value of the object tmnxWlanGwTuNumUeEsm indicates the number of
         ESM User Equipment's connected to this system through this tunnel."
    ::= { tmnxWlanGwTuEntry 54 }

tmnxWlanGwTuNumUeXcon            OBJECT-TYPE
    SYNTAX      Gauge32
    MAX-ACCESS  read-only
    STATUS      current
    DESCRIPTION
        "The value of the object tmnxWlanGwTuNumUeXcon indicates the number of
         cross-connect User Equipment's connected to this system through this
         tunnel."
    ::= { tmnxWlanGwTuEntry 55 }

tmnxWlanGwBdUeTable              OBJECT-TYPE
    SYNTAX      SEQUENCE OF TmnxWlanGwBdUeEntry
    MAX-ACCESS  not-accessible
    STATUS      current
    DESCRIPTION
        "The tmnxWlanGwBdUeTable contains information about WLAN Gateway Bridge
         Domain User Equipment (UE)."
    ::= { tmnxWlanGwObjs 15 }

tmnxWlanGwBdUeEntry              OBJECT-TYPE
    SYNTAX      TmnxWlanGwBdUeEntry
    MAX-ACCESS  not-accessible
    STATUS      current
    DESCRIPTION
        "Each conceptual row represents information about a WLAN Gateway User
         Equipment.

         Entries in this table are created and destroyed automatically by the
         system."
    INDEX       {
        tmnxWlanGwBdBridgeId,
        tmnxWlanGwBdUeMacAddress
    }
    ::= { tmnxWlanGwBdUeTable 1 }

TmnxWlanGwBdUeEntry              ::= SEQUENCE
{
    tmnxWlanGwBdBridgeId             Unsigned32,
    tmnxWlanGwBdUeMacAddress         MacAddress,
    tmnxWlanGwBdUeQTag               QTagFullRangeOrNone,
    tmnxWlanGwBdUeMplsLabel          MplsLabel,
    tmnxWlanGwBdUeTuRouter           TmnxVRtrID,
    tmnxWlanGwBdUeTuAddrType         InetAddressType,
    tmnxWlanGwBdUeTuRemoteAddr       InetAddress,
    tmnxWlanGwBdUeTuLocalAddr        InetAddress,
    tmnxWlanGwBdUeTuQosRetailService TmnxServId,
    tmnxWlanGwBdUeSsid               TNamedItemOrEmpty,
    tmnxWlanGwBdUePrevApAddrType     InetAddressType,
    tmnxWlanGwBdUePrevApAddr         InetAddress,
    tmnxWlanGwBdUeLastMoveTime       DateAndTime,
    tmnxWlanGwBdUeImsi               TmnxMobImsiStr,
    tmnxWlanGwBdUeService            TmnxServId,
    tmnxWlanGwBdUeSapPortId          TmnxPortID,
    tmnxWlanGwBdUeSapPortEncapValue  TmnxEncapVal,
    tmnxWlanGwBdUeEncapsulation      TmnxWlanGwUeEncapsulation
}

tmnxWlanGwBdBridgeId             OBJECT-TYPE
    SYNTAX      Unsigned32
    MAX-ACCESS  not-accessible
    STATUS      current
    DESCRIPTION
        "The value of the object tmnxWlanGwBdBridgeId indicates the Bridge
         Identifier of this UE.

         The value zero indicates absence of a Bridge Identifier."
    ::= { tmnxWlanGwBdUeEntry 1 }

tmnxWlanGwBdUeMacAddress         OBJECT-TYPE
    SYNTAX      MacAddress
    MAX-ACCESS  not-accessible
    STATUS      current
    DESCRIPTION
        "The value of the object tmnxWlanGwBdUeMacAddress indicates the MAC
         address of this UE."
    ::= { tmnxWlanGwBdUeEntry 2 }

tmnxWlanGwBdUeQTag               OBJECT-TYPE
    SYNTAX      QTagFullRangeOrNone
    MAX-ACCESS  read-only
    STATUS      current
    DESCRIPTION
        "The value of the object tmnxWlanGwBdUeQTag indicates the VLAN Q-tag
         present in the traffic received from this UE.

         The value of this object can be used to identify the retailer service,
         by means of the tmnxWlanGwIfRetailTable.

         The value minus one indicates that the traffic received from this UE
         does not have a VLAN Q-tag."
    ::= { tmnxWlanGwBdUeEntry 3 }

tmnxWlanGwBdUeMplsLabel          OBJECT-TYPE
    SYNTAX      MplsLabel
    MAX-ACCESS  read-only
    STATUS      current
    DESCRIPTION
        "The value of the object tmnxWlanGwBdUeMplsLabel indicates the MPLS
         label present in the traffic received from this UE.

         The value zero indicates that the traffic received from this UE does
         not have an MPLS label."
    ::= { tmnxWlanGwBdUeEntry 4 }

tmnxWlanGwBdUeTuRouter           OBJECT-TYPE
    SYNTAX      TmnxVRtrID
    MAX-ACCESS  read-only
    STATUS      current
    DESCRIPTION
        "The value of tmnxWlanGwBdUeTuRouter indicates the identifier of the
         virtual router instance where the tunneled User Equipment traffic is
         routed."
    ::= { tmnxWlanGwBdUeEntry 5 }

tmnxWlanGwBdUeTuAddrType         OBJECT-TYPE
    SYNTAX      InetAddressType
    MAX-ACCESS  read-only
    STATUS      current
    DESCRIPTION
        "The value of tmnxWlanGwBdUeTuAddrType indicates the address type of
         tmnxWlanGwBdUeTuRemoteAddr and tmnxWlanGwBdUeTuLocalAddr."
    ::= { tmnxWlanGwBdUeEntry 6 }

tmnxWlanGwBdUeTuRemoteAddr       OBJECT-TYPE
    SYNTAX      InetAddress (SIZE (4|16))
    MAX-ACCESS  read-only
    STATUS      current
    DESCRIPTION
        "The value of the object tmnxWlanGwBdUeTuRemoteAddr indicates the IP
         address of the remote endpoint of this UE's tunnel, that is the source
         IP address in the tunnel header of received packets."
    ::= { tmnxWlanGwBdUeEntry 7 }

tmnxWlanGwBdUeTuLocalAddr        OBJECT-TYPE
    SYNTAX      InetAddress (SIZE (4|16))
    MAX-ACCESS  read-only
    STATUS      current
    DESCRIPTION
        "The value of the object tmnxWlanGwBdUeTuLocalAddr indicates the IP
         address of the local endpoint of this UE's tunnel, that is the
         destination IP address in the tunnel header of received packets."
    ::= { tmnxWlanGwBdUeEntry 8 }

tmnxWlanGwBdUeTuQosRetailService OBJECT-TYPE
    SYNTAX      TmnxServId
    MAX-ACCESS  read-only
    STATUS      current
    DESCRIPTION
        "The value of the object tmnxWlanGwBdUeTuQosRetailService indicates the
         identifier of the retail service.

         The value zero indicates that this UE's tunnel has per-tunnel QoS."
    ::= { tmnxWlanGwBdUeEntry 9 }

tmnxWlanGwBdUeSsid               OBJECT-TYPE
    SYNTAX      TNamedItemOrEmpty
    MAX-ACCESS  read-only
    STATUS      current
    DESCRIPTION
        "The value of tmnxWlanGwBdUeSsid indicates the Service Set ID (SSID) of
         this UE.

         This object refers to a conceptual row in the tmnxWlanGwSsidTable."
    ::= { tmnxWlanGwBdUeEntry 10 }

tmnxWlanGwBdUePrevApAddrType     OBJECT-TYPE
    SYNTAX      InetAddressType
    MAX-ACCESS  read-only
    STATUS      current
    DESCRIPTION
        "The value of tmnxWlanGwBdUePrevApAddrType indicates the address type
         of tmnxWlanGwBdUePrevApAddr."
    ::= { tmnxWlanGwBdUeEntry 11 }

tmnxWlanGwBdUePrevApAddr         OBJECT-TYPE
    SYNTAX      InetAddress (SIZE (0|4|16))
    MAX-ACCESS  read-only
    STATUS      current
    DESCRIPTION
        "The value of tmnxWlanGwBdUePrevApAddr indicates the IP address of the
         previous Access Point (AP) of this UE.

         Note that the address of the current AP of this UE is the value of the
         object tmnxWlanGwBdUeTuRemoteAddr."
    ::= { tmnxWlanGwBdUeEntry 12 }

tmnxWlanGwBdUeLastMoveTime       OBJECT-TYPE
    SYNTAX      DateAndTime (SIZE (11))
    MAX-ACCESS  read-only
    STATUS      current
    DESCRIPTION
        "The value of tmnxWlanGwBdUeLastMoveTime indicates the time of the most
         recent Access Point move of this UE."
    ::= { tmnxWlanGwBdUeEntry 13 }

tmnxWlanGwBdUeImsi               OBJECT-TYPE
    SYNTAX      TmnxMobImsiStr
    MAX-ACCESS  read-only
    STATUS      current
    DESCRIPTION
        "The value of tmnxWlanGwBdUeImsi indicates the IMSI (International
         Mobile Subscriber Identity) of this UE."
    ::= { tmnxWlanGwBdUeEntry 15 }

tmnxWlanGwBdUeService            OBJECT-TYPE
    SYNTAX      TmnxServId
    MAX-ACCESS  read-only
    STATUS      current
    DESCRIPTION
        "The value of the object tmnxWlanGwBdUeService indicates the service
         identifier of the (internal) SAP associated with this UE.

         While a subscriber is associated with this UE, that SAP is where its
         subscriber hosts can be found in the
         TIMETRA-SUBSCRIBER-MGMT-MIB::tmnxSubHostInfoV2Table.

         While no subscriber is associated with this UE, the value of
         tmnxWlanGwBdUeService is equal to zero."
    ::= { tmnxWlanGwBdUeEntry 16 }

tmnxWlanGwBdUeSapPortId          OBJECT-TYPE
    SYNTAX      TmnxPortID
    MAX-ACCESS  read-only
    STATUS      current
    DESCRIPTION
        "The value of the object tmnxWlanGwBdUeSapPortId indicates the port ID
         of the (internal) SAP associated with this UE.

         While no subscriber is associated with this UE, the value of
         tmnxWlanGwBdUeSapPortId is equal to '1E000000'H, the identifier of the
         'invalid port'."
    ::= { tmnxWlanGwBdUeEntry 17 }

tmnxWlanGwBdUeSapPortEncapValue  OBJECT-TYPE
    SYNTAX      TmnxEncapVal
    MAX-ACCESS  read-only
    STATUS      current
    DESCRIPTION
        "The value of the object tmnxWlanGwBdUeSapPortEncapValue indicates the
         value of the encapsulation of the (internal) SAP associated with this
         UE.

         While no subscriber is associated with this UE, the value of
         tmnxWlanGwBdUeSapPortEncapValue is equal to zero."
    ::= { tmnxWlanGwBdUeEntry 18 }

tmnxWlanGwBdUeEncapsulation      OBJECT-TYPE
    SYNTAX      TmnxWlanGwUeEncapsulation
    MAX-ACCESS  read-only
    STATUS      current
    DESCRIPTION
        "The value of the object tmnxWlanGwBdUeEncapsulation indicates the
         encapsulation used in this UE's tunnel."
    ::= { tmnxWlanGwBdUeEntry 19 }

tmnxWlanGwXcnctTable             OBJECT-TYPE
    SYNTAX      SEQUENCE OF TmnxWlanGwXcnctEntry
    MAX-ACCESS  not-accessible
    STATUS      current
    DESCRIPTION
        "The tmnxWlanGwXcnctTable contains information about the cross-connects
         for inter WLAN-GW mobility via anchoring on the Home-GW."
    ::= { tmnxWlanGwObjs 16 }

tmnxWlanGwXcnctEntry             OBJECT-TYPE
    SYNTAX      TmnxWlanGwXcnctEntry
    MAX-ACCESS  not-accessible
    STATUS      current
    DESCRIPTION
        "Each conceptual row represents information about a cross-connect for
         inter WLAN-GW mobility via anchoring on the Home-GW."
    AUGMENTS    { tmnxWlanGwEntry }
    ::= { tmnxWlanGwXcnctTable 1 }

TmnxWlanGwXcnctEntry             ::= SEQUENCE
{
    tmnxWlanGwXcnctLastCh            TimeStamp,
    tmnxWlanGwXcnctIsaGroup          TmnxWlanGwIsaGrpIdOrZero,
    tmnxWlanGwXcnctTnlSrcIpAddrType  InetAddressType,
    tmnxWlanGwXcnctTnlSrcIpAddr      InetAddress,
    tmnxWlanGwXcnctTnlSrcIpPrefixLen InetAddressPrefixLength,
    tmnxWlanGwXcnctAdminState        TmnxAdminState
}

tmnxWlanGwXcnctLastCh            OBJECT-TYPE
    SYNTAX      TimeStamp
    MAX-ACCESS  read-only
    STATUS      current
    DESCRIPTION
        "The value of tmnxWlanGwXcnctLastCh indicates the sysUpTime at the time
         of the most recent management-initiated change to this table row."
    ::= { tmnxWlanGwXcnctEntry 1 }

tmnxWlanGwXcnctIsaGroup          OBJECT-TYPE
    SYNTAX      TmnxWlanGwIsaGrpIdOrZero
    MAX-ACCESS  read-create
    STATUS      current
    DESCRIPTION
        "The value of the object tmnxWlanGwXcnctIsaGroup specifies the
         identifier of the WLAN Gateway ISA group that processes the
         cross-connect."
    DEFVAL      { 0 }
    ::= { tmnxWlanGwXcnctEntry 2 }

tmnxWlanGwXcnctTnlSrcIpAddrType  OBJECT-TYPE
    SYNTAX      InetAddressType
    MAX-ACCESS  read-create
    STATUS      current
    DESCRIPTION
        "The value of tmnxWlanGwXcnctTnlSrcIpAddrType specifies the type of the
         address stored in tmnxWlanGwXcnctTnlSrcIpAddr."
    DEFVAL      { unknown }
    ::= { tmnxWlanGwXcnctEntry 3 }

tmnxWlanGwXcnctTnlSrcIpAddr      OBJECT-TYPE
    SYNTAX      InetAddress (SIZE (0|16))
    MAX-ACCESS  read-create
    STATUS      current
    DESCRIPTION
        "The value of tmnxWlanGwXcnctTnlSrcIpAddr specifies the tunnel source
         IPv6 address of the cross-connect."
    DEFVAL      { ''H }
    ::= { tmnxWlanGwXcnctEntry 4 }

tmnxWlanGwXcnctTnlSrcIpPrefixLen OBJECT-TYPE
    SYNTAX      InetAddressPrefixLength (0..128)
    MAX-ACCESS  read-create
    STATUS      current
    DESCRIPTION
        "The value of tmnxWlanGwXcnctTnlSrcIpPrefixLen specifies the prefix
         length of the tunnel source IPv6 address of the cross-connect."
    DEFVAL      { 0 }
    ::= { tmnxWlanGwXcnctEntry 5 }

tmnxWlanGwXcnctAdminState        OBJECT-TYPE
    SYNTAX      TmnxAdminState
    MAX-ACCESS  read-create
    STATUS      current
    DESCRIPTION
        "The value of tmnxWlanGwXcnctAdminState specifies the administrative
         state of the cross-connect."
    DEFVAL      { outOfService }
    ::= { tmnxWlanGwXcnctEntry 6 }

tmnxWlanGwLeTable                OBJECT-TYPE
    SYNTAX      SEQUENCE OF TmnxWlanGwLeEntry
    MAX-ACCESS  not-accessible
    STATUS      current
    DESCRIPTION
        "The tmnxWlanGwLeTable allows configuration of WLAN Gateway home LAN
         Extension functions in a virtual router instance."
    ::= { tmnxWlanGwObjs 17 }

tmnxWlanGwLeEntry                OBJECT-TYPE
    SYNTAX      TmnxWlanGwLeEntry
    MAX-ACCESS  not-accessible
    STATUS      current
    DESCRIPTION
        "Each entry represents the configuration for  WLAN Gateway LAN
         Extension functions in a particular virtual  router instance.

         Entries in this table can be created and deleted via SNMP SET
         operations to tmnxWlanGwLeRowStatus.

         A corresponding row in the TIMETRA-VRTR-MIB::vRtrConfTable must exist
         in order to create a row in this table."
    INDEX       { vRtrID }
    ::= { tmnxWlanGwLeTable 1 }

TmnxWlanGwLeEntry                ::= SEQUENCE
{
    tmnxWlanGwLeRowStatus            RowStatus,
    tmnxWlanGwLeLastChanged          TimeStamp,
    tmnxWlanGwLeAdminState           TmnxEnabledDisabledAdminState,
    tmnxWlanGwLeWlanGwGrpId          TmnxWlanGwIsaGrpIdOrZero,
    tmnxWlanGwLeVtepStartType        InetAddressType,
    tmnxWlanGwLeVtepStart            InetAddress,
    tmnxWlanGwLeVtepEndType          InetAddressType,
    tmnxWlanGwLeVtepEnd              InetAddress,
    tmnxWlanGwLeVxlanPort            InetPortNumber
}

tmnxWlanGwLeRowStatus            OBJECT-TYPE
    SYNTAX      RowStatus
    MAX-ACCESS  read-create
    STATUS      current
    DESCRIPTION
        "The value of tmnxWlanGwLeRowStatus controls the creation and deletion
         of rows in the table."
    ::= { tmnxWlanGwLeEntry 1 }

tmnxWlanGwLeLastChanged          OBJECT-TYPE
    SYNTAX      TimeStamp
    MAX-ACCESS  read-only
    STATUS      current
    DESCRIPTION
        "The value of tmnxWlanGwLeLastChanged indicates the sysUpTime of the
         most recent management-initiated change to this conceptual row."
    ::= { tmnxWlanGwLeEntry 2 }

tmnxWlanGwLeAdminState           OBJECT-TYPE
    SYNTAX      TmnxEnabledDisabledAdminState
    MAX-ACCESS  read-create
    STATUS      current
    DESCRIPTION
        "The value of tmnxWlanGwLeAdminState specifies the administrative state
         of the home LAN Extension in this virtual router instance"
    DEFVAL      { disabled }
    ::= { tmnxWlanGwLeEntry 3 }

tmnxWlanGwLeWlanGwGrpId          OBJECT-TYPE
    SYNTAX      TmnxWlanGwIsaGrpIdOrZero
    MAX-ACCESS  read-create
    STATUS      current
    DESCRIPTION
        "The value of tmnxWlanGwLeWlanGwGrpId specifies the identifier of  the
         WLAN Gateway ISA group that processes home and data center  traffic in
         this virtual router instance"
    DEFVAL      { 0 }
    ::= { tmnxWlanGwLeEntry 4 }

tmnxWlanGwLeVtepStartType        OBJECT-TYPE
    SYNTAX      InetAddressType
    MAX-ACCESS  read-create
    STATUS      current
    DESCRIPTION
        "The value of tmnxWlanGwLeVtepStartType indicates the address type of
         tmnxWlanGwLeVtepStart."
    DEFVAL      { unknown }
    ::= { tmnxWlanGwLeEntry 5 }

tmnxWlanGwLeVtepStart            OBJECT-TYPE
    SYNTAX      InetAddress (SIZE (0|4|16))
    MAX-ACCESS  read-create
    STATUS      current
    DESCRIPTION
        "The value of the object tmnxWlanGwLeVtepStart indicates the first IP
         address in the VXLAN VTEP address range."
    DEFVAL      { "" }
    ::= { tmnxWlanGwLeEntry 6 }

tmnxWlanGwLeVtepEndType          OBJECT-TYPE
    SYNTAX      InetAddressType
    MAX-ACCESS  read-create
    STATUS      current
    DESCRIPTION
        "The value of tmnxWlanGwLeVtepEndType indicates the address type of
         tmnxWlanGwLeVtepEnd."
    DEFVAL      { unknown }
    ::= { tmnxWlanGwLeEntry 7 }

tmnxWlanGwLeVtepEnd              OBJECT-TYPE
    SYNTAX      InetAddress (SIZE (0|4|16))
    MAX-ACCESS  read-create
    STATUS      current
    DESCRIPTION
        "The value of the object tmnxWlanGwLeVtepEnd indicates the last IP
         address in the VXLAN VTEP address range.

         The value of tmnxWlanGwLeVtepEnd must be lexicographically greater
         than or equal to the value of tmnxWlanGwLeVtepStart."
    DEFVAL      { "" }
    ::= { tmnxWlanGwLeEntry 8 }

tmnxWlanGwLeVxlanPort            OBJECT-TYPE
    SYNTAX      InetPortNumber (4789 | 8472)
    MAX-ACCESS  read-create
    STATUS      current
    DESCRIPTION
        "The value of tmnxWlanGwLeVxlanPort indicates the default VXLAN port."
    DEFVAL      { 4789 }
    ::= { tmnxWlanGwLeEntry 9 }

tmnxWlanGwBdTable                OBJECT-TYPE
    SYNTAX      SEQUENCE OF TmnxWlanGwBdEntry
    MAX-ACCESS  not-accessible
    STATUS      current
    DESCRIPTION
        "The tmnxWlanGwBdTable contains information about WLAN Gateway Bridge
         Domains."
    ::= { tmnxWlanGwObjs 18 }

tmnxWlanGwBdEntry                OBJECT-TYPE
    SYNTAX      TmnxWlanGwBdEntry
    MAX-ACCESS  not-accessible
    STATUS      current
    DESCRIPTION
        "Each entry represents information about a WLAN Gateway Bridge Domain.

         Entries in this table are created and destroyed automatically by the
         system."
    INDEX       { tmnxWlanGwBdBridgeId }
    ::= { tmnxWlanGwBdTable 1 }

TmnxWlanGwBdEntry                ::= SEQUENCE
{
    tmnxWlanGwBdVNI                  Unsigned32,
    tmnxWlanGwBdRT                   TNamedItemOrEmpty,
    tmnxWlanGwBdRD                   TmnxVPNRouteDistinguisher,
    tmnxWlanGwBdWlanGwGrpId          TmnxWlanGwIsaGrpIdOrZero,
    tmnxWlanGwBdIsaMemberId          Unsigned32,
    tmnxWlanGwBdVlanTag              QTagFullRangeOrNone,
    tmnxWlanGwBdService              TmnxServId,
    tmnxWlanGwBdInterface            InterfaceIndex,
    tmnxWlanGwBdMacTranslation       TmnxEnabledDisabledOrNA,
    tmnxWlanGwBdBdMac                MacAddress,
    tmnxWlanGwBdAssistAddrRes        TmnxEnabledDisabledOrNA,
    tmnxWlanGwBdNetwMaxMac           Unsigned32,
    tmnxWlanGwBdNetwAdminState       TmnxEnabledDisabledOrNA,
    tmnxWlanGwBdAccsMaxMac           Unsigned32,
    tmnxWlanGwBdAccsPolicer          TNamedItemOrEmpty,
    tmnxWlanGwBdNetwPolicer          TNamedItemOrEmpty
}

tmnxWlanGwBdVNI                  OBJECT-TYPE
    SYNTAX      Unsigned32
    MAX-ACCESS  read-only
    STATUS      current
    DESCRIPTION
        "The value of tmnxWlanGwBdVNI indicates the VXLAN Network Identifier
         (VNI) of this Bridge Domain."
    ::= { tmnxWlanGwBdEntry 1 }

tmnxWlanGwBdRT                   OBJECT-TYPE
    SYNTAX      TNamedItemOrEmpty
    MAX-ACCESS  read-only
    STATUS      current
    DESCRIPTION
        "The value of tmnxWlanGwBdRT indicates the route-target of this  Bridge
         Domain."
    ::= { tmnxWlanGwBdEntry 2 }

tmnxWlanGwBdRD                   OBJECT-TYPE
    SYNTAX      TmnxVPNRouteDistinguisher
    MAX-ACCESS  read-only
    STATUS      current
    DESCRIPTION
        "The value of tmnxWlanGwBdRD indicates the route-distinguisher of this
         Bridge Domain."
    ::= { tmnxWlanGwBdEntry 3 }

tmnxWlanGwBdWlanGwGrpId          OBJECT-TYPE
    SYNTAX      TmnxWlanGwIsaGrpIdOrZero
    MAX-ACCESS  read-only
    STATUS      current
    DESCRIPTION
        "The value of tmnxWlanGwBdWlanGwGrpId indicates the identifier of the
         WLAN Gateway ISA group associated with this Bridge Domain."
    ::= { tmnxWlanGwBdEntry 4 }

tmnxWlanGwBdIsaMemberId          OBJECT-TYPE
    SYNTAX      Unsigned32
    MAX-ACCESS  read-only
    STATUS      current
    DESCRIPTION
        "The value of the object tmnxWlanGwBdIsaMemberId indicates the
         identifier of the WLAN Gateway ISA Group member associated with  this
         Bridge Domain."
    ::= { tmnxWlanGwBdEntry 5 }

tmnxWlanGwBdVlanTag              OBJECT-TYPE
    SYNTAX      QTagFullRangeOrNone
    MAX-ACCESS  read-only
    STATUS      current
    DESCRIPTION
        "The value of the object tmnxWlanGwBdVlanTag indicates the VLAN tag
         associated with this BD."
    ::= { tmnxWlanGwBdEntry 6 }

tmnxWlanGwBdService              OBJECT-TYPE
    SYNTAX      TmnxServId
    MAX-ACCESS  read-only
    STATUS      current
    DESCRIPTION
        "The value of the object tmnxWlanGwBdService indicates the identifier
         of the service of the interface associated with this BD."
    ::= { tmnxWlanGwBdEntry 7 }

tmnxWlanGwBdInterface            OBJECT-TYPE
    SYNTAX      InterfaceIndex
    MAX-ACCESS  read-only
    STATUS      current
    DESCRIPTION
        "The value of the object tmnxWlanGwBdInterface indicates the identifier
         of the interface associated with this BD.

         Together with tmnxWlanGwBdService, it identifies a row in the
         tmnxWlanGwSoftGreIfTable."
    ::= { tmnxWlanGwBdEntry 8 }

tmnxWlanGwBdMacTranslation       OBJECT-TYPE
    SYNTAX      TmnxEnabledDisabledOrNA
    MAX-ACCESS  read-only
    STATUS      current
    DESCRIPTION
        "The value of tmnxWlanGwBdMacTranslation specifies whether MAC
         translation is enabled for this bridge domain."
    ::= { tmnxWlanGwBdEntry 9 }

tmnxWlanGwBdBdMac                OBJECT-TYPE
    SYNTAX      MacAddress
    MAX-ACCESS  read-only
    STATUS      current
    DESCRIPTION
        "The value of tmnxWlanGwBdBdMac specifies the MAC address for  the
         bridge domain in case MAC translation is enabled."
    ::= { tmnxWlanGwBdEntry 10 }

tmnxWlanGwBdAssistAddrRes        OBJECT-TYPE
    SYNTAX      TmnxEnabledDisabledOrNA
    MAX-ACCESS  read-only
    STATUS      current
    DESCRIPTION
        "The value of tmnxWlanGwBdAssistAddrRes specifies whether the
         assistive address resolution is enabled in bridge domains."
    ::= { tmnxWlanGwBdEntry 11 }

tmnxWlanGwBdNetwMaxMac           OBJECT-TYPE
    SYNTAX      Unsigned32 (0..64)
    MAX-ACCESS  read-only
    STATUS      current
    DESCRIPTION
        "The value of tmnxWlanGwBdNetwMaxMac specifies the maximum number of VM
         MAC entries in each bridge domain."
    ::= { tmnxWlanGwBdEntry 12 }

tmnxWlanGwBdNetwAdminState       OBJECT-TYPE
    SYNTAX      TmnxEnabledDisabledOrNA
    MAX-ACCESS  read-only
    STATUS      current
    DESCRIPTION
        "The value of tmnxWlanGwBdNetwAdminState specifies whether data center
         connections are allowed."
    ::= { tmnxWlanGwBdEntry 13 }

tmnxWlanGwBdAccsMaxMac           OBJECT-TYPE
    SYNTAX      Unsigned32 (0..256)
    MAX-ACCESS  read-only
    STATUS      current
    DESCRIPTION
        "The value of tmnxWlanGwBdAccsMaxMac specifies the maximum number  of
         home MAC entries in each bridge domain."
    ::= { tmnxWlanGwBdEntry 14 }

tmnxWlanGwBdAccsPolicer          OBJECT-TYPE
    SYNTAX      TNamedItemOrEmpty
    MAX-ACCESS  read-only
    STATUS      current
    DESCRIPTION
        "The value of tmnxWlanGwBdAccsPolicer specifies the identifier of the
         bridge domain policer for ingress access traffic."
    ::= { tmnxWlanGwBdEntry 16 }

tmnxWlanGwBdNetwPolicer          OBJECT-TYPE
    SYNTAX      TNamedItemOrEmpty
    MAX-ACCESS  read-only
    STATUS      current
    DESCRIPTION
        "The value of tmnxWlanGwBdNetwPolicer specifies the identifier of the
         bridge domain policer for ingress data center traffic."
    ::= { tmnxWlanGwBdEntry 18 }

tmnxWlanGwVlanXcnctTable         OBJECT-TYPE
    SYNTAX      SEQUENCE OF TmnxWlanGwVlanXcnctEntry
    MAX-ACCESS  not-accessible
    STATUS      current
    DESCRIPTION
        "The tmnxWlanGwVlanXcnctTable contains objects to configure the
         cross-connect configuration data for WLAN GW VLAN ranges."
    ::= { tmnxWlanGwObjs 19 }

tmnxWlanGwVlanXcnctEntry         OBJECT-TYPE
    SYNTAX      TmnxWlanGwVlanXcnctEntry
    MAX-ACCESS  not-accessible
    STATUS      current
    DESCRIPTION
        "Each conceptual row represents the set of cross-connect configuration
         data for a range of VLAN Q-tags."
    INDEX       {
        svcId,
        iesIfIndex,
        tmnxWlanGwVlanTagStart,
        tmnxWlanGwVlanTagEnd
    }
    ::= { tmnxWlanGwVlanXcnctTable 1 }

TmnxWlanGwVlanXcnctEntry         ::= SEQUENCE
{
    tmnxWlanGwVlanXcnctLastChanged   TimeStamp,
    tmnxWlanGwVlanXcnctAccPolicy     TNamedItemOrEmpty,
    tmnxWlanGwVlanXcnctAdminState    TmnxAdminState,
    tmnxWlanGwVlanXcnctAcctUpdInterv Unsigned32,
    tmnxWlanGwVlanXcnctMobAcctUpd    TmnxEnabledDisabled
}

tmnxWlanGwVlanXcnctLastChanged   OBJECT-TYPE
    SYNTAX      TimeStamp
    MAX-ACCESS  read-only
    STATUS      current
    DESCRIPTION
        "The value of tmnxWlanGwVlanXcnctLastChanged indicates the time of the
         most recent management-initiated change."
    ::= { tmnxWlanGwVlanXcnctEntry 1 }

tmnxWlanGwVlanXcnctAccPolicy     OBJECT-TYPE
    SYNTAX      TNamedItemOrEmpty
    MAX-ACCESS  read-create
    STATUS      current
    DESCRIPTION
        "The value of tmnxWlanGwVlanXcnctAccPolicy specifies the name of the
         ISA Radius accounting policy for the WLAN GW VLAN range."
    DEFVAL      { ''H }
    ::= { tmnxWlanGwVlanXcnctEntry 2 }

tmnxWlanGwVlanXcnctAdminState    OBJECT-TYPE
    SYNTAX      TmnxAdminState
    MAX-ACCESS  read-create
    STATUS      current
    DESCRIPTION
        "The value of tmnxWlanGwVlanXcnctAdminState specifies the
         administrative state of the cross-connect."
    DEFVAL      { outOfService }
    ::= { tmnxWlanGwVlanXcnctEntry 3 }

tmnxWlanGwVlanXcnctAcctUpdInterv OBJECT-TYPE
    SYNTAX      Unsigned32 (0 | 5..259200)
    UNITS       "minutes"
    MAX-ACCESS  read-create
    STATUS      current
    DESCRIPTION
        "The value of tmnxWlanGwVlanXcnctAcctUpdInterv specifies the time
         interval between consecutive Interim Accounting Update messages.

         The value zero specifies that the system does not send Interim
         Accounting Update messages."
    REFERENCE
        "RFC 2866 RADIUS Accounting
         section 5.1 Acct-Status-Type.

         RFC 2869 RADIUS Extensions
         section 2.1.  RADIUS support for Interim Accounting Updates."
    DEFVAL      { 0 }
    ::= { tmnxWlanGwVlanXcnctEntry 4 }

tmnxWlanGwVlanXcnctMobAcctUpd    OBJECT-TYPE
    SYNTAX      TmnxEnabledDisabled
    MAX-ACCESS  read-create
    STATUS      current
    DESCRIPTION
        "The value of tmnxWlanGwVlanXcnctMobAcctUpd specifies the
         administrative state of sending mobility-triggered accounting interim
         updates."
    DEFVAL      { disabled }
    ::= { tmnxWlanGwVlanXcnctEntry 5 }

tmnxWlanGwTuBdUeTable            OBJECT-TYPE
    SYNTAX      SEQUENCE OF TmnxWlanGwTuBdUeEntry
    MAX-ACCESS  not-accessible
    STATUS      current
    DESCRIPTION
        "The tmnxWlanGwTuBdUeTable contains the  WLAN Gateway Bridge User
         Equipments (UE) connected to this  system by means of Soft GRE
         tunnels, ordered by tunnel."
    ::= { tmnxWlanGwObjs 20 }

tmnxWlanGwTuBdUeEntry            OBJECT-TYPE
    SYNTAX      TmnxWlanGwTuBdUeEntry
    MAX-ACCESS  not-accessible
    STATUS      current
    DESCRIPTION
        "Each conceptual row represents a WLAN Gateway Bridge User Equipment.

         Entries in this table are created and destroyed by the system."
    INDEX       {
        vRtrID,
        tmnxWlanGwSoftGreTuRemoteAddrTyp,
        tmnxWlanGwSoftGreTuRemoteAddr,
        tmnxWlanGwSoftGreTuLocalAddrType,
        tmnxWlanGwSoftGreTuLocalAddr,
        tmnxWlanGwBdBridgeId,
        tmnxWlanGwUeMacAddress
    }
    ::= { tmnxWlanGwTuBdUeTable 1 }

TmnxWlanGwTuBdUeEntry            ::= SEQUENCE
{ tmnxWlanGwTuBdUeSsid             TNamedItemOrEmpty }

tmnxWlanGwTuBdUeSsid             OBJECT-TYPE
    SYNTAX      TNamedItemOrEmpty
    MAX-ACCESS  read-only
    STATUS      current
    DESCRIPTION
        "The value of tmnxWlanGwTuBdUeSsid indicates the Service Set ID (SSID)
         of this UE.

          This object refers to a conceptual row in the tmnxWlanGwSsidTable."
    ::= { tmnxWlanGwTuBdUeEntry 1 }

tmnxWlanGwGrpTableLastCh         OBJECT-TYPE
    SYNTAX      TimeStamp
    MAX-ACCESS  read-only
    STATUS      current
    DESCRIPTION
        "The value of the object tmnxWlanGwGrpTableLastCh indicates the value
         of sysUpTime at the time of the last modification of an entry in the
         tmnxWlanGwGrpTable."
    ::= { tmnxWlanGwObjs 100 }

tmnxWlanGwIomTableLastCh         OBJECT-TYPE
    SYNTAX      TimeStamp
    MAX-ACCESS  read-only
    STATUS      current
    DESCRIPTION
        "The value of the object tmnxWlanGwIomTableLastCh indicates the value
         of sysUpTime at the time of the last modification of an entry in the
         tmnxWlanGwIomTable."
    ::= { tmnxWlanGwObjs 101 }

tmnxWlanGwSoftGreIfTableLastCh   OBJECT-TYPE
    SYNTAX      TimeStamp
    MAX-ACCESS  read-only
    STATUS      current
    DESCRIPTION
        "The value of the object tmnxWlanGwSoftGreIfTableLastCh indicates the
         value of sysUpTime at the time of the last modification of an entry in
         the tmnxWlanGwSoftGreIfTable."
    ::= { tmnxWlanGwObjs 102 }

tmnxWlanGwIfRetailTableLastCh    OBJECT-TYPE
    SYNTAX      TimeStamp
    MAX-ACCESS  read-only
    STATUS      obsolete
    DESCRIPTION
        "The value of the object tmnxWlanGwIfRetailTableLastCh indicates the
         value of sysUpTime at the time of the last modification of an entry in
         the tmnxWlanGwIfRetailTable."
    ::= { tmnxWlanGwObjs 103 }

tmnxWlanGwMgwProfTableLastCh     OBJECT-TYPE
    SYNTAX      TimeStamp
    MAX-ACCESS  read-only
    STATUS      current
    DESCRIPTION
        "The value of the object tmnxWlanGwMgwProfTableLastCh indicates the
         value of sysUpTime at the time of the last modification of an entry in
         the tmnxWlanGwMgwProfTable."
    ::= { tmnxWlanGwObjs 104 }

tmnxWlanGwMgwAddrTableLastCh     OBJECT-TYPE
    SYNTAX      TimeStamp
    MAX-ACCESS  read-only
    STATUS      current
    DESCRIPTION
        "The value of the object tmnxWlanGwMgwAddrTableLastCh indicates the
         value of sysUpTime at the time of the last modification of an entry in
         the tmnxWlanGwMgwAddrTable."
    ::= { tmnxWlanGwObjs 105 }

tmnxWlanGwTableLastCh            OBJECT-TYPE
    SYNTAX      TimeStamp
    MAX-ACCESS  read-only
    STATUS      current
    DESCRIPTION
        "The value of the object tmnxWlanGwTableLastCh indicates the value of
         sysUpTime at the time of the last modification of an entry in the
         tmnxWlanGwTable."
    ::= { tmnxWlanGwObjs 106 }

tmnxWlanGwVlanTableLastCh        OBJECT-TYPE
    SYNTAX      TimeStamp
    MAX-ACCESS  read-only
    STATUS      current
    DESCRIPTION
        "The value of the object tmnxWlanGwVlanTableLastCh indicates the value
         of sysUpTime at the time of the last modification of an entry in the
         tmnxWlanGwVlanTable."
    ::= { tmnxWlanGwObjs 107 }

tmnxWlanGwPgwTableLastCh         OBJECT-TYPE
    SYNTAX      TimeStamp
    MAX-ACCESS  read-only
    STATUS      current
    DESCRIPTION
        "The value of the object tmnxWlanGwPgwTableLastCh indicates the value
         of sysUpTime at the time of the last modification of an entry in the
         tmnxWlanGwPgwTable."
    ::= { tmnxWlanGwObjs 108 }

tmnxWlanGwGgsnTableLastCh        OBJECT-TYPE
    SYNTAX      TimeStamp
    MAX-ACCESS  read-only
    STATUS      current
    DESCRIPTION
        "The value of the object tmnxWlanGwGgsnTableLastCh indicates the value
         of sysUpTime at the time of the last modification of an entry in the
         tmnxWlanGwGgsnTable."
    ::= { tmnxWlanGwObjs 109 }

tmnxWlanGwSubIfTableLastCh       OBJECT-TYPE
    SYNTAX      TimeStamp
    MAX-ACCESS  read-only
    STATUS      current
    DESCRIPTION
        "The value of the object tmnxWlanGwSubIfTableLastCh indicates the value
         of sysUpTime at the time of the last modification of an entry in the
         tmnxWlanGwSubIfTable."
    ::= { tmnxWlanGwObjs 110 }

tmnxWlanGwVlanDsmTableLastCh     OBJECT-TYPE
    SYNTAX      TimeStamp
    MAX-ACCESS  read-only
    STATUS      current
    DESCRIPTION
        "The value of the object tmnxWlanGwVlanDsmTableLastCh indicates the
         value of sysUpTime at the time of the last modification of an entry in
         the tmnxWlanGwVlanDsmTable."
    ::= { tmnxWlanGwObjs 111 }

tmnxWlanGwDsmIpFilTableLastCh    OBJECT-TYPE
    SYNTAX      TimeStamp
    MAX-ACCESS  read-only
    STATUS      current
    DESCRIPTION
        "The value of the object tmnxWlanGwDsmIpFilTableLastCh indicates the
         value of sysUpTime at the time of the last modification of an entry in
         the tmnxWlanGwDsmIpFilTable."
    ::= { tmnxWlanGwObjs 112 }

tmnxWlanGwDsmIpFilN3TableLastCh  OBJECT-TYPE
    SYNTAX      TimeStamp
    MAX-ACCESS  read-only
    STATUS      current
    DESCRIPTION
        "The value of the object tmnxWlanGwDsmIpFilN3TableLastCh indicates the
         value of sysUpTime at the time of the last modification of an entry in
         the tmnxWlanGwDsmIpFilN3Table."
    ::= { tmnxWlanGwObjs 113 }

tmnxWlanGwPolicerTableLastCh     OBJECT-TYPE
    SYNTAX      TimeStamp
    MAX-ACCESS  read-only
    STATUS      current
    DESCRIPTION
        "The value of the object tmnxWlanGwPolicerTableLastCh indicates the
         value of sysUpTime at the time of the last modification of an entry in
         the tmnxWlanGwPolicerTable."
    ::= { tmnxWlanGwObjs 114 }

tmnxWlanGwL2ApTableLastCh        OBJECT-TYPE
    SYNTAX      TimeStamp
    MAX-ACCESS  read-only
    STATUS      current
    DESCRIPTION
        "The value of the object tmnxWlanGwL2ApTableLastCh indicates the value
         of sysUpTime at the time of the last modification of an entry in the
         tmnxWlanGwL2ApTable."
    ::= { tmnxWlanGwObjs 117 }

tmnxWlanGwVplsTableLastCh        OBJECT-TYPE
    SYNTAX      TimeStamp
    MAX-ACCESS  read-only
    STATUS      current
    DESCRIPTION
        "The value of the object tmnxWlanGwVplsTableLastCh indicates the value
         of sysUpTime at the time of the last modification of an entry in the
         tmnxWlanGwVplsTable."
    ::= { tmnxWlanGwObjs 118 }

tmnxWlanGwDsmIpFil6N3TableLastCh OBJECT-TYPE
    SYNTAX      TimeStamp
    MAX-ACCESS  read-only
    STATUS      current
    DESCRIPTION
        "The value of the object tmnxWlanGwDsmIpFil6N3TableLastCh indicates the
         value of sysUpTime at the time of the last modification of an entry in
         the tmnxWlanGwDsmIpFil6N3Table."
    ::= { tmnxWlanGwObjs 119 }

tmnxWlanGwVlanBrgTableLastCh     OBJECT-TYPE
    SYNTAX      TimeStamp
    MAX-ACCESS  read-only
    STATUS      current
    DESCRIPTION
        "The value of the object tmnxWlanGwVlanBrgTableLastCh indicates the
         value of sysUpTime at the time of the last modification of an entry in
         the tmnxWlanGwVlanBrgTable."
    ::= { tmnxWlanGwObjs 121 }

tmnxWlanGwSubIfPmTableLastCh     OBJECT-TYPE
    SYNTAX      TimeStamp
    MAX-ACCESS  read-only
    STATUS      current
    DESCRIPTION
        "The value of the object tmnxWlanGwSubIfPmTableLastCh indicates the
         value of sysUpTime at the time of the last modification of an entry in
         the tmnxWlanGwSubIfPmTable."
    ::= { tmnxWlanGwObjs 122 }

tmnxWlanGwVlanDhcp6TableLastCh   OBJECT-TYPE
    SYNTAX      TimeStamp
    MAX-ACCESS  read-only
    STATUS      current
    DESCRIPTION
        "The value of the object tmnxWlanGwVlanDhcp6TableLastCh indicates the
         value of sysUpTime at the time of the last modification of an entry in
         the tmnxWlanGwVlanDhcp6Table."
    ::= { tmnxWlanGwObjs 123 }

tmnxWlanGwVlanSlaacTableLastCh   OBJECT-TYPE
    SYNTAX      TimeStamp
    MAX-ACCESS  read-only
    STATUS      current
    DESCRIPTION
        "The value of the object tmnxWlanGwVlanSlaacTableLastCh indicates the
         value of sysUpTime at the time of the last modification of an entry in
         the tmnxWlanGwVlanSlaacTable."
    ::= { tmnxWlanGwObjs 124 }

tmnxWlanGwDsmTableLastCh         OBJECT-TYPE
    SYNTAX      TimeStamp
    MAX-ACCESS  read-only
    STATUS      current
    DESCRIPTION
        "The value of the object tmnxWlanGwDsmTableLastCh indicates the value
         of sysUpTime at the time of the last modification of an entry in the
         tmnxWlanGwDsmTable."
    ::= { tmnxWlanGwObjs 125 }

tmnxWlanGwMdaTableLastCh         OBJECT-TYPE
    SYNTAX      TimeStamp
    MAX-ACCESS  read-only
    STATUS      current
    DESCRIPTION
        "The value of the object tmnxWlanGwMdaTableLastCh indicates the value
         of sysUpTime at the time of the last modification of an entry in the
         tmnxWlanGwMdaTable."
    ::= { tmnxWlanGwObjs 127 }

tmnxWlanGwXcnctTableLastCh       OBJECT-TYPE
    SYNTAX      TimeStamp
    MAX-ACCESS  read-only
    STATUS      current
    DESCRIPTION
        "The value of the object tmnxWlanGwXcnctTableLastCh indicates the value
         of sysUpTime at the time of the last modification of an entry in the
         tmnxWlanGwXcnctTable."
    ::= { tmnxWlanGwObjs 128 }

tmnxWlanGwVlanXcnctTableLastCh   OBJECT-TYPE
    SYNTAX      TimeStamp
    MAX-ACCESS  read-only
    STATUS      current
    DESCRIPTION
        "The value of the object tmnxWlanGwVlanXcnctTableLastCh indicates the
         value of sysUpTime at the time of the last modification of an entry in
         the tmnxWlanGwVlanXcnctTable."
    ::= { tmnxWlanGwObjs 129 }

tmnxWlanGwVlanLeTableLastCh      OBJECT-TYPE
    SYNTAX      TimeStamp
    MAX-ACCESS  read-only
    STATUS      current
    DESCRIPTION
        "The value of the object tmnxWlanGwVlanLeTableLastCh indicates the
         value of sysUpTime at the time of the last modification of an entry in
         the tmnxWlanGwVlanLeTable."
    ::= { tmnxWlanGwObjs 130 }

tmnxWlanGwMmeTableLastChanged    OBJECT-TYPE
    SYNTAX      TimeStamp
    MAX-ACCESS  read-only
    STATUS      current
    DESCRIPTION
        "The value of the object tmnxWlanGwMmeTableLastChanged indicates the
         value of sysUpTime at the time of the last modification of an entry in
         the tmnxWlanGwMmeTable."
    ::= { tmnxWlanGwObjs 131 }

tmnxWlanGwGrpIfGwAddrTableLastCh OBJECT-TYPE
    SYNTAX      TimeStamp
    MAX-ACCESS  read-only
    STATUS      current
    DESCRIPTION
        "The value of the object tmnxWlanGwGrpIfGwAddrTableLastCh indicates the
         value of sysUpTime at the time of the last modification of an entry in
         the tmnxWlanGwGrpIfGwAddrTable."
    ::= { tmnxWlanGwObjs 132 }

tmnxWlanGwVlanExtTableLastCh     OBJECT-TYPE
    SYNTAX      TimeStamp
    MAX-ACCESS  read-only
    STATUS      current
    DESCRIPTION
        "The value of the object tmnxWlanGwVlanExtTableLastCh indicates the
         value of sysUpTime at the time of the last modification of an entry in
         the tmnxWlanGwVlanExtTable."
    ::= { tmnxWlanGwObjs 133 }

tmnxWlanGwResrcProblem           OBJECT-TYPE
    SYNTAX      TruthValue
    MAX-ACCESS  read-only
    STATUS      current
    DESCRIPTION
        "The value of the object tmnxWlanGwResrcProblem indicates if there is a
         resource problem detected while attempting to activate some part of
         the WLAN Gateway configuration of this system."
    ::= { tmnxWlanGwObjs 200 }

tmnxWlanGwNumSoftGreTu           OBJECT-TYPE
    SYNTAX      Gauge32
    MAX-ACCESS  read-only
    STATUS      current
    DESCRIPTION
        "The value of the object tmnxWlanGwNumSoftGreTu indicates the actual
         number of Soft GRE tunnels terminated by this system."
    ::= { tmnxWlanGwObjs 201 }

tmnxWlanGwPeakNumSoftGreTu       OBJECT-TYPE
    SYNTAX      Gauge32
    MAX-ACCESS  read-only
    STATUS      current
    DESCRIPTION
        "The value of the object tmnxWlanGwPeakNumSoftGreTu indicates the peak
         number of Soft GRE tunnels terminated by this system at any time,
         since the system was last initialized or the value of this object was
         last reset."
    ::= { tmnxWlanGwObjs 202 }

tmnxWlanGwNumUe                  OBJECT-TYPE
    SYNTAX      Gauge32
    MAX-ACCESS  read-only
    STATUS      current
    DESCRIPTION
        "The value of the object tmnxWlanGwNumUe indicates the actual number of
         UE processed by this system."
    ::= { tmnxWlanGwObjs 203 }

tmnxWlanGwPeakNumUe              OBJECT-TYPE
    SYNTAX      Gauge32
    MAX-ACCESS  read-only
    STATUS      current
    DESCRIPTION
        "The value of the object tmnxWlanGwPeakNumUe indicates the peak number
         of UE processed by this system at any time, since the system was last
         initialized or the value of this object was last reset."
    ::= { tmnxWlanGwObjs 204 }

tmnxWlanGwNumMgw                 OBJECT-TYPE
    SYNTAX      Gauge32
    MAX-ACCESS  read-only
    STATUS      current
    DESCRIPTION
        "The value of the object tmnxWlanGwNumMgw indicates the actual number
         of Mobile Gateways connected to this system.

         It is equal to the number of rows in the tmnxWlanGwMgwTable."
    ::= { tmnxWlanGwObjs 205 }

tmnxWlanGwMgwNumHeldSe           OBJECT-TYPE
    SYNTAX      Gauge32
    MAX-ACCESS  read-only
    STATUS      current
    DESCRIPTION
        "The value of the object tmnxWlanGwMgwNumHeldSe indicates the actual
         number of GTP session contexts held by this system while their
         associated UE are disconnected."
    ::= { tmnxWlanGwObjs 210 }

tmnxGtpNumMme                    OBJECT-TYPE
    SYNTAX      Gauge32
    MAX-ACCESS  read-only
    STATUS      current
    DESCRIPTION
        "The value of the object tmnxGtpNumMme indicates the actual number of
         Mobility Management Entities (MME) connected to this system. It is
         equal to the number of rows in the table 'tmnxWlanGwMgwTable' with
         interface type S11."
    ::= { tmnxWlanGwObjs 211 }

tmnxGtpNumEnodeB                 OBJECT-TYPE
    SYNTAX      Gauge32
    MAX-ACCESS  read-only
    STATUS      current
    DESCRIPTION
        "The value of the object tmnxGtpNumEnodeB indicates the actual number
         of Enode-B connected to this system. It is equal to the number of SDP
         tunnels created for GTP."
    ::= { tmnxWlanGwObjs 212 }

tmnxGtpNumS11Sessions            OBJECT-TYPE
    SYNTAX      Gauge32
    MAX-ACCESS  read-only
    STATUS      current
    DESCRIPTION
        "The value of the object tmnxGtpNumS11Sessions indicates the actual
         number of GTP S11 sessions. It is equal to the number of rows in the
         table 'tmnxGtpS11SeTable'."
    ::= { tmnxWlanGwObjs 213 }

tmnxGtpNumUplinks                OBJECT-TYPE
    SYNTAX      Gauge32
    MAX-ACCESS  read-only
    STATUS      current
    DESCRIPTION
        "The value of the object tmnxGtpNumUplinks indicates the actual number
         of GTP S2A, S2B or GGSN sessions. It is equal to the number of rows in
         the table 'tmnxWlanGwGtpSeTable'."
    ::= { tmnxWlanGwObjs 214 }

tmnxGtpNumS11IdleSessions        OBJECT-TYPE
    SYNTAX      Gauge32
    MAX-ACCESS  read-only
    STATUS      current
    DESCRIPTION
        "The value of the object tmnxGtpNumS11IdleSessions indicates the number
         of GTP S11 sessions in idle state."
    ::= { tmnxWlanGwObjs 215 }

tmnxWlanGwVappTableLastCh        OBJECT-TYPE
    SYNTAX      TimeStamp
    MAX-ACCESS  read-only
    STATUS      current
    DESCRIPTION
        "The value of the object tmnxWlanGwVappTableLastCh indicates the value
         of sysUpTime at the time of the last modification of an entry in the
         tmnxWlanGwVappTable."
    ::= { tmnxWlanGwObjs 216 }

tmnxWlanGwNotificationObjs       OBJECT IDENTIFIER ::= { tmnxWlanGw 2 }

tmnxWlanGwNotifyDescription      OBJECT-TYPE
    SYNTAX      DisplayString (SIZE (0..255))
    MAX-ACCESS  accessible-for-notify
    STATUS      current
    DESCRIPTION
        "The object tmnxWlanGwNotifyDescription is a printable character
         string."
    ::= { tmnxWlanGwNotificationObjs 1 }

tmnxWlanGwNotifyTrue             OBJECT-TYPE
    SYNTAX      TruthValue
    MAX-ACCESS  accessible-for-notify
    STATUS      current
    DESCRIPTION
        "The object tmnxWlanGwNotifyTrue contains a boolean truth value."
    ::= { tmnxWlanGwNotificationObjs 2 }

tmnxWlanGwNotify3gppRelease      OBJECT-TYPE
    SYNTAX      DisplayString (SIZE (2))
    MAX-ACCESS  accessible-for-notify
    STATUS      current
    DESCRIPTION
        "The object tmnxWlanGwNotify3gppRelease contains a string representing
         a 3GPP release."
    REFERENCE
        "3GPP TS 29.061, section 16.4.7.2 Coding 3GPP Vendor-Specific RADIUS attributes
         item 5 - 3GPP-GPRS Negotiated QoS profile."
    ::= { tmnxWlanGwNotificationObjs 3 }

tmnxWlanGwNotifyMdaSlotNum       OBJECT-TYPE
    SYNTAX      Unsigned32
    MAX-ACCESS  accessible-for-notify
    STATUS      current
    DESCRIPTION
        "The object tmnxWlanGwNotifyMdaSlotNum contains the value of an MDA
         slot within a specific IOM card."
    ::= { tmnxWlanGwNotificationObjs 4 }

tmnxWlanGwNotifySubIfIndex       OBJECT-TYPE
    SYNTAX      InterfaceIndex
    MAX-ACCESS  accessible-for-notify
    STATUS      current
    DESCRIPTION
        "The value of tmnxWlanGwNotifySubIfIndex indicates the index of the
         subscriber interface."
    ::= { tmnxWlanGwNotificationObjs 5 }

tmnxWlanGwNotifyAddrFamily       OBJECT-TYPE
    SYNTAX      TmnxWlanGwSubIfIpsAddrFamily
    MAX-ACCESS  accessible-for-notify
    STATUS      current
    DESCRIPTION
        "The value of tmnxWlanGwNotifyAddrFamily indicates the address family
         of the pool as defined in the textual convention
         TmnxWlanGwSubIfIpsAddrFamily."
    ::= { tmnxWlanGwNotificationObjs 6 }

tmnxWlanGwNotifyIsaGrpId         OBJECT-TYPE
    SYNTAX      TmnxWlanGwIsaGrpIdOrZero
    MAX-ACCESS  accessible-for-notify
    STATUS      current
    DESCRIPTION
        "The value of the object tmnxWlanGwNotifyIsaGrpId indicates the group
         identifier of the ISA for the given prefix."
    ::= { tmnxWlanGwNotificationObjs 7 }

tmnxWlanGwNotifyIsaMemberId      OBJECT-TYPE
    SYNTAX      Unsigned32
    MAX-ACCESS  accessible-for-notify
    STATUS      current
    DESCRIPTION
        "The value of the object tmnxWlanGwNotifyIsaMemberId indicates the
         member identifier of the ISA for the given prefix."
    ::= { tmnxWlanGwNotificationObjs 8 }

tmnxWlanGwNotifyD6cServer1       OBJECT-TYPE
    SYNTAX      InetAddressIPv6
    MAX-ACCESS  accessible-for-notify
    STATUS      current
    DESCRIPTION
        "The value of the object tmnxWlanGwNotifyD6cServer1 indicates one of
         the DHCPv6 servers."
    ::= { tmnxWlanGwNotificationObjs 9 }

tmnxWlanGwNotifyD6cServer2       OBJECT-TYPE
    SYNTAX      InetAddressIPv6
    MAX-ACCESS  accessible-for-notify
    STATUS      current
    DESCRIPTION
        "The value of the object tmnxWlanGwNotifyD6cServer2 indicates one of
         the DHCPv6 servers."
    ::= { tmnxWlanGwNotificationObjs 10 }

tmnxWlanGwNotifyD6cServer3       OBJECT-TYPE
    SYNTAX      InetAddressIPv6
    MAX-ACCESS  accessible-for-notify
    STATUS      current
    DESCRIPTION
        "The value of the object tmnxWlanGwNotifyD6cServer3 indicates one of
         the DHCPv6 servers."
    ::= { tmnxWlanGwNotificationObjs 11 }

tmnxWlanGwNotifyD6cServer4       OBJECT-TYPE
    SYNTAX      InetAddressIPv6
    MAX-ACCESS  accessible-for-notify
    STATUS      current
    DESCRIPTION
        "The value of the object tmnxWlanGwNotifyD6cServer4 indicates one of
         the DHCPv6 servers."
    ::= { tmnxWlanGwNotificationObjs 12 }

tmnxWlanGwNotifyD6cServer5       OBJECT-TYPE
    SYNTAX      InetAddressIPv6
    MAX-ACCESS  accessible-for-notify
    STATUS      current
    DESCRIPTION
        "The value of the object tmnxWlanGwNotifyD6cServer5 indicates one of
         the DHCPv6 servers."
    ::= { tmnxWlanGwNotificationObjs 13 }

tmnxWlanGwNotifyD6cServer6       OBJECT-TYPE
    SYNTAX      InetAddressIPv6
    MAX-ACCESS  accessible-for-notify
    STATUS      current
    DESCRIPTION
        "The value of the object tmnxWlanGwNotifyD6cServer6 indicates one of
         the DHCPv6 servers."
    ::= { tmnxWlanGwNotificationObjs 14 }

tmnxWlanGwNotifyD6cServer7       OBJECT-TYPE
    SYNTAX      InetAddressIPv6
    MAX-ACCESS  accessible-for-notify
    STATUS      current
    DESCRIPTION
        "The value of the object tmnxWlanGwNotifyD6cServer7 indicates one of
         the DHCPv6 servers."
    ::= { tmnxWlanGwNotificationObjs 15 }

tmnxWlanGwNotifyD6cServer8       OBJECT-TYPE
    SYNTAX      InetAddressIPv6
    MAX-ACCESS  accessible-for-notify
    STATUS      current
    DESCRIPTION
        "The value of the object tmnxWlanGwNotifyD6cServer8 indicates one of
         the DHCPv6 servers."
    ::= { tmnxWlanGwNotificationObjs 16 }

tmnxWlanGwNotifySubnetAddrType   OBJECT-TYPE
    SYNTAX      InetAddressType
    MAX-ACCESS  accessible-for-notify
    STATUS      current
    DESCRIPTION
        "The value of the object tmnxWlanGwNotifySubnetAddrType indicates the
         type of the subnet address sent in the notification."
    ::= { tmnxWlanGwNotificationObjs 17 }

tmnxWlanGwNotifySubnetAddr       OBJECT-TYPE
    SYNTAX      InetAddress (SIZE (0|4|16))
    MAX-ACCESS  accessible-for-notify
    STATUS      current
    DESCRIPTION
        "The value of the object tmnxWlanGwNotifySubnetAddr indicates the
         subnet address sent in the notification."
    ::= { tmnxWlanGwNotificationObjs 18 }

tmnxWlanGwNotifySubnetPrefLen    OBJECT-TYPE
    SYNTAX      InetAddressPrefixLength
    MAX-ACCESS  accessible-for-notify
    STATUS      current
    DESCRIPTION
        "The value of the object tmnxWlanGwNotifySubnetPrefLen indicates the
         prefix length of the subnet address sent in the notification."
    ::= { tmnxWlanGwNotificationObjs 19 }

tmnxWlanGwNotifyGtpMsgType       OBJECT-TYPE
    SYNTAX      Unsigned32 (0..255)
    MAX-ACCESS  accessible-for-notify
    STATUS      current
    DESCRIPTION
        "The value of the object tmnxWlanGwNotifyGtpMsgType indicates the type
         of a GTP message."
    REFERENCE
        "3GPP TS 29.060,
         section 7 GTP Messages and Message Formats, for Gn

         3GPP TS 129.274, section 6.1 Message Format and Type values, for S2a or S2b."
    ::= { tmnxWlanGwNotificationObjs 20 }

tmnxWlanGwNotifyGtpMsgDirection  OBJECT-TYPE
    SYNTAX      TDirectionIngEgr
    MAX-ACCESS  accessible-for-notify
    STATUS      current
    DESCRIPTION
        "The value of the object tmnxWlanGwNotifyGtpMsgDirection indicates the
         direction a GTP message."
    ::= { tmnxWlanGwNotificationObjs 21 }

tmnxWlanGwNotifyImsi             OBJECT-TYPE
    SYNTAX      TmnxMobImsiStr
    MAX-ACCESS  accessible-for-notify
    STATUS      current
    DESCRIPTION
        "The value of the object tmnxWlanGwNotifyImsi indicates an IMSI
         (International Mobile Subscriber Identity)."
    ::= { tmnxWlanGwNotificationObjs 22 }

tmnxWlanGwNotifyTeid             OBJECT-TYPE
    SYNTAX      Unsigned32
    MAX-ACCESS  accessible-for-notify
    STATUS      current
    DESCRIPTION
        "The value of the object tmnxWlanGwNotifyTeid indicates a Tunnel
         Endpoint Identifier (TEID)."
    ::= { tmnxWlanGwNotificationObjs 23 }

tmnxWlanGwNotifyBdBridgeId       OBJECT-TYPE
    SYNTAX      Unsigned32
    MAX-ACCESS  accessible-for-notify
    STATUS      current
    DESCRIPTION
        "The object tmnxWlanGwNotifyBdBridgeId indicates a WLAN Gateway Bridge
         Domain Bridge Id."
    ::= { tmnxWlanGwNotificationObjs 24 }

tmnxWlanGwNotifyUeMacAddress     OBJECT-TYPE
    SYNTAX      MacAddress
    MAX-ACCESS  accessible-for-notify
    STATUS      current
    DESCRIPTION
        "The object tmnxWlanGwNotifyUeMacAddress indicates a UE MAC address."
    ::= { tmnxWlanGwNotificationObjs 25 }

tmnxWlanGwNotifyChassisIndex     OBJECT-TYPE
    SYNTAX      TmnxChassisIndex
    MAX-ACCESS  accessible-for-notify
    STATUS      current
    DESCRIPTION
        "The object tmnxWlanGwNotifyChassisIndex contains the system
         identifier."
    ::= { tmnxWlanGwNotificationObjs 26 }

tmnxWlanGwNotifyCardSlotNum      OBJECT-TYPE
    SYNTAX      TmnxSlotNum
    MAX-ACCESS  accessible-for-notify
    STATUS      current
    DESCRIPTION
        "The object tmnxWlanGwNotifyCardSlotNum contains the unique value that
         identifies an IOM slot within the system."
    ::= { tmnxWlanGwNotificationObjs 27 }

tmnxWlanGwNotifyEntity           OBJECT-TYPE
    SYNTAX      TmnxWlanGwWatermarkEntity
    MAX-ACCESS  accessible-for-notify
    STATUS      current
    DESCRIPTION
        "The object tmnxWlanGwNotifyEntity indicates what kind of entity is
         associated with a usage watermark."
    ::= { tmnxWlanGwNotificationObjs 29 }

tmnxWlanGwNotifyEsaNum           OBJECT-TYPE
    SYNTAX      TmnxEsaNum
    MAX-ACCESS  accessible-for-notify
    STATUS      current
    DESCRIPTION
        "The value of tmnxWlanGwNotifyEsaNum indicates the number of the
         Extended Service Appliance where the member is located."
    ::= { tmnxWlanGwNotificationObjs 30 }

tmnxWlanGwNotifyEsaVappNum       OBJECT-TYPE
    SYNTAX      TmnxEsaVappNum
    MAX-ACCESS  accessible-for-notify
    STATUS      current
    DESCRIPTION
        "The value of tmnxWlanGwNotifyEsaVappNum indicates the number of the
         Virtual Machine within an Extended Service Appliance where the member
         is located."
    ::= { tmnxWlanGwNotificationObjs 31 }

tmnxGtpObjs                      OBJECT IDENTIFIER ::= { tmnxWlanGw 3 }

tmnxGtpS11ItfTableLastChanged    OBJECT-TYPE
    SYNTAX      TimeStamp
    MAX-ACCESS  read-only
    STATUS      current
    DESCRIPTION
        "The value of tmnxGtpS11ItfTableLastChanged indicates the  sysUpTime at
         the time of the most recent change to the tmnxGtpS11ItfTable."
    ::= { tmnxGtpObjs 1 }

tmnxGtpS11ItfTable               OBJECT-TYPE
    SYNTAX      SEQUENCE OF TmnxGtpS11ItfEntry
    MAX-ACCESS  not-accessible
    STATUS      current
    DESCRIPTION
        "The tmnxGtpS11ItfTable contains objects to configure the GTP S11
         interface."
    ::= { tmnxGtpObjs 2 }

tmnxGtpS11ItfEntry               OBJECT-TYPE
    SYNTAX      TmnxGtpS11ItfEntry
    MAX-ACCESS  not-accessible
    STATUS      current
    DESCRIPTION
        "Each conceptual row represents the configuration related to a GTP S11
         interface."
    INDEX       {
        vRtrID,
        tmnxGtpS11ItfName
    }
    ::= { tmnxGtpS11ItfTable 1 }

TmnxGtpS11ItfEntry               ::= SEQUENCE
{
    tmnxGtpS11ItfName                TNamedItem,
    tmnxGtpS11ItfRowStatus           RowStatus,
    tmnxGtpS11ItfLastChanged         TimeStamp,
    tmnxGtpS11ItfApnPolicyName       TNamedItemOrEmpty
}

tmnxGtpS11ItfName                OBJECT-TYPE
    SYNTAX      TNamedItem
    MAX-ACCESS  not-accessible
    STATUS      current
    DESCRIPTION
        "The value of tmnxGtpS11ItfName specifies the name of the GTP S11
         interface."
    ::= { tmnxGtpS11ItfEntry 1 }

tmnxGtpS11ItfRowStatus           OBJECT-TYPE
    SYNTAX      RowStatus
    MAX-ACCESS  read-create
    STATUS      current
    DESCRIPTION
        "The value of tmnxGtpS11ItfRowStatus specifies the row status of this
         row."
    ::= { tmnxGtpS11ItfEntry 2 }

tmnxGtpS11ItfLastChanged         OBJECT-TYPE
    SYNTAX      TimeStamp
    MAX-ACCESS  read-only
    STATUS      current
    DESCRIPTION
        "The value of tmnxGtpS11ItfLastChanged indicates the sysUpTime when an
         object in this table was last modified. A value 0 means that no change
         was made to this row since it was created."
    ::= { tmnxGtpS11ItfEntry 3 }

tmnxGtpS11ItfApnPolicyName       OBJECT-TYPE
    SYNTAX      TNamedItemOrEmpty
    MAX-ACCESS  read-create
    STATUS      current
    DESCRIPTION
        "The value of tmnxGtpS11ItfApnPolicyName specifies the name of the GTP
         S11 interface APN policy."
    DEFVAL      { ''H }
    ::= { tmnxGtpS11ItfEntry 4 }

tmnxGtpPpmTableLastChanged       OBJECT-TYPE
    SYNTAX      TimeStamp
    MAX-ACCESS  read-only
    STATUS      current
    DESCRIPTION
        "The value of tmnxGtpPpmTableLastChanged indicates the  sysUpTime at
         the time of the most recent change to the tmnxGtpPpmTable."
    ::= { tmnxGtpObjs 3 }

tmnxGtpPpmTable                  OBJECT-TYPE
    SYNTAX      SEQUENCE OF TmnxGtpPpmEntry
    MAX-ACCESS  not-accessible
    STATUS      current
    DESCRIPTION
        "The tmnxGtpPpmTable contains objects to configure the GTP peer profile
         mappings."
    ::= { tmnxGtpObjs 4 }

tmnxGtpPpmEntry                  OBJECT-TYPE
    SYNTAX      TmnxGtpPpmEntry
    MAX-ACCESS  not-accessible
    STATUS      current
    DESCRIPTION
        "Each conceptual row represents the configuration related to a GTP peer
         profile mapping."
    INDEX       {
        vRtrID,
        tmnxGtpPpmGtpItfType,
        tmnxGtpPpmAddrType,
        tmnxGtpPpmAddr,
        tmnxGtpPpmAddrPrefixLen
    }
    ::= { tmnxGtpPpmTable 1 }

TmnxGtpPpmEntry                  ::= SEQUENCE
{
    tmnxGtpPpmGtpItfType             TmnxGtpInterfaceType,
    tmnxGtpPpmAddrType               InetAddressType,
    tmnxGtpPpmAddr                   InetAddress,
    tmnxGtpPpmAddrPrefixLen          InetAddressPrefixLength,
    tmnxGtpPpmRowStatus              RowStatus,
    tmnxGtpPpmLastChanged            TimeStamp,
    tmnxGtpPpmProfileName            TNamedItemOrEmpty
}

tmnxGtpPpmGtpItfType             OBJECT-TYPE
    SYNTAX      TmnxGtpInterfaceType
    MAX-ACCESS  not-accessible
    STATUS      current
    DESCRIPTION
        "The value of tmnxGtpPpmGtpItfType specifies the type of the GTP
         interface."
    ::= { tmnxGtpPpmEntry 1 }

tmnxGtpPpmAddrType               OBJECT-TYPE
    SYNTAX      InetAddressType
    MAX-ACCESS  not-accessible
    STATUS      current
    DESCRIPTION
        "The value of tmnxGtpPpmAddrType specifies the address type of
         tmnxGtpPpmAddr."
    ::= { tmnxGtpPpmEntry 2 }

tmnxGtpPpmAddr                   OBJECT-TYPE
    SYNTAX      InetAddress (SIZE (4|16))
    MAX-ACCESS  not-accessible
    STATUS      current
    DESCRIPTION
        "The value of tmnxGtpPpmAddr specifies the IP address of the subnet."
    ::= { tmnxGtpPpmEntry 3 }

tmnxGtpPpmAddrPrefixLen          OBJECT-TYPE
    SYNTAX      InetAddressPrefixLength (0..128)
    MAX-ACCESS  not-accessible
    STATUS      current
    DESCRIPTION
        "The value of tmnxGtpPpmAddrPrefixLen specifies the prefix length of
         the subnet."
    ::= { tmnxGtpPpmEntry 4 }

tmnxGtpPpmRowStatus              OBJECT-TYPE
    SYNTAX      RowStatus
    MAX-ACCESS  read-create
    STATUS      current
    DESCRIPTION
        "The value of tmnxGtpPpmRowStatus specifies the row status of this row."
    ::= { tmnxGtpPpmEntry 5 }

tmnxGtpPpmLastChanged            OBJECT-TYPE
    SYNTAX      TimeStamp
    MAX-ACCESS  read-only
    STATUS      current
    DESCRIPTION
        "The value of tmnxGtpPpmLastChanged indicates the sysUpTime when an
         object in this table was last modified. A value 0 means that no change
         was made to this row since it was created."
    ::= { tmnxGtpPpmEntry 6 }

tmnxGtpPpmProfileName            OBJECT-TYPE
    SYNTAX      TNamedItemOrEmpty
    MAX-ACCESS  read-create
    STATUS      current
    DESCRIPTION
        "The value of tmnxGtpPpmProfileName specifies the name of the GTP peer
         profile."
    DEFVAL      { ''H }
    ::= { tmnxGtpPpmEntry 7 }

tmnxGtpS11SeTableLastChanged     OBJECT-TYPE
    SYNTAX      TimeStamp
    MAX-ACCESS  read-only
    STATUS      current
    DESCRIPTION
        "The value of tmnxGtpS11SeTableLastChanged indicates the sysUpTime at
         the time of the most recent change to the tmnxGtpS11SeTable."
    ::= { tmnxGtpObjs 5 }

tmnxGtpS11SeTable                OBJECT-TYPE
    SYNTAX      SEQUENCE OF TmnxGtpS11SeEntry
    MAX-ACCESS  not-accessible
    STATUS      current
    DESCRIPTION
        "The tmnxGtpS11SeTable contains information about GTP (GPRS Tunnel
         Protocol) S11 sessions."
    ::= { tmnxGtpObjs 6 }

tmnxGtpS11SeEntry                OBJECT-TYPE
    SYNTAX      TmnxGtpS11SeEntry
    MAX-ACCESS  not-accessible
    STATUS      current
    DESCRIPTION
        "Each conceptual row represents information about a particular GTP S11
         session.

         Rows are created or removed automatically by the system."
    INDEX       {
        tmnxGtpS11SeImsi,
        tmnxGtpS11SeApn
    }
    ::= { tmnxGtpS11SeTable 1 }

TmnxGtpS11SeEntry                ::= SEQUENCE
{
    tmnxGtpS11SeImsi                 TmnxMobImsiStr,
    tmnxGtpS11SeApn                  TmnxMobApn,
    tmnxGtpS11SePeerRouter           TmnxVRtrIDOrZero,
    tmnxGtpS11SePeerAddrType         InetAddressType,
    tmnxGtpS11SePeerAddr             InetAddress,
    tmnxGtpS11SeRemoteCtrlTeid       Unsigned32,
    tmnxGtpS11SeLocalCtrlTeid        Unsigned32,
    tmnxGtpS11SeChrgChar             TmnxWlanGwChargingCharBits,
    tmnxGtpS11SeQosUplinkAmbr        TmnxWlanGwAmbr,
    tmnxGtpS11SeQosDwnlinkAmbr       TmnxWlanGwAmbr,
    tmnxGtpS11SePdnTeid              Unsigned32,
    tmnxGtpS11SeUliCgi               OCTET STRING,
    tmnxGtpS11SeUliSai               OCTET STRING,
    tmnxGtpS11SeUliRai               OCTET STRING,
    tmnxGtpS11SeUliTai               OCTET STRING,
    tmnxGtpS11SeUliEcgi              OCTET STRING
}

tmnxGtpS11SeImsi                 OBJECT-TYPE
    SYNTAX      TmnxMobImsiStr (SIZE (9..15))
    MAX-ACCESS  not-accessible
    STATUS      current
    DESCRIPTION
        "The value of tmnxGtpS11SeImsi indicates the IMSI."
    ::= { tmnxGtpS11SeEntry 1 }

tmnxGtpS11SeApn                  OBJECT-TYPE
    SYNTAX      TmnxMobApn
    MAX-ACCESS  not-accessible
    STATUS      current
    DESCRIPTION
        "The value of the object tmnxGtpS11SeApn indicates the APN (Access
         Point Name)."
    REFERENCE
        "3GPP TS 23.003 Numbering, addressing and identification,
         section 9 Definition of Access Point Name"
    ::= { tmnxGtpS11SeEntry 2 }

tmnxGtpS11SePeerRouter           OBJECT-TYPE
    SYNTAX      TmnxVRtrIDOrZero
    MAX-ACCESS  read-only
    STATUS      current
    DESCRIPTION
        "The value of tmnxGtpS11SePeerRouter indicates the identifier of the
         virtual router instance where the GTP tunnel is terminated."
    ::= { tmnxGtpS11SeEntry 3 }

tmnxGtpS11SePeerAddrType         OBJECT-TYPE
    SYNTAX      InetAddressType
    MAX-ACCESS  read-only
    STATUS      current
    DESCRIPTION
        "The value of tmnxGtpS11SePeerAddrType indicates the address type of
         tmnxGtpS11SePeerAddr."
    ::= { tmnxGtpS11SeEntry 4 }

tmnxGtpS11SePeerAddr             OBJECT-TYPE
    SYNTAX      InetAddress (SIZE (4|16))
    MAX-ACCESS  read-only
    STATUS      current
    DESCRIPTION
        "The value of the object tmnxGtpS11SePeerAddr indicates the IP address
         of the MME. This is the source IP address in the tunnel header of
         received packets."
    ::= { tmnxGtpS11SeEntry 5 }

tmnxGtpS11SeRemoteCtrlTeid       OBJECT-TYPE
    SYNTAX      Unsigned32
    MAX-ACCESS  read-only
    STATUS      current
    DESCRIPTION
        "The value of tmnxGtpS11SeRemoteCtrlTeid indicates the remote control
         plane Tunnel Endpoint Identifier (TEID)."
    ::= { tmnxGtpS11SeEntry 6 }

tmnxGtpS11SeLocalCtrlTeid        OBJECT-TYPE
    SYNTAX      Unsigned32
    MAX-ACCESS  read-only
    STATUS      current
    DESCRIPTION
        "The value of tmnxGtpS11SeLocalCtrlTeid indicates the local control
         plane Tunnel Endpoint Identifier (TEID)."
    ::= { tmnxGtpS11SeEntry 7 }

tmnxGtpS11SeChrgChar             OBJECT-TYPE
    SYNTAX      TmnxWlanGwChargingCharBits
    MAX-ACCESS  read-only
    STATUS      current
    DESCRIPTION
        "The value of tmnxGtpS11SeChrgChar indicates the Charging
         Characteristics."
    ::= { tmnxGtpS11SeEntry 10 }

tmnxGtpS11SeQosUplinkAmbr        OBJECT-TYPE
    SYNTAX      TmnxWlanGwAmbr
    UNITS       "kilobps"
    MAX-ACCESS  read-only
    STATUS      current
    DESCRIPTION
        "The value of tmnxGtpS11SeQosUplinkAmbr indicates the uplink Aggregated
         Maximum Bit Rate (AMBR)."
    ::= { tmnxGtpS11SeEntry 11 }

tmnxGtpS11SeQosDwnlinkAmbr       OBJECT-TYPE
    SYNTAX      TmnxWlanGwAmbr
    UNITS       "kilobps"
    MAX-ACCESS  read-only
    STATUS      current
    DESCRIPTION
        "The value of tmnxGtpS11SeQosDwnlinkAmbr indicates the downlink
         Aggregated Maximum Bit Rate (AMBR)."
    ::= { tmnxGtpS11SeEntry 12 }

tmnxGtpS11SePdnTeid              OBJECT-TYPE
    SYNTAX      Unsigned32
    MAX-ACCESS  read-only
    STATUS      current
    DESCRIPTION
        "The value of tmnxGtpS11SePdnTeid indicates the local PDN (S5) Endpoint
         Identifier (TEID)."
    ::= { tmnxGtpS11SeEntry 13 }

tmnxGtpS11SeUliCgi               OBJECT-TYPE
    SYNTAX      OCTET STRING (SIZE (0|7))
    MAX-ACCESS  read-only
    STATUS      current
    DESCRIPTION
        "The value of tmnxGtpS11SeUliCgi indicates the Cell Global Identifier."
    ::= { tmnxGtpS11SeEntry 14 }

tmnxGtpS11SeUliSai               OBJECT-TYPE
    SYNTAX      OCTET STRING (SIZE (0|7))
    MAX-ACCESS  read-only
    STATUS      current
    DESCRIPTION
        "The value of tmnxGtpS11SeUliSai indicates the Service Area Identifier."
    ::= { tmnxGtpS11SeEntry 15 }

tmnxGtpS11SeUliRai               OBJECT-TYPE
    SYNTAX      OCTET STRING (SIZE (0|7))
    MAX-ACCESS  read-only
    STATUS      current
    DESCRIPTION
        "The value of tmnxGtpS11SeUliRai indicates the Routing Area Identity."
    ::= { tmnxGtpS11SeEntry 16 }

tmnxGtpS11SeUliTai               OBJECT-TYPE
    SYNTAX      OCTET STRING (SIZE (0|5))
    MAX-ACCESS  read-only
    STATUS      current
    DESCRIPTION
        "The value of tmnxGtpS11SeUliTai indicates the Tracking Area Identity."
    ::= { tmnxGtpS11SeEntry 17 }

tmnxGtpS11SeUliEcgi              OBJECT-TYPE
    SYNTAX      OCTET STRING (SIZE (0|7))
    MAX-ACCESS  read-only
    STATUS      current
    DESCRIPTION
        "The value of tmnxGtpS11SeUliEcgi indicates the E-UTRAN Cell Global
         Identifier."
    ::= { tmnxGtpS11SeEntry 18 }

tmnxGtpS11BcTableLastChanged     OBJECT-TYPE
    SYNTAX      TimeStamp
    MAX-ACCESS  read-only
    STATUS      current
    DESCRIPTION
        "The value of tmnxGtpS11BcTableLastChanged indicates the sysUpTime at
         the time of the most recent change to the tmnxGtpS11BcTable."
    ::= { tmnxGtpObjs 7 }

tmnxGtpS11BcTable                OBJECT-TYPE
    SYNTAX      SEQUENCE OF TmnxGtpS11BcEntry
    MAX-ACCESS  not-accessible
    STATUS      current
    DESCRIPTION
        "The tmnxGtpS11BcTable contains information about GTP (GPRS Tunnel
         Protocol) S11 bearers."
    ::= { tmnxGtpObjs 8 }

tmnxGtpS11BcEntry                OBJECT-TYPE
    SYNTAX      TmnxGtpS11BcEntry
    MAX-ACCESS  not-accessible
    STATUS      current
    DESCRIPTION
        "Each conceptual row represents information about a particular bearer
         context.

         Rows are created or removed automatically by the system."
    INDEX       {
        tmnxGtpS11SeImsi,
        tmnxGtpS11SeApn,
        tmnxGtpS11BcId
    }
    ::= { tmnxGtpS11BcTable 1 }

TmnxGtpS11BcEntry                ::= SEQUENCE
{
    tmnxGtpS11BcId                   TmnxMobBearerId,
    tmnxGtpS11BcRemoteTeid           Unsigned32,
    tmnxGtpS11BcLocalTeid            Unsigned32,
    tmnxGtpS11BcQosUlGbr             Unsigned32,
    tmnxGtpS11BcQosUlMbr             Unsigned32,
    tmnxGtpS11BcQosDlGbr             Unsigned32,
    tmnxGtpS11BcQosDlMbr             Unsigned32,
    tmnxGtpS11BcQosQci               TmnxMobExtQci,
    tmnxGtpS11BcQosArp               TmnxMobArp,
    tmnxGtpS11BcRemoteAddrType       InetAddressType,
    tmnxGtpS11BcRemoteAddr           InetAddress
}

tmnxGtpS11BcId                   OBJECT-TYPE
    SYNTAX      TmnxMobBearerId
    MAX-ACCESS  not-accessible
    STATUS      current
    DESCRIPTION
        "The value of tmnxGtpS11BcId indicates the identifier of this *S11*
         bearer context."
    ::= { tmnxGtpS11BcEntry 1 }

tmnxGtpS11BcRemoteTeid           OBJECT-TYPE
    SYNTAX      Unsigned32
    MAX-ACCESS  read-only
    STATUS      current
    DESCRIPTION
        "The value of tmnxGtpS11BcRemoteTeid indicates the remote Tunnel
         Endpoint Identifier (TEID)."
    ::= { tmnxGtpS11BcEntry 2 }

tmnxGtpS11BcLocalTeid            OBJECT-TYPE
    SYNTAX      Unsigned32
    MAX-ACCESS  read-only
    STATUS      current
    DESCRIPTION
        "The value of tmnxGtpS11BcLocalTeid indicates the local Tunnel Endpoint
         Identifier (TEID)."
    ::= { tmnxGtpS11BcEntry 3 }

tmnxGtpS11BcQosUlGbr             OBJECT-TYPE
    SYNTAX      Unsigned32
    UNITS       "kilobps"
    MAX-ACCESS  read-only
    STATUS      current
    DESCRIPTION
        "The value of tmnxGtpS11BcQosUlGbr indicates the uplink Guaranteed Bit
         Rate (GBR)."
    ::= { tmnxGtpS11BcEntry 10 }

tmnxGtpS11BcQosUlMbr             OBJECT-TYPE
    SYNTAX      Unsigned32
    UNITS       "kilobps"
    MAX-ACCESS  read-only
    STATUS      current
    DESCRIPTION
        "The value of tmnxGtpS11BcQosUlMbr indicates the uplink Maximum Bit
         Rate (MBR)."
    ::= { tmnxGtpS11BcEntry 11 }

tmnxGtpS11BcQosDlGbr             OBJECT-TYPE
    SYNTAX      Unsigned32
    UNITS       "kilobps"
    MAX-ACCESS  read-only
    STATUS      current
    DESCRIPTION
        "The value of tmnxGtpS11BcQosDlGbr indicates the downlink Guaranteed
         Bit Rate (GBR)."
    ::= { tmnxGtpS11BcEntry 12 }

tmnxGtpS11BcQosDlMbr             OBJECT-TYPE
    SYNTAX      Unsigned32
    UNITS       "kilobps"
    MAX-ACCESS  read-only
    STATUS      current
    DESCRIPTION
        "The value of tmnxGtpS11BcQosDlMbr indicates the downlink Maximum Bit
         Rate (MBR)."
    ::= { tmnxGtpS11BcEntry 13 }

tmnxGtpS11BcQosQci               OBJECT-TYPE
    SYNTAX      TmnxMobExtQci
    MAX-ACCESS  read-only
    STATUS      current
    DESCRIPTION
        "The value of tmnxGtpS11BcQosQci indicates the Qos Class Identifier"
    ::= { tmnxGtpS11BcEntry 14 }

tmnxGtpS11BcQosArp               OBJECT-TYPE
    SYNTAX      TmnxMobArp
    MAX-ACCESS  read-only
    STATUS      current
    DESCRIPTION
        "The value of tmnxGtpS11BcQosArp indicates the Allocation and Retention
         Priority (ARP)."
    ::= { tmnxGtpS11BcEntry 15 }

tmnxGtpS11BcRemoteAddrType       OBJECT-TYPE
    SYNTAX      InetAddressType
    MAX-ACCESS  read-only
    STATUS      current
    DESCRIPTION
        "The value of tmnxGtpS11BcRemoteAddrType indicates the address type of
         tmnxGtpS11BcRemoteAddr."
    ::= { tmnxGtpS11BcEntry 16 }

tmnxGtpS11BcRemoteAddr           OBJECT-TYPE
    SYNTAX      InetAddress (SIZE (4|16))
    MAX-ACCESS  read-only
    STATUS      current
    DESCRIPTION
        "The value of the object tmnxGtpS11BcRemoteAddr indicates the IP
         address of the eNodeB."
    ::= { tmnxGtpS11BcEntry 17 }

tmnxGtpUplinkTableLastChanged    OBJECT-TYPE
    SYNTAX      TimeStamp
    MAX-ACCESS  read-only
    STATUS      current
    DESCRIPTION
        "The value of tmnxGtpUplinkTableLastChanged indicates the sysUpTime at
         the time of the most recent change to the tmnxGtpUplinkTable."
    ::= { tmnxGtpObjs 9 }

tmnxGtpUplinkTable               OBJECT-TYPE
    SYNTAX      SEQUENCE OF TmnxGtpUplinkEntry
    MAX-ACCESS  not-accessible
    STATUS      current
    DESCRIPTION
        "The tmnxGtpUplinkTable contains objects to configure the GTP Uplink
         interface."
    ::= { tmnxGtpObjs 10 }

tmnxGtpUplinkEntry               OBJECT-TYPE
    SYNTAX      TmnxGtpUplinkEntry
    MAX-ACCESS  not-accessible
    STATUS      current
    DESCRIPTION
        "Each conceptual row represents the configuration related to a GTP
         Uplink interface."
    INDEX       { vRtrID }
    ::= { tmnxGtpUplinkTable 1 }

TmnxGtpUplinkEntry               ::= SEQUENCE
{
    tmnxGtpUplinkRowStatus           RowStatus,
    tmnxGtpUplinkLastChanged         TimeStamp,
    tmnxGtpUplinkApn                 TmnxMobApnOrZero,
    tmnxGtpUplinkPdnType             INTEGER
}

tmnxGtpUplinkRowStatus           OBJECT-TYPE
    SYNTAX      RowStatus
    MAX-ACCESS  read-create
    STATUS      current
    DESCRIPTION
        "The value of tmnxGtpUplinkRowStatus specifies the row status of this
         row."
    ::= { tmnxGtpUplinkEntry 1 }

tmnxGtpUplinkLastChanged         OBJECT-TYPE
    SYNTAX      TimeStamp
    MAX-ACCESS  read-only
    STATUS      current
    DESCRIPTION
        "The value of tmnxGtpUplinkLastChanged indicates the sysUpTime when an
         object in this table was last modified. A value 0 means that no change
         was made to this row since it was created."
    ::= { tmnxGtpUplinkEntry 2 }

tmnxGtpUplinkApn                 OBJECT-TYPE
    SYNTAX      TmnxMobApnOrZero (SIZE (0..80))
    MAX-ACCESS  read-create
    STATUS      current
    DESCRIPTION
        "The value of tmnxGtpUplinkApn specifies the Network Identifier part of
         the Access Point Name (APN) to be used for UE in this virtual router
         instance if the APN cannot be determined by other means."
    REFERENCE
        "3GPP TS 23.003,
         section 9.1.1 Format of APN Network Identifier"
    DEFVAL      { "" }
    ::= { tmnxGtpUplinkEntry 3 }

tmnxGtpUplinkPdnType             OBJECT-TYPE
    SYNTAX      INTEGER {
        ipv4   (0),
        ipv6   (1),
        ipv4v6 (2)
    }
    MAX-ACCESS  read-create
    STATUS      current
    DESCRIPTION
        "The value of tmnxGtpUplinkPdnType specifies the default 3GPP-PDN type
         to be used for the UE in this virtual router instance if the 3GPP-PDN
         type could not be determined by other means."
    DEFVAL      { ipv4 }
    ::= { tmnxGtpUplinkEntry 4 }

tmnxGtpUpfDataEpTableLastChanged OBJECT-TYPE
    SYNTAX      TimeStamp
    MAX-ACCESS  read-only
    STATUS      current
    DESCRIPTION
        "The value of tmnxGtpUpfDataEpTableLastChanged indicates the sysUpTime
         at the time of the most recent change to the
         tmnxGtpUpfDataEndpointTable."
    ::= { tmnxGtpObjs 11 }

tmnxGtpUpfDataEndpointTable      OBJECT-TYPE
    SYNTAX      SEQUENCE OF TmnxGtpUpfDataEndpointEntry
    MAX-ACCESS  not-accessible
    STATUS      current
    DESCRIPTION
        "The tmnxGtpUpfDataEndpointTable contains objects to configure the GTP
         data endpoint."
    ::= { tmnxGtpObjs 12 }

tmnxGtpUpfDataEndpointEntry      OBJECT-TYPE
    SYNTAX      TmnxGtpUpfDataEndpointEntry
    MAX-ACCESS  not-accessible
    STATUS      current
    DESCRIPTION
        "Each conceptual row represents the configuration related to a GTP data
         endpoint."
    INDEX       { vRtrID }
    ::= { tmnxGtpUpfDataEndpointTable 1 }

TmnxGtpUpfDataEndpointEntry      ::= SEQUENCE
{
    tmnxGtpUpfDataEndptRowStatus     RowStatus,
    tmnxGtpUpfDataEndptLastChanged   TimeStamp,
    tmnxGtpUpfDataEndptItfName       TNamedItemOrEmpty,
    tmnxGtpUpfDataEndpFpeId          TmnxFpeId
}

tmnxGtpUpfDataEndptRowStatus     OBJECT-TYPE
    SYNTAX      RowStatus
    MAX-ACCESS  read-create
    STATUS      current
    DESCRIPTION
        "The value of tmnxGtpUpfDataEndptRowStatus specifies the row status of
         this row."
    ::= { tmnxGtpUpfDataEndpointEntry 1 }

tmnxGtpUpfDataEndptLastChanged   OBJECT-TYPE
    SYNTAX      TimeStamp
    MAX-ACCESS  read-only
    STATUS      current
    DESCRIPTION
        "The value of tmnxGtpUpfDataEndptLastChanged indicates the sysUpTime
         when an object in this table was last modified. A value 0 means that
         no change was made to this row since it was created."
    ::= { tmnxGtpUpfDataEndpointEntry 2 }

tmnxGtpUpfDataEndptItfName       OBJECT-TYPE
    SYNTAX      TNamedItemOrEmpty
    MAX-ACCESS  read-create
    STATUS      current
    DESCRIPTION
        "The value of tmnxGtpUpfDataEndptItfName specifies the name of the GTP
         data endpoint interface."
    ::= { tmnxGtpUpfDataEndpointEntry 3 }

tmnxGtpUpfDataEndpFpeId          OBJECT-TYPE
    SYNTAX      TmnxFpeId
    MAX-ACCESS  read-create
    STATUS      current
    DESCRIPTION
        "The value of tmnxGtpUpfDataEndpFpeId specifies the
         id of the fpe which will be used for the setup of
         the gtp data endpoint."
    ::= { tmnxGtpUpfDataEndpointEntry 4 }

tmnxWlanGwConformance            OBJECT IDENTIFIER ::= { tmnxSRConfs 81 }

tmnxWlanGwCompliances            OBJECT IDENTIFIER ::= { tmnxWlanGwConformance 1 }

tmnxWlanGwCompliance             MODULE-COMPLIANCE
    STATUS      obsolete
    DESCRIPTION
        "The compliance statement for management of WLAN Gateway on Nokia 7xxx
         series systems."
    MODULE
        MANDATORY-GROUPS {
            tmnxWlanGwIsaGroup,
            tmnxWlanGwSoftGreGroup,
            tmnxWlanGwObjGroup
        }
    ::= { tmnxWlanGwCompliances 1 }

tmnxWlanGwNotifyCompliance       MODULE-COMPLIANCE
    STATUS      obsolete
    DESCRIPTION
        "The compliance statement for WLAN Gateway notifications on Nokia SROS
         series systems."
    MODULE
        MANDATORY-GROUPS {
            tmnxWlanGwNotifyGroup
        }
    ::= { tmnxWlanGwCompliances 2 }

tmnxWlanGwV10Compliance          MODULE-COMPLIANCE
    STATUS      obsolete
    DESCRIPTION
        "The compliance statement for management of WLAN Gateway on Nokia 7xxx
         series systems."
    MODULE
        MANDATORY-GROUPS {
            tmnxWlanGwIsaGroup,
            tmnxWlanGwSoftGreGroup,
            tmnxWlanGwObjGroup,
            tmnxWlanGwMgwGroup
        }
    ::= { tmnxWlanGwCompliances 3 }

tmnxWlanGwV11Compliance          MODULE-COMPLIANCE
    STATUS      obsolete
    DESCRIPTION
        "The compliance statement for management of WLAN Gateway on Nokia 7xxx
         series systems."
    MODULE
        MANDATORY-GROUPS {
            tmnxWlanGwIsaGroup,
            tmnxWlanGwSoftGreGroup,
            tmnxWlanGwSoftGreV11v0Group,
            tmnxWlanGwObjGroup,
            tmnxWlanGwMgwGroup,
            tmnxWlanGwMgwV11v0Group,
            tmnxWlanGwMgwQosIeGroup,
            tmnxWlanGwMgwChargingCharGroup,
            tmnxWlanGwObsoletedGroup
        }
    ::= { tmnxWlanGwCompliances 4 }

tmnxWlanGwV12Compliance          MODULE-COMPLIANCE
    STATUS      obsolete
    DESCRIPTION
        "The compliance statement for management of WLAN Gateway on Nokia 7xxx
         series systems release 12.0."
    MODULE
        MANDATORY-GROUPS {
            tmnxWlanGwIsaGroup,
            tmnxWlanGwSoftGreV12v0Group,
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMgwSeHoldTimeGroup,
            tmnxWlanGwDsmGroup,
            tmnxWlanGwObsoletedGroup
        }
    ::= { tmnxWlanGwCompliances 5 }

tmnxWlanGwV13Compliance          MODULE-COMPLIANCE
    STATUS      obsolete
    DESCRIPTION
        "The compliance statement for management of WLAN Gateway on Nokia 7xxx
         series systems release 13.0."
    MODULE
        MANDATORY-GROUPS {
            tmnxWlanGwIsaGroup,
            tmnxWlanGwSoftGreV12v0Group,
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwObsoletedGroup
        }
    ::= { tmnxWlanGwCompliances 6 }

tmnxWlanGwV14Compliance          MODULE-COMPLIANCE
    STATUS      obsolete
    DESCRIPTION
        "The compliance statement for management of WLAN Gateway on Nokia 7xxx
         series systems release 14.0."
    MODULE
        MANDATORY-GROUPS {
            tmnxWlanGwIsaGroup,
            tmnxWlanGwSoftGreV12v0Group,
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwV14v0Group,
            tmnxWlanGwMgwAmbrIeGroup,
            tmnxWlanGwVsrGroup,
            tmnxWlanGwObsoletedGroup,
            tmnxWlanGwDsmV14v0Group,
            tmnxWlanGwMdaRedundancyGroup,
            tmnxWlanGwInterVlanMobGroup,
            tmnxWlanGwTunnelQueryGroup
        }
    ::= { tmnxWlanGwCompliances 7 }

tmnxWlanGwV15Compliance          MODULE-COMPLIANCE
    STATUS      obsolete
    DESCRIPTION
        "The compliance statement for management of WLAN Gateway on Nokia 7xxx
         series systems release 15.0."
    MODULE
        MANDATORY-GROUPS {
            tmnxWlanGwIsaGroup,
            tmnxWlanGwSoftGreV12v0Group,
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMobilityV15v0Group,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwV14v0Group,
            tmnxWlanGwMgwAmbrIeGroup,
            tmnxWlanGwVsrGroup,
            tmnxWlanGwObsoletedGroup,
            tmnxWlanGwDsmV14v0Group,
            tmnxWlanGwMdaRedundancyGroup,
            tmnxWlanGwInterVlanMobGroup,
            tmnxWlanGwTunnelQueryGroup,
            tmnxWlanGwHomeUeGroup,
            tmnxWlanGwXconnectGroup,
            tmnxWlanGwLeV15v0Group,
            tmnxWlanGwDsmV15v0Group
        }
    ::= { tmnxWlanGwCompliances 8 }

tmnxWlanGwNotifyV15v0Compliance  MODULE-COMPLIANCE
    STATUS      obsolete
    DESCRIPTION
        "The compliance statement for WLAN Gateway notifications on Nokia SROS
         series systems in release 15.0."
    MODULE
        MANDATORY-GROUPS {
            tmnxWlanGwNotifyGroup,
            tmnxWlanGwNotifyV15v0Group
        }
    ::= { tmnxWlanGwCompliances 9 }

tmnxWlanGwV16Compliance          MODULE-COMPLIANCE
    STATUS      obsolete
    DESCRIPTION
        "The compliance statement for management of WLAN Gateway on Nokia 7xxx
         series systems release 16.0."
    MODULE
        MANDATORY-GROUPS {
            tmnxWlanGwIsaGroup,
            tmnxWlanGwSoftGreV12v0Group,
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMobilityV15v0Group,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwV14v0Group,
            tmnxWlanGwMgwAmbrIeGroup,
            tmnxWlanGwVsrGroup,
            tmnxWlanGwObsoletedGroup,
            tmnxWlanGwDsmV14v0Group,
            tmnxWlanGwMdaRedundancyGroup,
            tmnxWlanGwInterVlanMobGroup,
            tmnxWlanGwTunnelQueryGroup,
            tmnxWlanGwHomeUeGroup,
            tmnxWlanGwXconnectGroup,
            tmnxWlanGwLeV15v0Group,
            tmnxWlanGwDsmV15v0Group,
            tmnxWlanGwIsaV16v0Group,
            tmnxWlanGwIsaScalingGroup,
            tmnxWlanGwUeQryV16v0Group,
            tmnxWlanGwGrpIfGwAddrV16v0Group,
            tmnxWlanGwLePolicerV16v0Group,
            tmnxWlanGwQryNameGroup
        }
    ::= { tmnxWlanGwCompliances 10 }

tmnxWlanGwNotifyV16v0Compliance  MODULE-COMPLIANCE
    STATUS      current
    DESCRIPTION
        "The compliance statement for WLAN Gateway notifications on Nokia SROS
         series systems in release 16.0."
    MODULE
        MANDATORY-GROUPS {
            tmnxWlanGwNotifyGroup,
            tmnxWlanGwNotifyV15v0Group,
            tmnxWlanGwNotifyV16v0Group
        }
    ::= { tmnxWlanGwCompliances 11 }

tmnxWlanGwV19Compliance          MODULE-COMPLIANCE
    STATUS      obsolete
    DESCRIPTION
        "The compliance statement for management of WLAN Gateway on Nokia 7xxx
         series systems release 19.0."
    MODULE
        MANDATORY-GROUPS {
            tmnxWlanGwSoftGreV12v0Group,
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMobilityV15v0Group,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwV14v0Group,
            tmnxWlanGwMgwAmbrIeGroup,
            tmnxWlanGwVsrGroup,
            tmnxWlanGwObsoletedGroup,
            tmnxWlanGwDsmV14v0Group,
            tmnxWlanGwMdaRedundancyGroup,
            tmnxWlanGwInterVlanMobGroup,
            tmnxWlanGwTunnelQueryGroup,
            tmnxWlanGwHomeUeGroup,
            tmnxWlanGwXconnectGroup,
            tmnxWlanGwLeV15v0Group,
            tmnxWlanGwDsmV15v0Group,
            tmnxWlanGwIsaScalingGroup,
            tmnxWlanGwUeQryV16v0Group,
            tmnxWlanGwGrpIfGwAddrV16v0Group,
            tmnxWlanGwLePolicerV16v0Group,
            tmnxWlanGwQryNameGroup,
            tmnxWlanGwIsaV19v0Group,
            tmnxWlanGwDsmV19v0Group,
            tmnxWlanGwEsaV19v0Group,
            tmnxWlanGwDataTriggUeGroup,
            tmnxWlanGwVlanExtV21v0Group,
            tmnxWlanGwDsmV21v0Group,
            tmnxWlanGwRadiusLessAuthGroup,
            tmnxWlanGwRadiusLessAuthAaGroup
        }
    ::= { tmnxWlanGwCompliances 12 }

tmnxWlanGwV22Compliance          MODULE-COMPLIANCE
    STATUS      current
    DESCRIPTION
        "The compliance statement for management of WLAN Gateway on Nokia SROS
         series systems release 22.0."
    MODULE
        MANDATORY-GROUPS {
            tmnxWlanGwRedGroup,
            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMobilityV15v0Group,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwV14v0Group,
            tmnxWlanGwMgwAmbrIeGroup,
            tmnxWlanGwVsrGroup,
            tmnxWlanGwObsoletedGroup,
            tmnxWlanGwDsmV14v0Group,
            tmnxWlanGwMdaRedundancyGroup,
            tmnxWlanGwInterVlanMobGroup,
            tmnxWlanGwTunnelQueryGroup,
            tmnxWlanGwHomeUeGroup,
            tmnxWlanGwXconnectGroup,
            tmnxWlanGwLeV15v0Group,
            tmnxWlanGwDsmV15v0Group,
            tmnxWlanGwIsaScalingGroup,
            tmnxWlanGwUeQryV16v0Group,
            tmnxWlanGwGrpIfGwAddrV16v0Group,
            tmnxWlanGwLePolicerV16v0Group,
            tmnxWlanGwQryNameGroup,
            tmnxWlanGwIsaV19v0Group,
            tmnxWlanGwDsmV19v0Group,
            tmnxWlanGwEsaV19v0Group,
            tmnxWlanGwDataTriggUeGroup,
            tmnxWlanGwVlanExtV21v0Group,
            tmnxWlanGwDsmV21v0Group,
            tmnxWlanGwRadiusLessAuthGroup,
            tmnxWlanGwRadiusLessAuthAaGroup,
            tmnxWlanGwSoftGreV22v0Group,
            tmnxWlanGwDynL2WholesaleGroup
        }
    ::= { tmnxWlanGwCompliances 13 }

tmnxWlanGwGroups                 OBJECT IDENTIFIER ::= { tmnxWlanGwConformance 2 }

tmnxWlanGwIsaGroup               OBJECT-GROUP
    OBJECTS     {
        tmnxWlanGwGrpTableLastCh,
        tmnxWlanGwGrpRowStatus,
        tmnxWlanGwGrpLastMgmtChange,
        tmnxWlanGwGrpDescription,
        tmnxWlanGwGrpAdminState,
        tmnxWlanGwGrpActiveIomLimit,
        tmnxWlanGwGrpPortPlcy,
        tmnxWlanGwGrpTunnelPortPlcy,
        tmnxWlanGwGrpOperState,
        tmnxWlanGwIomTableLastCh,
        tmnxWlanGwIomRowStatus,
        tmnxWlanGwIomLastMgmtChange,
        tmnxWlanGwIomOperState,
        tmnxWlanGwIsaMemberChassisIndex,
        tmnxWlanGwIsaMemberCardSlotNum,
        tmnxWlanGwIsaMemberSlotNum,
        tmnxWlanGwIsaMemberNumSoftGreTu,
        tmnxWlanGwIsaMemberNumUe,
        tmnxWlanGwIsaMemberEegMemberAct,
        tmnxWlanGwIsaMemberEegMemberPend,
        tmnxWlanGwIsaMemberTuQosProblem,
        tmnxWlanGwIsaMemberStatsName,
        tmnxWlanGwIsaMemberStatsVal,
        tmnxWlanGwIsaMemberStatsValHw,
        tmnxWlanGwIsaMemberStatsValue,
        tmnxWlanGwResrcProblem
    }
    STATUS      obsolete
    DESCRIPTION
        "The group of objects providing configuration of WLAN Gateway ISA on
         Nokia SROS series systems."
    ::= { tmnxWlanGwGroups 1 }

tmnxWlanGwSoftGreGroup           OBJECT-GROUP
    OBJECTS     {
        tmnxWlanGwSoftGreIfLastCh,
        tmnxWlanGwSoftGreIfAdminState,
        tmnxWlanGwSoftGreIfRouter,
        tmnxWlanGwSoftGreIfGwAddrType,
        tmnxWlanGwSoftGreIfGwAddr,
        tmnxWlanGwSoftGreIfGrpId,
        tmnxWlanGwSoftGreIfShapingType,
        tmnxWlanGwSoftGreIfShapeMultiUe,
        tmnxWlanGwSoftGreIfEQosPlcy,
        tmnxWlanGwSoftGreIfESchedPlcy,
        tmnxWlanGwSoftGreIfEAggRateLimit,
        tmnxWlanGwSoftGreIfMobTrigger,
        tmnxWlanGwSoftGreIfMobHoldTime,
        tmnxWlanGwSoftGreIfDefRetailSvc,
        tmnxWlanGwSoftGreIfTcpMssAdjust,
        tmnxWlanGwSoftGreIfEHoldTime,
        tmnxWlanGwSoftGreIfNumSoftGreTu,
        tmnxWlanGwSoftGreIfTableLastCh,
        tmnxWlanGwSoftGreTuEstabTime,
        tmnxWlanGwSoftGreTuIsaGroup,
        tmnxWlanGwSoftGreTuIsaMember,
        tmnxWlanGwSoftGreTuNumUe,
        tmnxWlanGwTuQosEegSvcId,
        tmnxWlanGwTuQosEegPortId,
        tmnxWlanGwTuQosEegEncapValue,
        tmnxWlanGwTuQosEegName,
        tmnxWlanGwTuQosEegMember,
        tmnxWlanGwTuQosState,
        tmnxWlanGwTuQosNumUe,
        tmnxWlanGwTuQosRemainingHoldTime,
        tmnxWlanGwSoftGreTuUeSsid
    }
    STATUS      obsolete
    DESCRIPTION
        "The group of objects providing configuration of WLAN Gateway Soft GRE
         group interfaces on Nokia SROS series systems."
    ::= { tmnxWlanGwGroups 2 }

tmnxWlanGwObjGroup               OBJECT-GROUP
    OBJECTS     {
        tmnxWlanGwIfRetailRowStatus,
        tmnxWlanGwIfRetailLastCh,
        tmnxWlanGwIfRetailService,
        tmnxWlanGwIfRetailTableLastCh,
        tmnxWlanGwUeQTag,
        tmnxWlanGwUeMplsLabel,
        tmnxWlanGwUeTuRouter,
        tmnxWlanGwUeTuAddrType,
        tmnxWlanGwUeTuRemoteAddr,
        tmnxWlanGwUeTuLocalAddr,
        tmnxWlanGwUeTuQosRetailService,
        tmnxWlanGwUeSsid,
        tmnxWlanGwUePrevApAddrType,
        tmnxWlanGwUePrevApAddr,
        tmnxWlanGwUeLastMoveTime,
        tmnxWlanGwSsidNumUe,
        tmnxWlanGwNumSoftGreTu,
        tmnxWlanGwPeakNumSoftGreTu,
        tmnxWlanGwNumUe,
        tmnxWlanGwPeakNumUe
    }
    STATUS      obsolete
    DESCRIPTION
        "The group of objects providing configuration of WLAN Gateway on Nokia
         SROS series systems."
    ::= { tmnxWlanGwGroups 3 }

tmnxWlanGwMgwGroup               OBJECT-GROUP
    OBJECTS     {
        tmnxWlanGwUeImsi,
        tmnxWlanGwMgwProfTableLastCh,
        tmnxWlanGwMgwProfRowStatus,
        tmnxWlanGwMgwProfLastChanged,
        tmnxWlanGwMgwProfDescription,
        tmnxWlanGwMgwProfKeepAlvRetryCnt,
        tmnxWlanGwMgwProfMsgReTxTimeout,
        tmnxWlanGwMgwProfMsgReTxRetryCnt,
        tmnxWlanGwMgwProfKeepAlvTimeout,
        tmnxWlanGwMgwProfKeepAlvResp,
        tmnxWlanGwMgwProfTtl,
        tmnxWlanGwMgwProfInterfaceType,
        tmnxWlanGwMgwAddrTableLastCh,
        tmnxWlanGwMgwAddrRowStatus,
        tmnxWlanGwMgwAddrLastMgmtChange,
        tmnxWlanGwMgwAddrProfile,
        tmnxWlanGwMgwLocalAddrType,
        tmnxWlanGwMgwLocalAddr,
        tmnxWlanGwMgwTime,
        tmnxWlanGwMgwProfile,
        tmnxWlanGwMgwControl,
        tmnxWlanGwMgwRestartCnt,
        tmnxWlanGwMgwState,
        tmnxWlanGwMgwInterfaceType,
        tmnxWlanMgwStatsName,
        tmnxWlanMgwStatsVal,
        tmnxWlanMgwStatsValLw,
        tmnxWlanMgwStatsValHw,
        tmnxWlanGwGtpSeMgwRouter,
        tmnxWlanGwGtpSeMgwAddrType,
        tmnxWlanGwGtpSeMgwAddr,
        tmnxWlanGwGtpSeRemoteCtrlTeid,
        tmnxWlanGwGtpSeLocalCtrlTeid,
        tmnxWlanGwBcRemoteTeid,
        tmnxWlanGwBcLocalTeid,
        tmnxWlanGwSysCfgServingNwMcc,
        tmnxWlanGwSysCfgServingNwMnc,
        tmnxWlanGwRowStatus,
        tmnxWlanGwLastCh,
        tmnxWlanGwApn,
        tmnxWlanGwTableLastCh,
        tmnxWlanGwNumMgw,
        tmnxWlanGwGtpStatsName,
        tmnxWlanGwGtpStatsVal,
        tmnxWlanGwGtpStatsValLw,
        tmnxWlanGwGtpStatsValHw
    }
    STATUS      current
    DESCRIPTION
        "The group of objects providing configuration of WLAN Gateway Mobile
         Gateway profiles on Nokia SROS series systems."
    ::= { tmnxWlanGwGroups 4 }

tmnxWlanGwSoftGreV11v0Group      OBJECT-GROUP
    OBJECTS     {
        tmnxWlanGwSoftGreIfDataTrigg,
        tmnxWlanGwSoftGreIfAuthPlcy,
        tmnxWlanGwSoftGreIfAuthHoldTime,
        tmnxWlanGwSoftGreIfRadProxVrtr,
        tmnxWlanGwSoftGreIfRadProxSrv,
        tmnxWlanGwSoftGreIfRadProxMacFmt,
        tmnxWlanGwSoftGreIfGwV6AddrType,
        tmnxWlanGwSoftGreIfGwV6Addr,
        tmnxWlanGwSoftGreXtLastCh,
        tmnxWlanGwSoftGreXtDhcp,
        tmnxWlanGwSoftGreXtAddrType,
        tmnxWlanGwSoftGreXtAddr,
        tmnxWlanGwSoftGreXtLeaseTime,
        tmnxWlanGwSoftGreXtActLeaseTime,
        tmnxWlanGwSoftGreXtDns1AddrType,
        tmnxWlanGwSoftGreXtDns1Addr,
        tmnxWlanGwSoftGreXtDns2AddrType,
        tmnxWlanGwSoftGreXtDns2Addr,
        tmnxWlanGwSoftGreXtNb1AddrType,
        tmnxWlanGwSoftGreXtNb1Addr,
        tmnxWlanGwSoftGreXtNb2AddrType,
        tmnxWlanGwSoftGreXtNb2Addr,
        tmnxWlanGwSoftGreXtHttpRdrPlcy,
        tmnxWlanGwSoftGreXtNatPlcy,
        tmnxWlanGwVlanTableLastCh,
        tmnxWlanGwVlanLastCh,
        tmnxWlanGwVlanRowStatus,
        tmnxWlanGwVlanRetailService,
        tmnxWlanGwVlanDhcp,
        tmnxWlanGwVlanAddrType,
        tmnxWlanGwVlanAddr,
        tmnxWlanGwVlanLeaseTime,
        tmnxWlanGwVlanActLeaseTime,
        tmnxWlanGwVlanDns1AddrType,
        tmnxWlanGwVlanDns1Addr,
        tmnxWlanGwVlanDns2AddrType,
        tmnxWlanGwVlanDns2Addr,
        tmnxWlanGwVlanNb1AddrType,
        tmnxWlanGwVlanNb1Addr,
        tmnxWlanGwVlanNb2AddrType,
        tmnxWlanGwVlanNb2Addr,
        tmnxWlanGwVlanHttpRdrPlcy,
        tmnxWlanGwVlanNatPlcy,
        tmnxWlanGwVlanDataTrigg,
        tmnxWlanGwVlanAuthPlcy,
        tmnxWlanGwVlanAuthHoldTime,
        tmnxWlanGwVlanRadProxVrtr,
        tmnxWlanGwVlanRadProxSrv,
        tmnxWlanGwVlanRadProxMacFmt
    }
    STATUS      obsolete
    DESCRIPTION
        "The group of objects providing configuration of WLAN Gateway Soft GRE
         group interfaces on Nokia SROS series systems, added in release 11.0."
    ::= { tmnxWlanGwGroups 5 }

tmnxWlanGwMgwV11v0Group          OBJECT-GROUP
    OBJECTS     {
        tmnxWlanGwMgwArecCacheAddrType,
        tmnxWlanGwMgwArecCacheAddr,
        tmnxWlanGwMgwArecCacheTtl,
        tmnxWlanGwMgwSnaptrCachePref,
        tmnxWlanGwMgwSnaptrCacheService,
        tmnxWlanGwMgwSnaptrCacheNext,
        tmnxWlanGwMgwSnaptrCacheRepl,
        tmnxWlanGwMgwSnaptrCacheTtl,
        tmnxWlanGwMgwSrvCacheWeight,
        tmnxWlanGwMgwSrvCachePort,
        tmnxWlanGwMgwSrvCacheTarget,
        tmnxWlanGwMgwSrvCacheTtl
    }
    STATUS      current
    DESCRIPTION
        "The group of objects providing management of WLAN Gateway Mobile
         Gateways on Nokia SROS series systems, added in release 11.0."
    ::= { tmnxWlanGwGroups 6 }

tmnxWlanGwMgwQosIeGroup          OBJECT-GROUP
    OBJECTS     {
        tmnxWlanGwPgwLastChanged,
        tmnxWlanGwPgwQosUplinkGbrRate,
        tmnxWlanGwPgwQosUplinkMbrRate,
        tmnxWlanGwPgwQosDwnlinkGbrRate,
        tmnxWlanGwPgwQosDwnlinkMbrRate,
        tmnxWlanGwPgwQosArpValue,
        tmnxWlanGwPgwQosQciValue,
        tmnxWlanGwGgsnLastChanged,
        tmnxWlanGwGgsnQosUplinkGbrRate,
        tmnxWlanGwGgsnQosUplinkMbrRate,
        tmnxWlanGwGgsnQosDwnlinkGbrRate,
        tmnxWlanGwGgsnQosDwnlinkMbrRate,
        tmnxWlanGwGgsnQosArpValue,
        tmnxWlanGwPgwTableLastCh,
        tmnxWlanGwGgsnTableLastCh,
        tmnxWlanGwBcQosUlGbr,
        tmnxWlanGwBcQosUlMbr,
        tmnxWlanGwBcQosDlGbr,
        tmnxWlanGwBcQosDlMbr,
        tmnxWlanGwBcQosArp,
        tmnxWlanGwBcQosQci
    }
    STATUS      current
    DESCRIPTION
        "The group of objects providing management of WLAN Gateway Mobile
         Gateways QOS IE on Nokia SROS series systems."
    ::= { tmnxWlanGwGroups 10 }

tmnxWlanGwMgwChargingCharGroup   OBJECT-GROUP
    OBJECTS     {
        tmnxWlanGwMgwProfChrgCharHome,
        tmnxWlanGwMgwProfChrgCharRoam,
        tmnxWlanGwGtpSeChrgChar
    }
    STATUS      current
    DESCRIPTION
        "The group of objects providing management of WLAN Gateway Mobile
         Gateways Charging Characteristics on Nokia SROS series systems."
    ::= { tmnxWlanGwGroups 11 }

tmnxWlanGwMobilityGroup          OBJECT-GROUP
    OBJECTS     {
        tmnxWlanGwMobAcctInterimUpdate,
        tmnxWlanGwSoftGreIfMobArpAp,
        tmnxWlanGwSoftGreTuApMacAddress,
        tmnxWlanGwSoftGreTuApLearnFailed
    }
    STATUS      current
    DESCRIPTION
        "The group of objects providing management of WLAN Gateway UE Mobility
         on Nokia SROS series systems."
    ::= { tmnxWlanGwGroups 15 }

tmnxWlanGwMgwSeHoldTimeGroup     OBJECT-GROUP
    OBJECTS     {
        tmnxWlanGwMgwProfSeHoldTime,
        tmnxWlanGwSysCfgMgwMaxHeldSe,
        tmnxWlanGwMgwNumHeldSe
    }
    STATUS      current
    DESCRIPTION
        "The group of objects providing management of WLAN Gateway Mobile
         Gateways GTP session hold-timers on Nokia SROS series systems."
    ::= { tmnxWlanGwGroups 16 }

tmnxWlanGwV12v0Group             OBJECT-GROUP
    OBJECTS     {
        tmnxWlanGwGrpDegraded,
        tmnxWlanGwUeQTag,
        tmnxWlanGwUeMplsLabel,
        tmnxWlanGwUeTuRouter,
        tmnxWlanGwUeTuAddrType,
        tmnxWlanGwUeTuRemoteAddr,
        tmnxWlanGwUeTuLocalAddr,
        tmnxWlanGwUeTuQosRetailService,
        tmnxWlanGwUeSsid,
        tmnxWlanGwUePrevApAddrType,
        tmnxWlanGwUePrevApAddr,
        tmnxWlanGwUeLastMoveTime,
        tmnxWlanGwSsidNumUe,
        tmnxWlanGwNumSoftGreTu,
        tmnxWlanGwPeakNumSoftGreTu,
        tmnxWlanGwNumUe,
        tmnxWlanGwPeakNumUe,
        tmnxWlanGwMgwProfReportWlanLoc,
        tmnxWlanGwMgwProfProtocolCfgOpt,
        tmnxWlanGwUeService,
        tmnxWlanGwUeSapPortId,
        tmnxWlanGwUeSapPortEncapValue
    }
    STATUS      current
    DESCRIPTION
        "The group of objects providing configuration of WLAN Gateway added in
         release 12.0 of Nokia SROS series systems."
    ::= { tmnxWlanGwGroups 17 }

tmnxWlanGwSoftGreV12v0Group      OBJECT-GROUP
    OBJECTS     {
        tmnxWlanGwSoftGreIfLastCh,
        tmnxWlanGwSoftGreIfAdminState,
        tmnxWlanGwSoftGreIfRouter,
        tmnxWlanGwSoftGreIfGwAddrType,
        tmnxWlanGwSoftGreIfGwAddr,
        tmnxWlanGwSoftGreIfGrpId,
        tmnxWlanGwSoftGreIfShapingType,
        tmnxWlanGwSoftGreIfShapeMultiUe,
        tmnxWlanGwSoftGreIfEQosPlcy,
        tmnxWlanGwSoftGreIfESchedPlcy,
        tmnxWlanGwSoftGreIfEAggRateLimit,
        tmnxWlanGwSoftGreIfMobTrigger,
        tmnxWlanGwSoftGreIfMobHoldTime,
        tmnxWlanGwSoftGreIfDefRetailSvc,
        tmnxWlanGwSoftGreIfTcpMssAdjust,
        tmnxWlanGwSoftGreIfEHoldTime,
        tmnxWlanGwSoftGreIfNumSoftGreTu,
        tmnxWlanGwSoftGreIfTableLastCh,
        tmnxWlanGwSoftGreTuEstabTime,
        tmnxWlanGwSoftGreTuIsaGroup,
        tmnxWlanGwSoftGreTuIsaMember,
        tmnxWlanGwSoftGreTuNumUe,
        tmnxWlanGwTuQosEegSvcId,
        tmnxWlanGwTuQosEegPortId,
        tmnxWlanGwTuQosEegEncapValue,
        tmnxWlanGwTuQosEegName,
        tmnxWlanGwTuQosEegMember,
        tmnxWlanGwTuQosState,
        tmnxWlanGwTuQosNumUe,
        tmnxWlanGwTuQosRemainingHoldTime,
        tmnxWlanGwSoftGreTuUeSsid,
        tmnxWlanGwSoftGreIfGwV6AddrType,
        tmnxWlanGwSoftGreIfGwV6Addr,
        tmnxWlanGwVlanTableLastCh,
        tmnxWlanGwVlanLastCh,
        tmnxWlanGwVlanRowStatus,
        tmnxWlanGwVlanRetailService,
        tmnxWlanGwVlanDhcp,
        tmnxWlanGwVlanAddrType,
        tmnxWlanGwVlanAddr,
        tmnxWlanGwVlanLeaseTime,
        tmnxWlanGwVlanActLeaseTime,
        tmnxWlanGwVlanDns1AddrType,
        tmnxWlanGwVlanDns1Addr,
        tmnxWlanGwVlanDns2AddrType,
        tmnxWlanGwVlanDns2Addr,
        tmnxWlanGwVlanNb1AddrType,
        tmnxWlanGwVlanNb1Addr,
        tmnxWlanGwVlanNb2AddrType,
        tmnxWlanGwVlanNb2Addr,
        tmnxWlanGwVlanHttpRdrPlcy,
        tmnxWlanGwVlanNatPlcy,
        tmnxWlanGwVlanDataTrigg,
        tmnxWlanGwVlanAuthPlcy,
        tmnxWlanGwVlanAuthHoldTime,
        tmnxWlanGwVlanRadProxVrtr,
        tmnxWlanGwVlanRadProxSrv,
        tmnxWlanGwVlanRadProxMacFmt,
        tmnxWlanGwSoftGreIfDownIfGrpDeg
    }
    STATUS      obsolete
    DESCRIPTION
        "The group of objects providing configuration of WLAN Gateway Soft GRE
         group interfaces on Nokia SROS series systems, supported in release
         12.0."
    ::= { tmnxWlanGwGroups 18 }

tmnxWlanGwRedGroup               OBJECT-GROUP
    OBJECTS     {
        tmnxWlanGwSubIfTableLastCh,
        tmnxWlanGwSubIfRowStatus,
        tmnxWlanGwSubIfLastCh,
        tmnxWlanGwSubIfRedExpPrefixType,
        tmnxWlanGwSubIfRedExpPrefix,
        tmnxWlanGwSubIfRedExpPrefixLen,
        tmnxWlanGwSubIfRedMonPrefixType,
        tmnxWlanGwSubIfRedMonPrefix,
        tmnxWlanGwSubIfRedMonPrefixLen,
        tmnxWlanGwSubIfRedAdminState,
        tmnxWlanGwSubIfRedActive,
        tmnxWlanGwSubIfRedSwitch
    }
    STATUS      current
    DESCRIPTION
        "The group of objects providing configuration of WLAN Gateway
         redundancy on Nokia SROS series systems."
    ::= { tmnxWlanGwGroups 19 }

tmnxWlanGwDsmGroup               OBJECT-GROUP
    OBJECTS     {
        tmnxWlanGwGrpIsaAaGroup,
        tmnxWlanGwVlanAuthOnDhcp,
        tmnxWlanGwVlanDsmLastCh,
        tmnxWlanGwVlanDsmAdminState,
        tmnxWlanGwVlanDsmAcctPlcy,
        tmnxWlanGwVlanDsmEgressPolicer,
        tmnxWlanGwVlanDsmIngressPolicer,
        tmnxWlanGwVlanDsmIpFilter,
        tmnxWlanGwVlanDsmOneTimeRdrUrl,
        tmnxWlanGwVlanDsmOneTimeRdrPort,
        tmnxWlanGwVlanDsmAcctUpdInterv,
        tmnxWlanGwVlanDsmDefAppProfile,
        tmnxWlanGwVlanDsmTableLastCh,
        tmnxWlanGwDsmIpFilTableLastCh,
        tmnxWlanGwDsmIpFilRowStatus,
        tmnxWlanGwDsmIpFilLastCh,
        tmnxWlanGwDsmIpFilDescription,
        tmnxWlanGwDsmIpFilDefaultAction,
        tmnxWlanGwDsmIpFilDefaultAction6,
        tmnxWlanGwDsmIpFilN3TableLastCh,
        tmnxWlanGwDsmIpFilN3RowStatus,
        tmnxWlanGwDsmIpFilN3LastCh,
        tmnxWlanGwDsmIpFilN3Description,
        tmnxWlanGwDsmIpFilN3Action,
        tmnxWlanGwDsmIpFilN3Protocol,
        tmnxWlanGwDsmIpFilN3DestAddrType,
        tmnxWlanGwDsmIpFilN3DestAddr,
        tmnxWlanGwDsmIpFilN3DestPrefLen,
        tmnxWlanGwDsmIpFilN3DestPortOp,
        tmnxWlanGwDsmIpFilN3DestPort1,
        tmnxWlanGwDsmIpFil6N3TableLastCh,
        tmnxWlanGwDsmIpFil6N3RowStatus,
        tmnxWlanGwDsmIpFil6N3LastCh,
        tmnxWlanGwDsmIpFil6N3Description,
        tmnxWlanGwDsmIpFil6N3Action,
        tmnxWlanGwDsmIpFil6N3Protocol,
        tmnxWlanGwDsmIpFil6N3DestAddrTyp,
        tmnxWlanGwDsmIpFil6N3DestAddr,
        tmnxWlanGwDsmIpFil6N3DestPrefLen,
        tmnxWlanGwDsmIpFil6N3DestPortOp,
        tmnxWlanGwDsmIpFil6N3DestPort1,
        tmnxWlanGwDsmTableLastCh,
        tmnxWlanGwDsmLastCh,
        tmnxWlanGwDsmIpv6TcpMssAdjust,
        tmnxWlanGwPolicerRowLastChange,
        tmnxWlanGwPolicerRowStatus,
        tmnxWlanGwPolicerDescription,
        tmnxWlanGwPolicerType,
        tmnxWlanGwPolicerAction,
        tmnxWlanGwPolicerAdminPIR,
        tmnxWlanGwPolicerAdminCIR,
        tmnxWlanGwPolicerMBS,
        tmnxWlanGwPolicerCBS,
        tmnxWlanGwPolicerPIRAdaptation,
        tmnxWlanGwPolicerCIRAdaptation,
        tmnxWlanGwPolicerTableLastCh
    }
    STATUS      current
    DESCRIPTION
        "The group of objects providing configuration of WLAN Gateway
         Distributed subscriber management on Nokia SROS series systems."
    ::= { tmnxWlanGwGroups 20 }

tmnxWlanGwUeQryGroup             OBJECT-GROUP
    OBJECTS     {
        tmnxWlanGwUeNextQryId,
        tmnxWlanGwUeMaxQryId,
        tmnxWlanGwUeQryRowStatus,
        tmnxWlanGwUeQryWhereState,
        tmnxWlanGwUeQryWhereMacAddress,
        tmnxWlanGwUeQryWhereAddrType,
        tmnxWlanGwUeQryWhereAddr,
        tmnxWlanGwUeQryWhereIsaGrp,
        tmnxWlanGwUeQryWhereMemberId,
        tmnxWlanGwUeQryWhereQTag,
        tmnxWlanGwUeQryWhereTuRouter,
        tmnxWlanGwUeQryWhereTuRemAddrTyp,
        tmnxWlanGwUeQryWhereTuRemAddr,
        tmnxWlanGwUeQryWhereTuLocAddrTyp,
        tmnxWlanGwUeQryWhereTuLocAddr,
        tmnxWlanGwUeQryWhereEncap,
        tmnxWlanGwUeQryWhereSlaacPrefTyp,
        tmnxWlanGwUeQryWhereSlaacPref,
        tmnxWlanGwUeQryWhereDhcp6AddrTyp,
        tmnxWlanGwUeQryWhereDhcp6Addr,
        tmnxWlanGwUeQryNumResults,
        tmnxWlanGwUeResMacAddress,
        tmnxWlanGwUeResAddrType,
        tmnxWlanGwUeResAddr,
        tmnxWlanGwUeResState,
        tmnxWlanGwUeResIsaGrp,
        tmnxWlanGwUeResIsaMemberId,
        tmnxWlanGwUeResQTag,
        tmnxWlanGwUeResTuRouter,
        tmnxWlanGwUeResTuAddrType,
        tmnxWlanGwUeResTuLocalAddr,
        tmnxWlanGwUeResEncapsulation,
        tmnxWlanGwUeResTuRemoteAddr,
        tmnxWlanGwUeResSsid,
        tmnxWlanGwUeResApMacAddress,
        tmnxWlanGwUeResMplsLabel,
        tmnxWlanGwUeResLastMoveTime,
        tmnxWlanGwUeResExpirationTime,
        tmnxWlanGwUeResIdleTimeout,
        tmnxWlanGwUeResSessionTimeout,
        tmnxWlanGwUeResNatPlcy,
        tmnxWlanGwUeResHttpRdrPlcy,
        tmnxWlanGwUeResDsmIpFilter,
        tmnxWlanGwUeResDsmAcctPlcy,
        tmnxWlanGwUeResDsmAcctUpdInterv,
        tmnxWlanGwUeResAcctUpdate,
        tmnxWlanGwUeResIngOperPir,
        tmnxWlanGwUeResIngOperCir,
        tmnxWlanGwUeResEgrOperPir,
        tmnxWlanGwUeResEgrOperCir,
        tmnxWlanGwUeResDsmAppProfile,
        tmnxWlanGwUeResRxPkts,
        tmnxWlanGwUeResRxOctets,
        tmnxWlanGwUeResTxPkts,
        tmnxWlanGwUeResTxOctets,
        tmnxWlanGwUeResSlaacAddrType,
        tmnxWlanGwUeResSlaacPref,
        tmnxWlanGwUeResSlaacAddr1,
        tmnxWlanGwUeResSlaacAddr2,
        tmnxWlanGwUeResSlaacAddr3,
        tmnxWlanGwUeResDhcp6AddrType,
        tmnxWlanGwUeResDhcp6Addr,
        tmnxWlanGwUeResDhcp6AddrDepr,
        tmnxWlanGwUeResDhcp6IAID,
        tmnxWlanGwUeResDhcp6IAIDValid,
        tmnxWlanGwUeResSlaacLeaseExpire,
        tmnxWlanGwUeResDhcp6LeaseExpire,
        tmnxWlanGwUeResDhcpAddrDepr
    }
    STATUS      current
    DESCRIPTION
        "The group of objects providing queries for User Equipment on Nokia
         SROS series systems."
    ::= { tmnxWlanGwGroups 23 }

tmnxWlanGwDsmV13v0Group          OBJECT-GROUP
    OBJECTS     {
        tmnxWlanGwVlanL2Service,
        tmnxWlanGwVlanL2AdminState,
        tmnxWlanGwVlanL2Description,
        tmnxWlanGwVplsAdminState,
        tmnxWlanGwVplsDescription,
        tmnxWlanGwVplsSapTemplate,
        tmnxWlanGwVplsTableLastCh,
        tmnxWlanGwVplsLastMgmtChange,
        tmnxWlanGwPdnType,
        tmnxWlanGwSubIfPmTableLastCh,
        tmnxWlanGwSubIfPmLastChanged,
        tmnxWlanGwSubIfPmWatermarkHigh,
        tmnxWlanGwSubIfPmWatermarkLow,
        tmnxWlanGwSubIfPmWlanGwGroup,
        tmnxWlanGwSubIfPmD6cServer1,
        tmnxWlanGwSubIfPmD6cServer2,
        tmnxWlanGwSubIfPmD6cServer3,
        tmnxWlanGwSubIfPmD6cServer4,
        tmnxWlanGwSubIfPmD6cServer5,
        tmnxWlanGwSubIfPmD6cServer6,
        tmnxWlanGwSubIfPmD6cServer7,
        tmnxWlanGwSubIfPmD6cServer8,
        tmnxWlanGwSubIfPmD6cLeaseQuery,
        tmnxWlanGwSubIfPmD6cLeaseQueryMR,
        tmnxWlanGwSubIfPmD6cSourceIp,
        tmnxWlanGwSubIfPmD6cSlaacPoolNm,
        tmnxWlanGwSubIfPmD6cSlaacLinkAdd,
        tmnxWlanGwSubIfPmD6cSlaacAdminSt,
        tmnxWlanGwSubIfPmD6cIaNaPoolNm,
        tmnxWlanGwSubIfPmD6cIaNaLinkAdd,
        tmnxWlanGwSubIfPmD6cIaNaAdminSt,
        tmnxWlanGwSubIfIpsSubIfIndex,
        tmnxWlanGwSubIfIpsSubnetAddrType,
        tmnxWlanGwSubIfIpsSubnetAddr,
        tmnxWlanGwSubIfIpsSubnetPrefLen,
        tmnxWlanGwSubIfIpsAddrFamily,
        tmnxWlanGwSubIfIpsPoolIsOld,
        tmnxWlanGwSubIfIpsUsageLevelPct,
        tmnxWlanGwSubIfIpsDHCPv6Options,
        tmnxWlanGwSubIfIpsRemLeaseTime,
        tmnxWlanGwSubIfIpsIsaGrpId,
        tmnxWlanGwSubIfIpsIsaMemberId,
        tmnxWlanGwSubIfIpsServiceId,
        tmnxWlanGwVlanDhcp6TableLastCh,
        tmnxWlanGwVlanDhcp6LastChanged,
        tmnxWlanGwVlanDhcp6InitPrefLt,
        tmnxWlanGwVlanDhcp6ActPrefLt,
        tmnxWlanGwVlanDhcp6InitValidLt,
        tmnxWlanGwVlanDhcp6ActValidLt,
        tmnxWlanGwVlanDhcp6AdminState,
        tmnxWlanGwVlanSlaacTableLastCh,
        tmnxWlanGwVlanSlaacLastChanged,
        tmnxWlanGwVlanSlaacInitPrefLt,
        tmnxWlanGwVlanSlaacActPrefLt,
        tmnxWlanGwVlanSlaacInitValidLt,
        tmnxWlanGwVlanSlaacActValidLt,
        tmnxWlanGwVlanSlaacAdminState,
        tmnxWlanGwSysCfgVirtChassisId,
        tmnxWlanGwVlanIdleTimeoutAction
    }
    STATUS      current
    DESCRIPTION
        "The group of objects providing configuration of WLAN Gateway
         Distributed subscriber management on Nokia SROS series systems, added
         in release 13.0."
    ::= { tmnxWlanGwGroups 25 }

tmnxWlanGwL2ApGroup              OBJECT-GROUP
    OBJECTS     {
        tmnxWlanGwSoftGreIfL2ApEncapType,
        tmnxWlanGwSoftGreIfL2ApAutoSubId,
        tmnxWlanGwSoftGreTuEncap,
        tmnxWlanGwSoftGreTuEncapTag1,
        tmnxWlanGwSoftGreTuEncapTag2,
        tmnxWlanGwSoftGreTuService,
        tmnxWlanGwSoftGreTuInterface,
        tmnxWlanGwSoftGreTuApSapEncapVal,
        tmnxWlanGwSoftGreTuApSapPortId,
        tmnxWlanGwUeEncapsulation,
        tmnxWlanGwL2ApRowStatus,
        tmnxWlanGwL2ApLastCh,
        tmnxWlanGwL2ApAdminState,
        tmnxWlanGwL2ApEncapType,
        tmnxWlanGwL2ApEpipeSapTemplate,
        tmnxWlanGwL2ApId,
        tmnxWlanGwL2ApTableLastCh
    }
    STATUS      current
    DESCRIPTION
        "The group of objects providing configuration of WLAN Gateway Layer 2
         Access Points on Nokia SROS series systems."
    ::= { tmnxWlanGwGroups 26 }

tmnxWlanGwL2tpv3Group            OBJECT-GROUP
    OBJECTS     {
        tmnxWlanGwSoftGreIfMultiTuType,
        tmnxWlanGwSoftGreIfL2tpLrnCookie,
        tmnxWlanGwSoftGreIfL2tpCookie
    }
    STATUS      current
    DESCRIPTION
        "The group of objects providing configuration of L2TP tunnel
         connections with Access Points on Nokia SROS series systems."
    ::= { tmnxWlanGwGroups 27 }

tmnxWlanGwV14v0Group             OBJECT-GROUP
    OBJECTS     {
        tmnxWlanGwMgwProfPythonPolicy,
        tmnxWlanGwMgwProfRatType,
        tmnxWlanGwVlanBrgLastChanged,
        tmnxWlanGwVlanBrgAdminState,
        tmnxWlanGwVlanBrgDefBrgProfile,
        tmnxWlanGwVlanBrgAuthedBrgOnly,
        tmnxWlanGwVlanBrgTableLastCh,
        tmnxWlanGwVlanDsmAaAcctStats,
        tmnxWlanGwVlanAddrFromPool,
        tmnxWlanGwTuQosOvrPIR,
        tmnxWlanGwTuQosOvrCIR,
        tmnxWlanGwTuQosOvrAggRateLimit,
        tmnxWlanGwSoftGreIfLearnApMac,
        tmnxWlanGwSoftGreIfLearnApMacDA,
        tmnxWlanGwVlanAuthVlanMismatchTo,
        tmnxWlanGwSubIfIpsIpv4Addr,
        tmnxWlanGwSubIfIpsIpv4PrefLen,
        tmnxWlanGwSubIfIpsIpv4DefGwAddr,
        tmnxWlanGwSubIfIpsDnsServer1,
        tmnxWlanGwSubIfIpsDnsServer2
    }
    STATUS      current
    DESCRIPTION
        "The group of objects providing configuration of WLAN Gateway added in
         release 14.0 of Nokia SROS series systems."
    ::= { tmnxWlanGwGroups 28 }

tmnxWlanGwMgwAmbrIeGroup         OBJECT-GROUP
    OBJECTS     {
        tmnxWlanGwPgwQosUplinkAmbr,
        tmnxWlanGwPgwQosDwnlinkAmbr,
        tmnxWlanGwGgsnQosUplinkAmbr,
        tmnxWlanGwGgsnQosDwnlinkAmbr,
        tmnxWlanGwGtpSeQosUplinkAmbr,
        tmnxWlanGwGtpSeQosDwnlinkAmbr
    }
    STATUS      current
    DESCRIPTION
        "The group of objects providing management of WLAN Gateway Mobile
         Gateways AMBR IE on Nokia SROS series systems."
    ::= { tmnxWlanGwGroups 29 }

tmnxWlanGwVsrGroup               OBJECT-GROUP
    OBJECTS     {
        tmnxWlanGwIomApplication
    }
    STATUS      current
    DESCRIPTION
        "The group of objects providing management of the WLAN Gateway function
         in a virtual implementation."
    ::= { tmnxWlanGwGroups 30 }

tmnxWlanGwDsmV14v0Group          OBJECT-GROUP
    OBJECTS     {
        tmnxWlanGwSubIfPmD6cD4natPoolNm,
        tmnxWlanGwSubIfPmD6cD4natLinkAdd,
        tmnxWlanGwSubIfPmD6cD4natAdminSt
    }
    STATUS      current
    DESCRIPTION
        "The group of objects providing configuration of WLAN Gateway
         Distributed subscriber management on Nokia SROS series systems, added
         in release 14.0."
    ::= { tmnxWlanGwGroups 32 }

tmnxWlanGwMdaRedundancyGroup     OBJECT-GROUP
    OBJECTS     {
        tmnxWlanGwGrpRedundancyUnit,
        tmnxWlanGwGrpActiveMdaLimit,
        tmnxWlanGwMdaLastMgmtChange,
        tmnxWlanGwMdaRowStatus,
        tmnxWlanGwMdaTableLastCh
    }
    STATUS      current
    DESCRIPTION
        "The group of objects providing management of the WLAN Gateway function
         in a virtual implementation."
    ::= { tmnxWlanGwGroups 33 }

tmnxWlanGwInterVlanMobGroup      OBJECT-GROUP
    OBJECTS     {
        tmnxWlanGwSoftGreIfMobInterVlan
    }
    STATUS      current
    DESCRIPTION
        "The group of objects providing management of WLAN Gateway Mobile
         Gateways inter-VLAN mobility on Nokia SROS series systems."
    ::= { tmnxWlanGwGroups 34 }

tmnxWlanGwTunnelQueryGroup       OBJECT-GROUP
    OBJECTS     {
        tmnxWlanGwTuNextQryId,
        tmnxWlanGwTuMaxQryId,
        tmnxWlanGwTuQryRowStatus,
        tmnxWlanGwTuQryWhereTuRouter,
        tmnxWlanGwTuQryWhereRemAddrType,
        tmnxWlanGwTuQryWhereRemAddr,
        tmnxWlanGwTuQryWhereLocAddrType,
        tmnxWlanGwTuQryWhereLocAddr,
        tmnxWlanGwTuQryWhereAddrFamily,
        tmnxWlanGwTuQryWhereEncap,
        tmnxWlanGwTuQryWhereEncapTag1,
        tmnxWlanGwTuQryWhereEncapTag2,
        tmnxWlanGwTuQryWhereApSapPortId,
        tmnxWlanGwTuQryWhereApSapEncap,
        tmnxWlanGwTuQryWhereNumUeMin,
        tmnxWlanGwTuQryWhereNumUeMax,
        tmnxWlanGwTuQryWhereApLearnFail,
        tmnxWlanGwTuQryWhereUeType,
        tmnxWlanGwTuQryDoGetNumResults,
        tmnxWlanGwTuQryNumResults,
        tmnxWlanGwTuFirstMoveTime,
        tmnxWlanGwTuIsaGroup,
        tmnxWlanGwTuIsaMember,
        tmnxWlanGwTuService,
        tmnxWlanGwTuInterface,
        tmnxWlanGwTuApMacAddress,
        tmnxWlanGwTuApLearnFailed,
        tmnxWlanGwTuEncapTag1,
        tmnxWlanGwTuEncapTag2,
        tmnxWlanGwTuApSapPortId,
        tmnxWlanGwTuApSapEncapVal,
        tmnxWlanGwTuRemoteUdpPort,
        tmnxWlanGwTuNumUe,
        tmnxWlanGwTuNumUeMigrant,
        tmnxWlanGwTuNumUeDsm,
        tmnxWlanGwTuNumUeL2w,
        tmnxWlanGwTuNumUeEsm,
        tmnxWlanGwTuNumUeXcon
    }
    STATUS      current
    DESCRIPTION
        "The group of objects providing queries for tunnels connected to WLAN
         Gateway Access Points on Nokia SROS series systems."
    ::= { tmnxWlanGwGroups 35 }

tmnxWlanGwHomeUeGroup            OBJECT-GROUP
    OBJECTS     {
        tmnxWlanGwUeQryWhereBridgeId,
        tmnxWlanGwUeResBridgeId,
        tmnxWlanGwBdUeQTag,
        tmnxWlanGwBdUeMplsLabel,
        tmnxWlanGwBdUeTuRouter,
        tmnxWlanGwBdUeTuAddrType,
        tmnxWlanGwBdUeTuRemoteAddr,
        tmnxWlanGwBdUeTuLocalAddr,
        tmnxWlanGwBdUeTuQosRetailService,
        tmnxWlanGwBdUeSsid,
        tmnxWlanGwBdUePrevApAddrType,
        tmnxWlanGwBdUePrevApAddr,
        tmnxWlanGwBdUeLastMoveTime,
        tmnxWlanGwBdUeImsi,
        tmnxWlanGwBdUeService,
        tmnxWlanGwBdUeSapPortId,
        tmnxWlanGwBdUeSapPortEncapValue,
        tmnxWlanGwBdUeEncapsulation
    }
    STATUS      current
    DESCRIPTION
        "The group of objects providing home-aware monitoring of User Equipment
         on Nokia SROS series systems."
    ::= { tmnxWlanGwGroups 36 }

tmnxWlanGwXconnectGroup          OBJECT-GROUP
    OBJECTS     {
        tmnxWlanGwXcnctLastCh,
        tmnxWlanGwXcnctIsaGroup,
        tmnxWlanGwXcnctTnlSrcIpAddrType,
        tmnxWlanGwXcnctTnlSrcIpAddr,
        tmnxWlanGwXcnctTnlSrcIpPrefixLen,
        tmnxWlanGwXcnctAdminState,
        tmnxWlanGwXcnctTableLastCh,
        tmnxWlanGwVlanXcnctAccPolicy,
        tmnxWlanGwVlanXcnctLastChanged,
        tmnxWlanGwVlanXcnctAdminState,
        tmnxWlanGwVlanXcnctTableLastCh,
        tmnxWlanGwVlanXcnctAcctUpdInterv,
        tmnxWlanGwVlanXcnctMobAcctUpd
    }
    STATUS      current
    DESCRIPTION
        "The group of objects providing cross-connect inter WLAN-GW mobility
         via anchoring on Home-GW on Nokia SROS series systems."
    ::= { tmnxWlanGwGroups 37 }

tmnxWlanGwMobilityV15v0Group     OBJECT-GROUP
    OBJECTS     {
        tmnxWlanGwMobAcctIntUpdtInclCnts,
        tmnxWlanGwMobAcctIntUpdtHoldDown
    }
    STATUS      current
    DESCRIPTION
        "The group of objects providing management of WLAN Gateway UE Mobility
         on Nokia SROS series systems."
    ::= { tmnxWlanGwGroups 38 }

tmnxWlanGwLeV15v0Group           OBJECT-GROUP
    OBJECTS     {
        tmnxWlanGwLeRowStatus,
        tmnxWlanGwLeLastChanged,
        tmnxWlanGwLeAdminState,
        tmnxWlanGwLeWlanGwGrpId,
        tmnxWlanGwLeVtepStartType,
        tmnxWlanGwLeVtepStart,
        tmnxWlanGwLeVtepEndType,
        tmnxWlanGwLeVtepEnd,
        tmnxWlanGwLeVxlanPort,
        tmnxWlanGwBdVNI,
        tmnxWlanGwBdRT,
        tmnxWlanGwBdRD,
        tmnxWlanGwBdWlanGwGrpId,
        tmnxWlanGwBdIsaMemberId,
        tmnxWlanGwSoftGreIfMaxLanextBd,
        tmnxWlanGwVlanLeTableLastCh,
        tmnxWlanGwVlanLeLastChanged,
        tmnxWlanGwVlanLeAdminState,
        tmnxWlanGwVlanLeMacTranslation,
        tmnxWlanGwVlanLeBdMacPrefix,
        tmnxWlanGwVlanLeBdMacPrefixLen,
        tmnxWlanGwVlanLeAssistAddrRes,
        tmnxWlanGwVlanLeNetwPolicer,
        tmnxWlanGwVlanLeNetwMaxMac,
        tmnxWlanGwVlanLeNetwAdminState,
        tmnxWlanGwVlanLeAccsPolicer,
        tmnxWlanGwVlanLeAccsMaxMac,
        tmnxWlanGwTuBdUeSsid,
        tmnxWlanGwVlanLeAccsMultiAccess,
        tmnxWlanGwBdVlanTag,
        tmnxWlanGwBdService,
        tmnxWlanGwBdInterface,
        tmnxWlanGwBdMacTranslation,
        tmnxWlanGwBdBdMac,
        tmnxWlanGwBdAssistAddrRes,
        tmnxWlanGwBdNetwMaxMac,
        tmnxWlanGwBdNetwAdminState,
        tmnxWlanGwBdAccsMaxMac
    }
    STATUS      current
    DESCRIPTION
        "The group of objects providing management of WLAN Gateway  home LAN
         Extension on Nokia SROS series systems in release 15.0."
    ::= { tmnxWlanGwGroups 39 }

tmnxWlanGwDsmV15v0Group          OBJECT-GROUP
    OBJECTS     {
        tmnxWlanGwDsmIpFilType
    }
    STATUS      current
    DESCRIPTION
        "The group of objects providing configuration of WLAN Gateway
         Distributed subscriber management on Nokia SROS release 15.0  series
         systems."
    ::= { tmnxWlanGwGroups 40 }

tmnxWlanGwIsaV16v0Group          OBJECT-GROUP
    OBJECTS     {
        tmnxWlanGwIsaStatsName,
        tmnxWlanGwIsaStatsValue,
        tmnxWlanGwGrpWmLastMgmtChange,
        tmnxWlanGwGrpWmRowStatus,
        tmnxWlanGwGrpWmHi,
        tmnxWlanGwGrpWmLo,
        tmnxWlanGwGrpIsaAaOversub,
        tmnxWlanGwIsaResrcStatsName,
        tmnxWlanGwIsaResrcStatsMaxValue,
        tmnxWlanGwIsaResrcStatsValue,
        tmnxWlanGwIsaResrcStatsPeakValue,
        tmnxWlanGwIsaResrcStatsPeakTime
    }
    STATUS      obsolete
    DESCRIPTION
        "The group of objects providing configuration of WLAN Gateway ISA
         groups on Nokia SROS series systems added in release 16.0."
    ::= { tmnxWlanGwGroups 41 }

tmnxWlanGwIsaScalingGroup        OBJECT-GROUP
    OBJECTS     {
        tmnxWlanGwGrpScalingProfile
    }
    STATUS      current
    DESCRIPTION
        "The group of objects providing configuration of WLAN Gateway  ISA
         scaling profiles on Nokia SROS series systems."
    ::= { tmnxWlanGwGroups 42 }

tmnxWlanGwUeQryV16v0Group        OBJECT-GROUP
    OBJECTS     {
        tmnxWlanGwUeQryWhereAddrFamily,
        tmnxWlanGwUeResAddrFamily
    }
    STATUS      current
    DESCRIPTION
        "The group of objects providing queries for User Equipment on Nokia
         SROS release 16.0 series systems."
    ::= { tmnxWlanGwGroups 43 }

tmnxWlanGwGrpIfGwAddrV16v0Group  OBJECT-GROUP
    OBJECTS     {
        tmnxWlanGwGrpIfGwAddrRowStatus,
        tmnxWlanGwGrpIfGwAddrTableLastCh,
        tmnxWlanGwGrpIfGwAddrPurpose
    }
    STATUS      current
    DESCRIPTION
        "The group of objects providing queries for Group Interface Gateway
         Addresses on Nokia SROS release 16.0 series systems."
    ::= { tmnxWlanGwGroups 44 }

tmnxWlanGwLePolicerV16v0Group    OBJECT-GROUP
    OBJECTS     {
        tmnxWlanGwBdAccsPolicer,
        tmnxWlanGwBdNetwPolicer
    }
    STATUS      current
    DESCRIPTION
        "The group of objects providing management of WLAN Gateway home LAN
         Extension policers on Nokia SROS series systems in release 16.0."
    ::= { tmnxWlanGwGroups 46 }

tmnxWlanGwQryNameGroup           OBJECT-GROUP
    OBJECTS     {
        tmnxWlanGwUeQryName,
        tmnxWlanGwTuQryName,
        tmnxWlanGwTuQryVolatile
    }
    STATUS      current
    DESCRIPTION
        "The group of objects providing names for queries on Nokia SROS release
         16.0 series systems."
    ::= { tmnxWlanGwGroups 48 }

tmnxWlanGwIsaV19v0Group          OBJECT-GROUP
    OBJECTS     {
        tmnxWlanGwGrpTableLastCh,
        tmnxWlanGwGrpRowStatus,
        tmnxWlanGwGrpLastMgmtChange,
        tmnxWlanGwGrpDescription,
        tmnxWlanGwGrpAdminState,
        tmnxWlanGwGrpActiveIomLimit,
        tmnxWlanGwGrpPortPlcy,
        tmnxWlanGwGrpTunnelPortPlcy,
        tmnxWlanGwGrpOperState,
        tmnxWlanGwIomTableLastCh,
        tmnxWlanGwIomRowStatus,
        tmnxWlanGwIomLastMgmtChange,
        tmnxWlanGwIomOperState,
        tmnxWlanGwIsaMemberChassisIndex,
        tmnxWlanGwIsaMemberCardSlotNum,
        tmnxWlanGwIsaMemberSlotNum,
        tmnxWlanGwIsaMemberNumSoftGreTu,
        tmnxWlanGwIsaMemberNumUe,
        tmnxWlanGwIsaMemberEegMemberAct,
        tmnxWlanGwIsaMemberEegMemberPend,
        tmnxWlanGwIsaMemberTuQosProblem,
        tmnxWlanGwResrcProblem,
        tmnxWlanGwIsaStatsName,
        tmnxWlanGwIsaStatsValue,
        tmnxWlanGwGrpWmLastMgmtChange,
        tmnxWlanGwGrpWmRowStatus,
        tmnxWlanGwGrpWmHi,
        tmnxWlanGwGrpWmLo,
        tmnxWlanGwGrpIsaAaOversub,
        tmnxWlanGwIsaResrcStatsName,
        tmnxWlanGwIsaResrcStatsMaxValue,
        tmnxWlanGwIsaResrcStatsValue,
        tmnxWlanGwIsaResrcStatsPeakValue,
        tmnxWlanGwIsaResrcStatsPeakTime
    }
    STATUS      current
    DESCRIPTION
        "The group of objects providing configuration of WLAN Gateway ISA
         groups on Nokia SROS series systems."
    ::= { tmnxWlanGwGroups 49 }

tmnxWlanGwDsmV19v0Group          OBJECT-GROUP
    OBJECTS     {
        tmnxWlanGwDsmIpFilN3IngHitCount,
        tmnxWlanGwDsmIpFilN3RedirectURL,
        tmnxWlanGwDsmIpFil6N3IngHitCount,
        tmnxWlanGwDsmIpFil6N3RedirectURL
    }
    STATUS      current
    DESCRIPTION
        "The group of objects providing configuration of WLAN Gateway
         Distributed subscriber management on Nokia SROS release 19.0  series
         systems."
    ::= { tmnxWlanGwGroups 50 }

tmnxWlanGwEsaV19v0Group          OBJECT-GROUP
    OBJECTS     {
        tmnxWlanGwVappLastMgmtChange,
        tmnxWlanGwVappRowStatus,
        tmnxWlanGwVappTableLastCh,
        tmnxWlanGwIsaMemberEsaNum,
        tmnxWlanGwIsaMemberEsaVappNum
    }
    STATUS      current
    DESCRIPTION
        "The group of objects providing configuration of WLAN Gateway
         Distributed subscriber management on Nokia SROS release 19.0  series
         systems."
    ::= { tmnxWlanGwGroups 51 }

tmnxWlanGwDataTriggUeGroup       OBJECT-GROUP
    OBJECTS     {
        tmnxWlanGwVlanDataTriggArp
    }
    STATUS      current
    DESCRIPTION
        "The group of objects providing configuration of WLAN Gateway
         data-triggered authentication of User Equipment on Nokia SROS series
         systems."
    ::= { tmnxWlanGwGroups 52 }

tmnxWlanGwVlanExtV21v0Group      OBJECT-GROUP
    OBJECTS     {
        tmnxWlanGwVlanExtRowStatus,
        tmnxWlanGwVlanExtTableLastCh
    }
    STATUS      current
    DESCRIPTION
        "The group of objects providing configuration of WLAN Gateway VLAN
         extensions on Nokia SROS release 21.0 series systems."
    ::= { tmnxWlanGwGroups 53 }

tmnxWlanGwDsmV21v0Group          OBJECT-GROUP
    OBJECTS     {
        tmnxWlanGwVlanDsmQuotaDirection,
        tmnxWlanGwVlanDsmQuotaExhFilter,
        tmnxWlanGwUeQryWhereSoftQuotaExh,
        tmnxWlanGwUeResHardQuotaOctets,
        tmnxWlanGwUeResSoftQuotaOctets
    }
    STATUS      current
    DESCRIPTION
        "The group of objects providing configuration of WLAN Gateway
         Distributed subscriber management on Nokia SROS release 21.0  series
         systems."
    ::= { tmnxWlanGwGroups 54 }

tmnxWlanGwRadiusLessAuthGroup    OBJECT-GROUP
    OBJECTS     {
        tmnxWlanGwVlanLocAuthDefUeState,
        tmnxWlanGwVlanLocAuthCoAPlcy
    }
    STATUS      current
    DESCRIPTION
        "The group of objects providing configuration of WLAN Gateway
         RADIUS-less authentication of User Equipment on Nokia SROS  series
         systems."
    ::= { tmnxWlanGwGroups 55 }

tmnxWlanGwRadiusLessAuthAaGroup  OBJECT-GROUP
    OBJECTS     {
        tmnxWlanGwVlanDsmAaHttpUrlParam
    }
    STATUS      current
    DESCRIPTION
        "The group of objects providing Application Assurance specific
         configuration of WLAN Gateway RADIUS-less authentication of User
         Equipment on Nokia SROS series systems."
    ::= { tmnxWlanGwGroups 56 }

tmnxWlanGwSoftGreV22v0Group      OBJECT-GROUP
    OBJECTS     {
        tmnxWlanGwSoftGreIfLastCh,
        tmnxWlanGwSoftGreIfAdminState,
        tmnxWlanGwSoftGreIfRouter,
        tmnxWlanGwSoftGreIfGwAddrType,
        tmnxWlanGwSoftGreIfGwAddr,
        tmnxWlanGwSoftGreIfGrpId,
        tmnxWlanGwSoftGreIfShapingType,
        tmnxWlanGwSoftGreIfShapeMultiUe,
        tmnxWlanGwSoftGreIfEQosPlcy,
        tmnxWlanGwSoftGreIfESchedPlcy,
        tmnxWlanGwSoftGreIfEAggRateLimit,
        tmnxWlanGwSoftGreIfMobTrigger,
        tmnxWlanGwSoftGreIfMobHoldTime,
        tmnxWlanGwSoftGreIfTcpMssAdjust,
        tmnxWlanGwSoftGreIfEHoldTime,
        tmnxWlanGwSoftGreIfNumSoftGreTu,
        tmnxWlanGwSoftGreIfTableLastCh,
        tmnxWlanGwSoftGreTuEstabTime,
        tmnxWlanGwSoftGreTuIsaGroup,
        tmnxWlanGwSoftGreTuIsaMember,
        tmnxWlanGwSoftGreTuNumUe,
        tmnxWlanGwTuQosEegSvcId,
        tmnxWlanGwTuQosEegPortId,
        tmnxWlanGwTuQosEegEncapValue,
        tmnxWlanGwTuQosEegName,
        tmnxWlanGwTuQosEegMember,
        tmnxWlanGwTuQosState,
        tmnxWlanGwTuQosNumUe,
        tmnxWlanGwTuQosRemainingHoldTime,
        tmnxWlanGwSoftGreTuUeSsid,
        tmnxWlanGwSoftGreIfGwV6AddrType,
        tmnxWlanGwSoftGreIfGwV6Addr,
        tmnxWlanGwVlanTableLastCh,
        tmnxWlanGwVlanLastCh,
        tmnxWlanGwVlanRowStatus,
        tmnxWlanGwVlanRetailService,
        tmnxWlanGwVlanDhcp,
        tmnxWlanGwVlanAddrType,
        tmnxWlanGwVlanAddr,
        tmnxWlanGwVlanLeaseTime,
        tmnxWlanGwVlanActLeaseTime,
        tmnxWlanGwVlanDns1AddrType,
        tmnxWlanGwVlanDns1Addr,
        tmnxWlanGwVlanDns2AddrType,
        tmnxWlanGwVlanDns2Addr,
        tmnxWlanGwVlanNb1AddrType,
        tmnxWlanGwVlanNb1Addr,
        tmnxWlanGwVlanNb2AddrType,
        tmnxWlanGwVlanNb2Addr,
        tmnxWlanGwVlanHttpRdrPlcy,
        tmnxWlanGwVlanNatPlcy,
        tmnxWlanGwVlanDataTrigg,
        tmnxWlanGwVlanAuthPlcy,
        tmnxWlanGwVlanAuthHoldTime,
        tmnxWlanGwVlanRadProxVrtr,
        tmnxWlanGwVlanRadProxSrv,
        tmnxWlanGwVlanRadProxMacFmt,
        tmnxWlanGwSoftGreIfDownIfGrpDeg
    }
    STATUS      current
    DESCRIPTION
        "The group of objects providing configuration of WLAN Gateway Soft GRE
         group interfaces on Nokia SROS series systems, supported in release
         22."
    ::= { tmnxWlanGwGroups 58 }

tmnxWlanGwDynL2WholesaleGroup    OBJECT-GROUP
    OBJECTS     {
        tmnxWlanGwVlanDynService,
        tmnxWlanGwVplsWlanGwGrpId,
        tmnxWlanGwUeResL2Service
    }
    STATUS      current
    DESCRIPTION
        "The group of objects providing configuration of WLAN Gateway  Dynamic
         Layer 2 Wholesale on Nokia SROS series systems."
    ::= { tmnxWlanGwGroups 59 }

tmnxWlanGwObsoletedGroup         OBJECT-GROUP
    OBJECTS     {
        tmnxWlanGwMgwCacheTtl,
        tmnxWlanGwIfRetailRowStatus,
        tmnxWlanGwIfRetailLastCh,
        tmnxWlanGwIfRetailService,
        tmnxWlanGwIfRetailTableLastCh,
        tmnxWlanGwSoftGreIfDataTrigg,
        tmnxWlanGwSoftGreIfAuthPlcy,
        tmnxWlanGwSoftGreIfAuthHoldTime,
        tmnxWlanGwSoftGreIfRadProxVrtr,
        tmnxWlanGwSoftGreIfRadProxSrv,
        tmnxWlanGwSoftGreIfRadProxMacFmt,
        tmnxWlanGwSoftGreXtLastCh,
        tmnxWlanGwSoftGreXtDhcp,
        tmnxWlanGwSoftGreXtAddrType,
        tmnxWlanGwSoftGreXtAddr,
        tmnxWlanGwSoftGreXtLeaseTime,
        tmnxWlanGwSoftGreXtActLeaseTime,
        tmnxWlanGwSoftGreXtDns1AddrType,
        tmnxWlanGwSoftGreXtDns1Addr,
        tmnxWlanGwSoftGreXtDns2AddrType,
        tmnxWlanGwSoftGreXtDns2Addr,
        tmnxWlanGwSoftGreXtNb1AddrType,
        tmnxWlanGwSoftGreXtNb1Addr,
        tmnxWlanGwSoftGreXtNb2AddrType,
        tmnxWlanGwSoftGreXtNb2Addr,
        tmnxWlanGwSoftGreXtHttpRdrPlcy,
        tmnxWlanGwSoftGreXtNatPlcy,
        tmnxWlanGwIsaMemberStatsName,
        tmnxWlanGwIsaMemberStatsVal,
        tmnxWlanGwIsaMemberStatsValHw,
        tmnxWlanGwIsaMemberStatsValue,
        tmnxWlanGwSoftGreIfDefRetailSvc
    }
    STATUS      current
    DESCRIPTION
        "The group of obsoleted WLAN Gateway objects on Nokia SROS series
         systems."
    ::= { tmnxWlanGwGroups 98 }

tmnxWlanGwNotifyObjsGroup        OBJECT-GROUP
    OBJECTS     {
        tmnxWlanGwNotifyDescription,
        tmnxWlanGwNotifyTrue,
        tmnxWlanGwNotify3gppRelease,
        tmnxWlanGwNotifyMdaSlotNum,
        tmnxWlanGwNotifySubIfIndex,
        tmnxWlanGwNotifyAddrFamily,
        tmnxWlanGwNotifyIsaGrpId,
        tmnxWlanGwNotifyIsaMemberId,
        tmnxWlanGwNotifyD6cServer1,
        tmnxWlanGwNotifyD6cServer2,
        tmnxWlanGwNotifyD6cServer3,
        tmnxWlanGwNotifyD6cServer4,
        tmnxWlanGwNotifyD6cServer5,
        tmnxWlanGwNotifyD6cServer6,
        tmnxWlanGwNotifyD6cServer7,
        tmnxWlanGwNotifyD6cServer8,
        tmnxWlanGwNotifySubnetAddrType,
        tmnxWlanGwNotifySubnetAddr,
        tmnxWlanGwNotifySubnetPrefLen,
        tmnxWlanGwNotifyGtpMsgType,
        tmnxWlanGwNotifyGtpMsgDirection,
        tmnxWlanGwNotifyImsi,
        tmnxWlanGwNotifyTeid
    }
    STATUS      current
    DESCRIPTION
        "The group of notification objects supporting WLAN Gateway
         notifications on Nokia SROS series systems."
    ::= { tmnxWlanGwGroups 99 }

tmnxWlanGwNotifyGroup            NOTIFICATION-GROUP
    NOTIFICATIONS {
        tmnxWlanGwResrcProblemDetected,
        tmnxWlanGwResrcProblemCause,
        tmnxWlanGwTuQosProblem,
        tmnxWlanGwGrpOperStateChanged,
        tmnxWlanGwIomActive,
        tmnxWlanGwMgwConnected,
        tmnxWlanGwMgwRestarted,
        tmnxWlanGwNumMgwHi,
        tmnxWlanGwMgwStateChanged,
        tmnxWlanGwQosRadiusGtpMismatch,
        tmnxWlanGwDsmGtpTunnelSetupFail,
        tmnxWlanGwSubIfRedActiveChanged,
        tmnxWlanGwSubIfPmStartD6cFailed,
        tmnxWlanGwSubIfPmNewPlReqFailed,
        tmnxWlanGwSubIfPmAddNewPlFailed,
        tmnxWlanGwSubIfPmCrIntObjFailed,
        tmnxWlanGwSubIfPmPoolTimeout,
        tmnxWlanGwSubIfPmPoolUsageLow,
        tmnxWlanGwSubIfPmLsQryRtryFailed,
        tmnxWlanGwGtpMessageDropped,
        tmnxWlanGwSubIfPmPoolPartialUse
    }
    STATUS      current
    DESCRIPTION
        "The group of notifications supporting WLAN Gateway on Nokia SROS
         series systems."
    ::= { tmnxWlanGwGroups 100 }

tmnxGtpCompliances               OBJECT IDENTIFIER ::= { tmnxWlanGwConformance 3 }

tmnxGtpV15Compliance             MODULE-COMPLIANCE
    STATUS      current
    DESCRIPTION
        "The compliance statement for management of the GPRS Tunnel Protocol
         (GTP) on Nokia 7xxx series systems release 15.0."
    MODULE
        MANDATORY-GROUPS {
            tmnxGtpV15v0Group
        }
    ::= { tmnxGtpCompliances 1 }

tmnxGtpV16Compliance             MODULE-COMPLIANCE
    STATUS      current
    DESCRIPTION
        "The compliance statement for management of the GPRS Tunnel Protocol
         (GTP) on Nokia 7xxx series systems release 16.0."
    MODULE
        MANDATORY-GROUPS {
            tmnxGtpAccV16v0Group,
            tmnxGtpAccMobV16v0Group,
            tmnxGtpAccMobChngRepV16v0Group,
            tmnxGtpAccMobUliV16v0Group,
            tmnxGtpNumSessionV16v0Group
        }
    ::= { tmnxGtpCompliances 2 }

tmnxGtpCupsUpCompliance          MODULE-COMPLIANCE
    STATUS      current
    DESCRIPTION
        "The compliance statement for management of the CUPS GPRS Tunnel
         Protocol (GTP) on Nokia 7xxx series systems."
    MODULE
        MANDATORY-GROUPS {
            tmnxGtpSubCupsUpFwaGroup
        }
    ::= { tmnxGtpCompliances 3 }

tmnxWlanGwNotifyObjsV15v0Group   OBJECT-GROUP
    OBJECTS     {
        tmnxWlanGwNotifyBdBridgeId,
        tmnxWlanGwNotifyUeMacAddress
    }
    STATUS      current
    DESCRIPTION
        "The group of notification objects supporting WLAN Gateway
         notifications on Nokia SROS series systems in release 15.0."
    ::= { tmnxGtpCompliances 101 }

tmnxWlanGwNotifyV15v0Group       NOTIFICATION-GROUP
    NOTIFICATIONS {
        tmnxWlanGwBdCreated,
        tmnxWlanGwBdDeleted,
        tmnxWlanGwUeCreationFail,
        tmnxWlanGwUeReplacement
    }
    STATUS      current
    DESCRIPTION
        "The group of notifications supporting WLAN Gateway on Nokia SROS
         series systems in release 15.0."
    ::= { tmnxGtpCompliances 102 }

tmnxWlanGwNotifyObjsV16v0Group   OBJECT-GROUP
    OBJECTS     {
        tmnxWlanGwNotifyChassisIndex,
        tmnxWlanGwNotifyCardSlotNum,
        tmnxWlanGwNotifyEntity
    }
    STATUS      current
    DESCRIPTION
        "The group of notification objects supporting WLAN Gateway
         notifications on Nokia SROS series systems added in release 16.0."
    ::= { tmnxGtpCompliances 103 }

tmnxWlanGwNotifyV16v0Group       NOTIFICATION-GROUP
    NOTIFICATIONS {
        tmnxWlanGwGrpMemberUsageHigh
    }
    STATUS      current
    DESCRIPTION
        "The group of notifications supporting WLAN Gateway on Nokia SROS
         series systems added in release 16.0."
    ::= { tmnxGtpCompliances 104 }

tmnxWlanGwNotifyObjsV19v0Group   OBJECT-GROUP
    OBJECTS     {
        tmnxWlanGwNotifyEsaNum,
        tmnxWlanGwNotifyEsaVappNum
    }
    STATUS      current
    DESCRIPTION
        "The group of notification objects supporting WLAN Gateway
         notifications on Nokia SROS series systems added in release 19.0."
    ::= { tmnxGtpCompliances 105 }

tmnxGtpGroups                    OBJECT IDENTIFIER ::= { tmnxWlanGwConformance 4 }

tmnxGtpV15v0Group                OBJECT-GROUP
    OBJECTS     {
        tmnxGtpS11ItfTableLastChanged,
        tmnxGtpS11ItfRowStatus,
        tmnxGtpS11ItfLastChanged,
        tmnxGtpS11ItfApnPolicyName,
        tmnxGtpPpmTableLastChanged,
        tmnxGtpPpmRowStatus,
        tmnxGtpPpmLastChanged,
        tmnxGtpPpmProfileName,
        tmnxGtpS11SeTableLastChanged,
        tmnxGtpS11SePeerRouter,
        tmnxGtpS11SePeerAddrType,
        tmnxGtpS11SePeerAddr,
        tmnxGtpS11SeRemoteCtrlTeid,
        tmnxGtpS11SeLocalCtrlTeid,
        tmnxGtpS11SeChrgChar,
        tmnxGtpS11SeQosUplinkAmbr,
        tmnxGtpS11SeQosDwnlinkAmbr,
        tmnxGtpS11BcTableLastChanged,
        tmnxGtpS11BcRemoteTeid,
        tmnxGtpS11BcLocalTeid,
        tmnxGtpS11BcQosUlGbr,
        tmnxGtpS11BcQosUlMbr,
        tmnxGtpS11BcQosDlGbr,
        tmnxGtpS11BcQosDlMbr,
        tmnxGtpS11BcQosQci,
        tmnxGtpS11BcQosArp,
        tmnxGtpS11BcRemoteAddrType,
        tmnxGtpS11BcRemoteAddr,
        tmnxWlanGwMmeTableLastChanged,
        tmnxWlanGwMmeLastChanged,
        tmnxWlanGwMmeQosUplinkGbrRate,
        tmnxWlanGwMmeQosUplinkMbrRate,
        tmnxWlanGwMmeQosDwnlinkGbrRate,
        tmnxWlanGwMmeQosDwnlinkMbrRate,
        tmnxWlanGwMmeQosArpValue,
        tmnxWlanGwMmeQosQciValue,
        tmnxWlanGwMmeQosUplinkAmbr,
        tmnxWlanGwMmeQosDwnlinkAmbr,
        tmnxGtpNumMme,
        tmnxGtpNumEnodeB,
        tmnxGtpNumS11Sessions,
        tmnxGtpNumUplinks,
        tmnxGtpUplinkTableLastChanged,
        tmnxGtpUplinkRowStatus,
        tmnxGtpUplinkLastChanged,
        tmnxGtpUplinkApn,
        tmnxGtpUplinkPdnType,
        tmnxWlanGwMgwProfIpv4Mtu
    }
    STATUS      current
    DESCRIPTION
        "The group of objects providing management of the GPRS Tunnel Protocol
         (GTP) on Nokia SROS series systems in release 15.0."
    ::= { tmnxGtpGroups 1 }

tmnxGtpAccMobV16v0Group          OBJECT-GROUP
    OBJECTS     {
        tmnxWlanGwMgwProfEndMarkerCount
    }
    STATUS      current
    DESCRIPTION
        "The group of objects providing management of the GPRS Tunnel Protocol
         (GTP) for Access Mobility on Nokia SROS series systems in release
         16.0."
    ::= { tmnxGtpGroups 2 }

tmnxGtpAccMobChngRepV16v0Group   OBJECT-GROUP
    OBJECTS     {
        tmnxWlanGwMgwProfChangeRepAction
    }
    STATUS      current
    DESCRIPTION
        "The group of objects providing management of the GPRS Tunnel Protocol
         (GTP) for Access Mobility Change Reporting on Nokia SROS series
         systems in release 16.0."
    ::= { tmnxGtpGroups 3 }

tmnxGtpAccV16v0Group             OBJECT-GROUP
    OBJECTS     {
        tmnxGtpS11SePdnTeid
    }
    STATUS      current
    DESCRIPTION
        "The group of objects providing management of the GPRS Tunnel Protocol
         (GTP) on Nokia SROS series systems in release 16.0."
    ::= { tmnxGtpGroups 4 }

tmnxGtpAccMobUliV16v0Group       OBJECT-GROUP
    OBJECTS     {
        tmnxGtpS11SeUliCgi,
        tmnxGtpS11SeUliSai,
        tmnxGtpS11SeUliRai,
        tmnxGtpS11SeUliTai,
        tmnxGtpS11SeUliEcgi
    }
    STATUS      current
    DESCRIPTION
        "The group of objects providing management of the GTP Access Mobility
         User Location Information on Nokia SROS series systems in release
         16.0."
    ::= { tmnxGtpGroups 5 }

tmnxGtpNumSessionV16v0Group      OBJECT-GROUP
    OBJECTS     {
        tmnxGtpNumS11IdleSessions
    }
    STATUS      current
    DESCRIPTION
        "The group of objects providing management of the GTP Number of
         sessions on Nokia SROS series systems in release 16.0."
    ::= { tmnxGtpGroups 6 }

tmnxGtpSubCupsUpFwaGroup         OBJECT-GROUP
    OBJECTS     {
        tmnxGtpUpfDataEpTableLastChanged,
        tmnxGtpUpfDataEndptRowStatus,
        tmnxGtpUpfDataEndptLastChanged,
        tmnxGtpUpfDataEndptItfName,
        tmnxGtpUpfDataEndpFpeId
    }
    STATUS      current
    DESCRIPTION
        "The group of objects providing management of the GTP upf data endpoint
         configuration on Nokia SROS series systems."
    ::= { tmnxGtpGroups 7 }

tmnxWlanGwNotifyPrefix           OBJECT IDENTIFIER ::= { tmnxSRNotifyPrefix 81 }

tmnxWlanGwNotifications          OBJECT IDENTIFIER ::= { tmnxWlanGwNotifyPrefix 0 }

tmnxWlanGwResrcProblemDetected   NOTIFICATION-TYPE
    OBJECTS     {
        tmnxWlanGwResrcProblem
    }
    STATUS      current
    DESCRIPTION
        "The tmnxWlanGwResrcProblemDetected notification is sent when the value
         of the object tmnxWlanGwResrcProblem changes."
    ::= { tmnxWlanGwNotifications 1 }

tmnxWlanGwResrcProblemCause      NOTIFICATION-TYPE
    OBJECTS     {
        tmnxWlanGwNotifyDescription
    }
    STATUS      current
    DESCRIPTION
        "The tmnxWlanGwResrcProblemCause notification is sent to describe the
         cause of a WLAN Gateway resource problem."
    ::= { tmnxWlanGwNotifications 2 }

tmnxWlanGwTuQosProblem           NOTIFICATION-TYPE
    OBJECTS     {
        tmnxWlanGwIsaMemberTuQosProblem
    }
    STATUS      current
    DESCRIPTION
        "The tmnxWlanGwTuQosProblem notification is sent when the value of the
         object tmnxWlanGwIsaMemberTuQosProblem changes from or to zero for
         some member of a WLAN Gateway ISA Group in the system.

         [CAUSE] While creating a WLAN Gateway tunnel QoS infrastructure
         instance, there was a resource issue.

         [EFFECT] There are UE with a QoS infrastructure that does not match
         the configuration, for example: no shaper was instantiated.

         [RECOVERY] This may be a temporary phenomenon.

         If it persists, the QoS configuration or the scaling may have to be
         modified to ensure enough resources are available for the UE QoS."
    ::= { tmnxWlanGwNotifications 3 }

tmnxWlanGwGrpOperStateChanged    NOTIFICATION-TYPE
    OBJECTS     {
        tmnxWlanGwGrpOperState
    }
    STATUS      current
    DESCRIPTION
        "The tmnxWlanGwGrpOperStateChanged notification is sent when the value
         of the object tmnxWlanGwGrpOperState changes."
    ::= { tmnxWlanGwNotifications 4 }

tmnxWlanGwIomActive              NOTIFICATION-TYPE
    OBJECTS     {
        tmnxWlanGwIomLastMgmtChange,
        tmnxWlanGwNotifyTrue
    }
    STATUS      current
    DESCRIPTION
        "The tmnxWlanGwIomActive notification is sent when the value of the
         object tmnxWlanGwIomOperState changes from 'primary' to any other
         value, or the other way around.

         The value 'primary' means that the IOM is active in the group."
    ::= { tmnxWlanGwNotifications 5 }

tmnxWlanGwMgwConnected           NOTIFICATION-TYPE
    OBJECTS     {
        tmnxWlanGwMgwTime,
        tmnxWlanGwNotifyTrue
    }
    STATUS      current
    DESCRIPTION
        "The tmnxWlanGwMgwConnected notification is sent when this system adds
         a conceptual row to the tmnxWlanGwMgwTable, or removes it.

         [CAUSE] A connection is established between this system's WLAN Gateway
         function and a Mobile Gateway, or such a connection disappears.

         The interruption of a connection with a Mobile Gateway can be the
         expected result of a management action on the Mobile Gateway, or it
         can be caused by a network failure.

         [EFFECT] While there is a connection with a particular Mobile Gateway,
         User Equipment (UE) belonging to the associated PLMN (Public Land
         Mobile Network) and serviced by this WLAN Gateway can be connected to
         their Home PLMN.

         [RECOVERY] If a connection with a Mobile Gateway is interrupted as the
         expected result of a management action, no recovery is required."
    ::= { tmnxWlanGwNotifications 10 }

tmnxWlanGwMgwRestarted           NOTIFICATION-TYPE
    OBJECTS     {
        tmnxWlanGwMgwRestartCnt
    }
    STATUS      current
    DESCRIPTION
        "The tmnxWlanGwMgwRestarted notification is sent when this system
         learns that a Mobile Gateway has restarted.

         [CAUSE] A Mobile Gateway known to this system has restarted, has
         transmitted its restart counter to this system and it was found to be
         higher than its previously known value.

         [EFFECT] This system clears all sessions associated with the restarted
         Mobile Gateway (because that Mobile Gateway has lost its session data
         anyway).

         [RECOVERY] No recovery is required on this system."
    ::= { tmnxWlanGwNotifications 11 }

tmnxWlanGwNumMgwHi               NOTIFICATION-TYPE
    OBJECTS     {
        tmnxWlanGwNumMgw,
        tmnxWlanGwNotifyTrue
    }
    STATUS      current
    DESCRIPTION
        "The tmnxWlanGwNumMgwHi notification is sent when the value of
         tmnxWlanGwNumMgw reaches its high watermark ('true') or when it
         reaches its low watermark again ('false'). The value of the object
         tmnxWlanGwNumMgw indicates the actual number of Mobile Gateways
         connected to this system.

         The description below applies to the notification when sent with the
         value of 'true'.

         [CAUSE] The number of Mobile Gateways connected to this system is
         approaching the maximum supported value.

         [EFFECT] If the increasing trend continues, this system will not be
         able to connect some User Equipment (UE) with their Home PLMN.

         [RECOVERY] The network configuration may have to be modified such that
         this system will be associated with less Mobile Gateways."
    ::= { tmnxWlanGwNotifications 12 }

tmnxWlanGwMgwStateChanged        NOTIFICATION-TYPE
    OBJECTS     {
        tmnxWlanGwMgwState
    }
    STATUS      current
    DESCRIPTION
        "The tmnxWlanGwMgwStateChanged notification is sent when the state of a
         connection with a Mobile Gateway has changed.

         [CAUSE] The state of a connection with a Mobile Gateway has changed.

         [EFFECT] The effect depends on the new state.

         [RECOVERY] No recovery is required on this system."
    ::= { tmnxWlanGwNotifications 13 }

tmnxWlanGwQosRadiusGtpMismatch   NOTIFICATION-TYPE
    OBJECTS     {
        tmnxWlanGwMgwInterfaceType,
        tmnxWlanGwNotify3gppRelease
    }
    STATUS      current
    DESCRIPTION
        "The tmnxWlanGwQosRadiusGtpMismatch notification is sent when the
         Negotiated QoS profile RADIUS attribute contains a release indicator
         either for GGSN or PGW that does not correspond to the interface type
         actually used in GTP. e.g. the release indicator is for GGSN and the
         interface type used in GTP is S2a/S2b while it should be Gn.

         [CAUSE] Inconsistency between the release indicator in the RADIUS
         attribute and the GTP interface type.

         [EFFECT] The QoS values in the tmnxWlanGwPgwTable or the
         tmnxWlanGwGgsnTable of the conceptual row corresponding to the row in
         the tmnxWlanGwMgwAddrTable that matches the WLAN are used instead.

         [RECOVERY] The RADIUS Server configuration should be corrected."
    ::= { tmnxWlanGwNotifications 14 }

tmnxWlanGwSubIfRedActiveChanged  NOTIFICATION-TYPE
    OBJECTS     {
        tmnxWlanGwSubIfRedActive,
        tmnxWlanGwNotifyDescription
    }
    STATUS      current
    DESCRIPTION
        "The tmnxWlanGwSubIfRedActiveChanged notification is sent when the
         value of the object tmnxWlanGwSubIfRedActive has changed.

         [CAUSE] The tmnxWlanGwSubIfRedActiveChanged notification is sent when
         the value of the object tmnxWlanGwSubIfRedActive changes. The cause is
         explained in the tmnxWlanGwNotifyDescription.

         [EFFECT] While the value of the object tmnxWlanGwSubIfRedActive is equal to 'false', ...
         - this system is not performing Wifi Offload in the realm of this subscriber interface;
         the Wifi Offload functionality is supposed to be performed by its redundant peer.
         - this subscriber interface and all the group interfaces contained within this subscriber interface
         are operationally down;
         - for all group interfaces contained within this subscriber interface, the addresses
         specified in tmnxWlanGwSoftGreIfGwAddr and tmnxWlanGwSoftGreIfGwV6Addr are
         not advertised in the realm of the virtual router instance
         where the tunneled User Equipment traffic is routed;
         - the route specified with tmnxWlanGwSubIfRedExpPrefix is not exported
         in the realm of the virtual router instance associated with this subscriber interface.

         [RECOVERY] No recovery is required on this system."
    ::= { tmnxWlanGwNotifications 15 }

tmnxWlanGwDsmGtpTunnelSetupFail  NOTIFICATION-TYPE
    OBJECTS     {
        tmnxWlanGwIomRowStatus,
        tmnxWlanGwNotifyMdaSlotNum,
        tmnxWlanGwNotifyDescription
    }
    STATUS      current
    DESCRIPTION
        "The tmnxWlanGwDsmGtpTunnelSetupFail notification is sent when a
         problem occurred while trying to setup a GTP tunnel for a DSM
         subscriber.

         [CAUSE] A problem occurred while trying to setup a GTP tunnel for a
         DSM subscriber.

         This can be caused by:
         - incomplete system configuration, or
         - inconsistent RADIUS configuration, or
         - because the GTP peer is not reachable.

         [EFFECT] The DSM subscriber cannot establish a connection with his
         home mobile network.

         [RECOVERY] Depending on the cause, correct the system configuration,
         the RADIUS configuration or the network connectivity."
    ::= { tmnxWlanGwNotifications 16 }

tmnxWlanGwSubIfPmStartD6cFailed  NOTIFICATION-TYPE
    OBJECTS     {
        svcId,
        tmnxWlanGwNotifySubIfIndex,
        tmnxWlanGwNotifyAddrFamily,
        tmnxWlanGwNotifyIsaGrpId,
        tmnxWlanGwNotifyIsaMemberId,
        tmnxWlanGwNotifyDescription
    }
    STATUS      current
    DESCRIPTION
        "The tmnxWlanGwSubIfPmStartD6cFailed notification is sent when a DHCPv6
         client of the Pool Manager failed to start.

         [CAUSE] Failed to start a DHCPv6 client.

         [EFFECT] No pools can be requested for this ISA-BB.

         [RECOVERY] Perform a shutdown/no shutdown of the DHCPv6 client."
    ::= { tmnxWlanGwNotifications 17 }

tmnxWlanGwSubIfPmNewPlReqFailed  NOTIFICATION-TYPE
    OBJECTS     {
        svcId,
        tmnxWlanGwNotifySubIfIndex,
        tmnxWlanGwNotifyAddrFamily,
        tmnxWlanGwNotifyIsaGrpId,
        tmnxWlanGwNotifyIsaMemberId,
        tmnxWlanGwNotifyDescription
    }
    STATUS      current
    DESCRIPTION
        "The tmnxWlanGwSubIfPmNewPlReqFailed notification is sent when sending
         a request for a new pool is failing. (For example, when a DHCPv6
         server is unreachable.)

         [CAUSE] Failed to send a request for a new pool.

         [EFFECT] The ISA-BB may run out of free DHCPv6 addresses or SLAAC
         prefixes.

         [RECOVERY] No recovery is needed. Retry periodically."
    ::= { tmnxWlanGwNotifications 18 }

tmnxWlanGwSubIfPmAddNewPlFailed  NOTIFICATION-TYPE
    OBJECTS     {
        svcId,
        tmnxWlanGwNotifySubnetAddrType,
        tmnxWlanGwNotifySubnetAddr,
        tmnxWlanGwNotifySubnetPrefLen,
        tmnxWlanGwNotifySubIfIndex,
        tmnxWlanGwNotifyAddrFamily,
        tmnxWlanGwNotifyIsaGrpId,
        tmnxWlanGwNotifyIsaMemberId,
        tmnxWlanGwNotifyDescription
    }
    STATUS      current
    DESCRIPTION
        "The tmnxWlanGwSubIfPmAddNewPlFailed notification is sent when adding a
         new pool, given by the DHCPv6 server, is failing.
         (Examples : conflict with existing pool, subnet too small,
          maximum number of pools reached, out of memory, etc.)

         [CAUSE] Failed to add a new pool given by the server.

         [EFFECT] The ISA-BB may run out of free DHCPv6 addresses or SLAAC
         prefixes.

         [RECOVERY] No recovery is needed. Retry periodically."
    ::= { tmnxWlanGwNotifications 19 }

tmnxWlanGwSubIfPmCrIntObjFailed  NOTIFICATION-TYPE
    OBJECTS     {
        svcId,
        tmnxWlanGwSubIfIpsSubnetAddrType,
        tmnxWlanGwSubIfIpsSubnetAddr,
        tmnxWlanGwSubIfIpsSubnetPrefLen,
        tmnxWlanGwSubIfIpsSubIfIndex,
        tmnxWlanGwNotifyAddrFamily,
        tmnxWlanGwNotifyDescription
    }
    STATUS      current
    DESCRIPTION
        "The tmnxWlanGwSubIfPmCrIntObjFailed notification is sent when the
         creation of an internal object for a pool is failing.

         [CAUSE] Failed to create an internal object for a pool.

         [EFFECT] Forwarding will not work for UEs having an address/prefix
         from this pool.

         [RECOVERY] No recovery is needed. Retry periodically."
    ::= { tmnxWlanGwNotifications 20 }

tmnxWlanGwSubIfPmPoolTimeout     NOTIFICATION-TYPE
    OBJECTS     {
        tmnxWlanGwSubIfIpsRemLeaseTime,
        tmnxWlanGwNotifyAddrFamily,
        tmnxWlanGwNotifyDescription
    }
    STATUS      current
    DESCRIPTION
        "The tmnxWlanGwSubIfPmPoolTimeout notification is sent when a pool is
         timing out unexpectedly.

         [CAUSE] Pool timed out unexpectedly.

         [EFFECT] The pool is removed from the ISA-BB together with all
         associated UEs.

         [RECOVERY] No recovery possible."
    ::= { tmnxWlanGwNotifications 21 }

tmnxWlanGwSubIfPmPoolUsageLow    NOTIFICATION-TYPE
    OBJECTS     {
        tmnxWlanGwSubIfIpsUsageLevelPct,
        tmnxWlanGwNotifyAddrFamily
    }
    STATUS      current
    DESCRIPTION
        "The tmnxWlanGwSubIfPmPoolUsageLow notification is sent when the usage
         of a pool drops below 1%

         [CAUSE] Pool usage dropped below 1%.

         [EFFECT] The pool has become stale.

         [RECOVERY] Manually clear the pool."
    ::= { tmnxWlanGwNotifications 22 }

tmnxWlanGwSubIfPmLsQryRtryFailed NOTIFICATION-TYPE
    OBJECTS     {
        svcId,
        tmnxWlanGwNotifySubIfIndex,
        tmnxWlanGwNotifyAddrFamily,
        tmnxWlanGwNotifyIsaGrpId,
        tmnxWlanGwNotifyIsaMemberId,
        tmnxWlanGwNotifyDescription,
        tmnxWlanGwNotifyD6cServer1,
        tmnxWlanGwNotifyD6cServer2,
        tmnxWlanGwNotifyD6cServer3,
        tmnxWlanGwNotifyD6cServer4,
        tmnxWlanGwNotifyD6cServer5,
        tmnxWlanGwNotifyD6cServer6,
        tmnxWlanGwNotifyD6cServer7,
        tmnxWlanGwNotifyD6cServer8
    }
    STATUS      current
    DESCRIPTION
        "The tmnxWlanGwSubIfPmLsQryRtryFailed notification is sent when the
         lease query retry fails.

         [CAUSE] Lease query retry failed.

         [EFFECT] The old prefix couldn't be fetched from the DHCP server.

         [RECOVERY] No recovery possible."
    ::= { tmnxWlanGwNotifications 23 }

tmnxWlanGwGtpMessageDropped      NOTIFICATION-TYPE
    OBJECTS     {
        tmnxWlanGwMgwControl,
        tmnxWlanGwNotifyGtpMsgType,
        tmnxWlanGwNotifyGtpMsgDirection,
        tmnxWlanGwNotifyImsi,
        tmnxWlanGwNotifyTeid,
        tmnxWlanGwNotifyDescription
    }
    STATUS      current
    DESCRIPTION
        "The tmnxWlanGwGtpMessageDropped notification is sent when the system
         drops a GTP message while attempting to receive or transmit it.

         If available, the International Mobile Subscriber Identity (IMSI) in
         the GTP message is indicated in the tmnxWlanGwNotifyImsi.

         If available, the local control plane Tunnel Endpoint Identifier
         (TEID) in the GTP message is indicated in the tmnxWlanGwNotifyTeid.

         [CAUSE] The cause is indicated in the tmnxWlanGwNotifyDescription.

         [EFFECT] The effect depends on the dropped message and the state of
         the system.

         [RECOVERY] The recovery, if any, depends on the reason the message was
         dropped."
    ::= { tmnxWlanGwNotifications 24 }

tmnxWlanGwSubIfPmPoolPartialUse  NOTIFICATION-TYPE
    OBJECTS     {
        svcId,
        tmnxWlanGwNotifySubIfIndex,
        tmnxWlanGwNotifyAddrFamily,
        tmnxWlanGwNotifyIsaGrpId,
        tmnxWlanGwNotifyIsaMemberId,
        tmnxWlanGwNotifyDescription
    }
    STATUS      current
    DESCRIPTION
        "The tmnxWlanGwSubIfPmPoolPartialUse notification is sent when the
         server delegated prefix length maximum and the downlink subnet length
         on the ISA does not match.

         [CAUSE] The server delegated prefix length does not match the ISA
         subnet length.

         [EFFECT] An incomplete usage of the delegated prefix results in a loss
         of applicable IP addresses.

         [RECOVERY] Configure the delegated prefix length maximum to match the
         ISA subnet length."
    ::= { tmnxWlanGwNotifications 25 }

tmnxWlanGwBdCreated              NOTIFICATION-TYPE
    OBJECTS     {
        tmnxWlanGwNotifyBdBridgeId
    }
    STATUS      current
    DESCRIPTION
        "[CAUSE] The system issues the tmnxWlanGwBdCreated notification when it
         creates a conceptual row in the tmnxWlanGwBdTable.

         [EFFECT] The system is aware of a WLAN Gateway Bridge Domain and has
         context for it.

         [RECOVERY] Not required. This notification is informational."
    ::= { tmnxWlanGwNotifications 26 }

tmnxWlanGwBdDeleted              NOTIFICATION-TYPE
    OBJECTS     {
        tmnxWlanGwNotifyBdBridgeId
    }
    STATUS      current
    DESCRIPTION
        "[CAUSE] The system issues the tmnxWlanGwBdDeleted notification when it
         destroys a conceptual row in the tmnxWlanGwBdTable.

         [EFFECT] The system has become unaware of a WLAN Gateway Bridge
         Domain.

         [RECOVERY] Recovery may or may not be required, depending of the
         cause."
    ::= { tmnxWlanGwNotifications 27 }

tmnxWlanGwUeCreationFail         NOTIFICATION-TYPE
    OBJECTS     {
        tmnxWlanGwNotifyBdBridgeId,
        tmnxWlanGwNotifyUeMacAddress,
        tmnxWlanGwNotifyDescription
    }
    STATUS      current
    DESCRIPTION
        "[CAUSE] The system issues the tmnxWlanGwUeCreationFail notification
         when the creation of a WLAN Gateway UE in tmnxWlanGwUeTable fails.

         [EFFECT] The WLAN Gateway UE was not created.

         [RECOVERY] Recovery may or may not be required, depending of the
         cause."
    ::= { tmnxWlanGwNotifications 28 }

tmnxWlanGwUeReplacement          NOTIFICATION-TYPE
    OBJECTS     {
        tmnxWlanGwNotifyBdBridgeId,
        tmnxWlanGwNotifyUeMacAddress,
        tmnxWlanGwNotifyDescription
    }
    STATUS      current
    DESCRIPTION
        "[CAUSE] The system issues the tmnxWlanGwUeReplacement notification
         when a UE has been removed in favor of another UE.

         [EFFECT] The WLAN Gateway UE was replaced.

         [RECOVERY] Recovery may or may not be required, depending of the
         cause."
    ::= { tmnxWlanGwNotifications 29 }

tmnxWlanGwGrpMemberUsageHigh     NOTIFICATION-TYPE
    OBJECTS     {
        tmnxWlanGwNotifyEntity,
        tmnxWlanGwNotifyTrue,
        tmnxWlanGwNotifyIsaGrpId,
        tmnxWlanGwNotifyIsaMemberId,
        tmnxWlanGwNotifyChassisIndex,
        tmnxWlanGwNotifyCardSlotNum,
        tmnxWlanGwNotifyMdaSlotNum,
        tmnxWlanGwNotifyEsaNum,
        tmnxWlanGwNotifyEsaVappNum
    }
    STATUS      current
    DESCRIPTION
        "[CAUSE] The tmnxWlanGwGrpMemberUsageHigh notification is sent when the
         usage of a particular entity on a WLAN Gateway ISA group member
         reaches its high watermark ('true') or when it reaches its low
         watermark again ('false'). [EFFECT] There is no immediate effect.
         [RECOVERY] No recovery is required."
    ::= { tmnxWlanGwNotifications 30 }

END
